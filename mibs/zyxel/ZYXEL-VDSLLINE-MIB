-- ZyXEL Communications Corporation
-- Private Enterprise MIB definition

-- $Log: zyxel-VDSL.mib $
-- Revision 1.2  2002/11/12 07:45:14  jennyhsu
-- Revision 1.1  2002/11/12 07:40:52  jennyhsu
-- Initial revision


ZYXEL-VDSLLINE-MIB DEFINITIONS ::= BEGIN

   IMPORTS
	vesSeriesCommon			FROM ZYXEL-MIB
    	Gauge, Counter, TimeTicks		FROM RFC1155-SMI
	OBJECT-TYPE 			FROM RFC-1212
	DisplayString 			FROM RFC1213-MIB
	RowStatus			FROM SNMPv2-TC;

   accessSwitchVdslLineMib OBJECT IDENTIFIER ::= { vesSeriesCommon 1 }

   accessSwitchVdslLineMibObjects OBJECT IDENTIFIER ::= { accessSwitchVdslLineMib 1 }

   accessSwitchVdslLCSMib  OBJECT IDENTIFIER ::= { accessSwitchVdslLineMib 2 }

   accessSwitchVdslLCSMibObjects OBJECT IDENTIFIER ::= { accessSwitchVdslLCSMib 1 }

   accessSwitchVdslLCSQam OBJECT IDENTIFIER ::= { accessSwitchVdslLCSMib 2 }


	 -- accessSwitch VDSL Line Table

   	 accessSwitchVdslLineTable   OBJECT-TYPE
             SYNTAX          SEQUENCE OF AccessSwitchVdslLineEntry
             ACCESS          not-accessible
             STATUS          mandatory
             DESCRIPTION
                 "This table includes common attributes describing both ends of the line."
         ::= { accessSwitchVdslLineMibObjects 1 }

         accessSwitchVdslLineEntry   OBJECT-TYPE
             SYNTAX          AccessSwitchVdslLineEntry
             ACCESS          not-accessible
             STATUS          mandatory
             DESCRIPTION     "An entry in the accessSwitchVdslLineTable."
             INDEX           { ifIndex }
         ::= { accessSwitchVdslLineTable 1 }

         AccessSwitchVdslLineEntry ::=
             SEQUENCE {
		accessSwitchVdslLineCoding	INTEGER,
		accessSwitchVdslLineDiscCount	Counter,
		accessSwitchVdslLineConfProfile	DisplayString
	     }

         accessSwitchVdslLineCoding OBJECT-TYPE
             SYNTAX  INTEGER {
                          other(1),	-- none of the following
                          dmt(2),	-- Discrete MultiTone
                          cap(3),	-- Carrierless Amplitude & Phase modulation
                          qam(4)	-- Quadrature Amplitude Modulation
                      }
             ACCESS  read-only
             STATUS  mandatory
             DESCRIPTION
                      "Specifies the VDSL coding type used on this line."
         ::= { accessSwitchVdslLineEntry 1 }

         accessSwitchVdslLineDiscCount OBJECT-TYPE
             SYNTAX  Counter
             ACCESS  read-only
             STATUS  mandatory
             DESCRIPTION
                      "Count of the number of disconnection failures since agent reset."
         ::= { accessSwitchVdslLineEntry 2 }

         accessSwitchVdslLineConfProfile OBJECT-TYPE
             SYNTAX  DisplayString (SIZE (1..32))
             ACCESS  read-write
             STATUS  mandatory
             DESCRIPTION
                      "The value of this object identifies the row
                      in the VDSL Line Configuration Profile Table,
                      (accessSwitchVdslLineConfProfileTable), which applies for this
                      VDSL line."
         ::= { accessSwitchVdslLineEntry 3 }


	 -- accessSwitch VDSL VTU-O Physical Table

   	 accessSwitchVdslVtuoPhysTable   OBJECT-TYPE
             SYNTAX          SEQUENCE OF AccessSwitchVdslVtuoPhysEntry
             ACCESS          not-accessible
             STATUS          mandatory
             DESCRIPTION
                 "This table provides one row for each VTU-O.
                 Each row contains the physical layer parameters for that VTU-O."
         ::= { accessSwitchVdslLineMibObjects 2 }

         accessSwitchVdslVtuoPhysEntry   OBJECT-TYPE
             SYNTAX          AccessSwitchVdslVtuoPhysEntry
             ACCESS          not-accessible
             STATUS          mandatory
             DESCRIPTION     "An entry in the accessSwitchVdslVtuoPhysTable."
             INDEX           { ifIndex }
         ::= { accessSwitchVdslVtuoPhysTable 1 }

         AccessSwitchVdslVtuoPhysEntry ::=
             SEQUENCE {
         	accessSwitchVdslVtuoCurrSnrMgn              INTEGER,
		accessSwitchVdslVtuoCurrMse		   INTEGER,
		accessSwitchVdslVtuoCurrPsd		   INTEGER,
		accessSwitchVdslVtuoCurrRsErr		   Counter,
         	accessSwitchVdslVtuoCurrAtn                 Gauge,
         	accessSwitchVdslVtuoCurrOutputPwr           INTEGER,
		accessSwitchVdslVtuoCurrRate		   INTEGER,
         	accessSwitchVdslVtuoCurrAttainableRate      Gauge,
         	accessSwitchVdslVtuoCurrStatus              INTEGER
             }

         accessSwitchVdslVtuoCurrSnrMgn OBJECT-TYPE
             SYNTAX      INTEGER
             ACCESS      read-only
             STATUS      mandatory
             DESCRIPTION
                 "Noise Margin as seen by this VTU with respect to its
                 received signal in 0.01dB."
         ::= { accessSwitchVdslVtuoPhysEntry 1 }

         accessSwitchVdslVtuoCurrMse OBJECT-TYPE
             SYNTAX      INTEGER
             ACCESS      read-only
             STATUS      mandatory
             DESCRIPTION
                 "Minimum Square Error as seen by this VTU with respect to its
                 received signal in 0.01dB."
         ::= { accessSwitchVdslVtuoPhysEntry 2 }

         accessSwitchVdslVtuoCurrPsd OBJECT-TYPE
             SYNTAX      INTEGER
             ACCESS      read-only
             STATUS      mandatory
             DESCRIPTION
                 "Power Spectral Density as seen by this VTU with respect to its
                 received signal in 0.01dBm/Hz."
         ::= { accessSwitchVdslVtuoPhysEntry 3 }

         accessSwitchVdslVtuoCurrRsErr OBJECT-TYPE
             SYNTAX      Counter
             ACCESS      read-only
             STATUS      mandatory
             DESCRIPTION
                 "Reed-Solomon error counted by this VTU with respect to its
                 received signal."
         ::= { accessSwitchVdslVtuoPhysEntry 4 }

         accessSwitchVdslVtuoCurrAtn OBJECT-TYPE
             SYNTAX      Gauge
             ACCESS      read-only
             STATUS      mandatory
             DESCRIPTION
                 "Measured difference in the total power transmitted by
                 the peer VTU and the total power received by this VTU."
         ::= { accessSwitchVdslVtuoPhysEntry 5 }

         accessSwitchVdslVtuoCurrOutputPwr OBJECT-TYPE
             SYNTAX      INTEGER
             ACCESS      read-only
             STATUS      mandatory
             DESCRIPTION
                 "Measured total output power in 0.01dBm transmitted by this VTU."
         ::= { accessSwitchVdslVtuoPhysEntry 6 }

         accessSwitchVdslVtuoCurrRate OBJECT-TYPE
             SYNTAX      INTEGER
             ACCESS  	 read-only
             STATUS      mandatory
             DESCRIPTION
                 "Actual transmission rate in bits-per-second on this line."
         ::= { accessSwitchVdslVtuoPhysEntry 7 }

         accessSwitchVdslVtuoCurrAttainableRate OBJECT-TYPE
             SYNTAX      Gauge
             ACCESS      read-only
             STATUS      mandatory
             DESCRIPTION
                 "Indicates the maximum mandatoryly attainable data rate in bits-per-second
                 by the VTU.  This value will be equal or greater than
                 the mandatory line rate."
         ::= { accessSwitchVdslVtuoPhysEntry 8 }

        accessSwitchVdslVtuoCurrStatus OBJECT-TYPE
             SYNTAX	 INTEGER
             ACCESS      read-only
             STATUS      mandatory
             DESCRIPTION
                 "Indicates mandatory state of the VTU-O line.  This is a
                 bit-map of possible conditions.  The various bit
                 positions are:

          0      noDefect             There no defects on the line

          1      lossOfFraming        VTU-O failure due to not
                                      receiving valid frame.

          2      lossOfSignal         VTU-O failure due to not
                                      receiving signal.

          3      lossOfPower          VTU-O failure due to loss of
                                      power.
                                      Note: the Agent may still
                                      function.

          4      lossOfSignalQuality  Loss of Signal Quality is
                                      declared when the Noise Margin
                                      falls below the Minimum Noise
                                      Margin, or the bit-error-rate
                                      exceeds 10^-7.

          5      lossOfLink           VTU-O failure due to inability
                                      to link with VTU-R.

          6      dataInitFailure      VTU-O failure during
                                      initialization due to bit
                                      errors corrupting startup
                                      exchange data.

          7      configInitFailure    VTU-O failure during
                                      initialization due to peer
                                      VTU not able to support
                                      requested configuration

          8      protocolInitFailure  VTU-O failure during
                                      initialization due to
                                      incompatible protocol used by
                                      the peer VTU.

          9      noPeerVtuPresent     VTU-O failure during
                                      initialization due to no
                                      activation sequence detected
                                      from peer VTU.

                 This is intended to supplement ifOperStatus."
         ::= { accessSwitchVdslVtuoPhysEntry 9 }


	 -- accessSwitch VDSL VTU-R Physical Table

   	 accessSwitchVdslVturPhysTable   OBJECT-TYPE
             SYNTAX          SEQUENCE OF AccessSwitchVdslVturPhysEntry
             ACCESS          not-accessible
             STATUS          mandatory
             DESCRIPTION
                 "This table provides one row for each VTU-R.
                 Each row contains the physical layer parameters for that VTU-R."
         ::= { accessSwitchVdslLineMibObjects 3 }

         accessSwitchVdslVturPhysEntry   OBJECT-TYPE
             SYNTAX          AccessSwitchVdslVturPhysEntry
             ACCESS          not-accessible
             STATUS          mandatory
             DESCRIPTION     "An entry in the accessSwitchVdslVturPhysTable."
             INDEX           { ifIndex }
         ::= { accessSwitchVdslVturPhysTable 1 }

         AccessSwitchVdslVturPhysEntry ::=
             SEQUENCE {
         	accessSwitchVdslVturCurrSnrMgn              INTEGER,
		accessSwitchVdslVturCurrMse		   INTEGER,
		accessSwitchVdslVturCurrPsd		   INTEGER,
		accessSwitchVdslVturCurrRsErr		   Counter,
         	accessSwitchVdslVturCurrAtn                 Gauge,
         	accessSwitchVdslVturCurrOutputPwr           INTEGER,
		accessSwitchVdslVturCurrRate		   INTEGER,
         	accessSwitchVdslVturCurrAttainableRate      Gauge,
         	accessSwitchVdslVturCurrStatus              INTEGER
             }

         accessSwitchVdslVturCurrSnrMgn OBJECT-TYPE
             SYNTAX      INTEGER
             ACCESS      read-only
             STATUS      mandatory
             DESCRIPTION
                 "Noise Margin as seen by this VTU with respect to its
                 received signal in 0.01dB."
         ::= { accessSwitchVdslVturPhysEntry 1 }

         accessSwitchVdslVturCurrMse OBJECT-TYPE
             SYNTAX      INTEGER
             ACCESS      read-only
             STATUS      mandatory
             DESCRIPTION
                 "Minimum Square Error as seen by this VTU with respect to its
                 received signal in 0.01dB."
         ::= { accessSwitchVdslVturPhysEntry 2 }

         accessSwitchVdslVturCurrPsd OBJECT-TYPE
             SYNTAX      INTEGER
             ACCESS      read-only
             STATUS      mandatory
             DESCRIPTION
                 "Power Spectral Density as seen by this VTU with respect to its
                 received signal in 0.01dBm/Hz."
         ::= { accessSwitchVdslVturPhysEntry 3 }

         accessSwitchVdslVturCurrRsErr OBJECT-TYPE
             SYNTAX      Counter
             ACCESS      read-only
             STATUS      mandatory
             DESCRIPTION
                 "Reed-Solomon error counted by this VTU with respect to its
                 received signal."
         ::= { accessSwitchVdslVturPhysEntry 4 }

         accessSwitchVdslVturCurrAtn OBJECT-TYPE
             SYNTAX      Gauge
             ACCESS      read-only
             STATUS      mandatory
             DESCRIPTION
                 "Measured difference in the total power transmitted by
                 the peer VTU and the total power received by this VTU."
         ::= { accessSwitchVdslVturPhysEntry 5 }

         accessSwitchVdslVturCurrOutputPwr OBJECT-TYPE
             SYNTAX      INTEGER
             ACCESS      read-only
             STATUS      mandatory
             DESCRIPTION
                 "Measured total output power in 0.01dBm transmitted by this VTU."
         ::= { accessSwitchVdslVturPhysEntry 6 }

         accessSwitchVdslVturCurrRate OBJECT-TYPE
             SYNTAX      INTEGER
             ACCESS  	 read-only
             STATUS      mandatory
             DESCRIPTION
                 "Actual transmission rate in bits-per-second on this line."
         ::= { accessSwitchVdslVturPhysEntry 7 }

         accessSwitchVdslVturCurrAttainableRate OBJECT-TYPE
             SYNTAX      Gauge
             ACCESS      read-only
             STATUS      mandatory
             DESCRIPTION
                 "Indicates the maximum mandatoryly attainable data rate in bits-per-second
                 by the VTU.  This value will be equal or greater than
                 the mandatory line rate."
         ::= { accessSwitchVdslVturPhysEntry 8 }

         accessSwitchVdslVturCurrStatus OBJECT-TYPE
             SYNTAX	 INTEGER
             ACCESS      read-only
             STATUS      mandatory
             DESCRIPTION
                 "Indicates mandatory state of the VTU-R line.  This is a
                 bit-map of possible conditions.  The various bit
                 positions are:

          0      noDefect             There no defects on the line

          1      lossOfFraming        VTU-R failure due to not
                                      receiving valid frame.

          2      lossOfSignal         VTU-R failure due to not
                                      receiving signal.

          3      lossOfPower          VTU-R failure due to loss of
                                      power.
                                      Note: the Agent may still
                                      function.

          4      lossOfSignalQuality  Loss of Signal Quality is
                                      declared when the Noise Margin
                                      falls below the Minimum Noise
                                      Margin, or the bit-error-rate
                                      exceeds 10^-7.

                 This is intended to supplement ifOperStatus."
	 ::= { accessSwitchVdslVturPhysEntry 9 }


	 -- accessSwitch VDSL VTU-O Inventory Table

   	 accessSwitchVdslVtuoInventoryTable   OBJECT-TYPE
             SYNTAX          SEQUENCE OF AccessSwitchVdslVtuoInventoryEntry
             ACCESS          not-accessible
             STATUS          mandatory
             DESCRIPTION
                 "This table provides one row for each VTU-O.
                 Each row contains the inventory parameters for that VTU-O."
         ::= { accessSwitchVdslLineMibObjects 4 }

         accessSwitchVdslVtuoInventoryEntry   OBJECT-TYPE
             SYNTAX          AccessSwitchVdslVtuoInventoryEntry
             ACCESS          not-accessible
             STATUS          mandatory
             DESCRIPTION     "An entry in the accessSwitchVdslVtuoInventoryTable."
             INDEX           { ifIndex }
         ::= { accessSwitchVdslVtuoInventoryTable 1 }

         AccessSwitchVdslVtuoInventoryEntry ::=
             SEQUENCE {
         	accessSwitchVdslVtuoInvSerialNumber         DisplayString,
         	accessSwitchVdslVtuoInvVendorID             DisplayString,
         	accessSwitchVdslVtuoInvVersionNumber        DisplayString
	     }

         -- These items should describe the lowest level identifiable
         -- component, be it a stand-alone modem, a card in a rack,
         -- a child-board, etc.
         --
         accessSwitchVdslVtuoInvSerialNumber OBJECT-TYPE
             SYNTAX      DisplayString
             ACCESS      read-only
             STATUS      mandatory
             DESCRIPTION
                 "The vendor specific string that identifies the
                 vendor equipment."
         ::= { accessSwitchVdslVtuoInventoryEntry 1 }

         accessSwitchVdslVtuoInvVendorID OBJECT-TYPE
             SYNTAX      DisplayString
             ACCESS      read-only
             STATUS      mandatory
             DESCRIPTION
                 "The vendor ID code is a copy of the binary
                 vendor identification field defined by the
                 PHY[10] and expressed as readable characters."
         ::= { accessSwitchVdslVtuoInventoryEntry 2 }

         accessSwitchVdslVtuoInvVersionNumber OBJECT-TYPE
             SYNTAX      DisplayString
             ACCESS      read-only
             STATUS      mandatory
             DESCRIPTION
                 "The vendor specific version number sent by this VTU
                 as part of the initialization messages.  It is a copy
                 of the binary version number field defined by the
                 PHY[10] and expressed as readable characters."
         ::= { accessSwitchVdslVtuoInventoryEntry 3 }


	 -- accessSwitch VDSL VTU-R Inventory Table

   	 accessSwitchVdslVturInventoryTable   OBJECT-TYPE
             SYNTAX          SEQUENCE OF AccessSwitchVdslVturInventoryEntry
             ACCESS          not-accessible
             STATUS          mandatory
             DESCRIPTION
                 "This table provides one row for each VTU-R.
                 Each row contains the inventory parameters for that VTU-R."
         ::= { accessSwitchVdslLineMibObjects 5 }

         accessSwitchVdslVturInventoryEntry   OBJECT-TYPE
             SYNTAX          AccessSwitchVdslVturInventoryEntry
             ACCESS          not-accessible
             STATUS          mandatory
             DESCRIPTION     "An entry in the accessSwitchVdslVturInventoryTable."
             INDEX           { ifIndex }
         ::= { accessSwitchVdslVturInventoryTable 1 }

         AccessSwitchVdslVturInventoryEntry ::=
             SEQUENCE {
         	accessSwitchVdslVturInvSerialNumber         DisplayString,
         	accessSwitchVdslVturInvVendorID             DisplayString,
         	accessSwitchVdslVturInvVersionNumber        DisplayString
	     }

         -- These items should describe the lowest level identifiable
         -- component, be it a stand-alone modem, a card in a rack,
         -- a child-board, etc.
         --
         accessSwitchVdslVturInvSerialNumber OBJECT-TYPE
             SYNTAX      DisplayString
             ACCESS      read-only
             STATUS      mandatory
             DESCRIPTION
                 "The vendor specific string that identifies the
                 vendor equipment."
         ::= { accessSwitchVdslVturInventoryEntry 1 }

         accessSwitchVdslVturInvVendorID OBJECT-TYPE
             SYNTAX      DisplayString
             ACCESS      read-only
             STATUS      mandatory
             DESCRIPTION
                 "The vendor ID code is a copy of the binary
                 vendor identification field defined by the
                 PHY[10] and expressed as readable characters."
         ::= { accessSwitchVdslVturInventoryEntry 2 }

         accessSwitchVdslVturInvVersionNumber OBJECT-TYPE
             SYNTAX      DisplayString
             ACCESS      read-only
             STATUS      mandatory
             DESCRIPTION
                 "The vendor specific version number sent by this VTU
                 as part of the initialization messages.  It is a copy
                 of the binary version number field defined by the
                 PHY[10] and expressed as readable characters."
         ::= { accessSwitchVdslVturInventoryEntry 3 }


	 -- accessSwitch VDSL VTU-O Performance Data Table

         accessSwitchVdslVtuoPerfDataTable   OBJECT-TYPE
             SYNTAX          SEQUENCE OF AccessSwitchVdslVtuoPerfDataEntry
             ACCESS          not-accessible
             STATUS          mandatory
             DESCRIPTION
                 "This table provides one row for each VTU-O."
         ::= { accessSwitchVdslLineMibObjects 6 }

         accessSwitchVdslVtuoPerfDataEntry       OBJECT-TYPE
             SYNTAX          AccessSwitchVdslVtuoPerfDataEntry
             ACCESS          not-accessible
             STATUS          mandatory
             DESCRIPTION     "An entry in accessSwitchVdslVtuoPerfDataTable."
             INDEX           { ifIndex }
         ::= { accessSwitchVdslVtuoPerfDataTable 1 }

         AccessSwitchVdslVtuoPerfDataEntry ::=
             SEQUENCE {
                accessSwitchVdslVtuoPerfLofs                 Counter,
                accessSwitchVdslVtuoPerfLoss                 Counter,
                accessSwitchVdslVtuoPerfLols                 Counter,
                accessSwitchVdslVtuoPerfLprs                 Counter,
                accessSwitchVdslVtuoPerfESs                  Counter,
                accessSwitchVdslVtuoPerfInits                Counter,
                accessSwitchVdslVtuoPerfValidIntervals       INTEGER,
                accessSwitchVdslVtuoPerfInvalidIntervals     INTEGER,
                accessSwitchVdslVtuoPerfCurr15MinTimeElapsed Gauge,
                accessSwitchVdslVtuoPerfCurr15MinLofs        Counter,
                accessSwitchVdslVtuoPerfCurr15MinLoss        Counter,
                accessSwitchVdslVtuoPerfCurr15MinLols        Counter,
                accessSwitchVdslVtuoPerfCurr15MinLprs        Counter,
                accessSwitchVdslVtuoPerfCurr15MinESs         Counter,
                accessSwitchVdslVtuoPerfCurr15MinInits       Counter,
                accessSwitchVdslVtuoPerfCurr1DayTimeElapsed  Gauge,
                accessSwitchVdslVtuoPerfCurr1DayLofs         Counter,
                accessSwitchVdslVtuoPerfCurr1DayLoss         Counter,
                accessSwitchVdslVtuoPerfCurr1DayLols         Counter,
                accessSwitchVdslVtuoPerfCurr1DayLprs         Counter,
                accessSwitchVdslVtuoPerfCurr1DayESs          Counter,
                accessSwitchVdslVtuoPerfCurr1DayInits        Counter,
                accessSwitchVdslVtuoPerfPrev1DayMoniSecs     INTEGER,
                accessSwitchVdslVtuoPerfPrev1DayLofs         Counter,
                accessSwitchVdslVtuoPerfPrev1DayLoss         Counter,
                accessSwitchVdslVtuoPerfPrev1DayLols         Counter,
                accessSwitchVdslVtuoPerfPrev1DayLprs         Counter,
                accessSwitchVdslVtuoPerfPrev1DayESs          Counter,
                accessSwitchVdslVtuoPerfPrev1DayInits        Counter
             }

         -- Event Counters
         --
         -- Also see accessSwitchVdslVtuoIntervalTable for 15 minute interval
         -- elapsed counters.
         --
         accessSwitchVdslVtuoPerfLofs OBJECT-TYPE
             SYNTAX      Counter
             ACCESS      read-only
             STATUS      mandatory
             DESCRIPTION
                 "Count of the number of Loss of Framing failures since
                 agent reset."
         ::= { accessSwitchVdslVtuoPerfDataEntry 1 }

         accessSwitchVdslVtuoPerfLoss  OBJECT-TYPE
             SYNTAX      Counter
             ACCESS      read-only
             STATUS      mandatory
             DESCRIPTION
                 "Count of the number of Loss of Signal failures since
                 agent reset."
         ::= { accessSwitchVdslVtuoPerfDataEntry 2 }

         accessSwitchVdslVtuoPerfLols OBJECT-TYPE
             SYNTAX      Counter
             ACCESS      read-only
             STATUS      mandatory
             DESCRIPTION
                 "Count of the number of Loss of Link failures since
                 agent reset."
         ::= { accessSwitchVdslVtuoPerfDataEntry 3 }

         accessSwitchVdslVtuoPerfLprs OBJECT-TYPE
             SYNTAX      Counter
             ACCESS      read-only
             STATUS      mandatory
             DESCRIPTION
                 "Count of the number of Loss of Power failures since
                 agent reset."
         ::= { accessSwitchVdslVtuoPerfDataEntry 4 }

         accessSwitchVdslVtuoPerfESs OBJECT-TYPE
             SYNTAX      Counter
             ACCESS      read-only
             STATUS      mandatory
             DESCRIPTION
                 "Count of the number of Errored Seconds since agent
                 reset.  The errored second parameter is a count of
                 one-second intervals containing one or more crc
                 anomalies, or one or more los or sef defects."
         ::= { accessSwitchVdslVtuoPerfDataEntry 5 }

         accessSwitchVdslVtuoPerfInits OBJECT-TYPE
             SYNTAX      Counter
             ACCESS      read-only
             STATUS      mandatory
             DESCRIPTION
                 "Count of the line initialization attempts since
                 agent reset. Includes both successful and failed
                 attempts."
         ::= { accessSwitchVdslVtuoPerfDataEntry 6 }

         -- general 15 min interval information
	 --
         accessSwitchVdslVtuoPerfValidIntervals OBJECT-TYPE
             SYNTAX      INTEGER(0..96)
             ACCESS      read-only
             STATUS      mandatory
             DESCRIPTION
                 "The number of previous 15-minute intervals in the
                 interval table for which data was collected.  Given
                 that <n> is the maximum # of intervals supported.
                 The value will be <n> unless the measurement was
                 (re-)started within the last (<n>*15) minutes, in which
                 case the value will be the number of complete 15
                 minute intervals for which the agent has at least
                 some data. In certain cases (e.g., in the case
                 where the agent is a proxy) it is possible that some
                 intervals are unavailable.  In this case, this
                 interval is the maximum interval number for
                 which data is available."
         ::= { accessSwitchVdslVtuoPerfDataEntry 7 }

         accessSwitchVdslVtuoPerfInvalidIntervals OBJECT-TYPE
             SYNTAX      INTEGER(0..96)
             ACCESS      read-only
             STATUS      mandatory
             DESCRIPTION
                 "The number of intervals in the range from
                 0 to the value of accessSwitchVdslVtuoPerfValidIntervals
                 for which no data is available. This object
                 will typically be zero except in cases where
                 the data for some intervals are not available
                 (e.g., in proxy situations)."
         ::= { accessSwitchVdslVtuoPerfDataEntry 8 }

         -- 15 min mandatory performance group
         --
         accessSwitchVdslVtuoPerfCurr15MinTimeElapsed OBJECT-TYPE
             SYNTAX      Gauge(0..899)
             ACCESS      read-only
             STATUS      mandatory
             DESCRIPTION
                 "Total elapsed seconds in this interval."
         ::= { accessSwitchVdslVtuoPerfDataEntry 9 }

         accessSwitchVdslVtuoPerfCurr15MinLofs OBJECT-TYPE
             SYNTAX      Counter
             ACCESS      read-only
             STATUS      mandatory
             DESCRIPTION
                 "Count of seconds in the mandatory 15 minute interval
                 when there was Loss of Framing."
         ::= { accessSwitchVdslVtuoPerfDataEntry 10 }

         accessSwitchVdslVtuoPerfCurr15MinLoss  OBJECT-TYPE
             SYNTAX      Counter
             ACCESS      read-only
             STATUS      mandatory
             DESCRIPTION
                 "Count of seconds in the mandatory 15 minute interval
                 when there was Loss of Signal."
         ::= { accessSwitchVdslVtuoPerfDataEntry 11 }

         accessSwitchVdslVtuoPerfCurr15MinLols  OBJECT-TYPE
             SYNTAX      Counter
             ACCESS      read-only
             STATUS      mandatory
             DESCRIPTION
                 "Count of seconds in the mandatory 15 minute interval
                 when there was Loss of Link."
         ::= { accessSwitchVdslVtuoPerfDataEntry 12 }

         accessSwitchVdslVtuoPerfCurr15MinLprs  OBJECT-TYPE
             SYNTAX      Counter
             ACCESS      read-only
             STATUS      mandatory
             DESCRIPTION
                 "Count of seconds in the mandatory 15 minute interval
                 when there was Loss of Power."
         ::= { accessSwitchVdslVtuoPerfDataEntry 13 }

         accessSwitchVdslVtuoPerfCurr15MinESs OBJECT-TYPE
             SYNTAX      Counter
             ACCESS      read-only
             STATUS      mandatory
             DESCRIPTION
                 "Count of Errored Seconds in the mandatory 15 minute
                 interval.  The errored second parameter is a count of
                 one-second intervals containing one or more crc
                 anomalies, or one or more los or sef defects."
         ::= { accessSwitchVdslVtuoPerfDataEntry 14 }

         accessSwitchVdslVtuoPerfCurr15MinInits  OBJECT-TYPE
             SYNTAX      Counter
             ACCESS      read-only
             STATUS      mandatory
             DESCRIPTION
                 "Count of the line initialization attempts in the
                 mandatory 15 minute interval. Includes both successful
                 and failed attempts."
         ::= { accessSwitchVdslVtuoPerfDataEntry 15 }

         -- 1-day mandatory and previous performance group
         --
         accessSwitchVdslVtuoPerfCurr1DayTimeElapsed OBJECT-TYPE
             SYNTAX      Gauge(0..86399)
             ACCESS      read-only
             STATUS      mandatory
             DESCRIPTION
                 "Number of seconds that have elapsed since the
                 beginning of the mandatory 1-day interval."
         ::= { accessSwitchVdslVtuoPerfDataEntry 16 }

         accessSwitchVdslVtuoPerfCurr1DayLofs  OBJECT-TYPE
             SYNTAX      Counter
             ACCESS      read-only
             STATUS      mandatory
             DESCRIPTION
                 "Count of the number of seconds when there was Loss of
                 Framing during the mandatory day as measured by
                 accessSwitchVdslVtuoPerfCurr1DayTimeElapsed."
         ::= { accessSwitchVdslVtuoPerfDataEntry 17 }

         accessSwitchVdslVtuoPerfCurr1DayLoss  OBJECT-TYPE
             SYNTAX      Counter
             ACCESS      read-only
             STATUS      mandatory
             DESCRIPTION
                 "Count of the number of seconds when there was Loss of
                 Signal during the mandatory day as measured by
                 accessSwitchVdslVtuoPerfCurr1DayTimeElapsed."
         ::= { accessSwitchVdslVtuoPerfDataEntry 18 }

         accessSwitchVdslVtuoPerfCurr1DayLols  OBJECT-TYPE
             SYNTAX      Counter
             ACCESS      read-only
             STATUS      mandatory
             DESCRIPTION
                 "Count of the number of seconds when there was Loss of
                 Link during the mandatory day as measured by
                 accessSwitchVdslVtuoPerfCurr1DayTimeElapsed."
         ::= { accessSwitchVdslVtuoPerfDataEntry 19 }

         accessSwitchVdslVtuoPerfCurr1DayLprs  OBJECT-TYPE
             SYNTAX      Counter
             ACCESS      read-only
             STATUS      mandatory
             DESCRIPTION
                 "Count of the number of seconds when there was Loss of
                 Power during the mandatory day as measured by
                 accessSwitchVdslVtuoPerfCurr1DayTimeElapsed."
         ::= { accessSwitchVdslVtuoPerfDataEntry 20 }

         accessSwitchVdslVtuoPerfCurr1DayESs OBJECT-TYPE
             SYNTAX      Counter
             ACCESS      read-only
             STATUS      mandatory
             DESCRIPTION
                 "Count of Errored Seconds during the mandatory day as
                 measured by accessSwitchVdslVtuoPerfCurr1DayTimeElapsed.
                 The errored second parameter is a count of
                 one-second intervals containing one or more crc
                 anomalies, or one or more los or sef defects."
         ::= { accessSwitchVdslVtuoPerfDataEntry 21 }

         accessSwitchVdslVtuoPerfCurr1DayInits  OBJECT-TYPE
             SYNTAX      Counter
             ACCESS      read-only
             STATUS      mandatory
             DESCRIPTION
                 "Count of the line initialization attempts in the
                 day as measured by accessSwitchVdslVtuoPerfCurr1DayTimeElapsed.
                 Includes both successful and failed attempts."
         ::= { accessSwitchVdslVtuoPerfDataEntry 22 }

         accessSwitchVdslVtuoPerfPrev1DayMoniSecs OBJECT-TYPE
             SYNTAX      INTEGER(0..86400)
             ACCESS      read-only
             STATUS      mandatory
             DESCRIPTION
                 "The amount of time in the previous 1-day interval
                 over which the performance monitoring information
                 is actually counted. This value will be the same as
                 the interval duration except in a situation where
                 performance monitoring data could not be collected
                 for any reason."
         ::= { accessSwitchVdslVtuoPerfDataEntry 23 }

         accessSwitchVdslVtuoPerfPrev1DayLofs  OBJECT-TYPE
             SYNTAX      Counter
             ACCESS      read-only
             STATUS      mandatory
             DESCRIPTION
                 "Count of seconds in the interval when there was
                 Loss of Framing within the most recent previous
                 1-day period."
         ::= { accessSwitchVdslVtuoPerfDataEntry 24 }

         accessSwitchVdslVtuoPerfPrev1DayLoss  OBJECT-TYPE
             SYNTAX      Counter
             ACCESS      read-only
             STATUS      mandatory
             DESCRIPTION
                 "Count of seconds in the interval when there was
                 Loss of Signal within the most recent previous
                 1-day period."
         ::= { accessSwitchVdslVtuoPerfDataEntry 25 }

         accessSwitchVdslVtuoPerfPrev1DayLols  OBJECT-TYPE
             SYNTAX      Counter
             ACCESS      read-only
             STATUS      mandatory
             DESCRIPTION
                 "Count of seconds in the interval when there was
                 Loss of Link within the most recent previous
                 1-day period."
         ::= { accessSwitchVdslVtuoPerfDataEntry 26 }

         accessSwitchVdslVtuoPerfPrev1DayLprs  OBJECT-TYPE
             SYNTAX      Counter
             ACCESS      read-only
             STATUS      mandatory
             DESCRIPTION
                 "Count of seconds in the interval when there was
                 Loss of Power within the most recent previous
                 1-day period."
         ::= { accessSwitchVdslVtuoPerfDataEntry 27 }

         accessSwitchVdslVtuoPerfPrev1DayESs OBJECT-TYPE
             SYNTAX      Counter
             ACCESS      read-only
             STATUS      mandatory
             DESCRIPTION
                 "Count of Errored Seconds within the most recent
                 previous 1-day period. The errored second parameter is
                 a count of one-second intervals containing one or more
                 crc anomalies, or one or more los or sef defects."
         ::= { accessSwitchVdslVtuoPerfDataEntry 28 }

         accessSwitchVdslVtuoPerfPrev1DayInits  OBJECT-TYPE
             SYNTAX      Counter
             ACCESS      read-only
             STATUS      mandatory
             DESCRIPTION
                 "Count of the line initialization attempts in the most
                 recent previous 1-day period. Includes both successful
                 and failed attempts."
         ::= { accessSwitchVdslVtuoPerfDataEntry 29 }


	 -- accessSwitch VDSL VTU-R Performance Data Table

         accessSwitchVdslVturPerfDataTable   OBJECT-TYPE
             SYNTAX          SEQUENCE OF AccessSwitchVdslVturPerfDataEntry
             ACCESS          not-accessible
             STATUS          mandatory
             DESCRIPTION
                 "This table provides one row for each VTU-R."
         ::= { accessSwitchVdslLineMibObjects 7 }

         accessSwitchVdslVturPerfDataEntry       OBJECT-TYPE
             SYNTAX          AccessSwitchVdslVturPerfDataEntry
             ACCESS          not-accessible
             STATUS          mandatory
             DESCRIPTION     "An entry in accessSwitchVdslVturPerfDataTable."
             INDEX           { ifIndex }
         ::= { accessSwitchVdslVturPerfDataTable 1 }

         AccessSwitchVdslVturPerfDataEntry ::=
             SEQUENCE {
                accessSwitchVdslVturPerfLofs                 Counter,
                accessSwitchVdslVturPerfLoss                 Counter,
                accessSwitchVdslVturPerfLprs                 Counter,
                accessSwitchVdslVturPerfESs                  Counter,
                accessSwitchVdslVturPerfValidIntervals       INTEGER,
                accessSwitchVdslVturPerfInvalidIntervals     INTEGER,
                accessSwitchVdslVturPerfCurr15MinTimeElapsed Gauge,
                accessSwitchVdslVturPerfCurr15MinLofs        Counter,
                accessSwitchVdslVturPerfCurr15MinLoss        Counter,
                accessSwitchVdslVturPerfCurr15MinLprs        Counter,
                accessSwitchVdslVturPerfCurr15MinESs         Counter,
                accessSwitchVdslVturPerfCurr1DayTimeElapsed  Gauge,
                accessSwitchVdslVturPerfCurr1DayLofs         Counter,
                accessSwitchVdslVturPerfCurr1DayLoss         Counter,
                accessSwitchVdslVturPerfCurr1DayLprs         Counter,
                accessSwitchVdslVturPerfCurr1DayESs          Counter,
                accessSwitchVdslVturPerfPrev1DayMoniSecs     INTEGER,
                accessSwitchVdslVturPerfPrev1DayLofs         Counter,
                accessSwitchVdslVturPerfPrev1DayLoss         Counter,
                accessSwitchVdslVturPerfPrev1DayLprs         Counter,
                accessSwitchVdslVturPerfPrev1DayESs          Counter
             }

         -- Event Counters
         --
         -- Also see accessSwitchVdslVturIntervalTable for 15 minute interval
         -- elapsed counters.
         --
         accessSwitchVdslVturPerfLofs OBJECT-TYPE
             SYNTAX      Counter
             ACCESS      read-only
             STATUS      mandatory
             DESCRIPTION
                 "Count of the number of Loss of Framing failures since
                 agent reset."
         ::= { accessSwitchVdslVturPerfDataEntry 1 }

         accessSwitchVdslVturPerfLoss  OBJECT-TYPE
             SYNTAX      Counter
             ACCESS      read-only
             STATUS      mandatory
             DESCRIPTION
                 "Count of the number of Loss of Signal failures since
                 agent reset."
         ::= { accessSwitchVdslVturPerfDataEntry 2 }

         accessSwitchVdslVturPerfLprs OBJECT-TYPE
             SYNTAX      Counter
             ACCESS      read-only
             STATUS      mandatory
             DESCRIPTION
                 "Count of the number of Loss of Power failures since
                 agent reset."
         ::= { accessSwitchVdslVturPerfDataEntry 3 }

         accessSwitchVdslVturPerfESs OBJECT-TYPE
             SYNTAX      Counter
             ACCESS      read-only
             STATUS      mandatory
             DESCRIPTION
                 "Count of the number of Errored Seconds since agent
                 reset.  The errored second parameter is a count of
                 one-second intervals containing one or more crc
                 anomalies, or one or more los or sef defects."
         ::= { accessSwitchVdslVturPerfDataEntry 4 }

         -- general 15 min interval information
	 --
         accessSwitchVdslVturPerfValidIntervals OBJECT-TYPE
             SYNTAX      INTEGER(0..96)
             ACCESS      read-only
             STATUS      mandatory
             DESCRIPTION
                 "The number of previous 15-minute intervals in the
                 interval table for which data was collected.  Given
                 that <n> is the maximum # of intervals supported.
                 The value will be <n> unless the measurement was
                 (re-)started within the last (<n>*15) minutes, in which
                 case the value will be the number of complete 15
                 minute intervals for which the agent has at least
                 some data. In certain cases (e.g., in the case
                 where the agent is a proxy) it is possible that some
                 intervals are unavailable.  In this case, this
                 interval is the maximum interval number for
                 which data is available."
         ::= { accessSwitchVdslVturPerfDataEntry 5 }

         accessSwitchVdslVturPerfInvalidIntervals OBJECT-TYPE
             SYNTAX      INTEGER(0..96)
             ACCESS      read-only
             STATUS      mandatory
             DESCRIPTION
                 "The number of intervals in the range from
                 0 to the value of accessSwitchVdslVturPerfValidIntervals
                 for which no data is available. This object
                 will typically be zero except in cases where
                 the data for some intervals are not available
                 (e.g., in proxy situations)."
         ::= { accessSwitchVdslVturPerfDataEntry 6 }

         -- 15 min mandatory performance group
         --
         accessSwitchVdslVturPerfCurr15MinTimeElapsed OBJECT-TYPE
             SYNTAX      Gauge(0..899)
             ACCESS      read-only
             STATUS      mandatory
             DESCRIPTION
                 "Total elapsed seconds in this interval."
         ::= { accessSwitchVdslVturPerfDataEntry 7 }

         accessSwitchVdslVturPerfCurr15MinLofs OBJECT-TYPE
             SYNTAX      Counter
             ACCESS      read-only
             STATUS      mandatory
             DESCRIPTION
                 "Count of seconds in the mandatory 15 minute interval
                 when there was Loss of Framing."
         ::= { accessSwitchVdslVturPerfDataEntry 8 }

         accessSwitchVdslVturPerfCurr15MinLoss  OBJECT-TYPE
             SYNTAX      Counter
             ACCESS      read-only
             STATUS      mandatory
             DESCRIPTION
                 "Count of seconds in the mandatory 15 minute interval
                 when there was Loss of Signal."
         ::= { accessSwitchVdslVturPerfDataEntry 9 }

         accessSwitchVdslVturPerfCurr15MinLprs  OBJECT-TYPE
             SYNTAX      Counter
             ACCESS      read-only
             STATUS      mandatory
             DESCRIPTION
                 "Count of seconds in the mandatory 15 minute interval
                 when there was Loss of Power."
         ::= { accessSwitchVdslVturPerfDataEntry 10 }

         accessSwitchVdslVturPerfCurr15MinESs OBJECT-TYPE
             SYNTAX      Counter
             ACCESS      read-only
             STATUS      mandatory
             DESCRIPTION
                 "Count of Errored Seconds in the mandatory 15 minute
                 interval.  The errored second parameter is a count of
                 one-second intervals containing one or more crc
                 anomalies, or one or more los or sef defects."
         ::= { accessSwitchVdslVturPerfDataEntry 11 }

         -- 1-day mandatory and previous performance group
         --
         accessSwitchVdslVturPerfCurr1DayTimeElapsed OBJECT-TYPE
             SYNTAX      Gauge(0..86399)
             ACCESS      read-only
             STATUS      mandatory
             DESCRIPTION
                 "Number of seconds that have elapsed since the
                 beginning of the mandatory 1-day interval."
         ::= { accessSwitchVdslVturPerfDataEntry 12 }

         accessSwitchVdslVturPerfCurr1DayLofs  OBJECT-TYPE
             SYNTAX      Counter
             ACCESS      read-only
             STATUS      mandatory
             DESCRIPTION
                 "Count of the number of seconds when there was Loss of
                 Framing during the mandatory day as measured by
                 accessSwitchVdslVturPerfCurr1DayTimeElapsed."
         ::= { accessSwitchVdslVturPerfDataEntry 13 }

         accessSwitchVdslVturPerfCurr1DayLoss  OBJECT-TYPE
             SYNTAX      Counter
             ACCESS      read-only
             STATUS      mandatory
             DESCRIPTION
                 "Count of the number of seconds when there was Loss of
                 Signal during the mandatory day as measured by
                 accessSwitchVdslVturPerfCurr1DayTimeElapsed."
         ::= { accessSwitchVdslVturPerfDataEntry 14 }

         accessSwitchVdslVturPerfCurr1DayLprs  OBJECT-TYPE
             SYNTAX      Counter
             ACCESS      read-only
             STATUS      mandatory
             DESCRIPTION
                 "Count of the number of seconds when there was Loss of
                 Power during the mandatory day as measured by
                 accessSwitchVdslVturPerfCurr1DayTimeElapsed."
         ::= { accessSwitchVdslVturPerfDataEntry 15 }

         accessSwitchVdslVturPerfCurr1DayESs OBJECT-TYPE
             SYNTAX      Counter
             ACCESS      read-only
             STATUS      mandatory
             DESCRIPTION
                 "Count of Errored Seconds during the mandatory day as
                 measured by accessSwitchVdslVturPerfCurr1DayTimeElapsed.
                 The errored second parameter is a count of
                 one-second intervals containing one or more crc
                 anomalies, or one or more los or sef defects."
         ::= { accessSwitchVdslVturPerfDataEntry 16 }

         accessSwitchVdslVturPerfPrev1DayMoniSecs OBJECT-TYPE
             SYNTAX      INTEGER(0..86400)
             ACCESS      read-only
             STATUS      mandatory
             DESCRIPTION
                 "The amount of time in the previous 1-day interval
                 over which the performance monitoring information
                 is actually counted. This value will be the same as
                 the interval duration except in a situation where
                 performance monitoring data could not be collected
                 for any reason."
         ::= { accessSwitchVdslVturPerfDataEntry 17 }

         accessSwitchVdslVturPerfPrev1DayLofs  OBJECT-TYPE
             SYNTAX      Counter
             ACCESS      read-only
             STATUS      mandatory
             DESCRIPTION
                 "Count of seconds in the interval when there was
                 Loss of Framing within the most recent previous
                 1-day period."
         ::= { accessSwitchVdslVturPerfDataEntry 18 }

         accessSwitchVdslVturPerfPrev1DayLoss  OBJECT-TYPE
             SYNTAX      Counter
             ACCESS      read-only
             STATUS      mandatory
             DESCRIPTION
                 "Count of seconds in the interval when there was
                 Loss of Signal within the most recent previous
                 1-day period."
         ::= { accessSwitchVdslVturPerfDataEntry 19 }

         accessSwitchVdslVturPerfPrev1DayLprs  OBJECT-TYPE
             SYNTAX      Counter
             ACCESS      read-only
             STATUS      mandatory
             DESCRIPTION
                 "Count of seconds in the interval when there was
                 Loss of Power within the most recent previous
                 1-day period."
         ::= { accessSwitchVdslVturPerfDataEntry 20 }

         accessSwitchVdslVturPerfPrev1DayESs OBJECT-TYPE
             SYNTAX      Counter
             ACCESS      read-only
             STATUS      mandatory
             DESCRIPTION
                 "Count of Errored Seconds within the most recent
                 previous 1-day period. The errored second parameter is
                 a count of one-second intervals containing one or more
                 crc anomalies, or one or more los or sef defects."
         ::= { accessSwitchVdslVturPerfDataEntry 21 }


	 -- accessSwitch VDSL VTU-O Interval Table

         accessSwitchVdslVtuoIntervalTable   OBJECT-TYPE
             SYNTAX          SEQUENCE OF AccessSwitchVdslVtuoIntervalEntry
             ACCESS          not-accessible
             STATUS          mandatory
             DESCRIPTION
                 "This table provides one row for each VTU-O
                 performance data collection interval."
         ::= { accessSwitchVdslLineMibObjects 8 }

         accessSwitchVdslVtuoIntervalEntry   OBJECT-TYPE
             SYNTAX          AccessSwitchVdslVtuoIntervalEntry
             ACCESS          not-accessible
             STATUS          mandatory
             DESCRIPTION     "An entry in the accessSwitchVdslVtuoIntervalTable."
             INDEX           { ifIndex, accessSwitchVdslVtuoIntervalNumber }
         ::= { accessSwitchVdslVtuoIntervalTable 1 }

         AccessSwitchVdslVtuoIntervalEntry ::=
             SEQUENCE {
                accessSwitchVdslVtuoIntervalNumber          INTEGER,
                accessSwitchVdslVtuoIntervalLofs            Counter,
                accessSwitchVdslVtuoIntervalLoss            Counter,
                accessSwitchVdslVtuoIntervalLols            Counter,
                accessSwitchVdslVtuoIntervalLprs            Counter,
                accessSwitchVdslVtuoIntervalESs             Counter,
                accessSwitchVdslVtuoIntervalInits           Counter,
                accessSwitchVdslVtuoIntervalValidData       INTEGER
             }

         accessSwitchVdslVtuoIntervalNumber OBJECT-TYPE
             SYNTAX      INTEGER(1..96)
             ACCESS      not-accessible
             STATUS      mandatory
             DESCRIPTION
                 "Performance Data Interval number 1 is the
                 the most recent previous interval; interval
                 96 is 24 hours ago.  Intervals 2..96 are
                 optional."
         ::= { accessSwitchVdslVtuoIntervalEntry 1 }

         accessSwitchVdslVtuoIntervalLofs OBJECT-TYPE
             SYNTAX      Counter
             ACCESS      read-only
             STATUS      mandatory
             DESCRIPTION
                 "Count of seconds in the interval when there was Loss
                 of Framing."
         ::= { accessSwitchVdslVtuoIntervalEntry 2 }

         accessSwitchVdslVtuoIntervalLoss  OBJECT-TYPE
             SYNTAX      Counter
             ACCESS      read-only
             STATUS      mandatory
             DESCRIPTION
                 "Count of seconds in the interval when there was Loss
                 of Signal."
         ::= { accessSwitchVdslVtuoIntervalEntry 3 }

         accessSwitchVdslVtuoIntervalLols  OBJECT-TYPE
             SYNTAX      Counter
             ACCESS      read-only
             STATUS      mandatory
             DESCRIPTION
                 "Count of seconds in the interval when there was Loss
                 of Link."
         ::= { accessSwitchVdslVtuoIntervalEntry 4 }

         accessSwitchVdslVtuoIntervalLprs  OBJECT-TYPE
             SYNTAX      Counter
             ACCESS      read-only
             STATUS      mandatory
             DESCRIPTION
                 "Count of seconds in the interval when there was Loss
                 of Power."
         ::= { accessSwitchVdslVtuoIntervalEntry 5 }

         accessSwitchVdslVtuoIntervalESs OBJECT-TYPE
             SYNTAX      Counter
             ACCESS      read-only
             STATUS      mandatory
             DESCRIPTION
                 "Count of Errored Seconds in the interval.
                 The errored second parameter is a count of
                 one-second intervals containing one or more crc
                 anomalies, or one or more los or sef defects."
         ::= { accessSwitchVdslVtuoIntervalEntry 6 }

         accessSwitchVdslVtuoIntervalInits  OBJECT-TYPE
             SYNTAX      Counter
             ACCESS      read-only
             STATUS      mandatory
             DESCRIPTION
                 "Count of the line initialization attempts
                 during the interval. Includes both successful
                 and failed attempts."
         ::= { accessSwitchVdslVtuoIntervalEntry 7 }

         accessSwitchVdslVtuoIntervalValidData OBJECT-TYPE
             SYNTAX INTEGER {
			true(1),
			false(2)
		    }
             ACCESS read-only
             STATUS mandatory
             DESCRIPTION
                 "This variable indicates if the data for this
                 interval is valid."
         ::= { accessSwitchVdslVtuoIntervalEntry 8 }


	 -- accessSwitch VDSL VTU-R Interval Table

         accessSwitchVdslVturIntervalTable   OBJECT-TYPE
             SYNTAX          SEQUENCE OF AccessSwitchVdslVturIntervalEntry
             ACCESS          not-accessible
             STATUS          mandatory
             DESCRIPTION
                 "This table provides one row for each VTU-R
                 performance data collection interval."
         ::= { accessSwitchVdslLineMibObjects 9 }

         accessSwitchVdslVturIntervalEntry   OBJECT-TYPE
             SYNTAX          AccessSwitchVdslVturIntervalEntry
             ACCESS          not-accessible
             STATUS          mandatory
             DESCRIPTION     "An entry in the accessSwitchVdslVturIntervalTable."
             INDEX           { ifIndex, accessSwitchVdslVturIntervalNumber }
         ::= { accessSwitchVdslVturIntervalTable 1 }

         AccessSwitchVdslVturIntervalEntry ::=
             SEQUENCE {
                accessSwitchVdslVturIntervalNumber          INTEGER,
                accessSwitchVdslVturIntervalLofs            Counter,
                accessSwitchVdslVturIntervalLoss            Counter,
                accessSwitchVdslVturIntervalLprs            Counter,
                accessSwitchVdslVturIntervalESs             Counter,
                accessSwitchVdslVturIntervalValidData       INTEGER
             }

         accessSwitchVdslVturIntervalNumber OBJECT-TYPE
             SYNTAX      INTEGER(1..96)
             ACCESS      not-accessible
             STATUS      mandatory
             DESCRIPTION
                 "Performance Data Interval number 1 is the
                 the most recent previous interval; interval
                 96 is 24 hours ago.  Intervals 2..96 are
                 optional."
         ::= { accessSwitchVdslVturIntervalEntry 1 }

         accessSwitchVdslVturIntervalLofs OBJECT-TYPE
             SYNTAX      Counter
             ACCESS      read-only
             STATUS      mandatory
             DESCRIPTION
                 "Count of seconds in the interval when there was Loss
                 of Framing."
         ::= { accessSwitchVdslVturIntervalEntry 2 }

         accessSwitchVdslVturIntervalLoss  OBJECT-TYPE
             SYNTAX      Counter
             ACCESS      read-only
             STATUS      mandatory
             DESCRIPTION
                 "Count of seconds in the interval when there was Loss
                 of Signal."
         ::= { accessSwitchVdslVturIntervalEntry 3 }

         accessSwitchVdslVturIntervalLprs  OBJECT-TYPE
             SYNTAX      Counter
             ACCESS      read-only
             STATUS      mandatory
             DESCRIPTION
                 "Count of seconds in the interval when there was Loss
                 of Power."
         ::= { accessSwitchVdslVturIntervalEntry 4 }

         accessSwitchVdslVturIntervalESs OBJECT-TYPE
             SYNTAX      Counter
             ACCESS      read-only
             STATUS      mandatory
             DESCRIPTION
                 "Count of Errored Seconds in the interval.
                 The errored second parameter is a count of
                 one-second intervals containing one or more crc
                 anomalies, or one or more los or sef defects."
         ::= { accessSwitchVdslVturIntervalEntry 5 }

         accessSwitchVdslVturIntervalValidData OBJECT-TYPE
             SYNTAX INTEGER {
			true(1),
			false(2)
		    }
             ACCESS read-only
             STATUS mandatory
             DESCRIPTION
                 "This variable indicates if the data for this
                 interval is valid."
	 ::= { accessSwitchVdslVturIntervalEntry 6 }



         -- Profile Group
         --

	 -- accessSwitch VDSL Configuration Profile Table

         accessSwitchVdslLineConfProfileTable    OBJECT-TYPE
             SYNTAX          SEQUENCE OF AccessSwitchVdslLineConfProfileEntry
             ACCESS          not-accessible
             STATUS          mandatory
             DESCRIPTION
                 "This table contains information on the VDSL line
                 configuration. One entry in this table reflects a
                 profile which can be used to configure the VDSL line."
         ::= { accessSwitchVdslLineMibObjects 10 }

         accessSwitchVdslLineConfProfileEntry    OBJECT-TYPE
             SYNTAX          AccessSwitchVdslLineConfProfileEntry
             ACCESS          not-accessible
             STATUS          mandatory
             DESCRIPTION
                 "Each entry consists of a list of parameters that
                 represents the configuration of an VDSL modem.

                 When `dynamic' profiles are implemented, a default
                 profile will always exist.  This profile's name will
                 be set to `DEFVAL' and its parameters will be set
                 to vendor specific values, unless otherwise specified
                 in this document.

                 When `static' profiles are implemented, profiles
                 are automaticly created or destroyed as VDSL
                 physical lines are discovered and removed by
                 the system.  The name of the profile will be
                 equivalent to the decimal value of the line's
                 interface index."
             INDEX { IMPLIED accessSwitchVdslLineConfProfileName}
         ::= { accessSwitchVdslLineConfProfileTable 1 }

         AccessSwitchVdslLineConfProfileEntry ::=
             SEQUENCE {
                accessSwitchVdslLineConfProfileName               DisplayString,
		accessSwitchVdslLineConfMode			  INTEGER,
		accessSwitchVdslVtuoConfRate			  INTEGER,
                accessSwitchVdslVtuoConfTargetSnrMgn              INTEGER,
                accessSwitchVdslVtuoConfMaxSnrMgn                 INTEGER,
                accessSwitchVdslVtuoConfMinSnrMgn                 INTEGER,
                accessSwitchVdslVturConfRate                      INTEGER,
                accessSwitchVdslVturConfTargetSnrMgn              INTEGER,
                accessSwitchVdslVturConfMaxSnrMgn                 INTEGER,
                accessSwitchVdslVturConfMinSnrMgn                 INTEGER,
		accessSwitchVdslLineConfProfileRowStatus          RowStatus
            }

         accessSwitchVdslLineConfProfileName    OBJECT-TYPE
                 SYNTAX          DisplayString (SIZE (1..32))
                 ACCESS          not-accessible
                 STATUS          mandatory
                 DESCRIPTION
                 "This object is used by the line configuration table
                 in order to identify a row of this table.

                 When `dynamic' profiles are implemented, the profile
                 name is user specified.  Also, the system will always
                 provide a default profile whose name is `DEFVAL'.

                 When `static' profiles are implemented, there is an
                 one-to-one relationship between each line and its
                 profile.  In which case, the profile name will
                 need to algorithmicly represent the Line's ifIndex.
                 Therefore, the profile's name is a decimalized string
                 of the ifIndex that is fixed-length (i.e., 10) with
                 leading zero(s).  For example, the profile name for
                 ifIndex which equals '15' will be '0000000015'."
         ::= { accessSwitchVdslLineConfProfileEntry 1 }

         accessSwitchVdslLineConfMode OBJECT-TYPE
             SYNTAX  INTEGER {
                          tenBase-S(0),	-- 10Base S mode
                          ansi(1),	-- ANSI/ETSI Band Plan 997
                          etsi(2)	-- ETSI Band Plan 998
                      }
             ACCESS  read-create
             STATUS  mandatory
             DESCRIPTION
                      "Specifies the VDSL mode type used on this line."
         ::= { accessSwitchVdslLineConfProfileEntry 2 }

         accessSwitchVdslVtuoConfRate OBJECT-TYPE
             SYNTAX  INTEGER
             ACCESS  read-create
             STATUS  mandatory
             DESCRIPTION
                      "Transmission rate in bits-per-second specified by this VTU."
         ::= { accessSwitchVdslLineConfProfileEntry 3 }

         accessSwitchVdslVtuoConfTargetSnrMgn OBJECT-TYPE
             SYNTAX      INTEGER
             ACCESS      read-create
             STATUS      mandatory
             DESCRIPTION
                 "Configured Target Signal/Noise Margin in 0.01dB.
                 This is the Noise Margin the modem must achieve
                 with a BER of 10-7 or better to successfully complete
                 initialization."
         ::= { accessSwitchVdslLineConfProfileEntry 4 }

       accessSwitchVdslVtuoConfMaxSnrMgn OBJECT-TYPE
             SYNTAX      INTEGER
             ACCESS      read-create
             STATUS      mandatory
             DESCRIPTION
                 "Configured Maximum acceptable Signal/Noise Margin in 0.01dB.
                 If the Noise Margin is above this the modem should
                 attempt to reduce its power output to optimize its
                 operation."
         ::= { accessSwitchVdslLineConfProfileEntry 5 }

         accessSwitchVdslVtuoConfMinSnrMgn  OBJECT-TYPE
             SYNTAX      INTEGER
             ACCESS      read-create
             STATUS      mandatory
             DESCRIPTION
                 "Configured Minimum acceptable Signal/Noise Margin in 0.01dB.
                 If the noise margin falls below this level, the modem
                 should attempt to increase its power output.  If that
                 is not possible the modem will attempt to
                 re-initialize or shut down."
         ::= { accessSwitchVdslLineConfProfileEntry 6 }

         accessSwitchVdslVturConfRate OBJECT-TYPE
             SYNTAX  INTEGER
             ACCESS  read-create
             STATUS  mandatory
             DESCRIPTION
                      "Transmission rate in bits-per-second specified by this VTU."
         ::= { accessSwitchVdslLineConfProfileEntry 7 }

         accessSwitchVdslVturConfTargetSnrMgn OBJECT-TYPE
             SYNTAX      INTEGER
             ACCESS      read-create
             STATUS      mandatory
             DESCRIPTION
                 "Configured Target Signal/Noise Margin in 0.01dB.
                 This is the Noise Margin the modem must achieve
                 with a BER of 10-7 or better to successfully complete
                 initialization."
         ::= { accessSwitchVdslLineConfProfileEntry 8 }

       accessSwitchVdslVturConfMaxSnrMgn OBJECT-TYPE
             SYNTAX      INTEGER
             ACCESS      read-create
             STATUS      mandatory
             DESCRIPTION
                 "Configured Maximum acceptable Signal/Noise Margin in 0.01dB.
                 If the Noise Margin is above this the modem should
                 attempt to reduce its power output to optimize its
                 operation."
         ::= { accessSwitchVdslLineConfProfileEntry 9 }

         accessSwitchVdslVturConfMinSnrMgn  OBJECT-TYPE
             SYNTAX      INTEGER
             ACCESS      read-create
             STATUS      mandatory
             DESCRIPTION
                 "Configured Minimum acceptable Signal/Noise Margin in 0.01dB.
                 If the noise margin falls below this level, the modem
                 should attempt to increase its power output.  If that
                 is not possible the modem will attempt to
                 re-initialize or shut down."
         ::= { accessSwitchVdslLineConfProfileEntry 10 }

         accessSwitchVdslLineConfProfileRowStatus OBJECT-TYPE
             SYNTAX          RowStatus
             ACCESS          read-create
             STATUS          mandatory
             DESCRIPTION
                 "This object is used to create a new row or modify or
                 delete an existing row in this table.
                 A profile activated by setting this object to
                 `active'.  When `active' is set, the system
                 will validate the profile.

                 Before a profile can be deleted or taken out of
                 service, (by setting this object to `destroy' or
                 `outOfService') it must be first unreferenced
                 from all associated lines.

                 If the implementator of this MIB has chosen not
                 to implement `dynamic assignment' of profiles, this
                 object's MIN-ACCESS is read-only and its value
                 is always to be `active'."
         ::= { accessSwitchVdslLineConfProfileEntry 11 }

	vesMaxNumOfProfiles OBJECT-TYPE
        SYNTAX  INTEGER
        ACCESS  read-only
        STATUS  mandatory
        DESCRIPTION
                      "The maximum number of VDSL profiles which the system supports."
        ::= { accessSwitchVdslLineMibObjects 11 }

	 -- accessSwitch VDSL VTU-O QAM Table

   	 accessSwitchVdslVtuoQamTable   OBJECT-TYPE
             SYNTAX          SEQUENCE OF AccessSwitchVdslVtuoQamEntry
             ACCESS          not-accessible
             STATUS          mandatory
             DESCRIPTION
                 "This table provides one row for each VTU-O if QAM is used.
                 Each row contains the modulation parameters for that VTU-O."
         ::= { accessSwitchVdslLCSQam 1 }

         accessSwitchVdslVtuoQamEntry   OBJECT-TYPE
             SYNTAX          AccessSwitchVdslVtuoQamEntry
             ACCESS          not-accessible
             STATUS          mandatory
             DESCRIPTION     "An entry in the accessSwitchVdslVtuoQamTable."
             INDEX           { ifIndex }
         ::= { accessSwitchVdslVtuoQamTable 1 }

         AccessSwitchVdslVtuoQamEntry ::=
             SEQUENCE {
		accessSwitchVdslVtuoQamConstellation		INTEGER,
		accessSwitchVdslVtuoQamInterpolation	        INTEGER,
		accessSwitchVdslVtuoQamFc		        INTEGER
             }

         accessSwitchVdslVtuoQamConstellation OBJECT-TYPE
             SYNTAX      INTEGER
             ACCESS  	 read-only
             STATUS      mandatory
             DESCRIPTION
                 "Modulation method used by this VTU."
         ::= { accessSwitchVdslVtuoQamEntry 1 }

         accessSwitchVdslVtuoQamInterpolation OBJECT-TYPE
             SYNTAX      INTEGER
             ACCESS  	 read-only
             STATUS      mandatory
             DESCRIPTION
                 "Modulation speed used by this VTU."
         ::= { accessSwitchVdslVtuoQamEntry 2 }

         accessSwitchVdslVtuoQamFc OBJECT-TYPE
             SYNTAX      INTEGER
             ACCESS  	 read-only
             STATUS      mandatory
             DESCRIPTION
                 "Carrier frequency in Hz used by this ATU."
         ::= { accessSwitchVdslVtuoQamEntry 3 }


	 -- accessSwitch VDSL VTU-R QAM Table

   	 accessSwitchVdslVturQamTable   OBJECT-TYPE
             SYNTAX          SEQUENCE OF AccessSwitchVdslVturQamEntry
             ACCESS          not-accessible
             STATUS          mandatory
             DESCRIPTION
                 "This table provides one row for each VTU-R if QAM is used.
                 Each row contains the modulation parameters for that VTU-R."
         ::= { accessSwitchVdslLCSQam 2 }

         accessSwitchVdslVturQamEntry   OBJECT-TYPE
             SYNTAX          AccessSwitchVdslVturQamEntry
             ACCESS          not-accessible
             STATUS          mandatory
             DESCRIPTION     "An entry in the accessSwitchVdslVturQamTable."
             INDEX           { ifIndex }
         ::= { accessSwitchVdslVturQamTable 1 }

         AccessSwitchVdslVturQamEntry ::=
             SEQUENCE {
		accessSwitchVdslVturQamConstellation		INTEGER,
		accessSwitchVdslVturQamInterpolation	        INTEGER,
		accessSwitchVdslVturQamFc		        INTEGER
             }

         accessSwitchVdslVturQamConstellation OBJECT-TYPE
             SYNTAX      INTEGER
             ACCESS  	 read-only
             STATUS      mandatory
             DESCRIPTION
                 "Modulation method used by this VTU."
         ::= { accessSwitchVdslVturQamEntry 1 }

         accessSwitchVdslVturQamInterpolation OBJECT-TYPE
             SYNTAX      INTEGER
             ACCESS  	 read-only
             STATUS      mandatory
             DESCRIPTION
                 "Modulation speed used by this VTU."
         ::= { accessSwitchVdslVturQamEntry 2 }

         accessSwitchVdslVturQamFc OBJECT-TYPE
             SYNTAX      INTEGER
             ACCESS  	 read-only
             STATUS      mandatory
             DESCRIPTION
                 "Carrier frequency in Hz used by this ATU."
         ::= { accessSwitchVdslVturQamEntry 3 }


END
