ZYXEL-XGS360026F-FUNCTION-MIB DEFINITIONS ::= BEGIN

IMPORTS
    DisplayString,MacAddress FROM SNMPv2-TC
    MODULE-COMPLIANCE,OBJECT-GROUP, NOTIFICATION-GROUP       FROM SNMPv2-CONF
    ifIndex    FROM RFC1213-MIB
    enterprises,MODULE-IDENTITY,OBJECT-TYPE,NOTIFICATION-TYPE,Counter32,Counter64,IpAddress        FROM SNMPv2-SMI
    InetAddress                   FROM INET-ADDRESS-MIB
    MacAddress FROM BRIDGE-MIB;

zyxel MODULE-IDENTITY
        LAST-UPDATED "201205150000Z"
        ORGANIZATION "Corp."
        CONTACT-INFO
            ""
        DESCRIPTION
            ""
        ::= { enterprises 890 }

products                                                         OBJECT IDENTIFIER ::= { zyxel 1 }

accessSwitch                                                    OBJECT IDENTIFIER ::= { products 5 }

esSeries                                                        OBJECT IDENTIFIER ::= { accessSwitch 8 }

xgs360026fProductId                                             OBJECT IDENTIFIER ::= { esSeries 77 }

xgs360026fSystem                                                OBJECT IDENTIFIER ::= { xgs360026fProductId 1 }

xgs360026fSystemInformation                                     OBJECT IDENTIFIER ::= { xgs360026fSystem 1 }

xgs360026fModelName OBJECT-TYPE
   SYNTAX       DisplayString
   MAX-ACCESS   read-only
   STATUS       current
   DESCRIPTION
       ""
 ::= { xgs360026fSystemInformation 1 }

xgs360026fBIOSVersion OBJECT-TYPE
   SYNTAX       DisplayString
   MAX-ACCESS   read-only
   STATUS       current
   DESCRIPTION
       ""
   ::= { xgs360026fSystemInformation 2 }

xgs360026fFirmwareVersion OBJECT-TYPE
   SYNTAX       DisplayString
   MAX-ACCESS   read-only
   STATUS       current
   DESCRIPTION
       ""
   ::= { xgs360026fSystemInformation 3 }

xgs360026fHardwareMechanicalVersion OBJECT-TYPE
   SYNTAX       DisplayString
   MAX-ACCESS   read-only
   STATUS       current
   DESCRIPTION
       ""
   ::= { xgs360026fSystemInformation 4 }

xgs360026fSeriesNumber OBJECT-TYPE
   SYNTAX       DisplayString
   MAX-ACCESS   read-only
   STATUS       current
   DESCRIPTION
       ""
   ::= { xgs360026fSystemInformation 5 }

xgs360026fHostMACAddress OBJECT-TYPE
   SYNTAX       MacAddress
   MAX-ACCESS   read-only
   STATUS       current
   DESCRIPTION
       ""
   ::= { xgs360026fSystemInformation 6 }

xgs360026fConsoleBaudrate OBJECT-TYPE
   SYNTAX       DisplayString
   MAX-ACCESS   read-only
   STATUS       current
   DESCRIPTION
       ""
   ::= { xgs360026fSystemInformation 7 }

xgs360026fRAMSize OBJECT-TYPE
   SYNTAX       DisplayString
   MAX-ACCESS   read-only
   STATUS       current
   DESCRIPTION
       ""
   ::= { xgs360026fSystemInformation 8 }

xgs360026fFlashSize OBJECT-TYPE
   SYNTAX       DisplayString
   MAX-ACCESS   read-only
   STATUS       current
   DESCRIPTION
       ""
   ::= { xgs360026fSystemInformation 9 }

xgs360026fBridgeFBDSize OBJECT-TYPE
   SYNTAX       DisplayString
   MAX-ACCESS   read-only
   STATUS       current
   DESCRIPTION
       ""
   ::= { xgs360026fSystemInformation 10 }

xgs360026fTransmitQueue OBJECT-TYPE
   SYNTAX       DisplayString
   MAX-ACCESS   read-only
   STATUS       current
   DESCRIPTION
       ""
   ::= { xgs360026fSystemInformation 11 }

xgs360026fMaximumFrameSize OBJECT-TYPE
   SYNTAX       DisplayString
   MAX-ACCESS   read-only
   STATUS       current
   DESCRIPTION
       ""
   ::= { xgs360026fSystemInformation 12 }

xgs360026fCPULoad OBJECT-TYPE
   SYNTAX       DisplayString
   MAX-ACCESS   read-only
   STATUS       current
   DESCRIPTION
       ""
   ::= { xgs360026fSystemInformation 13 }

xgs360026fFanSpeed OBJECT-TYPE
   SYNTAX       DisplayString
   MAX-ACCESS   read-only
   STATUS       current
   DESCRIPTION
       ""
   ::= { xgs360026fSystemInformation 14 }

xgs360026fPowers OBJECT-TYPE
   SYNTAX       DisplayString
   MAX-ACCESS   read-only
   STATUS       current
   DESCRIPTION
       ""
   ::= { xgs360026fSystemInformation 15 }

xgs360026fTemperature1 OBJECT-TYPE
   SYNTAX       DisplayString
   MAX-ACCESS   read-only
   STATUS       current
   DESCRIPTION
       ""
   ::= { xgs360026fSystemInformation 16 }

xgs360026fTemperature2 OBJECT-TYPE
   SYNTAX       DisplayString
   MAX-ACCESS   read-only
   STATUS       current
   DESCRIPTION
       ""
   ::= { xgs360026fSystemInformation 17 }

xgs360026fTemperature3 OBJECT-TYPE
   SYNTAX       DisplayString
   MAX-ACCESS   read-only
   STATUS       current
   DESCRIPTION
       ""
   ::= { xgs360026fSystemInformation 18 }

xgs360026fTemperature4 OBJECT-TYPE
   SYNTAX       DisplayString
   MAX-ACCESS   read-only
   STATUS       current
   DESCRIPTION
       ""
   ::= { xgs360026fSystemInformation 19 }


xgs360026fSystemTime                                            OBJECT IDENTIFIER ::= { xgs360026fSystem 2 }

xgs360026fSystemTimeManual                                      OBJECT IDENTIFIER ::= { xgs360026fSystemTime 1 }

xgs360026fSystemTimeManualClockSource OBJECT-TYPE
   SYNTAX       INTEGER(0|1)
   MAX-ACCESS   read-write
   STATUS       current
   DESCRIPTION
       "default: 0,
        0 : Use Local Settings,
        1 : Use NTP Server."
   ::= { xgs360026fSystemTimeManual 1 }

xgs360026fSystemTimeManualLocaltime OBJECT-TYPE
   SYNTAX       DisplayString
   MAX-ACCESS   read-write
   STATUS       current
   DESCRIPTION
       "Get/Set the system time of the device.
        The input format is 'Year-Month-Day Hour:Minute:Second'.
        ex: 2011-01-01 05:43:05  means 2011/1/1 - 05:43:05 .
        The value range:
        Year    : 2010 - 2090,
        Mouth   : 1 - 12,
        Day     : 1 - 31,
        Hour    : 0 - 23,
        Minute  : 0 - 59,
        Sec     : 0 - 59."
   ::= { xgs360026fSystemTimeManual 2 }

xgs360026fSystemTimeManualTimeZoneOffset OBJECT-TYPE
   SYNTAX       INTEGER(-720..780)
   MAX-ACCESS   read-write
   STATUS       current
   DESCRIPTION
       "Get/Set the NTP Time Zone.
        The value range is between -720 and 780 (minutes)."
   ::= { xgs360026fSystemTimeManual 3 }

xgs360026fSystemTimeManualDaylightSavings OBJECT-TYPE
   SYNTAX       INTEGER(0|1)
   MAX-ACCESS   read-write
   STATUS       current
   DESCRIPTION
       "default: 0,
        0 : Disable,
        1 : Enable."
   ::= { xgs360026fSystemTimeManual 4 }

xgs360026fSystemTimeManualTimeSetOffset OBJECT-TYPE
   SYNTAX       INTEGER(1..1440)
   MAX-ACCESS   read-write
   STATUS       current
   DESCRIPTION
       "Get/Set the Daylight Saving Time.
        The value range is between 1 and 1440 (minutes),
        Default : 60 (minutes)."
   ::= { xgs360026fSystemTimeManual 5 }

xgs360026fSystemTimeManualDaylightSavingsType OBJECT-TYPE
   SYNTAX       INTEGER(0|1)
   MAX-ACCESS   read-write
   STATUS       current
   DESCRIPTION
       "default: 0,
        0 : By dates,
        1 : Recurring."
   ::= { xgs360026fSystemTimeManual 6 }

xgs360026fSystemTimeManualDaylightSavingsBydatesFrom OBJECT-TYPE
   SYNTAX       DisplayString
   MAX-ACCESS   read-write
   STATUS       current
   DESCRIPTION
       "Get/Set the Start time of By dates Daylight Savings.
        The input format is 'Year-Month-Day Hour:Minute'.
        ex: 2011-01-01 05:43  means 2011/1/1 - 05:43 .
        The value range:
        Year    : 2010 - 2090,
        Mouth   : 1 - 12,
        Day     : 1 - 31,
        Hour    : 0 - 23,
        Minute  : 0 - 59."
   ::= { xgs360026fSystemTimeManual 7 }

xgs360026fSystemTimeManualDaylightSavingsBydatesTo OBJECT-TYPE
   SYNTAX       DisplayString
   MAX-ACCESS   read-write
   STATUS       current
   DESCRIPTION
       "Get/Set the End time of By dates Daylight Savings.
        The input format is 'Year-Month-Day Hour:Minute'.
        ex: 2011-01-01 05:43  means 2011/1/1 - 05:43 .
        The value range:
        Year    : 2010 - 2090,
        Mouth   : 1 - 12,
        Day     : 1 - 31,
        Hour    : 0 - 23,
        Minute  : 0 - 59."
   ::= { xgs360026fSystemTimeManual 8 }

xgs360026fSystemTimeManualDaylightSavingsRecurringDayFrom OBJECT-TYPE
   SYNTAX       INTEGER(0..6)
   MAX-ACCESS   read-write
   STATUS       current
   DESCRIPTION
       "Get/Set the Daylight Saving Time Day From.
        0 : Sun, 1 : Mon, 2 : Tue, 3 : Wed, 4 : Thu, 5 : Fri, 6 : Sat."
   ::= { xgs360026fSystemTimeManual 9 }

xgs360026fSystemTimeManualDaylightSavingsRecurringWeekFrom OBJECT-TYPE
   SYNTAX       INTEGER(1..5)
   MAX-ACCESS   read-write
   STATUS       current
   DESCRIPTION
       "Get/Set the Daylight Saving Time Week From.
        1 : first week, 2, 3, 4, 5 : last week"
   ::= { xgs360026fSystemTimeManual 10 }

xgs360026fSystemTimeManualDaylightSavingsRecurringMonthFrom OBJECT-TYPE
   SYNTAX       INTEGER(0..11)
   MAX-ACCESS   read-write
   STATUS       current
   DESCRIPTION
       "Get/Set the Daylight Saving Time Month From.
        1 : Jan, 2 : Feb, 3 : Mar, 4 : Apr, 5 : May, 6 : Jun,
        7 : Jul, 8 : Aug, 9 : Sep, 10 : Oct, 11 : Nov, 12 : Dec."
   ::= { xgs360026fSystemTimeManual 11 }

xgs360026fSystemTimeManualDaylightSavingsRecurringTimeFrom OBJECT-TYPE
   SYNTAX       DisplayString
   MAX-ACCESS   read-write
   STATUS       current
   DESCRIPTION
       "Get/Set the Start time of By dates Daylight Savings.
        The input format is 'Hour:Minute'.
        ex: 05:43.
        The value range:
        Hour    : 0 - 23,
        Minute  : 0 - 59."
   ::= { xgs360026fSystemTimeManual 12 }

xgs360026fSystemTimeManualDaylightSavingsRecurringDayTo OBJECT-TYPE
   SYNTAX       INTEGER(0..6)
   MAX-ACCESS   read-write
   STATUS       current
   DESCRIPTION
       "Get/Set the Daylight Saving Time Day To.
        0 : Sun, 1 : Mon, 2 : Tue, 3 : Wed, 4 : Thu, 5 : Fri, 6 : Sat."
   ::= { xgs360026fSystemTimeManual 13 }

xgs360026fSystemTimeManualDaylightSavingsRecurringWeekTo OBJECT-TYPE
   SYNTAX       INTEGER(1..5)
   MAX-ACCESS   read-write
   STATUS       current
   DESCRIPTION
       "Get/Set the Daylight Saving Time Week To.
        1 : first week, 2, 3, 4, 5 : last week"
   ::= { xgs360026fSystemTimeManual 14 }

xgs360026fSystemTimeManualDaylightSavingsRecurringMonthTo OBJECT-TYPE
   SYNTAX       INTEGER(0..11)
   MAX-ACCESS   read-write
   STATUS       current
   DESCRIPTION
       "Get/Set the Daylight Saving Time Month To.
        1 : Jan, 2 : Feb, 3 : Mar, 4 : Apr, 5 : May, 6 : Jun,
        7 : Jul, 8 : Aug, 9 : Sep, 10 : Oct, 11 : Nov, 12 : Dec."
   ::= { xgs360026fSystemTimeManual 15 }

xgs360026fSystemTimeManualDaylightSavingsRecurringTimeTo OBJECT-TYPE
   SYNTAX       DisplayString
   MAX-ACCESS   read-write
   STATUS       current
   DESCRIPTION
       "Get/Set the Start time of By dates Daylight Savings.
        The input format is 'Hour:Minute'.
        ex: 05:43.
        The value range:
        Hour    : 0 - 23,
        Minute  : 0 - 59."
   ::= { xgs360026fSystemTimeManual 16 }

xgs360026fSystemTimeNTP                                     OBJECT IDENTIFIER ::= { xgs360026fSystemTime 2 }

xgs360026fSystemTimeNTPTable OBJECT-TYPE
   SYNTAX      SEQUENCE OF XGS360026FSystemTimeNTPEntry
   MAX-ACCESS  not-accessible
   STATUS      current
   DESCRIPTION
       " "
   ::= { xgs360026fSystemTimeNTP 1 }

xgs360026fSystemTimeNTPEntry OBJECT-TYPE
   SYNTAX      XGS360026FSystemTimeNTPEntry
   MAX-ACCESS  not-accessible
   STATUS      current
   DESCRIPTION
       ""
   INDEX    { xgs360026fSystemTimeNTPIndex  }
   ::= { xgs360026fSystemTimeNTPTable 1 }

XGS360026FSystemTimeNTPEntry ::= SEQUENCE {
   xgs360026fSystemTimeNTPIndex             INTEGER,
   xgs360026fSystemTimeNTPServerIPType      INTEGER,
   xgs360026fSystemTimeNTPServer            DisplayString,
   xgs360026fSystemTimeNTPCurrentMode       INTEGER
}

xgs360026fSystemTimeNTPIndex OBJECT-TYPE
   SYNTAX      INTEGER (1..5)
   MAX-ACCESS  not-accessible
   STATUS      current
   DESCRIPTION
       " The index of the ntp entry. "
   ::= { xgs360026fSystemTimeNTPEntry 1 }

xgs360026fSystemTimeNTPServerIPType OBJECT-TYPE
   SYNTAX       INTEGER(0|1)
   MAX-ACCESS   read-write
   STATUS       current
   DESCRIPTION
       "Default: 0,
        0 : IPv4,
        1 : IPv6."
   ::= { xgs360026fSystemTimeNTPEntry 2 }

xgs360026fSystemTimeNTPServer OBJECT-TYPE
   SYNTAX       DisplayString
   MAX-ACCESS   read-write
   STATUS       current
   DESCRIPTION
       "Get/Set the NTP Time Server1. You can use the IP address or domain name."
   ::= { xgs360026fSystemTimeNTPEntry 3 }

xgs360026fSystemTimeNTPCurrentMode OBJECT-TYPE
   SYNTAX      INTEGER (0..3)
   MAX-ACCESS  read-write
   STATUS      current
   DESCRIPTION
       " 0: Empty
        1: Active
        2: Edit
        3: Delete"
   ::= { xgs360026fSystemTimeNTPEntry 4 }


xgs360026fSystemAccount                                         OBJECT IDENTIFIER ::= { xgs360026fSystem 3 }

xgs360026fSystemAccountUsers                                    OBJECT IDENTIFIER ::= { xgs360026fSystemAccount 1 }

xgs360026fSystemAccountUserCreate OBJECT-TYPE
   SYNTAX       INTEGER(0|1)
   MAX-ACCESS   read-write
   STATUS       current
   DESCRIPTION
       "default: 0
        0 : None  (read only)
        1 : Create a user account"
   ::= { xgs360026fSystemAccountUsers 1 }

xgs360026fSystemAccountUsersTable OBJECT-TYPE
   SYNTAX      SEQUENCE OF XGS360026FSystemAccountUsersEntry
   MAX-ACCESS  not-accessible
   STATUS      current
   DESCRIPTION
       " "
   ::= { xgs360026fSystemAccountUsers 2 }

xgs360026fSystemAccountUsersEntry OBJECT-TYPE
   SYNTAX      XGS360026FSystemAccountUsersEntry
   MAX-ACCESS  not-accessible
   STATUS      current
   DESCRIPTION
       ""
   INDEX    { xgs360026fUserIndex  }
   ::= { xgs360026fSystemAccountUsersTable 1 }


XGS360026FSystemAccountUsersEntry ::= SEQUENCE {
   xgs360026fUserIndex              INTEGER,
   xgs360026fUserName               DisplayString,
   xgs360026fPassword               DisplayString,
   xgs360026fUserPrivilegeLevel     INTEGER,
   xgs360026fAccountUserRowStatus   INTEGER
}


xgs360026fUserIndex OBJECT-TYPE
   SYNTAX      INTEGER (1..20)
   MAX-ACCESS  not-accessible
   STATUS      current
   DESCRIPTION
       " "
   ::= { xgs360026fSystemAccountUsersEntry 1 }

xgs360026fUserName OBJECT-TYPE
   SYNTAX      DisplayString (SIZE (1..32))
   MAX-ACCESS  read-write
   STATUS      current
   DESCRIPTION
       " "
   ::= { xgs360026fSystemAccountUsersEntry 2 }

xgs360026fPassword OBJECT-TYPE
   SYNTAX      DisplayString (SIZE (1..32))
   MAX-ACCESS  read-write
   STATUS      current
   DESCRIPTION
       " "
   ::= { xgs360026fSystemAccountUsersEntry 3 }

xgs360026fUserPrivilegeLevel OBJECT-TYPE
   SYNTAX      INTEGER (1..15)
   MAX-ACCESS  read-write
   STATUS      current
   DESCRIPTION
       "default:1
        User privilege level range : 1 - 15"
   ::= { xgs360026fSystemAccountUsersEntry 4 }

xgs360026fAccountUserRowStatus OBJECT-TYPE
   SYNTAX      INTEGER (1..5)
   MAX-ACCESS  read-write
   STATUS      current
   DESCRIPTION
       " 1: active
        2: notInservice
        3: edit
        4: destroy
        5: undo"
   ::= { xgs360026fSystemAccountUsersEntry 5 }

xgs360026fSystemAccountPrivilegeLevel                           OBJECT IDENTIFIER ::= { xgs360026fSystemAccount 2 }

xgs360026fAccountPrivilegeLevel OBJECT-TYPE
   SYNTAX      INTEGER (1..15)
   MAX-ACCESS  read-write
   STATUS      current
   DESCRIPTION
       "Default:10, Range : 1-15. "
   ::= { xgs360026fSystemAccountPrivilegeLevel 1 }

xgs360026fAggregationPrivilegeLevel OBJECT-TYPE
   SYNTAX      INTEGER (1..15)
   MAX-ACCESS  read-write
   STATUS      current
   DESCRIPTION
       "Default:10, Range : 1-15. "
   ::= { xgs360026fSystemAccountPrivilegeLevel 2 }

xgs360026fDiagnosticsPrivilegeLevel OBJECT-TYPE
   SYNTAX      INTEGER (1..15)
   MAX-ACCESS  read-write
   STATUS      current
   DESCRIPTION
       "Default:10, Range : 1-15. "
   ::= { xgs360026fSystemAccountPrivilegeLevel 3 }

xgs360026fEPSPrivilegeLevel OBJECT-TYPE
   SYNTAX      INTEGER (1..15)
   MAX-ACCESS  read-write
   STATUS      current
   DESCRIPTION
       "Default:10, Range : 1-15. "
   ::= { xgs360026fSystemAccountPrivilegeLevel 5 }

xgs360026fERPSPrivilegeLevel OBJECT-TYPE
   SYNTAX      INTEGER (1..15)
   MAX-ACCESS  read-write
   STATUS      current
   DESCRIPTION
       "Default:10, Range : 1-15. "
   ::= { xgs360026fSystemAccountPrivilegeLevel 6 }

xgs360026fETHLinkOAMPrivilegeLevel OBJECT-TYPE
   SYNTAX      INTEGER (1..15)
   MAX-ACCESS  read-write
   STATUS      current
   DESCRIPTION
       "Default:10, Range : 1-15. "
   ::= { xgs360026fSystemAccountPrivilegeLevel 7 }

xgs360026fEVCPrivilegeLevel OBJECT-TYPE
   SYNTAX      INTEGER (1..15)
   MAX-ACCESS  read-write
   STATUS      current
   DESCRIPTION
       "Default:10, Range : 1-15. "
   ::= { xgs360026fSystemAccountPrivilegeLevel 8 }

xgs360026fGARPPrivilegeLevel OBJECT-TYPE
   SYNTAX      INTEGER (1..15)
   MAX-ACCESS  read-write
   STATUS      current
   DESCRIPTION
       "Default:10, Range : 1-15. "
   ::= { xgs360026fSystemAccountPrivilegeLevel 10 }

xgs360026fGVRPPrivilegeLevel OBJECT-TYPE
   SYNTAX      INTEGER (1..15)
   MAX-ACCESS  read-write
   STATUS      current
   DESCRIPTION
       "Default:10, Range : 1-15. "
   ::= { xgs360026fSystemAccountPrivilegeLevel 11 }

xgs360026fIPPrivilegeLevel OBJECT-TYPE
   SYNTAX      INTEGER (1..15)
   MAX-ACCESS  read-write
   STATUS      current
   DESCRIPTION
       "Default:10, Range : 1-15. "
   ::= { xgs360026fSystemAccountPrivilegeLevel 12 }

xgs360026fIPMCSnoopingPrivilegeLevel OBJECT-TYPE
   SYNTAX      INTEGER (1..15)
   MAX-ACCESS  read-write
   STATUS      current
   DESCRIPTION
       "Default:10, Range : 1-15. "
   ::= { xgs360026fSystemAccountPrivilegeLevel 13 }

xgs360026fLACPPrivilegeLevel OBJECT-TYPE
   SYNTAX      INTEGER (1..15)
   MAX-ACCESS  read-write
   STATUS      current
   DESCRIPTION
       "Default:10, Range : 1-15. "
   ::= { xgs360026fSystemAccountPrivilegeLevel 14 }

xgs360026fLLDPPrivilegeLevel OBJECT-TYPE
   SYNTAX      INTEGER (1..15)
   MAX-ACCESS  read-write
   STATUS      current
   DESCRIPTION
       "Default:10, Range : 1-15. "
   ::= { xgs360026fSystemAccountPrivilegeLevel 15 }

xgs360026fLLDPMEDPrivilegeLevel OBJECT-TYPE
   SYNTAX      INTEGER (1..15)
   MAX-ACCESS  read-write
   STATUS      current
   DESCRIPTION
       "Default:10, Range : 1-15. "
   ::= { xgs360026fSystemAccountPrivilegeLevel 16 }

xgs360026fLoopProtectPrivilegeLevel OBJECT-TYPE
   SYNTAX      INTEGER (1..15)
   MAX-ACCESS  read-write
   STATUS      current
   DESCRIPTION
       "Default:10, Range : 1-15. "
   ::= { xgs360026fSystemAccountPrivilegeLevel 17 }

xgs360026fMACTablePrivilegeLevel OBJECT-TYPE
   SYNTAX      INTEGER (1..15)
   MAX-ACCESS  read-write
   STATUS      current
   DESCRIPTION
       "Default:10, Range : 1-15. "
   ::= { xgs360026fSystemAccountPrivilegeLevel 18 }

xgs360026fMEPPrivilegeLevel OBJECT-TYPE
   SYNTAX      INTEGER (1..15)
   MAX-ACCESS  read-write
   STATUS      current
   DESCRIPTION
       "Default:10, Range : 1-15. "
   ::= { xgs360026fSystemAccountPrivilegeLevel 20 }

xgs360026fMRSTPPrivilegeLevel OBJECT-TYPE
   SYNTAX      INTEGER (1..15)
   MAX-ACCESS  read-write
   STATUS      current
   DESCRIPTION
       "Default:10, Range : 1-15. "
   ::= { xgs360026fSystemAccountPrivilegeLevel 21 }

xgs360026fMVRPrivilegeLevel OBJECT-TYPE
   SYNTAX      INTEGER (1..15)
   MAX-ACCESS  read-write
   STATUS      current
   DESCRIPTION
       "Default:10, Range : 1-15. "
   ::= { xgs360026fSystemAccountPrivilegeLevel 22 }

xgs360026fMaintenancePrivilegeLevel OBJECT-TYPE
   SYNTAX      INTEGER (1..15)
   MAX-ACCESS  read-write
   STATUS      current
   DESCRIPTION
       "Default:10, Range : 1-15. "
   ::= { xgs360026fSystemAccountPrivilegeLevel 24 }

xgs360026fMirroringPrivilegeLevel OBJECT-TYPE
   SYNTAX      INTEGER (1..15)
   MAX-ACCESS  read-write
   STATUS      current
   DESCRIPTION
       "Default:10, Range : 1-15. "
   ::= { xgs360026fSystemAccountPrivilegeLevel 25 }

xgs360026fPTPPrivilegeLevel OBJECT-TYPE
   SYNTAX      INTEGER (1..15)
   MAX-ACCESS  read-write
   STATUS      current
   DESCRIPTION
       "Default:10, Range : 1-15. "
   ::= { xgs360026fSystemAccountPrivilegeLevel 26 }

xgs360026fPortsPrivilegeLevel OBJECT-TYPE
   SYNTAX      INTEGER (1..15)
   MAX-ACCESS  read-write
   STATUS      current
   DESCRIPTION
       "Default:10, Range : 1-15. "
   ::= { xgs360026fSystemAccountPrivilegeLevel 27 }

xgs360026fPrivateVLANsPrivilegeLevel OBJECT-TYPE
   SYNTAX      INTEGER (1..15)
   MAX-ACCESS  read-write
   STATUS      current
   DESCRIPTION
       "Default:10, Range : 1-15. "
   ::= { xgs360026fSystemAccountPrivilegeLevel 28 }

xgs360026fQoSPrivilegeLevel OBJECT-TYPE
   SYNTAX      INTEGER (1..15)
   MAX-ACCESS  read-write
   STATUS      current
   DESCRIPTION
       "Default:10, Range : 1-15. "
   ::= { xgs360026fSystemAccountPrivilegeLevel 29 }

xgs360026fSMTPPrivilegeLevel OBJECT-TYPE
   SYNTAX      INTEGER (1..15)
   MAX-ACCESS  read-write
   STATUS      current
   DESCRIPTION
       "Default:10, Range : 1-15. "
   ::= { xgs360026fSystemAccountPrivilegeLevel 31 }

xgs360026fSNMPPrivilegeLevel OBJECT-TYPE
   SYNTAX      INTEGER (1..15)
   MAX-ACCESS  read-write
   STATUS      current
   DESCRIPTION
       "Default:10, Range : 1-15. "
   ::= { xgs360026fSystemAccountPrivilegeLevel 32 }

xgs360026fSecurityPrivilegeLevel OBJECT-TYPE
   SYNTAX      INTEGER (1..15)
   MAX-ACCESS  read-write
   STATUS      current
   DESCRIPTION
       "Default:10, Range : 1-15. "
   ::= { xgs360026fSystemAccountPrivilegeLevel 33 }

xgs360026fSpanningTreePrivilegeLevel OBJECT-TYPE
   SYNTAX      INTEGER (1..15)
   MAX-ACCESS  read-write
   STATUS      current
   DESCRIPTION
       "Default:10, Range : 1-15. "
   ::= { xgs360026fSystemAccountPrivilegeLevel 35 }

xgs360026fSystemPrivilegeLevel OBJECT-TYPE
   SYNTAX      INTEGER (1..15)
   MAX-ACCESS  read-write
   STATUS      current
   DESCRIPTION
       "Default:10, Range : 1-15. "
   ::= { xgs360026fSystemAccountPrivilegeLevel 36 }

xgs360026fTrapEventPrivilegeLevel OBJECT-TYPE
   SYNTAX      INTEGER (1..15)
   MAX-ACCESS  read-write
   STATUS      current
   DESCRIPTION
       "Default:10, Range : 1-15. "
   ::= { xgs360026fSystemAccountPrivilegeLevel 37 }

xgs360026fVCLPrivilegeLevel OBJECT-TYPE
   SYNTAX      INTEGER (1..15)
   MAX-ACCESS  read-write
   STATUS      current
   DESCRIPTION
       "Default:10, Range : 1-15. "
   ::= { xgs360026fSystemAccountPrivilegeLevel 39 }

xgs360026fVLANTranslationPrivilegeLevel OBJECT-TYPE
   SYNTAX      INTEGER (1..15)
   MAX-ACCESS  read-write
   STATUS      current
   DESCRIPTION
       "Default:10, Range : 1-15. "
   ::= { xgs360026fSystemAccountPrivilegeLevel 40 }

xgs360026fVLANsPrivilegeLevel OBJECT-TYPE
   SYNTAX      INTEGER (1..15)
   MAX-ACCESS  read-write
   STATUS      current
   DESCRIPTION
       "Default:10, Range : 1-15. "
   ::= { xgs360026fSystemAccountPrivilegeLevel 41 }


xgs360026fIP                                                    OBJECT IDENTIFIER ::= { xgs360026fSystem 4 }

xgs360026fIPv4                                                  OBJECT IDENTIFIER ::= { xgs360026fIP 1 }

xgs360026fIPv4Configured                                                  OBJECT IDENTIFIER ::= { xgs360026fIPv4 1 }

xgs360026fIpv4DHCPClient OBJECT-TYPE
   SYNTAX      INTEGER (0|1)
   MAX-ACCESS  read-write
   STATUS      current
   DESCRIPTION
       "default:0
       0: disable
       1: enable"
   ::= { xgs360026fIPv4Configured 1 }

xgs360026fIPv4Address OBJECT-TYPE
   SYNTAX      IpAddress
   MAX-ACCESS  read-write
   STATUS      current
   DESCRIPTION
       ""
   ::= { xgs360026fIPv4Configured 2 }

xgs360026fIPv4Mask OBJECT-TYPE
   SYNTAX      IpAddress
   MAX-ACCESS  read-write
   STATUS      current
   DESCRIPTION
       ""
   ::= { xgs360026fIPv4Configured 3 }

xgs360026fIPv4Router OBJECT-TYPE
   SYNTAX      IpAddress
   MAX-ACCESS  read-write
   STATUS      current
   DESCRIPTION
       ""
   ::= { xgs360026fIPv4Configured 4 }

xgs360026fIPv4VLANId OBJECT-TYPE
   SYNTAX      INTEGER (1..4094)
   MAX-ACCESS  read-write
   STATUS      current
   DESCRIPTION
       "default:1"
   ::= { xgs360026fIPv4Configured 5 }

xgs360026fIPv4DNSServer OBJECT-TYPE
   SYNTAX      IpAddress
   MAX-ACCESS  read-write
   STATUS      current
   DESCRIPTION
       ""
   ::= { xgs360026fIPv4Configured 6 }

xgs360026fIPv4DNSProxy OBJECT-TYPE
   SYNTAX      INTEGER (0|1)
   MAX-ACCESS  read-write
   STATUS      current
   DESCRIPTION
       " "
   ::= { xgs360026fIPv4Configured 7 }

xgs360026fIPv4Current                                                  OBJECT IDENTIFIER ::= { xgs360026fIPv4 2 }

xgs360026fIpv4CurrentDHCPClient OBJECT-TYPE
   SYNTAX      INTEGER (0|1)
   MAX-ACCESS  read-write
   STATUS      current
   DESCRIPTION
       "default:0
       0: none (for read)
       1: renew"
   ::= { xgs360026fIPv4Current 1 }

xgs360026fIPv4CurrentAddress OBJECT-TYPE
   SYNTAX      IpAddress
   MAX-ACCESS  read-only
   STATUS      current
   DESCRIPTION
       ""
   ::= { xgs360026fIPv4Current 2 }

xgs360026fIPv4CurrentMask OBJECT-TYPE
   SYNTAX      IpAddress
   MAX-ACCESS  read-only
   STATUS      current
   DESCRIPTION
       ""
   ::= { xgs360026fIPv4Current 3 }

xgs360026fIPv4CurrentRouter OBJECT-TYPE
   SYNTAX      IpAddress
   MAX-ACCESS  read-only
   STATUS      current
   DESCRIPTION
       ""
   ::= { xgs360026fIPv4Current 4 }

xgs360026fIPv4CurrentVLANId OBJECT-TYPE
   SYNTAX      INTEGER (1..4094)
   MAX-ACCESS  read-only
   STATUS      current
   DESCRIPTION
       "default:1"
   ::= { xgs360026fIPv4Current 5 }

xgs360026fIPv4CurrentDNSServer OBJECT-TYPE
   SYNTAX      IpAddress
   MAX-ACCESS  read-only
   STATUS      current
   DESCRIPTION
       ""
   ::= { xgs360026fIPv4Current 6 }


xgs360026fIPv6                                                  OBJECT IDENTIFIER ::= { xgs360026fIP 2 }

xgs360026fIPv6Configured                                                  OBJECT IDENTIFIER ::= { xgs360026fIPv6 1 }

xgs360026fIpv6AutoConfiguration OBJECT-TYPE
   SYNTAX      INTEGER (0|1)
   MAX-ACCESS  read-write
   STATUS      current
   DESCRIPTION
       "default:0
       0: disable
       1: enable"
   ::= { xgs360026fIPv6Configured 1 }

xgs360026fIpv6Address OBJECT-TYPE
   SYNTAX      DisplayString (SIZE (0..30))
   MAX-ACCESS  read-write
   STATUS      current
   DESCRIPTION
       ""
   ::= { xgs360026fIPv6Configured 2 }

xgs360026fIpv6Prefix OBJECT-TYPE
   SYNTAX      INTEGER (1..128)
   MAX-ACCESS  read-write
   STATUS      current
   DESCRIPTION
       "default: 96"
   ::= { xgs360026fIPv6Configured 3 }

xgs360026fIpv6Router OBJECT-TYPE
   SYNTAX      DisplayString (SIZE (0..30))
   MAX-ACCESS  read-write
   STATUS      current
   DESCRIPTION
       " "
   ::= { xgs360026fIPv6Configured 4 }

xgs360026fIPv6Current                                                  OBJECT IDENTIFIER ::= { xgs360026fIPv6 2 }

xgs360026fIpv6CurrentAutoConfiguration OBJECT-TYPE
   SYNTAX      INTEGER (0|1)
   MAX-ACCESS  read-only
   STATUS      current
   DESCRIPTION
       "default:0
       0: disable
       1: enable"
   ::= { xgs360026fIPv6Current 1 }

xgs360026fIpv6CurrentAddress OBJECT-TYPE
   SYNTAX      DisplayString (SIZE (0..30))
   MAX-ACCESS  read-only
   STATUS      current
   DESCRIPTION
       ""
   ::= { xgs360026fIPv6Current 2 }


xgs360026fIpv6CurrentLinkLocalAddress OBJECT-TYPE
   SYNTAX      DisplayString(SIZE (0..30))
   MAX-ACCESS  read-only
   STATUS      current
   DESCRIPTION
       ""
   ::= { xgs360026fIPv6Current 3 }


xgs360026fIpv6CurrentPrefix OBJECT-TYPE
   SYNTAX      INTEGER (1..128)
   MAX-ACCESS  read-only
   STATUS      current
   DESCRIPTION
       ""
   ::= { xgs360026fIPv6Current 4 }

xgs360026fIpv6CurrentRouter OBJECT-TYPE
   SYNTAX      DisplayString (SIZE (0..30))
   MAX-ACCESS  read-only
   STATUS      current
   DESCRIPTION
       " "
   ::= { xgs360026fIPv6Current 5 }

xgs360026fSyslog                                                OBJECT IDENTIFIER ::= { xgs360026fSystem 5 }

xgs360026fSyslogConf                                            OBJECT IDENTIFIER ::= { xgs360026fSyslog 1 }

xgs360026fServerMode OBJECT-TYPE
   SYNTAX      INTEGER (0|1)
   MAX-ACCESS  read-write
   STATUS      current
   DESCRIPTION
       "default: 0
       0: disable
       1: enable "
   ::= { xgs360026fSyslogConf 1 }

xgs360026fServerAddress1 OBJECT-TYPE
   SYNTAX      IpAddress
   MAX-ACCESS  read-write
   STATUS      current
   DESCRIPTION
       " "
   ::= { xgs360026fSyslogConf 2 }

xgs360026fServerAddress2 OBJECT-TYPE
   SYNTAX      IpAddress
   MAX-ACCESS  read-write
   STATUS      current
   DESCRIPTION
       " "
   ::= { xgs360026fSyslogConf 3 }

xgs360026fSyslogLevel OBJECT-TYPE
   SYNTAX      INTEGER(0..7)
   MAX-ACCESS  read-write
   STATUS      current
   DESCRIPTION
       "default: 6 (Info)
       0: Emergency
       1: Alert
       2: Critical
       3: Error
       4: Warning
       5: Notice
       6: Info
       7: Debug"
   ::= { xgs360026fSyslogConf 4 }

xgs360026fSyslogDetailedInfo                                    OBJECT IDENTIFIER ::= { xgs360026fSyslog 2 }

xgs360026fSyslogDetailedInfoClear OBJECT-TYPE
   SYNTAX      INTEGER(0|1)
   MAX-ACCESS  read-write
   STATUS      current
   DESCRIPTION
      "default: 0
       0 : None  (read only)
       1 : Clear Syslog"
   ::= { xgs360026fSyslogDetailedInfo 1 }

xgs360026fSyslogDetailedInfoTable OBJECT-TYPE
  SYNTAX      SEQUENCE OF XGS360026FSyslogDetailedInfoEntry
  MAX-ACCESS  not-accessible
  STATUS      current
  DESCRIPTION
           " "
       ::= { xgs360026fSyslogDetailedInfo 2 }

xgs360026fSyslogDetailedInfoEntry OBJECT-TYPE
   SYNTAX      XGS360026FSyslogDetailedInfoEntry
   MAX-ACCESS  not-accessible
   STATUS      current
   DESCRIPTION
           ""
   INDEX    { xgs360026fSyslogDetailedInfoIndex  }
   ::= { xgs360026fSyslogDetailedInfoTable 1 }

XGS360026FSyslogDetailedInfoEntry ::= SEQUENCE {
   xgs360026fSyslogDetailedInfoIndex       INTEGER,
   xgs360026fSyslogDetailedInfoLevel       DisplayString,
   xgs360026fSyslogDetailedInfoTime        DisplayString,
   xgs360026fSyslogDetailedInfoMessage     DisplayString
}

xgs360026fSyslogDetailedInfoIndex OBJECT-TYPE
   SYNTAX      INTEGER (1..1024)
   MAX-ACCESS  not-accessible
   STATUS      current
   DESCRIPTION
       " "
   ::= { xgs360026fSyslogDetailedInfoEntry 1 }

xgs360026fSyslogDetailedInfoLevel OBJECT-TYPE
   SYNTAX      DisplayString
   MAX-ACCESS  read-only
   STATUS      current
   DESCRIPTION
       " "
   ::= { xgs360026fSyslogDetailedInfoEntry 2 }

xgs360026fSyslogDetailedInfoTime OBJECT-TYPE
   SYNTAX      DisplayString(SIZE (0..20))
   MAX-ACCESS  read-only
   STATUS      current
   DESCRIPTION
       " "
   ::= { xgs360026fSyslogDetailedInfoEntry 3 }

xgs360026fSyslogDetailedInfoMessage OBJECT-TYPE
   SYNTAX      DisplayString
   MAX-ACCESS  read-only
   STATUS      current
   DESCRIPTION
       " "
   ::= { xgs360026fSyslogDetailedInfoEntry 4 }


xgs360026fSnmp                                                OBJECT IDENTIFIER ::= { xgs360026fSystem 6 }

xgs360026fSnmpConf                                            OBJECT IDENTIFIER ::= { xgs360026fSnmp 1 }

xgs360026fGetCommunity OBJECT-TYPE
   SYNTAX       DisplayString
   MAX-ACCESS   read-write
   STATUS       current
   DESCRIPTION
       "Get/Set the get-community of the SNMP."
   ::= { xgs360026fSnmpConf 1 }

xgs360026fSetCommunityMode OBJECT-TYPE
   SYNTAX       INTEGER(0|1)
   MAX-ACCESS   read-write
   STATUS       current
   DESCRIPTION
       "Get/Set the set-community mode of the SNMP.
        default : 1, 0: disable, 1: enable. "
   ::= { xgs360026fSnmpConf 2 }

xgs360026fSetCommunity OBJECT-TYPE
   SYNTAX       DisplayString
   MAX-ACCESS   read-write
   STATUS       current
   DESCRIPTION
       "Get/Set the set-community of the SNMP."
   ::= { xgs360026fSnmpConf 3 }

xgs360026fTrapHostConfTable OBJECT-TYPE
   SYNTAX      SEQUENCE OF XGS360026FTrapHostConfEntry
   MAX-ACCESS  not-accessible
   STATUS      current
   DESCRIPTION
       "A list of trap host entry. The numbers of entries are given by the value of xgs360026fTrapHostConfNumber."
   ::= { xgs360026fSnmpConf 4 }

xgs360026fTrapHostConfEntry OBJECT-TYPE
   SYNTAX      XGS360026FTrapHostConfEntry
   MAX-ACCESS  not-accessible
   STATUS      current
   DESCRIPTION
       "This is the entry information for trap host."
   INDEX    { xgs360026fTrapHostConfIndex  }
   ::= { xgs360026fTrapHostConfTable 1 }

XGS360026FTrapHostConfEntry ::= SEQUENCE {
    xgs360026fTrapHostConfIndex             INTEGER,
    xgs360026fTrapHostConfVersion           INTEGER,
    xgs360026fTrapHostConfIPType            INTEGER,
    xgs360026fTrapHostConfIP                DisplayString,
    xgs360026fTrapHostConfPort              INTEGER,
    xgs360026fTrapHostConfCommunity         DisplayString,
    xgs360026fTrapHostConfSeverityLevel     INTEGER,
    xgs360026fTrapHostConfSecurityLevel     INTEGER,
    xgs360026fTrapHostConfAuthPtc           INTEGER,
    xgs360026fTrapHostConfAuthPassword      DisplayString,
    xgs360026fTrapHostConfPrivPtc           INTEGER,
    xgs360026fTrapHostConfPrivPassword      DisplayString,
    xgs360026fTrapHostConfCurrentMode       INTEGER
}

xgs360026fTrapHostConfIndex OBJECT-TYPE
   SYNTAX      INTEGER (1..6)
   MAX-ACCESS  not-accessible
   STATUS      current
   DESCRIPTION
       " The index of the trap host entry. "
   ::= { xgs360026fTrapHostConfEntry 1 }

xgs360026fTrapHostConfVersion OBJECT-TYPE
   SYNTAX       INTEGER(2..3)
   MAX-ACCESS   read-write
   STATUS       current
   DESCRIPTION
       "The version of the Trap PDU. Version : 2(SNMPv2c), 3(SNMPv3)"
   ::= { xgs360026fTrapHostConfEntry 2 }

xgs360026fTrapHostConfIPType OBJECT-TYPE
   SYNTAX       INTEGER(4|6)
   MAX-ACCESS   read-write
   STATUS       current
   DESCRIPTION
       "Server IP Type. Default: 4,
        4 : IPv4,
        6 : IPv6."
   ::= { xgs360026fTrapHostConfEntry 3 }

xgs360026fTrapHostConfIP OBJECT-TYPE
   SYNTAX       DisplayString
   MAX-ACCESS   read-write
   STATUS       current
   DESCRIPTION
       "This is the IP of the trap host."
   ::= { xgs360026fTrapHostConfEntry 4 }

xgs360026fTrapHostConfPort OBJECT-TYPE
   SYNTAX       INTEGER(1..65535)
   MAX-ACCESS   read-write
   STATUS       current
   DESCRIPTION
       "This is the receiving-port number of the trap host.
        range : 1 - 65535."
   ::= { xgs360026fTrapHostConfEntry 5 }

xgs360026fTrapHostConfCommunity OBJECT-TYPE
   SYNTAX       DisplayString (SIZE (1..32))
   MAX-ACCESS   read-write
   STATUS       current
   DESCRIPTION
       "The community/security name for the trap PDU."
   ::= { xgs360026fTrapHostConfEntry 6 }

xgs360026fTrapHostConfSeverityLevel	OBJECT-TYPE
   SYNTAX       INTEGER(0..7)
   MAX-ACCESS   read-write
   STATUS       current
   DESCRIPTION
       "The Severity Level.
        0 : Emerg, 1 : Alert, 2 : Crit, 3 : Error, 4 : Warning, 5 : Notice, 6 : Info, 7 : Debug."
	::= { xgs360026fTrapHostConfEntry 7 }

xgs360026fTrapHostConfSecurityLevel	OBJECT-TYPE
   SYNTAX       INTEGER(1..3)
   MAX-ACCESS   read-write
   STATUS       current
   DESCRIPTION
       "The Security Level, NoAuthNoPriv, AuthNoPriv, and AuthPriv.
        1 : NoAuthNoPriv, 2 : AuthNoPriv, 3 : AuthPriv.
        Privacy protocol will be configured as 'DES' automatically if security level is 3(AuthPriv)."
	::= { xgs360026fTrapHostConfEntry 8 }

xgs360026fTrapHostConfAuthPtc	OBJECT-TYPE
   SYNTAX       INTEGER(1..2)
   MAX-ACCESS   read-write
   STATUS       current
   DESCRIPTION
       "Authentication Protocol, there are SHA and MD5 supported presently.
        1 : MD5, 2 : SHA."
	::= { xgs360026fTrapHostConfEntry 9 }

xgs360026fTrapHostConfAuthPassword	OBJECT-TYPE
   SYNTAX      DisplayString
   MAX-ACCESS  read-write
   STATUS		current
   DESCRIPTION
       "Authentication Password, is used for authenticating. The return value is always '********'.
        If the authentication protocol is MD5, the length of password should be 8 ~ 32 characters.
        If the authentication protocol is SHA, the length of password should be 8 ~ 40 characters."
   ::= { xgs360026fTrapHostConfEntry 10 }

xgs360026fTrapHostConfPrivPtc	OBJECT-TYPE
   SYNTAX       INTEGER(1)
   MAX-ACCESS   read-write
   STATUS       current
   DESCRIPTION
       "This is the Privacy Protocol, which is used in AuthPriv. Only supports DES.
        An empty string will be returned if the security level is not 3(AuthPriv).
        1 : DES."
	::= { xgs360026fTrapHostConfEntry 11 }

xgs360026fTrapHostConfPrivPassword	OBJECT-TYPE
   SYNTAX       DisplayString
   MAX-ACCESS   read-write
   STATUS       current
   DESCRIPTION
       "The password is Privacy Key.  The return value is always '********'.  This Key
        must be more than 8 characters, and less than 32 characters."
   ::= { xgs360026fTrapHostConfEntry 12 }

xgs360026fTrapHostConfCurrentMode OBJECT-TYPE
   SYNTAX       INTEGER(0..2)
   MAX-ACCESS   read-write
   STATUS       current
   DESCRIPTION
       "0:Empty, 1:Active mode, 2:Edit mode, 3:Delete."
   ::= { xgs360026fTrapHostConfEntry 13 }


----------------------------------------------------------------------------------------------------

xgs360026fConfiguration                                         OBJECT IDENTIFIER ::= { xgs360026fProductId 2 }

xgs360026fPort                                                  OBJECT IDENTIFIER ::= { xgs360026fConfiguration 1 }

xgs360026fPortConfigurationTable OBJECT-TYPE
   SYNTAX      SEQUENCE OF XGS360026FPortConfigurationEntry
   MAX-ACCESS  not-accessible
   STATUS      current
   DESCRIPTION
       " Show port configurations. "
   ::= { xgs360026fPort 1 }

xgs360026fPortConfigurationEntry OBJECT-TYPE
   SYNTAX      XGS360026FPortConfigurationEntry
   MAX-ACCESS  not-accessible
   STATUS      current
   DESCRIPTION
       ""
   INDEX    { xgs360026fPortConfPort  }
   ::= { xgs360026fPortConfigurationTable 1 }

XGS360026FPortConfigurationEntry ::= SEQUENCE {
   xgs360026fPortConfPort                     INTEGER,
   xgs360026fPortConfPortMedia                DisplayString,
   xgs360026fPortConfLink                     DisplayString,
   xgs360026fPortConfCurrentSpeed             DisplayString,
   xgs360026fPortConfSpeed                    INTEGER,
   xgs360026fPortConfCurrentFlowControlRx     INTEGER,
   xgs360026fPortConfCurrentFlowControlTx     INTEGER,
   xgs360026fPortConfFlowControl              INTEGER,
   xgs360026fPortConfMaxFrameSize             INTEGER,
   xgs360026fPortConfExcessiveCollisionMode   INTEGER,
   xgs360026fPortConfPowerControl             INTEGER,
   xgs360026fPortConfDescription              DisplayString
}

xgs360026fPortConfPort OBJECT-TYPE
   SYNTAX      INTEGER (1..4095)
   MAX-ACCESS  not-accessible
   STATUS      current
   DESCRIPTION
       " port, range : 1 - port number. "
   ::= { xgs360026fPortConfigurationEntry 1 }

xgs360026fPortConfPortMedia OBJECT-TYPE
   SYNTAX      DisplayString(SIZE (1..4))
   MAX-ACCESS  read-only
   STATUS      current
   DESCRIPTION
       " Show port media. "
   ::= { xgs360026fPortConfigurationEntry 2 }

xgs360026fPortConfLink OBJECT-TYPE
   SYNTAX      DisplayString(SIZE (2..4))
   MAX-ACCESS  read-only
   STATUS      current
   DESCRIPTION
       " The current link state. "
   ::= { xgs360026fPortConfigurationEntry 3 }

xgs360026fPortConfCurrentSpeed OBJECT-TYPE
   SYNTAX      DisplayString(SIZE (6..12))
   MAX-ACCESS  read-only
   STATUS      current
   DESCRIPTION
       " The current link speed of the port. "
   ::= { xgs360026fPortConfigurationEntry 4 }

xgs360026fPortConfSpeed OBJECT-TYPE
   SYNTAX      INTEGER (0..11)
   MAX-ACCESS  read-write
   STATUS      current
   DESCRIPTION
       "default: 1,
        0: disable state,
        1: auto,
        2: 10 Half,
        3: 10 Full,
        4: 100 Half,
        5: 100 Full,
        6: 1G full,
        only 'Dual Media' port have 7-11 option.
        Dual Media port default: 7,
        7: SFP_Auto_AMS,
        8: 100FX_AMS,
        9: 1000X_AMS,
        10: 100FX,
        11: 1000X "
   ::= { xgs360026fPortConfigurationEntry 5 }

xgs360026fPortConfCurrentFlowControlRx OBJECT-TYPE
   SYNTAX      INTEGER (0|1)
   MAX-ACCESS  read-only
   STATUS      current
   DESCRIPTION
       "0: disable
        1: enable
        2: not support.  "
   ::= { xgs360026fPortConfigurationEntry 6 }

xgs360026fPortConfCurrentFlowControlTx OBJECT-TYPE
   SYNTAX      INTEGER (0|1)
   MAX-ACCESS  read-only
   STATUS      current
   DESCRIPTION
       "0: disable
        1: enable
        2: not support.  "
   ::= { xgs360026fPortConfigurationEntry 7 }

xgs360026fPortConfFlowControl OBJECT-TYPE
   SYNTAX      INTEGER (0|1)
   MAX-ACCESS  read-write
   STATUS      current
   DESCRIPTION
       "default: 0,
        0: disable
        1: enable
        2: not support. "
   ::= { xgs360026fPortConfigurationEntry 8 }

xgs360026fPortConfMaxFrameSize OBJECT-TYPE
   SYNTAX      INTEGER (1518..9600)
   MAX-ACCESS  read-write
   STATUS      current
   DESCRIPTION
       "default: 9600 , range : 1518 - 9600 "
   ::= { xgs360026fPortConfigurationEntry 9 }

xgs360026fPortConfExcessiveCollisionMode OBJECT-TYPE
   SYNTAX      INTEGER (0|1)
   MAX-ACCESS  read-write
   STATUS      current
   DESCRIPTION
       "default: 0,
        Excessive Collision Mode :
        0: Discard,
        1: Restart,
        2: not support.
       "
   ::= { xgs360026fPortConfigurationEntry 10 }

xgs360026fPortConfPowerControl OBJECT-TYPE
   SYNTAX      INTEGER (0..3)
   MAX-ACCESS  read-write
   STATUS      current
   DESCRIPTION
       "default: 0,
        PowerControl :
        0: disable,
        1: Actiphy,
        2: Dynamic (perfectReach),
        3: Enable,
        4: not support.
       "
   ::= { xgs360026fPortConfigurationEntry 11 }

xgs360026fPortConfDescription OBJECT-TYPE
   SYNTAX      DisplayString
   MAX-ACCESS  read-write
   STATUS      current
   DESCRIPTION
       " Interface specific description.
         Up to 47 characters describing this interface. "
   ::= { xgs360026fPortConfigurationEntry 12 }


xgs360026fPortTrafficStatisticsTable OBJECT-TYPE
   SYNTAX      SEQUENCE OF XGS360026FPortTrafficStatisticsEntry
   MAX-ACCESS  not-accessible
   STATUS      current
   DESCRIPTION
       " "
   ::= { xgs360026fPort 2 }

xgs360026fPortTrafficStatisticsEntry OBJECT-TYPE
   SYNTAX      XGS360026FPortTrafficStatisticsEntry
   MAX-ACCESS  not-accessible
   STATUS      current
   DESCRIPTION
       ""
   INDEX    { xgs360026fPortTrafficStatisticsPort  }
   ::= { xgs360026fPortTrafficStatisticsTable 1 }

XGS360026FPortTrafficStatisticsEntry ::= SEQUENCE {
   xgs360026fPortTrafficStatisticsPort          INTEGER,
   xgs360026fPortTrafficStatisticsClear         INTEGER,
   xgs360026fPortTrafficRxPackets               Counter64,
   xgs360026fPortTrafficRxOctets                Counter64,
   xgs360026fPortTrafficRxUnicast               Counter64,
   xgs360026fPortTrafficRxMulticast             Counter64,
   xgs360026fPortTrafficRxBroadcast             Counter64,
   xgs360026fPortTrafficRxPause                 Counter64,
   xgs360026fPortTrafficRx64Bytes               Counter64,
   xgs360026fPortTrafficRx65to127Bytes          Counter64,
   xgs360026fPortTrafficRx128to255Bytes         Counter64,
   xgs360026fPortTrafficRx256to511Bytes         Counter64,
   xgs360026fPortTrafficRx512to1023Bytes        Counter64,
   xgs360026fPortTrafficRx1024to1526Bytes       Counter64,
   xgs360026fPortTrafficRxExceecd1527Bytes      Counter64,
   xgs360026fPortTrafficRxQ0                    Counter64,
   xgs360026fPortTrafficRxQ1                    Counter64,
   xgs360026fPortTrafficRxQ2                    Counter64,
   xgs360026fPortTrafficRxQ3                    Counter64,
   xgs360026fPortTrafficRxQ4                    Counter64,
   xgs360026fPortTrafficRxQ5                    Counter64,
   xgs360026fPortTrafficRxQ6                    Counter64,
   xgs360026fPortTrafficRxQ7                    Counter64,
   xgs360026fPortTrafficRxDrops                 Counter64,
   xgs360026fPortTrafficRxCRCorAlignment        Counter64,
   xgs360026fPortTrafficRxUndersize             Counter64,
   xgs360026fPortTrafficRxOversize              Counter64,
   xgs360026fPortTrafficRxFragments             Counter64,
   xgs360026fPortTrafficRxJabber                Counter64,
   xgs360026fPortTrafficRxFiltered              Counter64,
   xgs360026fPortTrafficTxPackets               Counter64,
   xgs360026fPortTrafficTxOctets                Counter64,
   xgs360026fPortTrafficTxUnicast               Counter64,
   xgs360026fPortTrafficTxMulticast             Counter64,
   xgs360026fPortTrafficTxBroadcast             Counter64,
   xgs360026fPortTrafficTxPause                 Counter64,
   xgs360026fPortTrafficTx64Bytes               Counter64,
   xgs360026fPortTrafficTx65to127Bytes          Counter64,
   xgs360026fPortTrafficTx128to255Bytes         Counter64,
   xgs360026fPortTrafficTx256to511Bytes         Counter64,
   xgs360026fPortTrafficTx512to1023Bytes        Counter64,
   xgs360026fPortTrafficTx1024to1526Bytes       Counter64,
   xgs360026fPortTrafficTxExceecd1527Bytes      Counter64,
   xgs360026fPortTrafficTxQ0                    Counter64,
   xgs360026fPortTrafficTxQ1                    Counter64,
   xgs360026fPortTrafficTxQ2                    Counter64,
   xgs360026fPortTrafficTxQ3                    Counter64,
   xgs360026fPortTrafficTxQ4                    Counter64,
   xgs360026fPortTrafficTxQ5                    Counter64,
   xgs360026fPortTrafficTxQ6                    Counter64,
   xgs360026fPortTrafficTxQ7                    Counter64,
   xgs360026fPortTrafficTxDrops                 Counter64,
   xgs360026fPortTrafficTxLateOrExcColl         Counter64
}

xgs360026fPortTrafficStatisticsPort OBJECT-TYPE
   SYNTAX      INTEGER (1..4095)
   MAX-ACCESS  not-accessible
   STATUS      current
   DESCRIPTION
       " "
   ::= { xgs360026fPortTrafficStatisticsEntry 1 }

xgs360026fPortTrafficStatisticsClear OBJECT-TYPE
   SYNTAX      INTEGER(0|1)
   MAX-ACCESS  read-write
   STATUS      current
   DESCRIPTION
       " "
   ::= { xgs360026fPortTrafficStatisticsEntry 2 }

xgs360026fPortTrafficRxPackets OBJECT-TYPE
   SYNTAX      Counter64
   MAX-ACCESS  read-only
   STATUS      current
   DESCRIPTION
       " "
   ::= { xgs360026fPortTrafficStatisticsEntry 3 }

xgs360026fPortTrafficRxOctets OBJECT-TYPE
   SYNTAX      Counter64
   MAX-ACCESS  read-only
   STATUS      current
   DESCRIPTION
       " "
   ::= { xgs360026fPortTrafficStatisticsEntry 4 }

xgs360026fPortTrafficRxUnicast OBJECT-TYPE
   SYNTAX      Counter64
   MAX-ACCESS  read-only
   STATUS      current
   DESCRIPTION
       " "
   ::= { xgs360026fPortTrafficStatisticsEntry 5 }

xgs360026fPortTrafficRxMulticast OBJECT-TYPE
   SYNTAX      Counter64
   MAX-ACCESS  read-only
   STATUS      current
   DESCRIPTION
       " "
   ::= { xgs360026fPortTrafficStatisticsEntry 6 }

xgs360026fPortTrafficRxBroadcast OBJECT-TYPE
   SYNTAX      Counter64
   MAX-ACCESS  read-only
   STATUS      current
   DESCRIPTION
       " "
   ::= { xgs360026fPortTrafficStatisticsEntry 7 }

xgs360026fPortTrafficRxPause OBJECT-TYPE
   SYNTAX      Counter64
   MAX-ACCESS  read-only
   STATUS      current
   DESCRIPTION
       " "
   ::= { xgs360026fPortTrafficStatisticsEntry 8 }

xgs360026fPortTrafficRx64Bytes OBJECT-TYPE
   SYNTAX      Counter64
   MAX-ACCESS  read-only
   STATUS      current
   DESCRIPTION
       " "
   ::= { xgs360026fPortTrafficStatisticsEntry 9 }

xgs360026fPortTrafficRx65to127Bytes OBJECT-TYPE
   SYNTAX      Counter64
   MAX-ACCESS  read-only
   STATUS      current
   DESCRIPTION
       " "
   ::= { xgs360026fPortTrafficStatisticsEntry 10 }

xgs360026fPortTrafficRx128to255Bytes OBJECT-TYPE
   SYNTAX      Counter64
   MAX-ACCESS  read-only
   STATUS      current
   DESCRIPTION
       " "
   ::= { xgs360026fPortTrafficStatisticsEntry 11 }

xgs360026fPortTrafficRx256to511Bytes OBJECT-TYPE
   SYNTAX      Counter64
   MAX-ACCESS  read-only
   STATUS      current
   DESCRIPTION
       " "
   ::= { xgs360026fPortTrafficStatisticsEntry 12 }

xgs360026fPortTrafficRx512to1023Bytes OBJECT-TYPE
   SYNTAX      Counter64
   MAX-ACCESS  read-only
   STATUS      current
   DESCRIPTION
       " "
   ::= { xgs360026fPortTrafficStatisticsEntry 13 }

xgs360026fPortTrafficRx1024to1526Bytes OBJECT-TYPE
   SYNTAX      Counter64
   MAX-ACCESS  read-only
   STATUS      current
   DESCRIPTION
       " "
   ::= { xgs360026fPortTrafficStatisticsEntry 14 }

xgs360026fPortTrafficRxExceecd1527Bytes OBJECT-TYPE
   SYNTAX      Counter64
   MAX-ACCESS  read-only
   STATUS      current
   DESCRIPTION
       " "
   ::= { xgs360026fPortTrafficStatisticsEntry 15 }

xgs360026fPortTrafficRxQ0 OBJECT-TYPE
   SYNTAX      Counter64
   MAX-ACCESS  read-only
   STATUS      current
   DESCRIPTION
       " "
   ::= { xgs360026fPortTrafficStatisticsEntry 16 }

xgs360026fPortTrafficRxQ1 OBJECT-TYPE
   SYNTAX      Counter64
   MAX-ACCESS  read-only
   STATUS      current
   DESCRIPTION
       " "
   ::= { xgs360026fPortTrafficStatisticsEntry 17 }

xgs360026fPortTrafficRxQ2 OBJECT-TYPE
   SYNTAX      Counter64
   MAX-ACCESS  read-only
   STATUS      current
   DESCRIPTION
       " "
   ::= { xgs360026fPortTrafficStatisticsEntry 18 }

xgs360026fPortTrafficRxQ3 OBJECT-TYPE
   SYNTAX      Counter64
   MAX-ACCESS  read-only
   STATUS      current
   DESCRIPTION
       " "
   ::= { xgs360026fPortTrafficStatisticsEntry 19 }

xgs360026fPortTrafficRxQ4 OBJECT-TYPE
   SYNTAX      Counter64
   MAX-ACCESS  read-only
   STATUS      current
   DESCRIPTION
       " "
   ::= { xgs360026fPortTrafficStatisticsEntry 20 }

xgs360026fPortTrafficRxQ5 OBJECT-TYPE
   SYNTAX      Counter64
   MAX-ACCESS  read-only
   STATUS      current
   DESCRIPTION
       " "
   ::= { xgs360026fPortTrafficStatisticsEntry 21 }

xgs360026fPortTrafficRxQ6 OBJECT-TYPE
   SYNTAX      Counter64
   MAX-ACCESS  read-only
   STATUS      current
   DESCRIPTION
       " "
   ::= { xgs360026fPortTrafficStatisticsEntry 22 }

xgs360026fPortTrafficRxQ7 OBJECT-TYPE
   SYNTAX      Counter64
   MAX-ACCESS  read-only
   STATUS      current
   DESCRIPTION
       " "
   ::= { xgs360026fPortTrafficStatisticsEntry 23 }

xgs360026fPortTrafficRxDrops OBJECT-TYPE
   SYNTAX      Counter64
   MAX-ACCESS  read-only
   STATUS      current
   DESCRIPTION
       " "
   ::= { xgs360026fPortTrafficStatisticsEntry 24 }

xgs360026fPortTrafficRxCRCorAlignment OBJECT-TYPE
   SYNTAX      Counter64
   MAX-ACCESS  read-only
   STATUS      current
   DESCRIPTION
       " "
   ::= { xgs360026fPortTrafficStatisticsEntry 25 }

xgs360026fPortTrafficRxUndersize OBJECT-TYPE
   SYNTAX      Counter64
   MAX-ACCESS  read-only
   STATUS      current
   DESCRIPTION
       " "
   ::= { xgs360026fPortTrafficStatisticsEntry 26 }

xgs360026fPortTrafficRxOversize OBJECT-TYPE
   SYNTAX      Counter64
   MAX-ACCESS  read-only
   STATUS      current
   DESCRIPTION
       " "
   ::= { xgs360026fPortTrafficStatisticsEntry 27 }

xgs360026fPortTrafficRxFragments OBJECT-TYPE
   SYNTAX      Counter64
   MAX-ACCESS  read-only
   STATUS      current
   DESCRIPTION
       " "
   ::= { xgs360026fPortTrafficStatisticsEntry 28 }

xgs360026fPortTrafficRxJabber OBJECT-TYPE
   SYNTAX      Counter64
   MAX-ACCESS  read-only
   STATUS      current
   DESCRIPTION
       " "
   ::= { xgs360026fPortTrafficStatisticsEntry 29 }

xgs360026fPortTrafficRxFiltered OBJECT-TYPE
   SYNTAX      Counter64
   MAX-ACCESS  read-only
   STATUS      current
   DESCRIPTION
       " "
   ::= { xgs360026fPortTrafficStatisticsEntry 30 }

xgs360026fPortTrafficTxPackets OBJECT-TYPE
   SYNTAX      Counter64
   MAX-ACCESS  read-only
   STATUS      current
   DESCRIPTION
       " "
   ::= { xgs360026fPortTrafficStatisticsEntry 31 }

xgs360026fPortTrafficTxOctets OBJECT-TYPE
   SYNTAX      Counter64
   MAX-ACCESS  read-only
   STATUS      current
   DESCRIPTION
       " "
   ::= { xgs360026fPortTrafficStatisticsEntry 32 }

xgs360026fPortTrafficTxUnicast OBJECT-TYPE
   SYNTAX      Counter64
   MAX-ACCESS  read-only
   STATUS      current
   DESCRIPTION
       " "
   ::= { xgs360026fPortTrafficStatisticsEntry 33 }

xgs360026fPortTrafficTxMulticast OBJECT-TYPE
   SYNTAX      Counter64
   MAX-ACCESS  read-only
   STATUS      current
   DESCRIPTION
       " "
   ::= { xgs360026fPortTrafficStatisticsEntry 34 }

xgs360026fPortTrafficTxBroadcast OBJECT-TYPE
   SYNTAX      Counter64
   MAX-ACCESS  read-only
   STATUS      current
   DESCRIPTION
       " "
   ::= { xgs360026fPortTrafficStatisticsEntry 35 }

xgs360026fPortTrafficTxPause OBJECT-TYPE
   SYNTAX      Counter64
   MAX-ACCESS  read-only
   STATUS      current
   DESCRIPTION
       " "
   ::= { xgs360026fPortTrafficStatisticsEntry 36 }

xgs360026fPortTrafficTx64Bytes OBJECT-TYPE
   SYNTAX      Counter64
   MAX-ACCESS  read-only
   STATUS      current
   DESCRIPTION
       " "
   ::= { xgs360026fPortTrafficStatisticsEntry 37 }

xgs360026fPortTrafficTx65to127Bytes OBJECT-TYPE
   SYNTAX      Counter64
   MAX-ACCESS  read-only
   STATUS      current
   DESCRIPTION
       " "
   ::= { xgs360026fPortTrafficStatisticsEntry 38 }

xgs360026fPortTrafficTx128to255Bytes OBJECT-TYPE
   SYNTAX      Counter64
   MAX-ACCESS  read-only
   STATUS      current
   DESCRIPTION
       " "
   ::= { xgs360026fPortTrafficStatisticsEntry 39 }

xgs360026fPortTrafficTx256to511Bytes OBJECT-TYPE
   SYNTAX      Counter64
   MAX-ACCESS  read-only
   STATUS      current
   DESCRIPTION
       " "
   ::= { xgs360026fPortTrafficStatisticsEntry 40 }

xgs360026fPortTrafficTx512to1023Bytes OBJECT-TYPE
   SYNTAX      Counter64
   MAX-ACCESS  read-only
   STATUS      current
   DESCRIPTION
       " "
   ::= { xgs360026fPortTrafficStatisticsEntry 41 }

xgs360026fPortTrafficTx1024to1526Bytes OBJECT-TYPE
   SYNTAX      Counter64
   MAX-ACCESS  read-only
   STATUS      current
   DESCRIPTION
       " "
   ::= { xgs360026fPortTrafficStatisticsEntry 42 }

xgs360026fPortTrafficTxExceecd1527Bytes OBJECT-TYPE
   SYNTAX      Counter64
   MAX-ACCESS  read-only
   STATUS      current
   DESCRIPTION
       " "
   ::= { xgs360026fPortTrafficStatisticsEntry 43 }

xgs360026fPortTrafficTxQ0 OBJECT-TYPE
   SYNTAX      Counter64
   MAX-ACCESS  read-only
   STATUS      current
   DESCRIPTION
       " "
   ::= { xgs360026fPortTrafficStatisticsEntry 44 }

xgs360026fPortTrafficTxQ1 OBJECT-TYPE
   SYNTAX      Counter64
   MAX-ACCESS  read-only
   STATUS      current
   DESCRIPTION
       " "
   ::= { xgs360026fPortTrafficStatisticsEntry 45 }

xgs360026fPortTrafficTxQ2 OBJECT-TYPE
   SYNTAX      Counter64
   MAX-ACCESS  read-only
   STATUS      current
   DESCRIPTION
       " "
   ::= { xgs360026fPortTrafficStatisticsEntry 46 }

xgs360026fPortTrafficTxQ3 OBJECT-TYPE
   SYNTAX      Counter64
   MAX-ACCESS  read-only
   STATUS      current
   DESCRIPTION
       " "
   ::= { xgs360026fPortTrafficStatisticsEntry 47 }

xgs360026fPortTrafficTxQ4 OBJECT-TYPE
   SYNTAX      Counter64
   MAX-ACCESS  read-only
   STATUS      current
   DESCRIPTION
       " "
   ::= { xgs360026fPortTrafficStatisticsEntry 48 }

xgs360026fPortTrafficTxQ5 OBJECT-TYPE
   SYNTAX      Counter64
   MAX-ACCESS  read-only
   STATUS      current
   DESCRIPTION
       " "
   ::= { xgs360026fPortTrafficStatisticsEntry 49 }

xgs360026fPortTrafficTxQ6 OBJECT-TYPE
   SYNTAX      Counter64
   MAX-ACCESS  read-only
   STATUS      current
   DESCRIPTION
       " "
   ::= { xgs360026fPortTrafficStatisticsEntry 50 }


xgs360026fPortTrafficTxQ7 OBJECT-TYPE
   SYNTAX      Counter64
   MAX-ACCESS  read-only
   STATUS      current
   DESCRIPTION
       " "
   ::= { xgs360026fPortTrafficStatisticsEntry 51 }

xgs360026fPortTrafficTxDrops OBJECT-TYPE
   SYNTAX      Counter64
   MAX-ACCESS  read-only
   STATUS      current
   DESCRIPTION
       " "
   ::= { xgs360026fPortTrafficStatisticsEntry 52 }

xgs360026fPortTrafficTxLateOrExcColl OBJECT-TYPE
   SYNTAX      Counter64
   MAX-ACCESS  read-only
   STATUS      current
   DESCRIPTION
       " "
   ::= { xgs360026fPortTrafficStatisticsEntry 53 }


xgs360026fPortQoSStatistics                                     OBJECT IDENTIFIER ::= { xgs360026fPort 3 }

xgs360026fPortQoSStatisticsClear OBJECT-TYPE
   SYNTAX      INTEGER(0|1)
   MAX-ACCESS  read-only
   STATUS      current
   DESCRIPTION
       "default: 0
       0: none
       1: clear "
   ::= { xgs360026fPortQoSStatistics 1 }

xgs360026fPortQoSStatisticsTable OBJECT-TYPE
   SYNTAX      SEQUENCE OF XGS360026FPortQoSStatisticsEntry
   MAX-ACCESS  not-accessible
   STATUS      current
   DESCRIPTION
       " "
   ::= { xgs360026fPortQoSStatistics 2 }

xgs360026fPortQoSStatisticsEntry OBJECT-TYPE
   SYNTAX      XGS360026FPortQoSStatisticsEntry
   MAX-ACCESS  not-accessible
   STATUS      current
   DESCRIPTION
       ""
   INDEX    { xgs360026fPortQoSStatisticsPort  }
   ::= { xgs360026fPortQoSStatisticsTable 1 }

XGS360026FPortQoSStatisticsEntry ::= SEQUENCE {
   xgs360026fPortQoSStatisticsPort   INTEGER,
   xgs360026fPortQoSQ0Rx	            Counter64,
   xgs360026fPortQoSQ0Tx	            Counter64,
   xgs360026fPortQoSQ1Rx	            Counter64,
   xgs360026fPortQoSQ1Tx	            Counter64,
   xgs360026fPortQoSQ2Rx	            Counter64,
   xgs360026fPortQoSQ2Tx	            Counter64,
   xgs360026fPortQoSQ3Rx	            Counter64,
   xgs360026fPortQoSQ3Tx	            Counter64,
   xgs360026fPortQoSQ4Rx	            Counter64,
   xgs360026fPortQoSQ4Tx	            Counter64,
   xgs360026fPortQoSQ5Rx	            Counter64,
   xgs360026fPortQoSQ5Tx	            Counter64,
   xgs360026fPortQoSQ6Rx	            Counter64,
   xgs360026fPortQoSQ6Tx	            Counter64,
   xgs360026fPortQoSQ7Rx	            Counter64,
   xgs360026fPortQoSQ7Tx	            Counter64
}

xgs360026fPortQoSStatisticsPort OBJECT-TYPE
   SYNTAX      INTEGER (1..4095)
   MAX-ACCESS  not-accessible
   STATUS      current
   DESCRIPTION
       " "
   ::= { xgs360026fPortQoSStatisticsEntry 1 }

xgs360026fPortQoSQ0Rx OBJECT-TYPE
   SYNTAX      Counter64
   MAX-ACCESS  read-only
   STATUS      current
   DESCRIPTION
       " "
   ::= { xgs360026fPortQoSStatisticsEntry 2 }

xgs360026fPortQoSQ0Tx OBJECT-TYPE
   SYNTAX      Counter64
   MAX-ACCESS  read-only
   STATUS      current
   DESCRIPTION
       " "
   ::= { xgs360026fPortQoSStatisticsEntry 3 }

xgs360026fPortQoSQ1Rx OBJECT-TYPE
   SYNTAX      Counter64
   MAX-ACCESS  read-only
   STATUS      current
   DESCRIPTION
       " "
   ::= { xgs360026fPortQoSStatisticsEntry 4 }

xgs360026fPortQoSQ1Tx OBJECT-TYPE
   SYNTAX      Counter64
   MAX-ACCESS  read-only
   STATUS      current
   DESCRIPTION
       " "
   ::= { xgs360026fPortQoSStatisticsEntry 5 }

xgs360026fPortQoSQ2Rx OBJECT-TYPE
   SYNTAX      Counter64
   MAX-ACCESS  read-only
   STATUS      current
   DESCRIPTION
       " "
   ::= { xgs360026fPortQoSStatisticsEntry 6 }

xgs360026fPortQoSQ2Tx OBJECT-TYPE
   SYNTAX      Counter64
   MAX-ACCESS  read-only
   STATUS      current
   DESCRIPTION
       " "
   ::= { xgs360026fPortQoSStatisticsEntry 7 }

xgs360026fPortQoSQ3Rx OBJECT-TYPE
   SYNTAX      Counter64
   MAX-ACCESS  read-only
   STATUS      current
   DESCRIPTION
       " "
   ::= { xgs360026fPortQoSStatisticsEntry 8 }

xgs360026fPortQoSQ3Tx OBJECT-TYPE
   SYNTAX      Counter64
   MAX-ACCESS  read-only
   STATUS      current
   DESCRIPTION
       " "
   ::= { xgs360026fPortQoSStatisticsEntry 9 }

xgs360026fPortQoSQ4Rx OBJECT-TYPE
   SYNTAX      Counter64
   MAX-ACCESS  read-only
   STATUS      current
   DESCRIPTION
       " "
   ::= { xgs360026fPortQoSStatisticsEntry 10 }

xgs360026fPortQoSQ4Tx OBJECT-TYPE
   SYNTAX      Counter64
   MAX-ACCESS  read-only
   STATUS      current
   DESCRIPTION
       " "
   ::= { xgs360026fPortQoSStatisticsEntry 11 }

xgs360026fPortQoSQ5Rx OBJECT-TYPE
   SYNTAX      Counter64
   MAX-ACCESS  read-only
   STATUS      current
   DESCRIPTION
       " "
   ::= { xgs360026fPortQoSStatisticsEntry 12 }

xgs360026fPortQoSQ5Tx OBJECT-TYPE
   SYNTAX      Counter64
   MAX-ACCESS  read-only
   STATUS      current
   DESCRIPTION
       " "
   ::= { xgs360026fPortQoSStatisticsEntry 13 }

xgs360026fPortQoSQ6Rx OBJECT-TYPE
   SYNTAX      Counter64
   MAX-ACCESS  read-only
   STATUS      current
   DESCRIPTION
       " "
   ::= { xgs360026fPortQoSStatisticsEntry 14 }

xgs360026fPortQoSQ6Tx OBJECT-TYPE
   SYNTAX      Counter64
   MAX-ACCESS  read-only
   STATUS      current
   DESCRIPTION
       " "
   ::= { xgs360026fPortQoSStatisticsEntry 15 }

xgs360026fPortQoSQ7Rx OBJECT-TYPE
   SYNTAX      Counter64
   MAX-ACCESS  read-only
   STATUS      current
   DESCRIPTION
       " "
   ::= { xgs360026fPortQoSStatisticsEntry 16 }

xgs360026fPortQoSQ7Tx OBJECT-TYPE
   SYNTAX      Counter64
   MAX-ACCESS  read-only
   STATUS      current
   DESCRIPTION
       " "
   ::= { xgs360026fPortQoSStatisticsEntry 17 }

xgs360026fSFPInfoTable OBJECT-TYPE
   SYNTAX      SEQUENCE OF XGS360026FSFPInfoEntry
   MAX-ACCESS  not-accessible
   STATUS      current
   DESCRIPTION
       " "
   ::= { xgs360026fPort 4 }

xgs360026fSFPInfoEntry OBJECT-TYPE
   SYNTAX      XGS360026FSFPInfoEntry
   MAX-ACCESS  not-accessible
   STATUS      current
   DESCRIPTION
       ""
   INDEX    { xgs360026fSFPInfoIndex }
   ::= { xgs360026fSFPInfoTable 1 }

XGS360026FSFPInfoEntry ::= SEQUENCE {
   xgs360026fSFPInfoIndex               INTEGER,
   xgs360026fSFPInfoPort                DisplayString,
   xgs360026fSFPConnectorType           DisplayString,
   xgs360026fSFPFiberType               DisplayString,
   xgs360026fSFPTxCentralWavelength     DisplayString,
   xgs360026fSFPBaudRate                DisplayString,
   xgs360026fSFPVendorOUI               DisplayString,
   xgs360026fSFPVendorName              DisplayString,
   xgs360026fSFPVendorPN                DisplayString,
   xgs360026fSFPVendorRev               DisplayString,
   xgs360026fSFPVendorSN                DisplayString,
   xgs360026fSFPDateCode                DisplayString,
   xgs360026fSFPTemperature             DisplayString,
   xgs360026fSFPVcc                     DisplayString,
   xgs360026fSFPMon1Bias                DisplayString,
   xgs360026fSFPMon2TxPWR               DisplayString,
   xgs360026fSFPMon3RxPWR               DisplayString
}

xgs360026fSFPInfoIndex OBJECT-TYPE
   SYNTAX      INTEGER (1..4095)
   MAX-ACCESS  not-accessible
   STATUS      current
   DESCRIPTION
       " "
   ::= { xgs360026fSFPInfoEntry 1 }

xgs360026fSFPInfoPort OBJECT-TYPE
   SYNTAX      DisplayString
   MAX-ACCESS  read-only
   STATUS      current
   DESCRIPTION
       " "
   ::= { xgs360026fSFPInfoEntry 2 }

xgs360026fSFPConnectorType OBJECT-TYPE
   SYNTAX      DisplayString
   MAX-ACCESS  read-only
   STATUS      current
   DESCRIPTION
       " "
   ::= { xgs360026fSFPInfoEntry 3 }

xgs360026fSFPFiberType OBJECT-TYPE
   SYNTAX      DisplayString
   MAX-ACCESS  read-only
   STATUS      current
   DESCRIPTION
       " "
   ::= { xgs360026fSFPInfoEntry 4 }

xgs360026fSFPTxCentralWavelength OBJECT-TYPE
   SYNTAX      DisplayString
   MAX-ACCESS  read-only
   STATUS      current
   DESCRIPTION
       " "
   ::= { xgs360026fSFPInfoEntry 5 }

xgs360026fSFPBaudRate OBJECT-TYPE
   SYNTAX      DisplayString
   MAX-ACCESS  read-only
   STATUS      current
   DESCRIPTION
       " "
   ::= { xgs360026fSFPInfoEntry 6 }

xgs360026fSFPVendorOUI OBJECT-TYPE
   SYNTAX      DisplayString
   MAX-ACCESS  read-only
   STATUS      current
   DESCRIPTION
       " "
   ::= { xgs360026fSFPInfoEntry 7 }

xgs360026fSFPVendorName OBJECT-TYPE
   SYNTAX      DisplayString
   MAX-ACCESS  read-only
   STATUS      current
   DESCRIPTION
       " "
   ::= { xgs360026fSFPInfoEntry 8 }

xgs360026fSFPVendorPN OBJECT-TYPE
   SYNTAX      DisplayString
   MAX-ACCESS  read-only
   STATUS      current
   DESCRIPTION
       " "
   ::= { xgs360026fSFPInfoEntry 9 }

xgs360026fSFPVendorRev OBJECT-TYPE
   SYNTAX      DisplayString
   MAX-ACCESS  read-only
   STATUS      current
   DESCRIPTION
       " "
   ::= { xgs360026fSFPInfoEntry 10 }

xgs360026fSFPVendorSN OBJECT-TYPE
   SYNTAX      DisplayString
   MAX-ACCESS  read-only
   STATUS      current
   DESCRIPTION
       " "
   ::= { xgs360026fSFPInfoEntry 11 }

xgs360026fSFPDateCode OBJECT-TYPE
   SYNTAX      DisplayString
   MAX-ACCESS  read-only
   STATUS      current
   DESCRIPTION
       " "
   ::= { xgs360026fSFPInfoEntry 12 }

xgs360026fSFPTemperature OBJECT-TYPE
   SYNTAX      DisplayString
   MAX-ACCESS  read-only
   STATUS      current
   DESCRIPTION
       " "
   ::= { xgs360026fSFPInfoEntry 13 }

xgs360026fSFPVcc OBJECT-TYPE
   SYNTAX      DisplayString
   MAX-ACCESS  read-only
   STATUS      current
   DESCRIPTION
       " "
   ::= { xgs360026fSFPInfoEntry 14 }

xgs360026fSFPMon1Bias OBJECT-TYPE
   SYNTAX      DisplayString
   MAX-ACCESS  read-only
   STATUS      current
   DESCRIPTION
       " "
   ::= { xgs360026fSFPInfoEntry 15 }

xgs360026fSFPMon2TxPWR OBJECT-TYPE
   SYNTAX      DisplayString
   MAX-ACCESS  read-only
   STATUS      current
   DESCRIPTION
       " "
   ::= { xgs360026fSFPInfoEntry 16 }

xgs360026fSFPMon3RxPWR OBJECT-TYPE
   SYNTAX      DisplayString
   MAX-ACCESS  read-only
   STATUS      current
   DESCRIPTION
       " "
   ::= { xgs360026fSFPInfoEntry 17 }


xgs360026fGARP                                                   OBJECT IDENTIFIER ::= { xgs360026fConfiguration 3 }

xgs360026fGARPConfTable OBJECT-TYPE
   SYNTAX      SEQUENCE OF XGS360026FGARPConfEntry
   MAX-ACCESS  not-accessible
   STATUS      current
   DESCRIPTION
       " "
   ::= { xgs360026fGARP 1 }

xgs360026fGARPConfEntry OBJECT-TYPE
   SYNTAX      XGS360026FGARPConfEntry
   MAX-ACCESS  not-accessible
   STATUS      current
   DESCRIPTION
       ""
   INDEX    { xgs360026fGARPConfPort  }
   ::= { xgs360026fGARPConfTable 1 }

XGS360026FGARPConfEntry ::= SEQUENCE {
   xgs360026fGARPConfPort            INTEGER,
   xgs360026fGARPJoinTimer           INTEGER,
   xgs360026fGARPLeaveTimer          INTEGER,
   xgs360026fGARPLeaveAllTimer		INTEGER,
   xgs360026fGARPApplicantion		INTEGER,
   xgs360026fGARPAttributeType		INTEGER,
   xgs360026fGARPApplicant		    INTEGER
}

xgs360026fGARPConfPort OBJECT-TYPE
   SYNTAX      INTEGER (1..4095)
   MAX-ACCESS  not-accessible
   STATUS      current
   DESCRIPTION
       " "
   ::= { xgs360026fGARPConfEntry 1 }

xgs360026fGARPJoinTimer OBJECT-TYPE
   SYNTAX      INTEGER (200..1000)
   MAX-ACCESS  read-write
   STATUS      current
   DESCRIPTION
       "default: 200, range : 200 - 1000 "
   ::= { xgs360026fGARPConfEntry 2 }

xgs360026fGARPLeaveTimer OBJECT-TYPE
   SYNTAX      INTEGER (600..3000)
   MAX-ACCESS  read-write
   STATUS      current
   DESCRIPTION
       "default: 600 , range : 600 - 3000"
   ::= { xgs360026fGARPConfEntry 3 }

xgs360026fGARPLeaveAllTimer OBJECT-TYPE
   SYNTAX      INTEGER (10000..50000)
   MAX-ACCESS  read-write
   STATUS      current
   DESCRIPTION
       "default: 10000, range : 10000 - 50000 "
   ::= { xgs360026fGARPConfEntry 4 }

xgs360026fGARPApplicantion OBJECT-TYPE
   SYNTAX      INTEGER(1)
   MAX-ACCESS  read-write
   STATUS      current
   DESCRIPTION
       "default: 1
       1: GVRP"
   ::= { xgs360026fGARPConfEntry 5 }

xgs360026fGARPAttributeType OBJECT-TYPE
   SYNTAX      INTEGER(1)
   MAX-ACCESS  read-write
   STATUS      current
   DESCRIPTION
       "default: 1
       1: VLAN"
   ::= { xgs360026fGARPConfEntry 6 }

xgs360026fGARPApplicant OBJECT-TYPE
   SYNTAX      INTEGER(0|1)
   MAX-ACCESS  read-write
   STATUS      current
   DESCRIPTION
       "default: 0
       0: normal-participant
       1: non-participant"
   ::= { xgs360026fGARPConfEntry 7 }

xgs360026fGARPStatisticsTable OBJECT-TYPE
   SYNTAX      SEQUENCE OF XGS360026FGARPStatisticsEntry
   MAX-ACCESS  not-accessible
   STATUS      current
   DESCRIPTION
       " Show the basic GARP port statistics. "
   ::= { xgs360026fGARP 2 }

xgs360026fGARPStatisticsEntry OBJECT-TYPE
   SYNTAX      XGS360026FGARPStatisticsEntry
   MAX-ACCESS  not-accessible
   STATUS      current
   DESCRIPTION
       ""
   INDEX    { xgs360026fGARPStatisticsPort  }
   ::= { xgs360026fGARPStatisticsTable 1 }

XGS360026FGARPStatisticsEntry ::= SEQUENCE {
   xgs360026fGARPStatisticsPort          INTEGER,
   xgs360026fGARPStatisticsPeerMAC		DisplayString,
   xgs360026fGARPStatisticsFailedCount   Counter32
}

xgs360026fGARPStatisticsPort OBJECT-TYPE
   SYNTAX      INTEGER (1..4095)
   MAX-ACCESS  not-accessible
   STATUS      current
   DESCRIPTION
       " port, range : 1 - port number. "
   ::= { xgs360026fGARPStatisticsEntry 1 }

xgs360026fGARPStatisticsPeerMAC OBJECT-TYPE
   SYNTAX      DisplayString
   MAX-ACCESS  read-only
   STATUS      current
   DESCRIPTION
       " Peer MAC is MAC address of the neighbour Switch from with GARP frame is received.  "
   ::= { xgs360026fGARPStatisticsEntry 2 }

xgs360026fGARPStatisticsFailedCount OBJECT-TYPE
   SYNTAX      Counter32
   MAX-ACCESS  read-only
   STATUS      current
   DESCRIPTION
       " explain Failed count here. "
   ::= { xgs360026fGARPStatisticsEntry 3 }

xgs360026fGVRP                                                   OBJECT IDENTIFIER ::= { xgs360026fConfiguration 4 }

xgs360026fGVRPConf                                                   OBJECT IDENTIFIER ::= { xgs360026fGVRP 1 }

xgs360026fGVRPMode OBJECT-TYPE
   SYNTAX      INTEGER(0|1)
   MAX-ACCESS  read-write
   STATUS      current
   DESCRIPTION
       "default: 0,
        0: disable,
        1: enable. "
   ::= { xgs360026fGVRPConf 1 }

xgs360026fGVRPConfTable OBJECT-TYPE
   SYNTAX      SEQUENCE OF XGS360026FGVRPConfEntry
   MAX-ACCESS  not-accessible
   STATUS      current
   DESCRIPTION
       " "
   ::= { xgs360026fGVRPConf 2 }

xgs360026fGVRPConfEntry OBJECT-TYPE
   SYNTAX      XGS360026FGVRPConfEntry
   MAX-ACCESS  not-accessible
   STATUS      current
   DESCRIPTION
       ""
   INDEX    { xgs360026fGVRPConfPort  }
   ::= { xgs360026fGVRPConfTable 1 }

XGS360026FGVRPConfEntry ::= SEQUENCE {
   xgs360026fGVRPConfPort        INTEGER,
   xgs360026fGVRPConfPortMode	INTEGER,
   xgs360026fGVRPConfPortRRole	INTEGER
}

xgs360026fGVRPConfPort OBJECT-TYPE
   SYNTAX      INTEGER (1..4095)
   MAX-ACCESS  not-accessible
   STATUS      current
   DESCRIPTION
       " "
   ::= { xgs360026fGVRPConfEntry 1 }

xgs360026fGVRPConfPortMode OBJECT-TYPE
   SYNTAX      INTEGER(0|1)
   MAX-ACCESS  read-write
   STATUS      current
   DESCRIPTION
       "default: 0
       1: enable
       0: disable"
   ::= { xgs360026fGVRPConfEntry 2 }

xgs360026fGVRPConfPortRRole OBJECT-TYPE
   SYNTAX      INTEGER(0|1)
   MAX-ACCESS  read-write
   STATUS      current
   DESCRIPTION
       "default: 0
       1: enable
       0: disable"
   ::= { xgs360026fGVRPConfEntry 3 }

xgs360026fGVRPStatisticsTable OBJECT-TYPE
   SYNTAX      SEQUENCE OF XGS360026FGVRPStatisticsEntry
   MAX-ACCESS  not-accessible
   STATUS      current
   DESCRIPTION
       " "
   ::= { xgs360026fGVRP 2 }

xgs360026fGVRPStatisticsEntry OBJECT-TYPE
   SYNTAX      XGS360026FGVRPStatisticsEntry
   MAX-ACCESS  not-accessible
   STATUS      current
   DESCRIPTION
       ""
   INDEX    { xgs360026fGVRPStatisticsPort  }
   ::= { xgs360026fGVRPStatisticsTable 1 }

XGS360026FGVRPStatisticsEntry ::= SEQUENCE {
   xgs360026fGVRPStatisticsPort          INTEGER,
   xgs360026fGVRPStatisticsJoinTxCnt		Counter32,
   xgs360026fGVRPStatisticsLeaveTxCnt    Counter32
}

xgs360026fGVRPStatisticsPort OBJECT-TYPE
   SYNTAX      INTEGER (1..4095)
   MAX-ACCESS  not-accessible
   STATUS      current
   DESCRIPTION
       " "
   ::= { xgs360026fGVRPStatisticsEntry 1 }

xgs360026fGVRPStatisticsJoinTxCnt OBJECT-TYPE
   SYNTAX      Counter32
   MAX-ACCESS  read-only
   STATUS      current
   DESCRIPTION
       ""
   ::= { xgs360026fGVRPStatisticsEntry 2 }

xgs360026fGVRPStatisticsLeaveTxCnt OBJECT-TYPE
   SYNTAX      Counter32
   MAX-ACCESS  read-only
   STATUS      current
   DESCRIPTION
       ""
   ::= { xgs360026fGVRPStatisticsEntry 3 }

xgs360026fThermalProtection                                     OBJECT IDENTIFIER ::= { xgs360026fConfiguration 5 }

xgs360026fPriority0Temperature OBJECT-TYPE
   SYNTAX      INTEGER(0..255)
   MAX-ACCESS  read-write
   STATUS      current
   DESCRIPTION
       "default: 255, range : 0 - 255 "
   ::= { xgs360026fThermalProtection 1 }

xgs360026fPriority1Temperature OBJECT-TYPE
   SYNTAX      INTEGER(0..255)
   MAX-ACCESS  read-write
   STATUS      current
   DESCRIPTION
       "default: 255, range : 0 - 255 "
   ::= { xgs360026fThermalProtection 2 }

xgs360026fPriority2Temperature OBJECT-TYPE
   SYNTAX      INTEGER(0..255)
   MAX-ACCESS  read-write
   STATUS      current
   DESCRIPTION
       "default: 255, range : 0 - 255 "
   ::= { xgs360026fThermalProtection 3 }

xgs360026fPriority3Temperature OBJECT-TYPE
   SYNTAX      INTEGER(0..255)
   MAX-ACCESS  read-write
   STATUS      current
   DESCRIPTION
       "default: 255, range : 0 - 255 "
   ::= { xgs360026fThermalProtection 4 }

xgs360026fThermalProtectionTable OBJECT-TYPE
   SYNTAX      SEQUENCE OF XGS360026FThermalProtectionEntry
   MAX-ACCESS  not-accessible
   STATUS      current
   DESCRIPTION
       " "
   ::= { xgs360026fThermalProtection 5 }

xgs360026fThermalProtectionEntry OBJECT-TYPE
   SYNTAX      XGS360026FThermalProtectionEntry
   MAX-ACCESS  not-accessible
   STATUS      current
   DESCRIPTION
       ""
   INDEX    { xgs360026fThermalProtectionPort  }
   ::= { xgs360026fThermalProtectionTable 1 }

XGS360026FThermalProtectionEntry ::= SEQUENCE {
   xgs360026fThermalProtectionPort               INTEGER,
   xgs360026fThermalProtectionPortTemperature    INTEGER,
   xgs360026fThermalProtectionPortPriority		INTEGER,
   xgs360026fThermalProtectionPortStatus         DisplayString
}

xgs360026fThermalProtectionPort OBJECT-TYPE
   SYNTAX      INTEGER (1..4095)
   MAX-ACCESS  not-accessible
   STATUS      current
   DESCRIPTION
       " "
   ::= { xgs360026fThermalProtectionEntry 1 }

xgs360026fThermalProtectionPortTemperature OBJECT-TYPE
   SYNTAX      INTEGER(0..255)
   MAX-ACCESS  read-only
   STATUS      current
   DESCRIPTION
       ""
   ::= { xgs360026fThermalProtectionEntry 2 }

xgs360026fThermalProtectionPortPriority OBJECT-TYPE
   SYNTAX      INTEGER(0..3)
   MAX-ACCESS  read-write
   STATUS      current
   DESCRIPTION
       "default: 0, range : 0 - 3"
   ::= { xgs360026fThermalProtectionEntry 3 }

xgs360026fThermalProtectionPortStatus OBJECT-TYPE
   SYNTAX      DisplayString
   MAX-ACCESS  read-only
   STATUS      current
   DESCRIPTION
       ""
   ::= { xgs360026fThermalProtectionEntry 4 }


xgs360026fMirroring                                             OBJECT IDENTIFIER ::= { xgs360026fConfiguration 6 }

xgs360026fPortToMirrorOn OBJECT-TYPE
   SYNTAX      INTEGER(0..10)
   MAX-ACCESS  read-write
   STATUS      current
   DESCRIPTION
       "default: 0
        0: disable,
        range : 1 - port number. "
   ::= { xgs360026fMirroring 1 }

xgs360026fMirrorTable OBJECT-TYPE
   SYNTAX      SEQUENCE OF XGS360026FMirrorEntry
   MAX-ACCESS  not-accessible
   STATUS      current
   DESCRIPTION
       " "
   ::= { xgs360026fMirroring 2 }

xgs360026fMirrorEntry OBJECT-TYPE
   SYNTAX      XGS360026FMirrorEntry
   MAX-ACCESS  not-accessible
   STATUS      current
   DESCRIPTION
       ""
   INDEX    { xgs360026fMirrorPort  }
   ::= { xgs360026fMirrorTable 1 }

XGS360026FMirrorEntry ::= SEQUENCE {
   xgs360026fMirrorPort		INTEGER,
   xgs360026fMirrorMode		INTEGER
}

xgs360026fMirrorPort OBJECT-TYPE
   SYNTAX      INTEGER (1..4095)
   MAX-ACCESS  not-accessible
   STATUS      current
   DESCRIPTION
       " "
   ::= { xgs360026fMirrorEntry 1 }

xgs360026fMirrorMode OBJECT-TYPE
   SYNTAX      INTEGER(0..3)
   MAX-ACCESS  read-write
   STATUS      current
   DESCRIPTION
       "default: 0
       0: disable
       1: enable
       2: rx only
       3: tx only
       Setting Tx mirroring for analyzer port has no effect. Tx mirroring ignored"
   ::= { xgs360026fMirrorEntry 2 }

xgs360026fTrapEventSeverity                                             OBJECT IDENTIFIER ::= { xgs360026fConfiguration 7 }

xgs360026fTrapEventSeverityACL OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { xgs360026fTrapEventSeverity 1 }

xgs360026fTrapEventSeverityACLLog OBJECT-TYPE
   SYNTAX      INTEGER (0..7)
   MAX-ACCESS  read-write
   STATUS      current
   DESCRIPTION
       " default:  7(Debug)
        0: Emergency
        1: Alert
        2: Critical
        3: Error
        4: Warning
        5: Notice
        6: Info
        7: Debug"
   ::= { xgs360026fTrapEventSeverity 2 }

xgs360026fTrapEventSeverityAccessMgmt OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { xgs360026fTrapEventSeverity 3 }

xgs360026fTrapEventSeverityAuthFailed OBJECT-TYPE
   SYNTAX      INTEGER (0..7)
   MAX-ACCESS  read-write
   STATUS      current
   DESCRIPTION
       " default:  4(Warning)
        0: Emergency
        1: Alert
        2: Critical
        3: Error
        4: Warning
        5: Notice
        6: Info
        7: Debug"
   ::= { xgs360026fTrapEventSeverity 4 }

xgs360026fTrapEventSeverityColdStart OBJECT-TYPE
   SYNTAX      INTEGER (0..7)
   MAX-ACCESS  read-write
   STATUS      current
   DESCRIPTION
       " default:  4(Warning)
        0: Emergency
        1: Alert
        2: Critical
        3: Error
        4: Warning
        5: Notice
        6: Info
        7: Debug"
   ::= { xgs360026fTrapEventSeverity 5 }

xgs360026fTrapEventSeverityConfigInfo OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { xgs360026fTrapEventSeverity 6 }

xgs360026fTrapEventSeverityFirmwareUpgrade OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { xgs360026fTrapEventSeverity 7 }

xgs360026fTrapEventSeverityImportExport OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { xgs360026fTrapEventSeverity 8 }

xgs360026fTrapEventSeverityLACP OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { xgs360026fTrapEventSeverity 9 }

xgs360026fTrapEventSeverityLinkStatus OBJECT-TYPE
   SYNTAX      INTEGER (0..7)
   MAX-ACCESS  read-write
   STATUS      current
   DESCRIPTION
       " default:  4(Warning)
        0: Emergency
        1: Alert
        2: Critical
        3: Error
        4: Warning
        5: Notice
        6: Info
        7: Debug"
   ::= { xgs360026fTrapEventSeverity 10 }

xgs360026fTrapEventSeverityLogin OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { xgs360026fTrapEventSeverity 11 }

xgs360026fTrapEventSeverityLogout OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { xgs360026fTrapEventSeverity 12 }

xgs360026fTrapEventSeverityLoopProtect OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { xgs360026fTrapEventSeverity 13 }

xgs360026fTrapEventSeverityMgmtIPChange OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { xgs360026fTrapEventSeverity 14 }

xgs360026fTrapEventSeverityModuleChange OBJECT-TYPE
   SYNTAX      INTEGER (0..7)
   MAX-ACCESS  read-write
   STATUS      current
   DESCRIPTION
       " default:  5(Notice)
        0: Emergency
        1: Alert
        2: Critical
        3: Error
        4: Warning
        5: Notice
        6: Info
        7: Debug"
   ::= { xgs360026fTrapEventSeverity 15 }

xgs360026fTrapEventSeverityNAS OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { xgs360026fTrapEventSeverity 16 }

xgs360026fTrapEventSeverityPasswdChange OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { xgs360026fTrapEventSeverity 17 }

xgs360026fTrapEventSeverityPortSecurity OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { xgs360026fTrapEventSeverity 18 }

xgs360026fTrapEventSeverityThermalProtect OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { xgs360026fTrapEventSeverity 19 }

xgs360026fTrapEventSeverityVLAN OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { xgs360026fTrapEventSeverity 20 }

xgs360026fTrapEventSeverityWarmStart OBJECT-TYPE
   SYNTAX      INTEGER (0..7)
   MAX-ACCESS  read-write
   STATUS      current
   DESCRIPTION
       " default:  4(Warning)
        0: Emergency
        1: Alert
        2: Critical
        3: Error
        4: Warning
        5: Notice
        6: Info
        7: Debug"
   ::= { xgs360026fTrapEventSeverity 21 }


xgs360026fSMTP                                             OBJECT IDENTIFIER ::= { xgs360026fConfiguration 8 }

xgs360026fSMTPMailServer OBJECT-TYPE
   SYNTAX      DisplayString
   MAX-ACCESS  read-write
   STATUS      current
   DESCRIPTION
       " Up to 47 characters describing email server. "
   ::= { xgs360026fSMTP 1 }

xgs360026fSMTPUserName OBJECT-TYPE
   SYNTAX      DisplayString
   MAX-ACCESS  read-write
   STATUS      current
   DESCRIPTION
       " Up to 47 characters describing user name. "
   ::= { xgs360026fSMTP 2 }

xgs360026fSMTPPassword OBJECT-TYPE
   SYNTAX      DisplayString
   MAX-ACCESS  read-write
   STATUS      current
   DESCRIPTION
       " Up to 47 characters describing password. "
   ::= { xgs360026fSMTP 3 }

xgs360026fSMTPServeriryLevel OBJECT-TYPE
   SYNTAX      INTEGER(0..7)
   MAX-ACCESS  read-write
   STATUS      current
   DESCRIPTION
       "default: 6
       0: Emergency
       1: Alert
       2: Critical
       3: Error
       4: Warning
       5: Notice
       6: Info
       7: Debug"
   ::= { xgs360026fSMTP 4 }

xgs360026fSMTPSender OBJECT-TYPE
   SYNTAX      DisplayString
   MAX-ACCESS  read-write
   STATUS      current
   DESCRIPTION
       " Up to 47 characters describing sender. "
   ::= { xgs360026fSMTP 5 }

xgs360026fSMTPReturnPath OBJECT-TYPE
   SYNTAX      DisplayString
   MAX-ACCESS  read-write
   STATUS      current
   DESCRIPTION
       " Up to 47 characters describing return path. "
   ::= { xgs360026fSMTP 6 }

xgs360026fSMTPEmailAddress1 OBJECT-TYPE
   SYNTAX      DisplayString
   MAX-ACCESS  read-write
   STATUS      current
   DESCRIPTION
       " Up to 47 characters describing mail address. "
   ::= { xgs360026fSMTP 7 }

xgs360026fSMTPEmailAddress2 OBJECT-TYPE
   SYNTAX      DisplayString
   MAX-ACCESS  read-write
   STATUS      current
   DESCRIPTION
       " Up to 47 characters describing mail address. "
   ::= { xgs360026fSMTP 8 }

xgs360026fSMTPEmailAddress3 OBJECT-TYPE
   SYNTAX      DisplayString
   MAX-ACCESS  read-write
   STATUS      current
   DESCRIPTION
       " Up to 47 characters describing mail address. "
   ::= { xgs360026fSMTP 9 }

xgs360026fSMTPEmailAddress4 OBJECT-TYPE
   SYNTAX      DisplayString
   MAX-ACCESS  read-write
   STATUS      current
   DESCRIPTION
       " Up to 47 characters describing mail address. "
   ::= { xgs360026fSMTP 10 }

xgs360026fSMTPEmailAddress5 OBJECT-TYPE
   SYNTAX      DisplayString
   MAX-ACCESS  read-write
   STATUS      current
   DESCRIPTION
       " Up to 47 characters describing mail address. "
   ::= { xgs360026fSMTP 11 }

xgs360026fSMTPEmailAddress6 OBJECT-TYPE
   SYNTAX      DisplayString
   MAX-ACCESS  read-write
   STATUS      current
   DESCRIPTION
       " Up to 47 characters describing mail address. "
   ::= { xgs360026fSMTP 12 }


xgs360026fACL                                                   OBJECT IDENTIFIER ::= { xgs360026fConfiguration 9 }

xgs360026fACLPortsConfTable OBJECT-TYPE
   SYNTAX      SEQUENCE OF XGS360026FACLPortsConfEntry
   MAX-ACCESS  not-accessible
   STATUS      current
   DESCRIPTION
       " "
   ::= { xgs360026fACL 1 }

xgs360026fACLPortsConfEntry OBJECT-TYPE
   SYNTAX      XGS360026FACLPortsConfEntry
   MAX-ACCESS  not-accessible
   STATUS      current
   DESCRIPTION
       ""
   INDEX    { xgs360026fACLPortsConfPort  }
   ::= { xgs360026fACLPortsConfTable 1 }

XGS360026FACLPortsConfEntry ::= SEQUENCE {
   xgs360026fACLPortsConfPort               INTEGER,
   xgs360026fACLPortsConfPolicyID           INTEGER,
   xgs360026fACLPortsConfAction             INTEGER,
   xgs360026fACLPortsConfRateLimiterID      INTEGER,
   xgs360026fACLPortsConfPortRedirect       INTEGER,
   xgs360026fACLPortsConfLogging            INTEGER,
   xgs360026fACLPortsConfShutdown           INTEGER,
   xgs360026fACLPortsConfState              INTEGER,
   xgs360026fACLPortsConfCounter            Counter32
}

xgs360026fACLPortsConfPort OBJECT-TYPE
   SYNTAX      INTEGER (1..4095)
   MAX-ACCESS  not-accessible
   STATUS      current
   DESCRIPTION
       " "
   ::= { xgs360026fACLPortsConfEntry 1 }

xgs360026fACLPortsConfPolicyID OBJECT-TYPE
   SYNTAX      INTEGER (0..255)
   MAX-ACCESS  read-write
   STATUS      current
   DESCRIPTION
       "default: 0, range : 0 - 255 "
   ::= { xgs360026fACLPortsConfEntry 2 }

xgs360026fACLPortsConfAction OBJECT-TYPE
   SYNTAX      INTEGER(0|1)
   MAX-ACCESS  read-write
   STATUS      current
   DESCRIPTION
       "default: 1,
        0: Deny
        1: Permit"
   ::= { xgs360026fACLPortsConfEntry 3 }

xgs360026fACLPortsConfRateLimiterID OBJECT-TYPE
   SYNTAX      INTEGER (0..16)
   MAX-ACCESS  read-write
   STATUS      current
   DESCRIPTION
       "default: 0,
        0: Disable
        range : 0 - 16 "
   ::= { xgs360026fACLPortsConfEntry 4 }

xgs360026fACLPortsConfPortRedirect OBJECT-TYPE
   SYNTAX      INTEGER (0..4095)
   MAX-ACCESS  read-write
   STATUS      current
   DESCRIPTION
       "default: 0
        0: Disable
        range : 0 - end port number "
   ::= { xgs360026fACLPortsConfEntry 5 }

xgs360026fACLPortsConfLogging OBJECT-TYPE
   SYNTAX      INTEGER(0|1)
   MAX-ACCESS  read-write
   STATUS      current
   DESCRIPTION
       "default: 0
        0: Disable
        1: Enable "
   ::= { xgs360026fACLPortsConfEntry 7 }

xgs360026fACLPortsConfShutdown OBJECT-TYPE
   SYNTAX      INTEGER(0|1)
   MAX-ACCESS  read-write
   STATUS      current
   DESCRIPTION
       "default: 0
        0: Disable
        1: Enable "
   ::= { xgs360026fACLPortsConfEntry 8 }

xgs360026fACLPortsConfState OBJECT-TYPE
   SYNTAX      INTEGER(0|1)
   MAX-ACCESS  read-write
   STATUS      current
   DESCRIPTION
       "default: 1
        0: Disable
        1: Enable "
   ::= { xgs360026fACLPortsConfEntry 9 }

xgs360026fACLPortsConfCounter OBJECT-TYPE
   SYNTAX      Counter32
   MAX-ACCESS  read-only
   STATUS      current
   DESCRIPTION
       "Counts the number of frames that match this ACE. "
   ::= { xgs360026fACLPortsConfEntry 10 }


xgs360026fACLRateLimiterTable OBJECT-TYPE
   SYNTAX      SEQUENCE OF XGS360026FACLRateLimiterEntry
   MAX-ACCESS  not-accessible
   STATUS      current
   DESCRIPTION
       " "
   ::= { xgs360026fACL 2 }

xgs360026fACLRateLimiterEntry OBJECT-TYPE
   SYNTAX      XGS360026FACLRateLimiterEntry
   MAX-ACCESS  not-accessible
   STATUS      current
   DESCRIPTION
       ""
   INDEX    { xgs360026fACLRateLimiterID  }
   ::= { xgs360026fACLRateLimiterTable 1 }

XGS360026FACLRateLimiterEntry ::= SEQUENCE {
   xgs360026fACLRateLimiterID       INTEGER,
   xgs360026fACLRateLimiterRate     INTEGER
}

xgs360026fACLRateLimiterID OBJECT-TYPE
   SYNTAX      INTEGER (1..16)
   MAX-ACCESS  not-accessible
   STATUS      current
   DESCRIPTION
       " Rate Limiter ID.
         range : 1-16 "
   ::= { xgs360026fACLRateLimiterEntry 1 }

xgs360026fACLRateLimiterRate OBJECT-TYPE
   SYNTAX      INTEGER (0..3276700)
   MAX-ACCESS  read-write
   STATUS      current
   DESCRIPTION
       "default: 1,
        range : <0-3276700> pps
       "
   ::= { xgs360026fACLRateLimiterEntry 3 }


xgs360026fACLACE                                          OBJECT IDENTIFIER ::= { xgs360026fACL 3 }

xgs360026fACLACECreate OBJECT-TYPE
   SYNTAX       INTEGER(0|1)
   MAX-ACCESS   read-write
   STATUS       current
   DESCRIPTION
       "default: 0
        0 : None  (read only)
        1 : Create an ACE entry"
   ::= { xgs360026fACLACE 1 }

xgs360026fACLACETable OBJECT-TYPE
   SYNTAX      SEQUENCE OF XGS360026FACLACEEntry
   MAX-ACCESS  not-accessible
   STATUS      current
   DESCRIPTION
       " Create ACL ACE entry. "
   ::= { xgs360026fACLACE 2 }

xgs360026fACLACEEntry OBJECT-TYPE
   SYNTAX      XGS360026FACLACEEntry
   MAX-ACCESS  not-accessible
   STATUS      current
   DESCRIPTION
       ""
   INDEX    { xgs360026fACLACEIndex  }
   ::= { xgs360026fACLACETable 1 }

XGS360026FACLACEEntry ::= SEQUENCE {
   xgs360026fACLACEIndex                INTEGER,
   xgs360026fACLACEID                   INTEGER,
   xgs360026fACLACENextID               INTEGER,
   xgs360026fACLACEIngressPort          DisplayString,
   xgs360026fACLACEPortPolicyNumber     INTEGER,

   xgs360026fACLACEPortPolicyBitmask    INTEGER,
   xgs360026fACLACEFrameType            INTEGER,
   xgs360026fACLACEAction               INTEGER,
   xgs360026fACLACEDenyPortRedirect     DisplayString,
   xgs360026fACLACELogging              INTEGER,

   xgs360026fACLACERateLimiter          INTEGER,
   xgs360026fACLACEShutdown             INTEGER,
   xgs360026fACLACEVLANTagPriority      INTEGER,

   xgs360026fACLACEVLANVID              INTEGER,
   xgs360026fACLACEEtherType            INTEGER,
   xgs360026fACLACESMAC                 DisplayString,
   xgs360026fACLACEDMACType             INTEGER,
   xgs360026fACLACEDMAC                 DisplayString,

   xgs360026fACLACEArpOpcode            INTEGER,
   xgs360026fACLACEArpFlagsRequestReply INTEGER,
   xgs360026fACLACEArpFlagsArpSmac      INTEGER,
   xgs360026fACLACEArpFlagsRarpDmac     INTEGER,
   xgs360026fACLACEArpFlagsLength       INTEGER,

   xgs360026fACLACEArpFlagsIp           INTEGER,
   xgs360026fACLACEArpFlagsEthernet     INTEGER,
   xgs360026fACLACESIPType              INTEGER,
   xgs360026fACLACESIPIPAddress         IpAddress,
   xgs360026fACLACESIPNetworkPrefix     INTEGER,

   xgs360026fACLACEDIPType              INTEGER,
   xgs360026fACLACEDIPIPAddress         IpAddress,
   xgs360026fACLACEDIPNetworkPrefix     INTEGER,

   xgs360026fACLACEIPProtocol           INTEGER,
   xgs360026fACLACEIPFlagsTTL           INTEGER,
   xgs360026fACLACEIPFlagsOptions       INTEGER,
   xgs360026fACLACEIPFlagsFragment      INTEGER,
   xgs360026fACLACEICMPType             INTEGER,

   xgs360026fACLACEICMPCode             INTEGER,
   xgs360026fACLACESourcePortMin        INTEGER,
   xgs360026fACLACESourcePortMax        INTEGER,
   xgs360026fACLACEDestPortMin          INTEGER,
   xgs360026fACLACEDestPortMax          INTEGER,

   xgs360026fACLACETCPFlagsFin          INTEGER,
   xgs360026fACLACETCPFlagsSyn          INTEGER,
   xgs360026fACLACETCPFlagsRst          INTEGER,
   xgs360026fACLACETCPFlagsPsh          INTEGER,
   xgs360026fACLACETCPFlagsAck          INTEGER,

   xgs360026fACLACETCPFlagsUrg          INTEGER,

   xgs360026fACLACERowStatus            INTEGER
}

xgs360026fACLACEIndex OBJECT-TYPE
   SYNTAX      INTEGER (1..256)
   MAX-ACCESS  not-accessible
   STATUS      current
   DESCRIPTION
       " "
   ::= { xgs360026fACLACEEntry 1 }

xgs360026fACLACEID OBJECT-TYPE
   SYNTAX      INTEGER (1..256)
   MAX-ACCESS  read-write
   STATUS      current
   DESCRIPTION
       " If the ACE ID is specified and an entry with this ACE ID
         already exists, the ACE will be modified. Otherwise, a
         new ACE will be added.
         range : 1 - 256. "
   ::= { xgs360026fACLACEEntry 2 }

xgs360026fACLACENextID OBJECT-TYPE
   SYNTAX      INTEGER (0..256)
   MAX-ACCESS  read-write
   STATUS      current
   DESCRIPTION
       " If the next ACE ID is non zero, the ACE will be placed
         before this ACE in the list. If the next ACE ID is zero,
         the ACE will be placed last in the list.
         range : 0 - 256. "
   ::= { xgs360026fACLACEEntry 3 }

xgs360026fACLACEIngressPort OBJECT-TYPE
   SYNTAX      DisplayString
   MAX-ACCESS  read-write
   STATUS      current
   DESCRIPTION
       " Indicates the ingress port of the ACE. Possible values are:
         All: The ACE will match all ingress port.
         Port: The ACE will match a specific ingress port.Format: 1,3,6."
   ::= { xgs360026fACLACEEntry 4 }

xgs360026fACLACEPortPolicyNumber OBJECT-TYPE
   SYNTAX      INTEGER (0..255)
   MAX-ACCESS  read-write
   STATUS      current
   DESCRIPTION
       " policy value.
         range : 0 - 255. "
   ::= { xgs360026fACLACEEntry 5 }

xgs360026fACLACEPortPolicyBitmask OBJECT-TYPE
   SYNTAX      INTEGER (0..255)
   MAX-ACCESS  read-write
   STATUS      current
   DESCRIPTION
       " policy bitmask.
         range : 0 - 255(0xff). "
   ::= { xgs360026fACLACEEntry 6 }

xgs360026fACLACEFrameType OBJECT-TYPE
   SYNTAX      INTEGER (0..6)
   MAX-ACCESS  read-write
   STATUS      current
   DESCRIPTION
       " 0: any,
         1: arp,
         2: etype,
         3: icmp,
         4: ipv4,
         5: tcp,
         6: udp."
   ::= { xgs360026fACLACEEntry 7 }

xgs360026fACLACEAction OBJECT-TYPE
   SYNTAX      INTEGER(0|1)
   MAX-ACCESS  read-write
   STATUS      current
   DESCRIPTION
       "default: 1,
        0: Deny
        1: Permit"
   ::= { xgs360026fACLACEEntry 8 }

xgs360026fACLACEDenyPortRedirect OBJECT-TYPE
   SYNTAX      DisplayString
   MAX-ACCESS  read-write
   STATUS      current
   DESCRIPTION
       " Frames that hit the ACE are redirected to the port number specified here.
         Disabled: indicates that the port redirect operation is disabled.
         Port Format: 1,3,6."
   ::= { xgs360026fACLACEEntry 9 }

xgs360026fACLACELogging OBJECT-TYPE
   SYNTAX      INTEGER(0|1)
   MAX-ACCESS  read-write
   STATUS      current
   DESCRIPTION
       "default: 0,
        0: disable - Frames matching the ACE are not logged.
        1: enable - Frames matching the ACE are stored in the system log."
   ::= { xgs360026fACLACEEntry 10 }

xgs360026fACLACERateLimiter OBJECT-TYPE
   SYNTAX      INTEGER (0..16)
   MAX-ACCESS  read-write
   STATUS      current
   DESCRIPTION
       "default: 0,
        0: Disable
        range : 0 - 16 "
   ::= { xgs360026fACLACEEntry 12 }

xgs360026fACLACEShutdown OBJECT-TYPE
   SYNTAX      INTEGER(0|1)
   MAX-ACCESS  read-write
   STATUS      current
   DESCRIPTION
       "default: 0,
        0: disable - Port shut down is disabled for the AC.
        1: enable - If a frame matches the ACE, the ingress port will be disabled."
   ::= { xgs360026fACLACEEntry 13 }

xgs360026fACLACEVLANTagPriority OBJECT-TYPE
   SYNTAX      INTEGER (0..8)
   MAX-ACCESS  read-write
   STATUS      current
   DESCRIPTION
       "Specify the tag priority for this ACE.
        The tag priority can't be set when 802.1Q Tagged is disabled
        default: 8,
        8: Any,
        range : 0 - 8 "
   ::= { xgs360026fACLACEEntry 15 }

xgs360026fACLACEVLANVID OBJECT-TYPE
   SYNTAX      INTEGER (0..4094)
   MAX-ACCESS  read-write
   STATUS      current
   DESCRIPTION
       "Specify the VLAN ID filter for this ACE.
        The vid can't be set when 802.1Q Tagged is disabled.
        default: 0,
        0: Any - No VLAN ID filter is specified.
        range : 0 - 4094 "
   ::= { xgs360026fACLACEEntry 16 }

xgs360026fACLACEEtherType OBJECT-TYPE
   SYNTAX      INTEGER (0..65535)
   MAX-ACCESS  read-write
   STATUS      current
   DESCRIPTION
       " 0: Any - Any but excluding 0x0800(IPv4) 0x0806(ARP) and 0x86DD(IPv6).
         range : 0 or 1536(0x0600)- 65535(0xffff). "
   ::= { xgs360026fACLACEEntry 17 }

xgs360026fACLACESMAC OBJECT-TYPE
   SYNTAX      DisplayString
   MAX-ACCESS  read-write
   STATUS      current
   DESCRIPTION
       " Configure source MAC address for this ACE.
         <mac-address>: A frame that hits this ACE matches this source MAC address value.
         Any: Don't care."
   ::= { xgs360026fACLACEEntry 18 }

xgs360026fACLACEDMACType OBJECT-TYPE
   SYNTAX      INTEGER (0..4)
   MAX-ACCESS  read-write
   STATUS      current
   DESCRIPTION
       "DMAC Type.
        default: 0,
        0: Any - Don't care.
        1: Broadcast - Frame must be broadcast.
        2: Unicast - Frame must be unicast.
        3: Multicast - Frame must be multicast.
        4: mac address
        range : 0 - 4 "
   ::= { xgs360026fACLACEEntry 19 }

xgs360026fACLACEDMAC OBJECT-TYPE
   SYNTAX      DisplayString
   MAX-ACCESS  read-write
   STATUS      current
   DESCRIPTION
       " Configure destination MAC address for this ACE.
         <mac-address>: A frame that hits this ACE matches this destination MAC address value.
         Any: Don't care.
         Broadcast: Frame must be broadcast.
         Unicast: Frame must be unicast.
         Multicast: Frame must be multicast. "
   ::= { xgs360026fACLACEEntry 20 }

xgs360026fACLACEArpOpcode OBJECT-TYPE
   SYNTAX      INTEGER (0..3)
   MAX-ACCESS  read-write
   STATUS      current
   DESCRIPTION
       "Configure ARP opcode for this ACE.
        default: 0,
        0: Any - Don't care.
        1: arp.
        2: rarp.
        3: other.
        4: No data.
        range : 0 - 3 "
   ::= { xgs360026fACLACEEntry 21 }

xgs360026fACLACEArpFlagsRequestReply OBJECT-TYPE
   SYNTAX      INTEGER (0..2)
   MAX-ACCESS  read-write
   STATUS      current
   DESCRIPTION
       "Specify the available ARP/RARP opcode (OP) flag for this ACE.
        default: 2,
        0: Frame must have ARP Reply or RARP Reply OP flag.
        1: Frame must have ARP Request or RARP Request OP flag set.
        2: Any - Don't care.
        3: No data.
        range : 0 - 2 "
   ::= { xgs360026fACLACEEntry 22 }

xgs360026fACLACEArpFlagsArpSmac OBJECT-TYPE
   SYNTAX      INTEGER (0..2)
   MAX-ACCESS  read-write
   STATUS      current
   DESCRIPTION
       "Specify whether frames can hit the action according to their sender hardware address field (SHA) settings.
        default: 2,
        0: ARP frames where SHA is not equal to the SMAC address.
        1: ARP frames where SHA is equal to the SMAC address.
        2: Any - Don't care.
        3: No data.
        range : 0 - 2 "
   ::= { xgs360026fACLACEEntry 23 }

xgs360026fACLACEArpFlagsRarpDmac OBJECT-TYPE
   SYNTAX      INTEGER (0..2)
   MAX-ACCESS  read-write
   STATUS      current
   DESCRIPTION
       "Specify whether frames can hit the action according to their target hardware address field (THA) settings.
        default: 2,
        0: RARP frames where THA is not equal to the DMAC address.
        1: RARP frames where THA is equal to the DMAC address.
        2: Any - Don't care.
        3: No data.
        range : 0 - 2 "
   ::= { xgs360026fACLACEEntry 24 }

xgs360026fACLACEArpFlagsLength OBJECT-TYPE
   SYNTAX      INTEGER (0..2)
   MAX-ACCESS  read-write
   STATUS      current
   DESCRIPTION
       "Specify whether frames can hit the action according to their ARP/RARP hardware address length (HLN) and
        protocol address length (PLN) settings.
        default: 2,
        0: ARP/RARP frames where the HLN is not equal to Ethernet(0x06) or the (PLN) is not equal to IPv4(0x04).
        1: ARP/RARP frames where the HLN is equal to Ethernet (0x06) and the (PLN) is equal to IPv4(0x04).
        2: Any - Don't care.
        3: No data.
        range : 0 - 2 "
   ::= { xgs360026fACLACEEntry 25 }

xgs360026fACLACEArpFlagsIp OBJECT-TYPE
   SYNTAX      INTEGER (0..2)
   MAX-ACCESS  read-write
   STATUS      current
   DESCRIPTION
       "Specify whether frames can hit the action according to their ARP/RARP hardware address space (HRD) settings.
        default: 2,
        0: ARP/RARP frames where the HLD is not equal to Ethernet(1).
        1: ARP/RARP frames where the HLD is equal to Ethernet(1).
        2: Any - Don't care.
        3: No data.
        range : 0 - 2 "
   ::= { xgs360026fACLACEEntry 26 }

xgs360026fACLACEArpFlagsEthernet OBJECT-TYPE
   SYNTAX      INTEGER (0..2)
   MAX-ACCESS  read-write
   STATUS      current
   DESCRIPTION
       "Specify whether frames can hit the action according to their ARP/RARP protocol address space (PRO) settings.
        default: 2,
        0: ARP/RARP frames where the PRO is not equal to IP\n(0x800).
        1: ARP/RARP frames where the PRO is equal to IP(0x800).
        2: Any - Don't care.
        3: No data.
        range : 0 - 2 "
   ::= { xgs360026fACLACEEntry 27 }

xgs360026fACLACESIPType OBJECT-TYPE
   SYNTAX      INTEGER(0|1)
   MAX-ACCESS  read-write
   STATUS      current
   DESCRIPTION
       "Configure source IP address for this ACE.
        default: 0,
        0: Any - Don't care.
        1: IP Address.
        2: No data.
        range : 0 - 1"
   ::= { xgs360026fACLACEEntry 28 }

xgs360026fACLACESIPIPAddress OBJECT-TYPE
   SYNTAX      IpAddress
   MAX-ACCESS  read-write
   STATUS      current
   DESCRIPTION
       "A frame that hits this ACE matches this source IP address value."
   ::= { xgs360026fACLACEEntry 29 }

xgs360026fACLACESIPNetworkPrefix OBJECT-TYPE
   SYNTAX      INTEGER (1..32)
   MAX-ACCESS  read-write
   STATUS      current
   DESCRIPTION
       "Network prefix.
        default: 32,
        0: No data.
        range : 1 - 32"
   ::= { xgs360026fACLACEEntry 30 }


xgs360026fACLACEDIPType OBJECT-TYPE
   SYNTAX      INTEGER(0|1)
   MAX-ACCESS  read-write
   STATUS      current
   DESCRIPTION
       "Configure destination IP address for this ACE.
        default: 0,
        0: Any - Don't care.
        1: IP Address.
        2: No data.
        range : 0 - 1"
   ::= { xgs360026fACLACEEntry 32 }

xgs360026fACLACEDIPIPAddress OBJECT-TYPE
   SYNTAX      IpAddress
   MAX-ACCESS  read-write
   STATUS      current
   DESCRIPTION
       "A frame that hits this ACE matches this destination IP address value."
   ::= { xgs360026fACLACEEntry 33 }

xgs360026fACLACEDIPNetworkPrefix OBJECT-TYPE
   SYNTAX      INTEGER (1..32)
   MAX-ACCESS  read-write
   STATUS      current
   DESCRIPTION
       "Network prefix.
        default: 32,
        0: No data.
        range : 1 - 32"
   ::= { xgs360026fACLACEEntry 34 }


xgs360026fACLACEIPProtocol OBJECT-TYPE
   SYNTAX      INTEGER (0..256)
   MAX-ACCESS  read-write
   STATUS      current
   DESCRIPTION
       "Configure IP protocol for this ACE.
        default: 256,
        256: Any - Don't care.
        257: No data.
        range : 0 - 256"
   ::= { xgs360026fACLACEEntry 36 }

xgs360026fACLACEIPFlagsTTL OBJECT-TYPE
   SYNTAX      INTEGER (0..2)
   MAX-ACCESS  read-write
   STATUS      current
   DESCRIPTION
       "Configure IP Time-to-Live flags for this ACE.
        default: 2,
        0: IPv4 frames with a Time-to-Live field is equal to zero.
        1: IPv4 frames with a Time-to-Live field greater than zero.
        2: Any - Don't care.
        3: No data.
        range : 0 - 2 "
   ::= { xgs360026fACLACEEntry 37 }

xgs360026fACLACEIPFlagsOptions OBJECT-TYPE
   SYNTAX      INTEGER (0..2)
   MAX-ACCESS  read-write
   STATUS      current
   DESCRIPTION
       "Configure IP options flag for this ACE.
        default: 2,
        0: IPv4 frames where the options flag is unset.
        1: IPv4 frames where the options flag is set.
        2: Any - Don't care.
        3: No data.
        range : 0 - 2 "
   ::= { xgs360026fACLACEEntry 38 }

xgs360026fACLACEIPFlagsFragment OBJECT-TYPE
   SYNTAX      INTEGER (0..2)
   MAX-ACCESS  read-write
   STATUS      current
   DESCRIPTION
       "Configure IP fragment offset flags for this ACE.
        default: 2,
        0: IPv4 frames where the MF bit is unset and the FRAG OFFSET field is equal zero.
        1: IPv4 frames where the MF bit is set or the FRAG OFFSET field is greater than zero.
        2: Any - Don't care.
        3: No data.
        range : 0 - 2 "
   ::= { xgs360026fACLACEEntry 39 }

xgs360026fACLACEICMPType OBJECT-TYPE
   SYNTAX      INTEGER (0..256)
   MAX-ACCESS  read-write
   STATUS      current
   DESCRIPTION
       "Configure ICMP type for this ACE.
        default: 256,
        256: Any - Don't care.
        257: No data.
        range : 0 - 256"
   ::= { xgs360026fACLACEEntry 40 }

xgs360026fACLACEICMPCode OBJECT-TYPE
   SYNTAX      INTEGER (0..256)
   MAX-ACCESS  read-write
   STATUS      current
   DESCRIPTION
       "Configure ICMP code for this ACE.
        default: 256,
        256: Any - Don't care.
        257: No data.
        range : 0 - 256"
   ::= { xgs360026fACLACEEntry 41 }

xgs360026fACLACESourcePortMin OBJECT-TYPE
   SYNTAX      INTEGER (0..65535)
   MAX-ACCESS  read-write
   STATUS      current
   DESCRIPTION
       "Configure Source UDP/TCP port range for this ACE.
        default: 0,
        65536: No data.
        range : 0 - 65535"
   ::= { xgs360026fACLACEEntry 42 }

xgs360026fACLACESourcePortMax OBJECT-TYPE
   SYNTAX      INTEGER (0..65535)
   MAX-ACCESS  read-write
   STATUS      current
   DESCRIPTION
       "Configure Source UDP/TCP port range for this ACE.
        default: 0,
        65536: No data.
        range : 0 - 65535"
   ::= { xgs360026fACLACEEntry 43 }

xgs360026fACLACEDestPortMin OBJECT-TYPE
   SYNTAX      INTEGER (0..65535)
   MAX-ACCESS  read-write
   STATUS      current
   DESCRIPTION
       "Configure Destination UDP/TCP port range for this ACE.
        default: 0,
        65536: No data.
        range : 0 - 65535"
   ::= { xgs360026fACLACEEntry 44 }

xgs360026fACLACEDestPortMax OBJECT-TYPE
   SYNTAX      INTEGER (0..65535)
   MAX-ACCESS  read-write
   STATUS      current
   DESCRIPTION
       "Configure Destination UDP/TCP port range for this ACE.
        default: 0,
        65536: No data.
        range : 0 - 65535"
   ::= { xgs360026fACLACEEntry 45 }

xgs360026fACLACETCPFlagsFin OBJECT-TYPE
   SYNTAX      INTEGER (0..2)
   MAX-ACCESS  read-write
   STATUS      current
   DESCRIPTION
       "Configure TCP (FIN) flags for this ACE.
        default: 2,
        0: TCP frames where the FIN field is unset.
        1: TCP frames where the FIN field is set.
        2: Any - Don't care.
        3: No data.
        range : 0 - 2 "
   ::= { xgs360026fACLACEEntry 46 }

xgs360026fACLACETCPFlagsSyn OBJECT-TYPE
   SYNTAX      INTEGER (0..2)
   MAX-ACCESS  read-write
   STATUS      current
   DESCRIPTION
       "Configure TCP (SYN) flags for this ACE.
        default: 2,
        0: TCP frames where the SYN field is unset.
        1: TCP frames where the SYN field is set.
        2: Any - Don't care.
        3: No data.
        range : 0 - 2 "
   ::= { xgs360026fACLACEEntry 47 }

xgs360026fACLACETCPFlagsRst OBJECT-TYPE
   SYNTAX      INTEGER (0..2)
   MAX-ACCESS  read-write
   STATUS      current
   DESCRIPTION
       "Configure TCP (RST) flags for this ACE.
        default: 2,
        0: TCP frames where the RST field is unset.
        1: TCP frames where the RST field is set.
        2: Any - Don't care.
        3: No data.
        range : 0 - 2 "
   ::= { xgs360026fACLACEEntry 48 }

xgs360026fACLACETCPFlagsPsh OBJECT-TYPE
   SYNTAX      INTEGER (0..2)
   MAX-ACCESS  read-write
   STATUS      current
   DESCRIPTION
       "Configure TCP (PSH) flags for this ACE.
        default: 2,
        0: TCP frames where the PSH field is unset.
        1: TCP frames where the PSH field is set.
        2: Any - Don't care.
        3: No data.
        range : 0 - 2 "
   ::= { xgs360026fACLACEEntry 49 }

xgs360026fACLACETCPFlagsAck OBJECT-TYPE
   SYNTAX      INTEGER (0..2)
   MAX-ACCESS  read-write
   STATUS      current
   DESCRIPTION
       "Configure TCP (ACK) flags for this ACE.
        default: 2,
        0: TCP frames where the ACK field is unset.
        1: TCP frames where the ACK field is set.
        2: Any - Don't care.
        3: No data.
        range : 0 - 2 "
   ::= { xgs360026fACLACEEntry 50 }

xgs360026fACLACETCPFlagsUrg OBJECT-TYPE
   SYNTAX      INTEGER (0..2)
   MAX-ACCESS  read-write
   STATUS      current
   DESCRIPTION
       "Configure TCP (URG) flags for this ACE.
        default: 2,
        0: TCP frames where the URG field is unset.
        1: TCP frames where the URG field is set.
        2: Any - Don't care.
        3: No data.
        range : 0 - 2 "
   ::= { xgs360026fACLACEEntry 51 }

xgs360026fACLACERowStatus OBJECT-TYPE
   SYNTAX      INTEGER (1..5)
   MAX-ACCESS  read-write
   STATUS      current
   DESCRIPTION
       " 1: active
         2: notInservice
         4: destroy
         5: undo"
   ::= { xgs360026fACLACEEntry 66 }


xgs360026fACLACEClear OBJECT-TYPE
   SYNTAX       INTEGER(0|1)
   MAX-ACCESS   read-write
   STATUS       current
   DESCRIPTION
       "default: 0
        0 : No action
        1 : Clear all ACL counters."
   ::= { xgs360026fACLACE 3 }

xgs360026fACLACEMoveACEID OBJECT-TYPE
   SYNTAX       INTEGER (1..256)
   MAX-ACCESS   read-write
   STATUS       current
   DESCRIPTION
       "Move ACE,
        default: 0
        ACE ID must be exist.
        range : 1 - 256."
   ::= { xgs360026fACLACE 4 }

xgs360026fACLACEMoveNextACEID OBJECT-TYPE
   SYNTAX       INTEGER (0..256)
   MAX-ACCESS   read-write
   STATUS       current
   DESCRIPTION
       "Move ACE,
        default: 0
        If the next ACE ID is non zero, the ACE will be placed before this ACE in the list. If the next ACE ID is zero,
        the ACE will be placed last in the list.
        range : 0 - 256."
   ::= { xgs360026fACLACE 5 }

xgs360026fACLACEStatusTable OBJECT-TYPE
   SYNTAX      SEQUENCE OF XGS360026FACLACEStatusEntry
   MAX-ACCESS  not-accessible
   STATUS      current
   DESCRIPTION
       " ACL ACE Status entry. "
   ::= { xgs360026fACLACE 6 }

xgs360026fACLACEStatusEntry OBJECT-TYPE
   SYNTAX      XGS360026FACLACEStatusEntry
   MAX-ACCESS  not-accessible
   STATUS      current
   DESCRIPTION
       ""
   INDEX    { xgs360026fACLACEStatusIndex  }
   ::= { xgs360026fACLACEStatusTable 1 }

XGS360026FACLACEStatusEntry ::= SEQUENCE {
   xgs360026fACLACEStatusIndex          INTEGER,
   xgs360026fACLACEStatusUser           DisplayString,
   xgs360026fACLACEStatusID             INTEGER,
   xgs360026fACLACEStatusIngressPort    DisplayString,
   xgs360026fACLACEStatusFrameType      DisplayString,
   xgs360026fACLACEStatusAction         DisplayString,
   xgs360026fACLACEStatusRateLimiter    DisplayString,
   xgs360026fACLACEStatusPortCopy       DisplayString,
   xgs360026fACLACEStatusMirror         DisplayString,
   xgs360026fACLACEStatusCPU            DisplayString,
   xgs360026fACLACEStatusCounter        Counter32,
   xgs360026fACLACEStatusConflict       DisplayString
}

xgs360026fACLACEStatusIndex OBJECT-TYPE
   SYNTAX      INTEGER (1..256)
   MAX-ACCESS  not-accessible
   STATUS      current
   DESCRIPTION
       " "
   ::= { xgs360026fACLACEStatusEntry 1 }

xgs360026fACLACEStatusUser OBJECT-TYPE
   SYNTAX      DisplayString
   MAX-ACCESS  read-only
   STATUS      current
   DESCRIPTION
       " Indicates the ACL user.
         S : Static.
         IPMG : IP Management.
         IPSG : IP Source Guard.
         IPMC : IPMC.
         ARPI : Arp Inspection.
         UPnP : UPnP.
         DHCP : DHCP. "
   ::= { xgs360026fACLACEStatusEntry 2 }

xgs360026fACLACEStatusID OBJECT-TYPE
   SYNTAX      INTEGER (1..256)
   MAX-ACCESS  read-only
   STATUS      current
   DESCRIPTION
       " ACE ID.
         range : 1 - 256. "
   ::= { xgs360026fACLACEStatusEntry 3 }

xgs360026fACLACEStatusIngressPort OBJECT-TYPE
   SYNTAX      DisplayString
   MAX-ACCESS  read-only
   STATUS      current
   DESCRIPTION
       " Indicates the ingress port of the ACE. Possible values are:
         All: The ACE will match all ingress port.
         Port: The ACE will match a specific ingress port. "
   ::= { xgs360026fACLACEStatusEntry 4 }

xgs360026fACLACEStatusFrameType OBJECT-TYPE
   SYNTAX      DisplayString
   MAX-ACCESS  read-only
   STATUS      current
   DESCRIPTION
       " Indicates the frame type of the ACE. "
   ::= { xgs360026fACLACEStatusEntry 5 }

xgs360026fACLACEStatusAction OBJECT-TYPE
   SYNTAX      DisplayString
   MAX-ACCESS  read-only
   STATUS      current
   DESCRIPTION
       " Indicates the forwarding action of the ACE. "
   ::= { xgs360026fACLACEStatusEntry 6 }

xgs360026fACLACEStatusRateLimiter OBJECT-TYPE
   SYNTAX      DisplayString
   MAX-ACCESS  read-only
   STATUS      current
   DESCRIPTION
       " Indicates the rate limiter number of the ACE. "
   ::= { xgs360026fACLACEStatusEntry 7 }

xgs360026fACLACEStatusPortCopy OBJECT-TYPE
   SYNTAX      DisplayString
   MAX-ACCESS  read-only
   STATUS      current
   DESCRIPTION
       " Indicates the port redirect operation of the ACE. Frames matching the ACE are redirected to the port number. "
   ::= { xgs360026fACLACEStatusEntry 8 }

xgs360026fACLACEStatusMirror OBJECT-TYPE
   SYNTAX      DisplayString
   MAX-ACCESS  read-only
   STATUS      current
   DESCRIPTION
       " Specify the mirror operation of this port. "
   ::= { xgs360026fACLACEStatusEntry 9 }

xgs360026fACLACEStatusCPU OBJECT-TYPE
   SYNTAX      DisplayString
   MAX-ACCESS  read-only
   STATUS      current
   DESCRIPTION
       " Forward packet that matched the specific ACE to CPU. "
   ::= { xgs360026fACLACEStatusEntry 10 }

xgs360026fACLACEStatusCounter OBJECT-TYPE
   SYNTAX      Counter32
   MAX-ACCESS  read-only
   STATUS      current
   DESCRIPTION
       " The counter indicates the number of times the ACE was hit by a frame. "
   ::= { xgs360026fACLACEStatusEntry 11 }

xgs360026fACLACEStatusConflict OBJECT-TYPE
   SYNTAX      DisplayString
   MAX-ACCESS  read-only
   STATUS      current
   DESCRIPTION
       " Indicates the hardware status of the specific ACE. The specific ACE is not applied to the hardware due to hardware limitations. "
   ::= { xgs360026fACLACEStatusEntry 12 }


xgs360026fERPS                                             OBJECT IDENTIFIER ::= { xgs360026fConfiguration 10 }

xgs360026fERPSConf                                          OBJECT IDENTIFIER ::= { xgs360026fERPS 1 }

xgs360026fERPSConfCreate OBJECT-TYPE
   SYNTAX       INTEGER(0|1)
   MAX-ACCESS   read-write
   STATUS       current
   DESCRIPTION
       "default: 0
        0 : None  (read only)
        1 : Create an ERPS entry"
   ::= { xgs360026fERPSConf 1 }

xgs360026fERPSConfTable OBJECT-TYPE
   SYNTAX      SEQUENCE OF XGS360026FERPSConfEntry
   MAX-ACCESS  not-accessible
   STATUS      current
   DESCRIPTION
       " Create one ERPS group. "
   ::= { xgs360026fERPSConf 2 }

xgs360026fERPSConfEntry OBJECT-TYPE
   SYNTAX      XGS360026FERPSConfEntry
   MAX-ACCESS  not-accessible
   STATUS      current
   DESCRIPTION
       ""
   INDEX    { xgs360026fERPSConfIndex  }
   ::= { xgs360026fERPSConfTable 1 }

XGS360026FERPSConfEntry ::= SEQUENCE {
   xgs360026fERPSConfIndex                  INTEGER,
   xgs360026fERPSConfERPSID                 INTEGER,
   xgs360026fERPSConfPort0                  INTEGER,
   xgs360026fERPSConfPort1                  INTEGER,
   xgs360026fERPSConfPort0SFMEP             INTEGER,
   xgs360026fERPSConfPort1SFMEP             INTEGER,
   xgs360026fERPSConfPort0APSMEP            INTEGER,
   xgs360026fERPSConfPort1APSMEP            INTEGER,
   xgs360026fERPSConfRingType               INTEGER,
   xgs360026fERPSConfInterconnectedNode     INTEGER,
   xgs360026fERPSConfVirtualChannel         INTEGER,
   xgs360026fERPSConfMajorRingID            INTEGER,
   xgs360026fERPSConfAlarm                  DisplayString,

   xgs360026fERPSInstanceConfConfigured     DisplayString,
   xgs360026fERPSInstanceConfGuardTime      INTEGER,
   xgs360026fERPSInstanceConfWTRTime        INTEGER,
   xgs360026fERPSInstanceConfHoldOffTime    INTEGER,
   xgs360026fERPSInstanceConfVersion        INTEGER,
   xgs360026fERPSInstanceConfRevertive      INTEGER,
   xgs360026fERPSInstanceConfVLANconfig     DisplayString,

   xgs360026fERPSConfRowStatus              INTEGER
}

xgs360026fERPSConfIndex OBJECT-TYPE
   SYNTAX      INTEGER (1..64)
   MAX-ACCESS  not-accessible
   STATUS      current
   DESCRIPTION
       " "
   ::= { xgs360026fERPSConfEntry 1 }

xgs360026fERPSConfERPSID OBJECT-TYPE
   SYNTAX      INTEGER (1..64)
   MAX-ACCESS  read-write
   STATUS      current
   DESCRIPTION
       " Protection group ID.
         range : 1 - 64. "
   ::= { xgs360026fERPSConfEntry 2 }

xgs360026fERPSConfPort0 OBJECT-TYPE
   SYNTAX      INTEGER (1..26)
   MAX-ACCESS  read-write
   STATUS      current
   DESCRIPTION
       " East port of the switch in the ring.
         range : 1 - 26. "
   ::= { xgs360026fERPSConfEntry 3 }

xgs360026fERPSConfPort1 OBJECT-TYPE
   SYNTAX      INTEGER (0..26)
   MAX-ACCESS  read-write
   STATUS      current
   DESCRIPTION
       " West port of the switch in the Ring.
         As interconnected sub-ring will have only one ring port, W port is configured as 0 for interconnected sub-ring.
         0: in this field indicates that no west port is associated with this instance.
         range : 0 - 26. "
   ::= { xgs360026fERPSConfEntry 4 }

xgs360026fERPSConfPort0SFMEP OBJECT-TYPE
   SYNTAX      INTEGER (1..32)
   MAX-ACCESS  read-write
   STATUS      current
   DESCRIPTION
       " The East Signal Fail reporting MEP.
         range : 1 - 32. "
   ::= { xgs360026fERPSConfEntry 5 }

xgs360026fERPSConfPort1SFMEP OBJECT-TYPE
   SYNTAX      INTEGER (0..32)
   MAX-ACCESS  read-write
   STATUS      current
   DESCRIPTION
       " The West Signal Fail reporting MEP. As only one SF MEP is associated with interconnected sub-ring without virtual channel,
         it is configured as 0 for such ring instances. 0: in this field indicates that no west SF MEP is associated with this instance.
         range : 0 - 32. "
   ::= { xgs360026fERPSConfEntry 6 }

xgs360026fERPSConfPort0APSMEP OBJECT-TYPE
   SYNTAX      INTEGER (1..32)
   MAX-ACCESS  read-write
   STATUS      current
   DESCRIPTION
       " The East APS PDU handling MEP.
         range : 1 - 32. "
   ::= { xgs360026fERPSConfEntry 7 }

xgs360026fERPSConfPort1APSMEP OBJECT-TYPE
   SYNTAX      INTEGER (0..32)
   MAX-ACCESS  read-write
   STATUS      current
   DESCRIPTION
       " The West APS PDU handling MEP. As only one APS MEP is associated with interconnected sub-ring without virtual channel,
         it is configured as 0 for such ring instances. 0: in this field indicates that no west APS MEP is associated with this instance.
         range : 0 - 32. "
   ::= { xgs360026fERPSConfEntry 8 }

xgs360026fERPSConfRingType OBJECT-TYPE
   SYNTAX      INTEGER (0|1)
   MAX-ACCESS  read-write
   STATUS      current
   DESCRIPTION
       " Type of Protectiong ring. It can be either major ring or sub-ring.
         default: 0,
         0: Major
         1: Sub"
   ::= { xgs360026fERPSConfEntry 9 }

xgs360026fERPSConfInterconnectedNode OBJECT-TYPE
   SYNTAX      INTEGER (0|1)
   MAX-ACCESS  read-write
   STATUS      current
   DESCRIPTION
       " Interconnected Node indicates that the ring instance is interconnected.
         default: 0,
         0: No - indicates that the configured instance is not interconnected.
         1: Yes - indicates it is an interconnected node for this instance. "
   ::= { xgs360026fERPSConfEntry 10 }

xgs360026fERPSConfVirtualChannel OBJECT-TYPE
   SYNTAX      INTEGER (0|1)
   MAX-ACCESS  read-write
   STATUS      current
   DESCRIPTION
       " Sub-rings can either have virtual channel or not on the interconnected node.
         default: 0,
         0: No - indicates, sub-ring doesn't have virtual channel.
         1: Yes - indicates it is a sub-ring with virtual channel. "
   ::= { xgs360026fERPSConfEntry 11 }

xgs360026fERPSConfMajorRingID OBJECT-TYPE
   SYNTAX      INTEGER (1..64)
   MAX-ACCESS  read-only
   STATUS      current
   DESCRIPTION
       " Major ring group ID for the interconnected sub-ring.
         It is used to send topology change updates on major ring.
         If ring is major, this value is same as the protection group ID of this ring. "
   ::= { xgs360026fERPSConfEntry 12 }

xgs360026fERPSConfAlarm OBJECT-TYPE
   SYNTAX      DisplayString (SIZE (1..32))
   MAX-ACCESS  read-only
   STATUS      current
   DESCRIPTION
       " There is an active alarm on the ERPS. "
   ::= { xgs360026fERPSConfEntry 13 }

xgs360026fERPSInstanceConfConfigured OBJECT-TYPE
   SYNTAX      DisplayString (SIZE (1..32))
   MAX-ACCESS  read-only
   STATUS      current
   DESCRIPTION
       " Down: This ERPS is only created and has not yet been configured - is not active.
         Up: This ERPS is configured - is active. "
   ::= { xgs360026fERPSConfEntry 14 }

xgs360026fERPSInstanceConfGuardTime OBJECT-TYPE
   SYNTAX      INTEGER (10..2000)
   MAX-ACCESS  read-write
   STATUS      current
   DESCRIPTION
       " Guard timeout value to be used to prevent ring nodes from receiving outdated R-APS messages.
         default : 500(ms).
         range : 10 - 2000(ms). "
   ::= { xgs360026fERPSConfEntry 15 }

xgs360026fERPSInstanceConfWTRTime OBJECT-TYPE
   SYNTAX      INTEGER (1..12)
   MAX-ACCESS  read-write
   STATUS      current
   DESCRIPTION
       " The Wait To Restore timing value to be used in revertive switching.
         default : 5(minutes).
         range : 1 - 12(minutes). "
   ::= { xgs360026fERPSConfEntry 16 }

xgs360026fERPSInstanceConfHoldOffTime OBJECT-TYPE
   SYNTAX      INTEGER (0..10000)
   MAX-ACCESS  read-write
   STATUS      current
   DESCRIPTION
       " The timing value to be used to make persistent check on Signal Fail before switching.
         default : 0(seconds).
         range : 0 - 10000(ms). "
   ::= { xgs360026fERPSConfEntry 17 }

xgs360026fERPSInstanceConfVersion OBJECT-TYPE
   SYNTAX      INTEGER (0|1)
   MAX-ACCESS  read-write
   STATUS      current
   DESCRIPTION
       " ERPS version of a group.
         default : 1.
         0: v1
         1: v2 "
   ::= { xgs360026fERPSConfEntry 18 }

xgs360026fERPSInstanceConfRevertive OBJECT-TYPE
   SYNTAX      INTEGER (0|1)
   MAX-ACCESS  read-write
   STATUS      current
   DESCRIPTION
       " ERPS revertibility of a group.
         default : 1.
         0: non-revertible
         1: revertible "
   ::= { xgs360026fERPSConfEntry 19 }

xgs360026fERPSInstanceConfVLANconfig OBJECT-TYPE
   SYNTAX      DisplayString (SIZE (1..255))
   MAX-ACCESS  read-write
   STATUS      current
   DESCRIPTION
       " VID of the protected vlan. "
   ::= { xgs360026fERPSConfEntry 20 }

xgs360026fERPSConfRowStatus OBJECT-TYPE
   SYNTAX      INTEGER (1..5)
   MAX-ACCESS  read-write
   STATUS      current
   DESCRIPTION
       " 1: active
        2: notInservice
        3: edit
        4: destroy
        5: undo"
   ::= { xgs360026fERPSConfEntry 21 }


xgs360026fMRSTP                                             OBJECT IDENTIFIER ::= { xgs360026fConfiguration 11 }

xgs360026fMRSTPInstance                                          OBJECT IDENTIFIER ::= { xgs360026fMRSTP 1 }

xgs360026fMRSTPInstanceConf                                          OBJECT IDENTIFIER ::= { xgs360026fMRSTPInstance 1 }

xgs360026fMRSTPInstanceConfGlobalState OBJECT-TYPE
   SYNTAX      INTEGER(0|1)
   MAX-ACCESS  read-write
   STATUS      current
   DESCRIPTION
       "default: 0
       0: disable
       1: enable"
   ::= { xgs360026fMRSTPInstanceConf 1 }

xgs360026fMRSTPInstanceConfigurationTable OBJECT-TYPE
   SYNTAX      SEQUENCE OF XGS360026FMRSTPInstanceConfigurationEntry
   MAX-ACCESS  not-accessible
   STATUS      current
   DESCRIPTION
       " show instance configuration. "
   ::= { xgs360026fMRSTPInstanceConf 2 }

xgs360026fMRSTPInstanceConfigurationEntry OBJECT-TYPE
   SYNTAX      XGS360026FMRSTPInstanceConfigurationEntry
   MAX-ACCESS  not-accessible
   STATUS      current
   DESCRIPTION
       ""
   INDEX    { xgs360026fMRSTPInstanceConfigurationInstance  }
   ::= { xgs360026fMRSTPInstanceConfigurationTable 1 }

XGS360026FMRSTPInstanceConfigurationEntry ::= SEQUENCE {
   xgs360026fMRSTPInstanceConfigurationInstance         INTEGER,
   xgs360026fMRSTPInstanceConfigurationState            INTEGER,
   xgs360026fMRSTPInstanceConfigurationVersion          INTEGER,
   xgs360026fMRSTPInstanceConfigurationPriority         INTEGER,
   xgs360026fMRSTPInstanceConfigurationHelloTime        INTEGER,
   xgs360026fMRSTPInstanceConfigurationMaxAge           INTEGER,
   xgs360026fMRSTPInstanceConfigurationFWDelay          INTEGER
}

xgs360026fMRSTPInstanceConfigurationInstance OBJECT-TYPE
   SYNTAX      INTEGER(1..12)
   MAX-ACCESS  not-accessible
   STATUS      current
   DESCRIPTION
       " mrstp instance id, range : 1-12 "
   ::= { xgs360026fMRSTPInstanceConfigurationEntry 1 }

xgs360026fMRSTPInstanceConfigurationState OBJECT-TYPE
   SYNTAX      INTEGER (0|1)
   MAX-ACCESS  read-write
   STATUS      current
   DESCRIPTION
       " MRSTP instance state. To really enable an MRSTP instance, the MRSTP Global State must also be enabled.
         default: 0,
         0: disable
         1: enable"
   ::= { xgs360026fMRSTPInstanceConfigurationEntry 2 }

xgs360026fMRSTPInstanceConfigurationVersion OBJECT-TYPE
   SYNTAX      INTEGER (0|1)
   MAX-ACCESS  read-write
   STATUS      current
   DESCRIPTION
       " The STP protocol version.
         default: 1,
         0: stp
         1: rstp"
   ::= { xgs360026fMRSTPInstanceConfigurationEntry 3 }

xgs360026fMRSTPInstanceConfigurationPriority OBJECT-TYPE
   SYNTAX      INTEGER(0..61440)
   MAX-ACCESS  read-write
   STATUS      current
   DESCRIPTION
       " The instance priority would be truncated to a multiple of 4096.
         range : 0 - 61440, default: 32768."
   ::= { xgs360026fMRSTPInstanceConfigurationEntry 4 }

xgs360026fMRSTPInstanceConfigurationHelloTime OBJECT-TYPE
   SYNTAX      INTEGER(1..10)
   MAX-ACCESS  read-write
   STATUS      current
   DESCRIPTION
       " The interval between periodic transmissions of STP Configuration Messages by Designated Ports when the Bridge Instance is the Root Bridge.
         range : 1 - 10 (seconds), and (HelloTime+1)*2 must be <= MaxAge.
         default: 2."
   ::= { xgs360026fMRSTPInstanceConfigurationEntry 5 }

xgs360026fMRSTPInstanceConfigurationMaxAge OBJECT-TYPE
   SYNTAX      INTEGER(6..40)
   MAX-ACCESS  read-write
   STATUS      current
   DESCRIPTION
       " The maximum age of the information transmitted by the Bridge Instance when it is the Root Bridge.
         range : 6 - 40 (seconds), and MaxAge must be <= (FwdDelay-1)*2.
         default: 20."
   ::= { xgs360026fMRSTPInstanceConfigurationEntry 6 }

xgs360026fMRSTPInstanceConfigurationFWDelay OBJECT-TYPE
   SYNTAX      INTEGER(4..30)
   MAX-ACCESS  read-write
   STATUS      current
   DESCRIPTION
       " The delay used by an MRSTP Bridge Instance to transit Root and Designated Ports to Forwarding
        (used in STP compatible mode).
         range : 4 - 30 (seconds), and MaxAge must be <= (FwdDelay-1)*2.
         default: 15."
   ::= { xgs360026fMRSTPInstanceConfigurationEntry 7 }

xgs360026fMRSTPInstanceStatus                                          OBJECT IDENTIFIER ::= { xgs360026fMRSTPInstance 2 }

xgs360026fMRSTPInstanceStatusTable OBJECT-TYPE
   SYNTAX      SEQUENCE OF XGS360026FMRSTPInstanceStatusEntry
   MAX-ACCESS  not-accessible
   STATUS      current
   DESCRIPTION
       " show mrstp status of instance(s). "
   ::= { xgs360026fMRSTPInstanceStatus 1 }

xgs360026fMRSTPInstanceStatusEntry OBJECT-TYPE
   SYNTAX      XGS360026FMRSTPInstanceStatusEntry
   MAX-ACCESS  not-accessible
   STATUS      current
   DESCRIPTION
       ""
   INDEX    { xgs360026fMRSTPInstanceStatusInstance  }
   ::= { xgs360026fMRSTPInstanceStatusTable 1 }

XGS360026FMRSTPInstanceStatusEntry ::= SEQUENCE {
   xgs360026fMRSTPInstanceStatusInstance                        INTEGER,
   xgs360026fMRSTPInstanceStatusGlobalState                     INTEGER,
   xgs360026fMRSTPInstanceStatusInstanceConfigState             INTEGER,
   xgs360026fMRSTPInstanceStatusInstanceCurrentState            INTEGER,
   xgs360026fMRSTPInstanceStatusBridgeID                        MacAddress,
   xgs360026fMRSTPInstanceStatusBridgePrioriry                  INTEGER,
   xgs360026fMRSTPInstanceStatusRootID                          MacAddress,
   xgs360026fMRSTPInstanceStatusRootPriority                    INTEGER,
   xgs360026fMRSTPInstanceStatusRootPort                        INTEGER,
   xgs360026fMRSTPInstanceStatusRootPathCost                    INTEGER,
   xgs360026fMRSTPInstanceStatusCurrentMaxAge                   INTEGER,
   xgs360026fMRSTPInstanceStatusCurrentForwardDelay             INTEGER,
   xgs360026fMRSTPInstanceStatusHelloTime                       INTEGER,
   xgs360026fMRSTPInstanceStatusTopologyChangeCount             INTEGER,
   xgs360026fMRSTPInstanceStatusTimeSinceLastTopologyChange     INTEGER
}

xgs360026fMRSTPInstanceStatusInstance OBJECT-TYPE
   SYNTAX      INTEGER(1..12)
   MAX-ACCESS  not-accessible
   STATUS      current
   DESCRIPTION
       " mrstp instance id, range : 1-12 "
   ::= { xgs360026fMRSTPInstanceStatusEntry 1 }

xgs360026fMRSTPInstanceStatusGlobalState OBJECT-TYPE
   SYNTAX      INTEGER (0|1)
   MAX-ACCESS  read-only
   STATUS      current
   DESCRIPTION
       " The global state of MRSTP. If disabled,all instances won't be in an active state.
         0: disable
         1: enable"
   ::= { xgs360026fMRSTPInstanceStatusEntry 2 }

xgs360026fMRSTPInstanceStatusInstanceConfigState OBJECT-TYPE
   SYNTAX      INTEGER (0|1)
   MAX-ACCESS  read-only
   STATUS      current
   DESCRIPTION
       " The configured state of an MRSTP instance.
         0: disable
         1: enable"
   ::= { xgs360026fMRSTPInstanceStatusEntry 3 }

xgs360026fMRSTPInstanceStatusInstanceCurrentState OBJECT-TYPE
   SYNTAX      INTEGER (0|1)
   MAX-ACCESS  read-only
   STATUS      current
   DESCRIPTION
       " The operational state of an MRSTP Bridge Instance.
         0: disable
         1: enable"
   ::= { xgs360026fMRSTPInstanceStatusEntry 4 }

xgs360026fMRSTPInstanceStatusBridgeID OBJECT-TYPE
   SYNTAX       MacAddress
   MAX-ACCESS   read-only
   STATUS       current
   DESCRIPTION
       " The Bridge ID of this Bridge instance. "
   ::= { xgs360026fMRSTPInstanceStatusEntry 5 }

xgs360026fMRSTPInstanceStatusBridgePrioriry OBJECT-TYPE
   SYNTAX      INTEGER(0..61440)
   MAX-ACCESS  read-only
   STATUS      current
   DESCRIPTION
       " The Bridge Priority of this Bridge instance. Value is shown in decimal.
         range : 0 - 61440 "
   ::= { xgs360026fMRSTPInstanceStatusEntry 6 }

xgs360026fMRSTPInstanceStatusRootID OBJECT-TYPE
   SYNTAX       MacAddress
   MAX-ACCESS   read-only
   STATUS       current
   DESCRIPTION
       " The Bridge ID of the currently elected root bridge. "
   ::= { xgs360026fMRSTPInstanceStatusEntry 7 }

xgs360026fMRSTPInstanceStatusRootPriority OBJECT-TYPE
   SYNTAX      INTEGER(0..61440)
   MAX-ACCESS  read-only
   STATUS      current
   DESCRIPTION
       " The Bridge Priority of the currently elected root bridge. Value is shown in decimal.
         range : 0 - 61440 "
   ::= { xgs360026fMRSTPInstanceStatusEntry 8 }

xgs360026fMRSTPInstanceStatusRootPort OBJECT-TYPE
   SYNTAX      INTEGER
   MAX-ACCESS  read-only
   STATUS      current
   DESCRIPTION
       " The switch port currently assigned the root port role. "
   ::= { xgs360026fMRSTPInstanceStatusEntry 9 }

xgs360026fMRSTPInstanceStatusRootPathCost OBJECT-TYPE
   SYNTAX      INTEGER
   MAX-ACCESS  read-only
   STATUS      current
   DESCRIPTION
       " For the Root Bridge it is zero. For all other Bridges, it is the sum of the Port Path Costs on the least cost path to the Root Bridge. "
   ::= { xgs360026fMRSTPInstanceStatusEntry 10 }

xgs360026fMRSTPInstanceStatusCurrentMaxAge OBJECT-TYPE
   SYNTAX      INTEGER(6..40)
   MAX-ACCESS  read-only
   STATUS      current
   DESCRIPTION
       " The Max Age inherited from the Root Bridge.
         range : 6 - 40 (seconds)"
   ::= { xgs360026fMRSTPInstanceStatusEntry 11 }

xgs360026fMRSTPInstanceStatusCurrentForwardDelay OBJECT-TYPE
   SYNTAX      INTEGER(4..30)
   MAX-ACCESS  read-only
   STATUS      current
   DESCRIPTION
       " The Forward Delay time inherited from the Root Bridge.
         range : 4 - 30 (seconds) "
   ::= { xgs360026fMRSTPInstanceStatusEntry 12 }

xgs360026fMRSTPInstanceStatusHelloTime OBJECT-TYPE
   SYNTAX      INTEGER(1..10)
   MAX-ACCESS  read-only
   STATUS      current
   DESCRIPTION
       " The Hello Time inherited from the Root Bridge.
         range : 1 - 10 (seconds) "
   ::= { xgs360026fMRSTPInstanceStatusEntry 13 }

xgs360026fMRSTPInstanceStatusTopologyChangeCount OBJECT-TYPE
   SYNTAX      INTEGER
   MAX-ACCESS  read-only
   STATUS      current
   DESCRIPTION
       " The Topology Change Count since the MRSTP Bridge Instance is actually enabled. "
   ::= { xgs360026fMRSTPInstanceStatusEntry 14 }

xgs360026fMRSTPInstanceStatusTimeSinceLastTopologyChange OBJECT-TYPE
   SYNTAX      INTEGER
   MAX-ACCESS  read-only
   STATUS      current
   DESCRIPTION
       " The time since last Topology Change occurred. "
   ::= { xgs360026fMRSTPInstanceStatusEntry 15 }

xgs360026fMRSTPPort                                          OBJECT IDENTIFIER ::= { xgs360026fMRSTP 2 }

xgs360026fMRSTPPortConfiguration                                          OBJECT IDENTIFIER ::= { xgs360026fMRSTPPort 1 }

xgs360026fMRSTPPortConfigurationTable OBJECT-TYPE
   SYNTAX      SEQUENCE OF XGS360026FMRSTPPortConfigurationEntry
   MAX-ACCESS  not-accessible
   STATUS      current
   DESCRIPTION
       " current MRSTP port configurations. "
   ::= { xgs360026fMRSTPPortConfiguration 1 }

xgs360026fMRSTPPortConfigurationEntry OBJECT-TYPE
   SYNTAX      XGS360026FMRSTPPortConfigurationEntry
   MAX-ACCESS  not-accessible
   STATUS      current
   DESCRIPTION
       ""
   INDEX    { xgs360026fMRSTPPortConfigurationPort  }
   ::= { xgs360026fMRSTPPortConfigurationTable 1 }

XGS360026FMRSTPPortConfigurationEntry ::= SEQUENCE {
   xgs360026fMRSTPPortConfigurationPort             INTEGER,
   xgs360026fMRSTPPortConfigurationInstance         INTEGER,
   xgs360026fMRSTPPortConfigurationPathCost         INTEGER,
   xgs360026fMRSTPPortConfigurationPriority         INTEGER,
   xgs360026fMRSTPPortConfigurationAdminEdge        INTEGER,
   xgs360026fMRSTPPortConfigurationAdminP2P         INTEGER,
   xgs360026fMRSTPPortConfigurationMigrateCheck     INTEGER
}

xgs360026fMRSTPPortConfigurationPort OBJECT-TYPE
   SYNTAX      INTEGER(1..4095)
   MAX-ACCESS  not-accessible
   STATUS      current
   DESCRIPTION
       " The switch port number of the MRSTP port. "
   ::= { xgs360026fMRSTPPortConfigurationEntry 1 }

xgs360026fMRSTPPortConfigurationInstance OBJECT-TYPE
   SYNTAX      INTEGER(0..61440)
   MAX-ACCESS  read-write
   STATUS      current
   DESCRIPTION
       " MRSTP Bridge Instance. default: 0
         range : 0 - 12, 0: None "
   ::= { xgs360026fMRSTPPortConfigurationEntry 2 }

xgs360026fMRSTPPortConfigurationPathCost OBJECT-TYPE
   SYNTAX      INTEGER(0..200000000)
   MAX-ACCESS  read-write
   STATUS      current
   DESCRIPTION
       " port path cost;when the value is 0,path cost is determined by physical port speed.
         default: 0
         range : 0 - 200000000, 0: Auto"
   ::= { xgs360026fMRSTPPortConfigurationEntry 3 }

xgs360026fMRSTPPortConfigurationPriority OBJECT-TYPE
   SYNTAX      INTEGER(0..240)
   MAX-ACCESS  read-write
   STATUS      current
   DESCRIPTION
       " Port Priority; would be truncated to a multiple of 16.
         default: 128
         range : 0 - 240"
   ::= { xgs360026fMRSTPPortConfigurationEntry 4 }

xgs360026fMRSTPPortConfigurationAdminEdge OBJECT-TYPE
   SYNTAX      INTEGER(0|1)
   MAX-ACCESS  read-write
   STATUS      current
   DESCRIPTION
       " port(s) as edge or non-edge.
         default: 1
         0: non-edge
         1: edge "
   ::= { xgs360026fMRSTPPortConfigurationEntry 5 }

xgs360026fMRSTPPortConfigurationAdminP2P OBJECT-TYPE
   SYNTAX      INTEGER(0..2)
   MAX-ACCESS  read-write
   STATUS      current
   DESCRIPTION
       " administrative point-to-point (p2p) port.
         range : 0 - 2, default: 2
         0: force to be p2p port(s)
         1: force to be non-p2p port(s)
         2: auto-detected according to port duplex "
   ::= { xgs360026fMRSTPPortConfigurationEntry 6 }

xgs360026fMRSTPPortConfigurationMigrateCheck OBJECT-TYPE
   SYNTAX      INTEGER(0|1)
   MAX-ACCESS  read-write
   STATUS      current
   DESCRIPTION
       " default: 0
         0: none
         1: perform migration check on port(s) "
   ::= { xgs360026fMRSTPPortConfigurationEntry 7 }

xgs360026fMRSTPPortStatus                                          OBJECT IDENTIFIER ::= { xgs360026fMRSTPPort 2 }

xgs360026fMRSTPPortStatusTable OBJECT-TYPE
   SYNTAX      SEQUENCE OF XGS360026FMRSTPPortStatusEntry
   MAX-ACCESS  not-accessible
   STATUS      current
   DESCRIPTION
       " show mrstp port information. "
   ::= { xgs360026fMRSTPPortStatus 1 }

xgs360026fMRSTPPortStatusEntry OBJECT-TYPE
   SYNTAX      XGS360026FMRSTPPortStatusEntry
   MAX-ACCESS  not-accessible
   STATUS      current
   DESCRIPTION
       ""
   INDEX    { xgs360026fMRSTPPortStatusPort  }
   ::= { xgs360026fMRSTPPortStatusTable 1 }

XGS360026FMRSTPPortStatusEntry ::= SEQUENCE {
   xgs360026fMRSTPPortStatusPort                INTEGER,
   xgs360026fMRSTPPortStatusInstance            DisplayString,
   xgs360026fMRSTPPortStatusState               DisplayString,
   xgs360026fMRSTPPortStatusRole                DisplayString,
   xgs360026fMRSTPPortStatusPathCost            INTEGER,
   xgs360026fMRSTPPortStatusPathCostConfig      INTEGER,
   xgs360026fMRSTPPortStatusPriority            INTEGER,
   xgs360026fMRSTPPortStatusAdminEdge           DisplayString,
   xgs360026fMRSTPPortStatusAdminP2P            DisplayString
}

xgs360026fMRSTPPortStatusPort OBJECT-TYPE
   SYNTAX      INTEGER(1..4095)
   MAX-ACCESS  not-accessible
   STATUS      current
   DESCRIPTION
       " The switch port number of the MRSTP port. "
   ::= { xgs360026fMRSTPPortStatusEntry 1 }

xgs360026fMRSTPPortStatusInstance OBJECT-TYPE
   SYNTAX      DisplayString
   MAX-ACCESS  read-only
   STATUS      current
   DESCRIPTION
       " MRSTP Bridge Instance. "
   ::= { xgs360026fMRSTPPortStatusEntry 2 }

xgs360026fMRSTPPortStatusState OBJECT-TYPE
   SYNTAX      DisplayString
   MAX-ACCESS  read-only
   STATUS      current
   DESCRIPTION
       " The current RSTP port state. The port state can be one of the following values: DISCARDING LISTENING FORWARDING NON-MRSTP INST-DSBL.
         INST-DSBL indicates that the Bridge Instance the port belongs to is disabled. "
   ::= { xgs360026fMRSTPPortStatusEntry 3 }

xgs360026fMRSTPPortStatusRole OBJECT-TYPE
   SYNTAX      DisplayString
   MAX-ACCESS  read-only
   STATUS      current
   DESCRIPTION
       " The current MRSTP port role. The port role can be one of the following values: disable alternate backup ROOT DSGN none.
         none indicates that the Bridge Instance the port belongs to is disabled or the port is not an MRSTP port.
         DSGN indicates a Designated port role. "
   ::= { xgs360026fMRSTPPortStatusEntry 4 }

xgs360026fMRSTPPortStatusPathCost OBJECT-TYPE
   SYNTAX      INTEGER(0..200000000)
   MAX-ACCESS  read-only
   STATUS      current
   DESCRIPTION
       " path cost. "
   ::= { xgs360026fMRSTPPortStatusEntry 5 }

xgs360026fMRSTPPortStatusPathCostConfig OBJECT-TYPE
   SYNTAX      INTEGER(0..200000000)
   MAX-ACCESS  read-only
   STATUS      current
   DESCRIPTION
       " port path cost config. "
   ::= { xgs360026fMRSTPPortStatusEntry 6 }

xgs360026fMRSTPPortStatusPriority OBJECT-TYPE
   SYNTAX      INTEGER(0..240)
   MAX-ACCESS  read-only
   STATUS      current
   DESCRIPTION
       " port priority. "
   ::= { xgs360026fMRSTPPortStatusEntry 7 }

xgs360026fMRSTPPortStatusAdminEdge OBJECT-TYPE
   SYNTAX      DisplayString
   MAX-ACCESS  read-only
   STATUS      current
   DESCRIPTION
       " port(s) as edge or non-edge. "
   ::= { xgs360026fMRSTPPortStatusEntry 8 }

xgs360026fMRSTPPortStatusAdminP2P OBJECT-TYPE
   SYNTAX      DisplayString
   MAX-ACCESS  read-only
   STATUS      current
   DESCRIPTION
       " administrative point-to-point (p2p) port. "
   ::= { xgs360026fMRSTPPortStatusEntry 9 }

----------------------------------------------------------------------------------------------------------------------------
xgs360026fSecurity                                              OBJECT IDENTIFIER ::= { xgs360026fProductId 3 }

xgs360026fIPSourceGuard                                         OBJECT IDENTIFIER ::= { xgs360026fSecurity 1 }

xgs360026fIPSourceGuardConf                                     OBJECT IDENTIFIER ::= { xgs360026fIPSourceGuard 1 }

xgs360026fIPSourceGuardMode OBJECT-TYPE
   SYNTAX      INTEGER (0|1)
   MAX-ACCESS  read-write
   STATUS      current
   DESCRIPTION
       " default:  0
        0: disable
        1: enable"
   ::= { xgs360026fIPSourceGuardConf 1 }

xgs360026fIPSourceGuardPortConfigTable OBJECT-TYPE
   SYNTAX      SEQUENCE OF XGS360026FIPSourceGuardPortConfigEntry
   MAX-ACCESS  not-accessible
   STATUS      current
   DESCRIPTION
       " "
   ::= { xgs360026fIPSourceGuardConf 2 }

xgs360026fIPSourceGuardPortConfigEntry OBJECT-TYPE
   SYNTAX      XGS360026FIPSourceGuardPortConfigEntry
   MAX-ACCESS  not-accessible
   STATUS      current
   DESCRIPTION
       ""
   INDEX    { xgs360026fIPSourceGuardPortConfigPort  }
   ::= { xgs360026fIPSourceGuardPortConfigTable 1 }

XGS360026FIPSourceGuardPortConfigEntry ::= SEQUENCE {
   xgs360026fIPSourceGuardPortConfigPort               INTEGER,
   xgs360026fIPSourceGuardPortConfigMode               INTEGER,
   xgs360026fIPSourceGuardPortMaxDynamicClients        INTEGER
}

xgs360026fIPSourceGuardPortConfigPort OBJECT-TYPE
   SYNTAX      INTEGER (1..4095)
   MAX-ACCESS  not-accessible
   STATUS      current
   DESCRIPTION
       " "
   ::= { xgs360026fIPSourceGuardPortConfigEntry 1 }

xgs360026fIPSourceGuardPortConfigMode OBJECT-TYPE
   SYNTAX      INTEGER (0|1)
   MAX-ACCESS  read-write
   STATUS      current
   DESCRIPTION
       "default: 0
       0:disable
       1:enable "
   ::= { xgs360026fIPSourceGuardPortConfigEntry 2 }

xgs360026fIPSourceGuardPortMaxDynamicClients OBJECT-TYPE
   SYNTAX      INTEGER (0..2|99)
   MAX-ACCESS  read-write
   STATUS      current
   DESCRIPTION
       "default: 99
       0~2: Max Dynamic clients
       99:Unlimited "
   ::= { xgs360026fIPSourceGuardPortConfigEntry 3 }


xgs360026fIPSourceGuardStatic                                OBJECT IDENTIFIER ::= { xgs360026fIPSourceGuard 2 }

xgs360026fIPSourceGuardStaticCreate OBJECT-TYPE
   SYNTAX       INTEGER(0|1)
   MAX-ACCESS   read-write
   STATUS       current
   DESCRIPTION
       "default: 0
        0 : None  (read only)
        1 : Create a IP Source Guard"
   ::= { xgs360026fIPSourceGuardStatic 1 }

xgs360026fIPSourceGuardStaticTable OBJECT-TYPE
   SYNTAX      SEQUENCE OF XGS360026FIPSourceGuardStaticEntry
   MAX-ACCESS  not-accessible
   STATUS      current
   DESCRIPTION
       " "
   ::= { xgs360026fIPSourceGuardStatic 2 }

xgs360026fIPSourceGuardStaticEntry OBJECT-TYPE
   SYNTAX      XGS360026FIPSourceGuardStaticEntry
   MAX-ACCESS  not-accessible
   STATUS      current
   DESCRIPTION
       ""
   INDEX    { xgs360026fIPSourceGuardStaticIndex  }
   ::= { xgs360026fIPSourceGuardStaticTable 1 }

XGS360026FIPSourceGuardStaticEntry ::= SEQUENCE {
   xgs360026fIPSourceGuardStaticIndex         INTEGER,
   xgs360026fIPSourceGuardStaticPort          INTEGER,
   xgs360026fIPSourceGuardStaticVLANId        INTEGER,
   xgs360026fIPSourceGuardStaticIPAddress     IpAddress,
   xgs360026fIPSourceGuardStaticMACAddress    MacAddress,
   xgs360026fIPSourceGuardStaticRowStatus     INTEGER
}

xgs360026fIPSourceGuardStaticIndex OBJECT-TYPE
   SYNTAX      INTEGER (1..28)
   MAX-ACCESS  not-accessible
   STATUS      current
   DESCRIPTION
       " "
   ::= { xgs360026fIPSourceGuardStaticEntry 1 }

xgs360026fIPSourceGuardStaticPort OBJECT-TYPE
   SYNTAX      INTEGER (1..4095)
   MAX-ACCESS  read-write
   STATUS      current
   DESCRIPTION
       " Port, range: 1 - port number. "
   ::= { xgs360026fIPSourceGuardStaticEntry 2 }

xgs360026fIPSourceGuardStaticVLANId OBJECT-TYPE
   SYNTAX      INTEGER (1..4094)
   MAX-ACCESS  read-write
   STATUS      current
   DESCRIPTION
       " VLAN ID, range: 1 - 4094. "
   ::= { xgs360026fIPSourceGuardStaticEntry 3 }

xgs360026fIPSourceGuardStaticIPAddress OBJECT-TYPE
   SYNTAX      IpAddress
   MAX-ACCESS  read-write
   STATUS      current
   DESCRIPTION
       " IP address allowed for doing IP source guard. "
   ::= { xgs360026fIPSourceGuardStaticEntry 4 }

xgs360026fIPSourceGuardStaticMACAddress OBJECT-TYPE
   SYNTAX      MacAddress
   MAX-ACCESS  read-write
   STATUS      current
   DESCRIPTION
       " Allowed Source MAC address, format 0a 1b 2c 3d 4e 5f "
   ::= { xgs360026fIPSourceGuardStaticEntry 5 }

xgs360026fIPSourceGuardStaticRowStatus OBJECT-TYPE
   SYNTAX      INTEGER (1..5)
   MAX-ACCESS  read-write
   STATUS      current
   DESCRIPTION
       "1: active
        2: notInservice
        3: edit
        4: destroy
        5: undo"
   ::= { xgs360026fIPSourceGuardStaticEntry 6 }

xgs360026fIPSourceGuardDynamicTable OBJECT-TYPE
   SYNTAX      SEQUENCE OF XGS360026FIPSourceGuardDynamicEntry
   MAX-ACCESS  not-accessible
   STATUS      current
   DESCRIPTION
       " "
   ::= { xgs360026fIPSourceGuard 3 }

xgs360026fIPSourceGuardDynamicEntry OBJECT-TYPE
   SYNTAX      XGS360026FIPSourceGuardDynamicEntry
   MAX-ACCESS  not-accessible
   STATUS      current
   DESCRIPTION
       ""
   INDEX    { xgs360026fIPSourceGuardDynamicIndex  }
   ::= { xgs360026fIPSourceGuardDynamicTable 1 }

XGS360026FIPSourceGuardDynamicEntry ::= SEQUENCE {
   xgs360026fIPSourceGuardDynamicIndex		    INTEGER,
   xgs360026fIPSourceGuardDynamicPort		    INTEGER,
   xgs360026fIPSourceGuardDynamicVLANId		    INTEGER,
   xgs360026fIPSourceGuardDynamicIPAddress		IpAddress,
   xgs360026fIPSourceGuardDynamicMACAddress		MacAddress
}

xgs360026fIPSourceGuardDynamicIndex OBJECT-TYPE
   SYNTAX      INTEGER(1..4095)
   MAX-ACCESS  not-accessible
   STATUS      current
   DESCRIPTION
       " "
   ::= { xgs360026fIPSourceGuardDynamicEntry 1 }

xgs360026fIPSourceGuardDynamicPort OBJECT-TYPE
   SYNTAX      INTEGER (1..10)
   MAX-ACCESS  read-only
   STATUS      current
   DESCRIPTION
       " "
   ::= { xgs360026fIPSourceGuardDynamicEntry 2 }

xgs360026fIPSourceGuardDynamicVLANId OBJECT-TYPE
   SYNTAX      INTEGER (1..4094)
   MAX-ACCESS  read-only
   STATUS      current
   DESCRIPTION
       " "
   ::= { xgs360026fIPSourceGuardDynamicEntry 3 }

xgs360026fIPSourceGuardDynamicIPAddress OBJECT-TYPE
   SYNTAX      IpAddress
   MAX-ACCESS  read-only
   STATUS      current
   DESCRIPTION
       " "
   ::= { xgs360026fIPSourceGuardDynamicEntry 4 }

xgs360026fIPSourceGuardDynamicMACAddress OBJECT-TYPE
   SYNTAX      MacAddress
   MAX-ACCESS  read-only
   STATUS      current
   DESCRIPTION
       " "
   ::= { xgs360026fIPSourceGuardDynamicEntry 5 }

xgs360026fARPInspection                                         OBJECT IDENTIFIER ::= { xgs360026fSecurity 2 }

xgs360026fARPInspectionConf                                     OBJECT IDENTIFIER ::= { xgs360026fARPInspection 1 }

xgs360026fARPInspectionConfMode OBJECT-TYPE
   SYNTAX      INTEGER(0|1)
   MAX-ACCESS  read-write
   STATUS      current
   DESCRIPTION
       "default: 0
        0: disable
        1: enable"
   ::= { xgs360026fARPInspectionConf 1 }

xgs360026fARPInspectionConfTable OBJECT-TYPE
   SYNTAX      SEQUENCE OF XGS360026FARPInspectionConfEntry
   MAX-ACCESS  not-accessible
   STATUS      current
   DESCRIPTION
       " "
   ::= { xgs360026fARPInspectionConf 2 }

xgs360026fARPInspectionConfEntry OBJECT-TYPE
   SYNTAX      XGS360026FARPInspectionConfEntry
   MAX-ACCESS  not-accessible
   STATUS      current
   DESCRIPTION
       ""
   INDEX    { xgs360026fARPInspectionConfPortIndex  }
   ::= { xgs360026fARPInspectionConfTable 1 }

XGS360026FARPInspectionConfEntry ::= SEQUENCE {
   xgs360026fARPInspectionConfPortIndex	INTEGER,
   xgs360026fARPInspectionConfPortMode	INTEGER
}

xgs360026fARPInspectionConfPortIndex OBJECT-TYPE
   SYNTAX      INTEGER(1..4095)
   MAX-ACCESS  not-accessible
   STATUS      current
   DESCRIPTION
       " "
   ::= { xgs360026fARPInspectionConfEntry 1 }

xgs360026fARPInspectionConfPortMode OBJECT-TYPE
   SYNTAX      INTEGER (0|1)
   MAX-ACCESS  read-write
   STATUS      current
   DESCRIPTION
       "default: 0
        0: disable
        1: enable"
   ::= { xgs360026fARPInspectionConfEntry 2 }


xgs360026fARPInspectionStatic                                OBJECT IDENTIFIER ::= { xgs360026fARPInspection 2 }

xgs360026fARPInspectionStaticCreate OBJECT-TYPE
   SYNTAX      INTEGER (0|1)
   MAX-ACCESS  read-write
   STATUS      current
   DESCRIPTION
       "default: 0
        0: none
        1: create"
   ::= { xgs360026fARPInspectionStatic 1 }

xgs360026fARPInspectionStaticTable OBJECT-TYPE
   SYNTAX      SEQUENCE OF XGS360026FARPInspectionStaticEntry
   MAX-ACCESS  not-accessible
   STATUS      current
   DESCRIPTION
       " "
   ::= { xgs360026fARPInspectionStatic 2 }

xgs360026fARPInspectionStaticEntry OBJECT-TYPE
   SYNTAX      XGS360026FARPInspectionStaticEntry
   MAX-ACCESS  not-accessible
   STATUS      current
   DESCRIPTION
       ""
   INDEX    { xgs360026fARPInspectionStaticIndex  }
   ::= { xgs360026fARPInspectionStaticTable 1 }

XGS360026FARPInspectionStaticEntry ::= SEQUENCE {
   xgs360026fARPInspectionStaticIndex        INTEGER,
   xgs360026fARPInspectionStaticPort         INTEGER,
   xgs360026fARPInspectionStaticVLANId       INTEGER,
   xgs360026fARPInspectionStaticIPAddress	IpAddress,
   xgs360026fARPInspectionStaticMACAddress	MacAddress,
   xgs360026fARPInspectionStaticRowStatus	INTEGER
}

xgs360026fARPInspectionStaticIndex OBJECT-TYPE
   SYNTAX      INTEGER(1..4095)
   MAX-ACCESS  not-accessible
   STATUS      current
   DESCRIPTION
       ""
   ::= { xgs360026fARPInspectionStaticEntry 1 }

xgs360026fARPInspectionStaticPort OBJECT-TYPE
   SYNTAX      INTEGER(1..4095)
   MAX-ACCESS  read-write
   STATUS      current
   DESCRIPTION
       " Port, range: 1 - port number. "
   ::= { xgs360026fARPInspectionStaticEntry 2 }

xgs360026fARPInspectionStaticVLANId OBJECT-TYPE
   SYNTAX      INTEGER (1..4094)
   MAX-ACCESS  read-write
   STATUS      current
   DESCRIPTION
       " VLAN ID, range: 1 - 4094. "
   ::= { xgs360026fARPInspectionStaticEntry 3 }

xgs360026fARPInspectionStaticIPAddress OBJECT-TYPE
   SYNTAX      IpAddress
   MAX-ACCESS  read-write
   STATUS      current
   DESCRIPTION
       " IP address allowed for doing ARP request. "
   ::= { xgs360026fARPInspectionStaticEntry 4 }

xgs360026fARPInspectionStaticMACAddress OBJECT-TYPE
   SYNTAX      MacAddress
   MAX-ACCESS  read-write
   STATUS      current
   DESCRIPTION
       " Allowed Source MAC address in ARP request packets, format 0a 1b 2c 3d 4e 5f "
   ::= { xgs360026fARPInspectionStaticEntry 5 }

xgs360026fARPInspectionStaticRowStatus OBJECT-TYPE
   SYNTAX      INTEGER(1..5)
   MAX-ACCESS  read-write
   STATUS      current
   DESCRIPTION
       "1: active
        2: notInservice
        3: edit
        4: destroy
        5: undo"
   ::= { xgs360026fARPInspectionStaticEntry 6 }

xgs360026fARPInspectionDynamicTable OBJECT-TYPE
   SYNTAX      SEQUENCE OF XGS360026FARPInspectionDynamicEntry
   MAX-ACCESS  not-accessible
   STATUS      current
   DESCRIPTION
       " "
   ::= { xgs360026fARPInspection 3 }

xgs360026fARPInspectionDynamicEntry OBJECT-TYPE
   SYNTAX      XGS360026FARPInspectionDynamicEntry
   MAX-ACCESS  not-accessible
   STATUS      current
   DESCRIPTION
       ""
   INDEX    { xgs360026fARPInspectionDynamicIndex  }
   ::= { xgs360026fARPInspectionDynamicTable 1 }

XGS360026FARPInspectionDynamicEntry ::= SEQUENCE {
   xgs360026fARPInspectionDynamicIndex		    INTEGER,
   xgs360026fARPInspectionDynamicPort		    INTEGER,
   xgs360026fARPInspectionDynamicVLANId		    INTEGER,
   xgs360026fARPInspectionDynamicIPAddress		IpAddress,
   xgs360026fARPInspectionDynamicMACAddress		MacAddress
}

xgs360026fARPInspectionDynamicIndex OBJECT-TYPE
   SYNTAX      INTEGER(1..4095)
   MAX-ACCESS  not-accessible
   STATUS      current
   DESCRIPTION
       " "
   ::= { xgs360026fARPInspectionDynamicEntry 1 }

xgs360026fARPInspectionDynamicPort OBJECT-TYPE
   SYNTAX      INTEGER(1..4095)
   MAX-ACCESS  read-only
   STATUS      current
   DESCRIPTION
       ""
   ::= { xgs360026fARPInspectionDynamicEntry 2 }

xgs360026fARPInspectionDynamicVLANId OBJECT-TYPE
   SYNTAX      INTEGER (1..4094)
   MAX-ACCESS  read-only
   STATUS      current
   DESCRIPTION
       ""
   ::= { xgs360026fARPInspectionDynamicEntry 3 }

xgs360026fARPInspectionDynamicIPAddress OBJECT-TYPE
   SYNTAX      IpAddress
   MAX-ACCESS  read-only
   STATUS      current
   DESCRIPTION
       ""
   ::= { xgs360026fARPInspectionDynamicEntry 4 }

xgs360026fARPInspectionDynamicMACAddress OBJECT-TYPE
   SYNTAX      MacAddress
   MAX-ACCESS  read-only
   STATUS      current
   DESCRIPTION
       ""
   ::= { xgs360026fARPInspectionDynamicEntry 5 }

xgs360026fDHCPSnooping                                          OBJECT IDENTIFIER ::= { xgs360026fSecurity 3 }

xgs360026fDHCPSnoopingConf                                          OBJECT IDENTIFIER ::= { xgs360026fDHCPSnooping 1 }

xgs360026fDHCPSnoopingMode OBJECT-TYPE
   SYNTAX      INTEGER(0|1)
   MAX-ACCESS  read-write
   STATUS      current
   DESCRIPTION
       "default: 0
       0: disable
       1: enable"
   ::= { xgs360026fDHCPSnoopingConf 1 }

xgs360026fDHCPSnoopingPortModeConfigurationTable OBJECT-TYPE
   SYNTAX      SEQUENCE OF XGS360026FDHCPSnoopingPortModeConfigurationEntry
   MAX-ACCESS  not-accessible
   STATUS      current
   DESCRIPTION
       " "
   ::= { xgs360026fDHCPSnoopingConf 2 }

xgs360026fDHCPSnoopingPortModeConfigurationEntry OBJECT-TYPE
   SYNTAX      XGS360026FDHCPSnoopingPortModeConfigurationEntry
   MAX-ACCESS  not-accessible
   STATUS      current
   DESCRIPTION
       ""
   INDEX    { xgs360026fDHCPSnoopingPortModeConfigurationPort  }
   ::= { xgs360026fDHCPSnoopingPortModeConfigurationTable 1 }

XGS360026FDHCPSnoopingPortModeConfigurationEntry ::= SEQUENCE {
   xgs360026fDHCPSnoopingPortModeConfigurationPort	INTEGER,
   xgs360026fDHCPSnoopingPortModeConfigurationMode	INTEGER
}

xgs360026fDHCPSnoopingPortModeConfigurationPort OBJECT-TYPE
   SYNTAX      INTEGER(1..4095)
   MAX-ACCESS  not-accessible
   STATUS      current
   DESCRIPTION
       " "
   ::= { xgs360026fDHCPSnoopingPortModeConfigurationEntry 1 }

xgs360026fDHCPSnoopingPortModeConfigurationMode OBJECT-TYPE
   SYNTAX      INTEGER (0|1)
   MAX-ACCESS  read-write
   STATUS      current
   DESCRIPTION
       "default: 1
       0: trust port mode
       1: untrust port mode"
   ::= { xgs360026fDHCPSnoopingPortModeConfigurationEntry 2 }

xgs360026fDHCPSnoopingStatisticsTable OBJECT-TYPE
   SYNTAX      SEQUENCE OF XGS360026FDHCPSnoopingStatisticsEntry
   MAX-ACCESS  not-accessible
   STATUS      current
   DESCRIPTION
       " "
   ::= { xgs360026fDHCPSnooping 2 }

xgs360026fDHCPSnoopingStatisticsEntry OBJECT-TYPE
   SYNTAX      XGS360026FDHCPSnoopingStatisticsEntry
   MAX-ACCESS  not-accessible
   STATUS      current
   DESCRIPTION
       ""
   INDEX    { xgs360026fDHCPSnoopingStatisticsPort  }
   ::= { xgs360026fDHCPSnoopingStatisticsTable 1 }

XGS360026FDHCPSnoopingStatisticsEntry ::= SEQUENCE {
   xgs360026fDHCPSnoopingStatisticsPort         INTEGER,
   xgs360026fDHCPSnoopingStatisticsClear        INTEGER,
   xgs360026fDHCPSnoopingRxDiscover             Counter32,
   xgs360026fDHCPSnoopingRxOffer                Counter32,
   xgs360026fDHCPSnoopingRxRequest              Counter32,
   xgs360026fDHCPSnoopingRxDecline              Counter32,
   xgs360026fDHCPSnoopingRxACK                  Counter32,
   xgs360026fDHCPSnoopingRxNAK                  Counter32,
   xgs360026fDHCPSnoopingRxRelease              Counter32,
   xgs360026fDHCPSnoopingRxInform               Counter32,
   xgs360026fDHCPSnoopingRxLeaseQuery           Counter32,
   xgs360026fDHCPSnoopingRxLeaseUnassigned      Counter32,
   xgs360026fDHCPSnoopingRxLeaseUnknown         Counter32,
   xgs360026fDHCPSnoopingRxLeaseActive          Counter32,
   xgs360026fDHCPSnoopingTxDiscover             Counter32,
   xgs360026fDHCPSnoopingTxOffer                Counter32,
   xgs360026fDHCPSnoopingTxRequest              Counter32,
   xgs360026fDHCPSnoopingTxDecline              Counter32,
   xgs360026fDHCPSnoopingTxACK                  Counter32,
   xgs360026fDHCPSnoopingTxNAK                  Counter32,
   xgs360026fDHCPSnoopingTxRelease              Counter32,
   xgs360026fDHCPSnoopingTxInform               Counter32,
   xgs360026fDHCPSnoopingTxLeaseQuery           Counter32,
   xgs360026fDHCPSnoopingTxLeaseUnassigned      Counter32,
   xgs360026fDHCPSnoopingTxLeaseUnknown         Counter32,
   xgs360026fDHCPSnoopingTxLeaseActive          Counter32
}

xgs360026fDHCPSnoopingStatisticsPort OBJECT-TYPE
   SYNTAX      INTEGER(1..4095)
   MAX-ACCESS  not-accessible
   STATUS      current
   DESCRIPTION
       " "
   ::= { xgs360026fDHCPSnoopingStatisticsEntry 1 }

xgs360026fDHCPSnoopingStatisticsClear OBJECT-TYPE
   SYNTAX      INTEGER (0|1)
   MAX-ACCESS  read-write
   STATUS      current
   DESCRIPTION
       "default: 0
       0: none
       1: clear"
   ::= { xgs360026fDHCPSnoopingStatisticsEntry 2 }

xgs360026fDHCPSnoopingRxDiscover OBJECT-TYPE
   SYNTAX      Counter32
   MAX-ACCESS  read-only
   STATUS      current
   DESCRIPTION
       " "
   ::= { xgs360026fDHCPSnoopingStatisticsEntry 3 }

xgs360026fDHCPSnoopingRxOffer OBJECT-TYPE
   SYNTAX      Counter32
   MAX-ACCESS  read-only
   STATUS      current
   DESCRIPTION
       " "
   ::= { xgs360026fDHCPSnoopingStatisticsEntry 4 }

xgs360026fDHCPSnoopingRxRequest OBJECT-TYPE
   SYNTAX      Counter32
   MAX-ACCESS  read-only
   STATUS      current
   DESCRIPTION
       " "
   ::= { xgs360026fDHCPSnoopingStatisticsEntry 5 }

xgs360026fDHCPSnoopingRxDecline OBJECT-TYPE
   SYNTAX      Counter32
   MAX-ACCESS  read-only
   STATUS      current
   DESCRIPTION
       " "
   ::= { xgs360026fDHCPSnoopingStatisticsEntry 6 }

xgs360026fDHCPSnoopingRxACK OBJECT-TYPE
   SYNTAX      Counter32
   MAX-ACCESS  read-only
   STATUS      current
   DESCRIPTION
       " "
   ::= { xgs360026fDHCPSnoopingStatisticsEntry 7 }

xgs360026fDHCPSnoopingRxNAK OBJECT-TYPE
   SYNTAX      Counter32
   MAX-ACCESS  read-only
   STATUS      current
   DESCRIPTION
       " "
   ::= { xgs360026fDHCPSnoopingStatisticsEntry 8 }

xgs360026fDHCPSnoopingRxRelease OBJECT-TYPE
   SYNTAX      Counter32
   MAX-ACCESS  read-only
   STATUS      current
   DESCRIPTION
       " "
   ::= { xgs360026fDHCPSnoopingStatisticsEntry 9 }

xgs360026fDHCPSnoopingRxInform OBJECT-TYPE
   SYNTAX      Counter32
   MAX-ACCESS  read-only
   STATUS      current
   DESCRIPTION
       " "
   ::= { xgs360026fDHCPSnoopingStatisticsEntry 10 }

xgs360026fDHCPSnoopingRxLeaseQuery OBJECT-TYPE
   SYNTAX      Counter32
   MAX-ACCESS  read-only
   STATUS      current
   DESCRIPTION
       " "
   ::= { xgs360026fDHCPSnoopingStatisticsEntry 11 }

xgs360026fDHCPSnoopingRxLeaseUnassigned OBJECT-TYPE
   SYNTAX      Counter32
   MAX-ACCESS  read-only
   STATUS      current
   DESCRIPTION
       " "
   ::= { xgs360026fDHCPSnoopingStatisticsEntry 12 }

xgs360026fDHCPSnoopingRxLeaseUnknown OBJECT-TYPE
   SYNTAX      Counter32
   MAX-ACCESS  read-only
   STATUS      current
   DESCRIPTION
       " "
   ::= { xgs360026fDHCPSnoopingStatisticsEntry 13 }

xgs360026fDHCPSnoopingRxLeaseActive OBJECT-TYPE
   SYNTAX      Counter32
   MAX-ACCESS  read-only
   STATUS      current
   DESCRIPTION
       " "
   ::= { xgs360026fDHCPSnoopingStatisticsEntry 14 }

xgs360026fDHCPSnoopingTxDiscover OBJECT-TYPE
   SYNTAX      Counter32
   MAX-ACCESS  read-only
   STATUS      current
   DESCRIPTION
       " "
   ::= { xgs360026fDHCPSnoopingStatisticsEntry 15 }

xgs360026fDHCPSnoopingTxOffer OBJECT-TYPE
   SYNTAX      Counter32
   MAX-ACCESS  read-only
   STATUS      current
   DESCRIPTION
       " "
   ::= { xgs360026fDHCPSnoopingStatisticsEntry 16 }

xgs360026fDHCPSnoopingTxRequest OBJECT-TYPE
   SYNTAX      Counter32
   MAX-ACCESS  read-only
   STATUS      current
   DESCRIPTION
       " "
   ::= { xgs360026fDHCPSnoopingStatisticsEntry 17 }

xgs360026fDHCPSnoopingTxDecline OBJECT-TYPE
   SYNTAX      Counter32
   MAX-ACCESS  read-only
   STATUS      current
   DESCRIPTION
       " "
   ::= { xgs360026fDHCPSnoopingStatisticsEntry 18 }

xgs360026fDHCPSnoopingTxACK OBJECT-TYPE
   SYNTAX      Counter32
   MAX-ACCESS  read-only
   STATUS      current
   DESCRIPTION
       " "
   ::= { xgs360026fDHCPSnoopingStatisticsEntry 19 }

xgs360026fDHCPSnoopingTxNAK OBJECT-TYPE
   SYNTAX      Counter32
   MAX-ACCESS  read-only
   STATUS      current
   DESCRIPTION
       " "
   ::= { xgs360026fDHCPSnoopingStatisticsEntry 20 }

xgs360026fDHCPSnoopingTxRelease OBJECT-TYPE
   SYNTAX      Counter32
   MAX-ACCESS  read-only
   STATUS      current
   DESCRIPTION
       " "
   ::= { xgs360026fDHCPSnoopingStatisticsEntry 21 }

xgs360026fDHCPSnoopingTxInform OBJECT-TYPE
   SYNTAX      Counter32
   MAX-ACCESS  read-only
   STATUS      current
   DESCRIPTION
       " "
   ::= { xgs360026fDHCPSnoopingStatisticsEntry 22 }

xgs360026fDHCPSnoopingTxLeaseQuery OBJECT-TYPE
   SYNTAX      Counter32
   MAX-ACCESS  read-only
   STATUS      current
   DESCRIPTION
       " "
   ::= { xgs360026fDHCPSnoopingStatisticsEntry 23 }

xgs360026fDHCPSnoopingTxLeaseUnassigned OBJECT-TYPE
   SYNTAX      Counter32
   MAX-ACCESS  read-only
   STATUS      current
   DESCRIPTION
       " "
   ::= { xgs360026fDHCPSnoopingStatisticsEntry 24 }

xgs360026fDHCPSnoopingTxLeaseUnknown OBJECT-TYPE
   SYNTAX      Counter32
   MAX-ACCESS  read-only
   STATUS      current
   DESCRIPTION
       " "
   ::= { xgs360026fDHCPSnoopingStatisticsEntry 25 }

xgs360026fDHCPSnoopingTxLeaseActive OBJECT-TYPE
   SYNTAX      Counter32
   MAX-ACCESS  read-only
   STATUS      current
   DESCRIPTION
       " "
   ::= { xgs360026fDHCPSnoopingStatisticsEntry 26 }


xgs360026fDHCPRelay                                             OBJECT IDENTIFIER ::= { xgs360026fSecurity 4 }

xgs360026fDHCPRelayConfiguration                                         OBJECT IDENTIFIER ::= { xgs360026fDHCPRelay 1 }

xgs360026fDHCPRelayMode OBJECT-TYPE
   SYNTAX      INTEGER(0|1)
   MAX-ACCESS  read-write
   STATUS      current
   DESCRIPTION
       "default: 0
       0: disable
       1: enable
       We need at least one server"
   ::= { xgs360026fDHCPRelayConfiguration 1 }

xgs360026fDHCPRelayServer OBJECT-TYPE
   SYNTAX      IpAddress
   MAX-ACCESS  read-write
   STATUS      current
   DESCRIPTION
       " "
   ::= { xgs360026fDHCPRelayConfiguration 2 }

xgs360026fDHCPRelayInformationMode OBJECT-TYPE
   SYNTAX      INTEGER(0|1)
   MAX-ACCESS  read-write
   STATUS      current
   DESCRIPTION
       "default: 0
       0: disable
       1: enable "
   ::= { xgs360026fDHCPRelayConfiguration 3 }

xgs360026fDHCPRelayInformationPolicy OBJECT-TYPE
   SYNTAX      INTEGER(0..2)
   MAX-ACCESS  read-write
   STATUS      current
   DESCRIPTION
       "default: 0
       0: replace
       1: keep
       2: drop "
   ::= { xgs360026fDHCPRelayConfiguration 4 }

xgs360026fDHCPRelayStatistics                                   OBJECT IDENTIFIER ::= { xgs360026fDHCPRelay 2 }

xgs360026fDHCPRelayServerStatistics                                   OBJECT IDENTIFIER ::= { xgs360026fDHCPRelayStatistics 1 }

xgs360026fServerStatTransmitToServer OBJECT-TYPE
   SYNTAX      Counter32
   MAX-ACCESS  read-only
   STATUS      current
   DESCRIPTION
       " "
   ::= { xgs360026fDHCPRelayServerStatistics 1 }

xgs360026fServerStatTransmitError OBJECT-TYPE
   SYNTAX      Counter32
   MAX-ACCESS  read-only
   STATUS      current
   DESCRIPTION
       " "
   ::= { xgs360026fDHCPRelayServerStatistics 2 }

xgs360026fServerStatReceiveFromServer OBJECT-TYPE
   SYNTAX      Counter32
   MAX-ACCESS  read-only
   STATUS      current
   DESCRIPTION
       " "
   ::= { xgs360026fDHCPRelayServerStatistics 3 }

xgs360026fServerStatReceiveMissingAgentOption OBJECT-TYPE
   SYNTAX      Counter32
   MAX-ACCESS  read-only
   STATUS      current
   DESCRIPTION
       " "
   ::= { xgs360026fDHCPRelayServerStatistics 4 }

xgs360026fServerStatReceiveMissingCircuitID OBJECT-TYPE
   SYNTAX      Counter32
   MAX-ACCESS  read-only
   STATUS      current
   DESCRIPTION
       " "
   ::= { xgs360026fDHCPRelayServerStatistics 5 }

xgs360026fServerStatReceiveMissingRemoteID OBJECT-TYPE
   SYNTAX      Counter32
   MAX-ACCESS  read-only
   STATUS      current
   DESCRIPTION
       " "
   ::= { xgs360026fDHCPRelayServerStatistics 6 }

xgs360026fServerStatReceiveBadCircuitID OBJECT-TYPE
   SYNTAX      Counter32
   MAX-ACCESS  read-only
   STATUS      current
   DESCRIPTION
       " "
   ::= { xgs360026fDHCPRelayServerStatistics 7 }

xgs360026fServerStatReceiveBadRemoteID OBJECT-TYPE
   SYNTAX      Counter32
   MAX-ACCESS  read-only
   STATUS      current
   DESCRIPTION
       " "
   ::= { xgs360026fDHCPRelayServerStatistics 8 }

xgs360026fDHCPRelayClientStatistics                                   OBJECT IDENTIFIER ::= { xgs360026fDHCPRelayStatistics 2 }

xgs360026fClientStatTransmitToClient OBJECT-TYPE
   SYNTAX      Counter32
   MAX-ACCESS  read-only
   STATUS      current
   DESCRIPTION
       " "
   ::= { xgs360026fDHCPRelayClientStatistics 1 }

xgs360026fClientStatTransmitError OBJECT-TYPE
   SYNTAX      Counter32
   MAX-ACCESS  read-only
   STATUS      current
   DESCRIPTION
       " "
   ::= { xgs360026fDHCPRelayClientStatistics 2 }

xgs360026fClientStatReceivefromClient OBJECT-TYPE
   SYNTAX      Counter32
   MAX-ACCESS  read-only
   STATUS      current
   DESCRIPTION
       " "
   ::= { xgs360026fDHCPRelayClientStatistics 3 }

xgs360026fClientStatReceiveAgentOption OBJECT-TYPE
   SYNTAX      Counter32
   MAX-ACCESS  read-only
   STATUS      current
   DESCRIPTION
       " "
   ::= { xgs360026fDHCPRelayClientStatistics 4 }

xgs360026fClientStatReplaceAgentOption OBJECT-TYPE
   SYNTAX      Counter32
   MAX-ACCESS  read-only
   STATUS      current
   DESCRIPTION
       " "
   ::= { xgs360026fDHCPRelayClientStatistics 5 }

xgs360026fClientStatKeepAgentOption OBJECT-TYPE
   SYNTAX      Counter32
   MAX-ACCESS  read-only
   STATUS      current
   DESCRIPTION
       " "
   ::= { xgs360026fDHCPRelayClientStatistics 6 }

xgs360026fClientStatDropAgentOption OBJECT-TYPE
   SYNTAX      Counter32
   MAX-ACCESS  read-only
   STATUS      current
   DESCRIPTION
       " "
   ::= { xgs360026fDHCPRelayClientStatistics 7 }

xgs360026fPortSecurity                                          OBJECT IDENTIFIER ::= { xgs360026fSecurity 5 }

xgs360026fPortSecLimitCtrl                                      OBJECT IDENTIFIER ::= { xgs360026fPortSecurity 1 }

xgs360026fPortSecLimitCtrlSystemConf                                      OBJECT IDENTIFIER ::= { xgs360026fPortSecLimitCtrl 1 }

xgs360026fPortSecurityMode OBJECT-TYPE
   SYNTAX      INTEGER(0|1)
   MAX-ACCESS  read-write
   STATUS      current
   DESCRIPTION
       "default: 0
       0: disable
       1: enable "
   ::= { xgs360026fPortSecLimitCtrlSystemConf 1 }

xgs360026fPortSecurityAging OBJECT-TYPE
   SYNTAX      INTEGER(0|1)
   MAX-ACCESS  read-write
   STATUS      current
   DESCRIPTION
       "default: 0
       0: disable
       1: enable "
   ::= { xgs360026fPortSecLimitCtrlSystemConf 2 }

xgs360026fPortSecurityAgingPeriod OBJECT-TYPE
   SYNTAX      INTEGER(10..10000000)
   MAX-ACCESS  read-write
   STATUS      current
   DESCRIPTION
       "default: 3600, range: 10-10000000 "
   ::= { xgs360026fPortSecLimitCtrlSystemConf 3 }

xgs360026fPortSecLimitCtrlTable OBJECT-TYPE
   SYNTAX      SEQUENCE OF XGS360026FPortSecLimitCtrlEntry
   MAX-ACCESS  not-accessible
   STATUS      current
   DESCRIPTION
       " "
   ::= { xgs360026fPortSecLimitCtrl 2 }

xgs360026fPortSecLimitCtrlEntry OBJECT-TYPE
   SYNTAX      XGS360026FPortSecLimitCtrlEntry
   MAX-ACCESS  not-accessible
   STATUS      current
   DESCRIPTION
       ""
   INDEX    { xgs360026fPortSecLimitCtrlPort  }
   ::= { xgs360026fPortSecLimitCtrlTable 1 }

XGS360026FPortSecLimitCtrlEntry ::= SEQUENCE {
   xgs360026fPortSecLimitCtrlPort        INTEGER,
   xgs360026fPortSecLimitCtrlPortMode	INTEGER,
   xgs360026fPortSecLimitCtrlPortLimit	INTEGER,
   xgs360026fPortSecLimitCtrlPortAction	INTEGER,
   xgs360026fPortSecLimitCtrlPortState	DisplayString,
   xgs360026fPortSecLimitCtrlPortReOpen	INTEGER
}

xgs360026fPortSecLimitCtrlPort OBJECT-TYPE
   SYNTAX      INTEGER (1..4095)
   MAX-ACCESS  not-accessible
   STATUS      current
   DESCRIPTION
       " "
   ::= { xgs360026fPortSecLimitCtrlEntry 1 }

xgs360026fPortSecLimitCtrlPortMode OBJECT-TYPE
   SYNTAX      INTEGER (0|1)
   MAX-ACCESS  read-write
   STATUS      current
   DESCRIPTION
       "default: 0
       0: disable
       1: enable"
   ::= { xgs360026fPortSecLimitCtrlEntry 2 }

xgs360026fPortSecLimitCtrlPortLimit OBJECT-TYPE
   SYNTAX      INTEGER(1..1024)
   MAX-ACCESS  read-write
   STATUS      current
   DESCRIPTION
       "default: 4, range: 1-1024"
   ::= { xgs360026fPortSecLimitCtrlEntry 3 }

xgs360026fPortSecLimitCtrlPortAction OBJECT-TYPE
   SYNTAX      INTEGER(0..3)
   MAX-ACCESS  read-write
   STATUS      current
   DESCRIPTION
       "default: 0
       0: none
       1: trap
       2: shutdown
       3: trap&shutdown"
   ::= { xgs360026fPortSecLimitCtrlEntry 4 }

xgs360026fPortSecLimitCtrlPortState OBJECT-TYPE
   SYNTAX      DisplayString
   MAX-ACCESS  read-only
   STATUS      current
   DESCRIPTION
       ""
   ::= { xgs360026fPortSecLimitCtrlEntry 5 }

xgs360026fPortSecLimitCtrlPortReOpen OBJECT-TYPE
   SYNTAX      INTEGER (0|1)
   MAX-ACCESS  read-write
   STATUS      current
   DESCRIPTION
       "default: 0
       0: none
       1: reopen"
   ::= { xgs360026fPortSecLimitCtrlEntry 6 }

xgs360026fPortSecSwitchStatusTable OBJECT-TYPE
   SYNTAX      SEQUENCE OF XGS360026FPortSecSwitchStatusEntry
   MAX-ACCESS  not-accessible
   STATUS      current
   DESCRIPTION
       " "
   ::= { xgs360026fPortSecurity 2 }

xgs360026fPortSecSwitchStatusEntry OBJECT-TYPE
   SYNTAX      XGS360026FPortSecSwitchStatusEntry
   MAX-ACCESS  not-accessible
   STATUS      current
   DESCRIPTION
       ""
   INDEX    { xgs360026fPortSecSwitchStatusPort  }
   ::= { xgs360026fPortSecSwitchStatusTable 1 }

XGS360026FPortSecSwitchStatusEntry ::= SEQUENCE {
   xgs360026fPortSecSwitchStatusPort		            INTEGER,
   xgs360026fPortSecSwitchStatusUsers        		DisplayString,
   xgs360026fPortSecSwitchStatusState		        DisplayString,
   xgs360026fPortSecSwitchStatusMACCountCurrent		INTEGER,
   xgs360026fPortSecSwitchStatusMACCountLimit		INTEGER
}

xgs360026fPortSecSwitchStatusPort OBJECT-TYPE
   SYNTAX      INTEGER (1..4095)
   MAX-ACCESS  not-accessible
   STATUS      current
   DESCRIPTION
       " "
   ::= { xgs360026fPortSecSwitchStatusEntry 1 }

xgs360026fPortSecSwitchStatusUsers OBJECT-TYPE
   SYNTAX      DisplayString
   MAX-ACCESS  read-only
   STATUS      current
   DESCRIPTION
       " Users Abbr: L = Limit Control, 8 = 802.1X, D = DHCP Snooping, V = Voice VLAN,
         '-' means that the corresponding user module is not enabled. "
   ::= { xgs360026fPortSecSwitchStatusEntry 2 }

xgs360026fPortSecSwitchStatusState OBJECT-TYPE
   SYNTAX      DisplayString
   MAX-ACCESS  read-only
   STATUS      current
   DESCRIPTION
       " Shows the current state of the port : Disabled, Ready, Limit Reached, Shutdown. "
   ::= { xgs360026fPortSecSwitchStatusEntry 3 }

xgs360026fPortSecSwitchStatusMACCountCurrent OBJECT-TYPE
   SYNTAX      INTEGER (1..4095)
   MAX-ACCESS  read-only
   STATUS      current
   DESCRIPTION
       ""
   ::= { xgs360026fPortSecSwitchStatusEntry 4 }

xgs360026fPortSecSwitchStatusMACCountLimit OBJECT-TYPE
   SYNTAX      INTEGER(1..4095)
   MAX-ACCESS  read-only
   STATUS      current
   DESCRIPTION
       ""
   ::= { xgs360026fPortSecSwitchStatusEntry 5 }

xgs360026fPortSecPortStatus                                      OBJECT IDENTIFIER ::= { xgs360026fPortSecurity 3 }

xgs360026fPortSecPortStatusPort OBJECT-TYPE
   SYNTAX       INTEGER (1..4095)
   MAX-ACCESS   read-write
   STATUS       current
   DESCRIPTION
       "default: 0
        0 : None"
   ::= { xgs360026fPortSecPortStatus 1 }

xgs360026fPortSecPortStatusTable OBJECT-TYPE
   SYNTAX      SEQUENCE OF XGS360026FPortSecPortStatusEntry
   MAX-ACCESS  not-accessible
   STATUS      current
   DESCRIPTION
      " "
   ::= { xgs360026fPortSecPortStatus 2 }

xgs360026fPortSecPortStatusEntry OBJECT-TYPE
   SYNTAX      XGS360026FPortSecPortStatusEntry
   MAX-ACCESS  not-accessible
   STATUS      current
   DESCRIPTION
       ""
   INDEX    { xgs360026fPortSecPortStatusIndex  }
   ::= { xgs360026fPortSecPortStatusTable 1 }

XGS360026FPortSecPortStatusEntry ::= SEQUENCE {
   xgs360026fPortSecPortStatusIndex              INTEGER,
   xgs360026fPortSecPortStatusMACAddress         MacAddress,
   xgs360026fPortSecPortStatusVLANId             INTEGER,
   xgs360026fPortSecPortStatusState              DisplayString,
   xgs360026fPortSecPortStatusTimeOfAddition     DisplayString,
   xgs360026fPortSecPortStatusAgeAndHold         DisplayString
}

xgs360026fPortSecPortStatusIndex OBJECT-TYPE
   SYNTAX      INTEGER(1..4095)
   MAX-ACCESS  not-accessible
   STATUS      current
   DESCRIPTION
       " "
   ::= { xgs360026fPortSecPortStatusEntry 1 }

xgs360026fPortSecPortStatusMACAddress OBJECT-TYPE
   SYNTAX      MacAddress
   MAX-ACCESS  read-only
   STATUS      current
   DESCRIPTION
       " "
   ::= { xgs360026fPortSecPortStatusEntry 2 }

xgs360026fPortSecPortStatusVLANId OBJECT-TYPE
   SYNTAX      INTEGER(1..4094)
   MAX-ACCESS  read-only
   STATUS      current
   DESCRIPTION
       " "
   ::= { xgs360026fPortSecPortStatusEntry 3 }

xgs360026fPortSecPortStatusState OBJECT-TYPE
   SYNTAX      DisplayString
   MAX-ACCESS  read-only
   STATUS      current
   DESCRIPTION
       "Blocked / Forwarding "
   ::= { xgs360026fPortSecPortStatusEntry 4 }

xgs360026fPortSecPortStatusTimeOfAddition OBJECT-TYPE
   SYNTAX      DisplayString
   MAX-ACCESS  read-only
   STATUS      current
   DESCRIPTION
       " "
   ::= { xgs360026fPortSecPortStatusEntry 5 }

xgs360026fPortSecPortStatusAgeAndHold OBJECT-TYPE
   SYNTAX      DisplayString
   MAX-ACCESS  read-only
   STATUS      current
   DESCRIPTION
       " "
   ::= { xgs360026fPortSecPortStatusEntry 6 }


xgs360026fAccessManagement                                      OBJECT IDENTIFIER ::= { xgs360026fSecurity 6 }

xgs360026fAccessMgtConf                                         OBJECT IDENTIFIER ::= { xgs360026fAccessManagement 1 }

xgs360026fAccessMgtConfMode OBJECT-TYPE
   SYNTAX      INTEGER(0|1)
   MAX-ACCESS  read-write
   STATUS      current
   DESCRIPTION
       "default: 0
       0: disable
       1: enable "
   ::= { xgs360026fAccessMgtConf 1 }

xgs360026fAccessMgtConfCreate OBJECT-TYPE
   SYNTAX      INTEGER(0|1)
   MAX-ACCESS  read-write
   STATUS      current
   DESCRIPTION
       "default: 0
       0: none
       1: create "
   ::= { xgs360026fAccessMgtConf 2 }

xgs360026fAccessMgtConfTable OBJECT-TYPE
   SYNTAX      SEQUENCE OF XGS360026FAccessMgtConfEntry
   MAX-ACCESS  not-accessible
   STATUS      current
   DESCRIPTION
       " "
   ::= { xgs360026fAccessMgtConf 3 }

xgs360026fAccessMgtConfEntry OBJECT-TYPE
   SYNTAX      XGS360026FAccessMgtConfEntry
   MAX-ACCESS  not-accessible
   STATUS      current
   DESCRIPTION
       ""
   INDEX    { xgs360026fAccessMgtIndex  }
   ::= { xgs360026fAccessMgtConfTable 1 }

XGS360026FAccessMgtConfEntry ::= SEQUENCE {
   xgs360026fAccessMgtIndex             INTEGER,
   xgs360026fAccessMgtAddresstype       INTEGER,
   xgs360026fAccessMgtStartIpAddress    DisplayString,
   xgs360026fAccessMgtEndIpAddress      DisplayString,
   xgs360026fAccessMgtHttpHttps         INTEGER,
   xgs360026fAccessMgtSNMP              INTEGER,
   xgs360026fAccessMgtTelnetSSH         INTEGER,
   xgs360026fAccessMgtRowStatus         INTEGER
}

xgs360026fAccessMgtIndex OBJECT-TYPE
   SYNTAX      INTEGER(1..16)
   MAX-ACCESS  read-write
   STATUS      current
   DESCRIPTION
       "Set Access Management config index
        range : 1-16."
   ::= { xgs360026fAccessMgtConfEntry 1 }

xgs360026fAccessMgtAddresstype OBJECT-TYPE
   SYNTAX      INTEGER(0|1)
   MAX-ACCESS  read-write
   STATUS      current
   DESCRIPTION
       "0: ipv4
       1: ipv6 "
   ::= { xgs360026fAccessMgtConfEntry 2 }

xgs360026fAccessMgtStartIpAddress OBJECT-TYPE
   SYNTAX      DisplayString
   MAX-ACCESS  read-write
   STATUS      current
   DESCRIPTION
       " Start IP address.
         IP address doesn't allowed all zero or all 'ff'H."
   ::= { xgs360026fAccessMgtConfEntry 3 }

xgs360026fAccessMgtEndIpAddress OBJECT-TYPE
   SYNTAX      DisplayString
   MAX-ACCESS  read-write
   STATUS      current
   DESCRIPTION
       " End IP address.
         IP address doesn't allowed all zero or all 'ff'H.
         End ip address is not less than start ip address."
   ::= { xgs360026fAccessMgtConfEntry 4 }

xgs360026fAccessMgtHttpHttps OBJECT-TYPE
   SYNTAX      INTEGER(0|1)
   MAX-ACCESS  read-write
   STATUS      current
   DESCRIPTION
       "default: 0
       0: disable
       1: enable "
   ::= { xgs360026fAccessMgtConfEntry 5 }

xgs360026fAccessMgtSNMP OBJECT-TYPE
   SYNTAX      INTEGER(0|1)
   MAX-ACCESS  read-write
   STATUS      current
   DESCRIPTION
       "default: 0
       0: disable
       1: enable "
   ::= { xgs360026fAccessMgtConfEntry 6 }

xgs360026fAccessMgtTelnetSSH OBJECT-TYPE
   SYNTAX      INTEGER(0|1)
   MAX-ACCESS  read-write
   STATUS      current
   DESCRIPTION
       "default: 0
       0: disable
       1: enable "
   ::= { xgs360026fAccessMgtConfEntry 7 }

xgs360026fAccessMgtRowStatus OBJECT-TYPE
   SYNTAX      INTEGER(1..5)
   MAX-ACCESS  read-write
   STATUS      current
   DESCRIPTION
       "1: active
        2: notInservice
        3: edit
        4: destroy
        5: undo"
   ::= { xgs360026fAccessMgtConfEntry 8 }

xgs360026fAccessMgtStatistics                                   OBJECT IDENTIFIER ::= { xgs360026fAccessManagement 2 }

xgs360026fHttpReceivedPkts OBJECT-TYPE
   SYNTAX      Counter32
   MAX-ACCESS  read-only
   STATUS      current
   DESCRIPTION
       " "
   ::= { xgs360026fAccessMgtStatistics 1 }

xgs360026fHttpAllowedPkts OBJECT-TYPE
   SYNTAX      Counter32
   MAX-ACCESS  read-only
   STATUS      current
   DESCRIPTION
       " "
   ::= { xgs360026fAccessMgtStatistics 2 }

xgs360026fHttpDiscardedPkts OBJECT-TYPE
   SYNTAX      Counter32
   MAX-ACCESS  read-only
   STATUS      current
   DESCRIPTION
       " "
   ::= { xgs360026fAccessMgtStatistics 3 }

xgs360026fHttpsReceivedPkts OBJECT-TYPE
   SYNTAX      Counter32
   MAX-ACCESS  read-only
   STATUS      current
   DESCRIPTION
       " "
   ::= { xgs360026fAccessMgtStatistics 4 }

xgs360026fHttpsAllowedPkts OBJECT-TYPE
   SYNTAX      Counter32
   MAX-ACCESS  read-only
   STATUS      current
   DESCRIPTION
       " "
   ::= { xgs360026fAccessMgtStatistics 5 }

xgs360026fHttpsDiscardedPkts OBJECT-TYPE
   SYNTAX      Counter32
   MAX-ACCESS  read-only
   STATUS      current
   DESCRIPTION
       " "
   ::= { xgs360026fAccessMgtStatistics 6 }

xgs360026fSnmpReceivedPkts OBJECT-TYPE
   SYNTAX      Counter32
   MAX-ACCESS  read-only
   STATUS      current
   DESCRIPTION
       " "
   ::= { xgs360026fAccessMgtStatistics 7 }

xgs360026fSnmpAllowedPkts OBJECT-TYPE
   SYNTAX      Counter32
   MAX-ACCESS  read-only
   STATUS      current
   DESCRIPTION
       " "
   ::= { xgs360026fAccessMgtStatistics 8 }

xgs360026fSnmpDiscardedPkts OBJECT-TYPE
   SYNTAX      Counter32
   MAX-ACCESS  read-only
   STATUS      current
   DESCRIPTION
       " "
   ::= { xgs360026fAccessMgtStatistics 9 }

xgs360026fTelnetReceivedPkts OBJECT-TYPE
   SYNTAX      Counter32
   MAX-ACCESS  read-only
   STATUS      current
   DESCRIPTION
       " "
   ::= { xgs360026fAccessMgtStatistics 10 }

xgs360026fTelnetAllowedPkts OBJECT-TYPE
   SYNTAX      Counter32
   MAX-ACCESS  read-only
   STATUS      current
   DESCRIPTION
       " "
   ::= { xgs360026fAccessMgtStatistics 11 }

xgs360026fTelnetDiscardedPkts OBJECT-TYPE
   SYNTAX      Counter32
   MAX-ACCESS  read-only
   STATUS      current
   DESCRIPTION
       " "
   ::= { xgs360026fAccessMgtStatistics 12 }

xgs360026fSSHReceivedPkts OBJECT-TYPE
   SYNTAX      Counter32
   MAX-ACCESS  read-only
   STATUS      current
   DESCRIPTION
       " "
   ::= { xgs360026fAccessMgtStatistics 13 }

xgs360026fSSHAllowedPkts OBJECT-TYPE
   SYNTAX      Counter32
   MAX-ACCESS  read-only
   STATUS      current
   DESCRIPTION
       " "
   ::= { xgs360026fAccessMgtStatistics 14 }

xgs360026fSSHDiscardedPkts OBJECT-TYPE
   SYNTAX      Counter32
   MAX-ACCESS  read-only
   STATUS      current
   DESCRIPTION
       " "
   ::= { xgs360026fAccessMgtStatistics 15 }

xgs360026fAccessMgtStatisticsClearAll OBJECT-TYPE
   SYNTAX      INTEGER(0|1)
   MAX-ACCESS  read-write
   STATUS      current
   DESCRIPTION
       "0: none
        1: clear"
   ::= { xgs360026fAccessMgtStatistics 16 }

xgs360026fSSH                                                   OBJECT IDENTIFIER ::= { xgs360026fSecurity 7 }

xgs360026fSSHMode OBJECT-TYPE
   SYNTAX      INTEGER(0|1)
   MAX-ACCESS  read-write
   STATUS      current
   DESCRIPTION
       "default: 1
        0: disable
        1: enable"
   ::= { xgs360026fSSH 1 }

xgs360026fHTTPS                                                 OBJECT IDENTIFIER ::= { xgs360026fSecurity 8 }

xgs360026fHTTPSMode OBJECT-TYPE
   SYNTAX      INTEGER(0|1)
   MAX-ACCESS  read-write
   STATUS      current
   DESCRIPTION
       "default: 1
        0: disable
        1: enable"
   ::= { xgs360026fHTTPS 1 }

xgs360026fHTTPSAutoRedirect OBJECT-TYPE
   SYNTAX      INTEGER(0|1)
   MAX-ACCESS  read-write
   STATUS      current
   DESCRIPTION
       "default: 0
        0: disable
        1: enable"
   ::= { xgs360026fHTTPS 2 }

xgs360026fAuthMethod                                            OBJECT IDENTIFIER ::= { xgs360026fSecurity 9 }

xgs360026fConsoleAuthMethod OBJECT-TYPE
   SYNTAX      INTEGER(0..3)
   MAX-ACCESS  read-write
   STATUS      current
   DESCRIPTION
       "default: 1
        0: none
        1: local
        2: RADIUS
        3: TACACS+"
   ::= { xgs360026fAuthMethod 1 }

xgs360026fConsoleFallback OBJECT-TYPE
   SYNTAX      INTEGER(0|1)
   MAX-ACCESS  read-write
   STATUS      current
   DESCRIPTION
       "default: 0
        0:disable
        1:enable"
   ::= { xgs360026fAuthMethod 2 }

xgs360026fTelnetAuthMethod OBJECT-TYPE
   SYNTAX      INTEGER(0..3)
   MAX-ACCESS  read-write
   STATUS      current
   DESCRIPTION
       "default: 1
        0: none
        1: local
        2: RADIUS
        3: TACACS+"
   ::= { xgs360026fAuthMethod 3 }

xgs360026fTelnetFallback OBJECT-TYPE
   SYNTAX      INTEGER(0|1)
   MAX-ACCESS  read-write
   STATUS      current
   DESCRIPTION
       "default: 0
        0:disable
        1:enable"
   ::= { xgs360026fAuthMethod 4 }

xgs360026fSshAuthMethod OBJECT-TYPE
   SYNTAX      INTEGER(0..3)
   MAX-ACCESS  read-write
   STATUS      current
   DESCRIPTION
       "default: 1
        0: none
        1: local
        2: RADIUS
        3: TACACS+"
   ::= { xgs360026fAuthMethod 5 }

xgs360026fSshFallback OBJECT-TYPE
   SYNTAX      INTEGER(0|1)
   MAX-ACCESS  read-write
   STATUS      current
   DESCRIPTION
       "default: 0
        0:disable
        1:enable"
   ::= { xgs360026fAuthMethod 6 }

xgs360026fWebAuthMethod OBJECT-TYPE
   SYNTAX      INTEGER(0..3)
   MAX-ACCESS  read-write
   STATUS      current
   DESCRIPTION
       "default: 1
        0: none
        1: local
        2: RADIUS
        3: TACACS+"
   ::= { xgs360026fAuthMethod 7 }

xgs360026fWebFallback OBJECT-TYPE
   SYNTAX      INTEGER(0|1)
   MAX-ACCESS  read-write
   STATUS      current
   DESCRIPTION
       "default: 0
        0:disable
        1:enable"
   ::= { xgs360026fAuthMethod 8 }

xgs360026fMaintenance                                           OBJECT IDENTIFIER ::= { xgs360026fProductId 4 }

xgs360026fRestartDevice OBJECT-TYPE
   SYNTAX      INTEGER(0|1)
   MAX-ACCESS  read-write
   STATUS      current
   DESCRIPTION
       "default: 0
        0:none
        1:yes"
   ::= { xgs360026fMaintenance 1 }

xgs360026fFirmware                                         OBJECT IDENTIFIER ::= { xgs360026fMaintenance 2 }

xgs360026fFirmwareIpAddress OBJECT-TYPE
   SYNTAX       IpAddress
   MAX-ACCESS   read-write
   STATUS       current
   DESCRIPTION
        "Get/Set the firmware tftp server."
   ::= { xgs360026fFirmware 1 }

xgs360026fFirmwareFileName OBJECT-TYPE
   SYNTAX       DisplayString
   MAX-ACCESS   read-write
   STATUS       current
   DESCRIPTION
        "Get/Set the path and filename for firmware upgrading."
   ::= { xgs360026fFirmware 2 }

xgs360026fDoFirmwareUpgrade OBJECT-TYPE
   SYNTAX       INTEGER(0|1)
   MAX-ACCESS   read-write
   STATUS       current
   DESCRIPTION
        "Do firmware upgrade. Get this OID always return zero.
              1 - do firmware upgrade.
              0 - do nothing."
   ::= { xgs360026fFirmware 3 }

xgs360026fSaveOrRestore                                         OBJECT IDENTIFIER ::= { xgs360026fMaintenance 3 }

xgs360026fFactoryDefaults OBJECT-TYPE
   SYNTAX      INTEGER(0|1)
   MAX-ACCESS  read-write
   STATUS      current
   DESCRIPTION
       "default: 0
        0:none
        1:yes"
   ::= { xgs360026fSaveOrRestore 1 }

xgs360026fSaveStart OBJECT-TYPE
   SYNTAX      INTEGER(0|1)
   MAX-ACCESS  read-write
   STATUS      current
   DESCRIPTION
       "default: 0
        0:none
        1:yes"
   ::= { xgs360026fSaveOrRestore 2 }

xgs360026fSaveUser OBJECT-TYPE
   SYNTAX      INTEGER(0|1)
   MAX-ACCESS  read-write
   STATUS      current
   DESCRIPTION
       "default: 0
        0:none
        1:yes"
   ::= { xgs360026fSaveOrRestore 3 }

xgs360026fRestoreUser OBJECT-TYPE
   SYNTAX      INTEGER(0|1)
   MAX-ACCESS  read-write
   STATUS      current
   DESCRIPTION
       "default: 0
        0:none
        1:yes"
   ::= { xgs360026fSaveOrRestore 4 }


xgs360026fExportOrImport                                        OBJECT IDENTIFIER ::= { xgs360026fMaintenance 4 }

xgs360026fExportIpAddress OBJECT-TYPE
   SYNTAX       IpAddress
   MAX-ACCESS   read-write
   STATUS       current
   DESCRIPTION
        "Get/Set the export tftp server."
   ::= { xgs360026fExportOrImport 1 }

xgs360026fExportConfigName OBJECT-TYPE
   SYNTAX       DisplayString
   MAX-ACCESS   read-write
   STATUS       current
   DESCRIPTION
       "Get/Set the export file path and name."
   ::= { xgs360026fExportOrImport 2 }

xgs360026fDoExportConfig OBJECT-TYPE
   SYNTAX       INTEGER(1)
   MAX-ACCESS   read-write
   STATUS       current
   DESCRIPTION
        "Do export-config.
         Get this OID always return zero.
         1 - export."
   ::= { xgs360026fExportOrImport 3 }

xgs360026fImportIpAddress OBJECT-TYPE
   SYNTAX       IpAddress
   MAX-ACCESS   read-write
   STATUS       current
   DESCRIPTION
        "Get/Set the import tftp server."
   ::= { xgs360026fExportOrImport 4 }

xgs360026fImportConfigName OBJECT-TYPE
   SYNTAX      DisplayString
   MAX-ACCESS  read-write
   STATUS      current
   DESCRIPTION
       "Get/Set the import file path and name."
   ::= { xgs360026fExportOrImport 5 }

xgs360026fDoImportConfig OBJECT-TYPE
   SYNTAX       INTEGER(1)
   MAX-ACCESS   read-write
   STATUS       current
   DESCRIPTION
        "Do export-config.
         Get this OID always return zero.
         1 - import."
   ::= { xgs360026fExportOrImport 6 }

xgs360026fDiagnostics                                           OBJECT IDENTIFIER ::= { xgs360026fMaintenance 5 }

xgs360026fPingIpAddress OBJECT-TYPE
   SYNTAX      IpAddress
   MAX-ACCESS  read-write
   STATUS      current
   DESCRIPTION
       " The destination IP Address. "
   ::= { xgs360026fDiagnostics 1 }

xgs360026fPingSize OBJECT-TYPE
   SYNTAX      INTEGER(60..1400)
   MAX-ACCESS  read-write
   STATUS      current
   DESCRIPTION
       " Size of ICMP echo packet.
         range : 60-1400, default : 64. "
   ::= { xgs360026fDiagnostics 2 }

xgs360026fDoPingConfig OBJECT-TYPE
   SYNTAX      INTEGER(1)
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { xgs360026fDiagnostics 3 }

xgs360026fPingResult OBJECT-TYPE
   SYNTAX      DisplayString
   MAX-ACCESS  read-only
   STATUS      current
   DESCRIPTION
       " Show ping result. "
   ::= { xgs360026fDiagnostics 4 }

xgs360026fPing6IpAddress OBJECT-TYPE
   SYNTAX      DisplayString
   MAX-ACCESS  read-write
   STATUS      current
   DESCRIPTION
       " The destination IPv6 Address. "
   ::= { xgs360026fDiagnostics 5 }

xgs360026fPing6Size OBJECT-TYPE
   SYNTAX      INTEGER(60..1400)
   MAX-ACCESS  read-write
   STATUS      current
   DESCRIPTION
       " Size of ICMP echo packet.
         range : 60-1400. "
   ::= { xgs360026fDiagnostics 6 }

xgs360026fDoPing6Config OBJECT-TYPE
   SYNTAX      INTEGER(1)
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { xgs360026fDiagnostics 7 }

xgs360026fPing6Result OBJECT-TYPE
   SYNTAX      DisplayString
   MAX-ACCESS  read-only
   STATUS      current
   DESCRIPTION
       " Show ping result. "
   ::= { xgs360026fDiagnostics 8 }


xgs360026fVeriPHY                                           OBJECT IDENTIFIER ::= { xgs360026fDiagnostics 9 }

xgs360026fVeriPHYTest OBJECT-TYPE
   SYNTAX      INTEGER (1..4095)
   MAX-ACCESS  read-write
   STATUS      current
   DESCRIPTION
       "Run VeriPHY Cable Diagnostics.
        port, range : 0 - port number.
        0 : ALL "
   ::= { xgs360026fVeriPHY 1 }

xgs360026fVeriPHYTable OBJECT-TYPE
   SYNTAX      SEQUENCE OF XGS360026FVeriPHYEntry
   MAX-ACCESS  not-accessible
   STATUS      current
   DESCRIPTION
       " "
   ::= { xgs360026fVeriPHY 2 }

xgs360026fVeriPHYEntry OBJECT-TYPE
   SYNTAX      XGS360026FVeriPHYEntry
   MAX-ACCESS  not-accessible
   STATUS      current
   DESCRIPTION
       ""
   INDEX    { xgs360026fVeriPHYPort  }
   ::= { xgs360026fVeriPHYTable 1 }

XGS360026FVeriPHYEntry ::= SEQUENCE {
   xgs360026fVeriPHYPort		    INTEGER,
   xgs360026fVeriPHYPairA		DisplayString,
   xgs360026fVeriPHYLengthA		DisplayString,
   xgs360026fVeriPHYPairB		DisplayString,
   xgs360026fVeriPHYLengthB		DisplayString,
   xgs360026fVeriPHYPairC		DisplayString,
   xgs360026fVeriPHYLengthC		DisplayString,
   xgs360026fVeriPHYPairD		DisplayString,
   xgs360026fVeriPHYLengthD		DisplayString
}

xgs360026fVeriPHYPort OBJECT-TYPE
   SYNTAX      INTEGER (1..4095)
   MAX-ACCESS  not-accessible
   STATUS      current
   DESCRIPTION
       " The length (in meters) of the cable pair. "
   ::= { xgs360026fVeriPHYEntry 1 }

xgs360026fVeriPHYPairA OBJECT-TYPE
   SYNTAX      DisplayString
   MAX-ACCESS  read-only
   STATUS      current
   DESCRIPTION
       " The status of the cable pair. "
   ::= { xgs360026fVeriPHYEntry 2 }

xgs360026fVeriPHYLengthA OBJECT-TYPE
   SYNTAX      DisplayString
   MAX-ACCESS  read-only
   STATUS      current
   DESCRIPTION
       " The length (in meters) of the cable pair. "
   ::= { xgs360026fVeriPHYEntry 3 }

xgs360026fVeriPHYPairB OBJECT-TYPE
   SYNTAX      DisplayString
   MAX-ACCESS  read-only
   STATUS      current
   DESCRIPTION
       " The status of the cable pair. "
   ::= { xgs360026fVeriPHYEntry 4 }

xgs360026fVeriPHYLengthB OBJECT-TYPE
   SYNTAX      DisplayString
   MAX-ACCESS  read-only
   STATUS      current
   DESCRIPTION
       " The length (in meters) of the cable pair. "
   ::= { xgs360026fVeriPHYEntry 5 }

xgs360026fVeriPHYPairC OBJECT-TYPE
   SYNTAX      DisplayString
   MAX-ACCESS  read-only
   STATUS      current
   DESCRIPTION
       " The status of the cable pair. "
   ::= { xgs360026fVeriPHYEntry 6 }

xgs360026fVeriPHYLengthC OBJECT-TYPE
   SYNTAX      DisplayString
   MAX-ACCESS  read-only
   STATUS      current
   DESCRIPTION
       " The length (in meters) of the cable pair. "
   ::= { xgs360026fVeriPHYEntry 7 }

xgs360026fVeriPHYPairD OBJECT-TYPE
   SYNTAX      DisplayString
   MAX-ACCESS  read-only
   STATUS      current
   DESCRIPTION
       " The status of the cable pair. "
   ::= { xgs360026fVeriPHYEntry 8 }

xgs360026fVeriPHYLengthD OBJECT-TYPE
   SYNTAX      DisplayString
   MAX-ACCESS  read-only
   STATUS      current
   DESCRIPTION
       " The length (in meters) of the cable pair. "
   ::= { xgs360026fVeriPHYEntry 9 }


------------------------------------------------------------------------------------------------------------------
xgs360026fTrap                                                  OBJECT IDENTIFIER ::= { xgs360026fProductId 5 }

xgs360026fTrapEvent                                             OBJECT IDENTIFIER ::= { xgs360026fTrap 1 }

xgs360026fEmergency NOTIFICATION-TYPE
  OBJECTS   { xgs360026fInformation }
  STATUS        current
    DESCRIPTION
        "The severity level is Emergency. The system is unusable."
    ::= { xgs360026fTrapEvent 1 }

xgs360026fAlert NOTIFICATION-TYPE
  OBJECTS   { xgs360026fInformation }
  STATUS        current
    DESCRIPTION
        "The severity level is Alert. The action must be taken immediately."
    ::= { xgs360026fTrapEvent 2 }

xgs360026fCritical NOTIFICATION-TYPE
  OBJECTS   { xgs360026fInformation }
  STATUS        current
    DESCRIPTION
        "The severity level is Critical. Critical conditions."
    ::= { xgs360026fTrapEvent 3 }

xgs360026fError NOTIFICATION-TYPE
  OBJECTS   { xgs360026fInformation }
  STATUS        current
    DESCRIPTION
        "The severity level is Error. Error conditions."
    ::= { xgs360026fTrapEvent 4 }

xgs360026fWarning NOTIFICATION-TYPE
  OBJECTS   { xgs360026fInformation }
  STATUS        current
    DESCRIPTION
        "The severity level is Warning. Warning conditions."
    ::= { xgs360026fTrapEvent 5 }

xgs360026fNotice NOTIFICATION-TYPE
  OBJECTS   { xgs360026fInformation }
  STATUS        current
    DESCRIPTION
        "The severity level is Notice. Normal but significant condition."
    ::= { xgs360026fTrapEvent 6 }

xgs360026fInformational NOTIFICATION-TYPE
  OBJECTS   { xgs360026fInformation }
  STATUS        current
    DESCRIPTION
        "The severity level is Informational. Informational messages."
    ::= { xgs360026fTrapEvent 7 }

xgs360026fDebug NOTIFICATION-TYPE
  OBJECTS   { xgs360026fInformation }
  STATUS        current
    DESCRIPTION
        "The severity level is Debug. debug-level messages."
    ::= { xgs360026fTrapEvent 8 }

xgs360026fTrapVariable                                          OBJECT IDENTIFIER ::= { xgs360026fTrap 2 }

xgs360026fInformation OBJECT-TYPE
    SYNTAX      DisplayString
    MAX-ACCESS  read-only
    STATUS      current
    DESCRIPTION
        "Trap information."
    ::= { xgs360026fTrapVariable 1 }


END
