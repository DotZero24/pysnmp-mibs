--  =======================================================================
--   Proprietary MIB for Managed  8TX+2G Switch
--  =======================================================================
--  Copyright 2009.  All Rights Reserved.
--  File Name: zyxel-mes2110.mib
--  Version: 1.0
--  Date Created: 03/10/2009

ZYXEL-MES2110-MIB DEFINITIONS ::= BEGIN
IMPORTS
	enterprises, IpAddress
		FROM RFC1155-SMI
	DisplayString
		FROM RFC1213-MIB
	OBJECT-TYPE
		FROM RFC-1212
	TRAP-TYPE
		FROM RFC-1215;

zyxel		      OBJECT IDENTIFIER ::= {enterprises 890}
products	      OBJECT IDENTIFIER ::= { zyxel 1 }
accessSwitch      OBJECT IDENTIFIER ::= { products 5 }
esSeries	      OBJECT IDENTIFIER ::= { accessSwitch 8 }

--  =================================================================
--  MODULE IDENTITY & REVISION HISTORY
--  =================================================================
mes2110_MIB	OBJECT IDENTIFIER ::= { esSeries 2110 }

--  =================================================================
--  mes2110-MIB SUB-BRANCHES
--  =================================================================
mes2110_SystemInfo	OBJECT IDENTIFIER 	::= { mes2110_MIB 1}
mes2110_Mgt		    OBJECT IDENTIFIER 	::= { mes2110_MIB 2}
mes2110_Port		OBJECT IDENTIFIER 	::= { mes2110_MIB 3}
mes2110_Traps		OBJECT IDENTIFIER 	::= { mes2110_MIB 4}

--  =================================================================
--  mes2110_SystemInfo Group
--
--  mes2110_SystemInfo	OBJECT IDENTIFIER ::= ( mes2110_MIB 1}
--  =================================================================
mes2110_SystemContact	OBJECT-TYPE
	SYNTAX	DisplayString (SIZE (1..255))
	ACCESS	read-write
	STATUS	mandatory
	DESCRIPTION
		"The contact person of this system."
	::= { mes2110_SystemInfo 1 }

mes2110_SystemName	OBJECT-TYPE
	SYNTAX	DisplayString (SIZE (1..255))
	ACCESS	read-write
	STATUS	mandatory
	DESCRIPTION
		"The name of this system."
	::= { mes2110_SystemInfo 2 }

mes2110_SystemLocation	OBJECT-TYPE
	SYNTAX	DisplayString (SIZE (1..255))
	ACCESS	read-write
	STATUS	mandatory
	DESCRIPTION
		"The location of this system."
	::= { mes2110_SystemInfo 3 }


--  ============================================================================
--  mes2110 Management module group
--	mes2110_Mgt	OBJECT IDENTIFIER :: = { mes2110_MIB 2}
--  ============================================================================
mes2110_MgtSnmpVer	OBJECT-TYPE
	SYNTAX	INTEGER {
		v1	(1),
		v2c	(2)
	}
	ACCESS	read-only
	STATUS	mandatory
	DESCRIPTION
		"This object specifies the SNMP version(s) supported by
		 the module."
	::= { mes2110_Mgt 1 }

mes2110_MgtModPN	OBJECT-TYPE
	SYNTAX	DisplayString (SIZE (1..16))
	ACCESS	read-only
	STATUS	mandatory
	DESCRIPTION
		"This object specifies the managemnt module part
		 number."
	::= { mes2110_Mgt 2 }

mes2110_MgtModSN	OBJECT-TYPE
	SYNTAX	DisplayString (SIZE (1..16))
	ACCESS	read-only
	STATUS	mandatory
	DESCRIPTION
		"This object specifies the managemnt module serial
		 number."
	::= { mes2110_Mgt 3 }

mes2110_MgtModManuDate	OBJECT-TYPE
	SYNTAX	DisplayString (SIZE (1..16))
	ACCESS	read-only
	STATUS	mandatory
	DESCRIPTION
		"This object specifies the management module
		 manufacture date."
	::= { mes2110_Mgt 4 }

mes2110_MgtModRev	OBJECT-TYPE
	SYNTAX	DisplayString (SIZE (1..16))
	ACCESS	read-only
	STATUS	mandatory
	DESCRIPTION
		"This object specifies the managemnt module fireware
		 revision number."
	::= { mes2110_Mgt 5 }

mes2110_MgtModDesc	OBJECT-TYPE
	SYNTAX	DisplayString (SIZE (1..64))
	ACCESS	read-only
	STATUS	mandatory
	DESCRIPTION	"This object describes the management module."
	::= { mes2110_Mgt 6 }

communityStringRO OBJECT-TYPE
	SYNTAX	DisplayString (SIZE (1..32))
	ACCESS 	read-write
	STATUS 	mandatory
	DESCRIPTION
		"This is the community string required to authenticate a read
		 access to all MIB objects except for the read-write objects."
	::= { mes2110_Mgt 7 }

communityStringRW OBJECT-TYPE
	SYNTAX	DisplayString (SIZE (1..32))
	ACCESS 	read-write
	STATUS 	mandatory
	DESCRIPTION
		"This is the community string required to authenticate a read
		 or write access to all MIB objects."
	::= { mes2110_Mgt 8 }

defaultGateway	OBJECT-TYPE
	SYNTAX	IpAddress
	ACCESS 	read-write
	STATUS 	mandatory
	DESCRIPTION
		"This object specifies the default gateway address."
	::= { mes2110_Mgt 9 }

interfaceIpAddress	OBJECT-TYPE
	SYNTAX	IpAddress
	ACCESS 	read-write
	STATUS 	mandatory
	DESCRIPTION
		"This object identifies the IP address of the MIB-II
		 interface on the management module."
	::= { mes2110_Mgt 10 }

interfaceSubnetMask	OBJECT-TYPE
	SYNTAX	IpAddress
	ACCESS 	read-write
	STATUS 	mandatory
	DESCRIPTION
		"This object specifies the subnet mask associated with
		 the interface address of the module."
	::= { mes2110_Mgt 11 }

mgtStp	OBJECT-TYPE
	SYNTAX	INTEGER {
		disable	(0),
		enable	(1)
	}
	ACCESS	read-write
	STATUS	mandatory
	DESCRIPTION
		"This object specifies the switch STP function."
	::= { mes2110_Mgt 12 }

trapManagerTable	OBJECT-TYPE
	SYNTAX	SEQUENCE OF TrapManagerTableEntry
	ACCESS	not-accessible
	STATUS	mandatory
	DESCRIPTION
		"This object contains the entries of Network Management Systems
		 to which traps will be sent."
	::= { mes2110_Mgt 13 }

trapManagerTableEntry	OBJECT-TYPE
	SYNTAX	TrapManagerTableEntry
	ACCESS	not-accessible
	STATUS	mandatory
	DESCRIPTION
		"This object specifies an entry in the trap manager table."
	INDEX	{ trapManagerIndex }
	::= { trapManagerTable 1 }

TrapManagerTableEntry ::=
        SEQUENCE {
           trapManagerIndex
                   INTEGER,
	   trapManagerIpAddress
                   IpAddress,
	   trapManagerName
                   DisplayString,
	   trapManagerStatus
                   INTEGER
	}

trapManagerIndex    OBJECT-TYPE
      SYNTAX    INTEGER
      ACCESS    read-only
      STATUS    mandatory
      ::= { trapManagerTableEntry 1}

trapManagerIpAddress	OBJECT-TYPE
	SYNTAX	IpAddress
	ACCESS 	read-write
	STATUS 	mandatory
	DESCRIPTION
		"This object specifies the IP address of the destination
		 of a network management system to which traps will be sent."
	::= { trapManagerTableEntry 2 }

trapManagerName	OBJECT-TYPE
	SYNTAX	DisplayString (SIZE (1..32))
	ACCESS 	read-write
	STATUS 	mandatory
	DESCRIPTION
		"This object identifies the name of the destination of a
		 network management system to which traps will be sent."
	::= { trapManagerTableEntry 3 }

trapManagerStatus	OBJECT-TYPE
	SYNTAX  INTEGER {
		enabled  (1),
		disabled (2)
	}
	ACCESS 	read-write
	STATUS 	mandatory
	DESCRIPTION
		"This object specifies a trap manager entry status in the trap
		 manager table. (1) -- Enabled or (2) -- Disabled."
	::= { trapManagerTableEntry 4 }

--  =================================================================
--  	Port group
--  	mes2110_Port	OBJECT IDENTIFIER :: = { mes2110_MIB 3}
--  =================================================================
mes2110_PortTable	OBJECT-TYPE
	SYNTAX	SEQUENCE OF Mes2110_PortEntry
	ACCESS	not-accessible
	STATUS	mandatory
	DESCRIPTION
		"This object lists port entries on the mes2110 module."
	::= { mes2110_Port 1 }

mes2110_PortEntry	OBJECT-TYPE
	SYNTAX	Mes2110_PortEntry
	ACCESS	not-accessible
	STATUS	mandatory
	DESCRIPTION
		"This object specifies a port entry in the port table, mes2110_PortTable.
		 The port entry contains the information about a single port."
	INDEX	{ portIndex }
	::= { mes2110_PortTable 1 }

Mes2110_PortEntry ::= SEQUENCE {
	portIndex		INTEGER,
	portName		DisplayString,
	portAdminStatus		INTEGER,
	portLinkStatus		INTEGER,
	portSpeedMode		INTEGER,
	portDuplexMode		INTEGER,
	portAuto		INTEGER,
	portFfc			INTEGER
}

portIndex	OBJECT-TYPE
	SYNTAX	INTEGER (1..256)
	ACCESS	read-only
	STATUS	mandatory
	DESCRIPTION
		"This object is the port index, which uniquely identifies
		 a port. It ranges from 1 to the total port number."
	::= { mes2110_PortEntry 1 }

portName	OBJECT-TYPE
	SYNTAX	DisplayString (SIZE (1..64))
	ACCESS	read-write
	STATUS	mandatory
	DESCRIPTION
		"This object specifies the user defined descriptive name
		 for the port."
	::= { mes2110_PortEntry 2 }

portAdminStatus	OBJECT-TYPE
	SYNTAX	INTEGER {
		disable	(1),
		enable	(4)
	}
	ACCESS	read-write
	STATUS	mandatory
	DESCRIPTION
		"This object specifies the port admin state. Setting this object
		 to disable(1) disables the port. Setting this object to enable(4)
		 enables the port."
	::= { mes2110_PortEntry 3 }

portLinkStatus	OBJECT-TYPE
	SYNTAX	INTEGER {
		down (1),
		up	 (2)
	}
	ACCESS	read-only
	STATUS	mandatory
	DESCRIPTION
		"This object indicates the link status attached to the port."
	::= { mes2110_PortEntry 4 }

portSpeedMode	OBJECT-TYPE
	SYNTAX	INTEGER {
		speed-10M	(1),
		speed-100M	(2),
		speed-1000M (3)
	}
	ACCESS	read-write
	STATUS	mandatory
	DESCRIPTION
	        "This object specifies the speed of the port, 10M(1) or 100M(2) or 100M(3)."
	::= { mes2110_PortEntry 5 }

portDuplexMode	OBJECT-TYPE
	SYNTAX	INTEGER {
		half	(1),
		full	(2)
	}
	ACCESS	read-write
	STATUS	mandatory
	DESCRIPTION
		"This object specifies the duplex mode of the port, half duplex(1)
		 or full duplex(2)."
	::= { mes2110_PortEntry 6 }

portAuto	OBJECT-TYPE
	SYNTAX	INTEGER {
		disable	(1),
		enable	(2)
	}
	ACCESS	read-write
	STATUS	mandatory
	DESCRIPTION
		"This object specifies the auto negotiation status of the port."
	::= { mes2110_PortEntry 7 }

portFfc	OBJECT-TYPE
	SYNTAX	INTEGER {
		disable	(1),
		enable	(2)
	}
	ACCESS	read-write
	STATUS	mandatory
	DESCRIPTION
		"This object specifies the force flow control status of a port."
	::= { mes2110_PortEntry 8 }

--  ========================================================================
--  	mes2110_Traps Group
--  	proprietary traps ...
--	  mes2110_Traps		OBJECT IDENTIFIER :: = ( mes2110_MIB 4}
--  ========================================================================
almColdStart	TRAP-TYPE
  ENTERPRISE mes2110_Traps
	DESCRIPTION
		"This trap is sent when the system is started from
		power down."
	::= 1

almWarmStart	TRAP-TYPE
	ENTERPRISE	mes2110_Traps
	DESCRIPTION
		"This trap is sent when the system is reset."
	::= 2

almLinkUp	TRAP-TYPE
	ENTERPRISE mes2110_Traps
	DESCRIPTION
		"This trap is sent when the link associated with the
		port indexed 'portIndex' changes its
		'portLinkStatus' from down(2) to up(1)."
	::= 3

almLinkDown	TRAP-TYPE
	ENTERPRISE	mes2110_Traps
	DESCRIPTION
		"This trap is sent when the link associated with the
		port indexed 'portIndex' changes its
		'portLinkStatus' from up(1) to down(2)."
	::= 4

almConfChange	TRAP-TYPE
	ENTERPRISE	mes2110_Traps
	DESCRIPTION
		"This trap is sent when the system configuration has
		been changed."
	::= 5

END
