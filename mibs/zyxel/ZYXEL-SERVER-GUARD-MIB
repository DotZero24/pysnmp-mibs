-- ZyXEL Communications Corporation
-- Private Enterprise MIB definition

-- This file describes the ZyXEL Communications Corporation Enterprise MIB.
-- It contains ZyXEL products OIDs, and common managed objects.

ZYXEL-SERVER-GUARD-MIB DEFINITIONS ::= BEGIN

    IMPORTS
	OBJECT-TYPE
		FROM SNMPv2-SMI			-- RFC2578

	MODULE-IDENTITY
		FROM SNMPv2-SMI

	EnabledStatus
		FROM  P-BRIDGE-MIB

	dot1dBasePort
       	FROM BRIDGE-MIB

	esMgmt
		FROM ZYXEL-ES-SMI;

	zyxelDhcpServerGuard MODULE-IDENTITY
		LAST-UPDATED	"201911180000Z"
		ORGANIZATION "Enterprise Solution ZyXEL"
		CONTACT-INFO
			""
		DESCRIPTION
			"The subtree for DHCP server guard"
		::= { esMgmt 122 }

	zyxelDhcpServerGuardSetup   	OBJECT IDENTIFIER ::= { zyxelDhcpServerGuard 1 }

 -- ******************************************************************
-- *
-- 122. zyxelDhcpServerGuardSetup
-- *
-- ******************************************************************

        zyDhcpServerGuardState OBJECT-TYPE
        SYNTAX  EnabledStatus
        MAX-ACCESS  read-write
        STATUS  current
        DESCRIPTION
        "Enable/Disable DHCP server guard on the switch."
        ::= { zyxelDhcpServerGuardSetup 1 }


-- 		zyxelDhcpServerGuardPortTable

		zyxelDhcpServerGuardPortTable OBJECT-TYPE
		SYNTAX	SEQUENCE OF ZyxelDhcpServerGuardPortEntry
        MAX-ACCESS  not-accessible
        STATUS  current
        DESCRIPTION
        "The table contains DHCP server guard port configuration."
        ::= { zyxelDhcpServerGuardSetup 2 }

		zyxelDhcpServerGuardPortEntry OBJECT-TYPE
        SYNTAX	ZyxelDhcpServerGuardPortEntry
        MAX-ACCESS	not-accessible
        STATUS	current
        DESCRIPTION
		"An entry contains DHCP server guard port configuration."
        INDEX          	{ dot1dBasePort }
        ::= { zyxelDhcpServerGuardPortTable 1 }

		ZyxelDhcpServerGuardPortEntry ::=
		SEQUENCE {
			zyDhcpServerGuardPortState	 INTEGER
		}

        zyDhcpServerGuardPortState OBJECT-TYPE
        SYNTAX  EnabledStatus
        MAX-ACCESS  read-write
        STATUS  current
        DESCRIPTION
        "Enable/Disable this port to be a trusted port (enable) or an un-trusted port(disable)."
        ::= { zyxelDhcpServerGuardPortEntry 1 }

END
