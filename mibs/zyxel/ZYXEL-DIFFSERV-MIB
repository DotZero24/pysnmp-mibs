-- ZyXEL Communications Corporation
-- Private Enterprise MIB definition

-- This file describes the ZyXEL Communications Corporation Enterprise MIB.
-- It contains ZyXEL products OIDs, and common managed objects.

-- $Log: ZYXEL-DIFFSERV-MIB.mib $
-- Revision 1.4  2013/12/06 07:04:10  ccho
-- remove uncessary imports
-- Revision 1.3  2012/09/19 07:32:06  Kevin
-- if it's leaf node, revise the vender name from zyxel to zy
-- Revision 1.2  2012/07/05 06:22:36  Kevin
-- 1. upgrade from SNMP to SNMPv2
-- 2. clean warning
-- Revision 1.1  2012/05/30 07:48:47  Kevin
-- Initial revision

ZYXEL-DIFFSERV-MIB DEFINITIONS ::= BEGIN

    IMPORTS
	OBJECT-TYPE
		FROM SNMPv2-SMI			-- RFC2578

	MODULE-IDENTITY
		FROM SNMPv2-SMI

	EnabledStatus
		FROM  P-BRIDGE-MIB

	dot1dBasePort
		FROM BRIDGE-MIB

	esMgmt
		FROM ZYXEL-ES-SMI;

	zyxelDiffserv MODULE-IDENTITY
		LAST-UPDATED	"201207010000Z"
		ORGANIZATION "Enterprise Solution ZyXEL"
		CONTACT-INFO
			""
		DESCRIPTION
			"The subtree for Differentiated services (Diffserv)"
		::= { esMgmt 22 }

	zyxelDiffservSetup     	OBJECT IDENTIFIER ::= { zyxelDiffserv 1 }

  --  1.zyxelDiffservSetup

        zyDiffservState OBJECT-TYPE
        SYNTAX  EnabledStatus
        MAX-ACCESS  read-write
        STATUS  current
        DESCRIPTION
		"Enable/Disable DiffServ on the switch. DiffServ is a class of service (CoS)
		 model that marks packets so that they receive specific per-hop treatment at
		 DiffServ-compliant network devices along the route based on the application types and traffic flow."
        ::= { zyxelDiffservSetup 1 }

-- 		zyxelDiffservMapTable
        zyxelDiffservMapTable OBJECT-TYPE
        SYNTAX	SEQUENCE OF ZyxelDiffservMapEntry
        MAX-ACCESS  not-accessible
        STATUS  current
        DESCRIPTION
        "The table contains Diffserv map configuration. "
        ::= { zyxelDiffservSetup 2 }

		zyxelDiffservMapEntry OBJECT-TYPE
        SYNTAX	ZyxelDiffservMapEntry
        MAX-ACCESS	not-accessible
        STATUS	current
        DESCRIPTION
		"An entry contains Diffserv map configuration."
        INDEX          	{ zyDiffservMapDscp }
        ::= { zyxelDiffservMapTable 1 }

        ZyxelDiffservMapEntry ::=
           SEQUENCE {
        	zyDiffservMapDscp		INTEGER,
        	zyDiffservMapPriority	INTEGER
           }

        zyDiffservMapDscp OBJECT-TYPE
        SYNTAX  INTEGER
        MAX-ACCESS  not-accessible
        STATUS  current
        DESCRIPTION
		"The DSCP classification identification number."
        ::= { zyxelDiffservMapEntry 1 }

        zyDiffservMapPriority OBJECT-TYPE
        SYNTAX  INTEGER
        MAX-ACCESS  read-write
        STATUS  current
        DESCRIPTION
		"Set the IEEE 802.1p priority mapping."
        ::= { zyxelDiffservMapEntry 2 }

-- 		zyxelDiffservPortTable
        zyxelDiffservPortTable OBJECT-TYPE
        SYNTAX	SEQUENCE OF ZyxelDiffservPortEntry
        MAX-ACCESS  not-accessible
        STATUS  current
        DESCRIPTION
        "The table contains Diffserv port configuration."
        ::= { zyxelDiffservSetup 3 }

		zyxelDiffservPortEntry OBJECT-TYPE
        SYNTAX	ZyxelDiffservPortEntry
        MAX-ACCESS	not-accessible
        STATUS	current
        DESCRIPTION
		"An entry contains Diffserv port configuration."
        INDEX          	{ dot1dBasePort }
        ::= { zyxelDiffservPortTable 1 }

        ZyxelDiffservPortEntry ::=
           SEQUENCE {
        	zyDiffservPortState	EnabledStatus
           }

        zyDiffservPortState OBJECT-TYPE
        SYNTAX  EnabledStatus
        MAX-ACCESS  read-write
        STATUS  current
        DESCRIPTION
        "Enable/Disable DiffServ on the port."
        ::= { zyxelDiffservPortEntry 1 }


END
