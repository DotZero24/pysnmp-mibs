-- ZyXEL Communications Corporation
-- Private Enterprise MIB definition

-- This file describes the ZyXEL Communications Corporation Enterprise MIB.
-- It contains ZyXEL products OIDs, and common managed objects.

-- $Log: ZYXEL-VLAN-MIB.mib $
-- Revision 1.6  2013/12/06 07:09:10  ccho
-- remove uncessary imports
-- Revision 1.5  2013/11/20 06:56:25  ccho
-- renaming identifier name for SMI.V2
-- Revision 1.4  2013/11/06 05:43:02  ccho
-- fix mib style
-- Revision 1.3  2012/09/19 08:21:24  Kevin
-- if it's leaf node, revise the vender name from zyxel to zy
-- Revision 1.2  2012/07/05 06:25:06  Kevin
-- 1. upgrade from SNMP to SNMPv2
-- 2. clean warning
-- Revision 1.1  2012/05/30 07:50:54  Kevin
-- Initial revision

ZYXEL-VLAN-MIB DEFINITIONS ::= BEGIN

    IMPORTS

	OBJECT-TYPE
		FROM SNMPv2-SMI			-- RFC2578

	MODULE-IDENTITY
		FROM SNMPv2-SMI


	EnabledStatus
		FROM  P-BRIDGE-MIB

	esMgmt
		FROM ZYXEL-ES-SMI;

	zyxelVlan MODULE-IDENTITY
		LAST-UPDATED	"201207010000Z"
		ORGANIZATION "Enterprise Solution ZyXEL"
		CONTACT-INFO
			""
		DESCRIPTION
			"The subtree for Virtual LAN (VLAN)"
		::= { esMgmt 86 }

	zyxelVlanSetup  	OBJECT IDENTIFIER ::= { zyxelVlan 1 }

-- *******************************************************************
-- *
-- * zyxelVlanSetup
-- *
-- *******************************************************************

-- zyxelVlanType
		zyVlanType OBJECT-TYPE
        SYNTAX  INTEGER {
         		dot1Q(1),
         		portBased(2)
        }
        MAX-ACCESS  read-write
        STATUS  current
        DESCRIPTION
                      "Set 802.1Q VLAN type or Port Based VLAN type."
        ::= { zyxelVlanSetup 1 }

     zyVlanIngressCheckState OBJECT-TYPE
        SYNTAX  EnabledStatus
        MAX-ACCESS  read-write
        STATUS  current
        DESCRIPTION
                      "Enable/Disable tag VLAN Ingress check on the switch.
					  If enabled, the Switch discards incoming frames on a port for VLANs that do not include this port in its member set."
        ::= { zyxelVlanSetup 2 }

END
