-- ZyXEL Communications Corporation
 -- Private Enterprise MIB definition - Calvin Chai
 -- 04/30/96

 -- This file describes the ZyXEL Communications Corporation Enterprise MIB.
 -- It includes object identifiers and object definitions for the ZyXEL
 -- Enterprise MIB only, and should be used for compilation by a management
 -- tool in order to extend the tool to support the ZyXEL MIB.

 -- edited by Manfred Recla <support@europe.zyxel.com>
 -- 2001/07/11
 -- renamed "ZYXEL-MIB" into "ZyXEL-COE-MIB"

    ZyXEL-COE-MIB DEFINITIONS ::= BEGIN

    IMPORTS
	enterprises, NetworkAddress, IpAddress, Counter
		FROM RFC1155-SMI
	PhysAddress
	    FROM RFC1213-MIB
	OBJECT-TYPE
		FROM RFC-1212
	TRAP-TYPE
	    FROM RFC-1215;

	DisplayString	::=	OCTET STRING

 -- tree structure

	zyxel			OBJECT IDENTIFIER ::= { enterprises 890 }

	products		OBJECT IDENTIFIER ::= { zyxel 1 }

	prestige 		OBJECT IDENTIFIER ::= { products 2 }
	mtu		    	OBJECT IDENTIFIER ::= { products 3 }
	dslam			OBJECT IDENTIFIER ::= { products 4 }
	systemTraps		OBJECT IDENTIFIER ::= { products 999 }

	-- prestige products


	-- MTU products
	aes-100			OBJECT IDENTIFIER ::= { mtu 1 }
	pes-100			OBJECT IDENTIFIER ::= { mtu 2 }
	ves-100			OBJECT IDENTIFIER ::= { mtu 3 }
	shes-100		OBJECT IDENTIFIER ::= { mtu 4 }
	p1600			OBJECT IDENTIFIER ::= { mtu 5 }
	p1400			OBJECT IDENTIFIER ::= { mtu 6 }
	p2100			OBJECT IDENTIFIER ::= { mtu 7 }
	aes-100-1		OBJECT IDENTIFIER ::= { mtu 8 }

	-- DSLAM products
	zysam-1000			OBJECT IDENTIFIER ::= { dslam 1 }
	zysam-1100			OBJECT IDENTIFIER ::= { dslam 2 }
	zysam-1200			OBJECT IDENTIFIER ::= { dslam 3 }
	zysam-2000			OBJECT IDENTIFIER ::= { dslam 4 }

	-- System traps

	problemCause	OBJECT-TYPE
        SYNTAX	DisplayString
        ACCESS  read-only
        STATUS  mandatory
        DESCRIPTION
               		"The variable is the description of sytsem problem."
     	::= { systemTraps 1 }

 	systemTemperature	OBJECT-TYPE
        SYNTAX	DisplayString
        ACCESS  read-only
        STATUS  mandatory
        DESCRIPTION
               		"The variable is the current temperature in Celsius of the system."
     	::= { systemTraps 2 }

	reboot	TRAP-TYPE
	ENTERPRISE	zyxel
        VARIABLES       {
                        problemCause
                        }
	DESCRIPTION	"Send a message to the manager that the system is going to reboot.
	                 The variable is the reason why the system reboots."
	::= 1

	systemShutdown	TRAP-TYPE
	ENTERPRISE	zyxel
        VARIABLES       {
                        problemCause
                        }
	DESCRIPTION	"Send a message to the manager that the system is going to shutdown.
	                 The variable is the reason that causes the system to shutdown."
	::= 2

	overheat	TRAP-TYPE
	ENTERPRISE	zyxel
        VARIABLES       {
                        systemTemperature
                        }
	DESCRIPTION	"Send a message to the manager that the system is overheated.
	                 The variable in the binding list is the current temperature in Celsius
	                 of the system."
	::= 3

	overheatOver	TRAP-TYPE
	ENTERPRISE	zyxel
        VARIABLES       {
                        systemTemperature
                        }
	DESCRIPTION	"Send a message to the manager that the overheated condition is over.
	                 The variable in the binding list is the current temperature in Celsius
	                 of the system."
	::= 4





END
