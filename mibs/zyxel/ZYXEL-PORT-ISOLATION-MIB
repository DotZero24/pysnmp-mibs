-- ZyXEL Communications Corporation
-- Private Enterprise MIB definition

-- This file describes the ZyXEL Communications Corporation Enterprise MIB.
-- It contains ZyXEL products OIDs, and common managed objects.

-- $Log: ZYXEL-PORT-ISOLATION-MIB.mib $
-- Revision 1.5  2013/12/06 07:08:01  ccho
-- remove uncessary imports
-- Revision 1.4  2012/09/19 07:44:08  Kevin
-- if it's leaf node, revise the vender name from zyxel to zy
-- Revision 1.3  2012/08/22 09:47:35  Kevin
-- clean warning for SNMPc
-- Revision 1.2  2012/07/05 06:24:16  Kevin
-- 1. upgrade from SNMP to SNMPv2
-- 2. clean warning
-- Revision 1.1  2012/05/30 07:50:25  Kevin
-- Initial revision

ZYXEL-PORT-ISOLATION-MIB DEFINITIONS ::= BEGIN

    IMPORTS
	OBJECT-TYPE
		FROM SNMPv2-SMI			-- RFC2578

	MODULE-IDENTITY
		FROM SNMPv2-SMI

	EnabledStatus
		FROM  P-BRIDGE-MIB

	dot1dBasePort
       	FROM BRIDGE-MIB

	esMgmt
		FROM ZYXEL-ES-SMI;

	zyxelPortIsolation MODULE-IDENTITY
		LAST-UPDATED	"201207010000Z"
		ORGANIZATION "Enterprise Solution ZyXEL"
		CONTACT-INFO
			""
		DESCRIPTION
			"The subtree for port isolation"
		::= { esMgmt 64 }

	zyxelPortIsolationSetup     OBJECT IDENTIFIER ::= { zyxelPortIsolation 1 }


-- *******************************************************************
-- *
-- * zyxelPortIsolationSetup
-- *
-- *******************************************************************

-- zyxelPortIsolationPortTable
        zyxelPortIsolationPortTable OBJECT-TYPE
        SYNTAX	SEQUENCE OF ZyxelPortIsolationPortEntry
        MAX-ACCESS  not-accessible
        STATUS  current
        DESCRIPTION
			"The table contains port isolation configuration. "
        ::= { zyxelPortIsolationSetup 1 }

		zyxelPortIsolationPortEntry OBJECT-TYPE
        SYNTAX	ZyxelPortIsolationPortEntry
        MAX-ACCESS	not-accessible
        STATUS	current
        DESCRIPTION
			"An entry contains port isolation configuration. "
        INDEX          	{ dot1dBasePort }
        ::= { zyxelPortIsolationPortTable 1 }

        ZyxelPortIsolationPortEntry ::=
           SEQUENCE {
        	zyPortIsolationPortState				EnabledStatus
           }

        zyPortIsolationPortState OBJECT-TYPE
        SYNTAX  EnabledStatus
        MAX-ACCESS  read-write
        STATUS  current
        DESCRIPTION
			"Enable/Disable Port isolation on the port. Enable to allow this port to communicate only with the CPU
			management port and the ports on which the isolation feature is not enabled. "
        ::= { zyxelPortIsolationPortEntry 1 }

        zyPortIsolationSmartIsolationState OBJECT-TYPE
        SYNTAX  EnabledStatus
        MAX-ACCESS  read-write
        STATUS  current
        DESCRIPTION
			"Enable/Disable smart Port isolation on the switch. The designated port(s) then becomes the isolated
			port. Smart isolation allows you to prevent isolated ports on different switch from transmitting traffic
			to each other."
        ::= { zyxelPortIsolationSetup 2 }

END
