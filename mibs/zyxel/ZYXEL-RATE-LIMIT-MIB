-- ZyXEL Communications Corporation
-- Private Enterprise MIB definition

-- This file describes the ZyXEL Communications Corporation Enterprise MIB.
-- It contains ZyXEL products OIDs, and common managed objects.

-- $Log: ZYXEL-RATE-LIMIT-MIB.mib $
-- Revision 1.5  2013/12/06 07:08:11  ccho
-- remove uncessary imports
-- Revision 1.4  2012/09/19 07:45:46  Kevin
-- if it's leaf node, revise the vender name from zyxel to zy
-- Revision 1.3  2012/08/22 09:48:49  Kevin
-- clean warning for SNMPc
-- Revision 1.2  2012/07/05 06:24:31  Kevin
-- 1. upgrade from SNMP to SNMPv2
-- 2. clean warning
-- Revision 1.1  2012/05/30 07:50:30  Kevin
-- Initial revision

ZYXEL-RATE-LIMIT-MIB DEFINITIONS ::= BEGIN

    IMPORTS
	OBJECT-TYPE
		FROM SNMPv2-SMI			-- RFC2578

	MODULE-IDENTITY
		FROM SNMPv2-SMI

	EnabledStatus
		FROM  P-BRIDGE-MIB

	dot1dBasePort
       	FROM BRIDGE-MIB

	esMgmt
		FROM ZYXEL-ES-SMI;

	zyxelRateLimit MODULE-IDENTITY
		LAST-UPDATED	"201207010000Z"
		ORGANIZATION "Enterprise Solution ZyXEL"
		CONTACT-INFO
			""
		DESCRIPTION
			"The subtree for rate limit"
		::= { esMgmt 72 }

	zyxelRateLimitSetup     OBJECT IDENTIFIER ::= { zyxelRateLimit 1 }

-- *******************************************************************
-- *
-- * zyxelRateLimitSetup
-- *
-- *******************************************************************

-- zyxelRateLimitState
        zyRateLimitState OBJECT-TYPE
        SYNTAX  EnabledStatus
        MAX-ACCESS  read-write
        STATUS  current
        DESCRIPTION
			"Enabled/Disabled ingress/egress rate limiting for the switch."
        ::= { zyxelRateLimitSetup 1 }

-- zyxelRateLimitPortTable
        zyxelRateLimitPortTable OBJECT-TYPE
        SYNTAX	SEQUENCE OF ZyxelRateLimitPortEntry
        MAX-ACCESS  not-accessible
        STATUS  current
        DESCRIPTION
			"The table contains rate limit port configuration."
        ::= { zyxelRateLimitSetup 2 }

		zyxelRateLimitPortEntry OBJECT-TYPE
        SYNTAX	ZyxelRateLimitPortEntry
        MAX-ACCESS	not-accessible
        STATUS	current
        DESCRIPTION
			"An entry contains rate limit port configuration. "
        INDEX          	{ dot1dBasePort }
        ::= { zyxelRateLimitPortTable 1 }

        ZyxelRateLimitPortEntry ::=
           SEQUENCE {
        	zyRateLimitPortCommitState 	EnabledStatus,
        	zyRateLimitPortCommitRate	INTEGER,
			zyRateLimitPortPeakState	EnabledStatus,
			zyRateLimitPortPeakRate		INTEGER,
			zyRateLimitPortEgressState	EnabledStatus,
			zyRateLimitPortEgressRate	INTEGER

           }

        zyRateLimitPortCommitState OBJECT-TYPE
        SYNTAX  EnabledStatus
        MAX-ACCESS  read-write
        STATUS  current
        DESCRIPTION
			"Enabled/Disabled ingress commit rate limiting  on the specified port."
        ::= { zyxelRateLimitPortEntry 1 }

        zyRateLimitPortCommitRate OBJECT-TYPE
        SYNTAX  INTEGER
        MAX-ACCESS  read-write
        STATUS  current
        DESCRIPTION
			"Specify the guaranteed bandwidth allowed in kilobits per second (Kbps) for the incoming traffic flow
			on the specified port. The commit rate should be less than the peak rate. The sum of commit rates
			cannot be greater than or equal to the uplink bandwidth."
        ::= { zyxelRateLimitPortEntry 2 }

        zyRateLimitPortPeakState OBJECT-TYPE
        SYNTAX  EnabledStatus
        MAX-ACCESS  read-write
        STATUS  current
        DESCRIPTION
			"Enabled/Disabled ingress peak rate limiting on the specified port."
        ::= { zyxelRateLimitPortEntry 3 }

        zyRateLimitPortPeakRate OBJECT-TYPE
        SYNTAX  INTEGER
        MAX-ACCESS  read-write
        STATUS  current
        DESCRIPTION
			"Specify the maximum bandwidth allowed in kilobits per second (Kbps) for the incoming traffic flow
			on the specified port."
        ::= { zyxelRateLimitPortEntry 4 }

        zyRateLimitPortEgressState OBJECT-TYPE
        SYNTAX  EnabledStatus
        MAX-ACCESS  read-write
        STATUS  current
        DESCRIPTION
			"Enabled/Disabled egress rate limiting  on the specified port."
        ::= { zyxelRateLimitPortEntry 5 }

        zyRateLimitPortEgressRate OBJECT-TYPE
        SYNTAX  INTEGER
        MAX-ACCESS  read-write
        STATUS  current
        DESCRIPTION
			"Specify the maximum bandwidth allowed in kilobits per second (Kbps) for the out-going traffic flow
			on the specified port."
        ::= { zyxelRateLimitPortEntry 6 }

END
