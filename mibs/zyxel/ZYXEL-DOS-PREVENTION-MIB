-- ZyXEL Communications Corporation
-- Private Enterprise MIB definition

-- This file describes the ZyXEL Communications Corporation Enterprise MIB.
-- It contains ZyXEL products OIDs, and common managed objects.


ZYXEL-DOS-PREVENTION-MIB DEFINITIONS ::= BEGIN

    IMPORTS
	OBJECT-TYPE
		FROM SNMPv2-SMI			-- RFC2578

	MODULE-IDENTITY
		FROM SNMPv2-SMI

	EnabledStatus
		FROM  P-BRIDGE-MIB

	dot1dBasePort
       	FROM BRIDGE-MIB

    ifIndex
    	FROM IF-MIB					-- RFC2863

	esMgmt
		FROM ZYXEL-ES-SMI;

	zyxelDoSPrevention MODULE-IDENTITY
		LAST-UPDATED	"201207010000Z"
		ORGANIZATION "Enterprise Solution ZyXEL"
		CONTACT-INFO
			""
		DESCRIPTION
			"The subtree for dos prevention"
		::= { esMgmt 119 }

	zyxelDoSPreventionSetup	     		OBJECT IDENTIFIER ::= { zyxelDoSPrevention 1 }

-- *******************************************************************
-- *
-- * zyxelDoSPreventionSetup
-- *
-- *******************************************************************

-- 	zyxelDoSPreventionState

		zyDoSPreventionState OBJECT-TYPE
        SYNTAX  EnabledStatus
        MAX-ACCESS  read-write
        STATUS  current
        DESCRIPTION
			"Enable/Disable DoS Prevention on the switch."
        ::= { zyxelDoSPreventionSetup 1 }

-- 	zyxelDoSPreventionPortTable

		zyxelDoSPreventionPortTable OBJECT-TYPE
		SYNTAX	SEQUENCE OF ZyxelDoSPreventionPortEntry
        MAX-ACCESS  not-accessible
        STATUS  current
        DESCRIPTION
        	"The table contains DoS Prevention port configuration."
        ::= { zyxelDoSPreventionSetup 2 }

		zyxelDoSPreventionPortEntry OBJECT-TYPE
        SYNTAX	ZyxelDoSPreventionPortEntry
        MAX-ACCESS	not-accessible
        STATUS	current
        DESCRIPTION
           	"An entry contains DoS Prevention port configuration."
        INDEX          	{ dot1dBasePort }
        ::= { zyxelDoSPreventionPortTable 1 }

		ZyxelDoSPreventionPortEntry ::=
		SEQUENCE {
			zyDoSPreventionPortState	EnabledStatus
		}

        zyDoSPreventionPortState OBJECT-TYPE
        SYNTAX  EnabledStatus
        MAX-ACCESS  read-write
        STATUS  current
        DESCRIPTION
        	"Enable/Disable DoS Prevention on the port."
        ::= { zyxelDoSPreventionPortEntry 1 }

END
