-- ZyXEL Communications Corporation
-- Private Enterprise MIB definition

-- This file describes the ZyXEL Communications Corporation Enterprise MIB.
-- It contains ZyXEL products OIDs, and common managed objects.


ZYXEL-ROUTER-MIB DEFINITIONS ::= BEGIN

    IMPORTS
	OBJECT-TYPE
		FROM SNMPv2-SMI			-- RFC2578

	MODULE-IDENTITY
		FROM SNMPv2-SMI

	EnabledStatus
		FROM  P-BRIDGE-MIB

	esMgmt
		FROM ZYXEL-ES-SMI;

	zyxelRouter MODULE-IDENTITY
		LAST-UPDATED	"201612140000Z"
		ORGANIZATION "Enterprise Solution ZyXEL"
		CONTACT-INFO
			""
		DESCRIPTION
			"The subtree for zyxel router"
		::= { esMgmt 113 }

	zyxelRouterNsf	     	OBJECT IDENTIFIER ::= { zyxelRouter 1 }
	zyxelRouterNsfSetup	     OBJECT IDENTIFIER ::= { zyxelRouterNsf 1 }

	zyRouterNsfEnable OBJECT-TYPE
	SYNTAX  EnabledStatus
	MAX-ACCESS  read-write
	STATUS  current
	DESCRIPTION
					"Enable/Disable nonstop forwarding."
	::= { zyxelRouterNsfSetup 1 }

	zyRouterNsfTimer OBJECT-TYPE
	SYNTAX  INTEGER
	MAX-ACCESS  read-write
	STATUS  current
	DESCRIPTION
		"Set nonstop forwarding wait timer."
	::= { zyxelRouterNsfSetup 2 }
END
