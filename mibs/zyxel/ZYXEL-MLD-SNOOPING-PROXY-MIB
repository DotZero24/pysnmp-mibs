-- ZyXEL Communications Corporation
-- Private Enterprise MIB definition

-- This file describes the ZyXEL Communications Corporation Enterprise MIB.
-- It contains ZyXEL products OIDs, and common managed objects.

-- $Log: ZYXEL-MLD-SNOOPING-PROXY-MIB.mib $
-- Revision 1.6  2013/12/06 07:07:21  ccho
-- remove uncessary imports
-- Revision 1.5  2013/11/08 03:39:17  Kevin
-- add clear entries
-- Revision 1.4  2012/10/31 07:55:02  Dana
-- fix zyMldSnoopingProxyUpstreamVlanLastMemberQueryInterval's value range
-- Revision 1.3  2012/09/19 07:41:37  Kevin
-- if it's leaf node, revise the vender name from zyxel to zy
-- Revision 1.2  2012/07/05 06:23:41  Kevin
-- 1. upgrade from SNMP to SNMPv2
-- 2. clean warning
-- Revision 1.1  2012/05/30 07:49:36  Kevin
-- Initial revision

ZYXEL-MLD-SNOOPING-PROXY-MIB DEFINITIONS ::= BEGIN

    IMPORTS
	OBJECT-TYPE
		FROM SNMPv2-SMI			-- RFC2578

	MODULE-IDENTITY
		FROM SNMPv2-SMI

	RowStatus
		FROM SNMPv2-TC			-- RFC2579

	EnabledStatus
		FROM  P-BRIDGE-MIB

	PortList
		FROM  Q-BRIDGE-MIB

	dot1dBasePort
       	FROM BRIDGE-MIB

	InetAddressType, InetAddress
		FROM INET-ADDRESS-MIB		-- RFC2851

	esMgmt
		FROM ZYXEL-ES-SMI;

	zyxelMldSnoopingProxy MODULE-IDENTITY
		LAST-UPDATED	"201207010000Z"
		ORGANIZATION "Enterprise Solution ZyXEL"
		CONTACT-INFO
			""
		DESCRIPTION
			"The subtree for Multicast Listener Discovery (MLD) snooping proxy"
		::= { esMgmt 51 }

	zyxelMldSnoopingProxyFilteringSetup	     	OBJECT IDENTIFIER ::= { zyxelMldSnoopingProxy 1 }
	zyxelMldSnoopingProxyStatistics	     		OBJECT IDENTIFIER ::= { zyxelMldSnoopingProxy 2 }
	zyxelMldSnoopingProxySetup	     			OBJECT IDENTIFIER ::= { zyxelMldSnoopingProxy 3 }
	zyxelMldSnoopingProxyMembershipStatus	    OBJECT IDENTIFIER ::= { zyxelMldSnoopingProxy 4 }


        zyMldSnoopingProxyFilteringMaxNumberOfProfiles	OBJECT-TYPE
        SYNTAX	INTEGER
        MAX-ACCESS  read-only
        STATUS  current
        DESCRIPTION
        "The maximum number of MLD Snooping filter profile entries that can be created."
        ::= { zyxelMldSnoopingProxyFilteringSetup 1 }


--  zyxelMldSnoopingProxyFilteringProfileTable
        zyxelMldSnoopingProxyFilteringProfileTable	OBJECT-TYPE
        SYNTAX	SEQUENCE OF ZyxelMldSnoopingProxyFilteringProfileEntry
        MAX-ACCESS  not-accessible
        STATUS  current
        DESCRIPTION
        "The table contains MLD snooping proxy filtering profile configuration."
        ::= { zyxelMldSnoopingProxyFilteringSetup 2 }

		zyxelMldSnoopingProxyFilteringProfileEntry OBJECT-TYPE
        SYNTAX	ZyxelMldSnoopingProxyFilteringProfileEntry
        MAX-ACCESS	not-accessible
        STATUS	current
        DESCRIPTION
        "An entry contains MLD snooping proxy filtering profile configuration."
        INDEX
        {
        	zyMldSnoopingProxyFilteringProfileName,
        	zyMldSnoopingProxyFilteringProfileStartIpAddressType,
       		zyMldSnoopingProxyFilteringProfileStartIpAddress,
        	zyMldSnoopingProxyFilteringProfileEndIpAddressType,
        	zyMldSnoopingProxyFilteringProfileEndIpAddress
        }
        ::= { zyxelMldSnoopingProxyFilteringProfileTable 1 }

        ZyxelMldSnoopingProxyFilteringProfileEntry ::=
		SEQUENCE
		{
			zyMldSnoopingProxyFilteringProfileName					OCTET STRING,
        	zyMldSnoopingProxyFilteringProfileStartIpAddressType	InetAddressType,
        	zyMldSnoopingProxyFilteringProfileStartIpAddress		InetAddress,
        	zyMldSnoopingProxyFilteringProfileEndIpAddressType		InetAddressType,
        	zyMldSnoopingProxyFilteringProfileEndIpAddress			InetAddress,
        	zyMldSnoopingProxyFilteringProfileRowStatus				RowStatus
        }

		zyMldSnoopingProxyFilteringProfileName OBJECT-TYPE
        SYNTAX  OCTET STRING
        MAX-ACCESS  not-accessible
        STATUS  current
        DESCRIPTION
        "A descriptive name for the profile for identification purposes."
        ::= { zyxelMldSnoopingProxyFilteringProfileEntry 1 }

        zyMldSnoopingProxyFilteringProfileStartIpAddressType OBJECT-TYPE
        SYNTAX  InetAddressType
        MAX-ACCESS  not-accessible
        STATUS  current
        DESCRIPTION
        "The start address type of filtering range for filtering profile."
        ::= { zyxelMldSnoopingProxyFilteringProfileEntry 2 }

        zyMldSnoopingProxyFilteringProfileStartIpAddress OBJECT-TYPE
        SYNTAX  InetAddress
        MAX-ACCESS  not-accessible
        STATUS  current
        DESCRIPTION
        "The start address of filtering range for filtering profile."
        ::= { zyxelMldSnoopingProxyFilteringProfileEntry 3 }

        zyMldSnoopingProxyFilteringProfileEndIpAddressType OBJECT-TYPE
        SYNTAX  InetAddressType
        MAX-ACCESS  not-accessible
        STATUS  current
        DESCRIPTION
        "The end address type of filtering range for filtering profile."
        ::= { zyxelMldSnoopingProxyFilteringProfileEntry 4 }

        zyMldSnoopingProxyFilteringProfileEndIpAddress OBJECT-TYPE
        SYNTAX  InetAddress
        MAX-ACCESS  not-accessible
        STATUS  current
        DESCRIPTION
        "The end address of filtering range for filtering profile."
        ::= { zyxelMldSnoopingProxyFilteringProfileEntry 5 }

        zyMldSnoopingProxyFilteringProfileRowStatus OBJECT-TYPE
        SYNTAX  RowStatus
        MAX-ACCESS  read-create
        STATUS  current
        DESCRIPTION
        "This object allow entry to be create and deleted a MLD Snooping-proxy filter profile entry."
        ::= { zyxelMldSnoopingProxyFilteringProfileEntry 6 }

--	zyxelMldSnoopingProxyFilteringPortTable
    	zyxelMldSnoopingProxyFilteringPortTable	OBJECT-TYPE
        SYNTAX	SEQUENCE OF ZyxelMldSnoopingProxyFilteringPortEntry
        MAX-ACCESS  not-accessible
        STATUS  current
        DESCRIPTION
        "The table contains MLD snooping proxy filtering port configuration."
        ::= { zyxelMldSnoopingProxyFilteringSetup 3 }

 		zyxelMldSnoopingProxyFilteringPortEntry OBJECT-TYPE
        SYNTAX	ZyxelMldSnoopingProxyFilteringPortEntry
        MAX-ACCESS	not-accessible
        STATUS	current
        DESCRIPTION
        "An entry contains MLD snooping proxy filtering port configuration."
        INDEX    {dot1dBasePort}
        ::= { zyxelMldSnoopingProxyFilteringPortTable 1 }

        ZyxelMldSnoopingProxyFilteringPortEntry ::=
		SEQUENCE
		{
			zyMldSnoopingProxyFilteringPortProfile				OCTET STRING,
        	zyMldSnoopingProxyFilteringPortGroupLimitState		EnabledStatus,
        	zyMldSnoopingProxyFilteringPortMaxNumberOfGroups	INTEGER
        }

		zyMldSnoopingProxyFilteringPortProfile OBJECT-TYPE
        SYNTAX  OCTET STRING
        MAX-ACCESS  read-write
        STATUS  current
        DESCRIPTION
        "Type a name of the MLD Snooping-proxy filtering profile to use for this port. "
        ::= { zyxelMldSnoopingProxyFilteringPortEntry 1 }

        zyMldSnoopingProxyFilteringPortGroupLimitState OBJECT-TYPE
        SYNTAX  EnabledStatus
        MAX-ACCESS  read-write
        STATUS  current
        DESCRIPTION
        "Enable/disable this entry to limit the number of multicast groups on this port is allowed to join. "
        ::= { zyxelMldSnoopingProxyFilteringPortEntry 2 }

        zyMldSnoopingProxyFilteringPortMaxNumberOfGroups OBJECT-TYPE
        SYNTAX  INTEGER
        MAX-ACCESS  read-write
        STATUS  current
        DESCRIPTION
        "The maximum number of group number on the port, when group limit is enable."
        ::= { zyxelMldSnoopingProxyFilteringPortEntry 3 }


--	zyxelMldSnoopingProxyStatistics

        zyMldSnoopingProxySysStatisticsV1QueryRx OBJECT-TYPE
        SYNTAX  INTEGER
        MAX-ACCESS  read-only
        STATUS  current
        DESCRIPTION
        "MLDv1 Query Rx statistic for system."
        ::= { zyxelMldSnoopingProxyStatistics 1 }

        zyMldSnoopingProxySysStatisticsV1QueryTx OBJECT-TYPE
        SYNTAX  INTEGER
        MAX-ACCESS  read-only
        STATUS  current
        DESCRIPTION
        "MLDv1 Query Tx statistic for system."
        ::= { zyxelMldSnoopingProxyStatistics 2 }

        zyMldSnoopingProxySysStatisticsV1QueryDrop OBJECT-TYPE
        SYNTAX  INTEGER
        MAX-ACCESS  read-only
        STATUS  current
        DESCRIPTION
        "MLDv1 Query Drop statistic for system."
        ::= { zyxelMldSnoopingProxyStatistics 3 }

        zyMldSnoopingProxySysStatisticsV1ReportRx OBJECT-TYPE
        SYNTAX  INTEGER
        MAX-ACCESS  read-only
        STATUS  current
        DESCRIPTION
        "MLDv1 Report Rx statistic for system."
        ::= { zyxelMldSnoopingProxyStatistics 4 }

        zyMldSnoopingProxySysStatisticsV1ReportTx OBJECT-TYPE
        SYNTAX  INTEGER
        MAX-ACCESS  read-only
        STATUS  current
        DESCRIPTION
        "MLDv1 Report Tx statistic for system."
        ::= { zyxelMldSnoopingProxyStatistics 5 }

        zyMldSnoopingProxySysStatisticsV1ReportDrop OBJECT-TYPE
        SYNTAX  INTEGER
        MAX-ACCESS  read-only
        STATUS  current
        DESCRIPTION
        "MLDv1 Report Drop statistic for system."
        ::= { zyxelMldSnoopingProxyStatistics 6 }

        zyMldSnoopingProxySysStatisticsV1DoneRx OBJECT-TYPE
        SYNTAX  INTEGER
        MAX-ACCESS  read-only
        STATUS  current
        DESCRIPTION
        "MLDv1 Done Rx statistic for system."
        ::= { zyxelMldSnoopingProxyStatistics 7 }

        zyMldSnoopingProxySysStatisticsV1DoneTx OBJECT-TYPE
        SYNTAX  INTEGER
        MAX-ACCESS  read-only
        STATUS  current
        DESCRIPTION
        "MLDv1 Done Tx statistic for system."
        ::= { zyxelMldSnoopingProxyStatistics 8 }

        zyMldSnoopingProxySysStatisticsV1DoneDrop OBJECT-TYPE
        SYNTAX  INTEGER
        MAX-ACCESS  read-only
        STATUS  current
        DESCRIPTION
        "MLDv1 Done Drop statistic for system."
        ::= { zyxelMldSnoopingProxyStatistics 9 }

        zyMldSnoopingProxySysStatisticsV2QueryRx OBJECT-TYPE
        SYNTAX  INTEGER
        MAX-ACCESS  read-only
        STATUS  current
        DESCRIPTION
        "MLDv2 Query Rx statistic for system."
        ::= { zyxelMldSnoopingProxyStatistics 10 }

        zyMldSnoopingProxySysStatisticsV2QueryTx OBJECT-TYPE
        SYNTAX  INTEGER
        MAX-ACCESS  read-only
        STATUS  current
        DESCRIPTION
        "MLDv2 Query Tx statistic for system."
        ::= { zyxelMldSnoopingProxyStatistics 11 }

        zyMldSnoopingProxySysStatisticsV2QueryDrop OBJECT-TYPE
        SYNTAX  INTEGER
        MAX-ACCESS  read-only
        STATUS  current
        DESCRIPTION
        "MLDv2 Query Drop statistic for system."
        ::= { zyxelMldSnoopingProxyStatistics 12 }

        zyMldSnoopingProxySysStatisticsV2ReportRx OBJECT-TYPE
        SYNTAX  INTEGER
        MAX-ACCESS  read-only
        STATUS  current
        DESCRIPTION
        "MLDv2Report Rx statistic for system."
        ::= { zyxelMldSnoopingProxyStatistics 13 }

        zyMldSnoopingProxySysStatisticsV2ReportTx OBJECT-TYPE
        SYNTAX  INTEGER
        MAX-ACCESS  read-only
        STATUS  current
        DESCRIPTION
        "MLDv2 Report Tx statistic for system."
        ::= { zyxelMldSnoopingProxyStatistics 14 }

        zyMldSnoopingProxySysStatisticsV2ReportDrop OBJECT-TYPE
        SYNTAX  INTEGER
        MAX-ACCESS  read-only
        STATUS  current
        DESCRIPTION
        "MLDv2 Report Drop statistic for system."
        ::= { zyxelMldSnoopingProxyStatistics 15 }


--	zyxelMldSnoopingProxyVlanStatisticsTable
       	zyxelMldSnoopingProxyStatisticsVlanTable	OBJECT-TYPE
        SYNTAX	SEQUENCE OF ZyxelMldSnoopingProxyStatisticsVlanEntry
        MAX-ACCESS  not-accessible
        STATUS  current
        DESCRIPTION
        "The table contains MLD snooping proxy statistics VLAN information."
        ::= { zyxelMldSnoopingProxyStatistics 16 }

		zyxelMldSnoopingProxyStatisticsVlanEntry	OBJECT-TYPE
        SYNTAX	ZyxelMldSnoopingProxyStatisticsVlanEntry
        MAX-ACCESS	not-accessible
        STATUS	current
        DESCRIPTION
        "An entry contains MLD snooping proxy statistics VLAN information."
        INDEX          	{ zyMldSnoopingProxyVlanVid }
        ::= { zyxelMldSnoopingProxyStatisticsVlanTable 1 }

        ZyxelMldSnoopingProxyStatisticsVlanEntry ::=
		SEQUENCE
		{
			zyMldSnoopingProxyStatisticsVlanV1QueryRx		INTEGER,
			zyMldSnoopingProxyStatisticsVlanV1QueryTx		INTEGER,
			zyMldSnoopingProxyStatisticsVlanV1QueryDrop		INTEGER,
			zyMldSnoopingProxyStatisticsVlanV1ReportRx		INTEGER,
			zyMldSnoopingProxyStatisticsVlanV1ReportTx		INTEGER,
        	zyMldSnoopingProxyStatisticsVlanV1ReportDrop	INTEGER,
			zyMldSnoopingProxyStatisticsVlanV1DoneRx		INTEGER,
       		zyMldSnoopingProxyStatisticsVlanV1DoneTx		INTEGER,
        	zyMldSnoopingProxyStatisticsVlanV1DoneDrop		INTEGER,
        	zyMldSnoopingProxyStatisticsVlanV2QueryRx		INTEGER,
			zyMldSnoopingProxyStatisticsVlanV2QueryTx		INTEGER,
        	zyMldSnoopingProxyStatisticsVlanV2QueryDrop		INTEGER,
        	zyMldSnoopingProxyStatisticsVlanV2ReportRx		INTEGER,
			zyMldSnoopingProxyStatisticsVlanV2ReportTx		INTEGER,
			zyMldSnoopingProxyStatisticsVlanV2ReportDrop	INTEGER
        }


        zyMldSnoopingProxyStatisticsVlanV1QueryRx OBJECT-TYPE
        SYNTAX  INTEGER
        MAX-ACCESS  read-only
        STATUS  current
        DESCRIPTION	"MLDv1 Query Rx statistic for VLAN"

        ::= { zyxelMldSnoopingProxyStatisticsVlanEntry 1 }

        zyMldSnoopingProxyStatisticsVlanV1QueryTx OBJECT-TYPE
        SYNTAX  INTEGER
        MAX-ACCESS  read-only
        STATUS  current
        DESCRIPTION	"MLDv1 Query Tx statistic for VLAN"

        ::= { zyxelMldSnoopingProxyStatisticsVlanEntry 2 }

        zyMldSnoopingProxyStatisticsVlanV1QueryDrop OBJECT-TYPE
        SYNTAX  INTEGER
        MAX-ACCESS  read-only
        STATUS  current
        DESCRIPTION	"MLDv1 Query Drop statistic for VLAN"

        ::= { zyxelMldSnoopingProxyStatisticsVlanEntry 3 }

        zyMldSnoopingProxyStatisticsVlanV1ReportRx OBJECT-TYPE
        SYNTAX  INTEGER
        MAX-ACCESS  read-only
        STATUS  current
        DESCRIPTION	"MLDv1 Report Rx statistic for VLAN"

        ::= { zyxelMldSnoopingProxyStatisticsVlanEntry 4 }

        zyMldSnoopingProxyStatisticsVlanV1ReportTx OBJECT-TYPE
        SYNTAX  INTEGER
        MAX-ACCESS  read-only
        STATUS  current
        DESCRIPTION	"MLDv1 Report Tx statistic for VLAN"

        ::= { zyxelMldSnoopingProxyStatisticsVlanEntry 5 }

        zyMldSnoopingProxyStatisticsVlanV1ReportDrop OBJECT-TYPE
        SYNTAX  INTEGER
        MAX-ACCESS  read-only
        STATUS  current
        DESCRIPTION	"MLDv1 Report Drop statistic for VLAN"

        ::= { zyxelMldSnoopingProxyStatisticsVlanEntry 6 }

        zyMldSnoopingProxyStatisticsVlanV1DoneRx OBJECT-TYPE
        SYNTAX  INTEGER
        MAX-ACCESS  read-only
        STATUS  current
        DESCRIPTION	"MLDv1 Done Rx statistic for VLAN"

        ::= { zyxelMldSnoopingProxyStatisticsVlanEntry 7 }

        zyMldSnoopingProxyStatisticsVlanV1DoneTx OBJECT-TYPE
        SYNTAX  INTEGER
        MAX-ACCESS  read-only
        STATUS  current
        DESCRIPTION	"MLDv1 Done Tx statistic for VLAN"

        ::= { zyxelMldSnoopingProxyStatisticsVlanEntry 8 }

        zyMldSnoopingProxyStatisticsVlanV1DoneDrop OBJECT-TYPE
        SYNTAX  INTEGER
        MAX-ACCESS  read-only
        STATUS  current
        DESCRIPTION	"MLDv1 Done Drop statistic for VLAN"

        ::= { zyxelMldSnoopingProxyStatisticsVlanEntry 9 }

        zyMldSnoopingProxyStatisticsVlanV2QueryRx OBJECT-TYPE
        SYNTAX  INTEGER
        MAX-ACCESS  read-only
        STATUS  current
        DESCRIPTION	"MLDv2 Query Rx statistic for VALN"

        ::= { zyxelMldSnoopingProxyStatisticsVlanEntry 10 }

        zyMldSnoopingProxyStatisticsVlanV2QueryTx OBJECT-TYPE
        SYNTAX  INTEGER
        MAX-ACCESS  read-only
        STATUS  current
        DESCRIPTION	"MLDv2 Query Tx statistic for VALN"

        ::= { zyxelMldSnoopingProxyStatisticsVlanEntry 11 }

        zyMldSnoopingProxyStatisticsVlanV2QueryDrop OBJECT-TYPE
        SYNTAX  INTEGER
        MAX-ACCESS  read-only
        STATUS  current
        DESCRIPTION	"MLDv2 Query Drop statistic for VLAN"

        ::= { zyxelMldSnoopingProxyStatisticsVlanEntry 12 }

        zyMldSnoopingProxyStatisticsVlanV2ReportRx OBJECT-TYPE
        SYNTAX  INTEGER
        MAX-ACCESS  read-only
        STATUS  current
        DESCRIPTION	"MLDv2Report Rx statistic for VLAN"

        ::= { zyxelMldSnoopingProxyStatisticsVlanEntry 13 }

        zyMldSnoopingProxyStatisticsVlanV2ReportTx OBJECT-TYPE
        SYNTAX  INTEGER
        MAX-ACCESS  read-only
        STATUS  current
        DESCRIPTION	"MLDv2 Report Tx statistic for VLAN"

        ::= { zyxelMldSnoopingProxyStatisticsVlanEntry 14 }

        zyMldSnoopingProxyStatisticsVlanV2ReportDrop OBJECT-TYPE
        SYNTAX  INTEGER
        MAX-ACCESS  read-only
        STATUS  current
        DESCRIPTION	"MLDv2 Report Drop statistic for VLAN"

        ::= { zyxelMldSnoopingProxyStatisticsVlanEntry 15 }

--	 zyxelMldSnoopingProxyPortStatisticsTable
       	zyxelMldSnoopingProxyStatisticsPortTable	OBJECT-TYPE
        SYNTAX	SEQUENCE OF ZyxelMldSnoopingProxyStatisticsPortEntry
        MAX-ACCESS  not-accessible
        STATUS  current
        DESCRIPTION	"The table contains MLD snooping proxy statistics port information."
        ::= { zyxelMldSnoopingProxyStatistics 17 }

		zyxelMldSnoopingProxyStatisticsPortEntry	OBJECT-TYPE
        SYNTAX	ZyxelMldSnoopingProxyStatisticsPortEntry
        MAX-ACCESS	not-accessible
        STATUS	current
        DESCRIPTION    	"An entry contains MLD snooping proxy statistics port information."
        INDEX          	{ dot1dBasePort }
        ::= { zyxelMldSnoopingProxyStatisticsPortTable 1 }

        ZyxelMldSnoopingProxyStatisticsPortEntry ::=
		SEQUENCE
		{
			zyMldSnoopingProxyStatisticsPortV1QueryRx		INTEGER,
			zyMldSnoopingProxyStatisticsPortV1QueryTx		INTEGER,
			zyMldSnoopingProxyStatisticsPortV1QueryDrop		INTEGER,
			zyMldSnoopingProxyStatisticsPortV1ReportRx		INTEGER,
			zyMldSnoopingProxyStatisticsPortV1ReportTx		INTEGER,
        	zyMldSnoopingProxyStatisticsPortV1ReportDrop	INTEGER,
			zyMldSnoopingProxyStatisticsPortV1DoneRx		INTEGER,
       		zyMldSnoopingProxyStatisticsPortV1DoneTx		INTEGER,
        	zyMldSnoopingProxyStatisticsPortV1DoneDrop		INTEGER,
        	zyMldSnoopingProxyStatisticsPortV2QueryRx		INTEGER,
			zyMldSnoopingProxyStatisticsPortV2QueryTx		INTEGER,
        	zyMldSnoopingProxyStatisticsPortV2QueryDrop		INTEGER,
        	zyMldSnoopingProxyStatisticsPortV2ReportRx		INTEGER,
			zyMldSnoopingProxyStatisticsPortV2ReportTx		INTEGER,
			zyMldSnoopingProxyStatisticsPortV2ReportDrop	INTEGER
        }


        zyMldSnoopingProxyStatisticsPortV1QueryRx OBJECT-TYPE
        SYNTAX  INTEGER
        MAX-ACCESS  read-only
        STATUS  current
        DESCRIPTION	"MLDv1 Query Rx statistic for port"

        ::= { zyxelMldSnoopingProxyStatisticsPortEntry 1 }

        zyMldSnoopingProxyStatisticsPortV1QueryTx OBJECT-TYPE
        SYNTAX  INTEGER
        MAX-ACCESS  read-only
        STATUS  current
        DESCRIPTION	"MLDv1 Query Tx statistic for port"

        ::= { zyxelMldSnoopingProxyStatisticsPortEntry 2 }

        zyMldSnoopingProxyStatisticsPortV1QueryDrop OBJECT-TYPE
        SYNTAX  INTEGER
        MAX-ACCESS  read-only
        STATUS  current
        DESCRIPTION	"MLDv1 Query Drop statistic for port"

        ::= { zyxelMldSnoopingProxyStatisticsPortEntry 3 }

        zyMldSnoopingProxyStatisticsPortV1ReportRx OBJECT-TYPE
        SYNTAX  INTEGER
        MAX-ACCESS  read-only
        STATUS  current
        DESCRIPTION	"MLDv1 Report Rx statistic for port"

        ::= { zyxelMldSnoopingProxyStatisticsPortEntry 4 }

        zyMldSnoopingProxyStatisticsPortV1ReportTx OBJECT-TYPE
        SYNTAX  INTEGER
        MAX-ACCESS  read-only
        STATUS  current
        DESCRIPTION	"MLDv1 Report Tx statistic for port"

        ::= { zyxelMldSnoopingProxyStatisticsPortEntry 5 }

        zyMldSnoopingProxyStatisticsPortV1ReportDrop OBJECT-TYPE
        SYNTAX  INTEGER
        MAX-ACCESS  read-only
        STATUS  current
        DESCRIPTION	"MLDv1 Report Drop statistic for port"

        ::= { zyxelMldSnoopingProxyStatisticsPortEntry 6 }

        zyMldSnoopingProxyStatisticsPortV1DoneRx OBJECT-TYPE
        SYNTAX  INTEGER
        MAX-ACCESS  read-only
        STATUS  current
        DESCRIPTION	"MLDv1 Done Rx statistic for port"

        ::= { zyxelMldSnoopingProxyStatisticsPortEntry 7 }

        zyMldSnoopingProxyStatisticsPortV1DoneTx OBJECT-TYPE
        SYNTAX  INTEGER
        MAX-ACCESS  read-only
        STATUS  current
        DESCRIPTION	"MLDv1 Done Tx statistic for port"

        ::= { zyxelMldSnoopingProxyStatisticsPortEntry 8 }

        zyMldSnoopingProxyStatisticsPortV1DoneDrop OBJECT-TYPE
        SYNTAX  INTEGER
        MAX-ACCESS  read-only
        STATUS  current
        DESCRIPTION	"MLDv1 Done Drop statistic for port"

        ::= { zyxelMldSnoopingProxyStatisticsPortEntry 9 }

        zyMldSnoopingProxyStatisticsPortV2QueryRx OBJECT-TYPE
        SYNTAX  INTEGER
        MAX-ACCESS  read-only
        STATUS  current
        DESCRIPTION	"MLDv2 Query Rx statistic for port"

        ::= { zyxelMldSnoopingProxyStatisticsPortEntry 10 }

        zyMldSnoopingProxyStatisticsPortV2QueryTx OBJECT-TYPE
        SYNTAX  INTEGER
        MAX-ACCESS  read-only
        STATUS  current
        DESCRIPTION	"MLDv2 Query Tx statistic for port"

        ::= { zyxelMldSnoopingProxyStatisticsPortEntry 11 }

        zyMldSnoopingProxyStatisticsPortV2QueryDrop OBJECT-TYPE
        SYNTAX  INTEGER
        MAX-ACCESS  read-only
        STATUS  current
        DESCRIPTION	"MLDv2 Query Drop statistic for port"

        ::= { zyxelMldSnoopingProxyStatisticsPortEntry 12 }

        zyMldSnoopingProxyStatisticsPortV2ReportRx OBJECT-TYPE
        SYNTAX  INTEGER
        MAX-ACCESS  read-only
        STATUS  current
        DESCRIPTION	"MLDv2Report Rx statistic for port"

        ::= { zyxelMldSnoopingProxyStatisticsPortEntry 13 }

        zyMldSnoopingProxyStatisticsPortV2ReportTx OBJECT-TYPE
        SYNTAX  INTEGER
        MAX-ACCESS  read-only
        STATUS  current
        DESCRIPTION	"MLDv2 Report Tx statistic for port"

        ::= { zyxelMldSnoopingProxyStatisticsPortEntry 14 }

        zyMldSnoopingProxyStatisticsPortV2ReportDrop OBJECT-TYPE
        SYNTAX  INTEGER
        MAX-ACCESS  read-only
        STATUS  current
        DESCRIPTION	"MLDv2 Report Drop statistic for port"

        ::= { zyxelMldSnoopingProxyStatisticsPortEntry 15 }

--	zyMldSnoopingProxyStatisticsClear

		zyMldSnoopingProxyStatisticsClear OBJECT-TYPE
        SYNTAX  EnabledStatus
        MAX-ACCESS  read-write
        STATUS  current
        DESCRIPTION
		"Clear all MLD snooping proxy statistics of the switch."
        ::= { zyxelMldSnoopingProxyStatistics 18 }

		zyMldSnoopingProxyStatisticsClearSystem OBJECT-TYPE
        SYNTAX  EnabledStatus
        MAX-ACCESS  read-write
        STATUS  current
        DESCRIPTION
		"Clear the MLD snooping proxy statistics of the system."
        ::= { zyxelMldSnoopingProxyStatistics 19 }

		zyMldSnoopingProxyStatisticsClearPort OBJECT-TYPE
        SYNTAX  EnabledStatus
        MAX-ACCESS  read-write
        STATUS  current
        DESCRIPTION
		"Clear the MLD snooping proxy statistics of the port(s)."
        ::= { zyxelMldSnoopingProxyStatistics 20 }

		zyMldSnoopingProxyStatisticsClearVlan OBJECT-TYPE
        SYNTAX  EnabledStatus
        MAX-ACCESS  read-write
        STATUS  current
        DESCRIPTION
		"Clear the MLD snooping proxy statistics of the VLAN(s)."
        ::= { zyxelMldSnoopingProxyStatistics 21 }

--	zyxelMldSnoopingProxySetup

		zyMldSnoopingProxyState OBJECT-TYPE
        SYNTAX  EnabledStatus
        MAX-ACCESS  read-write
        STATUS  current
        DESCRIPTION
        "Enable/disable MLD Snooping-proxy to forward multicast traffic
         only to ports that are members of that multicast group. "
        ::= { zyxelMldSnoopingProxySetup 1 }

		zyMldSnoopingProxyFilteringState OBJECT-TYPE
        SYNTAX  EnabledStatus
        MAX-ACCESS  read-write
        STATUS  current
        DESCRIPTION
        "Enable/disable MLD Snooping-proxy filtering to control which
         MLD Snooping-proxy groups a subscriber on a port can join.
		 Note: If you enable MLD Snooping-proxy filtering, you must create and
		 assign MLD Snooping-proxy filtering profiles for the ports that you want to allow to join multicast groups. "
        ::= { zyxelMldSnoopingProxySetup 2 }

        zyMldSnoopingProxy8021pPriority OBJECT-TYPE
        SYNTAX  INTEGER
        MAX-ACCESS  read-write
        STATUS  current
        DESCRIPTION
        "Enter a priority level (0-7) to which the switch changes the priority
         in outgoing MLD control packets (The default value is 0)."
        ::= { zyxelMldSnoopingProxySetup 3 }

	   	zyMldSnoopingProxyMaxNumberOfVlans OBJECT-TYPE
        SYNTAX  INTEGER
        MAX-ACCESS  read-only
        STATUS  current
        DESCRIPTION
        "The maximum number of MLD Snoopign-proxy VLAN entries that can be created."
        ::= { zyxelMldSnoopingProxySetup 4 }

--  zyxelMldSnoopingProxyVlanTable
        zyxelMldSnoopingProxyVlanTable	OBJECT-TYPE
        SYNTAX	SEQUENCE OF ZyxelMldSnoopingProxyVlanEntry
        MAX-ACCESS  not-accessible
        STATUS  current
        DESCRIPTION
        "The table contains MLD snooping proxy VLAN configuration."
        ::= { zyxelMldSnoopingProxySetup 5 }

		zyxelMldSnoopingProxyVlanEntry OBJECT-TYPE
        SYNTAX	ZyxelMldSnoopingProxyVlanEntry
        MAX-ACCESS	not-accessible
        STATUS	current
        DESCRIPTION
        "An entry contains MLD snooping proxy VLAN configuration."
        INDEX          	{ zyMldSnoopingProxyVlanVid }
        ::= { zyxelMldSnoopingProxyVlanTable 1 }

        ZyxelMldSnoopingProxyVlanEntry ::=
		SEQUENCE
		{
			zyMldSnoopingProxyVlanVid		INTEGER,
			zyMldSnoopingProxyVlanRowStatus	RowStatus
		}

        zyMldSnoopingProxyVlanVid OBJECT-TYPE
        SYNTAX  INTEGER
        MAX-ACCESS  not-accessible
        STATUS  current
        DESCRIPTION
        "The VLAN ID for which MLD Snoopign-proxy is enabled."
        ::= { zyxelMldSnoopingProxyVlanEntry 1 }

        zyMldSnoopingProxyVlanRowStatus OBJECT-TYPE
        SYNTAX  RowStatus
        MAX-ACCESS  read-create
        STATUS  current
        DESCRIPTION
        "This object allow entry to be create and deleted a MLD Snoopign-proxy VLAN entry."
        ::= { zyxelMldSnoopingProxyVlanEntry 2 }


--  zyxelMldSnoopingProxyVlanUpstreamTable
        zyxelMldSnoopingProxyUpstreamVlanTable	OBJECT-TYPE
        SYNTAX	SEQUENCE OF ZyxelMldSnoopingProxyUpstreamVlanEntry
        MAX-ACCESS  not-accessible
        STATUS  current
        DESCRIPTION
        "The table contains MLD snooping proxy upstream VLAN configuration."
        ::= { zyxelMldSnoopingProxySetup 6 }

		zyxelMldSnoopingProxyUpstreamVlanEntry OBJECT-TYPE
        SYNTAX	ZyxelMldSnoopingProxyUpstreamVlanEntry
        MAX-ACCESS	not-accessible
        STATUS	current
        DESCRIPTION
        "An entry contains MLD snooping proxy upstream VLAN configuration."
        INDEX          	{ zyMldSnoopingProxyVlanVid }
        ::= { zyxelMldSnoopingProxyUpstreamVlanTable 1 }

        ZyxelMldSnoopingProxyUpstreamVlanEntry ::=
		SEQUENCE
		{
			zyMldSnoopingProxyUpstreamVlanPorts						PortList,
			zyMldSnoopingProxyUpstreamVlanQueryInterval				INTEGER,
			zyMldSnoopingProxyUpstreamVlanMaxResponseTime			INTEGER,
			zyMldSnoopingProxyUpstreamVlanRobustness				INTEGER,
			zyMldSnoopingProxyUpstreamVlanLastMemberQueryInterval	INTEGER
		}


		zyMldSnoopingProxyUpstreamVlanPorts OBJECT-TYPE
        SYNTAX  PortList
        MAX-ACCESS  read-write
        STATUS  current
        DESCRIPTION	"Port list for the Upstream part on a particular VLAN."
        ::= { zyxelMldSnoopingProxyUpstreamVlanEntry 1 }

		zyMldSnoopingProxyUpstreamVlanQueryInterval OBJECT-TYPE
        SYNTAX  INTEGER(1000..31744000)
        MAX-ACCESS  read-write
        STATUS  current
        DESCRIPTION	"The query interval  for the Uptream part on a particular VLAN."
        ::= { zyxelMldSnoopingProxyUpstreamVlanEntry 2 }

		zyMldSnoopingProxyUpstreamVlanMaxResponseTime OBJECT-TYPE
        SYNTAX  INTEGER(1000..25000)
        MAX-ACCESS  read-write
        STATUS  current
        DESCRIPTION	"The maximum query response interval for the Uptream part on a particular VLAN."
        ::= { zyxelMldSnoopingProxyUpstreamVlanEntry 3 }

		zyMldSnoopingProxyUpstreamVlanRobustness OBJECT-TYPE
        SYNTAX  INTEGER(1..25)
        MAX-ACCESS  read-write
        STATUS  current
        DESCRIPTION
        "The Robustness Variable  for the Upwnstream part on a particular VLAN.
        The Robustness Variable allows tuning for the expected packet loss on a subnet.
        If a subnet is expected to be lossy, the Robustness Variable may be increased."
        ::= { zyxelMldSnoopingProxyUpstreamVlanEntry 4 }

		zyMldSnoopingProxyUpstreamVlanLastMemberQueryInterval OBJECT-TYPE
        SYNTAX  INTEGER(1..8387584)
		MAX-ACCESS  read-write
        STATUS  current
        DESCRIPTION
        "The last member query interval  for the Upstream part on a particular VLAN.
         The Last Member Query Interval is the Max Query Response Interval inserted
         into group-specific queries sent in response to leave group messages, and
         is also the amount of time between group-specific query messages.
         This value may be tuned to modify the leave latency of the network.
         A reduced value results in reduced time to detect the loss of the last member of a group."
        ::= { zyxelMldSnoopingProxyUpstreamVlanEntry 5 }

--  zyxelMldSnoopingProxyVlanDownstreamTable
        zyxelMldSnoopingProxyDownstreamVlanTable	OBJECT-TYPE
        SYNTAX	SEQUENCE OF ZyxelMldSnoopingProxyDownstreamVlanEntry
        MAX-ACCESS  not-accessible
        STATUS  current
        DESCRIPTION
        "The table contains MLD snooping proxy downstream VLAN configuration."
        ::= { zyxelMldSnoopingProxySetup 7 }

		zyxelMldSnoopingProxyDownstreamVlanEntry OBJECT-TYPE
        SYNTAX	ZyxelMldSnoopingProxyDownstreamVlanEntry
        MAX-ACCESS	not-accessible
        STATUS	current
        DESCRIPTION
        "An entry contains MLD snooping proxy downstream VLAN configuration."
        INDEX          	{ zyMldSnoopingProxyVlanVid }
        ::= { zyxelMldSnoopingProxyDownstreamVlanTable 1 }

        ZyxelMldSnoopingProxyDownstreamVlanEntry ::=
		SEQUENCE
		{
			zyMldSnoopingProxyDownstreamVlanPorts				PortList,
			zyMldSnoopingProxyDownstreamVlanQueryInterval		INTEGER,
			zyMldSnoopingProxyDownstreamVlanMaxResponseTime		INTEGER
		}

		zyMldSnoopingProxyDownstreamVlanPorts OBJECT-TYPE
        SYNTAX  PortList
        MAX-ACCESS  read-write
        STATUS  current
        DESCRIPTION
        "Port list for the Downstream part on a particular VLAN."
        ::= { zyxelMldSnoopingProxyDownstreamVlanEntry 1 }

		zyMldSnoopingProxyDownstreamVlanQueryInterval OBJECT-TYPE
        SYNTAX  INTEGER(1000..31744000)
        MAX-ACCESS  read-write
        STATUS  current
        DESCRIPTION
        "Sets the amount of time (in miliseconds) between general query messages sent by the downstream port."
        ::= { zyxelMldSnoopingProxyDownstreamVlanEntry 2 }

		zyMldSnoopingProxyDownstreamVlanMaxResponseTime OBJECT-TYPE
        SYNTAX  INTEGER(1000..25000)
        MAX-ACCESS  read-write
        STATUS  current
        DESCRIPTION
        "Sets the maximum time (in miliseconds) that the Switch waits for a response to a general query message
        sent by the downstream port."
        ::= { zyxelMldSnoopingProxyDownstreamVlanEntry 3 }

--  zyxelMldSnoopingProxyDownstreamVlanPortTable
        zyxelMldSnoopingProxyDownstreamVlanPortTable	OBJECT-TYPE
        SYNTAX	SEQUENCE OF ZyxelMldSnoopingProxyDownstreamVlanPortEntry
        MAX-ACCESS  not-accessible
        STATUS  current
        DESCRIPTION
        "The table contains MLD snooping proxy downstream VLAN port configuration."
        ::= { zyxelMldSnoopingProxySetup 8 }

		zyxelMldSnoopingProxyDownstreamVlanPortEntry OBJECT-TYPE
        SYNTAX	ZyxelMldSnoopingProxyDownstreamVlanPortEntry
        MAX-ACCESS	not-accessible
        STATUS	current
        DESCRIPTION
        "An entry contains MLD snooping proxy downstream VLAN port configuration."
        INDEX          	{ zyMldSnoopingProxyVlanVid, zyMldSnoopingProxyDownstreamVlanPortIndex }
        ::= { zyxelMldSnoopingProxyDownstreamVlanPortTable 1 }

        ZyxelMldSnoopingProxyDownstreamVlanPortEntry ::=
		SEQUENCE
		{
			zyMldSnoopingProxyDownstreamVlanPortIndex				INTEGER,
			zyMldSnoopingProxyDownstreamVlanPortLeaveMode			INTEGER,
			zyMldSnoopingProxyDownstreamVlanPortLeaveTimeout		INTEGER,
			zyMldSnoopingProxyDownstreamVlanPortFastLeaveTimeout	INTEGER
		}

		zyMldSnoopingProxyDownstreamVlanPortIndex OBJECT-TYPE
        SYNTAX  INTEGER
		MAX-ACCESS  not-accessible
        STATUS  current
        DESCRIPTION
        "Index number of downstream port is enabled."
        ::= { zyxelMldSnoopingProxyDownstreamVlanPortEntry 1 }

		zyMldSnoopingProxyDownstreamVlanPortLeaveMode OBJECT-TYPE
        SYNTAX  INTEGER
		{
           	immediate(0),
        	normal(1),
        	fast(2)
        }
        MAX-ACCESS  read-write
        STATUS  current
        DESCRIPTION
        "Leave mode for the port. When a done report is received, downstream sends MASQ to
         confirm a multicast address has no listener. Once the MASQ is timeout, the multicast
         group is deleted. This entry handle the mode of deleting a multicast address.
         Immediate : when a done report is received, a multicast address is immediately deleted.
         Fast: a timer for wating a response of a MASQ, and a multicast address is deleted when the timer is timout.
         Normal: a timer for wating a response of a MASQ, and a multicast address is deleted when the timer is timout."
        ::= { zyxelMldSnoopingProxyDownstreamVlanPortEntry 2 }

		zyMldSnoopingProxyDownstreamVlanPortLeaveTimeout OBJECT-TYPE
        SYNTAX  INTEGER
        MAX-ACCESS  read-write
        STATUS  current
        DESCRIPTION
        "Set the MLD snooping normal leave timeout (in miliseconds) the Switch uses to update the forwarding
        table for the specified downstream port(s).This defines how many seconds the Switch waits for an MLD
        report before removing an MLD snooping membership entry (learned on a downstream port) when an MLD Done
        message is received on this port from a host."
        ::= { zyxelMldSnoopingProxyDownstreamVlanPortEntry 3 }

		zyMldSnoopingProxyDownstreamVlanPortFastLeaveTimeout OBJECT-TYPE
        SYNTAX  INTEGER
        MAX-ACCESS  read-write
        STATUS  current
        DESCRIPTION
        "Sets the fast leave timeout (in miliseconds) for the specified downstream port(s).
        This defines how many seconds the Switch waits for an MLD report before removing an MLD snooping
        membership entry (learned on a downstream port) when an MLD Done message is received on this port
        from a host."
        ::= { zyxelMldSnoopingProxyDownstreamVlanPortEntry 4 }

--	zyxelMldSnoopingProxyMembershipStatus


--  zyxelMldSnoopingProxyMembershipTable
        zyxelMldSnoopingProxyMembershipTable	OBJECT-TYPE
        SYNTAX	SEQUENCE OF ZyxelMldSnoopingProxyMembershipEntry
        MAX-ACCESS  not-accessible
        STATUS  current
        DESCRIPTION
        "The table contains MLD snooping proxy Membership information."
        ::= { zyxelMldSnoopingProxyMembershipStatus 1 }

		zyxelMldSnoopingProxyMembershipEntry OBJECT-TYPE
        SYNTAX	ZyxelMldSnoopingProxyMembershipEntry
        MAX-ACCESS	not-accessible
        STATUS	current
        DESCRIPTION
        "An entry contains MLD snooping proxy Membership information."
        INDEX{
        	zyMldSnoopingProxyMembershipVid,
			zyMldSnoopingProxyMembershipPort,
			zyMldSnoopingProxyMembershipGroupIpAddressType,
			zyMldSnoopingProxyMembershipGroupIpAddress
		}
        ::= { zyxelMldSnoopingProxyMembershipTable 1 }

        ZyxelMldSnoopingProxyMembershipEntry ::=
		SEQUENCE
		{
			zyMldSnoopingProxyMembershipVid					INTEGER,
			zyMldSnoopingProxyMembershipPort				INTEGER,
			zyMldSnoopingProxyMembershipGroupIpAddressType	InetAddressType,
			zyMldSnoopingProxyMembershipGroupIpAddress		InetAddress,
			zyMldSnoopingProxyMembershipGroupTimeout		INTEGER
		}

        zyMldSnoopingProxyMembershipVid OBJECT-TYPE
        SYNTAX  INTEGER (1..4094)
        MAX-ACCESS  not-accessible
        STATUS  current
        DESCRIPTION
        "The VLAN ID for which this entry contains information for an IPv6 multicast group address."
        ::= { zyxelMldSnoopingProxyMembershipEntry 1 }

        zyMldSnoopingProxyMembershipPort OBJECT-TYPE
        SYNTAX  INTEGER
        MAX-ACCESS  not-accessible
        STATUS  current
        DESCRIPTION
        "The port for which this entry contains information for an IPv6 multicast group address."
        ::= { zyxelMldSnoopingProxyMembershipEntry 2 }

        zyMldSnoopingProxyMembershipGroupIpAddressType OBJECT-TYPE
        SYNTAX  InetAddressType
        MAX-ACCESS  not-accessible
        STATUS  current
        DESCRIPTION
        "The type of multicast group address for which this entry contains information."
        ::= { zyxelMldSnoopingProxyMembershipEntry 3 }

        zyMldSnoopingProxyMembershipGroupIpAddress OBJECT-TYPE
        SYNTAX  InetAddress
        MAX-ACCESS  not-accessible
        STATUS  current
        DESCRIPTION
        "The multicast group address for which this entry contains information."
        ::= { zyxelMldSnoopingProxyMembershipEntry 4 }

        zyMldSnoopingProxyMembershipGroupTimeout OBJECT-TYPE
        SYNTAX  INTEGER
        MAX-ACCESS  read-only
        STATUS  current
        DESCRIPTION
        "This value represents the time remaining before the Group Membership Interval state expires.
        The value must always be greater than or equal to 1."
        ::= { zyxelMldSnoopingProxyMembershipEntry 5 }



END
