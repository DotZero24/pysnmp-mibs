ARISTA-MAU-MIB DEFINITIONS ::= BEGIN

     IMPORTS
       MODULE-IDENTITY, OBJECT-IDENTITY
         FROM SNMPv2-SMI
       aristaMibs
         FROM ARISTA-SMI-MIB
       ;

     aristaMauMIB MODULE-IDENTITY
       LAST-UPDATED "201606230000Z"  -- June 23, 2016
       ORGANIZATION "Arista Networks, Inc."
       CONTACT-INFO
          "Arista Networks, Inc.

           Postal: 5453 Great America Parkway
                   Santa Clara, CA 95054

           Tel: +1 408 547-5500

           E-mail: snmp@arista.com"
       DESCRIPTION
         "This MIB module extends dot3MauType OBJECT-IDENTITIES
         defined in the IANA-MAU-MIB, covering all MAU types
         used by Arista Networks."

       REVISION     "201606230000Z"  -- June 23, 2016
       DESCRIPTION  "Revised to include aristaDot3MauType100GEDwdm2."

       REVISION     "201511300000Z"  -- November 30, 2015
       DESCRIPTION  "Revised to include aristaDot3MauType100GbaseCWDM4."

       REVISION     "201509010000Z"  -- September 01, 2015
       DESCRIPTION  "Revised to include aristaDot3MauType100GDwdmCoherentE."

       REVISION     "201507080000Z"  -- July 8, 2015
       DESCRIPTION  "Revised to include aristaDot3MauType100GbasePSM4 and
                    aristaDot3MauType100GbaseCLR4."

       REVISION     "201505290000Z"  -- May 29, 2015
       DESCRIPTION  "Revised to include aristaDot3MauType40GbaseSRBD and
                     aristaDot3MauType40GbaseSR4D."

       REVISION     "201504010000Z"  -- April 01, 2015
       DESCRIPTION  "Revised to include aristaDot3MauType10GbaseDwdmZT."

       REVISION     "201503010000Z"  -- March 01, 2015
       DESCRIPTION  "Revised to include aristaDot3MauType100GDwdmCoherent."

       REVISION     "201412090000Z"  -- December 9, 2014
       DESCRIPTION  "Revised to include aristaDot3MauType100GbaseLRL4."

       REVISION     "201411210000Z"  -- November 21, 2014
       DESCRIPTION  "Revised to include aristaDot3MauType100GbaseCR4 and
                    aristaDot3MauType100GbaseAR4."

       REVISION     "201411120000Z"  -- November 12, 2014
       DESCRIPTION  "Revised to include aristaDot3MauType10GbaseAR."

       REVISION     "201410210000Z"  -- October 21, 2014
       DESCRIPTION  "Revised to include aristaDot3MauType40GbaseER4 and
                    aristaDot3MauType100GbaseXSR10."

       REVISION     "201408150000Z"  -- August 15, 2014
       DESCRIPTION  "Updated postal and e-mail addresses."

       REVISION     "201406300000Z"  -- June 30, 2014
       DESCRIPTION  "Revised to include aristaDot3MauType40GbaseUniv."

       REVISION     "201401130000Z"  -- January 13, 2014
       DESCRIPTION  "Revised to include aristaDot3MauType100GbaseSR4."

       REVISION     "201312100000Z"  -- December 10, 2013
       DESCRIPTION  "Revised to include aristaDot3MauType40GbaseLRL4."

       REVISION     "201310240000Z"  -- October 24, 2013
       DESCRIPTION  "Revised to include aristaDot3MauType40GbasePSM4."

       REVISION     "201307170000Z"  -- July 17, 2013
       DESCRIPTION  "Revised to include aristaDot3MauType40GbaseAR4,
                    aristaDot3MauType40GbasePLR4, and
		    aristaDot3MauType40GbasePLRL4."

       REVISION     "201210120000Z"  -- October 12, 2012
       DESCRIPTION  "Revised to include aristaDot3MauType10GbaseZR and
                    aristaDot3MauType10GbaseLRL."

       REVISION     "201207260000Z"  -- July 26, 2012
       DESCRIPTION  "Revised to include aristaDot3MauType40GbaseXSR4."

       REVISION     "201206290000Z"  -- June 29, 2012
       DESCRIPTION  "Revised to include aristaDot3MauType100GbaseSR10,
                    aristaDot3MauType100GbaseLR4, and
		    aristaDot3MauType100GbaseER4."

       REVISION     "201205140000Z"  -- May 14, 2012
       DESCRIPTION  "Revised to include aristaDot3MauType10GbaseCRA."

       REVISION     "201204100000Z"  -- April 10, 2012
       DESCRIPTION  "Revised to include aristaDot3MauType10GbaseDwdmZR
                    and renamed aristaDot3MauType10GbaseDWDM to
                    aristaDot3MauType10GbaseDwdmER."

       REVISION     "201102250000Z"  -- February 25, 2011
       DESCRIPTION  "Initial version of this MIB."

       ::= { aristaSnmpDot3MauMgt 2 }

     aristaSnmpDot3MauMgt OBJECT IDENTIFIER ::= { aristaMibs 4 }
     aristaDot3MauType OBJECT IDENTIFIER ::= { aristaSnmpDot3MauMgt 1 }

     aristaDot3MauType10GbaseCR OBJECT-IDENTITY
       STATUS      current
       DESCRIPTION "Passive copper cable"
       REFERENCE   "SFF-8472 (Rev. 11.0), Table 3.6b"
       ::= { aristaDot3MauType 1 }

     aristaDot3MauType10GbaseDwdmER OBJECT-IDENTITY
       STATUS      current
       DESCRIPTION "Dense Wavelength Division Multiplexing ER"
       ::= { aristaDot3MauType 2 }

     aristaDot3MauType40GbaseSR4 OBJECT-IDENTITY
       STATUS      deprecated
       DESCRIPTION "Short range over multi-mode fiber

                   This object has been deprecated in favor of
		   IANA-MAU-MIB::dot3MauType40GbaseSR4."
       REFERENCE   "[IEEE802.3ba], Section 86"
       ::= { aristaDot3MauType 3 }

     aristaDot3MauType40GbaseLR4 OBJECT-IDENTITY
       STATUS      deprecated
       DESCRIPTION "Long range over WDM single-mode fiber

                   This object has been deprecated in favor of
		   IANA-MAU-MIB::dot3MauType40GbaseLR4."
       REFERENCE   "[IEEE802.3ba], Section 87"
       ::= { aristaDot3MauType 4 }

     aristaDot3MauType40GbaseCR4 OBJECT-IDENTITY
       STATUS      deprecated
       DESCRIPTION "Passive copper cable

                   This object has been deprecated in favor of
		   IANA-MAU-MIB::dot3MauType40GbaseCR4."
       REFERENCE   "[IEEE802.3ba], Section 85"
       ::= { aristaDot3MauType 5 }

     aristaDot3MauType10GbaseDwdmZR OBJECT-IDENTITY
       STATUS      current
       DESCRIPTION "Dense Wavelength Division Multiplexing ZR"
       ::= { aristaDot3MauType 6 }

     aristaDot3MauType10GbaseCRA OBJECT-IDENTITY
       STATUS      current
       DESCRIPTION "Active copper cable"
       REFERENCE   "SFF-8472 (Rev. 11.0), Table 3.6c"
       ::= { aristaDot3MauType 7 }

     aristaDot3MauType10GbaseZR OBJECT-IDENTITY
       STATUS      current
       DESCRIPTION "Very long range over single-mode fiber"
       ::= { aristaDot3MauType 8 }

     aristaDot3MauType10GbaseLRL OBJECT-IDENTITY
       STATUS      current
       DESCRIPTION "Long range (1km) over single-mode fiber"
       ::= { aristaDot3MauType 9 }

     aristaDot3MauType100GbaseSR10 OBJECT-IDENTITY
       STATUS      deprecated
       DESCRIPTION "Short range over multi-mode fiber

                   This object has been deprecated in favor of
		   IANA-MAU-MIB::dot3MauType100GbaseSR10."
       REFERENCE   "[IEEE802.3ba], Section 86"
       ::= { aristaDot3MauType 10 }

     aristaDot3MauType100GbaseLR4 OBJECT-IDENTITY
       STATUS      deprecated
       DESCRIPTION "Long range over WDM single-mode fiber

                   This object has been deprecated in favor of
		   IANA-MAU-MIB::dot3MauType100GbaseLR4."
       REFERENCE   "[IEEE802.3ba], Section 88"
       ::= { aristaDot3MauType 11 }

     aristaDot3MauType100GbaseER4 OBJECT-IDENTITY
       STATUS      deprecated
       DESCRIPTION "Extended range over WDM single-mode fiber

                   This object has been deprecated in favor of
		   IANA-MAU-MIB::dot3MauType100GbaseER4."
       REFERENCE   "[IEEE802.3ba], Section 88"
       ::= { aristaDot3MauType 12 }

     aristaDot3MauType40GbaseXSR4 OBJECT-IDENTITY
       STATUS      current
       DESCRIPTION "Short range (300m) over multi-mode fiber"
       REFERENCE   "[IEEE802.3ba], Section 86"
       ::= { aristaDot3MauType 13 }

     aristaDot3MauType40GbaseAR4 OBJECT-IDENTITY
       STATUS      current
       DESCRIPTION "Active cable"
       ::= { aristaDot3MauType 14 }

     aristaDot3MauType40GbasePLR4 OBJECT-IDENTITY
       STATUS      current
       DESCRIPTION "Long range over parallel single-mode fiber"
       ::= { aristaDot3MauType 15 }

     aristaDot3MauType40GbasePLRL4 OBJECT-IDENTITY
       STATUS      current
       DESCRIPTION "Long range (1km) over parallel single-mode fiber"
       ::= { aristaDot3MauType 16 }

     aristaDot3MauType40GbasePSM4 OBJECT-IDENTITY
       STATUS      current
       DESCRIPTION "Long range over parallel single-mode fiber"
       ::= { aristaDot3MauType 17 }

     aristaDot3MauType40GbaseLRL4 OBJECT-IDENTITY
       STATUS      current
       DESCRIPTION "Long range (1km) over WDM single-mode fiber"
       ::= { aristaDot3MauType 18 }

     aristaDot3MauType100GbaseSR4 OBJECT-IDENTITY
       STATUS      current
       DESCRIPTION "Short range over multi-mode fiber"
       ::= { aristaDot3MauType 19 }

     aristaDot3MauType40GbaseUniv OBJECT-IDENTITY
       STATUS      current
       DESCRIPTION "Long range over WDM single- or multi-mode fiber"
       ::= { aristaDot3MauType 20 }

     aristaDot3MauType40GbaseER4 OBJECT-IDENTITY
       STATUS      current
       DESCRIPTION "Extended range over WDM single-mode fiber"
       ::= { aristaDot3MauType 21 }

     aristaDot3MauType100GbaseXSR10 OBJECT-IDENTITY
       STATUS      current
       DESCRIPTION "Short range over multi-mode fiber, 300m range"
       ::= { aristaDot3MauType 22 }

     aristaDot3MauType10GbaseAR OBJECT-IDENTITY
       STATUS      current
       DESCRIPTION "Active cable"
       ::= { aristaDot3MauType 23 }

     aristaDot3MauType100GbaseAR4 OBJECT-IDENTITY
       STATUS      current
       DESCRIPTION "Active cable"
       ::= { aristaDot3MauType 24 }

     aristaDot3MauType100GbaseCR4 OBJECT-IDENTITY
       STATUS      current
       DESCRIPTION "Passive copper cable"
       ::= { aristaDot3MauType 25 }

     aristaDot3MauType100GbaseLRL4 OBJECT-IDENTITY
       STATUS      current
       DESCRIPTION "Long range (1km) over WDM single-mode fiber"
       ::= { aristaDot3MauType 26 }

     aristaDot3MauType100GDwdmCoherent OBJECT-IDENTITY
       STATUS      current
       DESCRIPTION "Very long range analog coherent limiting DWDM over single-mode
                   fiber"
       ::= { aristaDot3MauType 27 }

     aristaDot3MauType10GbaseDwdmZT OBJECT-IDENTITY
       STATUS      current
       DESCRIPTION "Dense Wavelength Division Multiplexing ZT"
       REFERENCE "SFF-8690 Rev 1.4"
       ::= { aristaDot3MauType 28 }

     aristaDot3MauType40GbaseSRBD OBJECT-IDENTITY
       STATUS      current
       DESCRIPTION "Short range over WDM multi-mode fiber"
       ::= { aristaDot3MauType 29 }

     aristaDot3MauType40GbaseSR4D OBJECT-IDENTITY
       STATUS      current
       DESCRIPTION "Short range (300m) over WDM multi-mode fiber"
       ::= { aristaDot3MauType 30 }

     aristaDot3MauType100GbasePSM4 OBJECT-IDENTITY
       STATUS      current
       DESCRIPTION "Long range (500m) over parallel single-mode fiber"
       ::= { aristaDot3MauType 31 }

     aristaDot3MauType100GbaseCLR4 OBJECT-IDENTITY
       STATUS      current
       DESCRIPTION "Long range (2km) over CWDM single-mode fiber"
       ::= { aristaDot3MauType 32 }

     aristaDot3MauType100GDwdmCoherentE OBJECT-IDENTITY
       STATUS      current
       DESCRIPTION "Very long range analog coherent linear DWDM over single-mode
                   fiber"
       ::= { aristaDot3MauType 33 }

     aristaDot3MauType100GbaseCWDM4 OBJECT-IDENTITY
       STATUS      current
       DESCRIPTION "Coarse Wavelength Division Multiplexing over single-mode fiber"
       ::= { aristaDot3MauType 35 }

     aristaDot3MauType100GEDwdm2 OBJECT-IDENTITY
       STATUS      current
       DESCRIPTION "Very long range Dense Wavelength Division Multiplexing"
       ::= { aristaDot3MauType 36 }

END
