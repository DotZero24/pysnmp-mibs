ADTRAN-GENTA5K-MIB

  DEFINITIONS ::= BEGIN

  -- TITLE:     Adtran TA5000 Group MIB
  -- DATE:      April 18, 2006
  --
  -- REVISION HISTORY: Date           Comments
  --                   04/18/2006     Created.
  --                   04/19/2006     Made to be .mi2 instead of .mib and module identity added
  --                   03/27/2007     aed - Added genEthernet and genBridge
  --                   07/18/2007     aed - Added Bulk PM MIB
  --                   09/20/2007     twc - Added DS3 MIB
  --                   09/20/2007     aed - Added Fdl MIB for Joe Onder
  --                   03/06/2008     jkb - Added IMA MIB
  --                   08/03/2009     srao - Reserved DIDs for genDslProxy.mi2
  --                   09/16/2009     cb - Added adGenDhcpClient
  -- DO NOT MAKE HISTORY COMMENTS HERE!!!! Revision history now in REVISION/DESCRIPTION clauses below

    IMPORTS
        MODULE-IDENTITY,
        OBJECT-TYPE,
        Integer32,
        Counter32,
        IpAddress
            FROM SNMPv2-SMI

      adShared,
      adIdentityShared
          FROM ADTRAN-MIB;

     adGenTa5kModuleIdentity MODULE-IDENTITY
        LAST-UPDATED "201302280000Z"
        ORGANIZATION
            "ADTRAN, Inc."
        CONTACT-INFO
            "CND Tech Support
                Postal: ADTRAN, Inc.
                        901 Explorer Blvd.
                        Huntsville, AL  35806
                        Tel: +1 800 726-8663
                        Fax: +1 256 963 6217
                        E-mail: support@adtran.com"
        DESCRIPTION
            "Total Access 5000 Shared Definitions MIB"
        REVISION "201503060000Z"
            DESCRIPTION "Added new DID range for genSubtendedHost.mi2"
        REVISION "201302280000Z"
            DESCRIPTION "Added adTa5kPbitRemapping."
        REVISION "201212100000Z"
            DESCRIPTION "WM - AddedTA5000 ACS Server Profile"
        REVISION "201112080000Z"
            DESCRIPTION "PSK - Added adTa5kFxoFac and adTa5kFxoFacID."
        REVISION "201111140000Z"
            DESCRIPTION "PSK - Added adTa5kFxsFac and adTa5kFxsFacID."
        ::= { adIdentityShared 67 }


  -- OBJECT IDENTIFIERS

  adGenTa5k                  OBJECT IDENTIFIER ::= { adShared 67  }
  adGenTa5kMgmt              OBJECT IDENTIFIER ::= { adGenTa5k 1  }
  adGenTa5kID                OBJECT IDENTIFIER ::= { adGenTa5kModuleIdentity 1 }

-- DIDs start at 0x4100
  adGenTa5kRedundancy        OBJECT IDENTIFIER ::= { adGenTa5kMgmt 1  }
  adGenTa5kRedundancyID      OBJECT IDENTIFIER ::= { adGenTa5kID   1  }

-- DIDs start at 0x4200
  adGenTa5kPseudowire        OBJECT IDENTIFIER ::= { adGenTa5kMgmt 2  }
  adGenTa5kPseudowireID      OBJECT IDENTIFIER ::= { adGenTa5kID   2  }

-- DIDs start at 0x4300
  adGenTa5kTiming            OBJECT IDENTIFIER ::= { adGenTa5kMgmt 3  }
  adGenTa5kTimingID          OBJECT IDENTIFIER ::= { adGenTa5kID   3  }

-- DIDs start at 0x4400
  adGenTa5kAtpCli            OBJECT IDENTIFIER ::= { adGenTa5kMgmt 4  }
  adGenTa5kAtpCliID          OBJECT IDENTIFIER ::= { adGenTa5kID   4  }

-- DIDs start at 0x4500
  adGenTa5kTlv               OBJECT IDENTIFIER ::= { adGenTa5kMgmt 5  }
  adGenTa5kTlvID             OBJECT IDENTIFIER ::= { adGenTa5kID   5  }

-- DIDs start at 0x4600
  adGenTa5kCommonDs1Prov     OBJECT IDENTIFIER ::= { adGenTa5kMgmt 6  }
  adGenTa5kCommonDs1ProvID   OBJECT IDENTIFIER ::= { adGenTa5kID   6  }

-- DIDs start at 0x4700
-- HouseKeeper, indexed by slot, gives temperature and card presense
  adGenTa5kHk                OBJECT IDENTIFIER ::= { adGenTa5kMgmt 7  }
  adGenTa5kHkID              OBJECT IDENTIFIER ::= { adGenTa5kID   7  }

-- DIDs start at 0x4800
  adGenTa5kSlot              OBJECT IDENTIFIER ::= { adGenTa5kMgmt 8  }
  adGenTa5kSlotID            OBJECT IDENTIFIER ::= { adGenTa5kID   8  }

-- DIDs start at 0x4900
  adGenTa5kErrorOid          OBJECT IDENTIFIER ::= { adGenTa5kMgmt 9  }
  adGenTa5kSErrorOidID       OBJECT IDENTIFIER ::= { adGenTa5kID   9  }

-- DIDs start at 0x5000
  adGenTa5kBandwidth         OBJECT IDENTIFIER ::= { adGenTa5kMgmt 10  }
  adGenTa5kBandwidthID       OBJECT IDENTIFIER ::= { adGenTa5kID   10  }

-- DIDs start at 0x5100
-- RPR Extention MIB - extends ieee802d17.mib
  adGenTa5kRprExt            OBJECT IDENTIFIER ::= { adGenTa5kMgmt 11  }
  adGenTa5kRprExtID          OBJECT IDENTIFIER ::= { adGenTa5kID   11  }

-- DIDs start at 0x5200
-- TR08
  adGenTa5kTr08              OBJECT IDENTIFIER ::= { adGenTa5kMgmt 12  }
  adGenTa5kTr08ID            OBJECT IDENTIFIER ::= { adGenTa5kID   12  }

-- DIDs start at 0x5300 through 0x5400 (block of 255)
-- OC3
  adGenTa5kOc3               OBJECT IDENTIFIER ::= { adGenTa5kMgmt 13  }
  adGenTa5kOc3ID             OBJECT IDENTIFIER ::= { adGenTa5kID   13  }

-- DIDs start at 0x5400 through 0x5500
-- ATM Line Modules
  adGenTa5kAtmLM             OBJECT IDENTIFIER ::= { adGenTa5kMgmt 14  }
  adGenTa5kAtmLMID           OBJECT IDENTIFIER ::= { adGenTa5kID   14  }

-- DIDs start at 0x5500 through 0x5580
-- Generic Ethernet MIB
   adGenEthernet             OBJECT IDENTIFIER ::= { adGenTa5kMgmt 15  }
   adGenEthernetID           OBJECT IDENTIFIER ::= { adGenTa5kID   15  }

-- DIDs start at 0x5580 through 0x55FF
-- Generic Bridge MIB
   adGenBridge               OBJECT IDENTIFIER ::= { adGenTa5kMgmt 16  }
   adGenBridgeID             OBJECT IDENTIFIER ::= { adGenTa5kID   16  }

-- DIDs start at 0x5600 through 0x5700
-- SHDSL 32 EFM
   adTA5kEfm32Shdsl          OBJECT IDENTIFIER ::= { adGenTa5kMgmt 17  }
   adTA5kEfm32ShdslID        OBJECT IDENTIFIER ::= { adGenTa5kID   17  }

-- DIDs start at 0x5700 through 0x5720
-- Bulk PM Instance values
   adGenTa5kBulkPM           OBJECT IDENTIFIER ::= { adGenTa5kMgmt 18  }
   adGenTa5kBulkPMID         OBJECT IDENTIFIER ::= { adGenTa5kID   18  }

-- DIDs start at 0x5720 through 0x5739 and 0x6200 through 0x6210
-- Generic GR909 Loop Tests MIB
   adGenGr909                OBJECT IDENTIFIER ::= { adGenTa5kMgmt 19  }
   adGenGr909ID              OBJECT IDENTIFIER ::= { adGenTa5kID   19  }

-- DIDs start at 0x573A through 0x576F
-- OAM
   adGenTa5kOam                OBJECT IDENTIFIER ::= { adGenTa5kMgmt 20  }
   adGenTa5kOamID              OBJECT IDENTIFIER ::= { adGenTa5kID   20  }

-- DIDs start at 0x5770 through 0x577F
-- DS3
   adGenTa5kDs3                OBJECT IDENTIFIER ::= { adGenTa5kMgmt 21  }
   adGenTa5kDs3ID              OBJECT IDENTIFIER ::= { adGenTa5kID   21  }

-- DIDs start at 0x5780 through 0x57A0
-- FDL
   adTa5kFdl                OBJECT IDENTIFIER ::= { adGenTa5kMgmt 22  }
   adTa5kFdlID              OBJECT IDENTIFIER ::= { adGenTa5kID   22  }

-- DIDs start at 0x57A0 through 0x58A0
-- MIB:  ADTRAN-GENERIC-PSEUDOWIRE-MGMT-MIB
  adGenTa5kPseudowireMgmt    OBJECT IDENTIFIER ::= { adGenTa5kMgmt 23  }
  adGenTa5kPseudowireMgmtID  OBJECT IDENTIFIER ::= { adGenTa5kID   23  }

-- DIDs start at 0x58A1 through 0x58FF
-- DS3 PM Threshold
   adGenTa5kDs3PMThreshold     OBJECT IDENTIFIER ::= { adGenTa5kMgmt 24  }
   adGenTa5kDs3PMThresholdID   OBJECT IDENTIFIER ::= { adGenTa5kID   24  }

-- DIDs start at 0x5900 through 0x59FF
-- IMA
   adGenIma                  OBJECT IDENTIFIER ::= { adGenTa5kMgmt 25  }
   adGenImaID                OBJECT IDENTIFIER ::= { adGenTa5kID   25  }

-- DIDs start at 0x6000 through 0x60FF
-- EFM Ext - commenting out since they are already defined in ADTRAN-SHARED-EFM-MIB
-- adGenEfmExt               OBJECT IDENTIFIER ::= { adEfm 3  }
-- adGenEfmExtID             OBJECT IDENTIFIER ::= { adEfmIdentity 3  }

-- DIDs start at 0x6100 through 0x61FF
-- GenQueue
   adGenQueue               OBJECT IDENTIFIER ::= { adGenTa5kMgmt 27  }
   adGenQueueID             OBJECT IDENTIFIER ::= { adGenTa5kID   27  }

-- DIDs start at 0x6200 through 0x6210 reserved for
-- Generic GR909 Loop Tests MIB (above)

-- DIDs start at 0x6300 through 0x63FF
-- QueueAdmin & QueueAdminStatus
   adGenQueueAdmin                OBJECT IDENTIFIER ::= { adGenTa5kMgmt 28  }
   adGenQueueAdminID             OBJECT IDENTIFIER ::= { adGenTa5kID   28  }

-- DIDs start at 0x6400 through 0x640F
   -- Newtork Mode Support for Line card
   adGenNWModeMisc                OBJECT IDENTIFIER ::= { adGenTa5kMgmt 29  }
   adGenNWModeMiscID             OBJECT IDENTIFIER ::= { adGenTa5kID   29  }

-- DIDs start at 0x6410 through 0x642F
-- ARP Display
   adGenArp                 OBJECT IDENTIFIER ::= { adGenTa5kMgmt 30 }
   adGenArpID               OBJECT IDENTIFIER ::= { adGenTa5kID   30 }

-- DIDs start at 0x6430 through 0x64ff
-- PPP Support
   adGenPpp               OBJECT IDENTIFIER ::= { adGenTa5kMgmt 31  }
   adGenPppID             OBJECT IDENTIFIER ::= { adGenTa5kID   31  }

-- TA5000 Tree Networking MIB
-- Uses DIDs 0x6500 through 0x657F
   adTa5kTreeNetworking     OBJECT IDENTIFIER ::= {adGenTa5kMgmt  32 }
   adTa5kTreeNetworkingID   OBJECT IDENTIFIER ::= {adGenTa5kID    32 }

-- TA5000 Link Aggregation MIB
-- Uses DIDs 0x6580 - 0x65BF
   adTa5kLinkAggregation      OBJECT IDENTIFIER ::= {adGenTa5kMgmt  33 }
   adTa5kLinkAggregationID    OBJECT IDENTIFIER ::= {adGenTa5kID    33 }

-- DIDs start at 0x65C0 through 0x65CF
-- MultiMode Support
   adGenMultiAppMode               OBJECT IDENTIFIER ::= { adGenTa5kMgmt 34  }
   adGenMultiAppModeID             OBJECT IDENTIFIER ::= { adGenTa5kID   34  }

 -- GenEgressQueue.mi2
 -- Uses DIDs 0x66D0 through 0x66FF

 -- genGponContainer.mi2
 -- Uses DIDs 0x6700 through 0x6C00

 -- genSubtendedHost.mi2
 -- Uses DIDs 0x6C01 through 0x6C1F
 -- Uses DIDs 0x6C40 through 0x6C5F

 -- genDslProxy.mi2
 -- Uses DIDs 0x6C20 through 0x6C3F

 -- genDhcpClient.mi2
 -- Uses DIDs 0xA42F through 0xA456

 -- TA5000 FXS Factory MIB
 -- no reserved DIDs
    adTa5kFxsFac         OBJECT IDENTIFIER ::= {adGenTa5kMgmt  35 }
    adTa5kFxsFacID       OBJECT IDENTIFIER ::= {adGenTa5kID    35 }

 -- TA5000 FXO Factory MIB
 -- no reserved DIDs
    adTa5kFxoFac         OBJECT IDENTIFIER ::= {adGenTa5kMgmt  36 }
    adTa5kFxoFacID       OBJECT IDENTIFIER ::= {adGenTa5kID    36 }

-- TA5000 ACS Server Profile
   adGenAcsServerProfile           OBJECT IDENTIFIER ::= { adGenTa5kMgmt 37  }
   adGenAcsServerProfileID         OBJECT IDENTIFIER ::= { adGenTa5kID   37  }

-- TA5000 P-bit Remapping
   adTa5kPbitRemapping             OBJECT IDENTIFIER ::= { adGenTa5kMgmt 38 }
   adTa5kPbitRemappingID           OBJECT IDENTIFIER ::= { adGenTa5kID 38 }

-- TA5000 Thermal Management
   adTa5kThermalManagement             OBJECT IDENTIFIER ::= { adGenTa5kMgmt 39 }
   adTa5kThermalManagementID           OBJECT IDENTIFIER ::= { adGenTa5kID 39 }
  END
