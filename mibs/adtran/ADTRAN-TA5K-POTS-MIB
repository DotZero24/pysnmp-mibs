ADTRAN-TA5K-POTS-MIB
    DEFINITIONS ::= BEGIN

    -- TITLE:     The ADTRAN Total Access 5000 POTS MIB
    -- PRODUCT:   1187100L1, 1187100L2, 1187150L1, and more (anything with POTS capability)
    -- VERSION:   1.3
    -- DATE:      11/05/08

    -- This MIB defines the management information for the POTS
    -- modules in a Total Access 5000 shelf.

    -- Revision History:
    --          11/05/2008      PSK - Updated enumeration for adTA5kPotsPortImpedance to include
    --                          recently added z1-z8 impedances. Added new provisioning item
    --                          adTA5kPotsPortAutoImpedanceMode.
    --          04/28/2009      PSK - Added new provisioning item adTA5kPotsPortRingVoltage for
    --                          changing the ringer voltage on the VDSL combo card. (And any future
    --                          cards with ringing SLICs.)
    --          08/06/2009      BCK - Conversion to V2 MIB
    -- DO NOT MAKE HISTORY COMMENTS HERE!!!! Revision history now in REVISION/DESCRIPTION clauses below


    IMPORTS

    OBJECT-TYPE,
    NOTIFICATION-TYPE,
    MODULE-IDENTITY,
    OBJECT-IDENTITY,
    Integer32
        FROM SNMPv2-SMI

    DisplayString, TruthValue
        FROM SNMPv2-TC

    sysName
        FROM SNMPv2-MIB

    ifIndex
        FROM IF-MIB

    adGenSlotInfoIndex,
    adGenSlotAlarmStatus
        FROM ADTRAN-GENSLOT-MIB

    adGenPortTrapIdentifier,
    adGenPortInfoIndex
        FROM ADTRAN-GENPORT-MIB

    adTrapInformSeqNum
        FROM ADTRAN-GENTRAPINFORM-MIB

    adProducts,
    adMgmt,
    adIdentity
        FROM ADTRAN-MIB
    ;
-- *********************************************************************************************************
  adTA5kPotsID MODULE-IDENTITY
   LAST-UPDATED "202201070000Z"
   ORGANIZATION "Adtran, Inc."
   CONTACT-INFO
     "CND Tech Support
         Postal: ADTRAN, Inc.
                 901 Explorer Blvd.
                 Huntsville, AL  35806
                 Tel: +1 800 726-8663
                 Fax: +1 256 963 6217
                 E-mail: support@adtran.com"
   DESCRIPTION
      "The is the MIB module that describes
       management information for the POTS.
       modules in a Total Access 5000 shelf"

   REVISION "202201070000Z"
   DESCRIPTION "Added 90 vrms as an option for adTA5kPotsPortRingVoltage."
   REVISION "201903210000Z"
   DESCRIPTION "Added adTA5kPotsPulseDigitDetectionEnable to allow the detection of pulse dial digits to be disabled."
   REVISION "201804020000Z"
   DESCRIPTION "Added support to access the description for FXS ports"
   REVISION "201801170000Z"
   DESCRIPTION "Added adTA5kPotsCardSelfTestLasVegas3Prog to support updates to the selftest->status page for the 48p RPOTS"
   REVISION "201709250000Z"
   DESCRIPTION "Added adTA5kPotsCardLineTestScheduleEnable, adTA5kPotsCardLoadCoilTestScheduleEnable, and adTA5kPotsCardLineTestScheduleTimeString to configure the scheduling of fxs line tests"
   REVISION "201612070000Z"
   DESCRIPTION "Added adTA5kPotsPortVoiceCallJitterBufferDepth, and adTA5kPotsPortFaxModemCallJitterBufferDepth to get and test the Jitter Buffer values"
   REVISION "201609080000Z"
   DESCRIPTION "Added adTA5kPotsPortMwiStatus, adTA5kPotsPortForceMwiOffEvent, and adTA5kPotsPortForceMwiOnEvent to get and test the status of the Message Waiting Indicator"
   REVISION "201603240000Z"
   DESCRIPTION "Added support for Message Waiting Indication Provisioning"
   REVISION "201603080000Z"
   DESCRIPTION "Added support for Over Temperature Alarm"
   REVISION "201509290000Z"
   DESCRIPTION "Added adTA5kPotsLineTestWarbleTone, adTA5kPotsLineTestWarbleToneFreq1, adTA5kPotsLineTestWarbleToneFreq2, and adTA5kPotsLineTestWarbleToneCadence oids
				to support the new warble tone feature."
   REVISION "201403060000Z"
   DESCRIPTION "Added adTA5kPotsPortImpedanceByLoopLength for setting impedances designated by short, medium, or long loop length; added related comment to adTA5kPotsPortImpedance.
   				Also added 85 vrms as an option for adTA5kPotsPortRingVoltage."
   REVISION "201303250000Z"
   DESCRIPTION "Added mgcp(3) enumeration to adTA5kPotsCardProvVoiceCallControl in order to maintain consistency with the CLI and Web GUI"
   REVISION "201108100000Z"
   DESCRIPTION "PSK - Added tipOpen(10) enumeration and some clarifying comments to adTA5kPotsLineTestLoopState"
      ::= {  adIdentity 753 }

-- ********************************************************************************************************


    -- OBJECT IDENTIFIERS

    -- adtran                     OBJECT IDENTIFIER        ::=  { enterprises 664         }
    -- adProducts                 OBJECT IDENTIFIER        ::=  { adtran 1                }
       adTA5kPots                 OBJECT IDENTIFIER        ::=  { adProducts 753          }
    -- adMgmt                     OBJECT IDENTIFIER        ::=  { adtran 2                }
       adTA5kPotsmg               OBJECT IDENTIFIER        ::=  { adMgmt 753              }
       adTA5kPotsProv             OBJECT IDENTIFIER        ::=  { adTA5kPotsmg 1          }
       adTA5kPotsStat             OBJECT IDENTIFIER        ::=  { adTA5kPotsmg 2          }
       adTA5kPotsTest             OBJECT IDENTIFIER        ::=  { adTA5kPotsmg 3          }
       adTA5kPotsAlarm            OBJECT IDENTIFIER        ::=  { adTA5kPotsmg 4          }
       adTA5kPotsAlarmEvents      OBJECT IDENTIFIER        ::=  { adTA5kPotsAlarm 0       }
    --
    -- The POTS Card-level provisioning group **************************************************************
    --

    adTA5kPotsCardProv        OBJECT IDENTIFIER ::= { adTA5kPotsProv 1 }

    adTA5kPotsCardProvTable OBJECT-TYPE
        SYNTAX  SEQUENCE OF AdTA5kPotsCardProvEntry
        MAX-ACCESS  not-accessible
        STATUS  current
        DESCRIPTION
            "The POTS Card-level Provisioning table."
        ::= { adTA5kPotsCardProv 1 }

    adTA5kPotsCardProvEntry  OBJECT-TYPE
        SYNTAX  AdTA5kPotsCardProvEntry
        MAX-ACCESS    not-accessible
        STATUS  current
        DESCRIPTION
            "An entry in the POTS Card-level Provisioning Table."
        INDEX    { adGenSlotInfoIndex }
            ::=  { adTA5kPotsCardProvTable 1 }

    AdTA5kPotsCardProvEntry ::= SEQUENCE {
        -- Card-level generic provisioning items
        adTA5kPotsCardProvRestoreFactoryDefaults        INTEGER,
        --    adTA5kPotsCardProvServiceState            INTEGER,

        -- Card-level POTS/Voice provisioning items
        -- adTA5kPotsCardProvVoiceCompandingLaw         INTEGER,
        adTA5kPotsCardProvVoiceCallControl              INTEGER,
        adTA5kPotsCardReboot                            INTEGER,
        adTA5kPotsCardRemoveBatteryInOosUas             INTEGER,
        adTA5kPotsCardProvLossOfTimingAlarm             INTEGER,
        adTA5kPotsCardProvAllAlarms                     INTEGER,
        adTA5kPotsCardLineTestScheduleEnable            INTEGER,
        adTA5kPotsCardLoadCoilTestScheduleEnable        INTEGER,
        adTA5kPotsCardLineTestScheduleTimeString        DisplayString
        }

     adTA5kPotsCardProvRestoreFactoryDefaults OBJECT-TYPE
         SYNTAX  INTEGER {
                         reset(1)
                         }
         MAX-ACCESS      read-write
         STATUS          current
         DESCRIPTION
            "A set command will reset the POTS card.  Get has
            no meaning and will always return 1."
         ::= { adTA5kPotsCardProvEntry 1 }

    -- adTA5kPotsCardProvServiceState OBJECT-TYPE
    --  SYNTAX  INTEGER {
    --                  is(1),
    --                  oosUAS(2),
    --                  oosMA(3)
    --                  }
    -- MAX-ACCESS       read-write
    -- STATUS           current
    -- DESCRIPTION
    --    "POTS card service state-
    --     1 = In Service
    --     2 = Out Of Service - Unassigned
    --     3 = Out Of Service - Maintenance"
    -- ::= { adTA5kPotsCardProvEntry 2 }


    -- adTA5kPotsCardProvVoiceCompandingLaw OBJECT-TYPE
    -- SYNTAX  INTEGER {
    --                 u-law(1),
    --                 a-law(2)
    --                 }
    -- MAX-ACCESS      read-write
    -- STATUS          current
    -- DESCRIPTION
    --    "The audio companding law used for all voice ports on this module -
    --            1 = u-law companding (North America, Japan)
    --            2 = A-law companding"
    -- ::= { adTA5kPotsCardProvEntry 2 }

    adTA5kPotsCardProvVoiceCallControl OBJECT-TYPE
        SYNTAX  INTEGER {
                        tunneledGR303(1),
                        ccSip(2),
                        mgcp(3)
                        }
        MAX-ACCESS     read-write
        STATUS         current
        DESCRIPTION
            "The call-control protocol for all voice ports on this module -
                1 = FXS Signaling (This is the same as tunneledGR303 in the syntax)
                2 = ccSip
                3 = MGCP"
        ::= { adTA5kPotsCardProvEntry 2 }

    adTA5kPotsCardReboot OBJECT-TYPE
        SYNTAX  INTEGER {
                         reboot(1)
                        }
        MAX-ACCESS      read-write
        STATUS          current
        DESCRIPTION
            "This field sets the card into boot mode
                1 = Reboot"
        ::= { adTA5kPotsCardProvEntry 3 }

    adTA5kPotsCardRemoveBatteryInOosUas OBJECT-TYPE
        SYNTAX  INTEGER {
                        yes(1),
                        no(2)
                        }
        MAX-ACCESS      read-write
        STATUS          current
        DESCRIPTION
            "Remove CO battery from loop when a port is set to Out of Service - Unassigned.
             This typically only applies to Combo ADSL/POTS units.
                1 = Yes
                2 = No"
        ::= { adTA5kPotsCardProvEntry 4 }

    adTA5kPotsCardProvLossOfTimingAlarm OBJECT-TYPE
        SYNTAX  INTEGER {
                        enable(1),
                        disable(2)
                        }
        MAX-ACCESS      read-write
        STATUS          current
        DESCRIPTION
            "Provisioning for Loss Of Timing Alarm which is a card level alarm.
                1 = Enable
                2 = Disable"
        ::= { adTA5kPotsCardProvEntry 5 }

    adTA5kPotsCardProvAllAlarms OBJECT-TYPE
        SYNTAX  INTEGER {
                        enable(1),
                        disable(2)
                        }
        MAX-ACCESS      read-write
        STATUS          current
        DESCRIPTION
            "Provisioning for All Alarms (Card and Port Level).
                1 = Enable
                2 = Disable"
        ::= { adTA5kPotsCardProvEntry 6 }
    adTA5kPotsCardLineTestScheduleEnable OBJECT-TYPE
        SYNTAX  INTEGER {
                        enable(1),
                        disable(2)
                        }
        MAX-ACCESS      read-write
        STATUS          current
        DESCRIPTION
            "Enable/Disable scheduled Fxs Line Tests.
            If enabled, the card will run a GR-909 line test on each applicable fxs port at the time of day set by the adTA5kPotsCardLineTestScheduleTimeString oid.
            If disabled, the card will not run any scheduled line tests.
                1 = enable
                2 = disable"
        DEFVAL { enable }
        ::= { adTA5kPotsCardProvEntry 7 }

    adTA5kPotsCardLoadCoilTestScheduleEnable OBJECT-TYPE
        SYNTAX  INTEGER {
                        enable(1),
                        disable(2)
                        }
        MAX-ACCESS      read-write
        STATUS          current
        DESCRIPTION
            "Enable/Disable scheduled Fxs Load Coil Tests.
            If enabled, the card will run the load coil detection tests in addition to the GR-909 line tests at the time of day set by the adTA5kPotsCardLineTestScheduleTimeString oid.
            If disabled, the card will not run the load coil detection tests.
            If adTA5kPotsCardLineTestScheduleEnable is disabled, then this oid has no effect.
                1 = enable
                2 = disable"
        DEFVAL { disable }
        ::= { adTA5kPotsCardProvEntry 8 }

    adTA5kPotsCardLineTestScheduleTimeString OBJECT-TYPE
        SYNTAX         DisplayString (SIZE(5))
        MAX-ACCESS     read-write
        STATUS         current
        DESCRIPTION
            "Set the scheduled start time of the Line Tests in 24 Hour Format HH:MM.
            If adTA5kPotsCardLineTestScheduleEnable is disabled, then this oid has no effect."
        DEFVAL { "02:00" }
        ::= { adTA5kPotsCardProvEntry 9 }
    --
        -- The POTS Port-level provisioning group ****************************************************************
        --

    adTA5kPotsPortProv        OBJECT IDENTIFIER ::= { adTA5kPotsProv 2 }

    adTA5kPotsPortProvTable OBJECT-TYPE
        SYNTAX        SEQUENCE OF AdTA5kPotsPortProvEntry
        MAX-ACCESS    not-accessible
        STATUS        current
        DESCRIPTION
            "The POTS Port-level Provisioning table."
        ::= { adTA5kPotsPortProv 1 }

    adTA5kPotsPortProvEntry  OBJECT-TYPE
        SYNTAX        AdTA5kPotsPortProvEntry
        MAX-ACCESS    not-accessible
        STATUS        current
        DESCRIPTION
            "An entry in the POTS Port-level Provisioning Table."
        INDEX    { ifIndex }
            ::=  { adTA5kPotsPortProvTable 1 }

    AdTA5kPotsPortProvEntry ::= SEQUENCE {
        -- Line-level POTS provisioning items
        adTA5kPotsPortMode                          INTEGER,
        adTA5kPotsPortImpedance                     INTEGER,
        adTA5kPotsPortTXTLPString                   DisplayString,
        adTA5kPotsPortRXTLPString                   DisplayString,
        adTA5kPotsPortOnHookMsg                     INTEGER,
        -- adTA5kPotsPortServiceState               INTEGER,
        adTA5kPotsPortTrunkConditioningAlarm        INTEGER,
        adTA5kPotsPortLineShoweringAlarm            INTEGER,
        adTA5kPotsPortAutoImpedanceMode             INTEGER,
        adTA5kPotsPortRingVoltage                   INTEGER,
        adTA5kPotsPortImpedanceByLoopLength         INTEGER,
        adTA5kPotsPortOverTempAlarmEnable           INTEGER,

        adTA5kPotsPortMwiType                       INTEGER,
        adTA5kPotsPortNeonMwiCadence                INTEGER,
        adTA5kPotsPortNeonMwiVoltage                INTEGER,
        adTA5kPotsPortVoiceCallJitterBufferDepth    Integer32,
        adTA5kPotsPortFaxModemCallJitterBufferDepth Integer32,
        adTA5kPotsPortCircuitIdentifier             DisplayString,
        adTA5kPotsPulseDigitDetectionEnable         TruthValue
        }

    adTA5kPotsPortMode OBJECT-TYPE
        SYNTAX  INTEGER {
                       loopStart(1),
                       groundStart(2),
                       tr08SingleParty(3),
                       tr08Uvg(4)
                       }
        MAX-ACCESS     read-write
        STATUS         current
        DESCRIPTION
            "POTS port operational Mode -
                1 = Loopstart
                2 = Groundstart
                3 = TR08 Single Party
                4 = TR08 UVG"
        ::= { adTA5kPotsPortProvEntry 1 }

-- Note: ohm900(2) and ohm600Plus216uF(3) are no longer supported by the product.
-- Setting a port to either of these values will, in fact, change the port to ohm900Plus216uF(4).
-- Note: This oid becomes read-only if product uses feature ID 145 (setting impedance by loop length)
    adTA5kPotsPortImpedance OBJECT-TYPE
        SYNTAX  INTEGER {
                       ohm600(1),
                       ohm900(2),
                       ohm600Plus216uF(3),
                       ohm900Plus216uF(4),
                       ohmz1(5),
                       ohmz2(6),
                       ohmz3(7),
                       ohmz4(8),
                       ohmz5(9),
                       ohmz6(10),
                       ohmz7(11),
                       ohmz8(12)
                       }
        MAX-ACCESS     read-write
        STATUS         current
        DESCRIPTION
            "POTS port 2-wire termination impedance -
              1 = 600 Ohms
              2,3 are no longer supported
              4 = 900 Ohms + 2.16 uF
              5 = z1 - 220 + (820 // 115nF)
              6 = z2 - 270 + (750 // 150nF)
              7 = z3 - 270 + (750 // 150nF), Zin = 600r
              8 = z4 - 320 + (1050 // 230nF)
              9 = z5 - 350 + (1000 // 210nF), Zin = 600r
              10 = z6 - 370 + (620 // 310nF)
              11 = z7 - 800 // (100 + 50nF), Zin = 900c
              12 = z8 - 1650 // (100 + 5nF), Zin = 900c"
        ::= { adTA5kPotsPortProvEntry 2 }

    adTA5kPotsPortTXTLPString OBJECT-TYPE
        SYNTAX         DisplayString (SIZE(0..4))
        MAX-ACCESS     read-write
        STATUS         current
        DESCRIPTION
            "POTS Port Transmit TLP -9.0dB to +6.0dB"
        ::= { adTA5kPotsPortProvEntry 3 }

    adTA5kPotsPortRXTLPString OBJECT-TYPE
        SYNTAX         DisplayString (SIZE(0..4))
        MAX-ACCESS     read-write
        STATUS         current
        DESCRIPTION
            "POTS Port Receive TLP -10.0dB to +6.0dB"
        ::= { adTA5kPotsPortProvEntry 4 }

    adTA5kPotsPortOnHookMsg OBJECT-TYPE
        SYNTAX  INTEGER {
                       enable(1),
                       disable(2)
                       }
        MAX-ACCESS     read-write
        STATUS         current
        DESCRIPTION
            "POTS Port On-Hook Messaging -
                1 = Enable
                2 = Disable"
        ::= { adTA5kPotsPortProvEntry 5 }

       --    adTA5kPotsPortServiceState OBJECT-TYPE
       --    SYNTAX  INTEGER {
       --                    is(1),
       --                    oosUAS(2),
       --                    oosMA(3)
       --                    }
       --    MAX-ACCESS     read-write
       --    STATUS         current
       --    DESCRIPTION
       --     "POTS port service state-
       --             1 = In Service
       --             2 = Out Of Service - Unassigned
       --             3 = Out Of Service - Maintenance"
       --    ::= { adTA5kPotsPortProvEntry 6 }

    adTA5kPotsPortTrunkConditioningAlarm OBJECT-TYPE
        SYNTAX  INTEGER {
                        enable(1),
                        disable(2)
                        }
        MAX-ACCESS      read-write
        STATUS          current
        DESCRIPTION
            "Provisioning for Enable/Disable Trunk Conditioning Alarm which is a port level alarm.
            1 = Enable
            2 = Disable"
        ::= { adTA5kPotsPortProvEntry 6 }

    adTA5kPotsPortLineShoweringAlarm OBJECT-TYPE
        SYNTAX  INTEGER {
                         enable(1),
                         disable(2)
                        }
        MAX-ACCESS     read-write
        STATUS         current
        DESCRIPTION
            "Provisioning for Enable/Disable Line Showering Alarm which is a port level alarm.
            1 = Enable
            2 = Disable"
        ::= { adTA5kPotsPortProvEntry 7 }

    adTA5kPotsPortAutoImpedanceMode OBJECT-TYPE
        SYNTAX  INTEGER {
                         manual(1),
                         automatic(2)
                        }
        MAX-ACCESS     read-write
        STATUS         current
        DESCRIPTION
            "POTS Automatic Impedance Mode -
                1 = Manual
              2 = Automatic"
        ::= { adTA5kPotsPortProvEntry 8 }

-- Note this is only supported by products with an internal ringing SLIC chip. Also the setting "eightyFive" is only valid
-- for products that support feature ID 146.  The setting "ninety" is only valid for products that support feature ID 221.
    adTA5kPotsPortRingVoltage OBJECT-TYPE
        SYNTAX  INTEGER {
                        fifty(1),
                        sixty(2),
                        seventy(3),
                        eighty(4),
                        eightyFive(5),
                        ninety(6)
                        }
        MAX-ACCESS     read-write
        STATUS         current
        DESCRIPTION
            "POTS Ringer Voltage -
                1 = 50 Vrms
                2 = 60 Vrms
                3 = 70 Vrms
                4 = 80 Vrms
                5 = 85 Vrms
                6 = 90 Vrms"
		DEFVAL { seventy }
        ::= { adTA5kPotsPortProvEntry 9 }

    adTA5kPotsPortImpedanceByLoopLength OBJECT-TYPE
        SYNTAX  INTEGER {
                        loopLengthOther(1),
                        loopLengthShort(2),
                        loopLengthMedium(3),
                        loopLengthLong(4)
                        }
        MAX-ACCESS     read-write
        STATUS         current
        DESCRIPTION
            "POTS port 2-wire termination impedance by loop length-
            1 = Other - The impedance matches one of the values defined by adTA5kPotsPortImpedance that
            can not be accurately represented by the values used in this oid. This value is read-only.
            2 = Short loop length(< 2.5kft)
            3 = Medium loop length (<7.5kft)
            4 = Long loop length"
	    	DEFVAL { loopLengthShort }
        ::= { adTA5kPotsPortProvEntry 10 }

    adTA5kPotsPortOverTempAlarmEnable OBJECT-TYPE
        SYNTAX  INTEGER {
                        enable(1),
                        disable(2)
                        }
        MAX-ACCESS      read-write
        STATUS          current
        DESCRIPTION
            "Provisioning for Enable/Disable Over Temperature Alarm which is a port level alarm.
            1 = Enable
            2 = Disable"
	    	DEFVAL { enable }
        ::= { adTA5kPotsPortProvEntry 11 }

    adTA5kPotsPortMwiType OBJECT-TYPE
        SYNTAX  INTEGER {
                        mwiTypeFsk(1),
                        mwiTypeNeon(2)
                        }
        MAX-ACCESS      read-write
        STATUS          current
        DESCRIPTION
            "Provisioning for the type of Message Waiting Indication for this port to use.
            1 = Use Frequency Shift Keying (FSK) to indicate Message Waiting to the phone
            2 = Use Neon Voltage to indicate Message Waiting to the phone"
            DEFVAL { mwiTypeFsk }
        ::= { adTA5kPotsPortProvEntry 12 }

    adTA5kPotsPortNeonMwiCadence OBJECT-TYPE
        SYNTAX  INTEGER {
                        neonMwiCadence1000ms(1),
                        neonMwiCadence500ms(2),
                        neonMwiCadence250ms(3)
                        }
        MAX-ACCESS      read-write
        STATUS          current
        DESCRIPTION
            "Provisioning for the flashing cadence of Neon Message Waiting Indication for this port.
            1 = Flash the Neon lamp on or off every 1000ms
            2 = Flash the Neon lamp on or off every 500ms
            3 = Flash the Neon lamp on or off every 250ms"
            DEFVAL { neonMwiCadence1000ms }
        ::= { adTA5kPotsPortProvEntry 13 }

    adTA5kPotsPortNeonMwiVoltage OBJECT-TYPE
        SYNTAX  INTEGER {
                        neonMwiVoltage85volts(1),
                        neonMwiVoltage90volts(2),
                        neonMwiVoltage100volts(3),
                        neonMwiVoltage110volts(4),
                        neonMwiVoltage120volts(5),
                        neonMwiVoltage130volts(6)
                        }
        MAX-ACCESS      read-write
        STATUS          current
        DESCRIPTION
            "Provisioning for the voltage of Neon Message Waiting Indication for this port.
            1 = 85 volts
            2 = 90 volts
            3 = 100 volts
            4 = 110 volts
            5 = 120 volts
            6 = 130 volts"
            DEFVAL { neonMwiVoltage90volts }
        ::= { adTA5kPotsPortProvEntry 14 }

    adTA5kPotsPortVoiceCallJitterBufferDepth OBJECT-TYPE
        SYNTAX  Integer32(0..250)
        MAX-ACCESS      read-write
        STATUS          current
        DESCRIPTION
            "Provisioning for the Jitter Buffer Depth used for Voice Calls in mS"
            DEFVAL { 10 }
        ::= { adTA5kPotsPortProvEntry 15 }

    adTA5kPotsPortFaxModemCallJitterBufferDepth OBJECT-TYPE
        SYNTAX  Integer32 (0..250)
        MAX-ACCESS      read-write
        STATUS          current
        DESCRIPTION
            "Provisioning for the Jitter Buffer Depth used for Fax Modem Calls in mS"
            DEFVAL { 80 }
        ::= { adTA5kPotsPortProvEntry 16 }

    adTA5kPotsPortCircuitIdentifier OBJECT-TYPE
        SYNTAX      DisplayString (SIZE (0..40))
        MAX-ACCESS  read-write
        STATUS      current
        DESCRIPTION
            "The circuit identifier string for the fxs port."
        ::= { adTA5kPotsPortProvEntry 17 }

    adTA5kPotsPulseDigitDetectionEnable OBJECT-TYPE
        SYNTAX       TruthValue
        MAX-ACCESS   read-write
        STATUS       current
        DESCRIPTION
          "This entry is used to enable or disable the pulse dial digit detection for this port.
           This entry only applies to fxs ports that are connected to a VoIP service, such as SIP or MGCP.
           If set to true, then pulse dial digits will be detected from the loop and reported to the voice switch.
           If set to false, then pulse dial digits will be ignored and will not be reported to the voice switch.
           This object is true by default."
        DEFVAL     { true }
        ::= { adTA5kPotsPortProvEntry 18 }
    --
        -- The POTS Card-level status group **********************************************************************

        --

    adTA5kPotsCardStat        OBJECT IDENTIFIER ::= { adTA5kPotsStat 1 }

    adTA5kPotsCardStatTable OBJECT-TYPE
           SYNTAX      SEQUENCE OF AdTA5kPotsCardStatEntry
        MAX-ACCESS     not-accessible
        STATUS         current
        DESCRIPTION
            "The POTS Card-level Status table."
        ::= { adTA5kPotsCardStat 1 }

    adTA5kPotsCardStatEntry  OBJECT-TYPE
        SYNTAX        AdTA5kPotsCardStatEntry
        MAX-ACCESS    not-accessible
        STATUS        current
        DESCRIPTION
            "An entry in the POTS Card-level Status Table."
        INDEX    { adGenSlotInfoIndex }
            ::=  { adTA5kPotsCardStatTable 1 }

    AdTA5kPotsCardStatEntry ::= SEQUENCE {
    -- Card-level status items
    adTA5kPotsCardSelfTestFPGATest                   INTEGER,
    adTA5kPotsCardSelfTestFlashTest                  INTEGER,
    adTA5kPotsCardSelfTestLasVegas1Prog              INTEGER,
    adTA5kPotsCardSelfTestLasVegas2Prog              INTEGER,
    adTA5kPotsCardSelfTestVineticCodecAProg          INTEGER,
    adTA5kPotsCardSelfTestVineticCodecBProg          INTEGER,
    adTA5kPotsCardSelfTestVineticCodecCProg          INTEGER,
    adTA5kPotsCardSelfTestVineticCodecDProg          INTEGER,
    adTA5kPotsCardSelfTestVineticCodecEProg          INTEGER,
    adTA5kPotsCardSelfTestVineticCodecFProg          INTEGER,
    adTA5kPotsCardSelfTestLasVegas3Prog              INTEGER
    }

  adTA5kPotsCardSelfTestFPGATest OBJECT-TYPE
    SYNTAX        INTEGER {
                          failed(1),
                          passed(2)
                          }
        MAX-ACCESS        read-only
        STATUS            current
        DESCRIPTION
                "This variable indicates the Self-test FPGA Test Status of the module.
                1 = FAILED
                2 = PASSED"
        ::= { adTA5kPotsCardStatEntry 1 }

    adTA5kPotsCardSelfTestFlashTest OBJECT-TYPE
    SYNTAX        INTEGER {
                          failed(1),
                          passed(2)
                          }
        MAX-ACCESS        read-only
        STATUS            current
        DESCRIPTION
                "This variable indicates the Self-test FPGA Flash Test Status of the module.
                1 = FAILED
                2 = PASSED"
        ::= { adTA5kPotsCardStatEntry 2 }

    adTA5kPotsCardSelfTestLasVegas1Prog OBJECT-TYPE
    SYNTAX        INTEGER {
                          failed(1),
                          passed(2)
                          }
        MAX-ACCESS        read-only
        STATUS            current
        DESCRIPTION
                "This variable indicates the Self-test Las Vegas #1 Programming Status of the module.
                1 = FAILED
                2 = PASSED"
        ::= { adTA5kPotsCardStatEntry 3 }

    adTA5kPotsCardSelfTestLasVegas2Prog OBJECT-TYPE
    SYNTAX        INTEGER {
                          failed(1),
                          passed(2)
                          }
        MAX-ACCESS        read-only
        STATUS            current
        DESCRIPTION
                "This variable indicates the Self-test Las Vegas #2 Programming Status of the module.
                1 = FAILED
                2 = PASSED"
        ::= { adTA5kPotsCardStatEntry 4 }

    adTA5kPotsCardSelfTestVineticCodecAProg OBJECT-TYPE
    SYNTAX        INTEGER {
                          failed(1),
                          passed(2)
                          }
        MAX-ACCESS        read-only
        STATUS            current
        DESCRIPTION
                "This variable indicates the Self-test Vinetic Codec A Programming Status of the module.
                1 = FAILED
                2 = PASSED"
        ::= { adTA5kPotsCardStatEntry 5 }

    adTA5kPotsCardSelfTestVineticCodecBProg OBJECT-TYPE
    SYNTAX        INTEGER {
                          failed(1),
                          passed(2)
                          }
        MAX-ACCESS        read-only
        STATUS            current
        DESCRIPTION
                "This variable indicates the Self-test Vinetic Codec B Programming Status of the module.
                1 = FAILED
                2 = PASSED"
        ::= { adTA5kPotsCardStatEntry 6 }

    adTA5kPotsCardSelfTestVineticCodecCProg OBJECT-TYPE
    SYNTAX        INTEGER {
                          failed(1),
                          passed(2)
                          }
        MAX-ACCESS        read-only
        STATUS            current
        DESCRIPTION
                "This variable indicates the Self-test Vinetic Codec C Programming Status of the module.
                1 = FAILED
                2 = PASSED"
        ::= { adTA5kPotsCardStatEntry 7 }

    adTA5kPotsCardSelfTestVineticCodecDProg OBJECT-TYPE
    SYNTAX        INTEGER {
                          failed(1),
                          passed(2)
                          }
        MAX-ACCESS        read-only
        STATUS            current
        DESCRIPTION
                "This variable indicates the Self-test Vinetic Codec D Programming Status of the module.
                1 = FAILED
                2 = PASSED"
        ::= { adTA5kPotsCardStatEntry 8 }

    adTA5kPotsCardSelfTestVineticCodecEProg OBJECT-TYPE
    SYNTAX        INTEGER {
                          failed(1),
                          passed(2)
                          }
        MAX-ACCESS        read-only
        STATUS            current
        DESCRIPTION
                "This variable indicates the Self-test Vinetic Codec E Programming Status of the module.
                1 = FAILED
                2 = PASSED"
        ::= { adTA5kPotsCardStatEntry 9 }

     adTA5kPotsCardSelfTestVineticCodecFProg OBJECT-TYPE
    SYNTAX        INTEGER {
                          failed(1),
                          passed(2)
                          }
        MAX-ACCESS        read-only
        STATUS            current
        DESCRIPTION
                "This variable indicates the Self-test Vinetic Codec F Programming Status of the module.
                1 = FAILED
                2 = PASSED"
        ::= { adTA5kPotsCardStatEntry 10 }

        adTA5kPotsCardSelfTestLasVegas3Prog OBJECT-TYPE
    SYNTAX        INTEGER {
                          failed(1),
                          passed(2)
                          }
        MAX-ACCESS        read-only
        STATUS            current
        DESCRIPTION
                "This variable indicates the Self-test Las Vegas #3 Programming Status of the module.
                1 = FAILED
                2 = PASSED"
        ::= { adTA5kPotsCardStatEntry 11 }
        --
        -- The POTS Line-level status group **********************************************************************
        --

    adTA5kPotsPortStat        OBJECT IDENTIFIER ::= { adTA5kPotsStat 2 }

    adTA5kPotsPortStatTable OBJECT-TYPE
           SYNTAX      SEQUENCE OF AdTA5kPotsPortStatEntry
        MAX-ACCESS     not-accessible
        STATUS         current
        DESCRIPTION
            "The POTS Port-level Status table."
        ::= { adTA5kPotsPortStat 1 }

    adTA5kPotsPortStatEntry  OBJECT-TYPE
        SYNTAX         AdTA5kPotsPortStatEntry
        MAX-ACCESS     not-accessible
        STATUS         current
        DESCRIPTION
            "An entry in the POTS Port-level Status Table."
        INDEX    { ifIndex }
            ::=  { adTA5kPotsPortStatTable 1 }

    AdTA5kPotsPortStatEntry ::= SEQUENCE {
        -- Port-level status items
        adTA5kPotsPortStatLineMode              INTEGER,
        adTA5kPotsPortStatLineActive            INTEGER,
        adTA5kPotsPortStatLineCompression       INTEGER,
        adTA5kPotsPortStatLoopFeed              INTEGER,
        adTA5kPotsPortStatLoopState             INTEGER,
        adTA5kPotsPortStatTestActive            INTEGER,
        adTA5kPotsPortStatServiceState          INTEGER,
        adTA5kPotsPortMwiStatus                 INTEGER
        }

    adTA5kPotsPortStatLineMode OBJECT-TYPE
       SYNTAX  INTEGER {
                        loopStart(1),
                        groundStart(2)
                       }
        MAX-ACCESS     read-only
        STATUS         current
        DESCRIPTION
            "This item indicates which mode the port is currently operating in.
                1 = Loop Start
                2 = Ground Start"
        ::= { adTA5kPotsPortStatEntry 1 }

    adTA5kPotsPortStatLineActive OBJECT-TYPE
       SYNTAX  INTEGER {
                       active(1),
                       inActive(2)
                       }
        MAX-ACCESS     read-only
        STATUS         current
        DESCRIPTION
            "This item indicates whether the port is currently active or not.
                1 = Active
                2 = Not Active"
        ::= { adTA5kPotsPortStatEntry 2 }

    adTA5kPotsPortStatLineCompression OBJECT-TYPE
        SYNTAX  INTEGER {
                        g711(1),
                        g726(2)
                        }
        MAX-ACCESS      read-only
        STATUS          current
        DESCRIPTION
            "This item indicates which type of compression is being used.
                1 = G.711
                2 = G.726"
        ::= { adTA5kPotsPortStatEntry 3 }

    adTA5kPotsPortStatLoopFeed OBJECT-TYPE
       SYNTAX  INTEGER  {
                        lcf(1),
                        rlcf(2),
                        osi(3),
                        tipGround(4),
                        ringing(5),
                        powerDown(6)
                        }
        MAX-ACCESS      read-only
        STATUS          current
        DESCRIPTION
            "This item indicates the loop feed status of the port.
                1 = Loop Current Feed
                2 = Reverse Loop Current Feed
                3 = OSI
                4 = Tip Ground
                5 = Ringing
                6 = Power Down"
        ::= { adTA5kPotsPortStatEntry 4 }

    adTA5kPotsPortStatLoopState OBJECT-TYPE
        SYNTAX  INTEGER {
                        loopOpen(1),
                         loopClosed(2),
                         ringGround(3)
                         }
        MAX-ACCESS      read-only
        STATUS          current
        DESCRIPTION
            "This item indicates the loop state of the port.
                1 = Loop Open
                2 = Loop Closed
                3 = Ring Ground"
        ::= { adTA5kPotsPortStatEntry 5 }

    adTA5kPotsPortStatTestActive OBJECT-TYPE
        SYNTAX  INTEGER {
                        yes(1),
                        no(2)
                        }
        MAX-ACCESS      read-only
        STATUS          current
        DESCRIPTION
            "This item indicates whether a test is active on the port or not.
                1 = Active
                2 = Not Active"
        ::= { adTA5kPotsPortStatEntry 6 }

    adTA5kPotsPortStatServiceState OBJECT-TYPE
        SYNTAX  INTEGER {
                        is(1),
                        oosUAS(2),
                        oosMA(3)
                       }
        MAX-ACCESS     read-only
        STATUS         current
        DESCRIPTION
            "POTS port service state-
             1 = In Service
             2 = Out Of Service - Unassigned
             3 = Out Of Service - Maintenance"
        ::= { adTA5kPotsPortStatEntry 7 }

    adTA5kPotsPortMwiStatus OBJECT-TYPE
        SYNTAX  INTEGER {
                        unknown(1),
                        indicatorOff(2),
                        indicatorOn(3),
                        indicatorOffForced(4),
                        indicatorOnForced(5)
                        }
        MAX-ACCESS     read-only
        STATUS         current
        DESCRIPTION
            "POTS MWI Status -
                1 = Status Unknown
                2 = Indicator OFF
                3 = Indicator ON
                4 = Indicator OFF (forced)
                5 = Indicator ON (forced)
                Note: unknown will always be returned in FXS Signaling mode.
                This is because a FXS Signaling port has no knowledge of MWI events as they are generated by the voice switch
                and passed through the port transparently"
        ::= { adTA5kPotsPortStatEntry 8 }
    --
        -- The POTS Statistics **********************************************************************
        --

    adTA5kPotsStatistics        OBJECT IDENTIFIER ::= { adTA5kPotsStat 3 }



    --
        -- The POTS card-level Statistics group **********************************************************************
        --

    adTA5kPotscardStatistics    OBJECT IDENTIFIER ::=    { adTA5kPotsStatistics 1 }

    adTA5kPotscardStatisticsTable OBJECT-TYPE
        SYNTAX      SEQUENCE OF AdTA5kPotscardStatisticsEntry
        MAX-ACCESS  not-accessible
        STATUS      current
        DESCRIPTION
            "The POTS card-level Statistics table."
        ::= { adTA5kPotscardStatistics 1 }

    adTA5kPotscardStatisticsEntry  OBJECT-TYPE
        SYNTAX        AdTA5kPotscardStatisticsEntry
        MAX-ACCESS    not-accessible
        STATUS        current
        DESCRIPTION
            "An entry in the POTS card-level Statistics Table."
        INDEX    { adGenSlotInfoIndex  }
            ::=  { adTA5kPotscardStatisticsTable 1 }

    AdTA5kPotscardStatisticsEntry ::= SEQUENCE {
        -- POTS-card Statistics entry
        adTA5kPotsCardRXEthernetPkts             Integer32,
        adTA5kPotsCardTXEthernetPkts             Integer32,
        adTA5kPotsCardVoiceGatewayTimeouts       Integer32,
        adTA5kPotsCardClearStatistics            Integer32,
        adTA5kPotsPortClearStatistics            Integer32
        }

    adTA5kPotsCardRXEthernetPkts OBJECT-TYPE
        SYNTAX          Integer32
        MAX-ACCESS      read-only
        STATUS          current
        DESCRIPTION
            "This will give the number of Received ethernet packets"
        ::= { adTA5kPotscardStatisticsEntry 1 }

    adTA5kPotsCardTXEthernetPkts OBJECT-TYPE
        SYNTAX          Integer32
        MAX-ACCESS      read-only
        STATUS          current
        DESCRIPTION
            "This will give the number of transmitted ethernet packets"
        ::= { adTA5kPotscardStatisticsEntry 2 }

    adTA5kPotsCardVoiceGatewayTimeouts OBJECT-TYPE
        SYNTAX          Integer32
        MAX-ACCESS      read-only
        STATUS          current
        DESCRIPTION
            "This will give the voice gateway timeouts"
        ::= { adTA5kPotscardStatisticsEntry 3 }

    adTA5kPotsCardClearStatistics OBJECT-TYPE
        SYNTAX          Integer32
        MAX-ACCESS      read-write
        STATUS          current
        DESCRIPTION
            "This will clear all the card level statistics when set to 1. A get will always return a 1.
        1 = Clear "
        ::= { adTA5kPotscardStatisticsEntry 4 }

    adTA5kPotsPortClearStatistics OBJECT-TYPE
        SYNTAX          Integer32
        MAX-ACCESS      read-write
        STATUS          current
        DESCRIPTION
            "This will clear all Port level statistics when set to 1. A get will always return a 1.
        1 = Clear "
        ::= { adTA5kPotscardStatisticsEntry 5 }

    --
        -- The POTS Port-level Statistics group **********************************************************************
        --

    adTA5kPotsPortStatistics    OBJECT IDENTIFIER ::=    { adTA5kPotsStatistics 2 }

    adTA5kPotsPortStatisticsTable OBJECT-TYPE
        SYNTAX      SEQUENCE OF AdTA5kPotsPortStatisticsEntry
        MAX-ACCESS  not-accessible
        STATUS      current
        DESCRIPTION
            "The POTS port-level Statistics table."
        ::= { adTA5kPotsPortStatistics 1 }

    adTA5kPotsPortStatisticsEntry  OBJECT-TYPE
        SYNTAX        AdTA5kPotsPortStatisticsEntry
        MAX-ACCESS    not-accessible
        STATUS        current
        DESCRIPTION
            "An entry in the POTS port-level Statistics Table."
        INDEX    { ifIndex  }
            ::=  { adTA5kPotsPortStatisticsTable 1 }

    AdTA5kPotsPortStatisticsEntry ::= SEQUENCE {
        -- POTS-port Statistics entry
        adTA5kPotsPortRXVoicePkts             Integer32,
        adTA5kPotsPortTXVoicePkts             Integer32,
        adTA5kPotsPortRXSignalPkts            Integer32,
        adTA5kPotsPortTXSignalPkts            Integer32
        }

    adTA5kPotsPortRXVoicePkts OBJECT-TYPE
        SYNTAX          Integer32
        MAX-ACCESS      read-only
        STATUS           current
        DESCRIPTION
            "This will give the number of Received Voice packets"
        ::= { adTA5kPotsPortStatisticsEntry 1 }

    adTA5kPotsPortTXVoicePkts OBJECT-TYPE
        SYNTAX          Integer32
        MAX-ACCESS      read-only
        STATUS          current
        DESCRIPTION
            "This will give the number of transmitted Voice packets"
        ::= { adTA5kPotsPortStatisticsEntry 2 }

    adTA5kPotsPortRXSignalPkts OBJECT-TYPE
        SYNTAX          Integer32
        MAX-ACCESS      read-only
        STATUS          current
        DESCRIPTION
            "This will give the number of Received signal packets"
        ::= { adTA5kPotsPortStatisticsEntry 3 }

    adTA5kPotsPortTXSignalPkts OBJECT-TYPE
        SYNTAX          Integer32
        MAX-ACCESS      read-only
        STATUS          current
        DESCRIPTION
            "This will give the number of transmitted signal packets"
        ::= { adTA5kPotsPortStatisticsEntry 4 }

    --
        -- The POTS Card-level Test group ************************************************************************
        --

    adTA5kPotsCardTest        OBJECT IDENTIFIER ::= { adTA5kPotsTest 1 }

    adTA5kPotsCardTestTable OBJECT-TYPE
        SYNTAX          SEQUENCE OF AdTA5kPotsCardTestEntry
        MAX-ACCESS      not-accessible
        STATUS          current
        DESCRIPTION
            "The POTS Card-level Test table."
        ::= { adTA5kPotsCardTest 1 }

    adTA5kPotsCardTestEntry  OBJECT-TYPE
        SYNTAX        AdTA5kPotsCardTestEntry
        MAX-ACCESS    not-accessible
        STATUS        current
        DESCRIPTION
            "An entry in the POTS Card-level Test Table."
        INDEX    { adGenSlotInfoIndex }
            ::=  { adTA5kPotsCardTestTable 1 }

    AdTA5kPotsCardTestEntry ::= SEQUENCE {
        -- Card-level test items
        adTA5kPotsCardTestLpbkPotsLine           INTEGER,
        adTA5kPotsCardTestLpbkPotsPayload        INTEGER
        }

    adTA5kPotsCardTestLpbkPotsLine OBJECT-TYPE
        SYNTAX  INTEGER {
                        enable(1),
                        disable(2)
                        }
        MAX-ACCESS      read-write
        STATUS          current
        DESCRIPTION
            "This item enables/disables the POTS line loopback toward the network.
                1 = Enable
                2 = Disable"
        ::= { adTA5kPotsCardTestEntry 1 }

    adTA5kPotsCardTestLpbkPotsPayload OBJECT-TYPE
        SYNTAX  INTEGER {
                        enable(1),
                        disable(2)
                        }
        MAX-ACCESS      read-write
        STATUS          current
        DESCRIPTION
            "This item enables/disables the POTS payload loopback toward
                the network.
                1 = Enable
                2 = Disable"
        ::= { adTA5kPotsCardTestEntry 2 }

      --
        -- The POTS Line-level Test group ************************************************************************
        --

    adTA5kPotsLineTest        OBJECT IDENTIFIER ::= { adTA5kPotsTest 2 }

    adTA5kPotsLineTestTable OBJECT-TYPE
        SYNTAX      SEQUENCE OF AdTA5kPotsLineTestEntry
        MAX-ACCESS  not-accessible
        STATUS      current
        DESCRIPTION
            "The POTS Line-level Test table."
        ::= { adTA5kPotsLineTest 1 }

    adTA5kPotsLineTestEntry  OBJECT-TYPE
        SYNTAX        AdTA5kPotsLineTestEntry
        MAX-ACCESS    not-accessible
        STATUS        current
        DESCRIPTION
            "An entry in the POTS Line-level Test Table."
        INDEX    { ifIndex }
            ::=  { adTA5kPotsLineTestTable 1 }

    AdTA5kPotsLineTestEntry ::= SEQUENCE {
        -- Line-level test items
        adTA5kPotsLineTest1004HzTone                INTEGER,
        adTA5kPotsLineTestRingCadence               INTEGER,
        adTA5kPotsLineTestLoopState                 INTEGER,
        -- adTA5kPotsLineTestMetallicAccess         INTEGER,
        adTA5kPotsLineClearTest                     INTEGER,
        adTA5kPotsLineTestWarbleTone                INTEGER,
        adTA5kPotsLineTestWarbleToneFreq1           INTEGER,
        adTA5kPotsLineTestWarbleToneFreq2           INTEGER,
        adTA5kPotsLineTestWarbleToneCadence         INTEGER,
        adTA5kPotsPortForceMwiOffEvent              INTEGER,
        adTA5kPotsPortForceMwiOnEvent               INTEGER
        }

    adTA5kPotsLineTest1004HzTone OBJECT-TYPE
        SYNTAX  INTEGER {
                        toLoop(1),
                        toNetwork(2),
                        disable(3)
                        }
        MAX-ACCESS      read-write
        STATUS          current
        DESCRIPTION
            "This item controls the generation of a 1004 Hz    test tone
                from the POTS interface.
                1 = To Loop
                2 = To Network
                3 = Disable"
        ::= { adTA5kPotsLineTestEntry 1 }

    adTA5kPotsLineTestRingCadence OBJECT-TYPE
        SYNTAX  INTEGER {
                        enable(1),
                        disable(2)
                        }
        MAX-ACCESS      read-write
        STATUS          current
        DESCRIPTION
            "This item enables/disables the ring cadence test on the POTS interface.
                1 = Enable
                2 = Disable"
        ::= { adTA5kPotsLineTestEntry 2 }

    adTA5kPotsLineTestLoopState OBJECT-TYPE
        SYNTAX  INTEGER {
                        disable(1),             -- Turn off test
                        activeHigh(2),          -- Battery
                        activeLow(3),           -- No longer supported
                        reverseActiveHigh(4),   -- Reverse Battery
                        reverseActiveLow(5),    -- No longer supported
                        powerDownActive(6),     -- No longer supported
                        powerDownResistive(7),  -- No longer supported
                        tipGround(8),           -- No longer supported
                        activeTest(9),          -- No longer supported
                        tipOpen(10)             -- Tip Open
                        }
        MAX-ACCESS      read-write
        STATUS          current
        DESCRIPTION
            "This item controls the loop state test on the POTS interface.
                1 = Disable
                2 = Active High
                3 = Active Low
                4 = Reverse Active High
                5 = Reverse Active Low
                6 = Power Down Active
                7 = Power Down Resistive
                8 = Tip Ground
                9 = Active Test"
        ::= { adTA5kPotsLineTestEntry 3 }

    -- adTA5kPotsLineTestMetallicAccess OBJECT-TYPE
        -- SYNTAX  INTEGER {
        --                  active(1),
        --                  inactive(2)
        --                  }
        -- MAX-ACCESS      read-only
        -- STATUS          current
        -- DESCRIPTION
        --    "This item controls the metallic test access relays for the module.
        --        1 = active
        --        2 = Inactive (normal)"
        -- ::= { adTA5kPotsLineTestEntry 4 }


    adTA5kPotsLineClearTest OBJECT-TYPE
        SYNTAX  INTEGER {
                        clear(1)
                        }
        MAX-ACCESS      read-write
        STATUS          current
        DESCRIPTION
            "This will clear all Port Line Tests. The get will always return 1.
           1 = Clear "
        ::= { adTA5kPotsLineTestEntry 4 }

    adTA5kPotsLineTestWarbleTone OBJECT-TYPE
        SYNTAX  INTEGER {
                        enable(1),
                        disable(2)
                        }
        MAX-ACCESS      read-write
        STATUS          current
        DESCRIPTION
            "This will enable or disable a warble tone as defined by the oids
                adTA5kPotsLineTestWarbleToneFreq1, adTA5kPotsLineTestWarbleToneFreq2,
                and adTA5kPotsLineTestWarbleToneCadence."
        ::= { adTA5kPotsLineTestEntry 5 }

    adTA5kPotsLineTestWarbleToneFreq1 OBJECT-TYPE
        SYNTAX  INTEGER {
                        silence(1),
                        tone1004hz(2),
                        tone1400hz(3),
                        tone2040hz(4)
                        }
        MAX-ACCESS      read-write
        STATUS          current
        DESCRIPTION
            "The first alternating frequency used in the warble tone."
        ::= { adTA5kPotsLineTestEntry 6 }

    adTA5kPotsLineTestWarbleToneFreq2 OBJECT-TYPE
        SYNTAX  INTEGER {
                        silence(1),
                        tone1004hz(2),
                        tone1400hz(3),
                        tone2040hz(4)
                        }
        MAX-ACCESS      read-write
        STATUS          current
        DESCRIPTION
            "The second alternating frequency used in the warble tone."
        ::= { adTA5kPotsLineTestEntry 7 }

    adTA5kPotsLineTestWarbleToneCadence OBJECT-TYPE
        SYNTAX  INTEGER {
                        time100ms(1),
                        time250ms(2),
                        time500ms(3)
                        }
        MAX-ACCESS      read-write
        STATUS          current
        DESCRIPTION
            "The amount of time in ms that one frequency in the warble tone is played before
            alternating to the the other frequency."
        ::= { adTA5kPotsLineTestEntry 8 }
    adTA5kPotsPortForceMwiOffEvent OBJECT-TYPE
        SYNTAX  INTEGER {
                        indicatorOff(1)
                        }
        MAX-ACCESS     read-write
        STATUS         current
        DESCRIPTION
            "A set command will force the Message Waiting Indicator for the port to turn OFF.
            Get has no meaning and will always return indicatorOff(1).
            This provides a means for MWI events to be forced out to the fxs port locally.
            After this set has been issued, the port will still perform any subsequent MWI events that may be received from the network."
        ::= { adTA5kPotsLineTestEntry 9 }

    adTA5kPotsPortForceMwiOnEvent OBJECT-TYPE
        SYNTAX  INTEGER {
                        indicatorOn(1)
                        }
        MAX-ACCESS     read-write
        STATUS         current
        DESCRIPTION
            "A set command will force the Message Waiting Indicator for the port to turn ON.
            Get has no meaning and will always return indicatorOn(1).
            This provides a means for MWI events to be forced out to the fxs port locally.
            After this set has been issued, the port will still perform any subsequent MWI events that may be received from the network."
        ::= { adTA5kPotsLineTestEntry 10 }

        -- -------------------------------------
        -- POTS Alarms
        -- -------------------------------------
        adTa5kPotsTrunkConditioningTrapClear  NOTIFICATION-TYPE

        OBJECTS {
                adTrapInformSeqNum,
                sysName,
                adGenSlotInfoIndex,
                adGenPortInfoIndex
                }
        STATUS  current
        DESCRIPTION
                "Indicates Trunk Conditioning Alarm Clear."
        --#TYPE       "Status - Trunk Conditioning Alarm Clear"
        --#SUMMARY    "POTS:  Trunk Conditioning Alarm Clear for"
        --#SUMMARY    "Shelf: %s, Slot %d, Port %d"
        --#ARGUMENTS  {1, 2, 3}
        --#SEVERITY   MINOR
        --#GENERIC    6
        --#CATEGORY   "Alarm Events"
        --#SOURCE_ID  "A"
        --#TIMEINDEX  0
        ::= { adTA5kPotsAlarmEvents 2 }

        adTa5kPotsTrunkConditioningTrapActive  NOTIFICATION-TYPE

        OBJECTS {
                adTrapInformSeqNum,
                sysName,
                adGenSlotInfoIndex,
                adGenPortInfoIndex
                }
        STATUS  current
        DESCRIPTION
                "Indicates Trunk Conditioning Alarm Active."
        --#TYPE       "Status - Trunk Conditioning Alarm Active"
        --#SUMMARY    "POTS:  Trunk Conditioning Alarm Active for"
        --#SUMMARY    "Shelf: %s, Slot %d, Port %d"
        --#ARGUMENTS  {1, 2, 3}
        --#SEVERITY   MINOR
        --#GENERIC    6
        --#CATEGORY   "Alarm Events"
        --#SOURCE_ID  "A"
        --#TIMEINDEX  0
        ::= { adTA5kPotsAlarmEvents 3 }

        adTa5kPotsLineShoweringTrapClear  NOTIFICATION-TYPE

        OBJECTS {
                adTrapInformSeqNum,
                sysName,
                adGenSlotInfoIndex,
                adGenPortInfoIndex
                }
        STATUS  current
        DESCRIPTION
                "Indicates Line Showering Alarm Clear."
        --#TYPE       "Status - Line Showering Alarm Clear"
        --#SUMMARY    "POTS: Line Showering Alarm Clear for "
        --#SUMMARY    "Shelf: %s, Slot %d, Port %d"
        --#ARGUMENTS  {1, 2, 3}
        --#SEVERITY   MINOR
        --#GENERIC    6
        --#CATEGORY   "Alarm Events"
        --#SOURCE_ID  "A"
        --#TIMEINDEX  0
        ::= { adTA5kPotsAlarmEvents 4 }

        adTa5kPotsLineShoweringTrapActive  NOTIFICATION-TYPE

        OBJECTS {
                adTrapInformSeqNum,
                sysName,
                adGenSlotInfoIndex,
                adGenPortInfoIndex
                }
        STATUS  current
        DESCRIPTION
                "Indicates Line Showering Alarm Active."
        --#TYPE       "Status - Line Showering Active"
        --#SUMMARY    "POTS: Line Showering Alarm Active for "
        --#SUMMARY    "Shelf: %s, Slot %d, Port %d"
        --#ARGUMENTS  {1, 2, 3}
        --#SEVERITY   MINOR
        --#GENERIC    6
        --#CATEGORY   "Alarm Events"
        --#SOURCE_ID  "A"
        --#TIMEINDEX  0
        ::= { adTA5kPotsAlarmEvents 5 }

        adTa5kPotsBackplaneTimingTrapClear  NOTIFICATION-TYPE

        OBJECTS {
                adTrapInformSeqNum,
                sysName,
                adGenSlotInfoIndex,
                adGenPortInfoIndex
                }
        STATUS  current
        DESCRIPTION
                "Indicates Backplane Timing Alarm Clear."
        --#TYPE       "Status - Backplane Timing Alarm Clear"
        --#SUMMARY    "POTS: Backplane Timing Alarm Clear for "
        --#SUMMARY    "Shelf: %s, Slot %d, Port %d"
        --#ARGUMENTS  {1, 2, 3}
        --#SEVERITY   MINOR
        --#GENERIC    6
        --#CATEGORY   "Error Events"
        --#SOURCE_ID  "A"
        --#TIMEINDEX  0
        ::= { adTA5kPotsAlarmEvents 6 }

        adTa5kPotsBackplaneTimingTrapActive  NOTIFICATION-TYPE

        OBJECTS {
                adTrapInformSeqNum,
                sysName,
                adGenSlotInfoIndex,
                adGenPortInfoIndex
                }
        STATUS  current
        DESCRIPTION
                "Indicates Backplane Timing Alarm Active."
        --#TYPE       "Status - Backplane Timing Alarm Active"
        --#SUMMARY    "POTS: Backplane Timing Alarm Active for "
        --#SUMMARY    "Shelf: %s, Slot %d, Port %d"
        --#ARGUMENTS  {1, 2, 3}
        --#SEVERITY   MINOR
        --#GENERIC    6
        --#CATEGORY   "Error Events"
        --#SOURCE_ID  "A"
        --#TIMEINDEX  0
        ::= { adTA5kPotsAlarmEvents 7 }

        adTa5kPotsOverTempTrapClear  NOTIFICATION-TYPE

        OBJECTS {
                adTrapInformSeqNum,
                sysName,
                adGenSlotInfoIndex,
                adGenPortInfoIndex
                }
        STATUS  current
        DESCRIPTION
                "Indicates Over Temperature Alarm Clear if the POTS chipset
                 has not indicated, in the last five minutes, that the temperature
                 has risen to a level such that the port will not function."
        --#TYPE       "Status - Over Temperature Alarm Clear"
        --#SUMMARY    "POTS:  Over Temperature Alarm Clear for"
        --#SUMMARY    "Shelf: %s, Slot %d, Port %d"
        --#ARGUMENTS  {1, 2, 3}
        --#SEVERITY   MINOR
        --#GENERIC    6
        --#CATEGORY   "Alarm Events"
        --#SOURCE_ID  "A"
        --#TIMEINDEX  0
        ::= { adTA5kPotsAlarmEvents 8 }

        adTa5kPotsOverTempTrapActive  NOTIFICATION-TYPE

        OBJECTS {
                adTrapInformSeqNum,
                sysName,
                adGenSlotInfoIndex,
                adGenPortInfoIndex
                }
        STATUS  current
        DESCRIPTION
                "Indicates Over Temperature Alarm Active if the POTS chipset
                 has indicated, at least once in the last five minutes, that the
                 temperature for this port has risen to a level such that the
                 port will not function."
        --#TYPE       "Status - Over Temperature Alarm Active"
        --#SUMMARY    "POTS: Over Temperature Alarm Active for "
        --#SUMMARY    "Shelf: %s, Slot %d, Port %d"
        --#ARGUMENTS  {1, 2, 3}
        --#SEVERITY   MINOR
        --#GENERIC    6
        --#CATEGORY   "Alarm Events"
        --#SOURCE_ID  "A"
        --#TIMEINDEX  0
        ::= { adTA5kPotsAlarmEvents 9 }



END
