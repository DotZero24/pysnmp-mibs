ADTRAN-TA5K-HK-MIB

    DEFINITIONS ::= BEGIN

    -- TITLE:     The ADTRAN Total Access TA5000 HK MIB
    -- PRODUCT:   1187020L1
    -- VERSION:   1.0
    -- DATE:      April 15, 2006

    -- This MIB Contains tables specific to the TA5000 HK
    --

    -- MIBs supported:

    -- HISTORY:
    --     06/12/06 tpm First edition



    IMPORTS
        MODULE-IDENTITY,
        OBJECT-TYPE,
        Integer32,
        Counter32,
        IpAddress
--        Gauge32,
--        Counter64,
--        TimeTicks,
--        Unsigned32,
            FROM SNMPv2-SMI

        ifIndex
--        InterfaceIndexOrZero,
--        InterfaceIndex
            FROM IF-MIB

        DisplayString,
        TruthValue,
        RowStatus,
--        TimeInterval,
        MacAddress,
        TEXTUAL-CONVENTION
            FROM SNMPv2-TC

        adIdentity,
        adIdentityShared,
        adProducts,
        adMgmt
            FROM ADTRAN-MIB

        adGenTa5kHk,
        adGenTa5kHkID
            FROM ADTRAN-GENTA5K-MIB

        adGenSlotInfoIndex
            FROM ADTRAN-GENSLOT-MIB;

-- *********************************************************************************************************

    adTa5kHkModuleIdentity MODULE-IDENTITY
        LAST-UPDATED "200606120832Z"
        ORGANIZATION
            "ADTRAN, Inc."
        CONTACT-INFO
            "CND Tech Support
                Postal: ADTRAN, Inc.
                        901 Explorer Blvd.
                        Huntsville, AL  35806
                        Tel: +1 800 726-8663
                        Fax: +1 256 963 6217
                        E-mail: support@adtran.com"
        DESCRIPTION
            "Total Access 5000 Hk MIB"
        ::= { adGenTa5kHkID 1 }


    adTa5kHkTable OBJECT-TYPE
       SYNTAX      SEQUENCE OF AdTa5kHkEntry
       MAX-ACCESS  not-accessible
       STATUS      current
       DESCRIPTION
           "..."
       ::= { adGenTa5kHk 1 }

    adTa5kHkEntry OBJECT-TYPE
       SYNTAX      AdTa5kHkEntry
       MAX-ACCESS  not-accessible
       STATUS      current
       DESCRIPTION
           "..."
       INDEX { adGenSlotInfoIndex }
       ::= { adTa5kHkTable 1 }

   AdTa5kHkEntry ::=
       SEQUENCE {
           adTa5kHkPresent                   INTEGER,
           adTa5kHkTemp                      Integer32
       }

   adTa5kHkPresent               OBJECT-TYPE
       SYNTAX                    INTEGER {
           true (1),
           false (2)
           }
       MAX-ACCESS                read-only
       STATUS                    current
       DESCRIPTION
           ""
       ::= { adTa5kHkEntry 1 }

   adTa5kHkTemp                  OBJECT-TYPE
       SYNTAX                    Integer32
       MAX-ACCESS                read-only
       STATUS                    current
       DESCRIPTION
           ""
       ::= { adTa5kHkEntry 2 }

   END
