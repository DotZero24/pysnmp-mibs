ADTRAN-5KSCM-MIB  DEFINITIONS ::= BEGIN

   -- TITLE:       5kSCM MIB Definitions
   -- FILENAME:    ADTA5KSCM.MIB
   -- AUTHOR:      Arthur Poleon
   -- DATE:        2003/04/04
   --
   -- ==========================================================================
   -- History
   -- ==========================================================================
   --  01/29/04   AP    For SCA OID, DB0(data bit zeo) corresponds to the Accessory Slot.
   --  02/03/06   KMM   Additional changes made while adding support for packed
   --                   sstate msgs. Added:
   --                   *) service state set single fail
   --                   *) service state get single fail
   --                   *) service state set all fail
   --                   *) service state get all fail
   --  04/03/06   KMM   Removed alarms added on 02/03/06. These are auto-clearing alarms, therefore
   --                   do not have alarm status.
   --  04/17/06   JMC   Added Power Bus B Alarm active and clear.
   --  05/03/06   JMC   Fixed up some outdated descriptions.
   --  05/04/06   JMC   Fixed up some outdated descriptions, again.
   --  05/09/06   JMC   Added power shedding bit definitions to commments.
   --  05/17/06   JMC   Fixed alarm status bit for power shedding.
   --  05/26/06   JMC   Addition of Power Shedding alarms, cleanup.
   --  06/01/06   JMC   Lots of cleanup to bit definitions and commenting.
   --                   Fixup to adta5kSCMShelfRelatedAlarmStatus.
   --  06/05/06   JMC   Fixed adGenSlotAlarmStatus Bits 40-54.
   --  06/06/06   JMC   Removed some adGenSlotAlarmStatus bits - shouldn't have been there.
   --  06/09/06   JMC   Removed Card Removed and Fuse Blown status in adGenSlotAlarmStatus OID.
   --  10/19/06   AP    Remove adta5kSCMAlarmIndex index range.
   --  06/28/06   AP    Increase adta5kSCMAIDIndex value range from 40 to 128.
   --  03/27/08   WFE   Added adTASCM5kChassisRemoved, adTASCM5kChassisLinkStatusDown,  and
   --                   adTASCM5kChassisLinkStatusUp traps.
   --                   Updated adGenSlotAlarmStatus bits.
   --  09/26/13   RJF   "DO NOT MAKE HISTORY COMMENTS HERE!!!! Revision history now in REVISION/DESCRIPTION clauses below"
   --
   -- ==========================================================================



   -- ==========================================================================
   -- This MIB defines the enterprise specific MIB for the TA5000 SCM.
   -- ==========================================================================
   --   ADTRAN standard (ADTRAN)
   --   ADTRAN textual conventions (adtrantc)
   --   ADTRAN generic chassis (genchass)
   --   ADTRAN generic slot (genslot)
   --
   --
   -- ==========================================================================
   -- adGenSlotFaceplate
   -- ==========================================================================
   --     The various values for each LED are:
   --     00   Off
   --     01   Green
   --     10   Red
   --     11   Yellow
   --     There the 9 faceplate LEDs.  Each LED is represented by two bits.
   --     The first byte indicates the number of LEDs; the remaining
   --     bytes encode the status of the LEDs in order from top to bottom.
   --     The mapping of the 3 bytes is illustrated below:
   --     1,2   3,4   5,6   7,8   9,10   11,12   13,14   15,16   17,18
   --     LAN   HOST  ACO   CRI   MAJ    MIN     TEST    ALM     PWR
   --     1188010G2
   --     1,2   3,4   5,6   7,8    9,10   11,12   13,14   15,16
   --     HOST  ACO   CRI   MAJ    MIN     TEST    ALM     PWR
   --     1188011G1
   --     Same as 1188010G2 Plus
   --     17,18  19,20   21,22 23,24
   --     ETH2   ETH-ACT ETH   ETH-ACT
   --
   --     1187011G1 TA5k System Controller w/ Bridging (Domestic)
   --     1,2   3,4   5,6   7,8   9,10   11,12   13,14   15,16   17,18  19,20  21,22
   --     LAN   HOST  ACO   CRI   MAJ    MIN     TEST    ALM     PWR    ETH2   ETH2-ACT
   --
   -- ==========================================================================
   -- adGenSlotAlarmStatus
   -- ==========================================================================
   -- =========================================================================
   -- Bits Details for 1-16 SCM alarm/status
   -- =========================================================================
   --   Bit 1  Indicates that a alarm is present on the SCM.
   -- =========================================================================
   --   Bit 2  Alarm cut-off is on
   --   Bit 3  Alarm cut-off input is active
   -- =========================================================================
   --   Bit 4  N/A
   --   Bit 5  N/A
   --   Bit 6  N/A
   -- =========================================================================
   --   Bit 7  adTAeSCUCtrpBusApowerAlm (-48V Power Supply A alarm is active)
   --   Bit 8  adTAeSCUCtrpBusBpowerAlm (-48V Power Supply B alarm is active)
   --   Bit 9  Device comm failure - this is not a SNMP alarm
   --   Bit 10 One or more card fuses on this chassis is open
   --   Bit 11 adTAeSCUCraftLoginNotfication
   -- =========================================================================
   --   Bit 12 N/A
   --   Bit 13 N/A
   --   Bit 14 N/A
   --   Bit 15 N/A
   --   Bit 16 N/A
   --   Bit 17 N/A
   --   Bit 18 N/A
   --   Bit 19 N/A
   --   Bit 20 N/A
   -- =========================================================================
   --   Bit 21 adTAPowerSheddingInputAsserted
   --   Bit 22 adTAPowerSheddingActivated
   -- =========================================================================
   --   Bit 23 N/A
   -- =========================================================================
   --   Bit 24 adSCM5kExternalAlm  Input 1
   --   Bit 25 adSCM5kExternalAlm  Input 2
   --   Bit 26 adSCM5kExternalAlm  Input 3
   --   Bit 27 adSCM5kExternalAlm  Input 4
   --   Bit 28 adSCM5kExternalAlm  Input 5
   --   Bit 29 adSCM5kExternalAlm  Input 6
   --   Bit 30 adSCM5kExternalAlm  Input 7
   --   Bit 31 adSCM5kExternalAlm  Input 8
   --   Bit 32 adSCM5kExternalAlm  Input 9
   --   Bit 33 adSCM5kExternalAlm  Input 10
   --   Bit 34 adSCM5kExternalAlm  Input 11
   --   Bit 35 adSCM5kExternalAlm  Input 12
   --   Bit 36 adSCM5kExternalAlm  Input 13
   --   Bit 37 adSCM5kExternalAlm  Input 14
   --   Bit 38 adSCM5kExternalAlm  Input 15
   --   Bit 39 adSCM5kExternalAlm  Input 16
   -- =========================================================================
   --   Bit 40 adTACriticalAudibleRelayActive
   --   Bit 41 adTACriticalVisualRelayActive
   --   Bit 42 adTAMajAudibleRelayActive
   --   Bit 43 adTAMajVisualRelayActive
   --   Bit 44 adTAMinorAudibleRelayActive
   --   Bit 45 adTAMinorVisualRelayActive
   --   Bit 46 adTAAUSoftwareVerErrorActive
   --   Bit 47 adTASCM5kChassisLinkStatusDown Shelf 2
   --   Bit 48 adTASCM5kChassisLinkStatusDown Shelf 3
   --   Bit 49 adTASCM5kChassisLinkStatusDown Shelf 4
   --   Bit 50 Reserved     (Deprecated)
   --   Bit 51 Reserved     (Deprecated)
   --   Bit 52 Reserved
   --   Bit 53 Reserved
   --   Bit 54 AutoUpgrade End Of Software Support Warning (adTaSysCtrlAutoUpgradeEOSSWarning)
   --   Bit 55 AutoUpgrade End Of Software Support Denied  (adTaSysCtrlAutoUpgradeEOSSDenied)
   -- ==========================================================================


    IMPORTS
        NOTIFICATION-TYPE, OBJECT-TYPE, Integer32,
        MODULE-IDENTITY, OBJECT-IDENTITY,
        TimeTicks
            FROM SNMPv2-SMI
        DisplayString
            FROM SNMPv2-TC
        sysName
            FROM SNMPv2-MIB
        AdPresence
            FROM ADTRAN-TC
        adProducts,
        adMgmt
            FROM ADTRAN-MIB
        adGenSlotInfoIndex
            FROM ADTRAN-GENSLOT-MIB
        adTrapInformSeqNum
            FROM ADTRAN-GENTRAPINFORM-MIB
        adTAeSCUTrapAlarmLevel
            FROM ADTRAN-TAeSCUEXT1-MIB;


   adTA5kSCMmg MODULE-IDENTITY
         LAST-UPDATED "201309130752Z"
         ORGANIZATION "Adtran, Inc."
         CONTACT-INFO
           "CND Tech Support
               Postal: ADTRAN, Inc.
                       901 Explorer Blvd.
                       Huntsville, AL  35806
                       Tel: +1 800 726-8663
                       Fax: +1 256 963 6217
                       E-mail: support@adtran.com"
         DESCRIPTION
            "This MIB defines the objects for the adta5KSCM MIB."

        REVISION    "201309130752Z"
        DESCRIPTION "Added adGenSlotAlarmStatus comments for new EOSS alarms."

        REVISION "201104251300Z"
        DESCRIPTION "Add comment for SCM LED format."

        REVISION "201002241300Z"
        DESCRIPTION "Converted from SNMPv1 adta5kSCM.mib file."

      ::= { adMgmt 749 }

   -- OBJECT IDENTIFIERS
    adTA5kSCM                    OBJECT IDENTIFIER ::= { adProducts 749  }
    -- adTA5kSCMmg                  OBJECT IDENTIFIER ::= { adMgmt 749  }

    adta5kSCMMgmt         OBJECT IDENTIFIER ::= { adTA5kSCMmg 1 }


   --

   -- 5kSCM and MUXA and MUXB is in first shelf.
   -- To determine a line card shelf number you must
   -- ((adGenSlotInfoIndex - 1) / ad5kSCMNumSlotPerShelf + 1) for line cards,
   -- and the shelf slot number is ((adGenSlotInfoIndex - 1) modulus ad5kSCMNumSlotPerShelf + 1).
   -- However, I thought that the original idea was to make this look like a system and that cards would be addressed by their slot number across the entire . When do you expect this table to be used.

    -- A type to define 5kSCM shelf numbers
    -- Number of shelves possible in this  DSLAM (HDX). Default is 1.
    Adta5kSCMShelfNumber ::= Integer32 ( 1..255)


    -- Count of shelves provisioned to be installed, starting at 1.
   adta5kSCMNumberOfShelves OBJECT-TYPE
       SYNTAX     Adta5kSCMShelfNumber
       MAX-ACCESS     read-only
       STATUS     current
       DESCRIPTION
              "Defines the number of shelves presently provisioned in the system.
               Provisioning is done in the PSM provisioning menu."
       ::= { adta5kSCMMgmt 10 }

   adta5kSCMLastChanged OBJECT-TYPE
       SYNTAX     TimeTicks
       MAX-ACCESS     read-only
       STATUS     current
       DESCRIPTION
               "The sysUpTime When adta5kSCMNumberOfShelves changed, or any adta5kSCMShelfInfoState changed.
                Zero if unchanged since powerup"
     ::= { adta5kSCMMgmt 2 }


   --
   --
   --

   adta5kSCMShelfStatusMgmt         OBJECT IDENTIFIER ::= { adta5kSCMMgmt 12 }

   adta5kSCMShelfStatusTable OBJECT-TYPE
       SYNTAX    SEQUENCE OF Adta5kSCMShelfStatusEntry
       MAX-ACCESS    not-accessible
       STATUS    current
       DESCRIPTION
              "Comparable to the GENCHASSIS MIB, but applicable for
               all shelves in a subtended system like the HDX."
      ::= { adta5kSCMShelfStatusMgmt 1 }

   adta5kSCMShelfStatusEntry OBJECT-TYPE
     SYNTAX      Adta5kSCMShelfStatusEntry
     MAX-ACCESS      not-accessible
     STATUS      current
     DESCRIPTION
             ""
     INDEX      { adta5kSCMShelfNumber }
       ::= { adta5kSCMShelfStatusTable 1 }

   Adta5kSCMShelfStatusEntry ::=
        SEQUENCE {
            adta5kSCMShelfNumber
                Adta5kSCMShelfNumber,
            adta5kSCMShelfInfoState
                AdPresence,
            adta5kSCMShelfAlarmStatus
                OCTET STRING,
            adta5kSCMShelfProvVersion
                Integer32,
            adta5kSCMShelfViewAll
                OCTET STRING,
            adta5kSCMShelfRelatedAlarmStatus
                OCTET STRING
        }

    adta5kSCMShelfNumber OBJECT-TYPE
        SYNTAX     Adta5kSCMShelfNumber
        MAX-ACCESS     read-only
        STATUS     current
        DESCRIPTION
            "Index for each row in this table."
        ::= { adta5kSCMShelfStatusEntry 1 }

    adta5kSCMShelfInfoState OBJECT-TYPE
        SYNTAX     AdPresence
        MAX-ACCESS     read-only
        STATUS     current
        DESCRIPTION
            "Return the shelf status:
                empty(1):    Not provisioned to be present,
                virtual(2):  Provisioned but not operational (link status down),
                occupied(3): Provisioned and operational."
        ::= { adta5kSCMShelfStatusEntry 2 }

    adta5kSCMShelfAlarmStatus OBJECT-TYPE
        SYNTAX      OCTET STRING
        MAX-ACCESS      read-only
        STATUS      current
        DESCRIPTION
            "A bit encoded string representing a summary of the
            alarm state of the chassis"
        ::= { adta5kSCMShelfStatusEntry 3 }

    adta5kSCMShelfProvVersion OBJECT-TYPE
        SYNTAX      Integer32
        MAX-ACCESS      read-only
        STATUS      current
        DESCRIPTION
            "The sum of all the card Provisioning Counters in the generic slot MIB
             for this shelf that can be used by an EMS to detect local changes to
             card provisioning that need to be investigated for synchronization."
        ::= { adta5kSCMShelfStatusEntry 4 }

    adta5kSCMShelfViewAll OBJECT-TYPE
        SYNTAX      OCTET STRING
        MAX-ACCESS      read-only
        STATUS      current
        DESCRIPTION
            "A bit encoded string representing the status of faceplate
            indicators, LEDs, & switches for GUI visualization.
            Each product defines this as a bitmap of booleans, or
            a byte for each indicator if not binary. The strings from
            all the slots are concatenated into this one object, after
            prefixing each card indicator string with two bytes. The
            first byte contains the slot number as an integer, and
            the second byte contains the remaining string length for that
            slot. This object provides highest speed access for chassis
            views to overcome multiple varbind SNMP inefficiency."
        ::= { adta5kSCMShelfStatusEntry 5 }


    adta5kSCMShelfRelatedAlarmStatus OBJECT-TYPE
        SYNTAX      OCTET STRING
        MAX-ACCESS      read-only
        STATUS      current
        DESCRIPTION
            "A bit encoded string representing the alarm status of the
             environmental alarms for each  shelf.  The bits are defined
             in network order, that is, most significant bit first.
             0 = NOT-ALARMED, 1 = ALARMED
             The bit positions are:
             1 - PWR A
             2 - PWR B
             3 - N/A
             4 - N/A
             5 - N/A
             6 - N/A
             7 - N/A"
        ::= { adta5kSCMShelfStatusEntry 6 }

   --
   --
   --  Mapping table to translate from system slot number to shelf and local slot number

   adta5kSCMShelfXlateFromSlotTable OBJECT-TYPE
        SYNTAX      SEQUENCE OF Adta5kSCMShelfXlateFromSlotEntry
        MAX-ACCESS      not-accessible
        STATUS      current
        DESCRIPTION
              "Table of slots available for boards."
      ::= { adta5kSCMShelfStatusMgmt 2 }

   adta5kSCMShelfXlateFromSlotEntry OBJECT-TYPE
        SYNTAX      Adta5kSCMShelfXlateFromSlotEntry
        MAX-ACCESS      not-accessible
        STATUS      current
        DESCRIPTION
             ""
        INDEX       { adGenSlotInfoIndex}
       ::= { adta5kSCMShelfXlateFromSlotTable 1 }

   Adta5kSCMShelfXlateFromSlotEntry ::=
        SEQUENCE {
            adta5kSCMShelfOrdinal
                Adta5kSCMShelfNumber,
            adta5kSCMShelfSlotAddress
                Integer32
        }
    adta5kSCMShelfOrdinal OBJECT-TYPE
        SYNTAX     Adta5kSCMShelfNumber
        MAX-ACCESS     read-only
        STATUS     current
        DESCRIPTION
            "Return the chassis number that corresponds to the adGenSlotInfoIndex."
        ::= { adta5kSCMShelfXlateFromSlotEntry 1 }

    adta5kSCMShelfSlotAddress OBJECT-TYPE
        SYNTAX     Integer32 (1..255)
        MAX-ACCESS     read-only
   STATUS  	current
        DESCRIPTION
            "Return the chassis relative slot number that corresponds to the adGenSlotInfoIndex."
        ::= { adta5kSCMShelfXlateFromSlotEntry 2 }

    ---
    ---
    ---  Mapping table to translate from shelf and slot number to system slot number

    adta5kSCMShelfXlateToSlotTable OBJECT-TYPE
        SYNTAX    SEQUENCE OF Adta5kSCMShelfXlateToSlotEntry
        MAX-ACCESS    not-accessible
        STATUS    current
        DESCRIPTION
                  "Table of slots available for boards."
         ::= { adta5kSCMShelfStatusMgmt 3 }

   adta5kSCMShelfXlateToSlotEntry OBJECT-TYPE
       SYNTAX     Adta5kSCMShelfXlateToSlotEntry
       MAX-ACCESS     not-accessible
       STATUS     current
       DESCRIPTION
                  ""
       INDEX      { adGenSlotInfoIndex, adta5kSCMShelfNumberAddress}
       ::= { adta5kSCMShelfXlateToSlotTable 1 }

   Adta5kSCMShelfXlateToSlotEntry ::=
       SEQUENCE {
           adta5kSCMSystemSlotAddress
               Integer32,
           adta5kSCMShelfNumberAddress
               Integer32
         }
   adta5kSCMSystemSlotAddress OBJECT-TYPE
        SYNTAX     Integer32 (1..255)
        MAX-ACCESS     read-only
        STATUS     current
        DESCRIPTION
            "The global  DSLAM slot corresponding to this shelf relative slot."
        ::= { adta5kSCMShelfXlateToSlotEntry 1 }

   adta5kSCMShelfNumberAddress OBJECT-TYPE
        SYNTAX     Integer32 (1..255)
        MAX-ACCESS     read-only
        STATUS     current
        DESCRIPTION
            "The Shelf Address/Number."
        ::= { adta5kSCMShelfXlateToSlotEntry 2 }

   ---
   ---
   ---  Extension of genslot.mib for trap authentication status checking


    adta5kSCMShelfSlotAlarmStatusTable OBJECT-TYPE
        SYNTAX    SEQUENCE OF Adta5kSCMShelfSlotAlarmStatusEntry
        MAX-ACCESS    not-accessible
        STATUS    current
        DESCRIPTION
            "Table of slot alarms for states the cards themselves
             cannot report for various reasons."
        ::= { adta5kSCMShelfStatusMgmt 4 }

    adta5kSCMShelfSlotAlarmStatusEntry  OBJECT-TYPE
        SYNTAX    Adta5kSCMShelfSlotAlarmStatusEntry
        MAX-ACCESS    not-accessible
        STATUS    current
        DESCRIPTION
            ""
        INDEX     { adGenSlotInfoIndex }
        ::= { adta5kSCMShelfSlotAlarmStatusTable 1 }

    Adta5kSCMShelfSlotAlarmStatusEntry ::=
        SEQUENCE {
            adta5kSCMShelfSlotAlarmStatus
                OCTET STRING
        }
     adta5kSCMShelfSlotAlarmStatus  OBJECT-TYPE
        SYNTAX     OCTET STRING
        MAX-ACCESS     read-only
        STATUS     current
        DESCRIPTION
            "A bit encoded string representing the alarm status of the
             certain card/slot alarms for each HDX slot.  The bits are defined
             in network order, that is, most significant bit first.
             0 = NOT-ALARMED, 1 = ALARMED
             The bit positions are:
             1 - Card Removed
             2 - Fuse Blown"
        ::= { adta5kSCMShelfSlotAlarmStatusEntry 1 }

    ---
    ---
    ---  Shelf specific provisionable environmental alarms

   adta5kSCMUserDefinableAlarm OBJECT IDENTIFIER
          ::= { adta5kSCMMgmt 15 }

   adta5kSCMEnvAlarmsTable OBJECT-TYPE
          SYNTAX      SEQUENCE OF Adta5kSCMEnvAlarmsEntry
          MAX-ACCESS      not-accessible
          STATUS      current
          DESCRIPTION
               "The 5kSCM Environmental alarm table
                with the following alarms:
                This table is a superset of the the adTAeSCUEnvAlarmsTable.
                It includes the environmental alarms of the subtended shelves."
        ::= { adta5kSCMUserDefinableAlarm 1 }


     adta5kSCMEnvAlarmsEntry OBJECT-TYPE
         SYNTAX    Adta5kSCMEnvAlarmsEntry
         MAX-ACCESS    not-accessible
         STATUS    current
         DESCRIPTION
                   "An entry in the Controller Unit Environmental alarm table."
         INDEX     { adta5kSCMShelfNumber, adta5kSCMAlarmIndex}
        ::= { adta5kSCMEnvAlarmsTable 1 }

        Adta5kSCMEnvAlarmsEntry ::=
            SEQUENCE {
                adta5kSCMAlarmIndex
                    Integer32,
                adta5kSCMEnvAlarmDefaultName
                    DisplayString,
                adta5kSCMEnvAlarmUserName
                    DisplayString,
                adta5kSCMEnvAlarmInputLevel
                    INTEGER,
                adta5kSCMAIDIndex
                    Integer32,
                adta5kSCMConditionCode
                    DisplayString
          }
          adta5kSCMAlarmIndex OBJECT-TYPE
              SYNTAX    Integer32
              MAX-ACCESS    read-only
              STATUS    current
              DESCRIPTION
                   "Alarm Index for type of environmental alarm."
                  ::= { adta5kSCMEnvAlarmsEntry 1 }

          adta5kSCMEnvAlarmDefaultName OBJECT-TYPE
              SYNTAX    DisplayString
              MAX-ACCESS    read-only
              STATUS    current
              DESCRIPTION
                  "Default ENV alarm name."
              ::= { adta5kSCMEnvAlarmsEntry 2 }

          adta5kSCMEnvAlarmUserName OBJECT-TYPE
              SYNTAX    DisplayString (SIZE(1..16))
              MAX-ACCESS    read-write
              STATUS    current
              DESCRIPTION
                  "A user specified name.
                    adta5kSCMEnvAlarmDefaultName or a user provided name.
                    '-48V Bus A Input' is read-only.
                    '-48V Bus B Input' is read-only."
              ::= { adta5kSCMEnvAlarmsEntry 3 }

          adta5kSCMEnvAlarmInputLevel OBJECT-TYPE
              SYNTAX   INTEGER {
                  info(2),
                  alert(3),
                  minor(4),
                  major(5),
                  critical(6)
              }
              MAX-ACCESS    read-write
              STATUS    current
              DESCRIPTION
                   "Alarm level."
               ::= { adta5kSCMEnvAlarmsEntry 4 }

          adta5kSCMAIDIndex OBJECT-TYPE
               SYNTAX   Integer32 (1..128)
               MAX-ACCESS   read-write
               STATUS   current
               DESCRIPTION
                   "AID Index.
                    -48V Bus A Input has a maximum range of 45
                    -48V Bus B Input has a maximum range of 45
                    All other alarms will have a max index range of 64."
                  ::= { adta5kSCMEnvAlarmsEntry 5 }

          adta5kSCMConditionCode OBJECT-TYPE
              SYNTAX    DisplayString (SIZE(0..11))
              MAX-ACCESS    read-write
              STATUS    current
              DESCRIPTION
                  "Condition code."
                  ::= { adta5kSCMEnvAlarmsEntry 6 }

    --
    -- 5kSCM SCA support for primary and secondary shelves
    --

    adta5kSCMScaMgmt         OBJECT IDENTIFIER ::= { adta5kSCMMgmt 16 }

    adta5kSCMScaTable OBJECT-TYPE
       SYNTAX    SEQUENCE OF Adta5kSCMScaEntry
       MAX-ACCESS    not-accessible
       STATUS    current
       DESCRIPTION
              "Expansion OIDs for the HDX system."
      ::= { adta5kSCMScaMgmt 1 }

   adta5kSCMScaEntry OBJECT-TYPE
     SYNTAX      Adta5kSCMScaEntry
     MAX-ACCESS      not-accessible
     STATUS      current
     DESCRIPTION
             ""
     INDEX      { adta5kSCMShelfNumber }
       ::= { adta5kSCMScaTable 1 }

   Adta5kSCMScaEntry ::=
        SEQUENCE {
            adTAe5kSCMSCAProvItemChanged
                Integer32,
            adTAe5kSCMSCAPresentCards
                Integer32,
            adTAe5kSCMSCASlotsWithProvData
                Integer32,
            adTAe5kSCMSCAoptRestoreCardBitmask
                Integer32
        }

    adTAe5kSCMSCAProvItemChanged OBJECT-TYPE
                SYNTAX  Integer32
                MAX-ACCESS  read-only
                STATUS  current
                DESCRIPTION
                  "Bitmap of cards with changed provisions.
                  This read-only OID will return a bitmap of slots
                  whose provisions have changed since power-up or the
                  last SCA save operation.  DB1 corresponds to slot 1,
                  DB31 corresponds to slot 31.  DB0 corresponds to the
                  Accessory Slot"
                ::= { adta5kSCMScaEntry 1 }

    adTAe5kSCMSCAPresentCards OBJECT-TYPE
                SYNTAX  Integer32
                MAX-ACCESS  read-only
                STATUS  current
                DESCRIPTION
                  "Bitmap of card 'present' in the shelf.
                  This read-only OID will return a bitmap of
                  slots with cards installed.  DB1 corresponds
                  to slot 1, DB31 corresponds to slot 31.
                  DB0 corresponds to the Accessory Slot."
                ::= { adta5kSCMScaEntry 2 }

    adTAe5kSCMSCASlotsWithProvData OBJECT-TYPE
                SYNTAX  Integer32
                MAX-ACCESS  read-only
                STATUS  current
                DESCRIPTION
                  "Bitmap of slots with provision data.
                  This read-only OID will return a bitmap of slots
                  with provision information.  DB1 corresponds to
                  slot 1, DB31 corresponds to slot 31.  DB0 corresponds
                  to the Accessory Slot"
                ::= { adta5kSCMScaEntry 3 }

    adTAe5kSCMSCAoptRestoreCardBitmask OBJECT-TYPE
                SYNTAX  Integer32
                MAX-ACCESS  read-write
                STATUS  current
                DESCRIPTION
                  "SCA restore to linecard enable bitmask.
                   This OID accesses a enable/disable bitmap indicating which slots
                   should have their provision information restored during an SCA
                   restore operation.  Valid slots are 1..30 or 1..24, depending on
                   shelf type.  DB1 corresponds to slot 1, DB31 corresponds to slot
                   31."
                ::= { adta5kSCMScaEntry 4 }



     --   5kSCM environmental alarms
     --   5kSCM Chassis Traps

     adTA5kSCMNotificationEvents OBJECT-IDENTITY
                STATUS current
                DESCRIPTION "The SCM controller events"
                ::= { adTA5kSCM 0 }

            adSCM5kExternalAlmClear      NOTIFICATION-TYPE
                      OBJECTS    {
                                 adTrapInformSeqNum,
                                 sysName,
                                 adta5kSCMEnvAlarmUserName,
                                 adta5kSCMEnvAlarmInputLevel
                                 }
                      STATUS  current
                      DESCRIPTION
                                 "External Alarm clear"
            --#TYPE        "Warning - External Alarm Failure "
            --#SUMMARY   "adTA5kSCM 74902: External Alarm;"
            --#SUMMARY   "detected at shelf: %s"
            --#ARGUMENTS { 1 }
            --#SEVERITY  MINOR
            --#GENERIC   6
            --#CATEGORY  "Error Events"
            --#SOURCE_ID "A"
            --#TIMEINDEX 0
            ::= { adTA5kSCMNotificationEvents 74902 }

            adSCM5kExternalAlm      NOTIFICATION-TYPE
                      OBJECTS    {
                                 adTrapInformSeqNum,
                                 sysName,
                                 adta5kSCMEnvAlarmUserName,
                                 adta5kSCMEnvAlarmInputLevel
                                 }
                      STATUS  current
                      DESCRIPTION
                                 "External Failure Alarm active"
            --#TYPE        "Warning - External Failure Alarm active"
            --#SUMMARY   "adTA5kSCM 74903: External Alarm active;"
            --#SUMMARY   "detected at shelf: %s"
            --#ARGUMENTS { 1 }
            --#SEVERITY  MINOR
            --#GENERIC   6
            --#CATEGORY  "Error Events"
            --#SOURCE_ID "A"
            --#TIMEINDEX 0
            ::= { adTA5kSCMNotificationEvents 74903 }



         adTASCM5kBusApwrAlmClear    NOTIFICATION-TYPE
                OBJECTS {
                        adTrapInformSeqNum,
                        sysName,
                        adta5kSCMShelfNumber,
                        adta5kSCMEnvAlarmUserName,
                        adta5kSCMEnvAlarmInputLevel
                        }
                STATUS  current
                DESCRIPTION
                        "Bus A Power Failure Alarm clear"
        --#TYPE      "Informational - Bus A Power Failure Alarm clear"
        --#SUMMARY   "adTA5kSCM 74904: Bus A Power Failure Alarm cleared;"
        --#SUMMARY   "detected at 5kSCM: %s Shelf %d, Alarm: %s"
        --#ARGUMENTS { 1 , 2, 3}
        --#SEVERITY  INFORMATIONAL
        --#GENERIC   6
        --#CATEGORY  "Error Events"
        --#SOURCE_ID "A"
        --#TIMEINDEX 0
        ::= { adTA5kSCMNotificationEvents 74904 }

        adTASCM5kBusApowerAlm    NOTIFICATION-TYPE
               OBJECTS {
                        adTrapInformSeqNum,
                        sysName,
                        adta5kSCMShelfNumber,
                        adta5kSCMEnvAlarmUserName,
                        adta5kSCMEnvAlarmInputLevel
                        }
                STATUS  current
                DESCRIPTION
                        "Bus A Power Failure Alarm active"
        --#TYPE      "Major - Bus A Power Failure Alarm active"
        --#SUMMARY   "adTA5kSCM 74905: Bus A Power Failure Alarm active;"
        --#SUMMARY   "detected at 5kSCM: %s Shelf %d, Alarm: %s"
        --#ARGUMENTS { 1 , 2, 3}
        --#SEVERITY  MAJOR
        --#GENERIC   6
        --#CATEGORY  "Error Events"
        --#SOURCE_ID "A"
        --#TIMEINDEX 0
        ::= { adTA5kSCMNotificationEvents 74905 }


         adTASCM5kBusBpwrAlmClear    NOTIFICATION-TYPE
                OBJECTS {
                        adTrapInformSeqNum,
                        sysName,
                        adta5kSCMShelfNumber,
                        adta5kSCMEnvAlarmUserName,
                        adta5kSCMEnvAlarmInputLevel
                        }
                STATUS  current
                DESCRIPTION
                        "Bus B Power Failure Alarm clear"
        --#TYPE      "Informational - Bus B Power Failure Alarm clear"
        --#SUMMARY   "adTA5kSCM 74906: Bus B Power Failure Alarm cleared;"
        --#SUMMARY   "detected at 5kSCM: %s Shelf %d, Alarm: %s"
        --#ARGUMENTS { 1 , 2, 3}
        --#SEVERITY  INFORMATIONAL
        --#GENERIC   6
        --#CATEGORY  "Error Events"
        --#SOURCE_ID "A"
        --#TIMEINDEX 0
        ::= { adTA5kSCMNotificationEvents 74906 }

        adTASCM5kBusBpowerAlm    NOTIFICATION-TYPE
                OBJECTS {
                        adTrapInformSeqNum,
                        sysName,
                        adta5kSCMShelfNumber,
                        adta5kSCMEnvAlarmUserName,
                        adta5kSCMEnvAlarmInputLevel
                        }
                STATUS  current
                DESCRIPTION
                        "Bus B Power Failure Alarm active"
        --#TYPE      "Major - Bus B Power Failure Alarm active"
        --#SUMMARY   "adTA5kSCM 74907: Bus B Power Failure Alarm active;"
        --#SUMMARY   "detected at 5kSCM: %s Shelf %d, Alarm: %s"
        --#ARGUMENTS { 1 , 2, 3}
        --#SEVERITY  MAJOR
        --#GENERIC   6
        --#CATEGORY  "Error Events"
        --#SOURCE_ID "A"
        --#TIMEINDEX 0
        ::= { adTA5kSCMNotificationEvents 74907 }

        adTASCM5kChassisLinkStatusUp      NOTIFICATION-TYPE
               OBJECTS  {
                        adTrapInformSeqNum,
                        sysName,
                        adta5kSCMShelfNumber,
                        adTAeSCUTrapAlarmLevel
                        }
                STATUS  current
                DESCRIPTION
                        "SCM has detected a chassis link up."
        --#TYPE      "Informational - Chassis link down clear"
        --#SUMMARY   "adTA5kSCM 74908: Chassis link down clear;"
        --#SUMMARY   "detected at HDX: %s Shelf %d"
        --#ARGUMENTS { 1 , 2}
        --#SEVERITY  INFORMATIONAL
        --#GENERIC   6
        --#CATEGORY  "Configuration Events"
        --#SOURCE_ID "A"
        --#TIMEINDEX 0
        ::= { adTA5kSCMNotificationEvents  74908 }

        adTASCM5kChassisLinkStatusDown      NOTIFICATION-TYPE
                OBJECTS {
                        adTrapInformSeqNum,
                        sysName,
                        adta5kSCMShelfNumber,
                        adTAeSCUTrapAlarmLevel
                        }
                STATUS  current
                DESCRIPTION
                        "SCM has detected a chassis link down."
        --#TYPE      "Critical - Chassis link down active"
        --#SUMMARY   "adTA5kSCM 74909: Chassis link down active;"
        --#SUMMARY   "detected at HDX: %s Shelf %d"
        --#ARGUMENTS { 1 , 2}
        --#SEVERITY  CRITICAL
        --#GENERIC   6
        --#CATEGORY  "Error Events"
        --#SOURCE_ID "A"
        --#TIMEINDEX 0
        ::= { adTA5kSCMNotificationEvents 74909 }

        adTASCM5kChassisRemoved      NOTIFICATION-TYPE
                OBJECTS {
                        adTrapInformSeqNum,
                        sysName,
                        adta5kSCMShelfNumber,
                        adTAeSCUTrapAlarmLevel
                        }
                STATUS  current
                DESCRIPTION
                        "SCM has removed the last chassis because of a provisioning change.
                         All modules in the chassis will be removed."
        --#TYPE      "Informational - Chassis removed provisioned active"
        --#SUMMARY   "adTA5kSCM 74911: Chassis removed provisioned;"
        --#SUMMARY   "detected at HDX: %s Shelf %d"
        --#ARGUMENTS { 1 , 2}
        --#SEVERITY  INFORMATIONAL
        --#GENERIC   6
        --#CATEGORY  "Configuration Events"
        --#SOURCE_ID "A"
        --#TIMEINDEX 0
        ::= { adTA5kSCMNotificationEvents 74910 }


    END
