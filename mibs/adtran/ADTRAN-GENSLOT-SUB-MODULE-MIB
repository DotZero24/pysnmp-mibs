ADTRAN-GENSLOT-SUB-MODULE-MIB   DEFINITIONS ::= BEGIN

     -- TITLE:       Generic chassis slot sub module MIB (SMIv2)
     -- PRODUCT:     All chassis type products
     -- VERSION:     1.0
     -- DATE:        Jan. 17, 2011
     -- AUTHOR:      Albert Sue
     -- SNMP:        SNMPv2
     -- STATUS:      PRELIMINARY

     -- HISTORY:
     	-- 01/17/11 A S: Created
        -- 02/28/11 A S: added "adFactGenSubSlotSwVersion" and "adFactGenSubSlotDateOfManufacturing"

     IMPORTS
          OBJECT-TYPE,
          MODULE-IDENTITY,
          Integer32           FROM SNMPv2-SMI

          DisplayString,
          PhysAddress         FROM SNMPv2-TC

          sysName             FROM SNMPv2-MIB

          AdProductIdentifier FROM ADTRAN-TC

          adGenSlot,
          adGenSlotInfoIndex  FROM ADTRAN-GENSLOT-MIB;


   -- Slot Sub Module Group
   adGenSubSlotModule MODULE-IDENTITY
        LAST-UPDATED "201102280000Z"
        ORGANIZATION "ADTRAN, Inc."
        CONTACT-INFO
               "        Technical Support Dept.
                Postal: ADTRAN, Inc.
                        901 Explorer Blvd.
                        Huntsville, AL 35806

                   Tel: +1 800 726-8663
                   Fax: +1 256 963 6217
                E-mail: support@adtran.com"
        DESCRIPTION
               "The MIB module that describes the generic objects
               used to mananage individual cards in a shelf/bank
               developed by ADTRAN, Inc."
       ::= { adGenSlot 7 }

    --
    -- Product Information group for Sub Modules
    --
    -- This group contains information common for most all Adtran
    --  products. It is a slot addressable copy of the multi-scoped
    --  ADTRAN-MIB. It augments the slot info table.
    --

   adGenSubSlotProdTable OBJECT-TYPE
       SYNTAX      SEQUENCE OF AdGenSubSlotProdEntry
       MAX-ACCESS  not-accessible
       STATUS      current
       DESCRIPTION
               "Table of slots available for boards."
       ::= { adGenSlot 8 }

   adGenSubSlotProdEntry OBJECT-TYPE
       SYNTAX      AdGenSubSlotProdEntry
       MAX-ACCESS  not-accessible
       STATUS      current
       DESCRIPTION
               ""
       INDEX   { adGenSlotInfoIndex, adGenSubSlotProdInfoIndex }
       ::= { adGenSubSlotProdTable 1 }

   AdGenSubSlotProdEntry ::=
       SEQUENCE {
           adGenSubSlotProdInfoIndex    Integer32,
           adGenSubSlotProdName         DisplayString,
           adGenSubSlotProdPartNumber   DisplayString,
           adGenSubSlotProdCLEIcode     DisplayString,
           adGenSubSlotProdSerialNumber DisplayString,
           adGenSubSlotProdRevision     DisplayString,
           adGenSubSlotProdSwVersion    DisplayString,
           adGenSubSlotProdDateOfManufacturing  DisplayString
       }

   adGenSubSlotProdInfoIndex OBJECT-TYPE
       SYNTAX      Integer32
       MAX-ACCESS  read-only
       STATUS      current
       DESCRIPTION
               "A unique value for each slot's sub module."
       ::= { adGenSubSlotProdEntry 1 }

    adGenSubSlotProdName  OBJECT-TYPE
        SYNTAX      DisplayString
        MAX-ACCESS  read-only
        STATUS      current
        DESCRIPTION
            "The Adtran Product Name for the sub module"
        ::= { adGenSubSlotProdEntry 2 }

    adGenSubSlotProdPartNumber  OBJECT-TYPE
        SYNTAX      DisplayString
        MAX-ACCESS  read-only
        STATUS      current
        DESCRIPTION
            "The Adtran Product Part Number for the sub module"
        ::= { adGenSubSlotProdEntry 3 }

    adGenSubSlotProdCLEIcode  OBJECT-TYPE
        SYNTAX      DisplayString
        MAX-ACCESS  read-only
        STATUS      current
        DESCRIPTION
            "The Adtran Product CLEI Code for the sub module"
        ::= { adGenSubSlotProdEntry 4 }

    adGenSubSlotProdSerialNumber  OBJECT-TYPE
        SYNTAX      DisplayString
        MAX-ACCESS  read-only
        STATUS      current
        DESCRIPTION
            "The Adtran Product Serial Number for the sub module"
        ::= { adGenSubSlotProdEntry 5 }

    adGenSubSlotProdRevision  OBJECT-TYPE
        SYNTAX      DisplayString
        MAX-ACCESS  read-only
        STATUS      current
        DESCRIPTION
            "The Adtran Product Revision Number for the sub module"
        ::= { adGenSubSlotProdEntry 6 }

    adGenSubSlotProdSwVersion  OBJECT-TYPE
        SYNTAX      DisplayString
        MAX-ACCESS  read-only
        STATUS      current
        DESCRIPTION
            "The Adtran Product Software Version Number for the sub module"
        ::= { adGenSubSlotProdEntry 7 }

    adGenSubSlotProdDateOfManufacturing  OBJECT-TYPE
        SYNTAX  DisplayString
        MAX-ACCESS  read-only
        STATUS  current
        DESCRIPTION
            "The Adtran Date of Manufacturing for the sub module."
        ::= { adGenSubSlotProdEntry 8 }

    END
