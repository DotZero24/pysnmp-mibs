ADTRAN-GENGPON-MIB

    DEFINITIONS ::= BEGIN

    -- TITLE:     The ADTRAN Total Access 5000 GPON OLT/ONT MIB
    -- PRODUCT:   Total Access 5000 product
    -- VERSION:   0.1

    -- DATE:      2008/12/19
    -- AUTHOR:    Seetha Subramanian
    -- STATUS:    PRELIMINARY

    -- This MIB uses SMIv2 to define variables needed to manage GPON OLT/ONTs as part of the Total Access
    -- 5000 product.

    -- MIBs supported:

    -- HISTORY:
    --  2008/04/22 pcs First edition: Basic GPON OLT/ONT capabilities matching the OMCI
    --    model of G 984.4 with modest Adtran enhancements..
    --  2008/12/19 Updated the mib based on new GPON ifindex scheme and added all the
    --    new feature paramters
    --  2009/03/23  Removed the duplicate entries that are present in Etherflow mib
    --  2009/04/07  Included the OID to set the upstream bandwidth at the ONT level; Moved ONT number
    --    OID into the status table
    --  2009/04/14 Included the three more OID to set the upstream bandwidth based on different class of service
    --    Added the PON status table
    --  2009/04/30 tgc Added ONT Discovery and Activation traps; made varbinds and
    --    SUMMARY fields more consistent.
    --  2009/04/30 added ont part number & hardware revision OID; Updated alarms fields.
    --  2009/06/05 removed the range values from upstream bandwidth OID
    --  2009/06/09  added adGenGponOntLastCreateError and adGenGponOntPortLastCreateError
    --  2009/06/12  Moved adGenGponOntLastCreateError to PON and adGenGponOntPortLastCreateError to
    --              ONT table to provide the finer granularity
    --  2009/06/23  Added OID to return available downstrean bandwidth
    --  2009/06/23  Removed unused OIDs
    --  2009/07/10  Updated adGenGponOntSoftwareDownloadStatus enum value
    --  2009/07/30 tgc Modified trap severities based on input from PM and Engineering
    --  2009/08/04 ss  Swapped the adGenGponOltGponClock enum values
    --  2010/03/09 gg  added the adGenGponOltBackplaneNegSpeed
    --  2010/03/25 gg  added the units description for the POTS port gains
    --  2010/03/25 gg  added the OID adGenGponPonDeploymentRange to support the deployment range for PON
    --  2010/07/27 sgs added OID adGenGponPonActivationMode; SMIC verified;
    --  2010/07/27 sgs depreciated OIDs adGenGponPonAutoDiscoveryMode, adGenGponPonAutoOntActivateMode;
    --  2010/07/27 sgs added OID adGenGponOntRegistrationId; SMIC verified;
    --  2010/07/27 sgs added OID adGenGponPonDiscoveredRegistrationId; SMIC verified;
    --  2010/07/27 sgs added OID adGenGponOntLearnedSerialNumber; SMIC verified;
    --  2010/09/09 sgs the comment is changed in the adGenGponOntActivationAlarm trap(new ifDescr format)
    --  2010/03/25 xl  added the OID adGenGponOltOntBootCodeSwVersionOnFlash and adGenGponOntBootCodeSoftwareVersion
    --  2010/11/01 tgc Deprecated AdGenGponOntPortAutoDetectMode (TEXTUAL-CONVENTION) and
    --                 adGenGponOntPortAutoDetectionConfiguration (provisioning OID) in favor of the common
    --                 provisioning OIDs in genEthIfc.mi2 (i.e., adGenEthPortFixedSpeed, adGenEthPortFixedDuplex,
    --                 adGenEthAutoNegotiateCu, adGenEthAdvertisedSpeedAndDuplexCu, adGenEthAutoNegotiateFiber, and
    --                 adGenEthAdvertisedDuplexFiber). The status OID, adGenGponOntPortConfigurationInd, was not
    --                 deprecated as it may still be useful. Added status OID, adGenGponOntPortOmciEthProvPrelimCheck.
    --  2010/12/15 kkb Added several OIDs for ONT configuration file provisioning, status, and alarms,
    --                 including adGenGponAvailableVOIPConfigMethods,
    --                 adGenGponConfigFileState, adGenGponConfigFileChecksum,
    --                 adGenGponConfigErrorString, adGenGponConfigFileRetrievalMethod,
    --                 adGenGponConfigFilePrimaryServer, adGenGponConfigFileSecondaryServer,
    --                 adGenGponConfigFileInterface, adGenGponConfigFileName,
    --                 adGenGponConfigFileRetrieve, adGenGponConfigServerAlarmSet/Clear,
    --                 adGenGponConfigFileAlarmSet/Clear, and
    --                 adGenGponConfigChecksumMismatchAlarmSet/Clear
    -- 2011/01/06 sgs  Added adGenGponOntOMCICommFailAlarmClear, adGenGponOntOMCICommFailAlarmSet
    -- 2011/01/07 jb   Added OID adGenGponOntRssi to AdGenGponOntStatusEntry
    -- 2011/01/11 jp   Added adGenGponOntPortRFSignalLevel to AdGenGponOntPortStatusEntry
    -- 2011/01/31 jp   Added the following alarm set/clear OIDs
    --                 adGenGponOntVideoPortLOSAlarmSet/clear
    --                 adGenGponOntVideoPortOORLowAlarmSet/clear
    --                 adGenGponOntVideoPortOORHighAlarmSet/clear
    --                 Added the following OIDs to adGenGponOntProvEntry
    --                 adGenGponOntVideoPortEnableLOSAlarm
    --                 adGenGponOntVideoPortEnableOORLowAlarm
    --                 adGenGponOntVideoPortEnableOORHighAlarm
    --                 Modified the description of the OID "adGenGponOntPortOpticalSignalLevel" in adGenGponOntPortStatusEntry
    --                 Added OID adGenGponOntPortRFOpticalSignalLevel to adGenGponOntPortStatusEntry

    --  2011/03/14 xl added registrationUnlock mode in adGenGponPonActivationMode

    -- 2011/4/14 jp DO NOT MAKE HISTORY COMMENTS HERE!!!! Revision history now in REVISION/DESCRIPTION clauses below


--******************************************************************************************

    IMPORTS
        adGenGponProduct, adGenGponProductID, adGenGponProductConformance
            FROM ADTRAN-GENGPONCONTAINER-MIB
        MODULE-IDENTITY, OBJECT-TYPE, NOTIFICATION-TYPE, TimeTicks,Integer32, IpAddress, Gauge32, Counter32, Counter64
            FROM SNMPv2-SMI
        DisplayString, RowStatus, PhysAddress, TEXTUAL-CONVENTION
            FROM SNMPv2-TC
        sysName
            FROM SNMPv2-MIB
        InterfaceIndex, ifIndex, ifDescr, InterfaceIndexOrZero
            FROM IF-MIB
        adGenSlotInfoIndex, adGenSlotAlarmStatus
            FROM ADTRAN-GENSLOT-MIB
        adGenPortInfoIndex
            FROM ADTRAN-GENPORT-MIB
        adTrapInformSeqNum
            FROM ADTRAN-GENTRAPINFORM-MIB;


    adGenGponMIB MODULE-IDENTITY
        LAST-UPDATED "202206070000Z"

        ORGANIZATION
            "ADTRAN, Inc."
        CONTACT-INFO
            "CND Tech Support
                Postal: ADTRAN, Inc.
                        901 Explorer Blvd.
                        Huntsville, AL  35806
                        Tel: +1 800 726-8663
                        Fax: +1 256 963 6217
                        E-mail: support@adtran.com"
        DESCRIPTION
            "GPON MIB"

           REVISION "202206070000Z"
           DESCRIPTION "Added new OIDs adGenGponOntClrDyingGaspAlarm, adGenGponOntSetDyingGaspAlarm
            Add varbind to report the alarm level for adGenGponOntxxxLOSAlarm,adGenGponOntxxxPoweringAlarm,
            adGenGponOntxxxDyingGaspAlarm"

           REVISION "202205310000Z"
           DESCRIPTION "Added new OID adGenGponGalEthDiscardedFrames."

           REVISION "202203290000Z"
           DESCRIPTION "Added new OIDs adGenGponOntUsFecProcessedCodewords, adGenGponOntUsFecCorrectedCodewords
                        adGenGponOntUsFecCorrectedCodebytes and adGenGponOntUsFecUncorrectedCodewords."

           REVISION "202203140000Z"
           DESCRIPTION "Added new OIDs adGenGponOntAlarmSlotDyingGaspEnable, adGenGponOntAlarmSlotDyingGaspLevel."

           REVISION "202203040000Z"
           DESCRIPTION "Added tenGigabitFull (5), twentyFiveHundredFull (6), fiveGigabitFull (7), tenHalf (17), hundredHalf (18), thousandHalf (19) to AdGenGponOntPortAutoDetectMode.
	   Added tenGigabitEthernetFullDuplex (4), twentyFiveHundredEthernetFullDuplex (5), fiveGigabitEthernetFullDuplex (6) to adGenGponOntPortConfigurationInd."

           REVISION "202202230000Z"
           DESCRIPTION "Added new OIDs adGenGponOntTemperature, adGenGponOntBiasCurrent, and adGenGponOntVoltage."

           REVISION "202008270000Z"
           DESCRIPTION "Added new alarm OIDs adGenGponPonHwFailureAlarm and adGenGponPonDegradationAlarm."

           REVISION "202003300000Z"
           DESCRIPTION "Added new adGenGponOntAlarmSlot OIDs to provision the severities for the LOS and Powering alarms for the slot."

           REVISION "202003250000Z"
           DESCRIPTION "Added wdmpon(3) to adGenGponPonTechnology for WDM-PON technology"

           REVISION "201912200000Z"
           DESCRIPTION "Added new OID adGenGponPonTechnologyMode to show the fixed operation mode of the PON interface"

           REVISION "201904080000Z"
           DESCRIPTION "Added new alarm adGenGponPonFailoverAlarm(Clear/Active) to show PON failover alarms"

           REVISION "201802230000Z"
           DESCRIPTION "Added new Varbind adGenGponPonDescriptionString to varbind list for adGenGponPonLosAlarmClear and adGenGponPonLosAlarmSet alarms."

           REVISION "201801260000Z"
           DESCRIPTION "Added new OID adGenGponProtection to enable/disable Slot Protection for PON Redundancy"

           REVISION "201710230000Z"
           DESCRIPTION "Added new OID adGenGponPonDescriptionString to show the description of the PON."

           REVISION "201701060000Z"
           DESCRIPTION "Added new OID adGenGponOntCpuRateLimitCountersClear for clearing CPU rate limit counters."

           REVISION "201608160000Z"
           DESCRIPTION "Added new alarm OID adGenGponOntDyingGaspAlarm to adGponOntAlarmEvents"

           REVISION "201604290000Z"
           DESCRIPTION "Synced up varbind list for adGenGponPonLosAlarmClear and adGenGponPonLosAlarmSet alarms."
           REVISION "201601110000Z"
           DESCRIPTION "Added adGenGponOntUpstreamBipTcaAlarmClear and adGenGponOntUpstreamBipTcaAlarmSet notification types.
           Added adGenGponOntDownstreamBipTcaAlarmClear and adGenGponOntDownstreamBipTcaAlarmSet notification types.
           Added adGenGponOltBipTcaAlarmThreshold OID for setting BIP threshold value on the OLT."

           REVISION "201601040000Z"
           DESCRIPTION "Added adGenGponPonTechnology and adGenGponPonWavelength to adGenGponOntDiscoveryAlarm.
                        Added adGenGponPonTechnology, adGenGponPonWavelength, and adGenGponOntEverActivated to adGenGponOntActivationAlarm."

           REVISION "201508050000Z"
           DESCRIPTION "Added adGenGponPonCounterResetTable and adGenGponPonBIPCountersReset OID to reset the upstream and downstream BIP errors rolling counters on the PON"

           REVISION "201504080000Z"
           DESCRIPTION "Added OIDs adGenGponOntSoftwareDownloadOnly and adGenGponOntSoftwareActivate to adGenGponOntProvTable"

           REVISION "201502200000Z"
           DESCRIPTION "Added adGenGponOltOntSwOnFlashGlbFilename to adGenGponOltConfigTable"

           REVISION "201501270000Z"
           DESCRIPTION "Added adGenGponOntInactiveSoftwareVersion as varbind to adGenGponOntActivationAlarm"

           REVISION "201501060000Z"
           DESCRIPTION "Added adGenGponPonDiscoveredInvalidSNAlarm and adGenGponOntInvalidSNAlarm notification types"

           REVISION "201412100000Z"
           DESCRIPTION "Added enums startAndDeferActivate(3) and activateAndCommit(4) to adGenGponPonOntSoftwareDownloadFlag definition.
                        Added downloadCompletedNotActivated(13) to adGenGponOntSoftwareDownloadStatus definition"

           REVISION "201412050000Z"
           DESCRIPTION "Added OID to enable upstream forward error correction (FEC)"

           REVISION "201409020000Z"
           DESCRIPTION "Added OID to provision vectoring enable on all vdsl ports on the specified ONT"

           REVISION "201407310000Z"
           DESCRIPTION "Updated description for the OID adGenGponPonDownstreamTotalMinRate"

           REVISION "201405230000Z"
           DESCRIPTION "Added test to AdGenGponOntPortOperState
                        Updated adGenGponPonLosAlarmClear and adGenGponPonLosAlarmSet to CRITICAL"

           REVISION "201405190000Z"
           DESCRIPTION "Removed range from adGenGponPonDiscoveredOntSerialNumberIndex"
        REVISION "201405130000Z"
           DESCRIPTION "Added adGenGponPonDownstreamTotalMinRate, adGenGponPonDownstreamAvailableMinRate and
           adGenGponPonDownstreamCurrentMinRate."
           REVISION "201404220000Z"
           DESCRIPTION "Added adGenGponMulticastBwThresholdAlarmClear and adGenGponMulticastBwThresholdAlarmSet notification types.
           Added adGenGponPonMulticastBwThreshold OID for setting multicast bandwidth threshold value on the PON.
           Added adGenGponPonMulticastCac OID to enable or disable the multicast CAC on the PON.
           Added adGenGponPonMulticastCacStatus OID to show the multicast CAC status on the PON.
           Added AdGenGponMulticastCacStatus textual convention."
           REVISION "201402060000Z"
           DESCRIPTION "Added adGenPonLosAlarmSet and adGenGponPonLosAlarmClear notification types.  Also added OIDs
           for setting PON LOS active threshold and returning number of ONTs that caused to exceed the active PON LOS threshold."
           REVISION "201401090000Z"
           DESCRIPTION "Added new OID to adGenGponOntStatusTable:
                        adGenGponOntProductName"
       REVISION "201401060000Z"
           DESCRIPTION "Added adGenGponCirOversubscribedAlarmSet and adGenGponCirOversubscribedAlarmClear notification types."
           REVISION "201312120100Z"
           DESCRIPTION "Added adGenGponOntPortBondingPeer to adGenGponOntPortProvTable"
       REVISION "201312120000Z"
       DESCRIPTION "Added adGenGponOntRxPower, adGenGponOntTxPower
                             OIDs to adGenGponOntStatusTable.
                    Updated the description to adGenGponOntRssi OID"

           REVISION "201312050000Z"
           DESCRIPTION "Added the following OIDs to adGenGponPonProvisioningTable:
                           adGenGponPonResourceAllocationMode
                        Added the following OIDs to adGenGponPonStatusTable:
                           adGenGponPonMaxOnts
                           adGenGponPonMaxServicesPerOnt"
       REVISION "201312030000Z"
       DESCRIPTION "Added efmGroup and efmLink to adGenGponOntPortType and adGenGponOntSupportedType.
                        The value for ds3 is now being replaced by efmGroup."

       REVISION "201310100000Z"
       DESCRIPTION "Added adGenGponPonTotalProvFixedBandwidth, adGenGponPonTotalProvAssuredBandwidth
                             OIDs to adGenGponPonStatusTable."
       REVISION "201309180000Z"
           DESCRIPTION "Added adGenGponOntInactiveSoftwareVersion, adGenGponOntManagementMacAddress,
                  adGenGponOntFiberLength & adGenGponOntEqualizationDelay oids to adGenGponOntStatusTable. "
       REVISION "201309120000Z"
           DESCRIPTION "Added efmPort to adGenGponOntPortType and adGenGponOntSupportedType. "

       REVISION "201309040000Z"
           DESCRIPTION "Added adGenGponOntVoIPConfigMethod to specify the current ONT SIP provisining method.
                Added type voip in adGenGponOntPortType."

           REVISION "201308220000Z"
           DESCRIPTION "Added the following OIDs to the adGenGponPonStatusTable:
                        adGenGponPonAvailableFixedAssuredBandwidth (amount fixed/assured bandwidth
                        that can be provisioned on the PON before the line rate is reached)
                        adGenGponPonCurrDownstreamBandwidth (the downstream PIR rate provisioned in
                        hardware on this PON)
                        adGenGponPonCurrUpstreamBandwidth (the upstream PIR rate provisioned in
                        hardware on this PON)
                        adGenGponPonCurrFixedAssuredBandwidth (the fixed and assured bandwdith
                        provisioned in hardware on this PON)"

           REVISION "201307220000Z"
           DESCRIPTION "Added pseudowire and xdsl to adGenGponOntPortType enum list"
           REVISION "201306100000Z"
           DESCRIPTION "Added the following OIDs to adGenGponOntStatusTable:
                        adGenGponOntFeatureSupport"
           REVISION "201304100000Z"
           DESCRIPTION "Updated range value for adGenGponOntVideoPortReturnPathFrequency from 30000 KHz to 40000 KHz"
           REVISION "201303120000Z"
           DESCRIPTION "Added bridgeGroup(11) in adGenGponOntPortType/adGenGponOntSupportedType definition.
                Added new OIDs in the ONT port table:
                adGenGponOntPortBridgeGroupAgingTime,
                adGenGponOntPortBridgeGroupLearningLimit,
                adGenGponOntPortMapBridgeGroupIfIndex.
                        Added adGenGponAcsServerProfilePassword to AdGenGponOntStatusEntry.
                        Added adGenGponOntPortConnectToVEIP,
                        adGenGponOntPortConnectToBridgeGroup to AdGenGponOntPortStatusEntry.
                        Added new OIDs in the ONT port status table:
                        adGenGponOntPortConnectToVEIP,
                        adGenGponOntPortConnectToBridgeGroup."
           REVISION "201303080000Z"
           DESCRIPTION "Added two new objects - adGenGponPonDiscoveredOntSerialNumber,
                        adGenGponPonDiscoveredRegistrationId to the adGenGponOntDiscoveryAlarm"
           REVISION "201302050000Z"
           DESCRIPTION "Added new OID in the ONT port table:
                        adGenGponOntPortMapVEIPIfIndex."
           REVISION "201301230000Z"
           DESCRIPTION "Added two new varbinds for adGenGponOntActivationAlarm:
                        adGenGponOntLearnedSerialNumber
                        adGenGponOntRegistrationId."
           REVISION "201301170000Z"
           DESCRIPTION "Added adGenGponPonNextAvailableOntId to AdGenGponPonStatusEntry

                        Corrected description for adGenGponOltSystemUpTime and adGenGponOntUpTime"
           REVISION "201301100000Z"
           DESCRIPTION "Added adGenGponAcsServerProfile to AdGenGponOntProvEntry
                        Added adGenGponAcsServerProfileUserName to AdGenGponOntStatusEntry"
           REVISION "201212050000Z"
           DESCRIPTION "Added the following OIDs to adGenGponOntStatusTable:
                        adGenGponOntUpstreamGoodDBRuCounter
                        adGenGponOntUpstreamBadDBRuCounter"

           REVISION "201212040000Z"
           DESCRIPTION "Added the following OIDs to adGenGponPon15MinPMTable:
                        adGenGponPon15MinDownstreamBIPError

                        Added the following OIDs to adGenGponPon24HrPMTable:
                        adGenGponPon24HrDownstreamBIPError

                        Added the following OIDs to adGenGponPonCurrent15MinPMTable:
                        adGenGponPonDownstreamBIPErrorCurrent15Min

                        Added the following OIDs to adGenGponPonCurrent24HrPMTable:
                        adGenGponPonDownstreamBIPErrorCurrent24Hr"
           REVISION "201211260000Z"
           DESCRIPTION "Added the following OIDs to adGenGponPon15MinPMTable:
                        adGenGponPon15MinRxEthernetBytes
                        adGenGponPon15MinTxEthernetBytes
                        adGenGponPon15MinUsBwAverageUtil
                        adGenGponPon15MinUsBwPeakUtil
                        adGenGponPon15MinDsBwAverageUtil
                        adGenGponPon15MinDsBwPeakUtil
                        adGenGponPon15MinDsMulticastPackets
                        adGenGponPon15MinDsMulticastBytes
                        adGenGponPon15MinDsMulticastBwAverageUtil
                        adGenGponPon15MinDsMulticastBwPeakUtil

                        Added the following OIDs to adGenGponPon24HrPMTable:
                        adGenGponPon24HrRxEthernetBytes
                        adGenGponPon24HrTxEthernetBytes
                        adGenGponPon24HrUsBwAverageUtil
                        adGenGponPon24HrUsBwPeakUtil
                        adGenGponPon24HrDsBwAverageUtil
                        adGenGponPon24HrDsBwPeakUtil
                        adGenGponPon24HrDsMulticastPackets
                        adGenGponPon24HrDsMulticastBytes
                        adGenGponPon24HrDsMulticastBwAverageUtil
                        adGenGponPon24HrDsMulticastBwPeakUtil

                        Added the following OIDs to adGenGponPonCurrent15MinPMTable:
                        adGenGponPonRxEthernetBytesCurrent15Min
                        adGenGponPonTxEthernetBytesCurrent15Min
                        adGenGponPonUsBwAverageUtilCurrent15Min
                        adGenGponPonUsBwPeakUtilCurrent15Min
                        adGenGponPonDsBwAverageUtilCurrent15Min
                        adGenGponPonDsBwPeakUtilCurrent15Min
                        adGenGponPonDsMulticastPacketsCurrent15Min
                        adGenGponPonDsMulticastBytesCurrent15Min
                        adGenGponPonDsMulticastBwAverageUtilCurrent15Min
                        adGenGponPonDsMulticastBwPeakUtilCurrent15Min

                        Added the following OIDs to adGenGponPonCurrent24HrPMTable:
                        adGenGponPonRxEthernetBytesCurrent24Hr
                        adGenGponPonTxEthernetBytesCurrent24Hr
                        adGenGponPonUsBwAverageUtilCurrent24Hr
                        adGenGponPonUsBwPeakUtilCurrent24Hr
                        adGenGponPonDsBwAverageUtilCurrent24Hr
                        adGenGponPonDsBwPeakUtilCurrent24Hr
                        adGenGponPonDsMulticastPacketsCurrent24Hr
                        adGenGponPonDsMulticastBytesCurrent24Hr
                        adGenGponPonDsMulticastBwAverageUtilCurrent24hr
                        adGenGponPonDsMulticastBwPeakUtilCurrent24Hr"
           REVISION "201211060000Z"
           DESCRIPTION "Added OID adGenGponPonTotalProvUpstreamBandwidth and adGenGponPonTotalProvFixedAssuredBandwidth
                        to adGenGponPonStatusTable.  Include 'downstream' and 'peak information rate' in
                        adGenGponPonTotalProvDownstreamBandwidth description."
           REVISION "201211020000Z"
           DESCRIPTION "Added OID adGenGponOntPortDescription."
           REVISION "201210080000Z"
           DESCRIPTION "Added OID adGenGponPonTotalProvDownstreamBandwidth to adGenGponPonStatusTable."
           REVISION "201209050000Z"
           DESCRIPTION "Added adGenGponOltMaxOntsPerPon to adGenGponOltConfigEntry.
                        Added adGenGponOltNumPons to adGenGponOltConfigEntry."
           REVISION "201208200000Z"
           DESCRIPTION "Added three new varbinds for adGenGponOntActivationAlarm:
                        adGenGponOntActiveSoftwareVersion
                        adGenGponOntPartNumber
                        adGenGponOntHardwareRevision."
           REVISION "201208170000Z"
           DESCRIPTION "Added gpon(7) in adGenGponOntPortType/adGenGponOntSupportedType definition.
                        Added iphost(8) in adGenGponOntPortType/adGenGponOntSupportedType definition.
                        Added E1(9) in adGenGponOntPortType/adGenGponOntSupportedType definition.
                        Added virtualEthernet(10) in adGenGponOntPortType/adGenGponOntSupportedType definition."
           REVISION "201205220000Z"
           DESCRIPTION "Added OID adGenGponOntPortErrorString to adGenGponOntPortStatusTable."
           REVISION "201204120000Z"
           DESCRIPTION "Increased adGenGponOntVideoPortReturnPathFrequency upper limit from 27904 KHz to 30000 KHz"
           REVISION "201202200000Z"
           DESCRIPTION "Added nine new OIDs for VRP counters adGenGponOntVideoReturnPathCountersReset(to reset all VRP counters),
           adGenGponOntVideoReturnPathRxTotalBursts, adGenGponOntVideoReturnPathRxGoodBursts,
           adGenGponOntVideoReturnPathRxFECCorrectedBursts, adGenGponOntVideoReturnPathRxMissedBursts,
           adGenGponOntVideoReturnPathRxMinPower, adGenGponOntVideoReturnPathRxMaxPower,
           adGenGponOntVideoReturnPathRxCurrentPower, adGenGponOntVideoReturnPathRxFECCorrectedSymbols"
           REVISION "201201240000Z"
           DESCRIPTION "Added OID adGenGponMacSpoofingAllowed to adGenGponOntProvTable."
           REVISION "201112010000Z"
           DESCRIPTION "Added OIDs adGenGponOntUpstreamBIPError and adGenGponOntDownstreamBIPError to adGenGponOntStatusTable."
        REVISION "201111110000Z"
           DESCRIPTION "Added ten OIDs for PON status adGenGponPonConfiguredOnts, adGenGponPonDiscoveringOnts, adGenGponPonUnrecognizedOnts, adGenGponPonOperationallyUpOnts, adGenGponPonAvailableUpstreamBandwidth, adGenGponPonAvailableDownstreamBandwidth,
        adGenGponPonLongestFiberDistance, adGenGponPonShortestFiberDistance, adGenGponPonNearestOnt, adGenGponPonFarthestOnt to adGenGponPonStatusTable"
           REVISION "201110240000Z"
           DESCRIPTION "Added five OIDs for VRP adGenGponOntVideoPortReturnPathMode, adGenGponOntVideoPortReturnPathFrequency,
           adGenGponOntVideoPortReturnPathDestinationIPAddress, adGenGponOntVideoPortReturnPathDestinationUDPPort,
           adGenGponOntVideoPortReturnPathSourceUDPPort to adGenGponOntPortProvTable"
           REVISION "201108250000Z"
           DESCRIPTION "Change the unit of OID adGenGponOntPortRFOpticalSignalLevel from dBuV to dBmV "
           REVISION "201105210000Z"
           DESCRIPTION "Swapped http and tftp values in AdGenGponConfigFileRetrievalMethod, moved config file status from per PON to per ONT  "
           REVISION "201104140000Z"
           DESCRIPTION "Moved three OIDs adGenGponOntVideoPortEnableLOSAlarm, adGenGponOntVideoPortEnableOORLowAlarm and adGenGponOntVideoPortEnableOORHighAlarm from adGenGponOntProvTable to adGenGponOntPortProvTable"
        ::= {adGenGponProductID 1}

-- OBJECT IDENTIFIERS

adGponConfiguration     OBJECT IDENTIFIER ::= {adGenGponMIB 1}
adGponProvisioning      OBJECT IDENTIFIER ::= {adGenGponMIB 2}
adGponStatus            OBJECT IDENTIFIER ::= {adGenGponMIB 3}
adGponPerformance       OBJECT IDENTIFIER ::= {adGenGponMIB 4}
adGponAlarms            OBJECT IDENTIFIER ::= {adGenGponMIB 5}
adGponTests             OBJECT IDENTIFIER ::= {adGenGponMIB 6}

adGponOntAlarmEventsPrefix      OBJECT IDENTIFIER ::= {adGponAlarms 1}
adGponOntAlarmEvents            OBJECT IDENTIFIER ::= {adGponOntAlarmEventsPrefix 0}
adGponOntPortAlarmEventsPrefix  OBJECT IDENTIFIER ::= {adGponAlarms 2}
adGponOntPortAlarmEvents        OBJECT IDENTIFIER ::= {adGponOntPortAlarmEventsPrefix 0}

adGponOntTest                   OBJECT IDENTIFIER ::= {adGponTests 1 }


-- **********************************************************************
-- Textual Conventions
-- **********************************************************************
-- Flesh out enumerations and such here

AdGenGponEnableDisableValue ::= TEXTUAL-CONVENTION
        STATUS  current
        DESCRIPTION
            "Indicates enumeration value of the enable/disable"
        SYNTAX INTEGER {
                   enable  (1),
                   disable (2)
          }

AdGenGponTrueFalseValue ::= TEXTUAL-CONVENTION
        STATUS  current
        DESCRIPTION
            "Indicates enumeration value of the true/false"
        SYNTAX INTEGER {
                   false  (0),
                   true (1)
          }
AdGenGponYesNoValue ::= TEXTUAL-CONVENTION
        STATUS  current
        DESCRIPTION
            "Indicates enumeration value of the yes/no"
        SYNTAX INTEGER {
                   yes  (1),
                   no (2)
          }
AdGenGponOntAdminState ::= TEXTUAL-CONVENTION
        STATUS  current
        DESCRIPTION
            "Indicates the admin state of the GPON interface."
        SYNTAX INTEGER {
                   inService (1),
                   outOfSeriveUAS (2),
                   outOfServiceMA (3)
          }

AdGenGponOntOperState ::= TEXTUAL-CONVENTION
        STATUS  current
        DESCRIPTION
            "Indicates the operational state of the GPON ont."
        SYNTAX   INTEGER {
                 init (0),
                 discovering (1),
                 discovered  (2),
                 rejected (3),
                 up (4),
                 down (5)
        }

AdGenGponOntPortOperState ::= TEXTUAL-CONVENTION
        STATUS  current
        DESCRIPTION
            "Indicates the operational state of the GPON ont ports."
        SYNTAX   INTEGER {
                 up (1),
                 down (2),
                 test(3)
        }
AdGenGponOntPortAutoDetectMode ::= TEXTUAL-CONVENTION
        STATUS  deprecated
        DESCRIPTION
            "Indicates auto detection configuration of ONT Ethernet interface."
        SYNTAX   INTEGER {
                 autoAuto (0),
                 tenFull (1),
                 hundredFull (2),
                 thousandFull (3),
                 autoFull (4),
                 tenGigabitFull (5),
                 twentyFiveHundredFull (6),
                 fiveGigabitFull (7),
                 tenHalf (17),
                 hundredHalf (18),
                 thousandHalf (19)
        }

AdGenGponActivationMode ::= TEXTUAL-CONVENTION
        STATUS  current
        DESCRIPTION
            "Indicates the ONT activation mode used in PON interface"
        SYNTAX INTEGER {
                   manual  (1),
                   autodiscovery (2),
                   autoactivate (3),
                   registrationid (4),
                   registrationUnlock (5)
        }

AdGenGponConfigFileRetrievalMethod ::= TEXTUAL-CONVENTION
        STATUS  current
        DESCRIPTION
            "Indicates the protocol used for retrieving a configuration file."
        SYNTAX INTEGER {
                   none (0),
                   tftp (1),
                   http (2),
                   tr69 (3)
          }

AdGenGponConfigFileState ::= TEXTUAL-CONVENTION
        STATUS  current
        DESCRIPTION
            "Indicates the state of the configuration file being processed by the ONT."
        SYNTAX INTEGER {
                   inactive     (0),
                   active       (1),
                   initializing (2),
                   fault        (3)
          }

AdGenGponConfigFileInterface ::= TEXTUAL-CONVENTION
        STATUS  current
        DESCRIPTION
            "Indicates the interface used to transfer a config file to the ONT."
        SYNTAX INTEGER {
                   voipIpHost       (0),
                   managementIpHost (1)
          }

AdGenGponOntVideoPortReturnPathMode ::= TEXTUAL-CONVENTION
    STATUS current
    DESCRIPTION
        "Video return path mode:
        scte-1:      Mode 1, 256 kbit/s data rate, 62 byte PDUs, preceded by the unique word 0xCCCCCC00;
        scte-2-256:  Mode 2, 256 kbit/s data rate, 59 byte PDUs, preceded by the unique word 0xCCCCCC0D;
        scte-2-1544: Mode 2, 1.544 Mbit/s data rate, 59 byte PDUs, preceded by the unique word 0xCCCCCC0D;
        scte-2-3088: Mode 2, 3.088 Mbit/s data rate, 59 byte PDUs, preceded by the unique word 0xCCCCCC0D;
        rf-sample:   Proprietary RF sampling."
    SYNTAX INTEGER {
        scte-1      (0),
        scte-2-256  (1),
        scte-2-1544 (2),
        scte-2-3088 (3),
        rf-sample   (245)
    }

AdGenGponResourceAllocationMode ::= TEXTUAL-CONVENTION
        STATUS  current
        DESCRIPTION
                "Indicates the resource allocation mode used in PON interface:
                mode6416:      Maximum of 64 ONTs, 16 services per ONT;
                mode3232:      Maximum of 32 ONTs, 32 services per ONT;"
        SYNTAX INTEGER {
                mode6416 (1),
                mode3232 (2)
        }

AdGenGponMulticastCacStatus ::= TEXTUAL-CONVENTION
        STATUS  current
        DESCRIPTION
                "Indicates the multicast CAC status on the PON:
                 admitting: IGMP join message would not be rejected due to CAC;
                 rejecting: New IGMP group join message would be rejected due to CAC;
                 disabled:  Multicast CAC and MulticastBwThresholdAlarm are not enabled on the PON"
        SYNTAX INTEGER {
                admitting (1),
                rejecting (2),
                disabled (3)
        }

-- Config table

adGenGponOltConfigTable         OBJECT-TYPE
          SYNTAX         SEQUENCE OF AdGenGponOltConfigEntry
          MAX-ACCESS     not-accessible
          STATUS         current
          DESCRIPTION
           "The GPON Olt Configuration table.
            Each table entry corresponds to GPON OLT card"
          ::= { adGponConfiguration 1}

adGenGponOltConfigEntry         OBJECT-TYPE
          SYNTAX         AdGenGponOltConfigEntry
          MAX-ACCESS     not-accessible
          STATUS         current
          DESCRIPTION
           "An entry in the Gpon Olt Configuration table.
            This entry represents a particular GPON OLT. "
          INDEX  {adGenSlotInfoIndex}
          ::= { adGenGponOltConfigTable  1}

AdGenGponOltConfigEntry    ::= SEQUENCE  {
    adGenGponOltSystemUpTime                DisplayString,
    adGenGponOltOntSwVersionOnFlash         DisplayString,
    adGenGponOltOntBootCodeSwVersionOnFlash DisplayString,
    adGenGponOltMaxOntsPerPon               Integer32,
    adGenGponOltNumPons                     Integer32,
    adGenGponOltOntSwOnFlashGlbFilename     DisplayString
}

adGenGponOltSystemUpTime OBJECT-TYPE
          SYNTAX         DisplayString
          MAX-ACCESS     read-only
          STATUS         current
          DESCRIPTION
           "A string containing the time since the OLT was last re-initialized.
            The string is in one of the following formats:

              d days, h hours, m minutes, s seconds
              w weeks, d days, h hours, m minutes, s seconds
              y years, w weeks, d days, h hours, m minutes, s seconds

            where:
              y is the number of years
              w is the number of weeks
              d is the number of days
              h is the number of hours
              m is the number of minutes
              s is the number of seconds"
          ::= { adGenGponOltConfigEntry 1 }

adGenGponOltOntSwVersionOnFlash OBJECT-TYPE
          SYNTAX         DisplayString
          MAX-ACCESS     read-only
          STATUS         current
          DESCRIPTION
           "The version of the ONT software stored on OLT flash and currently
            available for ONT upgrade."
          ::= { adGenGponOltConfigEntry 2 }

adGenGponOltOntBootCodeSwVersionOnFlash OBJECT-TYPE
          SYNTAX         DisplayString
          MAX-ACCESS     read-only
          STATUS         current
          DESCRIPTION
           "The version of the ONT boot code software stored on OLT flash and currently
            available for ONT upgrade."
          ::= { adGenGponOltConfigEntry 3 }

adGenGponOltMaxOntsPerPon OBJECT-TYPE
          SYNTAX         Integer32
          MAX-ACCESS     read-only
          STATUS         current
          DESCRIPTION
           "The maximum number of ONTs per PON that the OLT supports."
          ::= { adGenGponOltConfigEntry 4 }

adGenGponOltNumPons OBJECT-TYPE
          SYNTAX         Integer32
          MAX-ACCESS     read-only
          STATUS         current
          DESCRIPTION
           "The number of PONs that the OLT has."
          ::= { adGenGponOltConfigEntry 5 }

adGenGponOltOntSwOnFlashGlbFilename OBJECT-TYPE
          SYNTAX         DisplayString
          MAX-ACCESS     read-only
          STATUS         current
          DESCRIPTION
           "The GLB file name used to upload the ONT image file currently stored
            in the OLT Flash file system."
          ::= { adGenGponOltConfigEntry 6 }

-- **********************************************************************
-- Provisioning
-- **********************************************************************

-- GPON OLT

adGenGponOltProvTable         OBJECT-TYPE
          SYNTAX         SEQUENCE OF AdGenGponOltProvEntry
          MAX-ACCESS     not-accessible
          STATUS         current
          DESCRIPTION
           "The GPON OLT provisioning table.
            Each table entry corresponds to a specific
            GPON OLT card"
          ::= { adGponProvisioning 1}

adGenGponOltProvEntry         OBJECT-TYPE
          SYNTAX         AdGenGponOltProvEntry
          MAX-ACCESS     not-accessible
          STATUS         current
          DESCRIPTION
           "An entry in the Gpon OLT provisioning table.
            This entry represents a particular GPON OLT card. "
          INDEX  {adGenSlotInfoIndex}
          ::= { adGenGponOltProvTable  1}


AdGenGponOltProvEntry    ::= SEQUENCE  {
    adGenGponOltStagTpid                 Integer32,
    adGenGponOltCtagTpid                 Integer32,
    adGenGponOltGponClock                INTEGER,
    adGenGponOltBackplaneNegSpeed        DisplayString,
    adGenGponOltBipTcaThreshold          Integer32,
    adGenGponProtection                  INTEGER,
    adGenGponOntAlarmSlotLosEnable       AdGenGponEnableDisableValue,

    adGenGponOntAlarmSlotLosLevel        INTEGER,

    adGenGponOntAlarmSlotPoweringEnable  AdGenGponEnableDisableValue,

    adGenGponOntAlarmSlotPoweringLevel   INTEGER,

    adGenGponOntAlarmSlotDyingGaspEnable AdGenGponEnableDisableValue,

    adGenGponOntAlarmSlotDyingGaspLevel  INTEGER


}

adGenGponOltStagTpid OBJECT-TYPE
          SYNTAX         Integer32
          MAX-ACCESS     read-only
          STATUS         current
          DESCRIPTION
           "The S-tag tpid value (set from SM)."
          ::= { adGenGponOltProvEntry 1 }

adGenGponOltCtagTpid OBJECT-TYPE
          SYNTAX         Integer32
          MAX-ACCESS     read-write
          STATUS         current
          DESCRIPTION
           "The C-tag tpid value (provisionable from AM);"
          ::= { adGenGponOltProvEntry 2 }

adGenGponOltGponClock OBJECT-TYPE
          SYNTAX   INTEGER {
          local (1),
          backplane (2)
          }
          MAX-ACCESS     read-write
          STATUS         current
          DESCRIPTION
           "This option is used to select the timing system for the GPON
            services. `local` uses the timing signals from OLT and other
            option uses the timing signals from the backplane."
          ::= { adGenGponOltProvEntry 3 }

adGenGponOltBackplaneNegSpeed OBJECT-TYPE
          SYNTAX         DisplayString
          MAX-ACCESS     read-only
          STATUS         current
          DESCRIPTION
           "The backplane negotiated speed rate for the OLT in Gbps.
           e.g. 1G X 1 CH is 1Gbps across 1 Channel and 2.5G is 2.5Gbps"
          ::= { adGenGponOltProvEntry 4 }

adGenGponOltBipTcaThreshold OBJECT-TYPE
          SYNTAX         Integer32
          MAX-ACCESS     read-write
          STATUS         current
          DESCRIPTION
           "The BIP threshold value for raising/clear upstream/downstream
           BIP Threshold Crossing Alarm, valid values 0, 3-9
           0 to disable the alarm, 3-9 to enable the alarm and set the BIP threshold"
          ::= { adGenGponOltProvEntry 5 }

adGenGponProtection         OBJECT-TYPE
          SYNTAX  INTEGER {
            disable(0),
            enable(1)
            }
          MAX-ACCESS     read-write
          STATUS         current
          DESCRIPTION
           "A card level provisioning item used for PON Redundancy.
            This item is used determine which card is the protecting
            card of a Protected pair."
          DEFVAL { disable }
          ::= { adGenGponOltProvEntry 6 }

adGenGponOntAlarmSlotLosEnable         OBJECT-TYPE

          SYNTAX  AdGenGponEnableDisableValue

          MAX-ACCESS     read-write

          STATUS         current

          DESCRIPTION

           "A card level provisioning item used to enable the ONT LOS alarm.

            Affects all ONTs on the slot."

          DEFVAL { enable }

          ::= { adGenGponOltProvEntry 7 }


adGenGponOntAlarmSlotLosLevel         OBJECT-TYPE

          SYNTAX  INTEGER {

                 info(2),

                 alert(3),

                 minor(4),

                 major(5),

                 critical(6)

                }

          MAX-ACCESS     read-write

          STATUS         current

          DESCRIPTION

           "A card level provisioning item used for Alarm Severity.

            This item is used to set the severity of the ONT LOS Alarm.

            Affects all ONTs on the slot."

          DEFVAL { major }

          ::= { adGenGponOltProvEntry 8 }

adGenGponOntAlarmSlotPoweringEnable         OBJECT-TYPE

          SYNTAX  AdGenGponEnableDisableValue

          MAX-ACCESS     read-write

          STATUS         current

          DESCRIPTION

           "A card level provisioning item used to enable the ONT Powering alarm.

            Affects all ONTs on the slot."

          DEFVAL { enable }

          ::= { adGenGponOltProvEntry 9 }


adGenGponOntAlarmSlotPoweringLevel         OBJECT-TYPE

          SYNTAX  INTEGER {

                 info(2),

                 alert(3),

                 minor(4),

                 major(5),

                 critical(6)

                }

          MAX-ACCESS     read-write

          STATUS         current

          DESCRIPTION

           "A card level provisioning item used for Alarm Severity.

            This item is used to set the severity of the ONT Powering Alarm.

            Affects all ONTs on the slot."

          DEFVAL { major }

          ::= { adGenGponOltProvEntry 10 }

adGenGponOntAlarmSlotDyingGaspEnable         OBJECT-TYPE

          SYNTAX  AdGenGponEnableDisableValue

          MAX-ACCESS     read-write

          STATUS         current

          DESCRIPTION

           "A card level provisioning item used to enable the ONT Dying Gasp alarm.

            Affects all ONTs on the slot."

          DEFVAL { enable }

          ::= { adGenGponOltProvEntry 11 }


adGenGponOntAlarmSlotDyingGaspLevel         OBJECT-TYPE

          SYNTAX  INTEGER {

                 info(2),

                 alert(3),

                 minor(4),

                 major(5),

                 critical(6)

                }

          MAX-ACCESS     read-write

          STATUS         current

          DESCRIPTION

           "A card level provisioning item used for Alarm Severity.

            This item is used to set the severity of the ONT Dying Gasp Alarm.

            Affects all ONTs on the slot."

          DEFVAL { alert }

          ::= { adGenGponOltProvEntry 12 }


-- GPON OLT PON Interface

adGenGponPonProvTable         OBJECT-TYPE
          SYNTAX         SEQUENCE OF AdGenGponPonProvEntry
          MAX-ACCESS     not-accessible
          STATUS         current
          DESCRIPTION
           "The GPON PON provisioning table.
            Each table entry corresponds to a specific
            GPON PON Interface"
          ::= { adGponProvisioning 2}

adGenGponPonProvEntry         OBJECT-TYPE
          SYNTAX         AdGenGponPonProvEntry
          MAX-ACCESS     not-accessible
          STATUS         current
          DESCRIPTION
           "An entry in the Gpon PON provisioning table.
            This entry represents a particular GPON PON interface. "
          INDEX  { ifIndex }
          ::= { adGenGponPonProvTable  1}


AdGenGponPonProvEntry    ::= SEQUENCE  {
    adGenGponPonDownstreamFec                  AdGenGponEnableDisableValue,
    adGenGponPonAutoDiscoveryMode              AdGenGponEnableDisableValue,
    adGenGponPonAutoOntActivateMode            AdGenGponEnableDisableValue,
    adGenGponPonOntSoftwareDownloadFlag        INTEGER,
    adGenGponPonRediscoverFlag                 AdGenGponEnableDisableValue,
    adGenGponOntLastCreateError                DisplayString,
    adGenGponPonDeploymentRange                INTEGER,
    adGenGponPonActivationMode                 AdGenGponActivationMode,
    adGenGponPonResourceAllocationMode         AdGenGponResourceAllocationMode,
    adGenGponPonLosActiveThreshold             INTEGER,
    adGenGponPonMulticastBwThreshold           Integer32,
    adGenGponPonMulticastCac                   AdGenGponEnableDisableValue,
    adGenGponPonDownstreamTotalMinRate         Integer32,
    adGenGponPonUpstreamFec                    AdGenGponEnableDisableValue,
    adGenGponPonDescriptionString              DisplayString,
    adGenGponPonTechnologyMode                 INTEGER
    }

adGenGponPonDownstreamFec OBJECT-TYPE
          SYNTAX         AdGenGponEnableDisableValue
          MAX-ACCESS     read-write
          STATUS         current
          DESCRIPTION
           "Downstream FEC mode value of GPON PON interface"
          ::= { adGenGponPonProvEntry 1 }

-- depreciated 07/26/10
adGenGponPonAutoDiscoveryMode OBJECT-TYPE
          SYNTAX         AdGenGponEnableDisableValue
          MAX-ACCESS     read-write
          STATUS         current
          DESCRIPTION
           "Auto discovery mode value of GPON PON interface"
          ::= { adGenGponPonProvEntry 2 }

-- depreciated 07/26/10
adGenGponPonAutoOntActivateMode OBJECT-TYPE
          SYNTAX         AdGenGponEnableDisableValue
          MAX-ACCESS     read-write
          STATUS         current
          DESCRIPTION
           "Auto activation of ONTs discovered on GPON PON interface"
          ::= { adGenGponPonProvEntry 3 }

adGenGponPonOntSoftwareDownloadFlag OBJECT-TYPE
          SYNTAX INTEGER
          {
            start (1),
            cancel (2),
            startAndDeferActivate(3),
            activateAndCommit(4)
          }
          MAX-ACCESS     read-write
          STATUS         current
          DESCRIPTION
           "Starting and cancelling the download of the software version currenly available on OLT flash to
            all of active ONTs on this PON interface. startAndDeferActivate will download the software version
            but will not activate the software. activateAndCommit will activate and commit the inactive image"
          ::= { adGenGponPonProvEntry 4 }

adGenGponPonRediscoverFlag OBJECT-TYPE
          SYNTAX         AdGenGponEnableDisableValue
          MAX-ACCESS     read-write
          STATUS         current
          DESCRIPTION
           "Send the wakeup all ploam message and triggers the PON discovery cycle"
          ::= { adGenGponPonProvEntry 5 }

adGenGponOntLastCreateError OBJECT-TYPE
    SYNTAX      DisplayString
    MAX-ACCESS  read-only
    STATUS      current
    DESCRIPTION
       "The reason for the last error that occured while attempting to create
        an entry in the ONT Prov Table."
     ::= { adGenGponPonProvEntry 6 }

adGenGponPonDeploymentRange OBJECT-TYPE
   SYNTAX       INTEGER
                {
                    standard(1),
                    extended(2),
                    maximum(3)
                }
   MAX-ACCESS   read-write
   STATUS       current
   DESCRIPTION
     "The deployment range for each PON can be selected.
      Standard range supports upto 20 Km at the maximum rate of 1.2 Gbps
      Extended range supports upto 37.5 Km at the maximum rate of 890 Mbps
      Maximum range will support upto 37.5 Km at the maximum rate of 1.2 Gbps"
    ::= { adGenGponPonProvEntry 7 }

adGenGponPonActivationMode OBJECT-TYPE
   SYNTAX       AdGenGponActivationMode
   MAX-ACCESS   read-write
   STATUS       current
   DESCRIPTION
     "The ONT activation mode used on this GPON interface"
    ::= { adGenGponPonProvEntry 8 }

adGenGponPonResourceAllocationMode OBJECT-TYPE
   SYNTAX       AdGenGponResourceAllocationMode
   MAX-ACCESS   read-write
   STATUS       current
   DESCRIPTION
     "The resource allocation mode used on this GPON interface"
    ::= { adGenGponPonProvEntry 9 }

adGenGponPonLosActiveThreshold OBJECT-TYPE
   SYNTAX       INTEGER (0..100)
   UNITS          "percent"
   MAX-ACCESS   read-write
   STATUS       current
   DESCRIPTION
     "The percentage of ONTs activated once that are in LOS condition.  Minimum setting is 0%,
       maximum is 100% and the user can provision in increments of 5%.  The default value of 0%
       is used to disable the PON LOS alarm"
   DEFVAL { 0 }
    ::= { adGenGponPonProvEntry 10 }

adGenGponPonMulticastBwThreshold OBJECT-TYPE
   SYNTAX       Integer32
   UNITS        "Mbps"
   MAX-ACCESS   read-write
   STATUS       current
   DESCRIPTION
     "The multicast bandwidth threshold value on the PON.
     The valid range is 0 through the maximum PON downstream link rate in Mbps.
     The default value of 0 is used to disable the MulticastBwThreshold alarm"
   DEFVAL { 0 }
    ::= { adGenGponPonProvEntry 11 }

adGenGponPonMulticastCac OBJECT-TYPE
   SYNTAX       AdGenGponEnableDisableValue
   MAX-ACCESS   read-write
   STATUS       current
   DESCRIPTION
     "Enable or disable multicast CAC on the PON.
     The default value 'disable' is used to disable the multicast CAC"
   DEFVAL { disable }
    ::= { adGenGponPonProvEntry 12 }

adGenGponPonDownstreamTotalMinRate OBJECT-TYPE
   SYNTAX       Integer32
   UNITS        "kbps"
   MAX-ACCESS   read-write
   STATUS       current
   DESCRIPTION
     "The total minimum rate per pon that can be distributed among onts on the pon
      to maintain minimum qos.
      A set on this OID with value lower than the cumulative min-rate configured
      in downstream shaper could get rejected by the network element.
      Based on the PON technology different ranges are defined:
      - GPON [0, 2488000]."
    ::= { adGenGponPonProvEntry 13 }

adGenGponPonUpstreamFec OBJECT-TYPE
   SYNTAX         AdGenGponEnableDisableValue
   MAX-ACCESS     read-write
   STATUS         current
   DESCRIPTION
     "Upstream FEC mode value of GPON PON interface"
   DEFVAL { disable }
    ::= { adGenGponPonProvEntry 14 }

adGenGponPonDescriptionString OBJECT-TYPE
   SYNTAX         DisplayString
   MAX-ACCESS     read-write
   STATUS         current
   DESCRIPTION
     "Description for this particular GPON PON."
   DEFVAL { "" }
    ::= { adGenGponPonProvEntry 15 }

adGenGponPonTechnologyMode OBJECT-TYPE
        SYNTAX INTEGER
        {
            gpon                    (0),
            xgspon                  (1),
            ngpon2                  (2),
            technologyNotDefined   (31)
        }
        MAX-ACCESS     read-only
        STATUS         current
        DESCRIPTION
            "Indicates the fixed PON technology mode for this interface"
        ::= { adGenGponPonProvEntry 16 }


-- GPON ONT Interface and Equipment Provisiong

adGenGponOntProvTable         OBJECT-TYPE
          SYNTAX         SEQUENCE OF AdGenGponOntProvEntry
          MAX-ACCESS     not-accessible
          STATUS         current
          DESCRIPTION
           "The ONT-G provisioning table.
            Each table entry corresponds to a specific
            GPON ONT Equipment. "
          ::= { adGponProvisioning 3}

adGenGponOntProvEntry         OBJECT-TYPE
          SYNTAX         AdGenGponOntProvEntry
          MAX-ACCESS     not-accessible
          STATUS         current
          DESCRIPTION
           "An entry in the ONT-G provisioning table.
            This entry represents a particular GPON ONT Equipment. "
          INDEX  { ifIndex }
          ::= { adGenGponOntProvTable  1}


AdGenGponOntProvEntry    ::= SEQUENCE  {
      adGenGponOntSerialNumber                 DisplayString,
      adGenGponOntDescriptionString            DisplayString,
      adGenGponOntBatteryBackup                AdGenGponTrueFalseValue,
      adGenGponOntAdminState                   AdGenGponOntAdminState,
      adGenGponOntAesMode                      AdGenGponEnableDisableValue,
      adGenGponOntSecurityMode                 Integer32,
      adGenGponOntSoftwareVersion              DisplayString,
      adGenGponOntGr303VoiceMacAddress         PhysAddress,
      adGenGponOntUpstreamFixedBandwidth       Integer32,
      adGenGponOntUpstreamAssuredBandwidth     Integer32,
      adGenGponOntUpstreamBestEffortBandwidth  Integer32,
      adGenGponOntUpstreamNonAssuredBandwidth  Integer32,
      adGenGponOntPotsServiceMode              INTEGER,
      adGenGponOntLastError                    DisplayString,
      adGenGponOntRowStatus                    RowStatus,
      adGenGponOntPortLastCreateError          DisplayString,
      adGenGponOntRegistrationId               DisplayString,
      adGenGponOntBootCodeSoftwareVersion      DisplayString,
      adGenGponConfigFileRetrievalMethod       AdGenGponConfigFileRetrievalMethod,
      adGenGponConfigFilePrimaryServer         DisplayString,
      adGenGponConfigFileSecondaryServer       DisplayString,
      adGenGponConfigFileInterface             AdGenGponConfigFileInterface,
      adGenGponConfigFilePath                  DisplayString,
      adGenGponConfigFileRetrieve              AdGenGponTrueFalseValue,
      adGenGponMacSpoofingAllowed              AdGenGponEnableDisableValue,
      adGenGponAcsServerProfile                DisplayString,
      adGenGponOntVoIPConfigMethod             INTEGER,
      adGenGponOntVectoringEnable              INTEGER,
      adGenGponOntSoftwareDownloadOnly         DisplayString,
      adGenGponOntSoftwareActivate             INTEGER,
      adGenGponOntCpuRateLimitCountersClear INTEGER
}
adGenGponOntSerialNumber OBJECT-TYPE
          SYNTAX         DisplayString
          MAX-ACCESS     read-write
          STATUS         current
          DESCRIPTION
           "The manufacturer's serial number for this particular GPON ONT."
          ::= { adGenGponOntProvEntry 1 }

adGenGponOntDescriptionString OBJECT-TYPE
          SYNTAX         DisplayString
          MAX-ACCESS     read-write
          STATUS         current
          DESCRIPTION
           "Description for this particular GPON ONT."
          ::= { adGenGponOntProvEntry 2 }

adGenGponOntBatteryBackup OBJECT-TYPE
          SYNTAX         AdGenGponTrueFalseValue
          MAX-ACCESS     read-write
          STATUS         current
          DESCRIPTION
           "Whether battery backup is enabled for this GPON ONT."
          ::= { adGenGponOntProvEntry 3 }

adGenGponOntAdminState OBJECT-TYPE
          SYNTAX         AdGenGponOntAdminState
          MAX-ACCESS     read-write
          STATUS         current
          DESCRIPTION
           "The admin state of the GPON ONT."
          ::= { adGenGponOntProvEntry 4 }

adGenGponOntAesMode OBJECT-TYPE
          SYNTAX         AdGenGponEnableDisableValue
          MAX-ACCESS     read-write
          STATUS         current
          DESCRIPTION
           "Enable/Disable AES security feature on downstream traffic on this GPON ONT."
          ::= { adGenGponOntProvEntry 5 }

adGenGponOntSecurityMode OBJECT-TYPE
          SYNTAX         Integer32 (0..255)
          MAX-ACCESS     read-write
          STATUS         current
          DESCRIPTION
           "The security mode of the GPON ONT."
          ::= { adGenGponOntProvEntry 6 }

adGenGponOntSoftwareVersion OBJECT-TYPE
          SYNTAX         DisplayString
          MAX-ACCESS     read-write
          STATUS         current
          DESCRIPTION
           "The software version of the GPON ONT. The software can be upgraded on the ONT by setting
           this OID with the version different than the version currently running on the ONT."
          ::= { adGenGponOntProvEntry 7 }

adGenGponOntGr303VoiceMacAddress OBJECT-TYPE
          SYNTAX         PhysAddress
          MAX-ACCESS     read-write
          STATUS         current
          DESCRIPTION
           "The MAC address assigned for the ONT GR-303-controlled voice ports."
          ::= { adGenGponOntProvEntry 8 }

adGenGponOntUpstreamFixedBandwidth OBJECT-TYPE
          SYNTAX         Integer32
          MAX-ACCESS     read-write
          STATUS         current
          DESCRIPTION
           "Subscription of upstream Fixed bandwidth (kbps) value on this GPON ONT."
          ::= { adGenGponOntProvEntry 9 }


adGenGponOntUpstreamAssuredBandwidth OBJECT-TYPE
          SYNTAX         Integer32
          MAX-ACCESS     read-write
          STATUS         current
          DESCRIPTION
           "Subscription of upstream Assured bandwidth (kbps) value on this GPON ONT"
          ::= { adGenGponOntProvEntry 10 }

adGenGponOntUpstreamBestEffortBandwidth OBJECT-TYPE
          SYNTAX         Integer32
          MAX-ACCESS     read-write
          STATUS         current
          DESCRIPTION
           "Subscription of upstream BestEffort bandwidth (kbps) value on this GPON ONT"
          ::= { adGenGponOntProvEntry 11 }

adGenGponOntUpstreamNonAssuredBandwidth OBJECT-TYPE
          SYNTAX         Integer32
          MAX-ACCESS     read-write
          STATUS         current
          DESCRIPTION
           "Subscription of upstream Non Assured bandwidth (bps) value on this GPON ONT"
          ::= { adGenGponOntProvEntry 12 }

adGenGponOntPotsServiceMode OBJECT-TYPE
          SYNTAX  INTEGER
          {
            none  (0),
            gr303 (1),
            sip   (2),
            mgcp  (3)
          }
          MAX-ACCESS     read-write
          STATUS         current
          DESCRIPTION
           "Setting the pots service mode on the ONT."
          ::= { adGenGponOntProvEntry 13 }

adGenGponOntLastError OBJECT-TYPE
          SYNTAX         DisplayString
          MAX-ACCESS     read-only
          STATUS         current
          DESCRIPTION
           "The last error reported by this ONT Interface configuration entity."
          ::= { adGenGponOntProvEntry 14 }

adGenGponOntRowStatus OBJECT-TYPE
          SYNTAX         RowStatus
          MAX-ACCESS     read-write
          STATUS         current
          DESCRIPTION
           "This object is used to create
            a new row or modify or delete an
            existing row in this table."
          ::= { adGenGponOntProvEntry 15 }

adGenGponOntPortLastCreateError OBJECT-TYPE
    SYNTAX      DisplayString
    MAX-ACCESS  read-only
    STATUS      current
    DESCRIPTION
       "The reason for the last error that occured while attempting to create
        an entry in the ONT Port Prov Table."
     ::= { adGenGponOntProvEntry 16 }

adGenGponOntRegistrationId OBJECT-TYPE
          SYNTAX         DisplayString
          MAX-ACCESS     read-write
          STATUS         current
          DESCRIPTION
           "The user programmed registration id of this GPON ONT.
            Used for ONT activation if serial number not a prefered one."
          ::= { adGenGponOntProvEntry 17 }

adGenGponOntBootCodeSoftwareVersion OBJECT-TYPE
          SYNTAX         DisplayString
          MAX-ACCESS     read-write
          STATUS         current
          DESCRIPTION
           "The boot code software version of the GPON ONT. The software can be upgraded on the ONT by setting
           this OID with the version different than the version currently running on the ONT."
          ::= { adGenGponOntProvEntry 18 }

adGenGponConfigFileRetrievalMethod OBJECT-TYPE
          SYNTAX         AdGenGponConfigFileRetrievalMethod
          MAX-ACCESS     read-write
          STATUS         current
          DESCRIPTION
           "The method used, if any, to retrieve a config file from an ONT."
          ::= { adGenGponOntProvEntry 19 }

adGenGponConfigFilePrimaryServer OBJECT-TYPE
          SYNTAX         DisplayString
          MAX-ACCESS     read-write
          STATUS         current
          DESCRIPTION
           "The primary server serving a configuration file."
          ::= { adGenGponOntProvEntry 20 }

adGenGponConfigFileSecondaryServer OBJECT-TYPE
          SYNTAX         DisplayString
          MAX-ACCESS     read-write
          STATUS         current
          DESCRIPTION
           "The secondary server serving a configuration file."
          ::= { adGenGponOntProvEntry 21 }

adGenGponConfigFileInterface OBJECT-TYPE
          SYNTAX         AdGenGponConfigFileInterface
          MAX-ACCESS     read-write
          STATUS         current
          DESCRIPTION
           "The interface used to retrieve the configuration file."
          ::= { adGenGponOntProvEntry 22 }

adGenGponConfigFilePath OBJECT-TYPE
          SYNTAX         DisplayString
          MAX-ACCESS     read-write
          STATUS         current
          DESCRIPTION
           "The configuration file path.  Contains the file name and any parameters passed to the
           config file server."
          ::= { adGenGponOntProvEntry 23 }

adGenGponConfigFileRetrieve OBJECT-TYPE
          SYNTAX         AdGenGponTrueFalseValue
          MAX-ACCESS     read-write
          STATUS         current
          DESCRIPTION
           "Used to trigger the config file retrieval by the ONT when there is
            a change in provisioning."
          ::= { adGenGponOntProvEntry 24 }

adGenGponMacSpoofingAllowed OBJECT-TYPE
          SYNTAX         AdGenGponEnableDisableValue
          MAX-ACCESS     read-write
          STATUS         current
          DESCRIPTION
           "Enable/Disable the ability to dynamically move mac addresses across ports on the same ONT."
          ::= { adGenGponOntProvEntry 25 }

adGenGponAcsServerProfile OBJECT-TYPE
          SYNTAX         DisplayString
          MAX-ACCESS     read-write
          STATUS         current
          DESCRIPTION
           "Attach an ACS profile to an ONT."
          ::= { adGenGponOntProvEntry 26 }

adGenGponOntVoIPConfigMethod OBJECT-TYPE
          SYNTAX  INTEGER
          {
            localONT      (0),
            omci          (1),
            fileRetrieval (2)
          }
          MAX-ACCESS     read-write
          STATUS         current
          DESCRIPTION
           "Specifies which method to use in order to configure VoIP to ONT.
           localONT: configure VoIP using the local ONT CLI commands;
           omci: configure VoIP using OMCI VoIP MEs;
           fileRetrival: configure VoIP using VoIP thru provisioning.
                 In this case the the OIDs adGenGponConfigFileRetrievalMethod,
                               adGenGponConfigFilePrimaryServer,
                                                   adGenGponConfigFileSecondaryServer,
                                                   adGenGponConfigFileInterface,
                                                   adGenGponConfigFilePath,
                                                   adGenGponConfigFileRetrieve
                         need to be configured properly"
          DEFVAL { fileRetrieval }
          ::= { adGenGponOntProvEntry 27 }

adGenGponOntVectoringEnable OBJECT-TYPE
          SYNTAX         INTEGER
          {
            disabled             (0),
            boardLevelEnabled    (1)
          }
          MAX-ACCESS     read-write
          STATUS         current
          DESCRIPTION
           "Set vdsl vectoring mode for all vdsl ports for this GPON ONT.
            Default value is disabled(0)."
          DEFVAL { disabled }
          ::= { adGenGponOntProvEntry 28 }

adGenGponOntSoftwareDownloadOnly OBJECT-TYPE
          SYNTAX         DisplayString
          MAX-ACCESS     read-write
          STATUS         current
          DESCRIPTION
           "Setting this OID with the ONT software version will start the software download to the ONT. This will only download the
            software but will not activate/commit the software. A GET on this OID will return the current ONT software version."
          ::= { adGenGponOntProvEntry 29 }

adGenGponOntSoftwareActivate OBJECT-TYPE
        SYNTAX         INTEGER
          {
            activateAndCommit (1)
          }
          MAX-ACCESS     read-write
          STATUS         current
          DESCRIPTION
           "Setting this OID will reboot the ONT and activate and commit the inactive software on the ONT."
          ::= { adGenGponOntProvEntry 30 }

adGenGponOntCpuRateLimitCountersClear OBJECT-TYPE
        SYNTAX         INTEGER
          {
            clear-counters (1)
          }
          MAX-ACCESS     read-write
          STATUS         current
          DESCRIPTION
           "Clears CPU Rate Limit Good and Drop Packets count."
          ::= { adGenGponOntProvEntry 31 }

-- GPON ONT Slot/Circuit Pack Provisioning

-- TBD: may require to add more for MDU units

-- GPON ONT Port Provisioning

adGenGponOntPortProvTable         OBJECT-TYPE
          SYNTAX         SEQUENCE OF AdGenGponOntPortProvEntry
          MAX-ACCESS     not-accessible
          STATUS         current
          DESCRIPTION
           "The ONT port provisioning table.
            Each table entry corresponds to an interface port."
          ::= { adGponProvisioning 4}

adGenGponOntPortProvEntry         OBJECT-TYPE
          SYNTAX         AdGenGponOntPortProvEntry
          MAX-ACCESS     not-accessible
          STATUS         current
          DESCRIPTION
           "An entry in the ONT port provisioning table.
            This entry represents an individual port of a particular type."
          INDEX  { ifIndex }
          ::= { adGenGponOntPortProvTable  1}

AdGenGponOntPortProvEntry    ::= SEQUENCE  {
      adGenGponOntPortAdminState           AdGenGponOntAdminState,
      adGenGponOntPortAutoDetectionConfiguration   AdGenGponOntPortAutoDetectMode,
      adGenGponOntPortBridgeIdorIpInd              INTEGER,
      adGenGponOntPortEthLoopbackConfiguration     INTEGER,
      adGenGponOntPortMaxFrameSize         Integer32,
      adGenGponOntPortDteOrDceInd          INTEGER,
      adGenGponOntPortPauseTime                Integer32,
      adGenGponOntPortPPPoEFilter          INTEGER,
      adGenGponOntPortPowerControl         INTEGER,
      adGenGponOntPortImpedance                    INTEGER,
      adGenGponOntPortTransmissionPath             INTEGER,
      adGenGponOntPortRxGain                       Integer32,
      adGenGponOntPortTxGain                       Integer32,
      adGenGponOntPortPotsHoldoverTime             Integer32,
      adGenGponOntPortPreprovIndicationFlag        AdGenGponTrueFalseValue,
      adGenGponOntPortLastError                    DisplayString,
      adGenGponOntPortRowStatus                    RowStatus,
      adGenGponOntPortOmciEthProvPrelimCheck       INTEGER,
      adGenGponOntVideoPortEnableLOSAlarm          AdGenGponEnableDisableValue,
      adGenGponOntVideoPortEnableOORLowAlarm       AdGenGponEnableDisableValue,
      adGenGponOntVideoPortEnableOORHighAlarm      AdGenGponEnableDisableValue,
      adGenGponOntVideoPortReturnPathMode                 AdGenGponOntVideoPortReturnPathMode,
      adGenGponOntVideoPortReturnPathFrequency            Integer32,
      adGenGponOntVideoPortReturnPathDestinationIPAddress IpAddress,
      adGenGponOntVideoPortReturnPathDestinationUDPPort   Integer32,
      adGenGponOntVideoPortReturnPathSourceUDPPort        Integer32,
      adGenGponOntPortDescriptionString                   DisplayString,
      adGenGponOntPortMapVEIPIfIndex                      InterfaceIndexOrZero,
      adGenGponOntPortMapBridgeGroupIfIndex               InterfaceIndexOrZero,
      adGenGponOntPortBridgeGroupAgingTime                Integer32,
      adGenGponOntPortBridgeGroupLearningLimit            Integer32,
      adGenGponOntPortBondingPeer                         Integer32
}

adGenGponOntPortAdminState OBJECT-TYPE
          SYNTAX         AdGenGponOntAdminState
          MAX-ACCESS     read-write
          STATUS         current
          DESCRIPTION
           "The Admin state of the GPON ONT Port."
          ::= { adGenGponOntPortProvEntry 1 }

adGenGponOntPortAutoDetectionConfiguration OBJECT-TYPE
          SYNTAX         AdGenGponOntPortAutoDetectMode
          MAX-ACCESS     read-write
          STATUS         deprecated
          DESCRIPTION
           "The Auto Detection Configuration value of GPON ONT Ethernet Port."
          ::= { adGenGponOntPortProvEntry 2 }

adGenGponOntPortBridgeIdorIpInd OBJECT-TYPE
          SYNTAX         INTEGER
          {
          bridged(0),
          ipRouter(1),
          dependsOnParent(2)
          }
          MAX-ACCESS     read-write
          STATUS         current
          DESCRIPTION
           "The Bridge or IP Indication value of GPON ONT Ethernet Port."
          ::= { adGenGponOntPortProvEntry 3 }

adGenGponOntPortEthLoopbackConfiguration OBJECT-TYPE
          SYNTAX         INTEGER
          {
          no(0),
          loop3(1)
          }
          MAX-ACCESS     read-write
          STATUS         current
          DESCRIPTION
           "The Loop back configuration of GPON ONT Ethernet Port."
          ::= { adGenGponOntPortProvEntry 4 }

adGenGponOntPortMaxFrameSize OBJECT-TYPE
          SYNTAX         Integer32
          MAX-ACCESS     read-write
          STATUS         current
          DESCRIPTION
           "The Maximum frame size allowed on GPON ONT Ethernet Port."
          ::= { adGenGponOntPortProvEntry 5 }

adGenGponOntPortDteOrDceInd OBJECT-TYPE
          SYNTAX         INTEGER
          {
          dce(0),
          dte(1)
          }
          MAX-ACCESS     read-write
          STATUS         current
          DESCRIPTION
           "The DCE or DTE indication value of GPON ONT Ethernet Port."
          ::= { adGenGponOntPortProvEntry 6 }

adGenGponOntPortPauseTime OBJECT-TYPE
          SYNTAX         Integer32
          MAX-ACCESS     read-write
          STATUS         current
          DESCRIPTION
           "The Pause time value of GPON ONT Ethernet Port."
          ::= { adGenGponOntPortProvEntry 7 }

adGenGponOntPortPPPoEFilter OBJECT-TYPE
          SYNTAX         INTEGER
          {
          allowAll(0),
          discardEverything(1)
          }
          MAX-ACCESS     read-write
          STATUS         current
          DESCRIPTION
           "The PPPoE Filter value of GPON ONT Ethernet Port."
          ::= { adGenGponOntPortProvEntry 8 }

adGenGponOntPortPowerControl OBJECT-TYPE
          SYNTAX         INTEGER
          {
          disable(0),
          enable(1)
          }
          MAX-ACCESS     read-write
          STATUS         current
          DESCRIPTION
           "The power control value of GPON ONT Ethernet Port."
          ::= { adGenGponOntPortProvEntry 9 }

adGenGponOntPortImpedance OBJECT-TYPE
          SYNTAX         INTEGER
          {
          sixHundredOhms(0),
          nineHundredOhms(1),
          c1150NfR1750ohmR2270ohm(2),
          c1115NfR1820ohmR2220ohm(3),
          c1230NfR11050ohmR2320ohm(4)
          }
          MAX-ACCESS     read-write
          STATUS         current
          DESCRIPTION
           "Impedance for GPON ONT Pots Port."
          ::= { adGenGponOntPortProvEntry 10 }

adGenGponOntPortTransmissionPath OBJECT-TYPE
          SYNTAX         INTEGER
          {
          fulltimeOnhook(0),
          parttimeOnhook(1)
          }
          MAX-ACCESS     read-write
          STATUS         current
          DESCRIPTION
           "Transmission mode of GPON ONT Pots Port."
          ::= { adGenGponOntPortProvEntry 11 }

adGenGponOntPortRxGain OBJECT-TYPE
          SYNTAX         Integer32
          MAX-ACCESS     read-write
          STATUS         current
          DESCRIPTION
           "Gain value for the received signal in the GPON ONT Pots Port.
            Unit is tenth of dB. Allowed range -120 to 60"
          ::= { adGenGponOntPortProvEntry 12 }

adGenGponOntPortTxGain OBJECT-TYPE
          SYNTAX         Integer32
          MAX-ACCESS     read-write
          STATUS         current
          DESCRIPTION
           "Gain value for the transmit signal in the GPON ONT Pots Port.
           Unit is tenth of dB. Allowed range -120 to 60"
          ::= { adGenGponOntPortProvEntry 13 }

adGenGponOntPortPotsHoldoverTime OBJECT-TYPE
          SYNTAX         Integer32
          MAX-ACCESS     read-write
          STATUS         current
          DESCRIPTION
           "Determines the time during which POTS loop voltage is
        held up when the ONT is not ranged on the PON."
          ::= { adGenGponOntPortProvEntry 14 }

adGenGponOntPortPreprovIndicationFlag OBJECT-TYPE
          SYNTAX         AdGenGponTrueFalseValue
          MAX-ACCESS     read-write
          STATUS         current
          DESCRIPTION
           "The flag to indicate whether the entry exists real or pre-provisioned from mgmt system."
          ::= { adGenGponOntPortProvEntry 15 }

adGenGponOntPortLastError OBJECT-TYPE
          SYNTAX         DisplayString
          MAX-ACCESS     read-only
          STATUS         current
          DESCRIPTION
           "The last error reported by this Interface configuration entity."
          ::= { adGenGponOntPortProvEntry 16 }

adGenGponOntPortRowStatus OBJECT-TYPE
          SYNTAX         RowStatus
          MAX-ACCESS     read-write
          STATUS         current
          DESCRIPTION
           "This object is used to create
            a new row or modify or delete an
            existing row in this table."
          ::= { adGenGponOntPortProvEntry 17 }

adGenGponOntPortOmciEthProvPrelimCheck OBJECT-TYPE
          SYNTAX         INTEGER {
                                valid (1),
                                invalid (2)
                                }
          MAX-ACCESS     read-only
          STATUS         current
          DESCRIPTION
           "The status of the OMCI Ethernet provisioning of this
           Interface to the degree that it can be determined by the
           OLT. The OLT must evaluate and accept commands on
           behalf of the ONTs, even in pre-provisioning cases. So there
           is a limited amount of validation that can be done. This OID
           represents the result of that limited validation."
          ::= { adGenGponOntPortProvEntry 18 }

adGenGponOntVideoPortEnableLOSAlarm OBJECT-TYPE
          SYNTAX         AdGenGponEnableDisableValue
          MAX-ACCESS     read-write
          STATUS         current
          DESCRIPTION
           "Used to enable/disable the LOS alarm generation on the ONT Video port ."
          ::= { adGenGponOntPortProvEntry 19 }

adGenGponOntVideoPortEnableOORLowAlarm OBJECT-TYPE
          SYNTAX         AdGenGponEnableDisableValue
          MAX-ACCESS     read-write
          STATUS         current
          DESCRIPTION
           "Used to enable/disable the OOR LOW alarm generation on the ONT Video port ."
          ::= { adGenGponOntPortProvEntry 20 }

adGenGponOntVideoPortEnableOORHighAlarm OBJECT-TYPE
          SYNTAX         AdGenGponEnableDisableValue
          MAX-ACCESS     read-write
          STATUS         current
          DESCRIPTION
           "Used to enable/disable the OOR HIGH alarm generation on the ONT Video port ."
          ::= { adGenGponOntPortProvEntry 21 }

adGenGponOntVideoPortReturnPathMode OBJECT-TYPE
    SYNTAX      AdGenGponOntVideoPortReturnPathMode
    MAX-ACCESS  read-write
    STATUS      current
    DESCRIPTION
    "This OID specifies the format to be used for the VRP service."
    ::= { adGenGponOntPortProvEntry 22 }

adGenGponOntVideoPortReturnPathFrequency OBJECT-TYPE
    SYNTAX      Integer32 (8096 .. 40000)
    MAX-ACCESS  read-write
    STATUS      current
    DESCRIPTION
    "This OID specifies the VRP tuner frequency to use, in units of kHz."
    ::= { adGenGponOntPortProvEntry 23 }

adGenGponOntVideoPortReturnPathDestinationIPAddress OBJECT-TYPE
    SYNTAX      IpAddress
    MAX-ACCESS  read-write
    STATUS      current
    DESCRIPTION
    "This OID specifies the IP address of the HEAD-END server for VRP service."
    ::= { adGenGponOntPortProvEntry 24 }

adGenGponOntVideoPortReturnPathDestinationUDPPort OBJECT-TYPE
    SYNTAX      Integer32
    MAX-ACCESS  read-write
    STATUS      current
    DESCRIPTION
    "This OID specifies the UDP port to use at the HEAD-END server for VRP service."
    ::= { adGenGponOntPortProvEntry 25 }

adGenGponOntVideoPortReturnPathSourceUDPPort OBJECT-TYPE
    SYNTAX      Integer32
    MAX-ACCESS  read-write
    STATUS      current
    DESCRIPTION
    "This OID specifies the UDP port to use at the ONT for VRP service."
    ::= { adGenGponOntPortProvEntry 26 }

 adGenGponOntPortDescriptionString OBJECT-TYPE
          SYNTAX         DisplayString
          MAX-ACCESS     read-write
          STATUS         current
          DESCRIPTION
           "Description for this particular GPON ONT Port."
          ::= { adGenGponOntPortProvEntry 27 }

adGenGponOntPortMapVEIPIfIndex OBJECT-TYPE
    SYNTAX      InterfaceIndexOrZero
    MAX-ACCESS  read-write
    STATUS      current
    DESCRIPTION
    "This is the ifIndex of the Virtual Ethernet Interface Point(VEIP) interface connected
     to a physical Ethernet ONT port. If zero, no VEIP is connected.
         For a SET operation to be accepted on this OID, the following must be true:
        - In the GPON extended ifIndex, the ONT and PON must be the same values
          for the VEIP as those for the physical port.
            - The virtual slot type included in the extended ifIndex must match the
              definition of virtualEthernet(10) defined in the adGenGponOntPortType.
         A  SET to this object is supported only for physical Ethernet ports."
     DEFVAL { 0 }
    ::= { adGenGponOntPortProvEntry 28 }

adGenGponOntPortMapBridgeGroupIfIndex OBJECT-TYPE
    SYNTAX      InterfaceIndexOrZero
    MAX-ACCESS  read-write
    STATUS      current
    DESCRIPTION
    "This is the ifIndex of a BridgeGroup of which this physical Ethernet ONT port is a member.
     If zero, port is not member of any BridgeGroup.
         For a SET operation to be accepted on this OID, the following must be true:
            - In the GPON extended ifIndex, the ONT and PON must be the same values
              for the BridgeGroup as those for the physical port.
            - The virtual slot type included in the extended ifIndex must match the
              definition of bridgeGroup(11) defined in the adGenGponOntPortType.
         A  SET to this object is supported only for physical Ethernet ports.
         Setting this oid to zero would remove port from the bridge group."
         DEFVAL { 0 }
    ::= { adGenGponOntPortProvEntry 29 }

adGenGponOntPortBridgeGroupAgingTime OBJECT-TYPE
    SYNTAX      Integer32 (10..1000000)
    MAX-ACCESS  read-write
    STATUS      current
    DESCRIPTION
    "This attribute specifies the age of dynamic filtering entries in the bridge database,
    after which unrefreshed entries are discarded.
    In accordance with [IEEE 802.1D] clause 7.9.2 and [IEEE 802.1Q] clause 8.8.3,
    the range is 10..1 000 000 seconds,
    with a resolution of 1 second and a default of 300 seconds"
    DEFVAL { 300 }
    ::= { adGenGponOntPortProvEntry 30 }

adGenGponOntPortBridgeGroupLearningLimit OBJECT-TYPE
    SYNTAX      Integer32 (0..255)
    MAX-ACCESS  read-write
    STATUS      current
    DESCRIPTION
    "This attribute specifies the maximum number of UNI MAC addresses to be learned by the bridge.
    The default value 0 specifies that there is no administratively-imposed limit."
    DEFVAL { 0 }
    ::= { adGenGponOntPortProvEntry 31 }

adGenGponOntPortBondingPeer OBJECT-TYPE
  SYNTAX    Integer32
  MAX-ACCESS  read-write
  STATUS    current
  DESCRIPTION
  "This attribute specifies the peer port number for 2-pair EFM Bonding.  The default value 0
   specifies that this port is not bonded and will operate as a single EFM Port."
  DEFVAL { 0 }
  ::= { adGenGponOntPortProvEntry 32 }

adGenGponOntPortExtendedFeatureProvTable         OBJECT-TYPE
          SYNTAX         SEQUENCE OF AdGenGponOntPortExtendedFeatureProvEntry
          MAX-ACCESS     not-accessible
          STATUS         current
          DESCRIPTION
           "This is the extension of ONT port provisioning table.
            Each table entry corresponds to an interface port supported
            by a circuit pack inserted into a GPON ONT slot."
          ::= { adGponProvisioning 5}

adGenGponOntPortExtendedFeatureProvEntry         OBJECT-TYPE
          SYNTAX         AdGenGponOntPortExtendedFeatureProvEntry
          MAX-ACCESS     not-accessible
          STATUS         current
          DESCRIPTION
           "An entry in the ONT port extended feature provisioning table."
          INDEX  { ifIndex }
          ::= { adGenGponOntPortExtendedFeatureProvTable  1}

AdGenGponOntPortExtendedFeatureProvEntry    ::= SEQUENCE  {
          adGenGponOntPortArc               Integer32,
      adGenGponOntPortArcInterval           Integer32,
      adGenGponOntPortSfThreshold           Integer32,
      adGenGponOntPortSdThreshold           Integer32,
      adGenGponOntPortLowerOpticalThreshold     Integer32,
      adGenGponOntPortUpperOpticalThreshold     Integer32,
      adGenGponOntPortGr303signalingCodeMode    Integer32,
          adGenGponOntPortGr303LineLoopBack     Integer32,
          adGenGponOntPortGr303PayloadLoopBack      Integer32,
      adGenGponOntPortGr303VoiceIpAddress       IpAddress
      }

adGenGponOntPortArc OBJECT-TYPE
          SYNTAX         Integer32 (0..255)
          MAX-ACCESS     read-write
          STATUS         current
          DESCRIPTION
           "The ARC of the ONT interface."
          ::= { adGenGponOntPortExtendedFeatureProvEntry 1 }

adGenGponOntPortArcInterval OBJECT-TYPE
          SYNTAX         Integer32 (0..255)
          MAX-ACCESS     read-write
          STATUS         current
          DESCRIPTION
           "The ARC Interval of the ONT interface."
          ::= { adGenGponOntPortExtendedFeatureProvEntry 2 }

adGenGponOntPortSfThreshold OBJECT-TYPE
          SYNTAX         Integer32 (0..255)
          MAX-ACCESS     read-write
          STATUS         current
          DESCRIPTION
           "The SF threshold of the PON interface."
          ::= { adGenGponOntPortExtendedFeatureProvEntry 3 }

adGenGponOntPortSdThreshold OBJECT-TYPE
          SYNTAX         Integer32 (0..255)
          MAX-ACCESS     read-write
          STATUS         current
          DESCRIPTION
           "The SD threshold of the PON interface."
          ::= { adGenGponOntPortExtendedFeatureProvEntry 4 }

adGenGponOntPortLowerOpticalThreshold OBJECT-TYPE
          SYNTAX         Integer32 (0..255)
          MAX-ACCESS     read-write
          STATUS         current
          DESCRIPTION
           "The lower optical level threshold of the PON interface."
          ::= { adGenGponOntPortExtendedFeatureProvEntry 5 }

adGenGponOntPortUpperOpticalThreshold OBJECT-TYPE
          SYNTAX         Integer32 (0..255)
          MAX-ACCESS     read-write
          STATUS         current
          DESCRIPTION
           "The upper optical level threshold of the PON interface."
          ::= { adGenGponOntPortExtendedFeatureProvEntry 6 }

adGenGponOntPortGr303signalingCodeMode OBJECT-TYPE
          SYNTAX         Integer32
          MAX-ACCESS     read-write
          STATUS         current
          DESCRIPTION
           "Gr303 signaling mode of the GPON ONT voice port."
          ::= { adGenGponOntPortExtendedFeatureProvEntry 7 }

adGenGponOntPortGr303LineLoopBack OBJECT-TYPE
          SYNTAX         Integer32
          MAX-ACCESS     read-write
          STATUS         current
          DESCRIPTION
           "Gr303 Loop back value of the GPON ONT voice port."
          ::= { adGenGponOntPortExtendedFeatureProvEntry 8 }

adGenGponOntPortGr303PayloadLoopBack OBJECT-TYPE
          SYNTAX         Integer32
          MAX-ACCESS     read-write
          STATUS         current
          DESCRIPTION
           "Gr303 pay load Loop back value of the GPON ONT voice port."
          ::= { adGenGponOntPortExtendedFeatureProvEntry 9 }

adGenGponOntPortGr303VoiceIpAddress OBJECT-TYPE
          SYNTAX         IpAddress
          MAX-ACCESS     read-write
          STATUS         current
          DESCRIPTION
           "Gr303 voice ip address of the GPON ONT voice port."
          ::= { adGenGponOntPortExtendedFeatureProvEntry 10 }

-- list of Discovered ONT Serial number on the PON interface

adGenGponPonDiscoveredOntSnTable         OBJECT-TYPE
          SYNTAX         SEQUENCE OF AdGenGponPonDiscoveredOntSnEntry
          MAX-ACCESS     not-accessible
          STATUS         current
          DESCRIPTION
           "The GPON PON Discovered ONT Serial Number table.
            Each table entry corresponds to a specific
            GPON PON Interface"
          ::= { adGponProvisioning 6}

adGenGponPonDiscoveredOntSnEntry         OBJECT-TYPE
          SYNTAX         AdGenGponPonDiscoveredOntSnEntry
          MAX-ACCESS     not-accessible
          STATUS         current
          DESCRIPTION
           "An entry in the Gpon PON Discovered ONT Serial Number table.
            This entry represents a particular Discovered ONT Serial Number. "
          INDEX  { ifIndex, adGenGponPonDiscoveredOntSerialNumberIndex }
          ::= { adGenGponPonDiscoveredOntSnTable  1}

AdGenGponPonDiscoveredOntSnEntry    ::= SEQUENCE  {
    adGenGponPonDiscoveredOntSerialNumberIndex         Integer32,
    adGenGponPonDiscoveredOntSerialNumber         DisplayString,
    adGenGponPonDiscoveredRegistrationId          DisplayString
}

adGenGponPonDiscoveredOntSerialNumberIndex OBJECT-TYPE
          SYNTAX         Integer32
          MAX-ACCESS     read-only
          STATUS         current
          DESCRIPTION
           "The list index of unrecognized ONT serial number
            that are learned as part of discovery process on this
            PON interface.  The actual range is a compile time
            constant of (MaxOltPort * MAX_ONTS_PER_PON)"
          ::= { adGenGponPonDiscoveredOntSnEntry 1 }

adGenGponPonDiscoveredOntSerialNumber OBJECT-TYPE
          SYNTAX         DisplayString
          MAX-ACCESS     read-only
          STATUS         current
          DESCRIPTION
           "The serial number of the unrecognized ONT
            that are learned as part of discovery process on this
            PON interface."
          ::= { adGenGponPonDiscoveredOntSnEntry 2 }

adGenGponPonDiscoveredRegistrationId OBJECT-TYPE
          SYNTAX         DisplayString
          MAX-ACCESS     read-only
          STATUS         current
          DESCRIPTION
           "The registration id of the unrecognized ONT
            that are learned as part of discovery process on this
            PON interface."
          ::= { adGenGponPonDiscoveredOntSnEntry 3 }

-- Status table

adGenGponOntStatusTable         OBJECT-TYPE
          SYNTAX         SEQUENCE OF AdGenGponOntStatusEntry
          MAX-ACCESS     not-accessible
          STATUS         current
          DESCRIPTION
           "The GPON ONT status table.
            Each table entry corresponds to a specific
            GPON ONT Equipment. "
          ::= { adGponStatus 1}

adGenGponOntStatusEntry         OBJECT-TYPE
          SYNTAX         AdGenGponOntStatusEntry
          MAX-ACCESS     not-accessible
          STATUS         current
          DESCRIPTION
           "An entry in the ONT-G status table.
            This entry represents a particular GPON ONT Equipment. "
          INDEX  { ifIndex }
          ::= { adGenGponOntStatusTable  1}

AdGenGponOntStatusEntry    ::= SEQUENCE  {
        adGenGponOntNumber                              Integer32,
        adGenGponOntTrafficManagementOption             INTEGER,
        adGenGponOntOmccVersion                         INTEGER,
        adGenGponOntMode                                INTEGER,
        adGenGponOntEquipmentID                         DisplayString,
        adGenGponOntUpTime                              DisplayString,
        adGenGponOntOperState                           AdGenGponOntOperState,
        adGenGponOntSoftwareDownloadStatus              INTEGER,
        adGenGponOntSoftwareDownloadProgress            Integer32,
        adGenGponOntActiveSoftwareVersion               DisplayString,
        adGenGponOntCurrentAvailableUpstreamBandwidth   Integer32,
        adGenGponOntPartNumber                          DisplayString,
        adGenGponOntHardwareRevision                    DisplayString,
        adGenGponOntCurrentAvailableDownstreamBandwidth Integer32,
        adGenGponOntLearnedSerialNumber                 DisplayString,
        adGenGponOntRssi                                Integer32,
        adGenGponAvailableVOIPConfigMethods             BITS,
        adGenGponConfigFileState                        AdGenGponConfigFileState,
        adGenGponConfigFileChecksum                     OCTET STRING,
        adGenGponConfigErrorString                      DisplayString,
        adGenGponOntUpstreamBIPError                    Counter32,
        adGenGponOntDownstreamBIPError                  Counter32,
        adGenGponOntUpstreamGoodDBRuCounter             Counter32,
        adGenGponOntUpstreamBadDBRuCounter              Counter32,
        adGenGponAcsServerProfileUserName               DisplayString,
        adGenGponAcsServerProfilePassword               DisplayString,
        adGenGponOntFeatureSupport                      BITS,
        adGenGponOntInactiveSoftwareVersion             DisplayString,
        adGenGponOntManagementMacAddress                PhysAddress,
        adGenGponOntFiberLength                         Integer32,
        adGenGponOntEqualizationDelay                   Integer32,
        adGenGponOntRxPower                             Integer32,
        adGenGponOntTxPower                             Integer32,
        adGenGponOntProductName                         DisplayString,
        adGenGponOntEverActivated                       AdGenGponTrueFalseValue,
        adGenGponOntTemperature                         Integer32,
        adGenGponOntBiasCurrent                         Integer32,
        adGenGponOntVoltage                             Integer32,
        adGenGponOntUsFecProcessedCodewords             Integer32,
        adGenGponOntUsFecCorrectedCodewords             Integer32,
        adGenGponOntUsFecCorrectedCodebytes             Integer32,
        adGenGponOntUsFecUncorrectedCodewords           Integer32,
        adGenGponGalEthDiscardedFrames                  Integer32
}

adGenGponOntNumber OBJECT-TYPE
          SYNTAX         Integer32 (1..64)
          MAX-ACCESS     read-only
          STATUS         current
          DESCRIPTION
           "A unique value of each GPON ONT on the PON."
          ::= { adGenGponOntStatusEntry 1 }

adGenGponOntTrafficManagementOption OBJECT-TYPE
          SYNTAX INTEGER
          {
            priorityControlled (0),
            rateControlled (1)
          }
          MAX-ACCESS     read-only
          STATUS         current
          DESCRIPTION
           "The traffic management option supported by the GPON ONT."
          ::= { adGenGponOntStatusEntry 2 }

adGenGponOntOmccVersion OBJECT-TYPE
          SYNTAX INTEGER
          {
           g984dot4June04 (128),
           g984dot4Amd1 (129),
           g984dot4Amd2 (130),
           g984dot4Amd3 (131),
           g984dot4Latest (132)
          }
          MAX-ACCESS     read-only
          STATUS         current
          DESCRIPTION
           "The OMCC version supported by the GPON ONT."
          ::= { adGenGponOntStatusEntry 3 }

adGenGponOntMode OBJECT-TYPE
-- values are - {ATM-only mode (0), GEM-only mode (1), both ATM and GEM mode (2)
          SYNTAX  INTEGER
          {
            atm (0),
            gem (1),
            dual (2)
          }
          MAX-ACCESS     read-only
          STATUS         current
          DESCRIPTION
           "The operating mode of the ONT PON interface."
          ::= { adGenGponOntStatusEntry 4 }

adGenGponOntEquipmentID OBJECT-TYPE
          SYNTAX         DisplayString
          MAX-ACCESS     read-only
          STATUS         current
          DESCRIPTION
           "The CLEI code of the GPON ONT."
          ::= { adGenGponOntStatusEntry 5 }

adGenGponOntUpTime OBJECT-TYPE
          SYNTAX         DisplayString
          MAX-ACCESS     read-only
          STATUS         current
          DESCRIPTION
           "A string containing the time since the ONT was last re-initialized.
            The string is in one of the following formats:

              d days, h hours, m minutes, s seconds
              w weeks, d days, h hours, m minutes, s seconds
              y years, w weeks, d days, h hours, m minutes, s seconds

            where:
              y is the number of years
              w is the number of weeks
              d is the number of days
              h is the number of hours
              m is the number of minutes
              s is the number of seconds"
          ::= { adGenGponOntStatusEntry 6 }

adGenGponOntOperState OBJECT-TYPE
          SYNTAX         AdGenGponOntOperState
          MAX-ACCESS     read-only
          STATUS         current
          DESCRIPTION
           "The operational state of the GPON ONT."
          ::= { adGenGponOntStatusEntry 7 }

adGenGponOntSoftwareDownloadStatus OBJECT-TYPE
          SYNTAX INTEGER
          {
            notStarted (0),
            downloadInProgress(1),
            downloadCompleted (2),
            activationAndReboot (3),
            activationCompleted (4),
            commitInProgress (5),
            commitCompleted (6),
            downloadFailed (7),
            activationFailed (8),
            commitFailed (9),
            sameversionSkipped (10),
            downloadPending (11),
            downloadCancelled(12),
            downloadCompletedNotActivated(13)
          }
          MAX-ACCESS     read-only
          STATUS         current
          DESCRIPTION
           "The software upload status of the particular GPON ONT."
          ::= { adGenGponOntStatusEntry 8 }

adGenGponOntSoftwareDownloadProgress OBJECT-TYPE
          SYNTAX         Integer32 (0..100)
          MAX-ACCESS     read-only
          STATUS         current
          DESCRIPTION
           "The software upload progress(in %) of the particular GPON ONT."
          ::= { adGenGponOntStatusEntry 9 }

adGenGponOntActiveSoftwareVersion OBJECT-TYPE
          SYNTAX         DisplayString
          MAX-ACCESS     read-only
          STATUS         current
          DESCRIPTION
           "The current running software version of the GPON ONT."
          ::= { adGenGponOntStatusEntry 10 }

adGenGponOntCurrentAvailableUpstreamBandwidth OBJECT-TYPE
          SYNTAX         Integer32
          MAX-ACCESS     read-only
          STATUS         current
          DESCRIPTION
           "The upstream bandwidth (minus all overheads) currently (kbps) available
            for subscription (on a particular PON)."
          ::= { adGenGponOntStatusEntry 11 }

adGenGponOntPartNumber OBJECT-TYPE
          SYNTAX         DisplayString
          MAX-ACCESS     read-only
          STATUS         current
          DESCRIPTION
           "The Part Number of the GPON ONT."
          ::= { adGenGponOntStatusEntry 12 }

adGenGponOntHardwareRevision OBJECT-TYPE
          SYNTAX         DisplayString
          MAX-ACCESS     read-only
          STATUS         current
          DESCRIPTION
           "The Hardware revision/version of the GPON ONT."
          ::= { adGenGponOntStatusEntry 13 }

adGenGponOntCurrentAvailableDownstreamBandwidth OBJECT-TYPE
          SYNTAX         Integer32
          MAX-ACCESS     read-only
          STATUS         current
          DESCRIPTION
           "The downstream bandwidth (minus all overheads) currently (kbps) available
            for subscription (on a particular PON)."
          ::= { adGenGponOntStatusEntry 14 }

adGenGponOntLearnedSerialNumber OBJECT-TYPE
          SYNTAX         DisplayString
          MAX-ACCESS     read-only
          STATUS         current
          DESCRIPTION
           "The unique Serial number of GPON ONT. Mainly
            useful to show the learned serial number when
            registration id mode is used during activation."
          ::= { adGenGponOntStatusEntry 15 }

adGenGponOntRssi OBJECT-TYPE
          SYNTAX         Integer32
          MAX-ACCESS     read-only
          STATUS         current
          DESCRIPTION
           "The OLT's RSSI (Received Signal Strength Indicatior) for this GPON ONT's optical signal.
           It is a measurement of this GPON ONT's optical transceiver power level(0.1dBm), received
           by the GPON OLT's optical transceiver. The default value -9999 indicates that the value is not available."
          ::= { adGenGponOntStatusEntry 16 }

adGenGponAvailableVOIPConfigMethods                 OBJECT-TYPE
        SYNTAX         BITS
                       {
                       omci(0),
                       configFileRetrieval(1),
                       tr69(2),
                       ietfSipping(3)
                       }
        MAX-ACCESS     read-only
        STATUS         current
        DESCRIPTION
        "Holds the bitmap of the configuration methods supported by the ONT.
         Will hold zero if no methods supported."
        ::= { adGenGponOntStatusEntry 17 }

adGenGponConfigFileState                        OBJECT-TYPE
        SYNTAX         AdGenGponConfigFileState
        MAX-ACCESS     read-only
        STATUS         current
        DESCRIPTION
        "Holds the state of the ONT configuration file processing."
        ::= { adGenGponOntStatusEntry 18 }

adGenGponConfigFileChecksum                     OBJECT-TYPE
        SYNTAX         OCTET STRING (SIZE(16))
        MAX-ACCESS     read-only
        STATUS         current
        DESCRIPTION
        "The MD5 digest of the ONT local config file."
        ::= { adGenGponOntStatusEntry 19 }

adGenGponConfigErrorString                      OBJECT-TYPE
        SYNTAX         DisplayString
        MAX-ACCESS     read-only
        STATUS         current
        DESCRIPTION
        "The error string associated with the config file alarm reported by the ONT."
        ::= { adGenGponOntStatusEntry 20 }

adGenGponOntUpstreamBIPError OBJECT-TYPE
          SYNTAX         Counter32
          MAX-ACCESS     read-only
          STATUS         current
          DESCRIPTION
          "The rolling counter of BIP (Bit-Interleaved Parity) errors for the ONT's upstream traffic flow:
          ONT => OLT"
          ::= { adGenGponOntStatusEntry 21 }

adGenGponOntDownstreamBIPError OBJECT-TYPE
          SYNTAX         Counter32
          MAX-ACCESS     read-only
          STATUS         current
          DESCRIPTION
          "The rolling counter of BIP (Bit-Interleaved Parity) errors for the ONT's downstream traffic flow:
          OLT => ONT"
          ::= { adGenGponOntStatusEntry 22 }

adGenGponOntUpstreamGoodDBRuCounter OBJECT-TYPE
          SYNTAX         Counter32
          MAX-ACCESS     read-only
          STATUS         current
          DESCRIPTION
          "The rolling counter of Good DBRu (Dynamic Bandwidth Report Upstream) for the ONT's upstream traffic:
          ONT => OLT"
          ::= { adGenGponOntStatusEntry 23 }

adGenGponOntUpstreamBadDBRuCounter OBJECT-TYPE
          SYNTAX         Counter32
          MAX-ACCESS     read-only
          STATUS         current
          DESCRIPTION
          "The rolling counter of Bad (CRC error) DBRu (Dynamic Bandwidth Report Upstream) for the ONT's upstream traffic:
          ONT => OLT"
          ::= { adGenGponOntStatusEntry 24 }

adGenGponAcsServerProfileUserName OBJECT-TYPE
          SYNTAX         DisplayString
          MAX-ACCESS     read-only
          STATUS         current
          DESCRIPTION
           "The generated TR69 username for this ONT."
          ::= { adGenGponOntStatusEntry 25 }

adGenGponAcsServerProfilePassword OBJECT-TYPE
          SYNTAX         DisplayString
          MAX-ACCESS     read-only
          STATUS         current
          DESCRIPTION
           "The generated TR69 password for this ONT."
          ::= { adGenGponOntStatusEntry 26 }

adGenGponOntFeatureSupport OBJECT-TYPE
        SYNTAX         BITS
                       {
                       ieee8021x(0)
                       }
        MAX-ACCESS     read-only
        STATUS         current
        DESCRIPTION
        "Holds the bitmap of the features supported by the ONT.
         Will hold zero if no features supported."
        ::= { adGenGponOntStatusEntry 27 }

adGenGponOntInactiveSoftwareVersion OBJECT-TYPE
          SYNTAX         DisplayString
          MAX-ACCESS     read-only
          STATUS         current
          DESCRIPTION
           "The current standby software version of the GPON ONT."
          ::= { adGenGponOntStatusEntry 28 }

adGenGponOntManagementMacAddress OBJECT-TYPE
          SYNTAX         PhysAddress
          MAX-ACCESS     read-only
          STATUS         current
          DESCRIPTION
           "The management MAC of the ONT either associated with ONT RADIUS CLIENT or with it's subtended Host provisioning."
          ::= { adGenGponOntStatusEntry 29 }

adGenGponOntFiberLength OBJECT-TYPE
          SYNTAX         Integer32
          UNITS        "meters"
          MAX-ACCESS     read-only
          STATUS         current
          DESCRIPTION
           "ONT Fiber distance in meters."
          ::= { adGenGponOntStatusEntry 30 }

adGenGponOntEqualizationDelay   OBJECT-TYPE
          SYNTAX         Integer32
          UNITS            "bits"
          MAX-ACCESS     read-only
          STATUS         current
          DESCRIPTION
           "ONT Equalization Delay in bits."
          ::= { adGenGponOntStatusEntry 31 }

adGenGponOntRxPower OBJECT-TYPE
          SYNTAX         Integer32
          UNITS          "tenth of dBm"
          MAX-ACCESS     read-only
          STATUS         current
          DESCRIPTION
           "The ONT's receive optical signal level.
           It is a measurement of the OLT's optical launch power (tenths of dBm), received by the ONT's optical transceiver.
           The default value -9999 indicates that the value is not available."
          ::= { adGenGponOntStatusEntry 32 }

adGenGponOntTxPower OBJECT-TYPE
          SYNTAX         Integer32
          UNITS          "tenth of dBm"
          MAX-ACCESS     read-only
          STATUS         current
          DESCRIPTION
           "The ONT's transmit optical signal level.
           It is a measurement of the ONT's optical launch power (tenths of dBm).
           The default value -9999 indicates that the value is not available."
          ::= { adGenGponOntStatusEntry 33 }

adGenGponOntProductName OBJECT-TYPE
        SYNTAX          DisplayString
        MAX-ACCESS      read-only
        STATUS          current
        DESCRIPTION
         "The Product Name of the ONT."
        ::= { adGenGponOntStatusEntry 34 }

adGenGponOntEverActivated OBJECT-TYPE
          SYNTAX         AdGenGponTrueFalseValue
          MAX-ACCESS     read-only
          STATUS         current
          DESCRIPTION
            "Indicates if ONT has been previously in the 'up' state on its PON.  This value should be false upon ONT ID creation but
             should return true once the ONT is in the 'up' state.  The value will only become false again if the ONT ID is deleted
             or the OLT is restarted."
          ::= { adGenGponOntStatusEntry 35 }

adGenGponOntTemperature OBJECT-TYPE
          SYNTAX         Integer32 (-64..63)
          UNITS          "degrees Celsius"
          MAX-ACCESS     read-only
          STATUS         current
          DESCRIPTION
           "The ONT's temperature.
           It is a measurement of the ONT's temperature (degrees C).
           The default value 127 indicates that the value is not available."
          ::= { adGenGponOntStatusEntry 36 }

adGenGponOntBiasCurrent OBJECT-TYPE
          SYNTAX         Integer32 (0..512)
          UNITS          "milliamps"
          MAX-ACCESS     read-only
          STATUS         current
          DESCRIPTION
           "The ONT's laser bias current.
           It is a measurement of the ONT's measured bias current (mA).
           The default value 0 indicates that the value is not available."
          ::= { adGenGponOntStatusEntry 37 }

adGenGponOntVoltage OBJECT-TYPE
          SYNTAX         Integer32 (0..50)
          UNITS          "tenths of volt"
          MAX-ACCESS     read-only
          STATUS         current
          DESCRIPTION
           "The ONT's transmit optical signal level.
           It is a measurement of the ONT's voltage (tenths of V).
           The default value 0 indicates that the value is not available."
          ::= { adGenGponOntStatusEntry 38 }

adGenGponOntUsFecProcessedCodewords OBJECT-TYPE
          SYNTAX         Integer32
          MAX-ACCESS     read-only
          STATUS         current
          DESCRIPTION
            "The rolling counter of FEC (Forward Error Correction) code words processed
             for the ONT's upstream traffic flow toward the OLT."
          ::= { adGenGponOntStatusEntry 39 }

adGenGponOntUsFecCorrectedCodewords OBJECT-TYPE
          SYNTAX         Integer32
          MAX-ACCESS     read-only
          STATUS         current
          DESCRIPTION
            "The rolling counter of FEC (Forward Error Correction) code words that were corrected
             for the ONT's upstream traffic flow toward the OLT."
          ::= { adGenGponOntStatusEntry 40 }

adGenGponOntUsFecCorrectedCodebytes OBJECT-TYPE
          SYNTAX         Integer32
          MAX-ACCESS     read-only
          STATUS         current
          DESCRIPTION
            "The rolling counter of FEC (Forward Error Correction) code bytes that were corrected
             for the ONT's upstream traffic flow toward the OLT."
          ::= { adGenGponOntStatusEntry 41 }

adGenGponOntUsFecUncorrectedCodewords OBJECT-TYPE
          SYNTAX         Integer32
          MAX-ACCESS     read-only
          STATUS         current
          DESCRIPTION
            "The rolling counter of FEC (Forward Error Correction) code words that were uncorrected
             for the ONT's upstream traffic flow toward the OLT."
          ::= { adGenGponOntStatusEntry 42 }

adGenGponGalEthDiscardedFrames OBJECT-TYPE
          SYNTAX         Integer32
          MAX-ACCESS     read-only
          STATUS         current
          DESCRIPTION
            "The rolling counter of downstream GEM frames discarded for any reason."
          ::= { adGenGponOntStatusEntry 43 }

-- GPON ONT slot status table

-- GPON ONT Port status table

adGenGponOntPortStatusTable         OBJECT-TYPE
          SYNTAX         SEQUENCE OF AdGenGponOntPortStatusEntry
          MAX-ACCESS     not-accessible
          STATUS         current
          DESCRIPTION
           "The ONT Port status table.
            Each table entry corresponds to a port of the
            GPON ONT. "
          ::= { adGponStatus 2}

adGenGponOntPortStatusEntry         OBJECT-TYPE
          SYNTAX         AdGenGponOntPortStatusEntry
          MAX-ACCESS     not-accessible
          STATUS         current
          DESCRIPTION
           "An entry in the ONT port status table.
            This entry represents a particular ONT Port."
          INDEX  { ifIndex }
          ::= { adGenGponOntPortStatusTable  1}


AdGenGponOntPortStatusEntry    ::= SEQUENCE  {
      adGenGponOntPortNumber                Integer32,
      adGenGponOntPortSrIndication          AdGenGponTrueFalseValue,
      adGenGponOntPortPiggybackDbaReporting INTEGER,
      adGenGponOntPortWholeOnuDbaReporting  INTEGER,
      adGenGponOntPortOpticalSignalLevel    Integer32,
      adGenGponOntPortType                  INTEGER,
      adGenGponOntPortConfigurationInd      INTEGER,
      adGenGponOntPortMaxGemPayloadSize     Integer32,
      adGenGponOntPortHookState             INTEGER,
      adGenGponOntPortOperState             AdGenGponOntPortOperState,
      adGenGponOntPortGemBlockLength        Integer32,
      adGenGponOntPortGr303CrvPortNumber    Integer32,
      adGenGponOntPortRFSignalLevel         Integer32,
      adGenGponOntPortRFOpticalSignalLevel  Integer32,
      adGenGponOntPortErrorString           DisplayString,
      adGenGponOntPortConnectToVEIP         OCTET STRING,
      adGenGponOntPortConnectToBridgeGroup  OCTET STRING
      }

adGenGponOntPortNumber OBJECT-TYPE
          SYNTAX         Integer32
          MAX-ACCESS     read-only
          STATUS         current
          DESCRIPTION
           "The GPON ONT Port Number."
          ::= { adGenGponOntPortStatusEntry 1 }

adGenGponOntPortSrIndication OBJECT-TYPE
          SYNTAX         AdGenGponTrueFalseValue
          MAX-ACCESS     read-only
          STATUS         current
          DESCRIPTION
           "The SR Indication for the PON interface."
          ::= { adGenGponOntPortStatusEntry 2 }

adGenGponOntPortPiggybackDbaReporting OBJECT-TYPE
          SYNTAX INTEGER
          {
          modeZeroOnly (0),
          modesZeroAndOne (1),
          modesZeroAndTwo (2),
          modesZeroOneAndTwo (3),
          noPiggybackDBA (4)
          }
          MAX-ACCESS     read-only
          STATUS         current
          DESCRIPTION
           "The configuration option for piggyback DBA reporting
       for the GPON ONT Physical Pon Interface."
          ::= { adGenGponOntPortStatusEntry 3 }

adGenGponOntPortWholeOnuDbaReporting OBJECT-TYPE
          SYNTAX INTEGER
          {
          notsupported(0),
          supported(1)
          }
          MAX-ACCESS     read-only
          STATUS         current
          DESCRIPTION
           "The whole-onu DBA reporting configuration option for the
       GPON ONT physical Pon Interface."
          ::= { adGenGponOntPortStatusEntry 4 }

adGenGponOntPortOpticalSignalLevel OBJECT-TYPE
          SYNTAX         Integer32
          MAX-ACCESS     read-only
          STATUS         current
          DESCRIPTION
           "The optical signal level (in dBmW) of the PON interface."
          ::= { adGenGponOntPortStatusEntry 5 }

adGenGponOntPortType OBJECT-TYPE
          SYNTAX INTEGER {
            ethernet (1),
            pots (2),
            video (3),
--          voip (4),  No port entries can be created with this portType. This is used to create IfIndex for Voice User.
            efmGroup(5),
            ds1 (6),
            gpon (7),
            iphost (8),
            e1 (9),
            virtualEthernet (10),
            bridgeGroup (11),
            pseudowire(12),
            xdsl(13),
            efmPort(14),
            efmLink(15)
            }
          MAX-ACCESS     read-only
          STATUS         current
          DESCRIPTION
           "The type of GPON ONT Port technology."
          ::= { adGenGponOntPortStatusEntry 6 }


adGenGponOntPortConfigurationInd OBJECT-TYPE
          SYNTAX INTEGER
          {
            unknown (0),
            tenBaseTFullDuplex (1),
            hundredBaseTFullDuplex (2),
            gigabitEthernetFullDuplex (3),
            tenGigabitEthernetFullDuplex (4),
            twentyFiveHundredEthernetFullDuplex (5),
            fiveGigabitEthernetFullDuplex (6),
            tenBaseTHalfDuplex (17),
            hundredBaseTHalfDuplex (18),
            gigabitEthernetHalfDuplex (19)
          }
          MAX-ACCESS     read-only
          STATUS         current
          DESCRIPTION
           "The Port Configuration Indication value of GPON ONT Ethernet Port."
          ::= { adGenGponOntPortStatusEntry 7 }

adGenGponOntPortMaxGemPayloadSize OBJECT-TYPE
          SYNTAX         Integer32
          MAX-ACCESS     read-only
          STATUS         current
          DESCRIPTION
           "Max Pay load size supported on the GPON ONT Gem Port."
          ::= { adGenGponOntPortStatusEntry 8 }

adGenGponOntPortHookState OBJECT-TYPE
          SYNTAX INTEGER
          {
             onHook(0),
             offHook(1)
          }
          MAX-ACCESS     read-only
          STATUS         current
          DESCRIPTION
           "Current state of the subscriber line in the GPON ONT Pots Port."
          ::= { adGenGponOntPortStatusEntry 9 }

adGenGponOntPortOperState OBJECT-TYPE
          SYNTAX         AdGenGponOntPortOperState
          MAX-ACCESS     read-only
          STATUS         current
          DESCRIPTION
           "The operational state of the GPON ONT Port."
          ::= { adGenGponOntPortStatusEntry 10 }

adGenGponOntPortGemBlockLength OBJECT-TYPE
          SYNTAX         Integer32
          MAX-ACCESS     read-only
          STATUS         current
          DESCRIPTION
           "The GEM Block Length configured for the PON interface."
          ::= { adGenGponOntPortStatusEntry 11 }

adGenGponOntPortGr303CrvPortNumber OBJECT-TYPE
          SYNTAX         Integer32
          MAX-ACCESS     read-only
          STATUS         current
          DESCRIPTION
           "The mapped GR303 CRV port number of the POTS interface
            (based on the static mapping calculation)."
          ::= { adGenGponOntPortStatusEntry 12 }

adGenGponOntPortRFSignalLevel OBJECT-TYPE
          SYNTAX         Integer32
          MAX-ACCESS     read-only
          STATUS         current
          DESCRIPTION
           "The RF signal level is a measurement of this GPON ONT's
           RF port output signal level in dBmV. A return value of
           -9999 indicates that a valid value can not be obtained from ONT."
          ::= { adGenGponOntPortStatusEntry 13 }

adGenGponOntPortRFOpticalSignalLevel OBJECT-TYPE
          SYNTAX         Integer32
          MAX-ACCESS     read-only
          STATUS         current
          DESCRIPTION
           "The optical signal level (in dBuW) of the Video(RF) port."
          ::= { adGenGponOntPortStatusEntry 14 }

adGenGponOntPortErrorString OBJECT-TYPE
          SYNTAX         DisplayString
          MAX-ACCESS     read-only
          STATUS         current
          DESCRIPTION
           "The error string associated with the ONT port."
          ::= { adGenGponOntPortStatusEntry 15 }

adGenGponOntPortConnectToVEIP OBJECT-TYPE
          SYNTAX         OCTET STRING (SIZE(0..64))
          MAX-ACCESS     read-only
          STATUS         current
          DESCRIPTION
           "Array reporting the UNI connected to the specified Virtual Ethernet Interface Point.
            When a UNI is connected to a Virtual Ethernet Interface Point the port id will be assigned to the first available octet."
          ::= { adGenGponOntPortStatusEntry 16 }

adGenGponOntPortConnectToBridgeGroup OBJECT-TYPE
          SYNTAX         OCTET STRING (SIZE(0..64))
          MAX-ACCESS     read-only
          STATUS         current
          DESCRIPTION
           "Array reporting the UNI connected to the specified Bridge group.
            When a UNI is connected to  a Bridge group the port id will be assigned to the first available octet."
          ::= { adGenGponOntPortStatusEntry 17 }

adGenGponOntInventoryInfoTable         OBJECT-TYPE
          SYNTAX         SEQUENCE OF AdGenGponOntInventoryInfoEntry
          MAX-ACCESS     not-accessible
          STATUS         current
          DESCRIPTION
           "The ONT Inventory Info."
          ::= { adGponStatus 3}

adGenGponOntInventoryInfoEntry         OBJECT-TYPE
          SYNTAX         AdGenGponOntInventoryInfoEntry
          MAX-ACCESS     not-accessible
          STATUS         current
          DESCRIPTION
            "This entry represents a particular ONT technology."
          INDEX  { ifIndex }
          ::= { adGenGponOntInventoryInfoTable  1}


AdGenGponOntInventoryInfoEntry    ::= SEQUENCE  {
          adGenGponOntSupportedType                 INTEGER,
          adGenGponOntMaxPortsPerType               Integer32
          }

adGenGponOntSupportedType OBJECT-TYPE
          SYNTAX INTEGER
          {
             ethernet (1),
             pots (2),
             video (3),
--           voip (4), No port entries are created with this portType. This is used for Voice User.
             efmGroup (5),
             ds1 (6),
             gpon (7),
             iphost (8),
             e1 (9),
             virtualEthernet (10),
             bridgeGroup (11),
             pseudowire (12),
             xdsl (13),
             efmPort(14),
             efmLink(15)
          }
          MAX-ACCESS     read-only
          STATUS         current
          DESCRIPTION
           "The supported GPON ONT technology/type (Ex: Ethernet, Pots, etc..)"
          ::= { adGenGponOntInventoryInfoEntry 1 }

adGenGponOntMaxPortsPerType OBJECT-TYPE
          SYNTAX         Integer32
          MAX-ACCESS     read-only
          STATUS         current
          DESCRIPTION
           "The Maximum available ports per technology/type (reported from ONT)."
          ::= { adGenGponOntInventoryInfoEntry 2 }

adGenGponPonStatusTable         OBJECT-TYPE
          SYNTAX         SEQUENCE OF AdGenGponPonStatusEntry
          MAX-ACCESS     not-accessible
          STATUS         current
          DESCRIPTION
           "The GPON PON status table.
            Each table entry corresponds to a specific
            GPON PON interface. "
          ::= { adGponStatus 4}

adGenGponPonStatusEntry         OBJECT-TYPE
          SYNTAX         AdGenGponPonStatusEntry
          MAX-ACCESS     not-accessible
          STATUS         current
          DESCRIPTION
           "This entry represents a particular GPON PON interface. "
          INDEX  { ifIndex }
          ::= { adGenGponPonStatusTable  1}

AdGenGponPonStatusEntry    ::= SEQUENCE  {

    adGenGponPonOntSoftwareDownloadInProgress   AdGenGponYesNoValue,
    adGenGponPonConfiguredOnts                  Integer32,
    adGenGponPonDiscoveringOnts                 Integer32,
    adGenGponPonUnrecognizedOnts                Integer32,
    adGenGponPonOperationallyUpOnts             Integer32,
    adGenGponPonAvailableUpstreamBandwidth      Integer32,
    adGenGponPonAvailableDownstreamBandwidth    Integer32,
    adGenGponPonLongestFiberDistance            Integer32,
    adGenGponPonShortestFiberDistance           Integer32,
    adGenGponPonNearestOnt                      Integer32,
    adGenGponPonFarthestOnt                     Integer32,
    adGenGponPonTotalProvDownstreamBandwidth    Integer32,
    adGenGponPonTotalProvUpstreamBandwidth      Integer32,
    adGenGponPonTotalProvFixedAssuredBandwidth  Integer32,
    adGenGponPonNextAvailableOntId              Integer32,
    adGenGponPonAvailableFixedAssuredBandwidth  Integer32,
    adGenGponPonCurrDownstreamBandwidth         Integer32,
    adGenGponPonCurrUpstreamBandwidth           Integer32,
    adGenGponPonCurrFixedAssuredBandwidth       Integer32,
    adGenGponPonTotalProvFixedBandwidth         Integer32,
    adGenGponPonTotalProvAssuredBandwidth       Integer32,
    adGenGponPonMaxOnts                         Integer32,
    adGenGponPonMaxServicesPerOnt               Integer32,
    adGenGponPonLosNumOntsDown                  Integer32,
    adGenGponPonMulticastCacStatus              AdGenGponMulticastCacStatus,
    adGenGponPonDownstreamAvailableMinRate      Integer32,
    adGenGponPonDownstreamCurrentMinRate        Integer32,
    adGenGponPonTechnology                      INTEGER,
    adGenGponPonWavelength                      INTEGER
}

adGenGponPonOntSoftwareDownloadInProgress OBJECT-TYPE
          SYNTAX         AdGenGponYesNoValue
          MAX-ACCESS     read-only
          STATUS         current
          DESCRIPTION
           "Indicates whether or not the ONT software download is in progress
            on this GPON PON interface"
          ::= { adGenGponPonStatusEntry 1 }

adGenGponPonConfiguredOnts  OBJECT-TYPE
          SYNTAX         Integer32
          MAX-ACCESS     read-only
          STATUS         current
          DESCRIPTION
           "Shows the number of ONTs configured in this PON interface."
          ::= { adGenGponPonStatusEntry 2 }

adGenGponPonDiscoveringOnts OBJECT-TYPE
          SYNTAX         Integer32
          MAX-ACCESS     read-only
          STATUS         current
          DESCRIPTION
           "Shows the number of ONTs discovering in this PON interface."
          ::= { adGenGponPonStatusEntry 3 }

adGenGponPonUnrecognizedOnts    OBJECT-TYPE
          SYNTAX         Integer32
          MAX-ACCESS     read-only
          STATUS         current
          DESCRIPTION
           "Shows the number of ONTs unrecognized in this PON interface."
          ::= { adGenGponPonStatusEntry 4 }

adGenGponPonOperationallyUpOnts OBJECT-TYPE
          SYNTAX         Integer32
          MAX-ACCESS     read-only
          STATUS         current
          DESCRIPTION
           "Shows the number of ONTs that are operationally UP in this PON interface."
          ::= { adGenGponPonStatusEntry 5 }
adGenGponPonAvailableUpstreamBandwidth  OBJECT-TYPE
          SYNTAX         Integer32
          MAX-ACCESS     read-only
          STATUS         current
          DESCRIPTION
           "The available PIR upstream bandwidth in kbps in this PON interface.  This will always be the line
            rate when oversubscription is supported - more best effort bandwidth can always be provisioned.  It
            will decrement when oversubscription is not supported, since best effort bandwidth is not supported."
          ::= { adGenGponPonStatusEntry 6 }
adGenGponPonAvailableDownstreamBandwidth    OBJECT-TYPE
          SYNTAX         Integer32
          MAX-ACCESS     read-only
          STATUS         current
          DESCRIPTION
           "Shows the available downstream bandwidth in kbps in this PON interface."
          ::= { adGenGponPonStatusEntry 7 }

adGenGponPonLongestFiberDistance    OBJECT-TYPE
          SYNTAX         Integer32
          MAX-ACCESS     read-only
          STATUS         current
          DESCRIPTION
           "Shows the longest fiber distance in metres in this PON interface."
          ::= { adGenGponPonStatusEntry 8 }

adGenGponPonShortestFiberDistance   OBJECT-TYPE
          SYNTAX         Integer32
          MAX-ACCESS     read-only
          STATUS         current
          DESCRIPTION
           "Shows the shortest fiber distance in metres in this PON interface."
          ::= { adGenGponPonStatusEntry 9 }

adGenGponPonNearestOnt  OBJECT-TYPE
          SYNTAX         Integer32
          MAX-ACCESS     read-only
          STATUS         current
          DESCRIPTION
           "Shows the nearest ONT ID to this PON interface."
          ::= { adGenGponPonStatusEntry 10 }

adGenGponPonFarthestOnt OBJECT-TYPE
          SYNTAX         Integer32
          MAX-ACCESS     read-only
          STATUS         current
          DESCRIPTION
           "Shows the farthest ONT ID to this PON interface."
          ::= { adGenGponPonStatusEntry 11 }

adGenGponPonTotalProvDownstreamBandwidth OBJECT-TYPE
          SYNTAX         Integer32
          MAX-ACCESS     read-only
          STATUS         current
          DESCRIPTION
           "The sum of all peak information rates on running downstream shapers provisioned on this PON interface."
          ::= { adGenGponPonStatusEntry 12 }

adGenGponPonTotalProvUpstreamBandwidth OBJECT-TYPE
          SYNTAX         Integer32
          MAX-ACCESS     read-only
          STATUS         current
          DESCRIPTION
           "The sum of all peak information rates on running upstream shapers provisioned on this PON interface."
          ::= { adGenGponPonStatusEntry 13 }

adGenGponPonTotalProvFixedAssuredBandwidth OBJECT-TYPE
          SYNTAX         Integer32
          MAX-ACCESS     read-only
          STATUS         current
          DESCRIPTION
           "The sum of all fixed and assured rates on running upstream shapers provisioned on this PON interface.
            The sum includes OMCI, VOIP, and PWE bandwidth as well as the provisioned assured and fixed rates."
          ::= { adGenGponPonStatusEntry 14 }

adGenGponPonNextAvailableOntId OBJECT-TYPE
          SYNTAX         Integer32
          MAX-ACCESS     read-only
          STATUS         current
          DESCRIPTION
           "The first available ONT ID (in numeric order) that can be assigned to an ONT on this PON interface. A
            value of -1 means no ONT ID available for use."
          ::= { adGenGponPonStatusEntry 15 }

adGenGponPonAvailableFixedAssuredBandwidth OBJECT-TYPE
          SYNTAX         Integer32
          MAX-ACCESS     read-only
          STATUS         current
          DESCRIPTION
           "Shows the available fixed and assured bandwidth in kbps left on this PON before reaching the line rate."
          ::= { adGenGponPonStatusEntry 16 }

adGenGponPonCurrDownstreamBandwidth OBJECT-TYPE
          SYNTAX         Integer32
          MAX-ACCESS     read-only
          STATUS         current
          DESCRIPTION
           "Shows the downstream bandwidth in kbps setup in hardware on this PON."
          ::= { adGenGponPonStatusEntry 17 }

adGenGponPonCurrUpstreamBandwidth OBJECT-TYPE
          SYNTAX         Integer32
          MAX-ACCESS     read-only
          STATUS         current
          DESCRIPTION
           "Shows the upstream bandwidth in kbps setup in hardware on this PON."
          ::= { adGenGponPonStatusEntry 18 }

adGenGponPonCurrFixedAssuredBandwidth OBJECT-TYPE
          SYNTAX         Integer32
          MAX-ACCESS     read-only
          STATUS         current
          DESCRIPTION
           "Shows the fixed and assured bandwidth in kbps setup in hardware on this PON."
          ::= { adGenGponPonStatusEntry 19 }

adGenGponPonTotalProvFixedBandwidth OBJECT-TYPE
          SYNTAX         Integer32
          UNITS        "kbps"
          MAX-ACCESS     read-only
          STATUS         current
          DESCRIPTION
           "The sum of all fixed rates in kbps on running upstream shapers provisioned on this PON interface."
          ::= { adGenGponPonStatusEntry 20 }

adGenGponPonTotalProvAssuredBandwidth OBJECT-TYPE
          SYNTAX         Integer32
          UNITS        "kbps"
          MAX-ACCESS     read-only
          STATUS         current
          DESCRIPTION
           "The sum of all assured rates in kbps on running upstream shapers provisioned on this PON interface."
          ::= { adGenGponPonStatusEntry 21 }

adGenGponPonMaxOnts OBJECT-TYPE
         SYNTAX          Integer32
         MAX-ACCESS      read-only
         STATUS          current
         DESCRIPTION
          "The maximum number of ONTs that can be running on this PON interface."
         ::= { adGenGponPonStatusEntry 22 }

adGenGponPonMaxServicesPerOnt OBJECT-TYPE
         SYNTAX          Integer32
         MAX-ACCESS      read-only
         STATUS          current
         DESCRIPTION
          "The maximum number of services that can be running per ONT on this PON interface."
         ::= { adGenGponPonStatusEntry 23 }

 adGenGponPonLosNumOntsDown OBJECT-TYPE
       SYNTAX       Integer32
       MAX-ACCESS   read-only
       STATUS       current
       DESCRIPTION
         "The number of ONTs that are operationally down on a PON that causes to exceed the PON LOS
           active threshold and raise the PON LOS alarm."
        ::= { adGenGponPonStatusEntry 24 }

 adGenGponPonMulticastCacStatus OBJECT-TYPE
       SYNTAX       AdGenGponMulticastCacStatus
       MAX-ACCESS   read-only
       STATUS       current
       DESCRIPTION
         "The multicast CAC status on the PON. If 'rejecting' any new IGMP group join messages would be
          rejected due to CAC. If 'admitting' IGMP joins would not be rejected due to CAC.
          If 'disabled' multicast CAC and MulticastBwThresholdAlarm are disabled on the PON."
        ::= { adGenGponPonStatusEntry 25 }

adGenGponPonDownstreamAvailableMinRate OBJECT-TYPE
          SYNTAX         Integer32
          UNITS          "kbps"
          MAX-ACCESS     read-only
          STATUS         current
          DESCRIPTION
           "The available per PON downstream min rate."
          ::= { adGenGponPonStatusEntry 26 }

adGenGponPonDownstreamCurrentMinRate OBJECT-TYPE
          SYNTAX         Integer32
          UNITS          "kbps"
          MAX-ACCESS     read-only
          STATUS         current
          DESCRIPTION
           "The total subscribed minimum rate (bandwidth) by all onts on the pon."
          ::= { adGenGponPonStatusEntry 27 }

adGenGponPonTechnology OBJECT-TYPE
        SYNTAX INTEGER
        {
            gpon                    (0),
            xgspon                  (1),
            ngpon2                  (2),
            wdmpon                  (3),
            cannnotDetectTechnology (30),
            technologyReportingNotSupported(31)
        }
        MAX-ACCESS     read-only
        STATUS         current
        DESCRIPTION
            "Indicates the PON technology on this interface"
        ::= { adGenGponPonStatusEntry 28 }

adGenGponPonWavelength OBJECT-TYPE
        SYNTAX INTEGER
        {
            wavelength1490down1310up (0),
            wavelength1577down1270up (1),
            wavelength1596down1538up (2),
            wavelength1597down1537up (3),
            wavelength1598down1536up (4),
            wavelength1598down1535up (5),
            wavelength1599down1535up (6),
            wavelength1600down1534up (7),
            wavelength1601down1533up (8),
            wavelength1602down1532up (9),
            cannotDetectWavelength   (30),
            wavelengthReportingNotSupported(31)
        }
        MAX-ACCESS     read-only
        STATUS         current
        DESCRIPTION
            "The current wavelength of this PON interface"
        ::= { adGenGponPonStatusEntry 29 }

-- *******************************************************************************
--  Performance Monitoring Counters
-- *******************************************************************************

-- GPON PON stats

adGenGponPon15MinPMTable      OBJECT-TYPE
          SYNTAX         SEQUENCE OF AdGenGponPon15MinPMEntry
          MAX-ACCESS     not-accessible
          STATUS         current
          DESCRIPTION
           "The GPON PON PM table.
            Each table entry corresponds to GPON PON interface "
          ::= { adGponPerformance 1}

adGenGponPon15MinPMEntry         OBJECT-TYPE
          SYNTAX         AdGenGponPon15MinPMEntry
          MAX-ACCESS     not-accessible
          STATUS         current
          DESCRIPTION
           "An entry in the GPON PON PM table. "
          INDEX  { ifIndex, adGenGponPon15MinPMIntervalNumber }
          ::= { adGenGponPon15MinPMTable  1}


AdGenGponPon15MinPMEntry    ::= SEQUENCE  {
      adGenGponPon15MinPMIntervalNumber          INTEGER,
      adGenGponPon15MinRxEthernetPackets         Gauge32,
      adGenGponPon15MinRxOMCIPackets             Gauge32,
      adGenGponPon15MinTxEthernetPackets         Gauge32,
      adGenGponPon15MinTxOMCIPackets             Gauge32,
      adGenGponPon15MinUpstreamBIPError          Gauge32,
      adGenGponPon15MinUpstreamDroppedPackets    Gauge32,
      adGenGponPon15MinBufferOverflow            Gauge32,
      adGenGponPon15MinPacketFragError           Gauge32,
      adGenGponPon15MinIntervalTimeStamp         DisplayString,
      adGenGponPon15MinRxEthernetBytes           Counter64,
      adGenGponPon15MinTxEthernetBytes           Counter64,
      adGenGponPon15MinUsBwAverageUtil           Gauge32,
      adGenGponPon15MinUsBwPeakUtil              Gauge32,
      adGenGponPon15MinDsBwAverageUtil           Gauge32,
      adGenGponPon15MinDsBwPeakUtil              Gauge32,
      adGenGponPon15MinDsMulticastPackets        Gauge32,
      adGenGponPon15MinDsMulticastBytes          Counter64,
      adGenGponPon15MinDsMulticastBwAverageUtil  Gauge32,
      adGenGponPon15MinDsMulticastBwPeakUtil     Gauge32,
      adGenGponPon15MinDownstreamBIPError        Gauge32
      }

adGenGponPon15MinPMIntervalNumber OBJECT-TYPE
          SYNTAX         INTEGER (1..96)
          MAX-ACCESS     not-accessible
          STATUS         current
          DESCRIPTION
           "A number between 1 and 96, where 1 is the most
            recently completed 15 minute interval and 96 is
            the 15 minutes interval completed 23 hours and 45
            minutes prior to interval 1."
          ::= { adGenGponPon15MinPMEntry 1 }

adGenGponPon15MinRxEthernetPackets OBJECT-TYPE
          SYNTAX         Gauge32
          MAX-ACCESS     read-only
          STATUS         current
          DESCRIPTION
           "The count of received ethernet packets on this PON interface. "
          ::= { adGenGponPon15MinPMEntry 2 }

adGenGponPon15MinRxOMCIPackets OBJECT-TYPE
          SYNTAX         Gauge32
          MAX-ACCESS     read-only
          STATUS         current
          DESCRIPTION
           "The count of received OMCI packets on this PON interface. "
          ::= { adGenGponPon15MinPMEntry 3 }

adGenGponPon15MinTxEthernetPackets OBJECT-TYPE
          SYNTAX         Gauge32
          MAX-ACCESS     read-only
          STATUS         current
          DESCRIPTION
           "The count of transmitted ethernet packets on this PON interface. "
          ::= { adGenGponPon15MinPMEntry 4 }

adGenGponPon15MinTxOMCIPackets OBJECT-TYPE
          SYNTAX         Gauge32
          MAX-ACCESS     read-only
          STATUS         current
          DESCRIPTION
           "The count of transmitted OMCI packets on this PON interface. "
          ::= { adGenGponPon15MinPMEntry 5 }

adGenGponPon15MinUpstreamBIPError OBJECT-TYPE
          SYNTAX         Gauge32
          MAX-ACCESS     read-only
          STATUS         current
          DESCRIPTION
           "The count of BIP error in the upstream direction on this PON
       interface. "
          ::= { adGenGponPon15MinPMEntry 6 }

adGenGponPon15MinUpstreamDroppedPackets OBJECT-TYPE
          SYNTAX         Gauge32
          MAX-ACCESS     read-only
          STATUS         current
          DESCRIPTION
           "The count of dropped packets in the upstream direction on this PON
       interface. "
          ::= { adGenGponPon15MinPMEntry 7 }

adGenGponPon15MinBufferOverflow OBJECT-TYPE
          SYNTAX         Gauge32
          MAX-ACCESS     read-only
          STATUS         current
          DESCRIPTION
           "The count of buffer overflow on this PON interface. "
          ::= { adGenGponPon15MinPMEntry 8 }

adGenGponPon15MinPacketFragError OBJECT-TYPE
          SYNTAX         Gauge32
          MAX-ACCESS     read-only
          STATUS         current
          DESCRIPTION
           "The count of packet fragmentation error on this PON interface. "
          ::= { adGenGponPon15MinPMEntry 9 }

adGenGponPon15MinIntervalTimeStamp OBJECT-TYPE
      SYNTAX          DisplayString
      MAX-ACCESS      read-only
      STATUS          current
      DESCRIPTION
        "Timestamp of the 15-minute interval"

      ::= { adGenGponPon15MinPMEntry 10 }

adGenGponPon15MinRxEthernetBytes OBJECT-TYPE
          SYNTAX         Counter64
          MAX-ACCESS     read-only
          STATUS         current
          DESCRIPTION
           "The count of received ethernet bytes on this PON interface. "
          ::= { adGenGponPon15MinPMEntry 11 }

adGenGponPon15MinTxEthernetBytes OBJECT-TYPE
          SYNTAX         Counter64
          MAX-ACCESS     read-only
          STATUS         current
          DESCRIPTION
           "The count of transmitted ethernet bytes on this PON interface. "
          ::= { adGenGponPon15MinPMEntry 12 }

adGenGponPon15MinUsBwAverageUtil OBJECT-TYPE
          SYNTAX         Gauge32
          MAX-ACCESS     read-only
          STATUS         current
          DESCRIPTION
           "Upstream average bandwidth percent utilization in 100th of a
            percent on this PON interface. "
          ::= { adGenGponPon15MinPMEntry 13 }

adGenGponPon15MinUsBwPeakUtil OBJECT-TYPE
          SYNTAX         Gauge32
          MAX-ACCESS     read-only
          STATUS         current
          DESCRIPTION
           "Upstream peak bandwidth percent utilization in 100th of a
            percent on this PON interface. "
          ::= { adGenGponPon15MinPMEntry 14 }

adGenGponPon15MinDsBwAverageUtil OBJECT-TYPE
          SYNTAX         Gauge32
          MAX-ACCESS     read-only
          STATUS         current
          DESCRIPTION
           "Downstream average bandwidth percent utilization in 100th of
            a percent on this PON interface. "
          ::= { adGenGponPon15MinPMEntry 15 }

adGenGponPon15MinDsBwPeakUtil OBJECT-TYPE
          SYNTAX         Gauge32
          MAX-ACCESS     read-only
          STATUS         current
          DESCRIPTION
           "Downstream peak bandwidth percent utilization in 100th of
            a percent on this PON interface. "
          ::= { adGenGponPon15MinPMEntry 16 }

adGenGponPon15MinDsMulticastPackets OBJECT-TYPE
          SYNTAX         Gauge32
          MAX-ACCESS     read-only
          STATUS         current
          DESCRIPTION
           "The count of downstream multicast packets on this PON interface. "
          ::= { adGenGponPon15MinPMEntry 17 }

adGenGponPon15MinDsMulticastBytes OBJECT-TYPE
          SYNTAX         Counter64
          MAX-ACCESS     read-only
          STATUS         current
          DESCRIPTION
           "The count of downstream multicast bytes on this PON interface. "
          ::= { adGenGponPon15MinPMEntry 18 }

adGenGponPon15MinDsMulticastBwAverageUtil OBJECT-TYPE
          SYNTAX         Gauge32
          MAX-ACCESS     read-only
          STATUS         current
          DESCRIPTION
           "Downstream multicast average bandwidth percent utilization in
            100th of a percent on this PON interface. "
          ::= { adGenGponPon15MinPMEntry 19 }

adGenGponPon15MinDsMulticastBwPeakUtil OBJECT-TYPE
          SYNTAX         Gauge32
          MAX-ACCESS     read-only
          STATUS         current
          DESCRIPTION
           "Downstream multicast peak bandwidth percent utilization in 100th
            of a percent on this PON interface. "
          ::= { adGenGponPon15MinPMEntry 20 }

adGenGponPon15MinDownstreamBIPError OBJECT-TYPE
          SYNTAX         Gauge32
          MAX-ACCESS     read-only
          STATUS         current
          DESCRIPTION
           "The count of BIP error in the downstream direction on this PON
       interface. "
          ::= { adGenGponPon15MinPMEntry 21 }

adGenGponPon24HrPMTable      OBJECT-TYPE
          SYNTAX         SEQUENCE OF AdGenGponPon24HrPMEntry
          MAX-ACCESS     not-accessible
          STATUS         current
          DESCRIPTION
           "The GPON PON PM table.
            Each table entry corresponds to GPON PON interface "
          ::= { adGponPerformance 2}

adGenGponPon24HrPMEntry         OBJECT-TYPE
          SYNTAX         AdGenGponPon24HrPMEntry
          MAX-ACCESS     not-accessible
          STATUS         current
          DESCRIPTION
           "An entry in the GPON PON PM table. "
          INDEX  {ifIndex, adGenGponPon24HrPMIntervalNumber}
          ::= { adGenGponPon24HrPMTable  1}


AdGenGponPon24HrPMEntry    ::= SEQUENCE  {
      adGenGponPon24HrPMIntervalNumber          INTEGER,
      adGenGponPon24HrRxEthernetPackets         Gauge32,
      adGenGponPon24HrRxOMCIPackets             Gauge32,
      adGenGponPon24HrTxEthernetPackets         Gauge32,
      adGenGponPon24HrTxOMCIPackets             Gauge32,
      adGenGponPon24HrUpstreamBIPError          Gauge32,
      adGenGponPon24HrUpstreamDroppedPackets    Gauge32,
      adGenGponPon24HrBufferOverflow            Gauge32,
      adGenGponPon24HrPacketFragError           Gauge32,
      adGenGponPon24HrIntervalTimeStamp         DisplayString,
      adGenGponPon24HrRxEthernetBytes           Counter64,
      adGenGponPon24HrTxEthernetBytes           Counter64,
      adGenGponPon24HrUsBwAverageUtil           Gauge32,
      adGenGponPon24HrUsBwPeakUtil              Gauge32,
      adGenGponPon24HrDsBwAverageUtil           Gauge32,
      adGenGponPon24HrDsBwPeakUtil              Gauge32,
      adGenGponPon24HrDsMulticastPackets        Gauge32,
      adGenGponPon24HrDsMulticastBytes          Counter64,
      adGenGponPon24HrDsMulticastBwAverageUtil  Gauge32,
      adGenGponPon24HrDsMulticastBwPeakUtil     Gauge32,
      adGenGponPon24HrDownstreamBIPError        Gauge32
      }

adGenGponPon24HrPMIntervalNumber OBJECT-TYPE
          SYNTAX         INTEGER (1..7)
          MAX-ACCESS     not-accessible
          STATUS         current
          DESCRIPTION
           "A number between 1 and 7, where 1 is the most
            recently completed 1 day interval and 7 is
            the 24 hour interval completed 6 days prior to
            interval 1."
          ::= { adGenGponPon24HrPMEntry 1 }

adGenGponPon24HrRxEthernetPackets OBJECT-TYPE
          SYNTAX         Gauge32
          MAX-ACCESS     read-only
          STATUS         current
          DESCRIPTION
           "The count of received ethernet packets on this PON interface. "
          ::= { adGenGponPon24HrPMEntry 2 }

adGenGponPon24HrRxOMCIPackets OBJECT-TYPE
          SYNTAX         Gauge32
          MAX-ACCESS     read-only
          STATUS         current
          DESCRIPTION
           "The count of received OMCI packets on this PON interface. "
          ::= { adGenGponPon24HrPMEntry 3 }

adGenGponPon24HrTxEthernetPackets OBJECT-TYPE
          SYNTAX         Gauge32
          MAX-ACCESS     read-only
          STATUS         current
          DESCRIPTION
           "The count of transmitted ethernet packets on this PON interface. "
          ::= { adGenGponPon24HrPMEntry 4 }

adGenGponPon24HrTxOMCIPackets OBJECT-TYPE
          SYNTAX         Gauge32
          MAX-ACCESS     read-only
          STATUS         current
          DESCRIPTION
           "The count of transmitted OMCI packets on this PON interface. "
          ::= { adGenGponPon24HrPMEntry 5 }

adGenGponPon24HrUpstreamBIPError OBJECT-TYPE
          SYNTAX         Gauge32
          MAX-ACCESS     read-only
          STATUS         current
          DESCRIPTION
           "The count of BIP error in the upstream direction on this PON interface. "
          ::= { adGenGponPon24HrPMEntry 6 }

adGenGponPon24HrUpstreamDroppedPackets OBJECT-TYPE
          SYNTAX         Gauge32
          MAX-ACCESS     read-only
          STATUS         current
          DESCRIPTION
           "The count of dropped packets in the upstream direction on this PONinterface. "
          ::= { adGenGponPon24HrPMEntry 7 }

adGenGponPon24HrBufferOverflow OBJECT-TYPE
          SYNTAX         Gauge32
          MAX-ACCESS     read-only
          STATUS         current
          DESCRIPTION
           "The count of buffer overflow on this PON interface. "
          ::= { adGenGponPon24HrPMEntry 8 }

adGenGponPon24HrPacketFragError OBJECT-TYPE
          SYNTAX         Gauge32
          MAX-ACCESS     read-only
          STATUS         current
          DESCRIPTION
           "The count of packet fragmentation error on this PON interface. "
          ::= { adGenGponPon24HrPMEntry 9 }

adGenGponPon24HrIntervalTimeStamp OBJECT-TYPE
      SYNTAX          DisplayString
      MAX-ACCESS      read-only
      STATUS          current
      DESCRIPTION
        "Timestamp of the 24-hr interval"

      ::= { adGenGponPon24HrPMEntry 10 }

adGenGponPon24HrRxEthernetBytes OBJECT-TYPE
          SYNTAX         Counter64
          MAX-ACCESS     read-only
          STATUS         current
          DESCRIPTION
           "The count of received ethernet bytes on this PON interface. "
          ::= { adGenGponPon24HrPMEntry 11 }

adGenGponPon24HrTxEthernetBytes OBJECT-TYPE
          SYNTAX         Counter64
          MAX-ACCESS     read-only
          STATUS         current
          DESCRIPTION
           "The count of transmitted ethernet bytes on this PON interface. "
          ::= { adGenGponPon24HrPMEntry 12 }

adGenGponPon24HrUsBwAverageUtil OBJECT-TYPE
          SYNTAX         Gauge32
          MAX-ACCESS     read-only
          STATUS         current
          DESCRIPTION
           "Upstream average bandwidth percent utilization in 100th of a
            percent on this PON interface. "
          ::= { adGenGponPon24HrPMEntry 13 }

adGenGponPon24HrUsBwPeakUtil OBJECT-TYPE
          SYNTAX         Gauge32
          MAX-ACCESS     read-only
          STATUS         current
          DESCRIPTION
           "Upstream peak bandwidth percent utilization in 100th of a
            percent on this PON interface. "
          ::= { adGenGponPon24HrPMEntry 14 }

adGenGponPon24HrDsBwAverageUtil OBJECT-TYPE
          SYNTAX         Gauge32
          MAX-ACCESS     read-only
          STATUS         current
          DESCRIPTION
           "Downstream average bandwidth percent utilization in 100th
            of a percent on this PON interface. "
          ::= { adGenGponPon24HrPMEntry 15 }

adGenGponPon24HrDsBwPeakUtil OBJECT-TYPE
          SYNTAX         Gauge32
          MAX-ACCESS     read-only
          STATUS         current
          DESCRIPTION
           "Downstream peak bandwidth percent utilization in 100th
            of a percent on this PON interface. "
          ::= { adGenGponPon24HrPMEntry 16 }

adGenGponPon24HrDsMulticastPackets OBJECT-TYPE
          SYNTAX         Gauge32
          MAX-ACCESS     read-only
          STATUS         current
          DESCRIPTION
           "The count of downstream multicast packets on this PON interface. "
          ::= { adGenGponPon24HrPMEntry 17 }

adGenGponPon24HrDsMulticastBytes OBJECT-TYPE
          SYNTAX         Counter64
          MAX-ACCESS     read-only
          STATUS         current
          DESCRIPTION
           "The count of downstream multicast bytes on this PON interface. "
          ::= { adGenGponPon24HrPMEntry 18 }

adGenGponPon24HrDsMulticastBwAverageUtil OBJECT-TYPE
          SYNTAX         Gauge32
          MAX-ACCESS     read-only
          STATUS         current
          DESCRIPTION
           "Downstream multicast average bandwidth percent utilization in
            100th of a percent on this PON interface. "
          ::= { adGenGponPon24HrPMEntry 19 }

adGenGponPon24HrDsMulticastBwPeakUtil OBJECT-TYPE
          SYNTAX         Gauge32
          MAX-ACCESS     read-only
          STATUS         current
          DESCRIPTION
           "Downstream multicast peak bandwidth percent utilization in
            100th of a percent on this PON interface. "
          ::= { adGenGponPon24HrPMEntry 20 }

adGenGponPon24HrDownstreamBIPError OBJECT-TYPE
          SYNTAX         Gauge32
          MAX-ACCESS     read-only
          STATUS         current
          DESCRIPTION
           "The count of BIP error in the downstream direction on this PON interface. "
          ::= { adGenGponPon24HrPMEntry 21 }

adGenGponPonCurrent15MinPMTable      OBJECT-TYPE
          SYNTAX         SEQUENCE OF AdGenGponPonCurrent15MinPMEntry
          MAX-ACCESS     not-accessible
          STATUS         current
          DESCRIPTION
           "The GPON PON PM table.
            Each table entry corresponds to GPON PON interface "
          ::= { adGponPerformance 3}

adGenGponPonCurrent15MinPMEntry         OBJECT-TYPE
          SYNTAX         AdGenGponPonCurrent15MinPMEntry
          MAX-ACCESS     not-accessible
          STATUS         current
          DESCRIPTION
           "An entry in the GPON PON PM table. "
          INDEX  { ifIndex }
          ::= { adGenGponPonCurrent15MinPMTable  1}

AdGenGponPonCurrent15MinPMEntry    ::= SEQUENCE  {
      adGenGponPonRxEthernetPacketsCurrent15Min         Gauge32,
      adGenGponPonRxOMCIPacketsCurrent15Min             Gauge32,
      adGenGponPonTxEthernetPacketsCurrent15Min         Gauge32,
      adGenGponPonTxOMCIPacketsCurrent15Min             Gauge32,
      adGenGponPonUpstreamBIPErrorCurrent15Min          Gauge32,
      adGenGponPonUpstreamDroppedPacketsCurrent15Min    Gauge32,
      adGenGponPonBufferOverflowCurrent15Min            Gauge32,
      adGenGponPonPacketFragErrorCurrent15Min           Gauge32,
      adGenGponPonRxEthernetBytesCurrent15Min           Counter64,
      adGenGponPonTxEthernetBytesCurrent15Min           Counter64,
      adGenGponPonUsBwAverageUtilCurrent15Min           Gauge32,
      adGenGponPonUsBwPeakUtilCurrent15Min              Gauge32,
      adGenGponPonDsBwAverageUtilCurrent15Min           Gauge32,
      adGenGponPonDsBwPeakUtilCurrent15Min              Gauge32,
      adGenGponPonDsMulticastPacketsCurrent15Min        Gauge32,
      adGenGponPonDsMulticastBytesCurrent15Min          Counter64,
      adGenGponPonDsMulticastBwAverageUtilCurrent15Min  Gauge32,
      adGenGponPonDsMulticastBwPeakUtilCurrent15Min     Gauge32,
      adGenGponPonDownstreamBIPErrorCurrent15Min        Gauge32
      }

adGenGponPonRxEthernetPacketsCurrent15Min OBJECT-TYPE
          SYNTAX         Gauge32
          MAX-ACCESS     read-only
          STATUS         current
          DESCRIPTION
           "The current 15 mins count of received ethernet packets on this PON interface. "
          ::= { adGenGponPonCurrent15MinPMEntry 2 }

adGenGponPonRxOMCIPacketsCurrent15Min OBJECT-TYPE
          SYNTAX         Gauge32
          MAX-ACCESS     read-only
          STATUS         current
          DESCRIPTION
           "The current 15 mins count of received OMCI packets on this PON interface. "
          ::= { adGenGponPonCurrent15MinPMEntry 3 }

adGenGponPonTxEthernetPacketsCurrent15Min OBJECT-TYPE
          SYNTAX         Gauge32
          MAX-ACCESS     read-only
          STATUS         current
          DESCRIPTION
           "The current 15 mins count of transmitted ethernet packets on this PON interface. "
          ::= { adGenGponPonCurrent15MinPMEntry 4 }

adGenGponPonTxOMCIPacketsCurrent15Min OBJECT-TYPE
          SYNTAX         Gauge32
          MAX-ACCESS     read-only
          STATUS         current
          DESCRIPTION
           "The current 15 mins count of transmitted OMCI packets on this PON interface. "
          ::= { adGenGponPonCurrent15MinPMEntry 5 }

adGenGponPonUpstreamBIPErrorCurrent15Min OBJECT-TYPE
          SYNTAX         Gauge32
          MAX-ACCESS     read-only
          STATUS         current
          DESCRIPTION
           "The current 15 mins count of BIP error in the upstream direction
           on this PON interface. "
          ::= { adGenGponPonCurrent15MinPMEntry 6 }

adGenGponPonUpstreamDroppedPacketsCurrent15Min OBJECT-TYPE
          SYNTAX         Gauge32
          MAX-ACCESS     read-only
          STATUS         current
          DESCRIPTION
           "The current 15 mins count of dropped packets in the upstream direction
           on this PON interface. "
          ::= { adGenGponPonCurrent15MinPMEntry 7 }

adGenGponPonBufferOverflowCurrent15Min OBJECT-TYPE
          SYNTAX         Gauge32
          MAX-ACCESS     read-only
          STATUS         current
          DESCRIPTION
           "The current 15 mins count of buffer overflow on this PON interface. "
          ::= { adGenGponPonCurrent15MinPMEntry 8 }

adGenGponPonPacketFragErrorCurrent15Min OBJECT-TYPE
          SYNTAX         Gauge32
          MAX-ACCESS     read-only
          STATUS         current
          DESCRIPTION
           "The current 15 mins count of packet fragmentation error on this PON interface. "
          ::= { adGenGponPonCurrent15MinPMEntry 9 }

adGenGponPonRxEthernetBytesCurrent15Min OBJECT-TYPE
          SYNTAX         Counter64
          MAX-ACCESS     read-only
          STATUS         current
          DESCRIPTION
           "The current 15 mins count of received ethernet bytes on this PON interface. "
          ::= { adGenGponPonCurrent15MinPMEntry 10 }

adGenGponPonTxEthernetBytesCurrent15Min OBJECT-TYPE
          SYNTAX         Counter64
          MAX-ACCESS     read-only
          STATUS         current
          DESCRIPTION
           "The current 15 mins count of transmitted ethernet bytes on this PON interface. "
          ::= { adGenGponPonCurrent15MinPMEntry 11 }

adGenGponPonUsBwAverageUtilCurrent15Min OBJECT-TYPE
          SYNTAX         Gauge32
          MAX-ACCESS     read-only
          STATUS         current
          DESCRIPTION
           "The current 15 mins of upstream average bandwidth percent utilization in 100th
            of a percent on this PON interface. "
          ::= { adGenGponPonCurrent15MinPMEntry 12 }

adGenGponPonUsBwPeakUtilCurrent15Min OBJECT-TYPE
          SYNTAX         Gauge32
          MAX-ACCESS     read-only
          STATUS         current
          DESCRIPTION
           "The current 15 mins of upstream peak bandwidth percent utilization in 100th of
            a percent on this PON interface. "
          ::= { adGenGponPonCurrent15MinPMEntry 13 }

adGenGponPonDsBwAverageUtilCurrent15Min OBJECT-TYPE
          SYNTAX         Gauge32
          MAX-ACCESS     read-only
          STATUS         current
          DESCRIPTION
           "The current 15 mins of downstream average bandwidth percent utilization in
            100th of a percent on this PON interface. "
          ::= { adGenGponPonCurrent15MinPMEntry 14 }

adGenGponPonDsBwPeakUtilCurrent15Min OBJECT-TYPE
          SYNTAX         Gauge32
          MAX-ACCESS     read-only
          STATUS         current
          DESCRIPTION
           "The current 15 mins of downstream peak bandwidth percent utilization in
            100th of a percent on this PON interface. "
          ::= { adGenGponPonCurrent15MinPMEntry 15 }

adGenGponPonDsMulticastPacketsCurrent15Min OBJECT-TYPE
          SYNTAX         Gauge32
          MAX-ACCESS     read-only
          STATUS         current
          DESCRIPTION
           "The current 15 mins count of downstream multicast packets on this PON interface. "
          ::= { adGenGponPonCurrent15MinPMEntry 16 }

adGenGponPonDsMulticastBytesCurrent15Min OBJECT-TYPE
          SYNTAX         Counter64
          MAX-ACCESS     read-only
          STATUS         current
          DESCRIPTION
           "The current 15 mins count of downstream multicast bytes on this PON interface. "
          ::= { adGenGponPonCurrent15MinPMEntry 17 }

adGenGponPonDsMulticastBwAverageUtilCurrent15Min OBJECT-TYPE
          SYNTAX         Gauge32
          MAX-ACCESS     read-only
          STATUS         current
          DESCRIPTION
           "The current 15 mins of downstream multicast average bandwidth percent utilization
            in 100th of a percent on this PON interface. "
          ::= { adGenGponPonCurrent15MinPMEntry 18 }

adGenGponPonDsMulticastBwPeakUtilCurrent15Min OBJECT-TYPE
          SYNTAX         Gauge32
          MAX-ACCESS     read-only
          STATUS         current
          DESCRIPTION
           "The current 15 mins of downstream multicast peak bandwidth percent utilization
            in 100th of a percent on this PON interface. "
          ::= { adGenGponPonCurrent15MinPMEntry 19 }

adGenGponPonDownstreamBIPErrorCurrent15Min OBJECT-TYPE
          SYNTAX         Gauge32
          MAX-ACCESS     read-only
          STATUS         current
          DESCRIPTION
           "The current 15 mins count of BIP error in the downstream direction
           on this PON interface. "
          ::= { adGenGponPonCurrent15MinPMEntry 20 }

adGenGponPonCurrent24HrPMTable      OBJECT-TYPE
          SYNTAX         SEQUENCE OF AdGenGponPonCurrent24HrPMEntry
          MAX-ACCESS     not-accessible
          STATUS         current
          DESCRIPTION
           "The GPON PON PM table.
            Each table entry corresponds to GPON PON interface "
          ::= { adGponPerformance 4}

adGenGponPonCurrent24HrPMEntry         OBJECT-TYPE
          SYNTAX         AdGenGponPonCurrent24HrPMEntry
          MAX-ACCESS     not-accessible
          STATUS         current
          DESCRIPTION
           "An entry in the GPON PON PM table. "
          INDEX  { ifIndex }
          ::= { adGenGponPonCurrent24HrPMTable  1}

AdGenGponPonCurrent24HrPMEntry    ::= SEQUENCE  {
      adGenGponPonRxEthernetPacketsCurrent24Hr         Gauge32,
      adGenGponPonRxOMCIPacketsCurrent24Hr             Gauge32,
      adGenGponPonTxEthernetPacketsCurrent24Hr         Gauge32,
      adGenGponPonTxOMCIPacketsCurrent24Hr             Gauge32,
      adGenGponPonUpstreamBIPErrorCurrent24Hr          Gauge32,
      adGenGponPonUpstreamDroppedPacketsCurrent24Hr    Gauge32,
      adGenGponPonBufferOverflowCurrent24Hr            Gauge32,
      adGenGponPonPacketFragErrorCurrent24Hr           Gauge32,
      adGenGponPonRxEthernetBytesCurrent24Hr           Counter64,
      adGenGponPonTxEthernetBytesCurrent24Hr           Counter64,
      adGenGponPonUsBwAverageUtilCurrent24Hr           Gauge32,
      adGenGponPonUsBwPeakUtilCurrent24Hr              Gauge32,
      adGenGponPonDsBwAverageUtilCurrent24Hr           Gauge32,
      adGenGponPonDsBwPeakUtilCurrent24Hr              Gauge32,
      adGenGponPonDsMulticastPacketsCurrent24Hr        Gauge32,
      adGenGponPonDsMulticastBytesCurrent24Hr          Counter64,
      adGenGponPonDsMulticastBwAverageUtilCurrent24Hr  Gauge32,
      adGenGponPonDsMulticastBwPeakUtilCurrent24Hr     Gauge32,
      adGenGponPonDownstreamBIPErrorCurrent24Hr        Gauge32
      }

adGenGponPonRxEthernetPacketsCurrent24Hr OBJECT-TYPE
          SYNTAX         Gauge32
          MAX-ACCESS     read-only
          STATUS         current
          DESCRIPTION
           "The current 24 Hr count of received ethernet packets on this PON interface. "
          ::= { adGenGponPonCurrent24HrPMEntry 2 }

adGenGponPonRxOMCIPacketsCurrent24Hr OBJECT-TYPE
          SYNTAX         Gauge32
          MAX-ACCESS     read-only
          STATUS         current
          DESCRIPTION
           "The current 24 Hr count of received OMCI packets on this PON interface. "
          ::= { adGenGponPonCurrent24HrPMEntry 3 }

adGenGponPonTxEthernetPacketsCurrent24Hr OBJECT-TYPE
          SYNTAX         Gauge32
          MAX-ACCESS     read-only
          STATUS         current
          DESCRIPTION
           "The current 24 Hr count of transmitted ethernet packets on this PON interface. "
          ::= { adGenGponPonCurrent24HrPMEntry 4 }

adGenGponPonTxOMCIPacketsCurrent24Hr OBJECT-TYPE
          SYNTAX         Gauge32
          MAX-ACCESS     read-only
          STATUS         current
          DESCRIPTION
           "The current 24 Hr count of transmitted OMCI packets on this PON interface. "
          ::= { adGenGponPonCurrent24HrPMEntry 5 }

adGenGponPonUpstreamBIPErrorCurrent24Hr OBJECT-TYPE
          SYNTAX         Gauge32
          MAX-ACCESS     read-only
          STATUS         current
          DESCRIPTION
           "The current 24 Hr count of BIP error in the upstream direction
           on this PON interface. "
          ::= { adGenGponPonCurrent24HrPMEntry 6 }

adGenGponPonUpstreamDroppedPacketsCurrent24Hr OBJECT-TYPE
          SYNTAX         Gauge32
          MAX-ACCESS     read-only
          STATUS         current
          DESCRIPTION
           "The current 24 Hr count of dropped packets in the upstream direction
           on this PON interface. "
          ::= { adGenGponPonCurrent24HrPMEntry 7 }

adGenGponPonBufferOverflowCurrent24Hr OBJECT-TYPE
          SYNTAX         Gauge32
          MAX-ACCESS     read-only
          STATUS         current
          DESCRIPTION
           "The current 24 Hr count of buffer overflow on this PON interface. "
          ::= { adGenGponPonCurrent24HrPMEntry 8 }

adGenGponPonPacketFragErrorCurrent24Hr OBJECT-TYPE
          SYNTAX         Gauge32
          MAX-ACCESS     read-only
          STATUS         current
          DESCRIPTION
           "The current 24 Hr count of packet fragmentation error on this PON interface. "
          ::= { adGenGponPonCurrent24HrPMEntry 9 }

adGenGponPonRxEthernetBytesCurrent24Hr OBJECT-TYPE
          SYNTAX         Counter64
          MAX-ACCESS     read-only
          STATUS         current
          DESCRIPTION
           "The current 24 Hr count of received ethernet bytes on this PON interface. "
          ::= { adGenGponPonCurrent24HrPMEntry 10 }

adGenGponPonTxEthernetBytesCurrent24Hr OBJECT-TYPE
          SYNTAX         Counter64
          MAX-ACCESS     read-only
          STATUS         current
          DESCRIPTION
           "The current 24 Hr count of transmitted ethernet bytes on this PON interface. "
          ::= { adGenGponPonCurrent24HrPMEntry 11 }

adGenGponPonUsBwAverageUtilCurrent24Hr OBJECT-TYPE
          SYNTAX         Gauge32
          MAX-ACCESS     read-only
          STATUS         current
          DESCRIPTION
           "The current 24 Hr of upstream average bandwidth percent utilization in 100th
            of a percent on this PON interface. "
          ::= { adGenGponPonCurrent24HrPMEntry 12 }

adGenGponPonUsBwPeakUtilCurrent24Hr OBJECT-TYPE
          SYNTAX         Gauge32
          MAX-ACCESS     read-only
          STATUS         current
          DESCRIPTION
           "The current 24 Hr of upstream peak bandwidth percent utilization in 100th of
            a percent on this PON interface. "
          ::= { adGenGponPonCurrent24HrPMEntry 13 }

adGenGponPonDsBwAverageUtilCurrent24Hr OBJECT-TYPE
          SYNTAX         Gauge32
          MAX-ACCESS     read-only
          STATUS         current
          DESCRIPTION
           "The current 24 Hr of downstream average bandwidth percent utilization in
            100th of a percent on this PON interface. "
          ::= { adGenGponPonCurrent24HrPMEntry 14 }

adGenGponPonDsBwPeakUtilCurrent24Hr OBJECT-TYPE
          SYNTAX         Gauge32
          MAX-ACCESS     read-only
          STATUS         current
          DESCRIPTION
           "The current 24 Hr of downstream peak bandwidth percent utilization in
            100th of a percent on this PON interface. "
          ::= { adGenGponPonCurrent24HrPMEntry 15 }

adGenGponPonDsMulticastPacketsCurrent24Hr OBJECT-TYPE
          SYNTAX         Gauge32
          MAX-ACCESS     read-only
          STATUS         current
          DESCRIPTION
           "The current 24 Hr count of downstream multicast packets on this PON interface. "
          ::= { adGenGponPonCurrent24HrPMEntry 16 }

adGenGponPonDsMulticastBytesCurrent24Hr OBJECT-TYPE
          SYNTAX         Counter64
          MAX-ACCESS     read-only
          STATUS         current
          DESCRIPTION
           "The current 24 Hr count of downstream multicast bytes on this PON interface. "
          ::= { adGenGponPonCurrent24HrPMEntry 17 }

adGenGponPonDsMulticastBwAverageUtilCurrent24Hr OBJECT-TYPE
          SYNTAX         Gauge32
          MAX-ACCESS     read-only
          STATUS         current
          DESCRIPTION
           "The current 24 Hr of downstream multicast average bandwidth percent utilization
            in 100th of a percent on this PON interface. "
          ::= { adGenGponPonCurrent24HrPMEntry 18 }

adGenGponPonDsMulticastBwPeakUtilCurrent24Hr OBJECT-TYPE
          SYNTAX         Gauge32
          MAX-ACCESS     read-only
          STATUS         current
          DESCRIPTION
           "The current 24 Hr of downstream multicast peak bandwidth percent utilization in
            100th of a percent on this PON interface. "
          ::= { adGenGponPonCurrent24HrPMEntry 19 }

adGenGponPonDownstreamBIPErrorCurrent24Hr OBJECT-TYPE
          SYNTAX         Gauge32
          MAX-ACCESS     read-only
          STATUS         current
          DESCRIPTION
           "The current 24 Hr count of BIP error in the downstream direction
           on this PON interface. "
          ::= { adGenGponPonCurrent24HrPMEntry 20 }

-- ********************************************
-- Performance History Port Reset
-- ********************************************

adGenGponPonPerfResetTable OBJECT-TYPE
   SYNTAX      SEQUENCE OF AdGenGponPonPerfResetEntry
   MAX-ACCESS  not-accessible
   STATUS      current
   DESCRIPTION
     "This table contains entries that allow the user to reset
      the performance history values for each GPON PON interface."
   ::= { adGponPerformance 5 }

adGenGponPonPerfResetEntry OBJECT-TYPE
   SYNTAX      AdGenGponPonPerfResetEntry
   MAX-ACCESS  not-accessible
   STATUS      current
   DESCRIPTION
     "An entry in the adGenGponPonPerfResetTable."
   INDEX { ifIndex }
   ::= { adGenGponPonPerfResetTable 1 }

AdGenGponPonPerfResetEntry ::=
   SEQUENCE
   {
   adGenGponPonPerfReset                    INTEGER
   }

adGenGponPonPerfReset OBJECT-TYPE
   SYNTAX      INTEGER
               {
               reset(1)
               }
   MAX-ACCESS  read-write
   STATUS      current
   DESCRIPTION
     "Resets the performance history values for all interfaces connected to
      the selected port."
   ::= { adGenGponPonPerfResetEntry 1 }


-- Video Return Path Counters reset

adGenGponOntVideoReturnPathCountersResetTable OBJECT-TYPE
   SYNTAX      SEQUENCE OF AdGenGponOntVideoReturnPathCountersResetEntry
   MAX-ACCESS  not-accessible
   STATUS      current
   DESCRIPTION
     "This table contains entries that allow the user to reset
      the counters of RF interface."
   ::= { adGponPerformance 6 }

adGenGponOntVideoReturnPathCountersResetEntry OBJECT-TYPE
   SYNTAX      AdGenGponOntVideoReturnPathCountersResetEntry
   MAX-ACCESS  not-accessible
   STATUS      current
   DESCRIPTION
     "An entry in the adGenGponOntVideoReturnPathCountersResetTable."
   INDEX { ifIndex }
   ::= { adGenGponOntVideoReturnPathCountersResetTable 1 }

AdGenGponOntVideoReturnPathCountersResetEntry ::=
   SEQUENCE
   {
   adGenGponOntVideoReturnPathCountersReset   INTEGER
   }

adGenGponOntVideoReturnPathCountersReset OBJECT-TYPE
   SYNTAX      INTEGER
   {
               reset(1)
   }
   MAX-ACCESS  read-write
   STATUS      current
   DESCRIPTION
     "Resets the counters."
   ::= { adGenGponOntVideoReturnPathCountersResetEntry 1 }

-- Video Return Path Counters table

adGenGponOntVideoReturnPathCountersTable         OBJECT-TYPE
          SYNTAX         SEQUENCE OF AdGenGponOntVideoReturnPathCountersEntry
          MAX-ACCESS     not-accessible
          STATUS         current
          DESCRIPTION
           "The Ont Video Return Path Counters table.
            Each table entry corresponds to RF port counters"
          ::= { adGponPerformance 7}

adGenGponOntVideoReturnPathCountersEntry         OBJECT-TYPE
          SYNTAX         AdGenGponOntVideoReturnPathCountersEntry
          MAX-ACCESS     not-accessible
          STATUS         current
          DESCRIPTION
           "An entry in the Ont Video Return Path Counters table.
            This entry represents a particular RF port counters. "
          INDEX  {ifIndex}
          ::= { adGenGponOntVideoReturnPathCountersTable  1}

AdGenGponOntVideoReturnPathCountersEntry    ::= SEQUENCE  {
    adGenGponOntVideoReturnPathRxTotalBursts           Counter32,
    adGenGponOntVideoReturnPathRxGoodBursts            Counter32,
    adGenGponOntVideoReturnPathRxFECCorrectedBursts    Counter32,
    adGenGponOntVideoReturnPathRxMissedBursts          Counter32,
    adGenGponOntVideoReturnPathRxMinPower              INTEGER,
    adGenGponOntVideoReturnPathRxMaxPower              INTEGER,
    adGenGponOntVideoReturnPathRxCurrentPower          INTEGER,
    adGenGponOntVideoReturnPathRxFECCorrectedSymbols   Counter32
}

adGenGponOntVideoReturnPathRxTotalBursts OBJECT-TYPE
          SYNTAX         Counter32
          MAX-ACCESS     read-only
          STATUS         current
          DESCRIPTION
           "Total number of bursts detected."
          ::= { adGenGponOntVideoReturnPathCountersEntry 1 }

adGenGponOntVideoReturnPathRxGoodBursts OBJECT-TYPE
          SYNTAX         Counter32
          MAX-ACCESS     read-only
          STATUS         current
          DESCRIPTION
           "Bursts detected and received correctly."
          ::= { adGenGponOntVideoReturnPathCountersEntry 2 }

adGenGponOntVideoReturnPathRxFECCorrectedBursts OBJECT-TYPE
          SYNTAX         Counter32
          MAX-ACCESS     read-only
          STATUS         current
          DESCRIPTION
           "Bursts detected with errors, but which were successfully corrected using FEC."
          ::= { adGenGponOntVideoReturnPathCountersEntry 3 }

adGenGponOntVideoReturnPathRxMissedBursts OBJECT-TYPE
          SYNTAX         Counter32
          MAX-ACCESS     read-only
          STATUS         current
          DESCRIPTION
           "Bursts detected that were not received correctly."
          ::= { adGenGponOntVideoReturnPathCountersEntry 4 }

adGenGponOntVideoReturnPathRxMinPower OBJECT-TYPE
          SYNTAX         INTEGER (0..255)
          MAX-ACCESS     read-only
          STATUS         current
          DESCRIPTION
           "Lowest power level of all bursts received(unit dBmV)."
          ::= { adGenGponOntVideoReturnPathCountersEntry 5 }

adGenGponOntVideoReturnPathRxMaxPower OBJECT-TYPE
          SYNTAX         INTEGER (0..255)
          MAX-ACCESS     read-only
          STATUS         current
          DESCRIPTION
           "Highest power level of all bursts received(unit dBmV)."
          ::= { adGenGponOntVideoReturnPathCountersEntry 6 }

adGenGponOntVideoReturnPathRxCurrentPower OBJECT-TYPE
          SYNTAX         INTEGER (0..255)
          MAX-ACCESS     read-only
          STATUS         current
          DESCRIPTION
           "Power level of the last burst received(unit dBmV)."
          ::= { adGenGponOntVideoReturnPathCountersEntry 7 }

adGenGponOntVideoReturnPathRxFECCorrectedSymbols OBJECT-TYPE
          SYNTAX         Counter32
          MAX-ACCESS     read-only
          STATUS         current
          DESCRIPTION
           "Numbers of symbols that were correctedthrough the use of FEC. It provides an indicator
            of the bit error rate of the link."
          ::= { adGenGponOntVideoReturnPathCountersEntry 8 }

-- ********************************************
-- Pon rolling counters reset
-- ********************************************

adGenGponPonCounterResetTable OBJECT-TYPE
   SYNTAX      SEQUENCE OF AdGenGponPonCounterResetEntry
   MAX-ACCESS  not-accessible
   STATUS      current
   DESCRIPTION
     "This table contains entries that allow the user to reset
      the rolling counter values for each GPON PON interface."
   ::= { adGponPerformance 8 }

adGenGponPonCounterResetEntry OBJECT-TYPE
   SYNTAX      AdGenGponPonCounterResetEntry
   MAX-ACCESS  not-accessible
   STATUS      current
   DESCRIPTION
     "An entry in the adGenGponPonCounterResetTable."
   INDEX { ifIndex }
   ::= { adGenGponPonCounterResetTable 1 }

AdGenGponPonCounterResetEntry ::=
   SEQUENCE
   {
   adGenGponPonBIPCountersReset                    INTEGER
   }

adGenGponPonBIPCountersReset OBJECT-TYPE
   SYNTAX      INTEGER
               {
               reset(1)
               }
   MAX-ACCESS  read-write
   STATUS      current
   DESCRIPTION
     "Resets both upstream and downstream BIP error counter values on all ONTs connected to
      the selected PON port."
   ::= { adGenGponPonCounterResetEntry 1 }


-- *******************************************************************************
--  ONT Alarms
-- *******************************************************************************

-- GPON ONT-G Alarms

adGenGponOntClrLOSAlarm NOTIFICATION-TYPE
      OBJECTS  {
         adTrapInformSeqNum,
         sysName,
         ifDescr,
         ifIndex,
         adGenGponOntAlarmSlotLosLevel
      }
      STATUS  current
      DESCRIPTION
         "This trap indicates that LOS alarm mode has cleared."
         --#TYPE         "Status - Alarm"
         --#SUMMARY      "GPON ONT LOS Condition Clear"
         --#SUMMARY      "Shelf: %s, ONT Details: %s"
         --#ARGUMENTS    {1,2}
         --#SEVERITY     MAJOR
         --#GENERIC      6
         --#CATEGORY     "Error Events"
         --#SOURCE_ID    "A"
         --#TIMEINDEX    0
      ::= { adGponOntAlarmEvents 1 }

adGenGponOntSetLOSAlarm NOTIFICATION-TYPE
      OBJECTS  {
         adTrapInformSeqNum,
         sysName,
         ifDescr,
         ifIndex,
         adGenGponOntAlarmSlotLosLevel
      }
      STATUS  current
      DESCRIPTION
         "This trap indicates that LOS alarm mode has set."
         --#TYPE         "Status - Alarm"
         --#SUMMARY      "GPON ONT LOS Condition Set"
         --#SUMMARY      "Shelf: %s, ONT Details: %s"
         --#ARGUMENTS    {1,2}
         --#SEVERITY     MAJOR
         --#GENERIC      6
         --#CATEGORY     "Error Events"
         --#SOURCE_ID    "A"
         --#TIMEINDEX    0
      ::= { adGponOntAlarmEvents 2 }
-- EquipmentAlarm

adGenGponOntClrEquipmentAlarm NOTIFICATION-TYPE
      OBJECTS  {
         adTrapInformSeqNum,
         sysName,
         ifDescr,
         ifIndex
      }
      STATUS  current
      DESCRIPTION
         "This trap indicates that ONT Equipment alarm mode has cleared."
         --#TYPE         "Status - Alarm"
         --#SUMMARY      "GPON ONT Equipment Alarm Condition Clear"
         --#SUMMARY      "Shelf: %s, ONT Details: %s"
         --#ARGUMENTS    {1,2}
         --#SEVERITY     MAJOR
         --#GENERIC      6
         --#CATEGORY     "Error Events"
         --#SOURCE_ID    "A"
         --#TIMEINDEX    0
      ::= { adGponOntAlarmEvents 3 }

adGenGponOntSetEquipmentAlarm NOTIFICATION-TYPE
      OBJECTS  {
         adTrapInformSeqNum,
         sysName,
         ifDescr,
         ifIndex
      }
      STATUS  current
      DESCRIPTION
         "This trap indicates that ONT Equipment alarm mode has set."
         --#TYPE         "Status - Alarm"
         --#SUMMARY      "GPON ONT Equipment Alarm Condition Set"
         --#SUMMARY      "Shelf: %s, ONT Details: %s"
         --#ARGUMENTS    {1,2}
         --#SEVERITY     MAJOR
         --#GENERIC      6
         --#CATEGORY     "Error Events"
         --#SOURCE_ID    "A"
         --#TIMEINDEX    0
      ::= { adGponOntAlarmEvents 4 }

-- PoweringAlarm

adGenGponOntClrPoweringAlarm NOTIFICATION-TYPE
      OBJECTS  {
         adTrapInformSeqNum,
         sysName,
         ifDescr,
         ifIndex,
         adGenGponOntAlarmSlotPoweringLevel
      }
      STATUS  current
      DESCRIPTION
         "This trap indicates that ONT Powering alarm mode has cleared."
         --#TYPE         "Status - Alarm"
         --#SUMMARY      "GPON ONT Powering Alarm Condition Clear"
         --#SUMMARY      "Shelf: %s, ONT Details: %s"
         --#ARGUMENTS    {1,2}
         --#SEVERITY     MAJOR
         --#GENERIC      6
         --#CATEGORY     "Error Events"
         --#SOURCE_ID    "A"
         --#TIMEINDEX    0
      ::= { adGponOntAlarmEvents 5 }

adGenGponOntSetPoweringAlarm NOTIFICATION-TYPE
      OBJECTS  {
         adTrapInformSeqNum,
         sysName,
         ifDescr,
         ifIndex,
         adGenGponOntAlarmSlotPoweringLevel
      }
      STATUS  current
      DESCRIPTION
         "This trap indicates that ONT Powering alarm mode has set."
         --#TYPE         "Status - Alarm"
         --#SUMMARY      "GPON ONT Powering Alarm Condition Set"
         --#SUMMARY      "Shelf: %s, ONT Details: %s"
         --#ARGUMENTS    {1,2}
         --#SEVERITY     MAJOR
         --#GENERIC      6
         --#CATEGORY     "Error Events"
         --#SOURCE_ID    "A"
         --#TIMEINDEX    0
      ::= { adGponOntAlarmEvents 6 }

-- BatteryMissing

adGenGponOntClrBatteryMissingAlarm NOTIFICATION-TYPE
      OBJECTS  {
         adTrapInformSeqNum,
         sysName,
         ifDescr,
         ifIndex
      }
      STATUS  current
      DESCRIPTION
         "This trap indicates that ONT Battery Missing alarm mode has cleared."
         --#TYPE         "Status - Alarm"
         --#SUMMARY      "GPON ONT Battery Missing Alarm Condition Clear"
         --#SUMMARY      "Shelf: %s, ONT Details: %s"
         --#ARGUMENTS    {1,2}
         --#SEVERITY     MINOR
         --#GENERIC      6
         --#CATEGORY     "Status Events"
         --#SOURCE_ID    "A"
         --#TIMEINDEX    0
      ::= { adGponOntAlarmEvents 7 }

adGenGponOntSetBatteryMissingAlarm NOTIFICATION-TYPE
      OBJECTS  {
         adTrapInformSeqNum,
         sysName,
         ifDescr,
         ifIndex
      }
      STATUS  current
      DESCRIPTION
         "This trap indicates that ONT Battery Missing alarm mode has set."
         --#TYPE         "Status - Alarm"
         --#SUMMARY      "GPON ONT Battery Missing Alarm Condition Set"
         --#SUMMARY      "Shelf: %s, ONT Details: %s"
         --#ARGUMENTS    {1,2}
         --#SEVERITY     MINOR
         --#GENERIC      6
         --#CATEGORY     "Status Events"
         --#SOURCE_ID    "A"
         --#TIMEINDEX    0
      ::= { adGponOntAlarmEvents 8 }

-- BatteryFailure

adGenGponOntClrBatteryFailureAlarm NOTIFICATION-TYPE
      OBJECTS  {
         adTrapInformSeqNum,
         sysName,
         ifDescr,
         ifIndex
      }
      STATUS  current
      DESCRIPTION
         "This trap indicates that ONT Battery Failure alarm mode has cleared."
         --#TYPE         "Status - Alarm"
         --#SUMMARY      "GPON ONT Battery Failure Alarm Condition Clear"
         --#SUMMARY      "Shelf: %s, ONT Details: %s"
         --#ARGUMENTS    {1,2}
         --#SEVERITY     MINOR
         --#GENERIC      6
         --#CATEGORY     "Error Events"
         --#SOURCE_ID    "A"
         --#TIMEINDEX    0
      ::= { adGponOntAlarmEvents 9 }

adGenGponOntSetBatteryFailureAlarm NOTIFICATION-TYPE
      OBJECTS  {
         adTrapInformSeqNum,
         sysName,
         ifDescr,
         ifIndex
      }
      STATUS  current
      DESCRIPTION
         "This trap indicates that ONT Battery Failure alarm mode has set."
         --#TYPE         "Status - Alarm"
         --#SUMMARY      "GPON ONT Battery Failure Alarm Condition Set"
         --#SUMMARY      "Shelf: %s, ONT Details: %s"
         --#ARGUMENTS    {1,2}
         --#SEVERITY     MINOR
         --#GENERIC      6
         --#CATEGORY     "Error Events"
         --#SOURCE_ID    "A"
         --#TIMEINDEX    0
      ::= { adGponOntAlarmEvents 10 }

-- BatteryLow

adGenGponOntClrBatteryLowAlarm NOTIFICATION-TYPE
      OBJECTS  {
         adTrapInformSeqNum,
         sysName,
         ifDescr,
         ifIndex
      }
      STATUS  current
      DESCRIPTION
         "This trap indicates that ONT Battery Low alarm mode has cleared."
         --#TYPE         "Status - Alarm"
         --#SUMMARY      "GPON ONT Battery Low Alarm Condition Clear"
         --#SUMMARY      "Shelf: %s, ONT Details: %s"
         --#ARGUMENTS    {1,2}
         --#SEVERITY     MINOR
         --#GENERIC      6
         --#CATEGORY     "Status Events"
         --#SOURCE_ID    "A"
         --#TIMEINDEX    0
      ::= { adGponOntAlarmEvents 11 }

adGenGponOntSetBatteryLowAlarm NOTIFICATION-TYPE
      OBJECTS  {
         adTrapInformSeqNum,
         sysName,
         ifDescr,
         ifIndex
      }
      STATUS  current
      DESCRIPTION
         "This trap indicates that ONT Battery Low alarm mode has set."
         --#TYPE         "Status - Alarm"
         --#SUMMARY      "GPON ONT Battery Low Alarm Condition Set"
         --#SUMMARY      "Shelf: %s, ONT Details: %s"
         --#ARGUMENTS    {1,2}
         --#SEVERITY     MINOR
         --#GENERIC      6
         --#CATEGORY     "Status Events"
         --#SOURCE_ID    "A"
         --#TIMEINDEX    0
      ::= { adGponOntAlarmEvents 12 }

-- PhysicalIntrustionAlarm

adGenGponOntClrPhyIntrustionAlarm NOTIFICATION-TYPE
      OBJECTS  {
         adTrapInformSeqNum,
         sysName,
         ifDescr,
         ifIndex
      }
      STATUS  current
      DESCRIPTION
         "This trap indicates that ONT Physical Intrustion alarm mode has cleared."
         --#TYPE         "Status - Alarm"
         --#SUMMARY      "GPON ONT Physical Intrustion Alarm Condition Clear"
         --#SUMMARY      "Shelf: %s, ONT Details: %s"
         --#ARGUMENTS    {1,2}
         --#SEVERITY     INFORMATIONAL
         --#GENERIC      6
         --#CATEGORY     "Status Events"
         --#SOURCE_ID    "A"
         --#TIMEINDEX    0
      ::= { adGponOntAlarmEvents 13 }

adGenGponOntSetPhyIntrusionAlarm NOTIFICATION-TYPE
      OBJECTS  {
         adTrapInformSeqNum,
         sysName,
         ifDescr,
         ifIndex
      }
      STATUS  current
      DESCRIPTION
         "This trap indicates that ONT Physical Intrusion alarm mode has set."
         --#TYPE         "Status - Alarm"
         --#SUMMARY      "GPON ONT Physical Intrusion Alarm Condition Set"
         --#SUMMARY      "Shelf: %s, ONT Details: %s"
         --#ARGUMENTS    {1,2}
         --#SEVERITY     INFORMATIONAL
         --#GENERIC      6
         --#CATEGORY     "Status Events"
         --#SOURCE_ID    "A"
         --#TIMEINDEX    0
      ::= { adGponOntAlarmEvents 14 }

adGenGponOntDiscoveryAlarm NOTIFICATION-TYPE
      OBJECTS  {
         adTrapInformSeqNum,  -- incl. for legacy info only; matches other GPON traps
         sysName,             -- TID/SID
         ifDescr,             -- string for EMS display; origin of the trap incl. Shelf: #, Slot: #, Port/PON: #
         ifIndex,             -- PON interface index for EMS or ETI to use as desired (can use to limit a
                              -- subsequent SNMP walk of adGenGponPonDiscoveredOntSnTable which
                              -- contains Serial Numbers only for ONTs that have been discovered and
                              -- NOT activated)
         adGenGponPonDiscoveredOntSerialNumber,
                              -- serial number of the ONT
         adGenGponPonDiscoveredRegistrationId,
                              -- registration ID of the ONT (if available)
         adGenGponPonTechnology,
                              -- enumerated type indicating the PON technology type
         adGenGponPonWavelength
                              -- enumerated type representing the pair of upstream/downstream wavelengths
         -- NO ONT Number...does not exist until activated
         -- The Management System could take this trap for the discovered ONT serial number
         -- and registration ID of interest.
      }
      STATUS  current
      DESCRIPTION
         "The OLT has discovered a new ONT that has not been activated yet."
         --#TYPE         "Status - ONT Discovery Alarm"
         --#SUMMARY      "GPON ONT Discovery Alarm Condition Set"
         --#SUMMARY      "Shelf: %s, ONT Location: %s"
         --#ARGUMENTS    {1,2}
         --#SEVERITY     WARNING
         --#GENERIC      6
         --#CATEGORY     "Status Events"
         --#SOURCE_ID    "A"
         --#TIMEINDEX    0
      ::= { adGponOntAlarmEvents 15 }

adGenGponOntActivationAlarm NOTIFICATION-TYPE
      OBJECTS  {
         adTrapInformSeqNum,  -- incl. for legacy info only; matches other GPON traps
                              -- (affects SUMMARY field positions)
         sysName,             -- TID/SID
         ifDescr,             -- string for EMS display; origin of the trap incl.
                              -- Shelf: #, Slot: #, Port/PON: #, ONT: #, ONT Serial No:  #, ONT Reg ID: #
                              -- which can be used to form the AID
         ifIndex,             -- ONT interface index for EMS or ETI to use as desired
         adGenGponOntActiveSoftwareVersion,   -- The current running software version of the GPON ONT
         adGenGponOntPartNumber,              -- The Part Number of the GPON ONT
         adGenGponOntHardwareRevision,        -- The Hardware revision/version of the GPON ONT
         adGenGponOntLearnedSerialNumber,     -- The unique serial number of the GPON ONT
         adGenGponOntRegistrationId,          -- The user programmed registration ID of the GPON ONT
         adGenGponOntInactiveSoftwareVersion, -- The secondary (inactive) software version of the GPON ONT
         adGenGponOntEverActivated,           -- boolean indicating whether or not the ONT has been previously activated on its PON
         adGenGponPonTechnology,              -- enumerated type indicating the PON technology type
         adGenGponPonWavelength               -- enumerated type representing the pair of upstream/downstream wavelengths
      }
      STATUS  current
      DESCRIPTION
         "The OLT has activated a new ONT which should be discovered by the management system."
         --#TYPE         "Status - ONT Activation Alarm"
         --#SUMMARY      "GPON ONT Activation Alarm Condition Set"
         --#SUMMARY      "Shelf: %s, ONT Details: %s"
         --#ARGUMENTS    {1,2}
         --#SEVERITY     WARNING
         --#GENERIC      9
         --#CATEGORY     "Status Events"
         --#SOURCE_ID    "A"
         --#TIMEINDEX    0
      ::= { adGponOntAlarmEvents 16 }

adGenGponConfigServerAlarmClear NOTIFICATION-TYPE
      OBJECTS  {
         adTrapInformSeqNum,  -- incl. for legacy info only; matches other GPON traps
                              -- (affects SUMMARY field positions)
         sysName,             -- TID/SID
         ifDescr,             -- string for display; origin of the trap incl.
                              -- Shelf: #, Slot: #, Port/PON: #, ONT: #, ONT Serial No:  #, ONT Reg ID: #
                              -- which can be used to form the AID
         ifIndex              -- ONT interface index
      }
      STATUS  current
      DESCRIPTION
         "The config server alarm has cleared."
         --#TYPE         "Status - Config Server Alarm"
         --#SUMMARY      "ONT Config Server Alarm Condition Set"
         --#SUMMARY      "Shelf: %s, ONT Details: %s"
         --#ARGUMENTS    {1,2}
         --#SEVERITY     Major
         --#GENERIC      6
         --#CATEGORY     "Error Events"
         --#SOURCE_ID    "A"
         --#TIMEINDEX    0
      ::= { adGponOntAlarmEvents 18 }

adGenGponConfigServerAlarmSet NOTIFICATION-TYPE
      OBJECTS  {
         adTrapInformSeqNum,  -- incl. for legacy info only; matches other GPON traps
                              -- (affects SUMMARY field positions)
         sysName,             -- TID/SID
         ifDescr,             -- string for display; origin of the trap incl.
                              -- Shelf: #, Slot: #, Port/PON: #, ONT: #, ONT Serial No:  #, ONT Reg ID: #
                              -- which can be used to form the AID
         ifIndex              -- ONT interface index
      }
      STATUS  current
      DESCRIPTION
         "The ONT encountered a problem communicating with the config file servers."
         --#TYPE         "Status - Config Server Alarm"
         --#SUMMARY      "ONT Config Server Alarm Condition Clear"
         --#SUMMARY      "Shelf: %s, ONT Details: %s"
         --#ARGUMENTS    {1,2}
         --#SEVERITY     Major
         --#GENERIC      6
         --#CATEGORY     "Error Events"
         --#SOURCE_ID    "A"
         --#TIMEINDEX    0
      ::= { adGponOntAlarmEvents 19 }

adGenGponConfigFileAlarmClear NOTIFICATION-TYPE
      OBJECTS  {
         adTrapInformSeqNum,  -- incl. for legacy info only; matches other GPON traps
                              -- (affects SUMMARY field positions)
         sysName,             -- TID/SID
         ifDescr,             -- string for display; origin of the trap incl.
                              -- Shelf: #, Slot: #, Port/PON: #, ONT: #, ONT Serial No:  #, ONT Reg ID: #
                              -- which can be used to form the AID
         ifIndex              -- ONT interface index
      }
      STATUS  current
      DESCRIPTION
         "The config file alarm has cleared."
         --#TYPE         "Status - ONT Config File Alarm"
         --#SUMMARY      "ONT Config File Alarm Condition Set"
         --#SUMMARY      "Shelf: %s, ONT Details: %s"
         --#ARGUMENTS    {1,2}
         --#SEVERITY     Major
         --#GENERIC      6
         --#CATEGORY     "Error Events"
         --#SOURCE_ID    "A"
         --#TIMEINDEX    0
      ::= { adGponOntAlarmEvents 20 }

adGenGponConfigFileAlarmSet NOTIFICATION-TYPE
      OBJECTS  {
         adTrapInformSeqNum,  -- incl. for legacy info only; matches other GPON traps
                              -- (affects SUMMARY field positions)
         sysName,             -- TID/SID
         ifDescr,             -- string for display; origin of the trap incl.
                              -- Shelf: #, Slot: #, Port/PON: #, ONT: #, ONT Serial No:  #, ONT Reg ID: #
                              -- which can be used to form the AID
         ifIndex              -- ONT interface index
      }
      STATUS  current
      DESCRIPTION
         "The ONT encountered an error processing the configuration file."
         --#TYPE         "Status - ONT Config File Alarm"
         --#SUMMARY      "ONT Config File Alarm Condition Clear"
         --#SUMMARY      "Shelf: %s, ONT Details: %s"
         --#ARGUMENTS    {1,2}
         --#SEVERITY     Major
         --#GENERIC      6
         --#CATEGORY     "Error Events"
         --#SOURCE_ID    "A"
         --#TIMEINDEX    0
      ::= { adGponOntAlarmEvents 21 }

adGenGponConfigChecksumMismatchAlarmClear NOTIFICATION-TYPE
      OBJECTS  {
         adTrapInformSeqNum,  -- incl. for legacy info only; matches other GPON traps
                              -- (affects SUMMARY field positions)
         sysName,             -- TID/SID
         ifDescr,             -- string for display; origin of the trap incl.
                              -- Shelf: #, Slot: #, Port/PON: #, ONT: #, ONT Serial No:  #, ONT Reg ID: #
                              -- which can be used to form the AID
         ifIndex              -- ONT interface index
      }
      STATUS  current
      DESCRIPTION
         "The config checksum mismatch alarm has cleared."
         --#TYPE         "Status - ONT Config Checksum Mismatch Alarm"
         --#SUMMARY      "ONT Config Checksum Mismatch Alarm Condition Set"
         --#SUMMARY      "Shelf: %s, ONT Details: %s"
         --#ARGUMENTS    {1,2}
         --#SEVERITY     MINOR
         --#GENERIC      6
         --#CATEGORY     "Status Events"
         --#SOURCE_ID    "A"
         --#TIMEINDEX    0
      ::= { adGponOntAlarmEvents 22 }

adGenGponConfigChecksumMismatchAlarmSet NOTIFICATION-TYPE
      OBJECTS  {
         adTrapInformSeqNum,  -- incl. for legacy info only; matches other GPON traps
                              -- (affects SUMMARY field positions)
         sysName,             -- TID/SID
         ifDescr,             -- string for display; origin of the trap incl.
                              -- Shelf: #, Slot: #, Port/PON: #, ONT: #, ONT Serial No:  #, ONT Reg ID: #
                              -- which can be used to form the AID
         ifIndex              -- ONT interface index
      }
      STATUS  current
      DESCRIPTION
         "The configuration file checksum has been changed locally on the ONT."
         --#TYPE         "Status - ONT Config Checksum Mismatch Alarm"
         --#SUMMARY      "ONT Config Checksum Mismatch Alarm Condition Clear"
         --#SUMMARY      "Shelf: %s, ONT Details: %s"
         --#ARGUMENTS    {1,2}
         --#SEVERITY     MINOR
         --#GENERIC      6
         --#CATEGORY     "Status Events"
         --#SOURCE_ID    "A"
         --#TIMEINDEX    0
      ::= { adGponOntAlarmEvents 23 }

adGenGponOntOMCICommFailAlarmClear NOTIFICATION-TYPE
      OBJECTS  {
         adTrapInformSeqNum,
         sysName,
         ifDescr,
         ifIndex
      }
      STATUS  current
      DESCRIPTION
         "This trap indicates that ONT successfully established the OMCI communication after the
         previous failure condition."
         --#TYPE         "Status - Alarm"
         --#SUMMARY      "GPON ONT OMCI Comm failure Condition Clear"
         --#SUMMARY      "Shelf: %s, ONT Details: %s"
         --#ARGUMENTS    {1,2}
         --#SEVERITY     MAJOR
         --#GENERIC      6
         --#CATEGORY     "Error Events"
         --#SOURCE_ID    "A"
         --#TIMEINDEX    0
      ::= { adGponOntAlarmEvents 24 }

adGenGponOntOMCICommFailAlarmSet NOTIFICATION-TYPE
      OBJECTS  {
         adTrapInformSeqNum,
         sysName,
         ifDescr,
         ifIndex
      }
      STATUS  current
      DESCRIPTION
         "This trap indicates that OMCI communication with an ONT failed to be established or has become inoperable."
         --#TYPE         "Status - Alarm"
         --#SUMMARY      "GPON ONT OMCI Comm failure Condition Set"
         --#SUMMARY      "Shelf: %s, ONT Details: %s"
         --#ARGUMENTS    {1,2}
         --#SEVERITY     MAJOR
         --#GENERIC      6
         --#CATEGORY     "Error Events"
         --#SOURCE_ID    "A"
         --#TIMEINDEX    0
      ::= { adGponOntAlarmEvents 25 }

adGenGponCirOversubscribedAlarmClear NOTIFICATION-TYPE
      OBJECTS  {
         adTrapInformSeqNum,
         sysName,
         ifDescr,
         ifIndex
      }
      STATUS  current
      DESCRIPTION
         "This trap indicates clearing of PON CIR bandwidth oversubscribed condition."
         --#TYPE         "Status - Alarm"
         --#SUMMARY      "GPON CIR OVERSUBSCRIBED Condition Clear"
         --#SUMMARY      "Shelf: %s, Pon Id: %s"
         --#ARGUMENTS    {1,2}
         --#SEVERITY     MAJOR
         --#GENERIC      6
         --#CATEGORY     "Error Events"
         --#SOURCE_ID    "A"
         --#TIMEINDEX    0
      ::= { adGponOntAlarmEvents 26 }

adGenGponCirOversubscribedAlarmSet NOTIFICATION-TYPE
      OBJECTS  {
         adTrapInformSeqNum,
         sysName,
         ifDescr,
         ifIndex
      }
      STATUS  current
      DESCRIPTION
         "This trap indicates that PON CIR bandwidth is oversubscribed.  Any further ONU activation might fail."
         --#TYPE         "Status - Alarm"
         --#SUMMARY      "GPON CIR OVERSUBSCRIBED Condition Set"
         --#SUMMARY      "Shelf: %s, Pon Id: %s"
         --#ARGUMENTS    {1,2}
         --#SEVERITY     MAJOR
         --#GENERIC      6
         --#CATEGORY     "Error Events"
         --#SOURCE_ID    "A"
         --#TIMEINDEX    0
      ::= { adGponOntAlarmEvents 27 }

adGenGponPonLosAlarmClear NOTIFICATION-TYPE
      OBJECTS  {
         adTrapInformSeqNum,
         sysName,
         ifDescr,
         ifIndex,
         adGenGponPonLosNumOntsDown,
         adGenGponPonDescriptionString
      }
      STATUS  current
      DESCRIPTION
         "User can provision a threshold limit on percentage of ONTs that are activated once and are now in LOS condition which
          will trigger the active alarm condition.  If number of ONTs corresponding to one-half of the above active threshold
          come back up again, this alarm will be cleared."
         --#TYPE         "Status - Alarm"
         --#SUMMARY      "GPON PON LOS Condition Clear"
         --#SUMMARY      "Shelf: %s, Pon Id: %s"
         --#ARGUMENTS    {1,2}
         --#SEVERITY     CRITICAL
         --#GENERIC      6
         --#CATEGORY     "Error Events"
         --#SOURCE_ID    "A"
         --#TIMEINDEX    0
      ::= { adGponOntAlarmEvents 28 }

adGenGponPonLosAlarmSet NOTIFICATION-TYPE
      OBJECTS  {
         adTrapInformSeqNum,
         sysName,
         ifDescr,
         ifIndex,
         adGenGponPonLosNumOntsDown,
         adGenGponPonDescriptionString
      }
      STATUS  current
      DESCRIPTION
         "The percentage of ONTs activated once on a single PON in LOS condition that exceeds a provisioned threshold level."
         --#TYPE         "Status - Alarm"
         --#SUMMARY      "GPON PON LOS Condition Set"
         --#SUMMARY      "Shelf: %s, Alarm Details: %s"
         --#ARGUMENTS    {1,2}
         --#SEVERITY     CRITICAL
         --#GENERIC      6
         --#CATEGORY     "Error Events"
         --#SOURCE_ID    "A"
         --#TIMEINDEX    0
      ::= { adGponOntAlarmEvents 29 }

adGenGponMulticastBwThresholdAlarmClear NOTIFICATION-TYPE
      OBJECTS  {
         adTrapInformSeqNum,
         sysName,
         ifDescr,
         ifIndex
      }
      STATUS  current
      DESCRIPTION
         "This trap indicates the multicast bandwidth used is less than the multicast bandwidth threshold value provisioned on the PON."
         --#TYPE         "Status - Alarm"
         --#SUMMARY      "MulticastBwThreshold alarm Condition Clear"
         --#SUMMARY      "Shelf: %s, Pon Id: %s"
         --#ARGUMENTS    {1,2}
         --#SEVERITY     MAJOR
         --#GENERIC      6
         --#CATEGORY     "Error Events"
         --#SOURCE_ID    "A"
         --#TIMEINDEX    0
      ::= { adGponOntAlarmEvents 30 }

adGenGponMulticastBwThresholdAlarmSet NOTIFICATION-TYPE
      OBJECTS  {
         adTrapInformSeqNum,
         sysName,
         ifDescr,
         ifIndex
      }
      STATUS  current
      DESCRIPTION
         "This trap indicates the multicast bandwidth used is equal to or greater than the multicast bandwidth threshold value provisioned on the PON."
         --#TYPE         "Status - Alarm"
         --#SUMMARY      "MulticastBwThreshold alarm Condition Set"
         --#SUMMARY      "Shelf: %s, Alarm Details: %s"
         --#ARGUMENTS    {1,2}
         --#SEVERITY     MAJOR
         --#GENERIC      6
         --#CATEGORY     "Error Events"
         --#SOURCE_ID    "A"
         --#TIMEINDEX    0
      ::= { adGponOntAlarmEvents 31 }

adGenGponPonDiscoveredInvalidSNAlarm NOTIFICATION-TYPE
      OBJECTS  {
         adTrapInformSeqNum,  -- incl. for legacy info only; matches other GPON traps
         sysName,             -- TID/SID
         ifDescr,             -- Shelf: #, Slot: #, PON: #
         ifIndex,             -- PON interface index for inactive ONT
         adGenGponPonDiscoveredOntSerialNumber
                              -- Discovered ONT serial number
         -- NO ONT Number
         -- The Management System could take this trap for an alert that an invalid ONT serial number is found during ONT discovery procedure
      }
      STATUS  current
      DESCRIPTION
         "This trap indicates that an ONT has an invalid serial number during ONT discovery procedure."
         --#TYPE         "Warning - Invalid ONT Serial Number is found during ONT discovery"
         --#SUMMARY      "Invalid ONT serial number Condition Set under ONT discovery"
         --#SUMMARY      "Shelf: %s, PON detail: %s, PON interface: %s, Invalid SN: %s"
         --#ARGUMENTS    {1, 2, 3, 4}
         --#SEVERITY     WARNING
         --#GENERIC      6
         --#CATEGORY     "Error Events"
         --#SOURCE_ID    "A"
         --#TIMEINDEX    0
      ::= { adGponOntAlarmEvents 32 }

adGenGponOntInvalidSNAlarm NOTIFICATION-TYPE
      OBJECTS  {
         adTrapInformSeqNum,  -- incl. for legacy info only; matches other GPON traps
         sysName,             -- TID/SID
         ifDescr,             -- Shelf: #, Slot: #, PON: #, ONT: #
         ifIndex,             -- ONT remote device interface
         adGenGponOntLearnedSerialNumber
                              -- serial number of the ONT
         -- The Management System could take this trap for an alert that an invalid ONT serial number is found during ONT activation procedure
      }
      STATUS  current
      DESCRIPTION
         "This trap indicates that an activated ONT reports an invalid serial number."
         --#TYPE         "Warning - Invalid ONT Serial Number is used"
         --#SUMMARY      "Invalid ONT serial number Condition Set during activation"
         --#SUMMARY      "Shelf: %s, ONT detail: %s, ONT interface: %s, Invalid SN: %s"
         --#ARGUMENTS    {1, 2, 3, 4}
         --#SEVERITY     WARNING
         --#GENERIC      6
         --#CATEGORY     "Error Events"
         --#SOURCE_ID    "A"
         --#TIMEINDEX    0
      ::= { adGponOntAlarmEvents 33 }

adGenGponOntUpstreamBipTcaAlarmClear NOTIFICATION-TYPE
      OBJECTS  {
         adTrapInformSeqNum,
         sysName,
         ifDescr,
         ifIndex
      }
      STATUS  current
      DESCRIPTION
         "This trap indicates the ONT upstream BIP error rate remains less than the BIP error threshold 10^-(n+1)
          for 1000 seconds, n is the BIP TCA Threshold value provisioned on the OLT."
         --#TYPE         "Status - Alarm"
         --#SUMMARY      "Upstream BIP threshold crossing alarm Condition Clear"
         --#SUMMARY      "Shelf: %s, ONT detail: %s"
         --#ARGUMENTS    {1,2}
         --#SEVERITY     MAJOR
         --#GENERIC      6
         --#CATEGORY     "Error Events"
         --#SOURCE_ID    "A"
         --#TIMEINDEX    0
      ::= { adGponOntAlarmEvents 34 }

adGenGponOntUpstreamBipTcaAlarmSet NOTIFICATION-TYPE
      OBJECTS  {
         adTrapInformSeqNum,
         sysName,
         ifDescr,
         ifIndex
      }
      STATUS  current
      DESCRIPTION
         "This trap indicates the ONT upstream BIP error rate is greater than or equal to the BIP threshold 10^-n,
          n is the BIP TCA threshold value provisioned on the OLT."
         --#TYPE         "Status - Alarm"
         --#SUMMARY      "Upstream BIP threashold Crossing alarm Condition Set"
         --#SUMMARY      "Shelf: %s, ONT detail: %s"
         --#ARGUMENTS    {1,2}
         --#SEVERITY     MAJOR
         --#GENERIC      6
         --#CATEGORY     "Error Events"
         --#SOURCE_ID    "A"
         --#TIMEINDEX    0
      ::= { adGponOntAlarmEvents 35 }

adGenGponOntDownstreamBipTcaAlarmClear NOTIFICATION-TYPE
      OBJECTS  {
         adTrapInformSeqNum,
         sysName,
         ifDescr,
         ifIndex
      }
      STATUS  current
      DESCRIPTION
         "This trap indicates the ONT downstream BIP error rate remains less than the BIP threshold value 10^-(n+1)
          for 1000 seconds, n is the BIP TCA threshold value provisioned on the OLT."
         --#TYPE         "Status - Alarm"
         --#SUMMARY      "Downstream BIP threshold crossing alarm Condition Clear"
         --#SUMMARY      "Shelf: %s, ONT detail: %s"
         --#ARGUMENTS    {1,2}
         --#SEVERITY     MAJOR
         --#GENERIC      6
         --#CATEGORY     "Error Events"
         --#SOURCE_ID    "A"
         --#TIMEINDEX    0
      ::= { adGponOntAlarmEvents 36 }

adGenGponOntDownstreamBipTcaAlarmSet NOTIFICATION-TYPE
      OBJECTS  {
         adTrapInformSeqNum,
         sysName,
         ifDescr,
         ifIndex
      }
      STATUS  current
      DESCRIPTION
         "This trap indicates the ONT downstream BIP error rate is greater than or equal to the BIP threshold value 10^-n,
          n is the BIP TCA threshold value provisioned on the OLT."
         --#TYPE         "Status - Alarm"
         --#SUMMARY      "Downstream BIP threashold Crossing alarm Condition Set"
         --#SUMMARY      "Shelf: %s, ONT detail: %s"
         --#ARGUMENTS    {1,2}
         --#SEVERITY     MAJOR
         --#GENERIC      6
         --#CATEGORY     "Error Events"
         --#SOURCE_ID    "A"
         --#TIMEINDEX    0
      ::= { adGponOntAlarmEvents 37 }

-- Dying gasp alarm

adGenGponOntDyingGaspAlarm NOTIFICATION-TYPE
      OBJECTS  {
         adTrapInformSeqNum,
         sysName,
         ifDescr,
         ifIndex,
         adGenGponOntAlarmSlotDyingGaspLevel
      }
      STATUS  current
      DESCRIPTION
         "This trap indicates that ONT is powering off imminently."
         --#TYPE         "Status - ONT Alarm"
         --#SUMMARY      "GPON ONT Dying gasp Alarm Condition"
         --#SUMMARY      "Shelf: %s, ONT Details: %s"
         --#ARGUMENTS    {1,2}
         --#SEVERITY     WARNING
         --#GENERIC      6
         --#CATEGORY     "Status Events"
         --#SOURCE_ID    "A"
         --#TIMEINDEX    0
      ::= { adGponOntAlarmEvents 38 }

adGenGponPonFailoverAlarmClear NOTIFICATION-TYPE
      OBJECTS  {
         adTrapInformSeqNum,
         sysName,
         ifDescr,
         ifIndex
      }
      STATUS  current
      DESCRIPTION
         "This trap indicates that a PON failover condition has been cleared."
         --#TYPE         "Status - Alarm"
         --#SUMMARY      "GPON PON Failover Event Cleared"
         --#SUMMARY      "Shelf: %s, Alarm Details: %s"
         --#ARGUMENTS    {1,2}
         --#SEVERITY     CRITICAL
         --#GENERIC      6
         --#CATEGORY     "Status Events"
         --#SOURCE_ID    "A"
         --#TIMEINDEX    0
      ::= { adGponOntAlarmEvents 39 }

adGenGponPonFailoverAlarmActive NOTIFICATION-TYPE
      OBJECTS  {
         adTrapInformSeqNum,
         sysName,
         ifDescr,
         ifIndex
      }
      STATUS  current
      DESCRIPTION
         "This trap indicates that a PON failover condition is active."
         --#TYPE         "Status - Alarm"
         --#SUMMARY      "GPON PON Failover Event Active"
         --#SUMMARY      "Shelf: %s, Alarm Details: %s"
         --#ARGUMENTS    {1,2}
         --#SEVERITY     CRITICAL
         --#GENERIC      6
         --#CATEGORY     "Status Events"
         --#SOURCE_ID    "A"
         --#TIMEINDEX    0
      ::= { adGponOntAlarmEvents 40 }

adGenGponPonHwFailureAlarmClear NOTIFICATION-TYPE
      OBJECTS  {
         adTrapInformSeqNum,
         sysName,
         adGenSlotInfoIndex
      }
      STATUS  current
      DESCRIPTION
         "This trap indicates that PON Hardware Failure alarm has cleared."
         --#TYPE         "Status - PON Alarm"
         --#SUMMARY      "GPON PON Hardware Failure Alarm Condition Clear"
         --#SUMMARY      "Shelf %s, Slot %d"
         --#ARGUMENTS    {1,2}
         --#SEVERITY     CRITICAL
         --#GENERIC      6
         --#CATEGORY     "Error Events"
         --#SOURCE_ID    "A"
         --#TIMEINDEX    0
      ::= { adGponOntAlarmEvents 41 }

adGenGponPonHwFailureAlarmSet NOTIFICATION-TYPE
      OBJECTS  {
         adTrapInformSeqNum,
         sysName,
         adGenSlotInfoIndex
      }
      STATUS  current
      DESCRIPTION
         "This trap indicates that PON Hardware Failure alarm has set"
         --#TYPE         "Status - PON Alarm"
         --#SUMMARY      "GPON PON Hardware Failure Alarm Condition Set"
         --#SUMMARY      "Shelf %s, Slot %d"
         --#ARGUMENTS    {1,2}
         --#SEVERITY     CRITICAL
         --#GENERIC      6
         --#CATEGORY     "Error Events"
         --#SOURCE_ID    "A"
         --#TIMEINDEX    0
      ::= { adGponOntAlarmEvents 42 }

adGenGponPonDegradationAlarmClear NOTIFICATION-TYPE
      OBJECTS  {
         adTrapInformSeqNum,
         sysName,
         adGenSlotInfoIndex
      }
      STATUS  current
      DESCRIPTION
         "This trap indicates that PON Degredation alarm has cleared"
         --#TYPE         "Status - PON Alarm"
         --#SUMMARY      "GPON PON Degradation Failure Alarm Condition Clear"
         --#SUMMARY      "Shelf %s, Slot %d"
         --#ARGUMENTS    {1,2}
         --#SEVERITY     MAJOR
         --#GENERIC      6
         --#CATEGORY     "Error Events"
         --#SOURCE_ID    "A"
         --#TIMEINDEX    0
      ::= { adGponOntAlarmEvents 43 }

adGenGponPonDegradationAlarmSet NOTIFICATION-TYPE
      OBJECTS  {
         adTrapInformSeqNum,
         sysName,
         adGenSlotInfoIndex
      }
      STATUS  current
      DESCRIPTION
         "This trap indicates that PON Degredation alarm has set"
         --#TYPE         "Status - PON Alarm"
         --#SUMMARY      "GPON PON Degradation Failure Alarm Condition Set"
         --#SUMMARY      "Shelf %s, Slot %d"
         --#ARGUMENTS    {1,2}
         --#SEVERITY     MAJOR
         --#GENERIC      6
         --#CATEGORY     "Error Events"
         --#SOURCE_ID    "A"
         --#TIMEINDEX    0
      ::= { adGponOntAlarmEvents 44 }

adGenGponOntClrDyingGaspAlarm NOTIFICATION-TYPE
      OBJECTS  {
         adTrapInformSeqNum,
         sysName,
         ifDescr,
         ifIndex,
         adGenGponOntAlarmSlotDyingGaspLevel
      }
      STATUS  current
      DESCRIPTION
         "This trap indicates that ONT Dying Gasp alarm has cleared."
         --#TYPE         "Status - ONT Dying Gasp Clear"
         --#SUMMARY      "GPON ONT Dying gasp Alarm Condition Clear"
         --#SUMMARY      "Shelf: %s, ONT Details: %s"
         --#ARGUMENTS    {1,2}
         --#SEVERITY     WARNING
         --#GENERIC      6
         --#CATEGORY     "Error Events"
         --#SOURCE_ID    "A"
         --#TIMEINDEX    0
      ::= { adGponOntAlarmEvents 45 }

adGenGponOntSetDyingGaspAlarm NOTIFICATION-TYPE
      OBJECTS  {
         adTrapInformSeqNum,
         sysName,
         ifDescr,
         ifIndex,
         adGenGponOntAlarmSlotDyingGaspLevel
      }
      STATUS  current
      DESCRIPTION
         "This trap indicates that ONT is powering off imminently."
         --#TYPE         "Status - ONT Dying Gasp Set"
         --#SUMMARY      "GPON ONT Dying gasp Alarm Condition Set"
         --#SUMMARY      "Shelf: %s, ONT Details: %s"
         --#ARGUMENTS    {1,2}
         --#SEVERITY     WARNING
         --#GENERIC      6
         --#CATEGORY     "Error Events"
         --#SOURCE_ID    "A"
         --#TIMEINDEX    0
      ::= { adGponOntAlarmEvents 46 }


-- GPON ONT Port Alarms

adGenGponOntClrLanLOSAlarm NOTIFICATION-TYPE
      OBJECTS  {
         adTrapInformSeqNum,
         sysName,
         ifDescr,
         ifIndex
      }
      STATUS  current
      DESCRIPTION
         "This trap indicates that GPON ONT ethernet port Lan LOS alarm mode has cleared."
         --#TYPE         "Status - Alarm"
         --#SUMMARY      "GPON ONT Port LAN LOS Condition Clear"
         --#SUMMARY      "Shelf: %s, ONT Port Details: %s"
         --#ARGUMENTS    {1,2}
         --#SEVERITY     MINOR
         --#GENERIC      6
         --#CATEGORY     "Error Events"
         --#SOURCE_ID    "A"
         --#TIMEINDEX    0
      ::= { adGponOntPortAlarmEvents 1 }

adGenGponOntPortSetLanLOSAlarm NOTIFICATION-TYPE
      OBJECTS  {
         adTrapInformSeqNum,
         sysName,
         ifDescr,
         ifIndex
      }
      STATUS  current
      DESCRIPTION
         "This trap indicates that GPON ONT ethernet port Lan LOS alarm mode has set."
         --#TYPE         "Status - Alarm"
         --#SUMMARY      "GPON ONT Port Lan LOS Condition Set"
         --#SUMMARY      "Shelf: %s, ONT Port Details: %s"
         --#ARGUMENTS    {1,2}
         --#SEVERITY     MINOR
         --#GENERIC      6
         --#CATEGORY     "Error Events"
         --#SOURCE_ID    "A"
         --#TIMEINDEX    0
      ::= { adGponOntPortAlarmEvents 2 }

adGenGponOntVideoPortLOSAlarmClear NOTIFICATION-TYPE
      OBJECTS  {
         adTrapInformSeqNum,
         sysName,
         ifDescr,
         ifIndex
      }
      STATUS  current
      DESCRIPTION
         "This trap indicates that GPON ONT video port LOS alarm mode has cleared."
         --#TYPE         "Status - Alarm"
         --#SUMMARY      "GPON ONT VIDEO Port LOS Condition Clear"
         --#SUMMARY      "Shelf: %s, ONT Port Details: %s"
         --#ARGUMENTS    {1,2}
         --#SEVERITY     MAJOR
         --#GENERIC      6
         --#CATEGORY     "Error Events"
         --#SOURCE_ID    "A"
         --#TIMEINDEX    0
      ::= { adGponOntPortAlarmEvents 3 }


adGenGponOntVideoPortLOSAlarmSet NOTIFICATION-TYPE
      OBJECTS  {
         adTrapInformSeqNum,
         sysName,
         ifDescr,
         ifIndex
      }
      STATUS  current
      DESCRIPTION
         "This trap indicates that GPON ONT video port LOS alarm mode has set."
         --#TYPE         "Status - Alarm"
         --#SUMMARY      "GPON ONT VIDEO Port LOS Condition SET"
         --#SUMMARY      "Shelf: %s, ONT Port Details: %s"
         --#ARGUMENTS    {1,2}
         --#SEVERITY     MAJOR
         --#GENERIC      6
         --#CATEGORY     "Error Events"
         --#SOURCE_ID    "A"
         --#TIMEINDEX    0
      ::= { adGponOntPortAlarmEvents 4 }

adGenGponOntVideoPortOORLowAlarmClear NOTIFICATION-TYPE
      OBJECTS  {
         adTrapInformSeqNum,
         sysName,
         ifDescr,
         ifIndex
      }
      STATUS  current
      DESCRIPTION
         "This trap indicates that GPON ONT video port OOR Low alarm mode has cleared."
         --#TYPE         "Status - Alarm"
         --#SUMMARY      "GPON ONT VIDEO Port OOR LOW Condition Clear"
         --#SUMMARY      "Shelf: %s, ONT Port Details: %s"
         --#ARGUMENTS    {1,2}
         --#SEVERITY     MAJOR
         --#GENERIC      6
         --#CATEGORY     "Error Events"
         --#SOURCE_ID    "A"
         --#TIMEINDEX    0
      ::= { adGponOntPortAlarmEvents 5 }


adGenGponOntVideoPortOORLowAlarmSet NOTIFICATION-TYPE
      OBJECTS  {
         adTrapInformSeqNum,
         sysName,
         ifDescr,
         ifIndex
      }
      STATUS  current
      DESCRIPTION
         "This trap indicates that GPON ONT video port OOR Low alarm mode has set."
         --#TYPE         "Status - Alarm"
         --#SUMMARY      "GPON ONT VIDEO Port OOR LOW Condition SET"
         --#SUMMARY      "Shelf: %s, ONT Port Details: %s"
         --#ARGUMENTS    {1,2}
         --#SEVERITY     MAJOR
         --#GENERIC      6
         --#CATEGORY     "Error Events"
         --#SOURCE_ID    "A"
         --#TIMEINDEX    0
      ::= { adGponOntPortAlarmEvents 6 }

adGenGponOntVideoPortOORHighAlarmClear NOTIFICATION-TYPE
      OBJECTS  {
         adTrapInformSeqNum,
         sysName,
         ifDescr,
         ifIndex
      }
      STATUS  current
      DESCRIPTION
         "This trap indicates that GPON ONT video port OOR High alarm mode has cleared."
         --#TYPE         "Status - Alarm"
         --#SUMMARY      "GPON ONT VIDEO Port OOR HIGH Condition Clear"
         --#SUMMARY      "Shelf: %s, ONT Port Details: %s"
         --#ARGUMENTS    {1,2}
         --#SEVERITY     MAJOR
         --#GENERIC      6
         --#CATEGORY     "Error Events"
         --#SOURCE_ID    "A"
         --#TIMEINDEX    0
      ::= { adGponOntPortAlarmEvents 7 }


adGenGponOntVideoPortOORHighAlarmSet NOTIFICATION-TYPE
      OBJECTS  {
         adTrapInformSeqNum,
         sysName,
         ifDescr,
         ifIndex
      }
      STATUS  current
      DESCRIPTION
         "This trap indicates that GPON ONT video port OOR High alarm mode has set."
         --#TYPE         "Status - Alarm"
         --#SUMMARY      "GPON ONT VIDEO Port OOR HIGH Condition SET"
         --#SUMMARY      "Shelf: %s, ONT Port Details: %s"
         --#ARGUMENTS    {1,2}
         --#SEVERITY     MAJOR
         --#GENERIC      6
         --#CATEGORY     "Error Events"
         --#SOURCE_ID    "A"
         --#TIMEINDEX    0
      ::= { adGponOntPortAlarmEvents 8 }


-- ************************************************************************
-- GPON ONT TEST
-- ************************************************************************
-- Need to map all the OMCI actions to SNMP
-- reset

adGenGponOntReset OBJECT-TYPE
         SYNTAX  INTEGER {
            deactivateOnt(1),
            rebootOnt(2)
         }
         MAX-ACCESS  read-write
         STATUS  current
         DESCRIPTION
            "Setting this OID deactivate or reboot the ONT."
         ::= { adGponOntTest 1 }

END
