ADTRAN-GENEVCMAP-MIB

-- TITLE:     The ADTRAN EVC Map MIB
-- PRODUCT:   Metro Ethernet Products
-- VERSION:   1.0
-- DATE:      07/21/10
-- AUTHOR:    Joey Boyd
-- STATUS:    PRELIMINARY

-- This MIB defines the object identifiers (OIDs) for the
-- ADTRAN GENEVCMAP MIB objects

-- HISTORY:
-- 09/14/09 jlb   STATUS: PRELIMINARY.
-- 06/21/10 ams   STATUS: PRELIMINARY.
-- 07/21/10 ams   Added a New table to report Evc Map creation error.  Added New tables to list
--                all associated Evc Maps and number of Evc Maps based on IfIndex, EVC name and
--                MEVC name.
-- 10/14/10 ams   Modified adGenEVCMapMENQueue from range to Enum.

-- ******************************************************************************************
DEFINITIONS ::= BEGIN

IMPORTS

   adGenEVCMap,
   adGenEVCMapID
      FROM ADTRAN-SHARED-CND-SYSTEM-MIB

   GenSystemInterfaceType
      FROM ADTRAN-SHARED-CND-SYSTEM-TC-MIB

   OBJECT-TYPE,
   MODULE-IDENTITY,
   Integer32
      FROM SNMPv2-SMI

   DisplayString,
   RowStatus,
   MacAddress
      FROM SNMPv2-TC

   InterfaceIndexOrZero,
   ifIndex
      FROM IF-MIB

   adGenSlotInfoIndex  FROM ADTRAN-GENSLOT-MIB

   ;

adGenEVCMapMIB MODULE-IDENTITY
   LAST-UPDATED "201908070000Z"
   ORGANIZATION "Adtran, Inc."
   CONTACT-INFO
     "CND Tech Support
         Postal: ADTRAN, Inc.
                 901 Explorer Blvd.
                 Huntsville, AL  35806
                 Tel: +1 800 726 8663
                 Fax: +1 256 963 6217
                 E-mail: support@adtran.com"
   DESCRIPTION
      "This MIB defines the objects for the EVC Map MIB."

   REVISION "201908070000Z"
   DESCRIPTION  "Added OID adGenEVCMapMatchInnerCEVLANID to adGenEVCMapTable, updated range and description
                 of existing OID adGenEVCMapMENCtag and removed unused Imports"

   REVISION "201408040000Z"
   DESCRIPTION  "Added OIDs adGenEVCMapMatchDestMacAddress and adGenEVCMapActivePolicerName to adGenEVCMapTable"

   REVISION "201307150000Z"
   DESCRIPTION  "Added adGenEVCMapConnectDiscard to adGenEVCMapTable"

   REVISION "201007210000Z"
   DESCRIPTION "Created"

::= { adGenEVCMapID 1 }

adGenEVCMapProvisioning                OBJECT IDENTIFIER ::= {adGenEVCMap 1}

--==================================================================================================================

   adGenEVCMapTable OBJECT-TYPE
      SYNTAX  SEQUENCE OF AdGenEVCMapEntry
      MAX-ACCESS  not-accessible
      STATUS  current
      DESCRIPTION
         "The EVC Map provisioning table."
      ::= { adGenEVCMapProvisioning 1 }

   adGenEVCMapEntry OBJECT-TYPE
      SYNTAX  AdGenEVCMapEntry
      MAX-ACCESS  not-accessible
      STATUS  current
      DESCRIPTION
         "An entry in the EVC Map provisioning table.  EVC Map entries
          are uniquely identified by their name."
      INDEX  { adGenSlotInfoIndex, IMPLIED adGenEVCMapName }
      ::= { adGenEVCMapTable 1 }

   AdGenEVCMapEntry ::=
      SEQUENCE {
         adGenEVCMapName
            DisplayString,
         adGenEVCMapRowStatus
            RowStatus,
         adGenEVCMapOperStatus
            INTEGER,
         adGenEVCMapOperStatusDetail
            DisplayString,
         adGenEVCMapLastProvError
            DisplayString,
	 adGenEVCMapConnectEVC
	    DisplayString,
	 adGenEVCMapConnectMEVC
	    DisplayString,
	 adGenEVCMapConnectUNIMethod
	    INTEGER,
	 adGenEVCMapConnectUNIByIfIndex
	    InterfaceIndexOrZero,
         adGenEVCMapConnectUNIByTypeAndStringTypeValue
	    GenSystemInterfaceType,
	 adGenEVCMapConnectUNIByTypeAndStringStringValue
	    OCTET STRING,
	 adGenEVCMapMENPriority
	    INTEGER,
	 adGenEVCMapMENQueue
	    INTEGER,
	 adGenEVCMapMENCtag
	    Integer32,
	 adGenEVCMapMENCtagPriority
	    INTEGER,
	 adGenEVCMapMatchCEVLANID
	    Integer32,
	 adGenEVCMapMatchCEVLANPriority
	    DisplayString,
         adGenMEFMapDSCPRange
	    DisplayString,
	 adGenEVCMapMatchUntagged
	    INTEGER,
	 adGenEVCMapMatchUnicast
	    INTEGER,
	 adGenEVCMapMatchBroadcast
	    INTEGER,
	 adGenEVCMapMatchMulticast
	    INTEGER,
	 adGenEVCMapMatchL2CP
	    INTEGER,
         adGenEVCMapConnectDiscard
            INTEGER,
         adGenEVCMapMatchDestMacAddress
            MacAddress,
         adGenEVCMapActivePolicerName
            DisplayString,
         adGenEVCMapMatchInnerCEVLANID
            Integer32
      }

      adGenEVCMapName OBJECT-TYPE
       	 SYNTAX  DisplayString (SIZE (1..50))
         MAX-ACCESS  not-accessible
         STATUS  current
         DESCRIPTION
            "A user configurable name for the EVC Map.  Upon creation of the EVC Map,
             the associated name will default to a unique value."
         ::= { adGenEVCMapEntry 1 }

      adGenEVCMapRowStatus OBJECT-TYPE
         SYNTAX  RowStatus
         MAX-ACCESS  read-create
         STATUS  current
         DESCRIPTION
           "This object is used to create a new row or modify or delete an
            existing row in the EVC Map table."
         ::= { adGenEVCMapEntry 2 }

      adGenEVCMapOperStatus OBJECT-TYPE
         SYNTAX INTEGER  {
            up(1),
            down(2)
         }
         MAX-ACCESS read-only
         STATUS current
         DESCRIPTION
            "Returns the current operational status of the EVC Map."
         ::= { adGenEVCMapEntry 3 }

      adGenEVCMapOperStatusDetail OBJECT-TYPE
         SYNTAX  DisplayString
         MAX-ACCESS  read-only
         STATUS  current
         DESCRIPTION
            "This variable provides the EVC Map status.  If there is no error, the EVC Map
             status will be 'running'.  If there is an error and the EVC Map cannot be
             applied, then adGenEVCMapOperStatusDetail will provide more details about the error."
         ::= { adGenEVCMapEntry 4 }

      adGenEVCMapLastProvError OBJECT-TYPE
          SYNTAX         DisplayString
          MAX-ACCESS     read-only
          STATUS         current
          DESCRIPTION
             "This string describes the last error experienced
              for this particular entry in the table."
         ::= { adGenEVCMapEntry 5 }

      adGenEVCMapConnectEVC OBJECT-TYPE
         SYNTAX  DisplayString (SIZE (1..50))
         MAX-ACCESS  read-create
         STATUS  current
         DESCRIPTION
            "The name of the EVC that this map connects to."
         ::= { adGenEVCMapEntry 6}

      adGenEVCMapConnectMEVC OBJECT-TYPE
         SYNTAX  DisplayString (SIZE (1..50))
         MAX-ACCESS  read-create
         STATUS  current
         DESCRIPTION
            "The name of the MEVC that this map connects to."
         ::= { adGenEVCMapEntry 7}

      adGenEVCMapConnectUNIMethod OBJECT-TYPE
         SYNTAX  INTEGER  {
            byIfIndex(1),
            byTypeAndString(2)
	 	 }
         MAX-ACCESS  read-create
         STATUS  current
         DESCRIPTION
            "This option specifies the method to be used for identifying the
	    connected UNI.
		Setting to byIfIndex(1) requires adGenEVCMapConnectUNIByIfIndex to be set.
		Setting to byTypeAndString(2) requires adGenEVCMapConnectUNIByTypeAndStringTypeValue
		and adGenEVCMapConnectUNIByTypeAndStringStringValue to be set."
         ::= { adGenEVCMapEntry 8}

      adGenEVCMapConnectUNIByIfIndex OBJECT-TYPE
         SYNTAX  InterfaceIndexOrZero
         MAX-ACCESS  read-create
         STATUS  current
         DESCRIPTION
            "Inteface index of the UNI to be connected to this map."
         ::= { adGenEVCMapEntry 9}

      adGenEVCMapConnectUNIByTypeAndStringTypeValue OBJECT-TYPE
         SYNTAX  GenSystemInterfaceType
         MAX-ACCESS  read-create
         STATUS  current
         DESCRIPTION
            "The ADTRAN interface type of the UNI to be connected to this map.
    	    adGenEVCMapConnectUNIByTypeAndStringStringValue must also be provisioned
	    for the UNI to be connected."
         ::= { adGenEVCMapEntry 10}

      adGenEVCMapConnectUNIByTypeAndStringStringValue OBJECT-TYPE
         SYNTAX  OCTET STRING
         MAX-ACCESS  read-create
         STATUS  current
         DESCRIPTION
            "A type specific string used to indicate the UNI to be connected
	    to this map.  For some interfaces, this may be a name or IP Address.
	    Others may bit encode values that uniquely identifies the interface.

	    adGenEVCMapConnectUNIByTypeAndStringTypeValue must also be provisioned
	    for the UNI to be connected."
         ::= { adGenEVCMapEntry 11}

      adGenEVCMapMENPriority OBJECT-TYPE
         SYNTAX  INTEGER  {
            explicit0(1),
            explicit1(2),
            explicit2(3),
            explicit3(4),
            explicit4(5),
            explicit5(6),
            explicit6(7),
            explicit7(8),
	    inheritFromCEVLANPbits(9)
	 }
         MAX-ACCESS  read-create
         STATUS  current
         DESCRIPTION
            "This option controls how the frames are classified for this Map.
             The CoS can be set explicitly or inherited from the CE VLAN P-bit
             value."
         ::= { adGenEVCMapEntry 20}

      adGenEVCMapMENQueue OBJECT-TYPE
         SYNTAX  INTEGER  {
	    inheritFromMenPriAndQosMap(0),
            queue0(1),
            queue1(2),
            queue2(3),
            queue3(4),
            queue4(5),
            queue5(6),
            queue6(7),
            queue7(8)
	 }
         MAX-ACCESS  read-create
         STATUS  current
         DESCRIPTION
            "This option specifies the egress queue used for traffic associated
	     with this map or inherit egress queue from MEN priority and
             translation of QoS map."
         ::= { adGenEVCMapEntry 21}

      adGenEVCMapMENCtag OBJECT-TYPE
         SYNTAX  Integer32 (1..4095)
         MAX-ACCESS  read-create
         STATUS  current
         DESCRIPTION
            "This option is used to specify a c-tag value to apply to this trafic
	     in addition to the s-tag added by the connected EVC. The value 4095
	     is a special value reserved for implementation use. While not applicable
	     for all implementations, the common usage of this value is to indicate
	     that no MEN c-tag is configured."
         ::= { adGenEVCMapEntry 22}

      adGenEVCMapMENCtagPriority OBJECT-TYPE
         SYNTAX  INTEGER  {
            explicit0(1),
            explicit1(2),
            explicit2(3),
            explicit3(4),
            explicit4(5),
            explicit5(6),
            explicit6(7),
            explicit7(8),
	    inheritFromCEVLANPbits(9)
	 }
         MAX-ACCESS  read-create
         STATUS  current
         DESCRIPTION
            "This option controls how the frames are classified for this Map.
             The CoS can be set explicitly or inherited from the CE VLAN P-bit
             value."
         ::= { adGenEVCMapEntry 23}

      adGenEVCMapMatchCEVLANID OBJECT-TYPE
         SYNTAX  Integer32 (0..4096)
         MAX-ACCESS  read-create
         STATUS  current
         DESCRIPTION
            "This option specifies the VID of the outermost tag of the ingress
             (CE) frame at the UNI port. Selecting 0 to 4095 specifies the CE
             VLAN ID using the selected value. Selecting 4096 leaves the value
             unspecified."
         ::= { adGenEVCMapEntry 24}

      adGenEVCMapMatchCEVLANPriority OBJECT-TYPE
         SYNTAX  DisplayString
         MAX-ACCESS  read-create
         STATUS  current
         DESCRIPTION
            "This option is used to specify a P-bit value
             of the outermost VLAN tag of the ingress (CE) frame as it is
             received on the UNI port.
             Example values:
                   Empty string = Unspecified
                   0,1,2        = P-bit values 0,1,2
                   0-2,5-7      = P-bit values 0,1,2,5,6,7"
         ::= { adGenEVCMapEntry 25}

      adGenMEFMapDSCPRange OBJECT-TYPE
         SYNTAX  DisplayString
         MAX-ACCESS  read-create
         STATUS  current
         DESCRIPTION
            "This option specifies a list of allowable DSCP values on the
             ingress frames at the UNI port. Each DSCP value can be from 0 to 63.
             Example values:
                   Empty string = Unspecified
                   0,1,2        = DSCP values 0,1,2
                   0-2,5-7      = DSCP values 0,1,2,5,6,7"
         ::= { adGenEVCMapEntry 26}

      adGenEVCMapMatchUntagged OBJECT-TYPE
         SYNTAX INTEGER  {
            enabled(1),
            disabled(2)
         }
         MAX-ACCESS  read-create
         STATUS  current
         DESCRIPTION
            "Thie option specifies untagged/priority tagged traffic to be included
		     in the match criteria."
         ::= { adGenEVCMapEntry 27}

      adGenEVCMapMatchUnicast OBJECT-TYPE
         SYNTAX INTEGER  {
            enabled(1),
            disabled(2)
         }
         MAX-ACCESS  read-create
         STATUS  current
         DESCRIPTION
            "Thie option specifies unicast traffic to be included
		     in the match criteria."
         ::= { adGenEVCMapEntry 28}

      adGenEVCMapMatchBroadcast OBJECT-TYPE
         SYNTAX INTEGER  {
            enabled(1),
            disabled(2)
         }
         MAX-ACCESS  read-create
         STATUS  current
         DESCRIPTION
            "Thie option specifies broadcast traffic to be included
		     in the match criteria."
         ::= { adGenEVCMapEntry 29}

      adGenEVCMapMatchMulticast OBJECT-TYPE
         SYNTAX INTEGER  {
            enabled(1),
            disabled(2)
         }
         MAX-ACCESS  read-create
         STATUS  current
         DESCRIPTION
            "Thie option specifies multicast traffic to be included
		     in the match criteria."
         ::= { adGenEVCMapEntry 30}

      adGenEVCMapMatchL2CP OBJECT-TYPE
         SYNTAX INTEGER  {
            enabled(1),
            disabled(2)
         }
         MAX-ACCESS  read-create
         STATUS  current
         DESCRIPTION
            "Thie option specifies Layer 2 Control Protocol traffic to be included
		     in the match criteria."
         ::= { adGenEVCMapEntry 31}

      adGenEVCMapConnectDiscard OBJECT-TYPE
         SYNTAX INTEGER  {
            enabled(1),
            disabled(2)
         }
         MAX-ACCESS  read-create
         STATUS  current
         DESCRIPTION
            "Discard all traffic matching this map."
         DEFVAL  { disabled }
         ::= { adGenEVCMapEntry 32}

      adGenEVCMapMatchDestMacAddress OBJECT-TYPE
         SYNTAX         MacAddress
         MAX-ACCESS     read-create
         STATUS         current
         DESCRIPTION
            "This option specifies a destination mac address to be included in the match criteria.
             Default value is 00:00:00:00:00:00"
         ::= { adGenEVCMapEntry 33}

      adGenEVCMapActivePolicerName OBJECT-TYPE
         SYNTAX         DisplayString
         MAX-ACCESS     read-only
         STATUS         current
         DESCRIPTION
            "The name of the policer that is attached to this evc map."
         ::= { adGenEVCMapEntry 34}

      adGenEVCMapMatchInnerCEVLANID OBJECT-TYPE
         SYNTAX  Integer32 (0..4096)
         MAX-ACCESS  read-create
         STATUS  current
         DESCRIPTION
            "This option specifies the VID of the Inner tag of the ingress
             (CE) frame at the UNI port. Selecting 0 to 4095 specifies the CE
             VLAN ID using the selected value. Selecting 4096 leaves the value
             unspecified."
         DEFVAL { 4096 }
         ::= { adGenEVCMapEntry 35}


--==================================================================================================================
   adGenEVCMapErrorTable OBJECT-TYPE
      SYNTAX  SEQUENCE OF AdGenEVCMapErrorEntry
      MAX-ACCESS  not-accessible
      STATUS  current
      DESCRIPTION
         "The EVC Map Creation Error table."
      ::= { adGenEVCMapProvisioning 2 }

   adGenEVCMapErrorEntry OBJECT-TYPE
      SYNTAX  AdGenEVCMapErrorEntry
      MAX-ACCESS  not-accessible
      STATUS  current
      DESCRIPTION
         "An entry in the EVC Map Creation Error table.
          The index, adGenSlotInfoIndex, identifies the SLOT."
      INDEX  { adGenSlotInfoIndex }
      ::= { adGenEVCMapErrorTable 1 }

   AdGenEVCMapErrorEntry ::=
      SEQUENCE {
         adGenEVCMapError
            DisplayString
      }

      adGenEVCMapError OBJECT-TYPE
       	 SYNTAX  DisplayString
         MAX-ACCESS  read-only
         STATUS  current
         DESCRIPTION
         "Returns information about the last error for the EVC Map
         create on SLOT. If row creation fails, this string
         will provide details about why the row could not be created."
         ::= { adGenEVCMapErrorEntry 1}

--==================================================================================================================

   adGenEVCMapUNINumberOfMapsTable OBJECT-TYPE
      SYNTAX  SEQUENCE OF AdGenEVCMapUNINumberOfMapsEntry
      MAX-ACCESS  not-accessible
      STATUS  current
      DESCRIPTION
         "The Evc Map table to display number of EVC Maps associated with the UNI."
      ::= { adGenEVCMapProvisioning 3 }

   adGenEVCMapUNINumberOfMapsEntry OBJECT-TYPE
      SYNTAX  AdGenEVCMapUNINumberOfMapsEntry
      MAX-ACCESS  not-accessible
      STATUS  current
      DESCRIPTION
         "An entry in the EVC Map UNI Number Of Maps table.
          The index, ifIndex, identifies the UNI port."
      INDEX  { ifIndex }
      ::= { adGenEVCMapUNINumberOfMapsTable 1 }

   AdGenEVCMapUNINumberOfMapsEntry ::=
      SEQUENCE {
	 adGenEVCMapUNINumberOfMaps
            Integer32
      }

      adGenEVCMapUNINumberOfMaps OBJECT-TYPE
         SYNTAX  Integer32
         MAX-ACCESS  read-only
         STATUS  current
         DESCRIPTION
            "This variable is used to display number of Evc Maps associated
             with the UNI."
         ::= { adGenEVCMapUNINumberOfMapsEntry 1}

--==================================================================================================================

   adGenEVCMapUNILookupTable OBJECT-TYPE
      SYNTAX  SEQUENCE OF AdGenEVCMapUNILookupEntry
      MAX-ACCESS  not-accessible
      STATUS  current
      DESCRIPTION
         "The Evc Map lookup table to display EVC Maps namses associated with the UNI."
      ::= { adGenEVCMapProvisioning 4 }

   adGenEVCMapUNILookupEntry OBJECT-TYPE
      SYNTAX  AdGenEVCMapUNILookupEntry
      MAX-ACCESS  not-accessible
      STATUS  current
      DESCRIPTION
         "An entry in the EVCMap UNI Lookup table.
          The first index, ifIndex, identifies the UNI port.
          The second index, adGenEVCMapUNILookupIndex, identifies the associated
          Evc Map index."
      INDEX  { ifIndex, adGenEVCMapUNILookupIndex }
      ::= { adGenEVCMapUNILookupTable 1 }

   AdGenEVCMapUNILookupEntry ::=
      SEQUENCE {
	 adGenEVCMapUNILookupIndex
            Integer32,
         adGenEVCMapUNILookupName
            DisplayString
      }

      adGenEVCMapUNILookupIndex OBJECT-TYPE
         SYNTAX  Integer32
         MAX-ACCESS  not-accessible
         STATUS  current
         DESCRIPTION
            "This variable is used as an index into the Map table."
         ::= { adGenEVCMapUNILookupEntry 1}

      adGenEVCMapUNILookupName OBJECT-TYPE
         SYNTAX  DisplayString
         MAX-ACCESS  read-only
         STATUS  current
         DESCRIPTION
            "This variable lists the map name specified by adGenEVCMapName
             that are connected to the UNI."
         ::= { adGenEVCMapUNILookupEntry 2}

--==================================================================================================================

   adGenEVCMapMEVCNumberOfMapsTable OBJECT-TYPE
      SYNTAX  SEQUENCE OF AdGenEVCMapMEVCNumberOfMapsEntry
      MAX-ACCESS  not-accessible
      STATUS  current
      DESCRIPTION
         "The Evc Map table to display number Of EVC Maps associated with the MEVC."
      ::= { adGenEVCMapProvisioning 5 }

   adGenEVCMapMEVCNumberOfMapsEntry OBJECT-TYPE
      SYNTAX  AdGenEVCMapMEVCNumberOfMapsEntry
      MAX-ACCESS  not-accessible
      STATUS  current
      DESCRIPTION
         "An entry in the Evc Map MEVC Number of Maps table.
          The first index, adGenSlotInfoIndex, identifies the SLOT.
          The second index, adGenEVCMapMEVCName, identifies the MEVC."
      INDEX  { adGenSlotInfoIndex, adGenEVCMapMEVCName }
      ::= { adGenEVCMapMEVCNumberOfMapsTable 1 }

   AdGenEVCMapMEVCNumberOfMapsEntry ::=
      SEQUENCE {
         adGenEVCMapMEVCName
            OCTET STRING,
         adGenEVCMapMEVCNumberOfMaps
            Integer32
      }

      adGenEVCMapMEVCName OBJECT-TYPE
       	 SYNTAX  OCTET STRING (SIZE (1..50))
         MAX-ACCESS  not-accessible
         STATUS  current
         DESCRIPTION
            "A user configured name for the MEVC. This string matches
            adGenMEVCName from adGenMEVCTable."
         ::= { adGenEVCMapMEVCNumberOfMapsEntry 1}

      adGenEVCMapMEVCNumberOfMaps OBJECT-TYPE
         SYNTAX  Integer32
         MAX-ACCESS  read-only
         STATUS  current
         DESCRIPTION
            "This variable is used to display number of Evc Maps associated
             with the MEVC."
         ::= { adGenEVCMapMEVCNumberOfMapsEntry 2}

--==================================================================================================================

   adGenEVCMapMEVCLookupTable OBJECT-TYPE
      SYNTAX  SEQUENCE OF AdGenEVCMapMEVCLookupEntry
      MAX-ACCESS  not-accessible
      STATUS  current
      DESCRIPTION
         "The Evc Map lookup table to display EVC Maps names associated with the MEVC."
      ::= { adGenEVCMapProvisioning 6 }

   adGenEVCMapMEVCLookupEntry OBJECT-TYPE
      SYNTAX  AdGenEVCMapMEVCLookupEntry
      MAX-ACCESS  not-accessible
      STATUS  current
      DESCRIPTION
         "An entry in the Evc Map MEvc Look up table.
          The first index, adGenSlotInfoIndex, identifies the SLOT.
          The second index, adGenEVCMapMEVCFixedLengthName, identifies the MEVC.
          The third index, adGenEVCMapMEVCLookupIndex, identifies the associated
          Evc Map index."
      INDEX  { adGenSlotInfoIndex, adGenEVCMapMEVCFixedLengthName, adGenEVCMapMEVCLookupIndex }
      ::= { adGenEVCMapMEVCLookupTable 1 }

   AdGenEVCMapMEVCLookupEntry ::=
      SEQUENCE {
         adGenEVCMapMEVCFixedLengthName
            OCTET STRING,
         adGenEVCMapMEVCLookupIndex
            Integer32,
         adGenEVCMapMEVCLookupName
            DisplayString
      }

      adGenEVCMapMEVCFixedLengthName OBJECT-TYPE
       	 SYNTAX  OCTET STRING (SIZE (50))
         MAX-ACCESS  not-accessible
         STATUS  current
         DESCRIPTION
            "A user configured name for the MEVC. This string matches
            adGenMEVCName from adGenMEVCTable, but it is padded at the
            end with 0x00 so that the table index has a fixed length of
            50 characters."
         ::= { adGenEVCMapMEVCLookupEntry 1}

      adGenEVCMapMEVCLookupIndex OBJECT-TYPE
         SYNTAX  Integer32
         MAX-ACCESS  not-accessible
         STATUS  current
         DESCRIPTION
            "This variable is used as an index into the Map table."
         ::= { adGenEVCMapMEVCLookupEntry 2}

      adGenEVCMapMEVCLookupName OBJECT-TYPE
         SYNTAX  DisplayString
         MAX-ACCESS  read-only
         STATUS  current
         DESCRIPTION
            "This variable list the map name specified by adGenEVCMapName
             that are connected to the MEVC."
         ::= { adGenEVCMapMEVCLookupEntry 3}

--==================================================================================================================

   adGenEVCMapEVCNumberOfMapsTable OBJECT-TYPE
      SYNTAX  SEQUENCE OF AdGenEVCMapEVCNumberOfMapsEntry
      MAX-ACCESS  not-accessible
      STATUS  current
      DESCRIPTION
         "The Evc Map table to display number Of EVC Maps associated with the EVC."
      ::= { adGenEVCMapProvisioning 7 }

   adGenEVCMapEVCNumberOfMapsEntry OBJECT-TYPE
      SYNTAX  AdGenEVCMapEVCNumberOfMapsEntry
      MAX-ACCESS  not-accessible
      STATUS  current
      DESCRIPTION
         "An entry in the Evc Map EVC Number of Maps table.
          The first index, adGenSlotInfoIndex, identifies the SLOT.
          The second index, adGenEVCMapEVCName, identifies the EVC."
      INDEX  { adGenSlotInfoIndex, adGenEVCMapEVCName }
      ::= { adGenEVCMapEVCNumberOfMapsTable 1 }

   AdGenEVCMapEVCNumberOfMapsEntry ::=
      SEQUENCE {
         adGenEVCMapEVCName
            OCTET STRING,
         adGenEVCMapEVCNumberOfMaps
            Integer32
      }

      adGenEVCMapEVCName OBJECT-TYPE
       	 SYNTAX  OCTET STRING (SIZE (1..50))
         MAX-ACCESS  not-accessible
         STATUS  current
         DESCRIPTION
            "A user configured name for the EVC. This string matches
            adGenEVCName from adGenEVCTable."
         ::= { adGenEVCMapEVCNumberOfMapsEntry 1}

      adGenEVCMapEVCNumberOfMaps OBJECT-TYPE
         SYNTAX  Integer32
         MAX-ACCESS  read-only
         STATUS  current
         DESCRIPTION
            "This variable is used to display number of Evc Maps associated
             with the EVC."
         ::= { adGenEVCMapEVCNumberOfMapsEntry 2}

--==================================================================================================================

   adGenEVCMapEVCLookupTable OBJECT-TYPE
      SYNTAX  SEQUENCE OF AdGenEVCMapEVCLookupEntry
      MAX-ACCESS  not-accessible
      STATUS  current
      DESCRIPTION
         "The Evc Map lookup table to display EVC Maps Names associated with the EVC."
      ::= { adGenEVCMapProvisioning 8 }

   adGenEVCMapEVCLookupEntry OBJECT-TYPE
      SYNTAX  AdGenEVCMapEVCLookupEntry
      MAX-ACCESS  not-accessible
      STATUS  current
      DESCRIPTION
         "An entry in the Evc Map EVC Lookup table.
          The first index, adGenSlotInfoIndex, identifies the SLOT.
          The second index, adGenEVCMapEVCFixedLengthName, identifies the EVC.
          The third index, adGenEVCMapEVCLookupIndex, identifies the associated
          Evc Map index."
      INDEX  { adGenSlotInfoIndex, adGenEVCMapEVCFixedLengthName, adGenEVCMapEVCLookupIndex }
      ::= { adGenEVCMapEVCLookupTable 1 }

   AdGenEVCMapEVCLookupEntry ::=
      SEQUENCE {
         adGenEVCMapEVCFixedLengthName
            OCTET STRING,
         adGenEVCMapEVCLookupIndex
            Integer32,
         adGenEVCMapEVCLookupName
            DisplayString
      }

      adGenEVCMapEVCFixedLengthName OBJECT-TYPE
       	 SYNTAX  OCTET STRING (SIZE (50))
         MAX-ACCESS  not-accessible
         STATUS  current
         DESCRIPTION
            "A user configured name for the EVC. This string matches
            adGenEVCName from adGenEVCTable, but it is padded at the
            end with 0x00 so that the table index has a fixed length of
            50 characters."
         ::= { adGenEVCMapEVCLookupEntry 1}

      adGenEVCMapEVCLookupIndex OBJECT-TYPE
         SYNTAX  Integer32
         MAX-ACCESS  not-accessible
         STATUS  current
         DESCRIPTION
            "This variable is used as an index into the Map table."
         ::= { adGenEVCMapEVCLookupEntry 2}

      adGenEVCMapEVCLookupName OBJECT-TYPE
         SYNTAX  DisplayString
         MAX-ACCESS  read-only
         STATUS  current
         DESCRIPTION
            "This variable list the map name specified by adGenEVCMapName
             that are connected to the EVC."
         ::= { adGenEVCMapEVCLookupEntry 3}

END
