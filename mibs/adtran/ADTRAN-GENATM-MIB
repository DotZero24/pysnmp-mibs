ADTRAN-GENATM-MIB

-- TITLE:     The ADTRAN ATM MIB
-- PRODUCT:   Products supporting ATM
-- VERSION:   1.0
-- DATE:      12/28/11
-- AUTHOR:    Gilbert Fernandez
-- STATUS:    PRELIMINARY

-- This MIB defines the object identifier (OID) for the
-- ADTRAN SHARED CND SYSTEM MIB objects

-- HISTORY:
-- 12/28/11 glf  STATUS: PRELIMINARY.

-- ******************************************************************************************

DEFINITIONS ::= BEGIN

--==================================================================================================================
-- IMPORTS
--==================================================================================================================
    IMPORTS
   		OBJECT-TYPE,
   		NOTIFICATION-TYPE,
   		MODULE-IDENTITY,
   		Unsigned32,
   		Integer32,
   		Gauge32
   		   FROM SNMPv2-SMI
   		sysName
   		   FROM SNMPv2-MIB
   		OBJECT-GROUP,
   		NOTIFICATION-GROUP
   		   FROM SNMPv2-CONF
   		adGenAtm,
   		adGenAtmID
   		   FROM ADTRAN-SHARED-CND-SYSTEM-MIB
                adGenSlotInfoIndex
                   FROM ADTRAN-GENSLOT-MIB
   	;

--==================================================================================================================
-- MODULE IDENTITY
--==================================================================================================================
adGenAtmIdentity MODULE-IDENTITY
   	LAST-UPDATED "201112280000Z"
   	ORGANIZATION "Adtran, Inc."
   	CONTACT-INFO
     	"CND Tech Support
         Postal: ADTRAN, Inc.
                 901 Explorer Blvd.
                 Huntsville, AL  35806
                 Tel: +1 800 726-8663
                 Fax: +1 256 963 6217
                 E-mail: support@adtran.com"
   	DESCRIPTION
      	"This MIB defines the objects for the genATM MIB."
   	REVISION "201112280000Z"
   	DESCRIPTION "Created"
	::= { adGenAtmID 1 }

--==================================================================================================================
-- OBJECT IDENTIFIERS
--==================================================================================================================

	adGenAtmStatus                      OBJECT IDENTIFIER ::= {adGenAtm 1}
	adGenAtmBulkATM                     OBJECT IDENTIFIER ::= {adGenAtm 2}

--==================================================================================================================
-- ATM Status Tables
--==================================================================================================================

    adGenAtmTotalCountStatusTable
     OBJECT-TYPE
       SYNTAX      SEQUENCE OF AdGenAtmTotalCountStatusEntry
       MAX-ACCESS  not-accessible
       STATUS      current
       DESCRIPTION
           "Table contains instances that return the number of Vcls, Vpls, Vcccs, Vpccs, Interworked VCs, and Interworked VPs created"
       ::= { adGenAtmStatus 1 }

    adGenAtmTotalCountStatusEntry OBJECT-TYPE
       SYNTAX      AdGenAtmTotalCountStatusEntry
       MAX-ACCESS  not-accessible
       STATUS      current
       DESCRIPTION
           "Index is the slot number."
       INDEX { adGenSlotInfoIndex }
       ::= { adGenAtmTotalCountStatusTable 1 }

    AdGenAtmTotalCountStatusEntry ::=
       SEQUENCE {
           adGenAtmTotalCountVcl           Integer32,
           adGenAtmTotalCountVpl           Integer32,
           adGenAtmTotalCountVccc          Integer32,
           adGenAtmTotalCountVpcc          Integer32,
           adGenAtmTotalCountVcIntwk       Integer32,
           adGenAtmTotalCountVpIntwk       Integer32
       }

    adGenAtmTotalCountVcl      OBJECT-TYPE
       SYNTAX                    		Integer32
       MAX-ACCESS                		read-only
       STATUS                    		current
       DESCRIPTION
           "Return the total number of Vcls created"
        ::= { adGenAtmTotalCountStatusEntry 1 }

    adGenAtmTotalCountVpl      OBJECT-TYPE
       SYNTAX                    		Integer32
       MAX-ACCESS                		read-only
       STATUS                    		current
       DESCRIPTION
           "Return the total number of Vpls created"
        ::= { adGenAtmTotalCountStatusEntry 2 }

    adGenAtmTotalCountVccc      OBJECT-TYPE
       SYNTAX                    		Integer32
       MAX-ACCESS                		read-only
       STATUS                    		current
       DESCRIPTION
           "Return the total number of Vcccs created"
        ::= { adGenAtmTotalCountStatusEntry 3 }

    adGenAtmTotalCountVpcc      OBJECT-TYPE
       SYNTAX                    		Integer32
       MAX-ACCESS                		read-only
       STATUS                    		current
       DESCRIPTION
           "Return the total number of Vpccs created"
        ::= { adGenAtmTotalCountStatusEntry 4 }

    adGenAtmTotalCountVcIntwk      OBJECT-TYPE
       SYNTAX                    		Integer32
       MAX-ACCESS                		read-only
       STATUS                    		current
       DESCRIPTION
           "Return the total number of Interwork VCs created"
        ::= { adGenAtmTotalCountStatusEntry 5 }

    adGenAtmTotalCountVpIntwk      OBJECT-TYPE
       SYNTAX                    		Integer32
       MAX-ACCESS                		read-only
       STATUS                    		current
       DESCRIPTION
           "Return the total number of Interwork VPs created"
        ::= { adGenAtmTotalCountStatusEntry 6 }

--==================================================================================================================
-- Bulk ATM table operation

-- Request a TLV Instance to read the ATM Tables
-- adGenATMReserveInstanceBulkATMSlotTable lets you do that

-- All filters are defaulted to 0xffffffff until set by the user.  The type is defaulted to 0.
-- Once the user obtains the instance number, the user must set the appropriate filters (type,slot1,port1,vpi1,vci1,node,slot2,port2,vpi2,vci2,stag,ctag)
-- The user must set the Type and at least one other filter order for the search to occur.
-- adGenAtmBulkATMFilterTable provides OIDs to do that.

-- Use the adGenAtmBulkATMSlotInstance OID in adGenAtmBulkATMFilterTable to build the filtered ATM Vccc, Vpcc, Vcl, Vpl, VcIntwk or VpIntwk entries
-- into TLV data for that instance based on the filters applied/associated with that instance.

-- All the above steps must be performed sequentially
-- The data stored in the TLV can be obtained by walking the OIDs in the TLV table (TLV-MIB).
--==================================================================================================================

--==================================================================================================================
-- Bulk ATM reserve instance
--==================================================================================================================

    adGenAtmReserveInstanceBulkATMSlotTable
     OBJECT-TYPE
       SYNTAX      SEQUENCE OF AdGenAtmReserveInstanceBulkATMSlotEntry
       MAX-ACCESS  not-accessible
       STATUS      current
       DESCRIPTION
           "Table contains instances that are created when there is a request to reserve a Bulk ATM instance"
       ::= { adGenAtmBulkATM 1 }

    adGenAtmReserveInstanceBulkATMSlotEntry OBJECT-TYPE
       SYNTAX      AdGenAtmReserveInstanceBulkATMSlotEntry
       MAX-ACCESS  not-accessible
       STATUS      current
       DESCRIPTION
           "Index is the slot number."
       INDEX { adGenSlotInfoIndex }
       ::= { adGenAtmReserveInstanceBulkATMSlotTable 1 }

    AdGenAtmReserveInstanceBulkATMSlotEntry ::=
       SEQUENCE {
           adGenAtmReserveInstanceBulkATMSlotInstance           Integer32
       }

    adGenAtmReserveInstanceBulkATMSlotInstance      OBJECT-TYPE
       SYNTAX                    		Integer32
       MAX-ACCESS                		read-only
       STATUS                    		current
       DESCRIPTION
           "Used to index the Tlv table; each time this is called by slot it
            creates an instance for that viewer"
        ::= { adGenAtmReserveInstanceBulkATMSlotEntry 1 }

--==================================================================================================================
-- The ATM Filter Table
--==================================================================================================================

   adGenAtmBulkATMFilterTable OBJECT-TYPE
       SYNTAX      SEQUENCE OF AdGenAtmBulkATMFilterEntry
       MAX-ACCESS  not-accessible
       STATUS      current
       DESCRIPTION
           "Table contains filters that can be applied on the requested instances"
       ::= { adGenAtmBulkATM 2 }

    adGenAtmBulkATMFilterEntry OBJECT-TYPE
       SYNTAX      AdGenAtmBulkATMFilterEntry
       MAX-ACCESS  not-accessible
       STATUS      current
       DESCRIPTION
           "Indexes are the slot and instance number"
       INDEX { adGenSlotInfoIndex, adGenAtmBulkATMFilterInstance }
       ::= { adGenAtmBulkATMFilterTable 1 }

    AdGenAtmBulkATMFilterEntry ::=
       SEQUENCE {
       	   adGenAtmBulkATMFilterInstance       Integer32,
       	   adGenAtmBulkATMFilterType           INTEGER,
       	   adGenAtmBulkATMFilterSlot1          Unsigned32,
       	   adGenAtmBulkATMFilterPort1          Unsigned32,
       	   adGenAtmBulkATMFilterVpi1           Unsigned32,
       	   adGenAtmBulkATMFilterVci1           Unsigned32,
       	   adGenAtmBulkATMFilterNode           Unsigned32,
       	   adGenAtmBulkATMFilterSlot2          Unsigned32,
       	   adGenAtmBulkATMFilterPort2          Unsigned32,
       	   adGenAtmBulkATMFilterVpi2           Unsigned32,
       	   adGenAtmBulkATMFilterVci2           Unsigned32,
       	   adGenAtmBulkATMFilterStag           Unsigned32,
       	   adGenAtmBulkATMFilterCtag           Unsigned32,
           adGenAtmBulkATMSlotInstance         INTEGER
       }

    adGenAtmBulkATMFilterInstance      	OBJECT-TYPE
       SYNTAX                    		Integer32
       MAX-ACCESS                		not-accessible
       STATUS                    		current
       DESCRIPTION
           "Used to index the Filter table by TLV Instance number."
        ::= { adGenAtmBulkATMFilterEntry 1 }

    adGenAtmBulkATMFilterType      OBJECT-TYPE
       SYNTAX                      INTEGER {
	                                        notspecified(0),
                                                    vccc(1),
                                                    vpcc(2),
                                                     vcl(3),
                                                     vpl(4),
                                                 vpintwk(5),
                                                 vcintwk(6)
                                           }
       MAX-ACCESS                  read-write
       STATUS                      current
       DESCRIPTION
           "Use this to set the type filter for a specific Bulk ATM instance of the Tlv table"
        ::= { adGenAtmBulkATMFilterEntry 2 }

    adGenAtmBulkATMFilterSlot1     OBJECT-TYPE
       SYNTAX                      Unsigned32
       MAX-ACCESS                  read-write
       STATUS                      current
       DESCRIPTION
           "Use this to set the slot endpoint1 filter for a specific Bulk ATM instance of the Tlv table"
        ::= { adGenAtmBulkATMFilterEntry 3 }

    adGenAtmBulkATMFilterPort1     OBJECT-TYPE
       SYNTAX                      Unsigned32
       MAX-ACCESS                  read-write
       STATUS                      current
       DESCRIPTION
           "Use this to set the port endpoint1 filter for a specific Bulk ATM instance of the Tlv table"
        ::= { adGenAtmBulkATMFilterEntry 4 }

    adGenAtmBulkATMFilterVpi1     OBJECT-TYPE
       SYNTAX                      Unsigned32
       MAX-ACCESS                  read-write
       STATUS                      current
       DESCRIPTION
           "Use this to set the vpi endpoint1 filter for a specific Bulk ATM instance of the Tlv table"
        ::= { adGenAtmBulkATMFilterEntry 5 }

    adGenAtmBulkATMFilterVci1     OBJECT-TYPE
       SYNTAX                      Unsigned32
       MAX-ACCESS                  read-write
       STATUS                      current
       DESCRIPTION
           "Use this to set the vci endpoint1 filter for a specific Bulk ATM instance of the Tlv table"
        ::= { adGenAtmBulkATMFilterEntry 6 }

    adGenAtmBulkATMFilterNode     OBJECT-TYPE
       SYNTAX                      Unsigned32
       MAX-ACCESS                  read-write
       STATUS                      current
       DESCRIPTION
           "Use this to set the node filter for a specific Bulk ATM instance of the Tlv table"
        ::= { adGenAtmBulkATMFilterEntry 7 }

    adGenAtmBulkATMFilterSlot2     OBJECT-TYPE
       SYNTAX                      Unsigned32
       MAX-ACCESS                  read-write
       STATUS                      current
       DESCRIPTION
           "Use this to set the slot endpoint2 filter for a specific Bulk ATM instance of the Tlv table"
        ::= { adGenAtmBulkATMFilterEntry 8 }

    adGenAtmBulkATMFilterPort2     OBJECT-TYPE
       SYNTAX                      Unsigned32
       MAX-ACCESS                  read-write
       STATUS                      current
       DESCRIPTION
           "Use this to set the port endpoint2 filter for a specific Bulk ATM instance of the Tlv table"
        ::= { adGenAtmBulkATMFilterEntry 9 }

    adGenAtmBulkATMFilterVpi2     OBJECT-TYPE
       SYNTAX                      Unsigned32
       MAX-ACCESS                  read-write
       STATUS                      current
       DESCRIPTION
           "Use this to set the vpi endpoint2 filter for a specific Bulk ATM instance of the Tlv table"
        ::= { adGenAtmBulkATMFilterEntry 10 }

    adGenAtmBulkATMFilterVci2     OBJECT-TYPE
       SYNTAX                      Unsigned32
       MAX-ACCESS                  read-write
       STATUS                      current
       DESCRIPTION
           "Use this to set the vci endpoint2 filter for a specific Bulk ATM instance of the Tlv table"
        ::= { adGenAtmBulkATMFilterEntry 11 }

    adGenAtmBulkATMFilterStag      OBJECT-TYPE
       SYNTAX                      Unsigned32
       MAX-ACCESS                  read-write
       STATUS                      current
       DESCRIPTION
           "Use this to set the s-tag filter for a specific Bulk ATM instance of the Tlv table"
        ::= { adGenAtmBulkATMFilterEntry 12 }

    adGenAtmBulkATMFilterCtag      OBJECT-TYPE
       SYNTAX                      Unsigned32
       MAX-ACCESS                  read-write
       STATUS                      current
       DESCRIPTION
           "Use this to set the c-tag filter for a specific Bulk ATM instance of the Tlv table"
        ::= { adGenAtmBulkATMFilterEntry 13 }

    adGenAtmBulkATMSlotInstance    OBJECT-TYPE
       SYNTAX INTEGER              {
       								 updateinstance(1)
       							   }
       MAX-ACCESS                  read-write
       STATUS                      current
       DESCRIPTION
           "Set this OID to 1 to update the instance with bulk ATM data based on filters.
            A get on this OID always returns a 1."
        ::= { adGenAtmBulkATMFilterEntry 14 }
END
