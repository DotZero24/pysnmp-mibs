ADTRAN-TACONTROLER-PRODUCT-MIB DEFINITIONS ::= BEGIN

   -- TITLE:     The ADTRAN TA3000 MIB
   -- PRODUCT:   1181001L1
   -- VERSION:   1.14
   -- DATE:      10/15/2008
   -- DATE:      10/24/2008
   -- AUTHOR:    Arthur Poleon
   -- SNMP:      SNMPv2
   -- MIB ARC:   adtran.adShared

   -- NOTES
      -- This is a generic MIB for all versions of the Total Access System Controller
      --   Units that use the second generation RMD files and the generic chassis MIBs.
      -- This MIB defines the object identifier (OID) for PCU HDX, SCU, OPTI6100,
      -- TA5000, TA110F, and others...

    -- HISTORY:
       -- 11/01/2005 ap   First edition.
       -- 11/11/2005 rjf  Update descriptions.
       -- 11/16/2005 rjf  More description updates.
       -- 11/17/2005 KGG  Changed taControllerMgmt to adTaControllerMgmt
       -- 02/06/2006 KMM  Changes while adding support for packed sstate msgs, added:
       --                 *) adTASetSingleServiceStateMsgFail
       --                 *) adTAGetSingleServiceStateMsgFail
       --                 *) adTASetAllServiceStateMsgFail
       --                 *) adTAGetAllServiceStateMsgFail
       -- 04/03/2006 KMM  Added support for provisioning mismatch alarm by adding
       --                 adTACleiCodeMisMatch.
       -- 04/05/2006 JMC  Added adTATIDSysNameSyncEnable.
       -- 04/06/2006 DLW  Added active/clear adTASoftwareVerMisMatch traps for the
       --                 software version mismatch alarm.
       -- 05/03/2006 KGG  Initial work on adding Power Shedding OIDs and Traps
       --                 to be completed by JMC - grep adTASysCtrlPowerShed for OIDs
       --                 grep PowerShedding for Traps
       -- 05/09/2006 JMC  Added Power Shedding OIDs and Alarms.
       -- 05/11/2006 JMC  Fixed up adTASysCtrlPowerShedAlmInput description with regard to TA3000.
       -- 06/02/2006 JMC  A few touches to Power Shedding provitems.  Added Module Discovery Status stuff.
       -- 06/12/2006 KMM  Adding support for HFANM. Added:
       --                 *) adTAFanMPowerAFailClear
       --                 *) adTAFanMPowerAFail
       --                 *) adTAFanMPowerBFailClear
       --                 *) adTAFanMPowerBFail
       -- 06/09/2006 JMC  Added shelf-indexed table for new alarm status OID.
       --                 Changed some naming of my previous slot-indexed table.
       -- 06/19/2006 KGG  Changed Cri,Maj,Min Relay Test Alarm Severities to match alarm type.
       -- 09/26/2006 KGG  Added  adTACleiCodeMisMatchClear  ID: 1006324.
       -- 09/28/2006 KGG  Updated Description of the PowerShedCountDown OID.
       -- 10/05/2006 BKP  Added OIDs and traps for System Release Manager feature support.
       -- 10/05/2006 BKP  Added OIDs and traps for System Release Manager feature support.
       --                 Fixed compiler Not Used Warning by removing adGenSlotProdSwVersion from the IMPORTS section.
       --                 Added a SRM release incomplete bitmask value of 32 Internal Modspec Info Error(Parser doesn't have info)
       -- 10/11/2006 BKP  Changed Release Incomplete references to Release Error. Modified incomplete bitmask and alarms.
       -- 10/19/2006 BKP  Changed the SRM Release Files table to return 1 string of all its info with adTaSysCtrlSrmRlsFilesInfo,
       --                 rather than having individual OIDs for the different types of file info. This new format improves readability.
       --                 Added adTaSysCtrlSrmUpgradeFilename as a varbind for the SRM Upgrade Traps, and adTaSysCtrlSrmReleaseFilename
       --                 as a varbind for the SRM Primary Backup Traps.
       -- 11/03/2006 BKP  Added adTaSysCtrlSrmUpgradeRetries and adTaSysCtrlSrmValidateInterval to support the new SRM provisioning options.
       -- 11/06/2006 BKP  Changed the interval for adTaSysCtrlSrmValidateInterval from hours to days, and decreased the max value to 365.
       -- 11/30/2006 BKP  Added the following description field text to select SRM prov items, "Sets to this OID will have no effect if the SRM system is busy."
       -- 11/30/2006 RJF  Add adTaSysCtrlAutoUpgrade brx @ 1.3.6.1.4.1.664.5.63.100
       -- 01/02/2007 DLW  Added adTASysCtrlAlarmSeverityChanged and adTASysCtrlAlarmSeverityLevel for Alarm Severity.
       -- 01/23/2007 BKP  Added adTaSysCtrlSrmSupport to be able to Enable and Disable the SRM feature.
       -- 01/24/2007 BKP  Changed adTaSysCtrlSrmSupport to adTaSysCtrlSrmAutoUpgradeCtrl.
       -- 02/20/2007 BKP  Removed KEY3's for SRM scheduled timers because they are only displayed with tech. supt.
       --                 privileges on the SRM more details screen. Also removed SNMP support and renumbered the SRM
       --                 OIDs, since we have not released this code.
       --                 Changed SRM variables and text to support the SRM "Download", "Activate", "Active Release", and "Backup Release" terminology.
       -- 02/23/2007 DLW  Added Traps adTASysCtrlDeviceComFail, adTASysCtrlSwdnldStarted, adTASysCtrlSwdnldComplete, adTASysCtrlSwdnldFailure
       -- 03/14/2007 AP   Add adTaSysCtrlFileExport - adTaSysCtrlSeltDelt - adTaSysCtrlGeneralFileExport - adTaSysCtrlSystemLog
       -- 08/15/2007 RJF  Add adTaSysCtrlAutoUpgradeErrorSlots.
       -- 11/05/2007 KABC Added support for KEY3_GENERATE_SSH_KEYS, KEY3_GENERATE_SSH_KEY_SIZE, and KEY3_CURRENT_SSH_KEY_SIZE.
       -- 11/07/2007 KABC Added support for KEY3_GENERATING_KEY_STATUS.
       -- 11/12/2007 KABC Corrected OBJECT IDENTIFIER definition for adTaSysCtrlSysSshKeyMgmt
       -- 12/06/2007 AP   Add DHCP Server Management OIDs
       -- 01/24/2008 RJF  Add Module Reset Oids
       -- 01/29/2008 BKP  Add TL1 Echo OID
       -- 02/12/2008 RJF  Remove enum containing 0 (zero) from adTaModuleResetCtrl.  The values are fully
       --                 documented in the OID-group comment heading.
       -- 03/25/2008 AP   Add SSL Oids.
       -- 07/17/2008 KABC Deprecated adTASysCtrlAlarmSeverityLevel
       -- 09/24/2008 RJF  Add adTaSysCtrlAutoUpgradeNeededSlots adTaSysCtrlAutoUpgradeDeferredResetSlots,
       --                 adTaSysCtrlAutoUpgradeUseSCR
       -- 09/24/2008 RJF  Add adTaSysCtrlReboot brx @ 1.3.6.1.4.1.664.5.63.170
       -- 10/02/2008 RJF  Add adTaSysCtrlAutoUpgradeActiveSlotsBitmask, adTaSysCtrlAutoUpgradeErrorSlotsBitmask,
       --                     adTaSysCtrlAutoUpgradeNeededSlotsBitmask, adTaSysCtrlAutoUpgradeDeferResetSlotsBitmask,
       --                     adTaSysCtrlAutoUpgradeSCRStatus, adTaSysCtrlRebootInitiate, adTaSysCtrlRebootLastStatus,
       --                     adTaSysCtrlRebootException (trap- roughed in)
       -- 10/15/2008 RJF  Prior to release, change adTaSysCtrlAutoUpgradeUseSCR enum from enable/disable to yes/no to match menus.
       --                 Correct numeric oid assignment error in adTaSysCtrlAutoUpgradeSCRStatus.
       -- 10/23/2008 AP   Add adTaSntpGMTtimeZoneString
       -- 10/24/2008 RJF  Re-tweak adTaSysCtrlAutoUpgradeSCRStatus enum value names
       -- 12/22/2008 RJF  Change extended SCA/AutoUpgrade bitmask oids to accept/return up to 256 bytes because
       --                 some systems already do (was 128).
       -- 01/27/2009 KABC Added adTATL1PortExchange
       -- 04/20/2009 DLW  Added severity OID adTASysCtrlPowerShedStateAlarmSeverity for power shed state.
       --                 Added severity variable to adTAPowerSheddingActivated.
       -- 05/08/2009 AP   Add syslog server 2, 3, and 4.
       -- 06/29/2009 KABC Convert to version SNMP v2
       -- 08/12/2009 WFE  Added adTaSysCtrlRebootArmedStatus.
       -- 02/01/2010 AP   Move "adTaSysCtrlRebootException" (adTaSysCtrlReboot.0.1006368) to adTaControllerMgmt.0.1006368
       --                 also known as "adTaControllerMgmtTraps.1006368".
       -- 06/22/2010 WFE  Move "adTaSysCtrlRebootException" from adTaControllerMgmt.0.1006368 to adTaSysCtrlReboot.0.1006368.
       --                 Added adTASysCtrlPowerShedStateAlarmSeverity varbind to adTAPowerSheddingDeActivated trap to match adTAPowerSheddingActivated.
       -- 07/20/2010 WFE  Added adTAPowerSheddingServerTimeoutClear and adTAPowerSheddingServerTimeout.
       --                 Increased max value of adTASysCtrlPowerShedAlmInput from 17 to 18.
       -- 02/10/2011 AP   Added adTaSntpServer2, adTaSntpServer3, adTaSntpServer4, adTaSntpTimeOutProv, adTaSntpTimeRetryProv
       -- 05/09/2011 WFE  "DO NOT MAKE HISTORY COMMENTS HERE!!!! Revision history now in REVISION/DESCRIPTION clauses below"

    IMPORTS
            Integer32, OBJECT-TYPE, MODULE-IDENTITY, NOTIFICATION-TYPE, IpAddress, TimeTicks, Counter32
                FROM SNMPv2-SMI
            adShared
                FROM ADTRAN-MIB
            adTrapInformSeqNum
                FROM ADTRAN-GENTRAPINFORM-MIB
            DisplayString
                FROM SNMPv2-TC
            sysName
                FROM SNMPv2-MIB
            adGenSlotInfoIndex, adGenSlotProdPartNumber, adGenSlotProdName, adGenSlotProdCLEIcode
                FROM ADTRAN-GENSLOT-MIB
            adGenPortTrapIdentifier
               FROM ADTRAN-GENPORT-MIB
            adTAeSCUenvAlarmUserName, adTAeSCUenvAlarmInputLevel, adTAeSCUTrapAlarmLevel
               FROM ADTRAN-TAeSCUEXT1-MIB
            ifIndex
               FROM IF-MIB
            InetAddress, InetAddressType
            FROM INET-ADDRESS-MIB;

-- Module ID ================================================================================================

    adTaControllerMgmt   MODULE-IDENTITY
        LAST-UPDATED    "202107201540Z"
        ORGANIZATION
            "ADTRAN, Inc."
        CONTACT-INFO
           "CND Tech Support
               Postal: ADTRAN, Inc.
                       901 Explorer Blvd.
                       Huntsville, AL  35806
                       Tel: +1 800 726-8663
                       Fax: +1 256 963 6217
                       E-mail: support@adtran.com"
        DESCRIPTION
            "ADTRAN TA Controller Products MIB"
        REVISION "202107201540Z"
        DESCRIPTION
             "Update support for signed certificate requests/signed certificates to provide import/export status."
        REVISION "202106300000Z"
        DESCRIPTION
             "Add support for generating signed certificate requests and importation of signed certs."
        REVISION "201606130000Z"
        DESCRIPTION
             "Add support IPV6 address for SCM servers."
        REVISION      "201310231139Z"
        DESCRIPTION
            "Decrease severity of adTaSysCtrlAutoUpgradeEOSSWarningActive (and *Clear)
             from Minor to Warning(Alert)
             Decrease severity of adTaSysCtrlAutoUpgradeEOSSDeniedActive (and *Clear)
             from Major to Minor.
             Minor rewording of the EOSS Warning/Deny descriptions."
        REVISION      "201310171355Z"
        DESCRIPTION
            "Add initial support for AutoUpgrade EOSS (End Of Software Support) query and trap oids.
             Clarify several AutoUpgrade bitmask descriptions."
        REVISION      "201310151500Z"
        DESCRIPTION
            "Add system configuration change alarm."
        REVISION      "201305031500Z"
        DESCRIPTION
            "Add adTaGeneralExportRemoteHostMethod - File transfer method to use to transfer General Export files from the controller."
        REVISION      "201206191500Z"
        DESCRIPTION
            "Add adTaGenExportExceptionReportEnable - Enable/Disable automatically generated exception reports."
        REVISION      "201107181639Z"
        DESCRIPTION
            "Added adTASysCtrlCardNotReady, adTASysCtrlCardReady, adTASysCtrlCardNotSensed, adTASysCtrlCardSensed"
        REVISION "201106300000Z"
        DESCRIPTION
            "Added adTaSysCtrlVLANBridge, adTaSysCtrlVLANBridgeMode, adTaSysCtrlVLANBridgeInterface.
             Added adTaSntpServer2, adTaSntpServer3, adTaSntpServer4, adTaSntpTimeOutProv, adTaSntpTimeRetryProv
             adTaSntpTimeOutCountServer2, adTaSntpTimeOutCountServer3, adTaSntpTimeOutCountServer4,
             adTaSntpCurrentServer, adTaGenExportPrefixString, adTaGenExportSuffixString"
        REVISION      "201105091256Z"
        DESCRIPTION   "Added adTAScmEthernetInterfaceModeTable."
        REVISION      "201611280000Z"
        DESCRIPTION   "Added adTaSysCtrlReKeyTimeout, adTaSysCtrlReKeyDataLimit, and adTaSysCtrlRebootMode."

        ::= { adShared 63 }

-- OBJECT IDENTIFIERS =======================================================================================

    adTaSysCtrlShelf             OBJECT IDENTIFIER ::= { adTaControllerMgmt 30 }
    adTaSysCtrlSlot              OBJECT IDENTIFIER ::= { adTaControllerMgmt 40 }
    adTaSysCtrlScaMgmt           OBJECT IDENTIFIER ::= { adTaControllerMgmt 50 }
    adTaSysCtrlProvMgmt          OBJECT IDENTIFIER ::= { adTaControllerMgmt 60 }
    adTaSysCtrlPowerShed         OBJECT IDENTIFIER ::= { adTaControllerMgmt 70 }
    adTaSysCtrlSysSSHMgmt        OBJECT IDENTIFIER ::= { adTaControllerMgmt 80 }
    adTaSysCtrlSysRlsMgmt        OBJECT IDENTIFIER ::= { adTaControllerMgmt 90 }
    adTaSysCtrlAutoUpgrade       OBJECT IDENTIFIER ::= { adTaControllerMgmt 100 }
    adTaSysCtrlFileExport        OBJECT IDENTIFIER ::= { adTaControllerMgmt 110 }
    adTaSysCtrlSNTP              OBJECT IDENTIFIER ::= { adTaControllerMgmt 120 }
    adTaSysLog                   OBJECT IDENTIFIER ::= { adTaControllerMgmt 130 }
    adTaDhcpServer               OBJECT IDENTIFIER ::= { adTaControllerMgmt 140 }
    adTaModuleReset              OBJECT IDENTIFIER ::= { adTaControllerMgmt 150 }
    adTaSecurity                 OBJECT IDENTIFIER ::= { adTaControllerMgmt 160 }
    adTaSysCtrlReboot            OBJECT IDENTIFIER ::= { adTaControllerMgmt 170 }
    adTaSysAlarmVarbinds         OBJECT IDENTIFIER ::= { adTaControllerMgmt 180 }
    adTaSysCtrlVLANBridge        OBJECT IDENTIFIER ::= { adTaControllerMgmt 190 }

    adTaSysCtrlSystemLog         OBJECT IDENTIFIER ::= { adTaSysCtrlFileExport 1 }
    adTaSysCtrlGeneralFileExport OBJECT IDENTIFIER ::= { adTaSysCtrlFileExport 20 }

    adTaSSLConfiguration         OBJECT IDENTIFIER ::= { adTaSecurity 50}
    adTaSSLRemoteKeyDownload     OBJECT IDENTIFIER ::= { adTaSSLConfiguration 100}


    --
    -- Controller SCA support for primary and secondary shelves
    --

    adTaSysCtrlScaTable OBJECT-TYPE
       SYNTAX    SEQUENCE OF AdTaSysCtrlScaEntry
       MAX-ACCESS    not-accessible
       STATUS    current
       DESCRIPTION
              "Expansion OIDs for the HDX system."
      ::= { adTaSysCtrlScaMgmt 20 }

   adTaSysCtrlScaEntry OBJECT-TYPE
     SYNTAX      AdTaSysCtrlScaEntry
     MAX-ACCESS      not-accessible
     STATUS      current
     DESCRIPTION
             ""
     INDEX      { adTaSysCtrlCUShelfNumber }
       ::= { adTaSysCtrlScaTable 1 }

   AdTaSysCtrlScaEntry ::=
        SEQUENCE {
            adTaSysCtrlCUShelfNumber
                INTEGER,
            adTaSysCtrlSCAProvItemChanged
                OCTET STRING,
            adTaSysCtrlSCAPresentCards
                OCTET STRING,
            adTaSysCtrlSCASlotsWithProvData
                OCTET STRING,
            adTaSysCtrlSCAoptRestoreCardBitmask
                OCTET STRING
        }

    adTaSysCtrlCUShelfNumber OBJECT-TYPE
                  SYNTAX  INTEGER (1..128)
                  MAX-ACCESS  read-only
                  STATUS  current
                  DESCRIPTION
                          "The shelf number the controller is installed in."
                  ::= { adTaSysCtrlScaEntry 1 }

    adTaSysCtrlSCAProvItemChanged OBJECT-TYPE
                SYNTAX  OCTET STRING (SIZE (0..256))
                MAX-ACCESS  read-only
                STATUS  current
                DESCRIPTION
                  "Bitmap of cards with changed provisions.  This read-only
                  OID will return a bitmap of slots whose provisions have
                  changed since power-up or the last SCA save operation.
                  This is an ascending sequence of bits where the LSB (Least
                  Significant Bit) of the first byte corresponds to slot 1,
                  the LSB of the second byte corresponds to slot 9, with
                  ascending slot numbers being represented until the last
                  byte.  In general, only the bytes required to convey all
                  the 1 bits will actually be sent, all remaining unsent
                  bytes are implied to contain only 0s.  At least one
                  byte will be sent.
                  A bit value of 1 indicates provisions have been changed."
                ::= { adTaSysCtrlScaEntry 5 }

    adTaSysCtrlSCAPresentCards OBJECT-TYPE
                SYNTAX  OCTET STRING (SIZE (0..256))
                MAX-ACCESS  read-only
                STATUS  current
                DESCRIPTION
                  "Bitmap of cards 'present' in the shelf.  This read-only
                  OID will return a bitmap of slots with cards installed.
                  This is an ascending sequence of bits where the LSB (Least
                  Significant Bit) of the first byte corresponds to slot 1,
                  the LSB of the second byte corresponds to slot 9, with
                  ascending slot numbers being represented until the last
                  byte.  In general, only the bytes required to convey all
                  the 1 bits will actually be sent, all remaining unsent
                  bytes are implied to contain only 0s.  At least one
                  byte will be sent.
                  A bit value of 1 indicates a card is present."
                ::= { adTaSysCtrlScaEntry 7 }

    adTaSysCtrlSCASlotsWithProvData OBJECT-TYPE
                SYNTAX  OCTET STRING (SIZE (0..256))
                MAX-ACCESS  read-only
                STATUS  current
                DESCRIPTION
                  "Bitmap of slots with provision data.  This read-only OID
                  will return a bitmap of slots with provision information.
                  This is an ascending sequence of bits where the LSB (Least
                  Significant Bit) of the first byte corresponds to slot 1,
                  the LSB of the second byte corresponds to slot 9, with
                  ascending slot numbers being represented until the last
                  byte.  In general, only the bytes required to convey all
                  the 1 bits will actually be sent, all remaining unsent
                  bytes are implied to contain only 0s.  At least one
                  byte will be sent.
                  A bit value of 1 indicates provisions are present."
                ::= { adTaSysCtrlScaEntry 9 }

    adTaSysCtrlSCAoptRestoreCardBitmask OBJECT-TYPE
                SYNTAX  OCTET STRING (SIZE (0..256))
                MAX-ACCESS  read-write
                STATUS  current
                DESCRIPTION
                  "SCA restore to linecard enable bitmask.  This OID accesses
                  an enable/disable bitmap indicating which slots should have
                  their provision information restored during an SCA restore
                  operation.
                  This is an ascending sequence of bits where the LSB (Least
                  Significant Bit) of the first byte corresponds to slot 1,
                  the LSB of the second byte corresponds to slot 9, with
                  ascending slot numbers being represented until the last
                  byte.  In general, only the bytes required to convey all
                  the 1 bits will actually be sent, all remaining unsent
                  bytes are implied to contain only 0s.  At least one
                  byte will be sent.
                  A bit value of 1 indicates restoration of provision
                  information is enabled for the corresponding slot."
                ::= { adTaSysCtrlScaEntry 11 }

   adTaSysCtrlSCAConfigChangeVersion OBJECT-TYPE
        SYNTAX Counter32
        MAX-ACCESS  read-only
        STATUS  current
        DESCRIPTION
            "The current version number of the SCA file.
             If a change happen on the system, this OID will return the next
             version of the SCA file."
        ::= { adTaSysCtrlScaMgmt 3 }
    --
    -- Controller Provisioning
    --

    adTATIDSysNameSyncEnable OBJECT-TYPE
                SYNTAX  INTEGER { enable(1), disable(2) }
                MAX-ACCESS  read-write
                STATUS  current
                DESCRIPTION
                  "Enable or disable the synchronization of the TID and SNMP SysName provisions.
                  Enabling this option will overwrite the current SysName with the TID and any
                  subsequent set to the SysName must meet TID syntax restrictions."
                ::= { adTaSysCtrlProvMgmt 10 }

    adTATL1echoEnable OBJECT-TYPE
                SYNTAX  INTEGER { enable(1), disable(2) }
                MAX-ACCESS  read-write
                STATUS  current
                DESCRIPTION
                  "Enable or disable character echo on the TL1 port."
                ::= { adTaSysCtrlProvMgmt 11 }


    adTATL1PortExchange OBJECT-TYPE
                SYNTAX  INTEGER { exchange(1)}
                MAX-ACCESS  read-write
                STATUS  current
                DESCRIPTION
                  "Exchange the TL1 ports."
                ::= { adTaSysCtrlProvMgmt 12 }

    adTAScmEthernetInterfaceModeTable OBJECT-TYPE
        SYNTAX     SEQUENCE OF AdTAScmEthernetInterfaceModeEntry
        MAX-ACCESS not-accessible
        STATUS     current
        DESCRIPTION
                "Table of ethernet interface modes."
        ::= { adTaSysCtrlProvMgmt 13 }

    adTAScmEthernetInterfaceModeEntry OBJECT-TYPE
                SYNTAX      AdTAScmEthernetInterfaceModeEntry
                MAX-ACCESS  not-accessible
                STATUS      current
                DESCRIPTION "Set ethernet interface mode to ethercraft or ethernet."
                INDEX       { ifIndex }
                ::= { adTAScmEthernetInterfaceModeTable 1 }

    AdTAScmEthernetInterfaceModeEntry ::= SEQUENCE {
        adTAScmEthernetInterfaceMode INTEGER
    }

    adTAScmEthernetInterfaceMode OBJECT-TYPE
                SYNTAX  INTEGER { ethercraft(1), ethernet(2) }
                MAX-ACCESS  read-write
                STATUS  current
                DESCRIPTION
                  "Set ethernet interface mode to ethercraft or ethernet."
                ::= { adTAScmEthernetInterfaceModeEntry 1 }

    --
    -- Controller Power Shed
    --

    adTASysCtrlPowerShedEnable OBJECT-TYPE
                SYNTAX  INTEGER { enable(1), disable(2) }
                MAX-ACCESS  read-write
                STATUS  current
                DESCRIPTION
                  "Global Enable / Disable of Power Shedding for the entire system."
                ::= { adTaSysCtrlPowerShed 10 }


    adTASysCtrlPowerShedAlmInput OBJECT-TYPE
                SYNTAX  INTEGER  (1..18)
                MAX-ACCESS  read-write
                STATUS  current
                DESCRIPTION
                   "This specifies the External Alarm Input that will be monitored that will indicate loss of AC power.
                   The enumerated set of values is system-dependent.

                   For TA5000:
                        External 1     = 1
                        External 2     = 2,
                        External 3     = 3,
                        External 4     = 4,
                        External 5     = 5,
                        External 6     = 6,
                        External 7     = 7,
                        External 8     = 8,
                        External 9     = 9,
                        External 10    = 10,
                        External 11    = 11,
                        External 12    = 12,
                        External 13    = 13,
                        External 14    = 14,
                        External 15    = 15,
                        External 16    = 16,
                        External ACO   = 17,
                        Remote Server  = 18

                   For OSP:
                        External 1     = 1
                        External 2     = 2,
                        External 3     = 3,
                        External 4     = 4,
                        External 5     = 5,
                        External ACO   = 6,
                        Remote Server  = 7


                   For TA3000 / HDX Systems:
                        External 1     = 1
                        External 2     = 2,
                        Remote         = 3,
                        External ACO   = 4
                   "

                 ::= { adTaSysCtrlPowerShed 11 }


    adTASysCtrlPowerShedActivateDelay OBJECT-TYPE
                SYNTAX  INTEGER  (1..1440)
                MAX-ACCESS  read-write
                STATUS  current
                DESCRIPTION
                   "This specifies the number of minutes the controller
                   should wait to initiate Power Shedding once AC power is lost."
                ::= { adTaSysCtrlPowerShed 12 }


    adTASysCtrlPowerShedDeActivateDelay OBJECT-TYPE
                SYNTAX  INTEGER  (1..1440)
                MAX-ACCESS  read-write
                STATUS  current
                DESCRIPTION
                   "This specifies the number of minutes the controller
                    should wait to cancel Power Shedding once AC power is restored."
                ::= { adTaSysCtrlPowerShed 13 }


    adTASysCtrlPowerShedACFailAlarmDescription OBJECT-TYPE
                SYNTAX  DisplayString (SIZE(1..16))
                MAX-ACCESS  read-write
                STATUS  current
                DESCRIPTION
                   "User specified string that describes the AC failure alarm."
                ::= { adTaSysCtrlPowerShed 14 }


    adTASysCtrlPowerShedACFailAlarmSeverity OBJECT-TYPE
                SYNTAX  INTEGER
                        {
                           info(2),
                           alert(3),
                           minor(4),
                           major(5),
                           critical(6)
                        }
                MAX-ACCESS   read-write
                STATUS  current
                DESCRIPTION
                   "Power Shedding AC Failure alarm severity."
                ::= { adTaSysCtrlPowerShed 15 }


    adTASysCtrlPowerShedACFailAlarmAIDIndex OBJECT-TYPE
                 SYNTAX  INTEGER (1..64)
                 MAX-ACCESS  read-write
                 STATUS  current
                 DESCRIPTION
                    "AID Index."
                ::= { adTaSysCtrlPowerShed 16 }


    adTASysCtrlPowerShedACFailAlarmConditionCode OBJECT-TYPE
                SYNTAX  DisplayString (SIZE(0..11))
                MAX-ACCESS  read-write
                STATUS  current
                DESCRIPTION
                   "Condition code."
                ::= { adTaSysCtrlPowerShed 17 }


    adTASysCtrlPowerShedStatus OBJECT-TYPE
                SYNTAX  INTEGER  { inactive(1), inactiveWaitingToActivate(2), active(3),  activeWaitingToDeactivate(4) }
                MAX-ACCESS  read-only
                STATUS  current
                DESCRIPTION
                   "This indicates the current Power Shedding Status of the System."
                ::= { adTaSysCtrlPowerShed 30 }


    adTASysCtrlPowerShedCountDown OBJECT-TYPE
                SYNTAX  INTEGER  (0..1440)
                MAX-ACCESS  read-only
                STATUS  current
                DESCRIPTION
                   "Countdown timer indicating the number of minutes remaining until Power Shedding is Activated or
                    until Power Shedding is Deactivated.  If Power Shedding is ENABLED and the CountDown is zero (0),
                    it means the countdown time has expired and Power Shedding is taking place.  If Power Shedding is
                    DISABLED and the CountDown is zero (0), it means Power Shedding is Inactive or Off."
                ::= { adTaSysCtrlPowerShed 31 }

    adTASysCtrlPowerShedStateAlarmSeverity OBJECT-TYPE
                SYNTAX  INTEGER
                        {
                           info(2),
                           alert(3),
                           minor(4),
                           major(5),
                           critical(6)
                        }
                MAX-ACCESS   read-write
                STATUS  current
                DESCRIPTION
                   "Power Shedding State alarm severity."
                ::= { adTaSysCtrlPowerShed 32 }

    adTASysCtrlPowerShedRemoteServerIP OBJECT-TYPE
               SYNTAX  IpAddress
               MAX-ACCESS  read-write
               STATUS  current
               DESCRIPTION
                  "Remote Power-Shedding server IP address. Zero
                  signifies 'none'."
               ::= { adTaSysCtrlPowerShed 33 }



    --
    -- Slot Indexed Table
    --

    adTASysCtrlModuleTable OBJECT-TYPE
        SYNTAX     SEQUENCE OF AdTASysCtrlModuleEntry
        MAX-ACCESS     not-accessible
        STATUS     current
        DESCRIPTION
                "Table of status OIDs indexed by slot/module."
        ::= { adTaSysCtrlSlot 3 }

    adTASysCtrlModuleEntry OBJECT-TYPE
        SYNTAX     AdTASysCtrlModuleEntry
        MAX-ACCESS     not-accessible
        STATUS     current
        DESCRIPTION
                ""
        INDEX { adTASysCtrlModuleNumber }
        ::= { adTASysCtrlModuleTable 1 }

    AdTASysCtrlModuleEntry ::= SEQUENCE {
        adTASysCtrlModuleNumber INTEGER,
        adTASysCtrlModuleDiscoveryStatus INTEGER
    }

    adTASysCtrlModuleNumber OBJECT-TYPE
        SYNTAX     INTEGER (1..255)
        MAX-ACCESS     read-only
        STATUS     current
        DESCRIPTION
                "Index for each slot/module."
        ::= { adTASysCtrlModuleEntry 1 }

    adTASysCtrlModuleDiscoveryStatus OBJECT-TYPE
        SYNTAX  INTEGER
                {
                   empty         (1),
                   discovering   (2),
                   ok-no-rmd     (3),
                   ok            (4),
                   unresponsive  (5),
                   unknown       (6)
                }
        MAX-ACCESS   read-only
        STATUS   current
        DESCRIPTION
           "The current discovery status of each slot or module in the system."
        ::= { adTASysCtrlModuleEntry 2 }


    --
    -- Shelf Indexed Table
    --

    adTASysCtrlShelfTable OBJECT-TYPE
        SYNTAX     SEQUENCE OF AdTASysCtrlShelfEntry
        MAX-ACCESS     not-accessible
        STATUS     current
        DESCRIPTION
                "A shelf-indexed table of information."
        ::= { adTaSysCtrlShelf 3 }

    adTASysCtrlShelfEntry OBJECT-TYPE
        SYNTAX     AdTASysCtrlShelfEntry
        MAX-ACCESS     not-accessible
        STATUS     current
        DESCRIPTION
                ""
        INDEX { adTASysCtrlShelfNumber }
        ::= { adTASysCtrlShelfTable 1 }

    AdTASysCtrlShelfEntry ::= SEQUENCE {
        adTASysCtrlShelfNumber INTEGER,
        adTASysCtrlModuleRemovedStatus OCTET STRING
    }

    adTASysCtrlShelfNumber OBJECT-TYPE
        SYNTAX     INTEGER (1..255)
        MAX-ACCESS     read-only
        STATUS     current
        DESCRIPTION
                "Index representing each shelf."
        ::= { adTASysCtrlShelfEntry 1 }

    adTASysCtrlModuleRemovedStatus OBJECT-TYPE
        SYNTAX   OCTET STRING (SIZE (0..32))
        MAX-ACCESS   read-only
        STATUS   current
        DESCRIPTION
           "A bitmask representing Module Removed status for each shelf.
            Trailing empty bytes are truncated."
        ::= { adTASysCtrlShelfEntry 2 }

    --
    -- Controller System SSH Manager OIDs
    --

    adTaSysCtrlSysSshKeyMgmt OBJECT IDENTIFIER
             ::= { adTaSysCtrlSysSSHMgmt 10 }

    adTaSysCtrlCurrentKeySize OBJECT-TYPE
        SYNTAX  INTEGER (512..2048)
        MAX-ACCESS  read-only
        STATUS  current
        DESCRIPTION
            "Read-only display of current key size."
        ::= { adTaSysCtrlSysSshKeyMgmt 1 }

    adTaSysCtrlKeySize OBJECT-TYPE
        SYNTAX  INTEGER (512..2048)
        MAX-ACCESS  read-write
        STATUS  current
        DESCRIPTION
            "Sets a new key size."
        ::= { adTaSysCtrlSysSshKeyMgmt 2 }

    adTaSysCtrlGenerateKeys OBJECT-TYPE
        SYNTAX  INTEGER (1..2)
        MAX-ACCESS  read-write
        STATUS  current
        DESCRIPTION
            "Generates new keys based upon new key size."
        ::= { adTaSysCtrlSysSshKeyMgmt 15 }

    adTaSysCtrlGenKeyStatus OBJECT-TYPE
        SYNTAX  INTEGER (1..3)
        MAX-ACCESS  read-only
        STATUS  current
        DESCRIPTION
            "Status of new keys generation process."
        ::= { adTaSysCtrlSysSshKeyMgmt 16 }

    adTaSysCtrlReKeyTimeout OBJECT-TYPE
        SYNTAX  INTEGER (0..1440)
        MAX-ACCESS  read-write
        STATUS  current
        DESCRIPTION
            "Amount of time in minutes since last key exchange to trigger a rekey. The default value
             is 480 minutes. Use 0 for no limit. "
        DEFVAL  { 480 }
        ::= { adTaSysCtrlSysSshKeyMgmt 20 }

    adTaSysCtrlReKeyDataLimit OBJECT-TYPE
        SYNTAX  INTEGER (0..10000)
        MAX-ACCESS  read-write
        STATUS  current
        DESCRIPTION
            "Amount of data exchange in megabytes since last key exchange to trigger a rekey. The default value
             is 1000 megabytes. Use 0 for no limit."
        DEFVAL  { 1000 }
        ::= { adTaSysCtrlSysSshKeyMgmt 21 }

    --
    -- Controller System Release Manager OIDs
    --

    -- SRM Active and/or Backup Release Table
    adTaSysCtrlSysRlsTable OBJECT-TYPE
        SYNTAX    SEQUENCE OF AdTaSysCtrlSysRlsEntry
        MAX-ACCESS    not-accessible
        STATUS    current
        DESCRIPTION
            "The SRM System Release Table."
        ::= { adTaSysCtrlSysRlsMgmt 1 }

    adTaSysCtrlSysRlsEntry OBJECT-TYPE
        SYNTAX      AdTaSysCtrlSysRlsEntry
        MAX-ACCESS      not-accessible
        STATUS      current
        DESCRIPTION
            "An entry in the SRM System Release Table."
        INDEX      { adTaSysCtrlSrmReleaseIndex }
        ::= { adTaSysCtrlSysRlsTable 1 }

    AdTaSysCtrlSysRlsEntry ::=
        SEQUENCE {
            adTaSysCtrlSrmReleaseIndex
                INTEGER,
            adTaSysCtrlSrmReleaseName
                DisplayString,
            adTaSysCtrlSrmReleaseFilename
                DisplayString,
            adTaSysCtrlSrmReleaseStatus
                DisplayString,
            adTaSysCtrlSrmReleaseMemoryUsageKB
                Integer32,
            adTaSysCtrlSrmReleaseFileCount
                Integer32,
            adTaSysCtrlSrmReleaseProductCount
                Integer32,
            adTaSysCtrlSrmReleaseFilesTableEntries
                Integer32,
            adTaSysCtrlSrmReleaseErrorBitmask
                Integer32
        }

    adTaSysCtrlSrmReleaseIndex OBJECT-TYPE
        SYNTAX  INTEGER (1..2)
        MAX-ACCESS  read-only
        STATUS  current
        DESCRIPTION
            "1 repersents the Active System Release, and
             2 represents the Backup System Release."
        ::= { adTaSysCtrlSysRlsEntry 1 }

    adTaSysCtrlSrmReleaseName OBJECT-TYPE
        SYNTAX  DisplayString (SIZE(0..40))
        MAX-ACCESS  read-only
        STATUS  current
        DESCRIPTION
            "This OID displays the System Release Name."
        ::= { adTaSysCtrlSysRlsEntry 2 }

    adTaSysCtrlSrmReleaseFilename OBJECT-TYPE
        SYNTAX  DisplayString (SIZE(0..32))
        MAX-ACCESS  read-only
        STATUS  current
        DESCRIPTION
            "The ReleaseFilename OID specifies the Release filename that
             was retrieved by the System Release Manager system.  This
             release file contains information such as module part number,
             firmware filename, and firmware file details that are necessary
             to validate a System Release."
        ::= { adTaSysCtrlSysRlsEntry 3 }

    adTaSysCtrlSrmReleaseStatus OBJECT-TYPE
        SYNTAX  DisplayString (SIZE(0..40))
        MAX-ACCESS  read-only
        STATUS  current
        DESCRIPTION
            "The Release Status indicates the current state, status, and
             file counts for the Active or Backup system release.
             For example: Idle, Complete, 27/27 Files"
        ::= { adTaSysCtrlSysRlsEntry 4 }

    adTaSysCtrlSrmReleaseMemoryUsageKB OBJECT-TYPE
        SYNTAX  Integer32
        MAX-ACCESS  read-only
        STATUS  current
        DESCRIPTION
            "The number of flash memory KBytes the System Release is
             currently using to store the system release files."
        ::= { adTaSysCtrlSysRlsEntry 5 }

    adTaSysCtrlSrmReleaseFileCount OBJECT-TYPE
        SYNTAX  Integer32
        MAX-ACCESS  read-only
        STATUS  current
        DESCRIPTION
            "The total number of unique files in a System Release,
             including the SRA file and the individual firmware files."
        ::= { adTaSysCtrlSysRlsEntry 6 }

    adTaSysCtrlSrmReleaseProductCount OBJECT-TYPE
        SYNTAX  Integer32
        MAX-ACCESS  read-only
        STATUS  current
        DESCRIPTION
            "The total number of products supported by the System Release."
        ::= { adTaSysCtrlSysRlsEntry 7 }

    adTaSysCtrlSrmReleaseFilesTableEntries OBJECT-TYPE
        SYNTAX  Integer32
        MAX-ACCESS  read-only
        STATUS  current
        DESCRIPTION
            "The number of entries in the adTaSysCtrlSysRlsFilesTable.
             This value is the adTaSysCtrlSrmReleaseProductCount plus 1 for
             the release file."
        ::= { adTaSysCtrlSysRlsEntry 8 }

    adTaSysCtrlSrmReleaseErrorBitmask OBJECT-TYPE
        SYNTAX  Integer32
        MAX-ACCESS  read-only
        STATUS  current
        DESCRIPTION
            "A system release can be in error for several reasons,
             and this bitmap is used to show which reason.
             The various bit value positions are:
                1 File Not Found
                2 Invalid File Length
                4 Invalid File CRC
                8 Invalid File Checksum
               16 Parse Failed
               32 Internal Modspec Info Error(Parser doesn't have info)"
        ::= { adTaSysCtrlSysRlsEntry 9 }


    -- SRM Release Files Table
    adTaSysCtrlSysRlsFilesTable OBJECT-TYPE
       SYNTAX    SEQUENCE OF AdTaSysCtrlSysRlsFilesEntry
       MAX-ACCESS    not-accessible
       STATUS    current
       DESCRIPTION
              ""
      ::= { adTaSysCtrlSysRlsMgmt 2 }


   adTaSysCtrlSysRlsFilesEntry OBJECT-TYPE
     SYNTAX      AdTaSysCtrlSysRlsFilesEntry
     MAX-ACCESS      not-accessible
     STATUS      current
     DESCRIPTION
             ""
     INDEX      { adTaSysCtrlSrmReleaseIndex,
                  adTaSysCtrlSrmRlsFilesIndex }
       ::= { adTaSysCtrlSysRlsFilesTable 1 }

   AdTaSysCtrlSysRlsFilesEntry ::=
        SEQUENCE {
            adTaSysCtrlSrmRlsFilesIndex
                Integer32,
            adTaSysCtrlSrmRlsFilesInfo
                DisplayString
        }

    adTaSysCtrlSrmRlsFilesIndex OBJECT-TYPE
        SYNTAX  Integer32
        MAX-ACCESS  read-only
        STATUS  current
        DESCRIPTION
            "Index for a file that is part of a System Release.
             There will be duplicate filenames in this table,
             because different products may share firmware."
        ::= { adTaSysCtrlSysRlsFilesEntry 1 }

    adTaSysCtrlSrmRlsFilesInfo OBJECT-TYPE
        SYNTAX  DisplayString (SIZE(0..80))
        MAX-ACCESS  read-only
        STATUS  current
        DESCRIPTION
            "This OID displays a release file's filename, product part number,
             product rev range, file rev, and detailed file status info.
             The file status info will display the size in KBytes stored to flash,
             and timestamp when the file was stored.
             If the File is not found, then this OID will display 'File Not Found'."
        ::= { adTaSysCtrlSysRlsFilesEntry 2 }


    -- SRM Scalar OIDs

    adTaSysCtrlSrmCancel OBJECT-TYPE
        SYNTAX  INTEGER {
            cancelSrmCommand(1)
            }
        MAX-ACCESS  read-write
        STATUS  current
        DESCRIPTION
            "Request that the current System Release Manager operation
             is be stopped. This OID will have no effect if the SRM system
             is not active (Idle/Cancel/Error/Complete states)."
        ::= { adTaSysCtrlSysRlsMgmt 10 }

    adTaSysCtrlSrmActivateBrls OBJECT-TYPE
        SYNTAX  INTEGER {
            activateBackupRls(1)
            }
        MAX-ACCESS  read-write
        STATUS  current
        DESCRIPTION
            "This OID instructs the System Release Manager to make the
             Backup and Active Releases to switch roles. The Backup
             Release becomes the Active Release and vice versa. This OID
             will have no effect if the SRM system is busy downloading,
             backing up, or the Backup Release has errors. An Auto Upgrade
             busy state will also inhibit this OID's operation."
        ::= { adTaSysCtrlSysRlsMgmt 11 }

    adTaSysCtrlSrmBackupArls OBJECT-TYPE
        SYNTAX  INTEGER {
            backupActiveRls(1)
            }
        MAX-ACCESS  read-write
        STATUS  current
        DESCRIPTION
            "This OID instructs the System Release Manager to overwrite the
             Backup Release with a backup copy of the Active Release.
             This OID will have no effect if the SRM system is busy downloading,
             backing up, or the Backup Release has errors."
        ::= { adTaSysCtrlSysRlsMgmt 12 }

    adTaSysCtrlSrmDownloadInitiate OBJECT-TYPE
        SYNTAX  INTEGER {
            initiateSrmDownload(1)
            }
        MAX-ACCESS  read-write
        STATUS  current
        DESCRIPTION
            "This OID instructs the System Release Manager to replace the
             Backup release files with the SRM Download Filename release.
             SRM will use Remote IO to acquire files that are needed to complete
             the new System release. This OID will have no effect if the SRM system
             is busy downloading or backing up."
        ::= { adTaSysCtrlSysRlsMgmt 13 }

    adTaSysCtrlSrmDownloadSameFiles OBJECT-TYPE
        SYNTAX  INTEGER { enable(1), disable(2) }
        MAX-ACCESS  read-write
        STATUS  current
        DESCRIPTION
            "Enable or disable the SRM Download Same Files option.
             Enabling this option will instruct SRM to completly delete
             the Backup release and remotely get every file that is
             part of the new System release.
             Disabling this option will instruct SRM to only delete the
             Backup release files that are NOT part of the new System
             release, and remotely get only those files needed to complete
             the new System release.
             Sets to this OID will have no effect if the SRM system is busy."
        ::= { adTaSysCtrlSysRlsMgmt 14 }

    adTaSysCtrlSrmDownloadRetries OBJECT-TYPE
        SYNTAX  INTEGER (0..10)
        MAX-ACCESS  read-write
        STATUS  current
        DESCRIPTION
            "This OID instructs the System Release Manager how many times it
             should attempt to Download files to the Backup system release after
             the first download has failed. Sets to this OID will have no effect if
             the SRM system is busy."
        ::= { adTaSysCtrlSysRlsMgmt 15 }

    adTaSysCtrlSrmDownloadFilename OBJECT-TYPE
        SYNTAX  DisplayString (SIZE(0..32))
        MAX-ACCESS  read-write
        STATUS  current
        DESCRIPTION
            "The DownloadFilename OID specifies the Release filename to
             be retrieved by the System Release Manager system.  This
             release file contains information such as module part number,
             firmware filename, and firmware file details that are necessary
             to perform System Release Manager operations.
             The Filename may not contain spaces, quotes, path info, or other
             unusual characters that would generally be considered invalid in
             a filename specification.
             Sets to this OID will have no effect if the SRM system is busy."
        ::= { adTaSysCtrlSysRlsMgmt 16 }

    adTaSysCtrlSrmDownloadBasepath OBJECT-TYPE
        SYNTAX  DisplayString (SIZE(0..40))
        MAX-ACCESS  read-write
        STATUS  current
        DESCRIPTION
            "The DownloadBasepath OID allows the customer to specify a
             directory prefix where the SRM release and firmware files
             will be located on the server.  It is assumed that the SRM
             release and firmware files will be located in the same directory.
             The Basepath argument may not contain spaces, commas,
             quotes, or other unusual characters that would generally
             be considered invalid in a path specification.  Although
             the Controller does not interpret the contents of this string,
             please keep in mind that different operating systems have
             different rules concerning what constitutes valid
             characters and path/file separators.
             Sets to this OID will have no effect if the SRM system is busy."
        ::= { adTaSysCtrlSysRlsMgmt 17 }

    adTaSysCtrlSrmScheduledDownload OBJECT-TYPE
        SYNTAX  DisplayString (SIZE(0..14))
        MAX-ACCESS  read-write
        STATUS  current
        DESCRIPTION
            "The ScheduledDownload OID allows the customer to specify a
             date and time that the SRM will start a download to the
             Backup System Release.
             The specified time must be greater than 1 minute, but no more
             than 90 days from the controller's current time.
             The date and time has the following format: MM/DD/YY HH:MM"
        ::= { adTaSysCtrlSysRlsMgmt 18 }

    adTaSysCtrlSrmScheduledActivate OBJECT-TYPE
        SYNTAX  DisplayString (SIZE(0..14))
        MAX-ACCESS  read-write
        STATUS  current
        DESCRIPTION
            "The ScheduledActivate OID allows the customer to specify a
             date and time that SRM will make the Backup System Release
             the Active System Release.
             The specified time must be greater than 1 minute, but no more
             than 90 days from the controller's current time.
             The date and time has the following format: MM/DD/YY HH:MM"
        ::= { adTaSysCtrlSysRlsMgmt 19 }

    adTaSysCtrlSrmValidateInterval OBJECT-TYPE
        SYNTAX  INTEGER (0..365)
        MAX-ACCESS  read-write
        STATUS  current
        DESCRIPTION
            "This OID instructs the System Release Manager how often, in days, it
             should check that a complete Active and/or Backup release is still
             valid. A value of 0 indicates interval checks should not be performed,
             and the validate checks performed at startup and after a Download or
             Backup are sufficient."
        ::= { adTaSysCtrlSysRlsMgmt 20 }

    adTaSysCtrlSrmStatus OBJECT-TYPE
        SYNTAX  DisplayString (SIZE(0..255))
        MAX-ACCESS  read-only
        STATUS  current
        DESCRIPTION
            "This OID will return a formatted string describing the current
             status and progress of the SRM operations.
             Refer to the ''System Release Manager Feature'' user guide for
             details."
        ::= { adTaSysCtrlSysRlsMgmt 21 }

    adTaSysCtrlSrmAutoUpgradeCtrl OBJECT-TYPE
        SYNTAX  INTEGER { enable(1), disable(2) }
        MAX-ACCESS  read-write
        STATUS  current
        DESCRIPTION
            "Enable or disable SRM's control of Auto Upgrade.
             This option is enabled by default for controllers that support SRM.
             Enabling Auto Upgrade control forces Auto Upgrade to retrieve the
             system release package from the Flash File System.
             Disabling Auto Upgrade control instructs the Auto Upgrade system
             to retrieve files based off of the Auto Upgrade provisioned settings."
        ::= { adTaSysCtrlSysRlsMgmt 22 }


    --
    -- AutoUpgrade OIDs
    --

    adTaSysCtrlAutoUpgradeActiveSlots OBJECT-TYPE
        SYNTAX  DisplayString (SIZE(0..255))
        MAX-ACCESS  read-only
        STATUS  current
        DESCRIPTION
            "Return information regarding active AutoUpgrades.
             The format is a(b,b,b) where a is the number of slots currently
             upgrading, and b is a comma separated list of zero or more SNMP
             slots being upgraded, which may be truncated if the set is very
             large"
        ::= { adTaSysCtrlAutoUpgrade 1 }

    adTaSysCtrlAutoUpgradeErrorSlots OBJECT-TYPE
        SYNTAX  DisplayString (SIZE(0..255))
        MAX-ACCESS  read-only
        STATUS  current
        DESCRIPTION
            "Return information regarding slots with AutoUpgrade errors.
             The format is a(b,b,b) where a is the number of slots that
             are currently in an AutoUpgrade error-state, and b is a comma
             separated list of zero or more SNMP slots in an AutoUpgrade error
             state, which may be truncated if the set is very large"
        ::= { adTaSysCtrlAutoUpgrade 2 }

    adTaSysCtrlAutoUpgradeNeededSlots OBJECT-TYPE
        SYNTAX  DisplayString (SIZE(0..255))
        MAX-ACCESS  read-only
        STATUS  current
        DESCRIPTION
            "Return information regarding the number of slots needing upgrade.
             The format is a(b,b,b) where a is the number of slots needing
             upgrade, and b is a comma separated list of zero or more SNMP
             slots that need upgrade, which may be truncated if the set is
             very large"
        ::= { adTaSysCtrlAutoUpgrade 3 }

    adTaSysCtrlAutoUpgradeDeferredResetSlots OBJECT-TYPE
        SYNTAX  DisplayString (SIZE(0..255))
        MAX-ACCESS  read-only
        STATUS  current
        DESCRIPTION
            "Return information regarding slots that AutoUpgrade has deferred
             module reset following upgrade in conjunction with System
             Controlled Reset (SCR).  The format is a(b,b,b) where a is the
             number of slots where reset has been deferred, and b is a comma
             separated list of zero or more SNMP slots that AutoUpgrade has
             deferred reset, which may be truncated if the set is very large"
        ::= { adTaSysCtrlAutoUpgrade 4 }

    adTaSysCtrlAutoUpgradeActiveSlotsBitmask OBJECT-TYPE
        SYNTAX  OCTET STRING (SIZE (0..256))
        MAX-ACCESS  read-only
        STATUS  current
        DESCRIPTION
          "This read-only OID will return a bitmap of slots currently upgrading.
          This is an ascending sequence of bits where the LSB (Least
          Significant Bit) of the first byte corresponds to slot 1,
          the LSB of the second byte corresponds to slot 9, with
          ascending slot numbers being represented until the last
          byte.  In general, only the bytes required to convey all
          the 1 bits will actually be sent, all remaining unsent
          bytes are implied to contain only 0s.  At least one
          byte will be sent.
          A bit value of 1 indicates a card is currently upgrading."
        ::= { adTaSysCtrlAutoUpgrade 5 }

    adTaSysCtrlAutoUpgradeErrorSlotsBitmask OBJECT-TYPE
        SYNTAX  OCTET STRING (SIZE (0..256))
        MAX-ACCESS  read-only
        STATUS  current
        DESCRIPTION
          "This read-only OID will return a bitmap of slots having an
          AutoUpgrade eror status.
          This is an ascending sequence of bits where the LSB (Least
          Significant Bit) of the first byte corresponds to slot 1,
          the LSB of the second byte corresponds to slot 9, with
          ascending slot numbers being represented until the last
          byte.  In general, only the bytes required to convey all
          the 1 bits will actually be sent, all remaining unsent
          bytes are implied to contain only 0s.  At least one
          byte will be sent.
          A bit value of 1 indicates a card has an AutoUpgrade error status."
        ::= { adTaSysCtrlAutoUpgrade 6 }

    adTaSysCtrlAutoUpgradeNeededSlotsBitmask OBJECT-TYPE
        SYNTAX  OCTET STRING (SIZE (0..256))
        MAX-ACCESS  read-only
        STATUS  current
        DESCRIPTION
          "This read-only OID will return a bitmap of slots needing upgrade.
          This is an ascending sequence of bits where the LSB (Least
          Significant Bit) of the first byte corresponds to slot 1,
          the LSB of the second byte corresponds to slot 9, with
          ascending slot numbers being represented until the last
          byte.  In general, only the bytes required to convey all
          the 1 bits will actually be sent, all remaining unsent
          bytes are implied to contain only 0s.  At least one
          byte will be sent.
          A bit value of 1 indicates a card needs upgrade."
        ::= { adTaSysCtrlAutoUpgrade 7 }

    adTaSysCtrlAutoUpgradeDeferResetSlotsBitmask OBJECT-TYPE
        SYNTAX  OCTET STRING (SIZE (0..256))
        MAX-ACCESS  read-only
        STATUS  current
        DESCRIPTION
          "This read-only OID will return a bitmap of slots whose post-
          upgrade reset has been deferred for System Controlled Reboot.
          This is an ascending sequence of bits where the LSB (Least
          Significant Bit) of the first byte corresponds to slot 1,
          the LSB of the second byte corresponds to slot 9, with
          ascending slot numbers being represented until the last
          byte.  In general, only the bytes required to convey all
          the 1 bits will actually be sent, all remaining unsent
          bytes are implied to contain only 0s.  At least one
          byte will be sent.
          A bit value of 1 indicates reset has been deferred for that slot."
        ::= { adTaSysCtrlAutoUpgrade 8 }


    adTaSysCtrlAutoUpgradeUseSCR OBJECT-TYPE
        SYNTAX  INTEGER { yes(1), no(2) }
        MAX-ACCESS  read-write
        STATUS  current
        DESCRIPTION
          "Controls AutoUpgrades use of the System Controlled Reboot (SCR) system.
           If set to yes, module reboot will be deferred until later, based upon SCR
           settings."
        ::= { adTaSysCtrlAutoUpgrade 10 }

    adTaSysCtrlAutoUpgradeSCRStatus OBJECT-TYPE
        SYNTAX  INTEGER {
                           nonePending(1),
                           readyForSCR(2),
                           scrBusy(3),
                           auNeeded(4),
                           auBusy(5),
                           auErrors(6),
                           auNotUsingSCR(7),
                           noneWaitingForSCR(8)
                        }
        MAX-ACCESS  read-only
        STATUS  current
        DESCRIPTION
          "Returns an enum indicating readiness to perform SCR with repect to the
           AutoUpgrade system.  The SCR system will ignore all initiate requests
           unless the current value of adTaSysCtrlAutoUpgradeSCRStatus is ReadyForSCR."
        ::= { adTaSysCtrlAutoUpgrade 12 }


    adTaSysCtrlAutoUpgradeEOSSCapable OBJECT-TYPE
        SYNTAX  INTEGER { yes(1), no(2) }
        MAX-ACCESS  read-only
        STATUS  current
        DESCRIPTION
          "Indicates whether EOSS (End Of Software Support) information is present and
           valid in this software build."
        ::= { adTaSysCtrlAutoUpgrade 30 }

    adTaSysCtrlAutoUpgradeEOSSWarnSlotsBitmask OBJECT-TYPE
        SYNTAX  OCTET STRING (SIZE (0..256))
        MAX-ACCESS  read-only
        STATUS  current
        DESCRIPTION
          "This read-only OID will return a bitmap of slots with an
          active EOSS (End Of Software Support) Warning status.
          This is an ascending sequence of bits where the LSB (Least
          Significant Bit) of the first byte corresponds to slot 1,
          the LSB of the second byte corresponds to slot 9, with
          ascending slot numbers being represented until the last
          byte.  In general, only the bytes required to convey all
          the 1 bits will actually be sent, all remaining unsent
          bytes are implied to contain only 0s.  At least one
          byte will be sent.
          A bit value of 1 indicates an active EOSS Warning status
          for this slot."
        ::= { adTaSysCtrlAutoUpgrade 32 }

    adTaSysCtrlAutoUpgradeEOSSDenySlotsBitmask OBJECT-TYPE
        SYNTAX  OCTET STRING (SIZE (0..256))
        MAX-ACCESS  read-only
        STATUS  current
        DESCRIPTION
          "This read-only OID will return a bitmap of slots with an
          active EOSS (End Of Software Support) Denied status.
          This is an ascending sequence of bits where the LSB (Least
          Significant Bit) of the first byte corresponds to slot 1,
          the LSB of the second byte corresponds to slot 9, with
          ascending slot numbers being represented until the last
          byte.  In general, only the bytes required to convey all
          the 1 bits will actually be sent, all remaining unsent
          bytes are implied to contain only 0s.  At least one
          byte will be sent.
          A bit value of 1 indicates an active EOSS Denied status
          for this slot."
        ::= { adTaSysCtrlAutoUpgrade 34 }


    --
    -- System Controlled Reboot (SCR) OIDs
    --

    adTaSysCtrlRebootOperMode OBJECT-TYPE
        SYNTAX  INTEGER { auto(1), manual(2), scheduled(3) }
        MAX-ACCESS  read-write
        STATUS  current
        DESCRIPTION
          "SCR Operating mode."
        ::= { adTaSysCtrlReboot 1 }

    adTaSysCtrlRebootSchedDateTime OBJECT-TYPE
        SYNTAX  DisplayString (SIZE(0..255))
        MAX-ACCESS  read-write
        STATUS  current
        DESCRIPTION
            "Future date/time to perform a scheduled SCR operation if SCR
             OperMode is set to scheduled, otherwise this value is ignored.
             Typical format of date/time strings are:
                 7/4/8           (date only, short 2008 year, 00:00:00 HRS)
                 7/4/2008        (date only, full  2008 year, 00:00:00 HRS)
                 8:15            (current date, 8:15:00 HRS)
                 8:15:5          (current date, 8:15:05 HRS)
                 7/4/2008 8:15   (7/4/2008 08:15:00)
                 7/4/8 08:15:05  (7/4/2008 08:15:05)
             Setting this provision to an empty string is valid and indicates a
             scheduled SCR operation should not be performed even if SCR OperMode
             has a value of scheduled.  This string will be reformatted by the
             controller to reflect a full and correct date/time value.  For
             example, if only the time is supplied, the current date will be
             inserted into the string in order to form a complete date/time
             specification."
        ::= { adTaSysCtrlReboot 2 }

    adTaSysCtrlRebootInitiate OBJECT-TYPE
        SYNTAX  INTEGER { initiateSCR(1) }
        MAX-ACCESS  read-write
        STATUS  current
        DESCRIPTION
            "This OID instructs the System Controlled Reboot (SCR) subsystem
             to reboot all modules in the sstem if any post-AutoUpgrade reboots have
             been deferred.  This is NOT a general system reset operation, which would
             constitude a serious Denial Of Service vulnerability.  The SCR system
             will ignore all initiate requests unless the current value of
             adTaSysCtrlAutoUpgradeSCRStatus is ReadyForSCR."
        ::= { adTaSysCtrlReboot 3 }

    adTaSysCtrlRebootLastStatus OBJECT-TYPE
        SYNTAX  DisplayString (SIZE(0..255))
        MAX-ACCESS  read-only
        STATUS  current
        DESCRIPTION
            "Returns the last SCR status string.  Error statuses are persistent.
             This string generally begin with a single-word state such as Idle, Busy, Error,
             and are optionally followed with a short error explanation."
        ::= { adTaSysCtrlReboot 4 }

    adTaSysCtrlRebootArmedStatus OBJECT-TYPE
        SYNTAX  INTEGER { armed(1), notArmed(2) }
        MAX-ACCESS  read-write
        STATUS  current
        DESCRIPTION
          "Returns the Armed Status of the SCR one-shot. Setting the value to armed will
           change the status to armed.  Currently, setting the value to notArmed will return
           an error.  In the future, setting the value to notArmed could change the status
           to notArmed."
        ::= { adTaSysCtrlReboot 5 }

    adTaSysCtrlRebootMode OBJECT-TYPE
        SYNTAX  INTEGER { concurrentMode(1), redundancyMode(2) }
        MAX-ACCESS  read-write
        STATUS  current
        DESCRIPTION
          "SCR reboot mode. concurrentMode will reboot cards in concurrent order, without considering redundancy status.
           redundancyMode will reboot cards in concurrent order, but also take into account redundancy status: reboot offline
           and non-redundant cards in the first pass, wait for all rebooted cards to come back up, then reboot online cards
           in the second pass. The default value is concurrentMode."
        DEFVAL  { concurrentMode }
        ::= { adTaSysCtrlReboot 6 }

    --
    -- Alarm Severity
    --

    adTASysCtrlAlarmSeverityLevel OBJECT-TYPE
        SYNTAX INTEGER {
                            none(1),
                            info(2),
                            alert(3),
                            minor(4),
                            major(5),
                            critical(6)
                       }
        MAX-ACCESS  read-only
        STATUS  deprecated
        DESCRIPTION
            "The highest active alarm severity level. Deprecated, please use adTaAlarmMasterSeverityLevel."
        ::= { adTaSysCtrlShelf 4 }

     adTASysConfigurationChangeTimer OBJECT-TYPE
        SYNTAX INTEGER (0..1440)
        MAX-ACCESS  read-write
        STATUS  current
        DESCRIPTION
            "The frequency  an alarm will be sent if a change occurs on the system."
        ::= { adTaSysCtrlShelf 6 }

     adTASysLastConfigChangeAlarmTime OBJECT-TYPE
        SYNTAX TimeTicks
        MAX-ACCESS  read-only
        STATUS  current
        DESCRIPTION
            "The last time the alarm was generated."
        ::= { adTaSysCtrlShelf 8 }

    -- ********************************************************************************
    --
    -- File Export  adTaSysCtrlFileExport - adTaSysCtrlGeneralFileExport - adTaSysCtrlSystemLog
    --

    adTASystemEventLogAutoExportMode OBJECT-TYPE
        SYNTAX INTEGER {
                            autoExportAt90PercentFull(1), -- Export when the System Log is 90 percent full
                            autoExportAtScheduledTime(2), -- Export at the specified time
                            autoExportDisabled(3)         -- Auto export is disabled.
                       }
        MAX-ACCESS  read-write
        STATUS  current
        DESCRIPTION
            "System log auto export mode.."
        ::= { adTaSysCtrlSystemLog 1 }

    adTaSystemEventLogPreventFileOverlap OBJECT-TYPE
        SYNTAX  INTEGER {
                            enabled(1),  -- enable feature to prevent file overlap
                            disabled(2)  -- disabled
                       }
        MAX-ACCESS  read-write
        STATUS  current
        DESCRIPTION
            "Prevent sending an event in the system log more than once."
        ::= { adTaSysCtrlSystemLog 3 }

    adTaSystemEventLogFilePrefix OBJECT-TYPE
        SYNTAX  DisplayString (SIZE(0..8))
        MAX-ACCESS  read-write
        STATUS  current
        DESCRIPTION
            "The prefix added to make the system log file name."
        ::= { adTaSysCtrlSystemLog 5 }

    adTaSystemEventLogFileSuffix OBJECT-TYPE
        SYNTAX  DisplayString (SIZE(0..8))
        MAX-ACCESS  read-write
        STATUS  current
        DESCRIPTION
            "The suffix added to make the system log file name."
        ::= { adTaSysCtrlSystemLog 7 }

    adTaSystemEventLogRemoteDirectory OBJECT-TYPE
        SYNTAX  DisplayString (SIZE(0..40))
        MAX-ACCESS  read-write
        STATUS  current
        DESCRIPTION
            "The remote directory on the severe where the system log file
             is exported to."
        ::= { adTaSysCtrlSystemLog 9 }

    adTaSystemEventLogRemoteFileName OBJECT-TYPE
        SYNTAX  DisplayString (SIZE(0..80))
        MAX-ACCESS  read-only
        STATUS  current
        DESCRIPTION
            "The remote file name on the severe where the system log file
             is exported to."
        ::= { adTaSysCtrlSystemLog 11 }

    adTaSystemEventLogAutoExportNumberOfDays OBJECT-TYPE
        SYNTAX  INTEGER (0..90)
        MAX-ACCESS  read-write
        STATUS  current
        DESCRIPTION
            "The number of days before the system log is exported. (Military Time/24 hour time)"
        ::= { adTaSysCtrlSystemLog 13 }

    adTaSystemEventLogHourOfDayToExportSysLog OBJECT-TYPE
        SYNTAX  INTEGER (0..23)
        MAX-ACCESS  read-write
        STATUS  current
        DESCRIPTION
            "The hour of the day to export system Log."
        ::= { adTaSysCtrlSystemLog 15 }

    adTaSystemEventLogMinuteOfDayToExportSysLog OBJECT-TYPE
        SYNTAX  INTEGER (0..59)
        MAX-ACCESS  read-write
        STATUS  current
        DESCRIPTION
            "The hour of the day to export system Log."
        ::= { adTaSysCtrlSystemLog 17 }

    adTaSystemEventLogExportRetries OBJECT-TYPE
        SYNTAX  INTEGER (0..2)
        MAX-ACCESS  read-write
        STATUS  current
        DESCRIPTION
            "The number of retries to export system event log."
        ::= { adTaSysCtrlSystemLog 19 }

    adTaSystemEventLogRemotetHost OBJECT-TYPE
        SYNTAX  DisplayString (SIZE(0..40))
        MAX-ACCESS  read-write
        STATUS  deprecated
        DESCRIPTION
            "The remote file Host.
            This OID is deprecated.  Use adTaSystemEventLogRemotetHostInetAddress
            to set IPv4 and IPv6 address."
        ::= { adTaSysCtrlSystemLog 21 }

    adTaSystemEventLogPrevExportTime OBJECT-TYPE
        SYNTAX  DisplayString (SIZE(0..255))
        MAX-ACCESS  read-only
        STATUS  current
        DESCRIPTION
            "The status of the last system log export."
        ::= { adTaSysCtrlSystemLog 23 }

    adTaSystemEventLogPrevExportStatus OBJECT-TYPE
        SYNTAX  DisplayString (SIZE(0..255))
        MAX-ACCESS  read-only
        STATUS  current
        DESCRIPTION
            "The previous export status."
        ::= { adTaSysCtrlSystemLog 25 }

    adTaSystemEventLogNextAutoExportScheduled OBJECT-TYPE
        SYNTAX  DisplayString (SIZE(0..255))
        MAX-ACCESS  read-only
        STATUS  current
        DESCRIPTION
            "The information about the next system log auto export."
        ::= { adTaSysCtrlSystemLog 27 }

    adTaSystemEventLogManualExport OBJECT-TYPE
        SYNTAX  INTEGER {
                            exportFullSystemLog(1),                -- Export full system log
                            exportUnsentEvents(2)  -- Export all events that have not been exported
                       }
        MAX-ACCESS  read-write
        STATUS  current
        DESCRIPTION
            "Manual export of system log."
        ::= { adTaSysCtrlSystemLog 29 }

    adTaSystemEventLogCurrentStatus OBJECT-TYPE
        SYNTAX  DisplayString (SIZE(0..255))
        MAX-ACCESS  read-only
        STATUS  current
        DESCRIPTION
            "The current export status."
        ::= { adTaSysCtrlSystemLog 31 }

    adTaSystemEventLogRemotetHostInetAddressType OBJECT-TYPE
        SYNTAX InetAddressType
        MAX-ACCESS  read-only
        STATUS  current
        DESCRIPTION
            "The remote file Host address type (Ipv6 or Ipv4)."
        ::= { adTaSysCtrlSystemLog 32 }

    adTaSystemEventLogRemotetHostInetAddress OBJECT-TYPE
        SYNTAX InetAddress
        MAX-ACCESS  read-write
        STATUS  current
        DESCRIPTION
            "The remote file Host address (Ipv6 or Ipv4).
             Backwards compatibility:  Setting this address to a IPv4
             address will update adTaSystemEventLogRemotetHost provision address
             with the new value.
             Setting this address to an IPV6 will leave adTaSystemEventLogRemotetHost as is."
                ::= { adTaSysCtrlSystemLog 33 }
    -- ***********************************************************
    adTaGenExportRemotetHost OBJECT-TYPE
        SYNTAX  DisplayString (SIZE(0..40))
        MAX-ACCESS  read-write
        STATUS  deprecated
        DESCRIPTION
            "The remote file name.
            This OID is deprecated.  Use adTaGenExportRemotetHostInetAddress to
            set IPv4 and IPv6 address."
        ::= { adTaSysCtrlGeneralFileExport 1 }

    adTaGeneralExportRemoteHostMethod OBJECT-TYPE
        SYNTAX INTEGER {
                                 ftmTFTP(1),
                                 ftmFTOT(2),
                                 ftmFTP(3),
                         ftmSFTP(4),
                         ftmLFFS(5)
                              }
               MAX-ACCESS  read-write
               STATUS  current
               DESCRIPTION
                  "File transfer method to use to transfer General Export files from the controller.
                   ftmTFTP(1) indicates TFTP transfer protocol.
                   ftmFTOT(2) indicates FTOT transfer protocol.
                   ftmFTP(3)  indicates FTP  transfer protocol.
                   ftmSFTP(4) indicates SFTP transfer protocol.
                   ftmLFFS(5) indicates Local Flash File System for OPTI-6100 SCM2 only."
        ::= { adTaSysCtrlGeneralFileExport 2 }

    adTaGenExportRemoteFilePath OBJECT-TYPE
        SYNTAX  DisplayString (SIZE(0..40))
        MAX-ACCESS  read-write
        STATUS  current
        DESCRIPTION
            "The remote file name on the severe where the system log file
             is exported to."
        ::= { adTaSysCtrlGeneralFileExport 3 }

    adTaGenExportStatus OBJECT-TYPE
        SYNTAX  DisplayString (SIZE(0..255))
        MAX-ACCESS  read-only
        STATUS  current
        DESCRIPTION
            "The previous export status."
        ::= { adTaSysCtrlGeneralFileExport 5 }

    adTaGenExportFileName OBJECT-TYPE
        SYNTAX  DisplayString (SIZE(0..40))
        MAX-ACCESS  read-only
        STATUS  current
        DESCRIPTION
            "The last file exported."
        ::= { adTaSysCtrlGeneralFileExport 7 }

    adTaGeneralExportRetries OBJECT-TYPE
        SYNTAX  INTEGER (0..2)
        MAX-ACCESS  read-write
        STATUS  current
        DESCRIPTION
            "The number of retries to export file."
        ::= { adTaSysCtrlGeneralFileExport 9 }

    adTaGenExportPrefixString OBJECT-TYPE
        SYNTAX  DisplayString (SIZE(0..30))
        MAX-ACCESS  read-write
        STATUS  current
        DESCRIPTION
            "A prefix to add to the General File Export file name received by the line card."
        ::= { adTaSysCtrlGeneralFileExport 11 }

    adTaGenExportSuffixString OBJECT-TYPE
        SYNTAX  DisplayString (SIZE(0..20))
        MAX-ACCESS  read-write
        STATUS  current
        DESCRIPTION
            "A suffix to add to the General File Export file name received by the line card."
        ::= { adTaSysCtrlGeneralFileExport 12 }

    adTaGenExportExceptionReportEnable OBJECT-TYPE
        SYNTAX  INTEGER { enable(1), disable(2) }
        MAX-ACCESS  read-write
        STATUS  current
        DESCRIPTION
            "Enable/Disable automatically generated exception reports. Manually generated reports are always enabled."
        ::= { adTaSysCtrlGeneralFileExport 14 }

    adTaGenExportRemotetHostInetAddressType OBJECT-TYPE
        SYNTAX InetAddressType
        MAX-ACCESS  read-only
        STATUS  current
        DESCRIPTION
            "The remote file server address InetAddress Type."

        ::= { adTaSysCtrlGeneralFileExport 15 }

    adTaGenExportRemotetHostInetAddress OBJECT-TYPE
        SYNTAX InetAddress
        MAX-ACCESS  read-write
        STATUS  current
        DESCRIPTION
            "The general export remote file Sever address.
            Backwards compatibility:  Setting this address to a IPv4
            address will update adTaGenExportRemotetHost provision address
            with the new value.
            Setting this address to an IPV6 will leave adTaGenExportRemotetHost as is."
        ::= { adTaSysCtrlGeneralFileExport 16 }
    -- ************************************************************************************

    adTaSntpServer OBJECT-TYPE
        SYNTAX  DisplayString (SIZE(0..40))
        MAX-ACCESS  read-write
        STATUS  current
        DESCRIPTION
            "The remote SNTP Server."
        ::= { adTaSysCtrlSNTP 1 }

    adTaDSTAutomaticAdjustment OBJECT-TYPE
        SYNTAX  INTEGER {
                            disabled(1), -- SNTP DST disabled
                            enabled(2),  -- SNTP DST enabled
                            pre2007Adjustment(3)    -- SNTP DST enable Pre 2007,
                       }
        MAX-ACCESS  read-write
        STATUS  current
        DESCRIPTION
            "This option sets automatic adjustment for North American daylight saving
             time. Available values are Enabled and Disabled. The default value is
             Enabled."
        ::= { adTaSysCtrlSNTP 3 }

    adTaLocalTimeZone OBJECT-TYPE
        SYNTAX  INTEGER {
                              hawaii(1),      -- SNTP TIMEZONE HAWAII
                              alaska(2),      -- SNTP TIMEZONE ALASKA,
                              pacific(3),     -- SNTP TIMEZONE PACIFIC,
                              mountain(4),    -- SNTP TIMEZONE MOUNTAIN,
                              central(5),     -- SNTP TIMEZONE CENTRAL,
                              eastern(6),     -- SNTP TIMEZONE EASTERN,
                              atlantic(7)     -- SNTP TIMEZONE ATLANTIC,
                       }
        MAX-ACCESS  read-write
        STATUS  deprecated
        DESCRIPTION
            "This option sets the time zone in which the MX2800 unit is located.
             Possible values consist of North American time zones from Hawaii-Aleutian
             Standard Time to Atlantic Standard Time. The default value is Eastern
             Standard Time."
        ::= { adTaSysCtrlSNTP 5 }

    adTaRefreshPeriod OBJECT-TYPE
        SYNTAX  INTEGER {
                            oneMinute(1),
                            fiveMinute(2),
                            tenMinute(3),
                            fifteenMinute(4),
                            twentyMinute(5),
                            twentyFiveMinute(6),
                            thirtyMinute(7),
                            thirtyFiveMinute(8),
                            fortyMinute(9),
                            fortyFiveMinute(10),
                            fiftyMinute(11),
                            fiftyFiveMinute(12),
                            sixtyMinute(13)
                       }
        MAX-ACCESS  read-write
        STATUS  current
        DESCRIPTION
            "This option sets the length of time between queries to the server.
             The available values range from 1 minute to 60 minutes at 5-minute
             increments. The default value is 5 minutes."
        ::= { adTaSysCtrlSNTP 7 }

    adTaTimeProtocolState OBJECT-TYPE
        SYNTAX  INTEGER {
                           disabled(1), -- sntp mode disabled,
                           sntp(2),     -- sntp
                           netTime(3)   -- Net Time
                        }
        MAX-ACCESS  read-write
        STATUS  current
        DESCRIPTION
            "This option sets the mode or protocol used to retrieve
             the date and time from the server. Possible values are
             Disabled, SNTP, and Net Time. When the State option is
             set to Disabled, then the user should explicitly set
             the date and time locally (via menus, TL1, or SNMP).
             If the State option is set to SNTP or Net Time, then
             the product prevents any attempt to set the time
             locally. The default value is Disabled."
        ::= { adTaSysCtrlSNTP 9 }

    adTaSntpOperationStaus OBJECT-TYPE
        SYNTAX  DisplayString (SIZE(0..80))
        MAX-ACCESS  read-only
        STATUS  current
        DESCRIPTION
            "SNTP operations status."
        ::= { adTaSysCtrlSNTP 11 }

    adTaSntpTimeOutCount OBJECT-TYPE
        SYNTAX  Integer32
        MAX-ACCESS  read-only
        STATUS  current
        DESCRIPTION
            "A running time out count of SNTP Server1. This count is reset
             to zero if the server is changed."
        ::= { adTaSysCtrlSNTP 13 }

     adTaSntpGMTtimeZoneString  OBJECT-TYPE
        SYNTAX  DisplayString
        MAX-ACCESS  read-write
        STATUS  current
        DESCRIPTION
            "This OID will set the Time Zone Offset.  This setting
             will override the adTaLocalTimeZoneGMToffset OID in the Controller.
             **
             Format: (GMT[+,-][00-23]:[00-59])Time Zone Name/Alias/Description.
             Time Zone Name 0 - 55 characters.
             **
             Example:(GMT-06:00)Central Time
             Example:(GMT-00:00) No Offset
             Example:(GMT+00:00) Greenwich Mean Time : London
             Example:(GMT+00:00) Greenwich Mean Time : London
             Example:(GMT+02:00) Amman
             Example:(GMT-04:30) Caracas
             Example:(GMT+04:45) Kathmandu
            "
        ::= { adTaSysCtrlSNTP 15 }

     adTaSntpServer2 OBJECT-TYPE
        SYNTAX  DisplayString (SIZE(0..40))
        MAX-ACCESS  read-write
        STATUS  current
        DESCRIPTION
            "The remote SNTP redundant Server 2."
        ::= { adTaSysCtrlSNTP 17 }
     adTaSntpServer3 OBJECT-TYPE
        SYNTAX  DisplayString (SIZE(0..40))
        MAX-ACCESS  read-write
        STATUS  current
        DESCRIPTION
            "The remote SNTP redundant Server 3."
        ::= { adTaSysCtrlSNTP 18 }
     adTaSntpServer4 OBJECT-TYPE
        SYNTAX  DisplayString (SIZE(0..40))
        MAX-ACCESS  read-write
        STATUS  current
        DESCRIPTION
            "The remote SNTP redundant Server 4."
        ::= { adTaSysCtrlSNTP 19 }
     adTaSntpTimeOutProv OBJECT-TYPE
        SYNTAX  Integer32 (0..5)
        MAX-ACCESS  read-write
        STATUS  current
        DESCRIPTION
            "SNTP wait time before it times out.
             The number of seconds before SNTP message time out."
        ::= { adTaSysCtrlSNTP 21 }
     adTaSntpTimeRetryProv OBJECT-TYPE
        SYNTAX  Integer32 (0..3)
        MAX-ACCESS  read-write
        STATUS  current
        DESCRIPTION
            "SNTP retry.  The number of times to retry a SNTP request each server.
             to a SNTP server."
        ::= { adTaSysCtrlSNTP 23 }

     adTaSntpTimeOutCountServer2 OBJECT-TYPE
        SYNTAX  Integer32
        MAX-ACCESS  read-only
        STATUS  current
        DESCRIPTION
            "A running time out count of SNTP Server2.  This count is reset
             to zero if the server is changed."
        ::= { adTaSysCtrlSNTP 25 }

     adTaSntpTimeOutCountServer3 OBJECT-TYPE
        SYNTAX  Integer32
        MAX-ACCESS  read-only
        STATUS  current
        DESCRIPTION
            "A running time out count of SNTP Server3.  This count is reset
             to zero if the server is changed."
        ::= { adTaSysCtrlSNTP 26 }
     adTaSntpTimeOutCountServer4 OBJECT-TYPE
        SYNTAX  Integer32
        MAX-ACCESS  read-only
        STATUS  current
        DESCRIPTION
            "A running time out count of SNTP Server4. This count is reset
             to zero if the server is changed."
        ::= { adTaSysCtrlSNTP 27 }

     adTaSntpCurrentServer OBJECT-TYPE
        SYNTAX  Integer32
        MAX-ACCESS  read-only
        STATUS  current
        DESCRIPTION
            "The current server being used. Server 1 to 4."
        ::= { adTaSysCtrlSNTP 29 }
    -- ********************************************************************************
    --
    -- syslog Protocol
    -- In its most simplistic terms, the syslog protocol provides a
    -- transport to allow a machine to send event notification messages
    -- across IP networks to event message collectors - also known as syslog
    -- servers.
    --

    adTaSysLogServer OBJECT-TYPE
        SYNTAX  DisplayString (SIZE(0..40))
        MAX-ACCESS  read-write
        STATUS  deprecated
        DESCRIPTION
            "The remote SysLog Server.
            This OID is deprecated for support of IPv6.  Use adTaSysLogServerNetAddress."
        ::= { adTaSysLog 1 }

     adTaSysLogServer2 OBJECT-TYPE
        SYNTAX  DisplayString (SIZE(0..40))
        MAX-ACCESS  read-write
        STATUS  deprecated
        DESCRIPTION
            "The second remote SysLog Server."
        ::= { adTaSysLog 2 }

    adTaSysLogMode OBJECT-TYPE
        SYNTAX  INTEGER {
                           enableSysLog(1), -- syslog mode enabled
                           disableSysLog(2) -- syslog mode disabled
                        }
        MAX-ACCESS  read-write
        STATUS  current
        DESCRIPTION
            "Enable or Disable SysLog feature."
        ::= { adTaSysLog 3}

    -- Send system event log events on the controller to RFC 3164 syslog clients
    adTaExportCtrlToSysLog OBJECT-TYPE
        SYNTAX  INTEGER {
                           exportSystemEventToSyslogServer(1)  -- send System Event Log Entries to SysLog
                        }
        MAX-ACCESS  read-write
        STATUS  current
        DESCRIPTION
            "Send the system event log entries to syslog client (RFC 3164 syslog clients)."
        ::= { adTaSysLog 4}


     adTaSysLogServer3 OBJECT-TYPE
        SYNTAX  DisplayString (SIZE(0..40))
        MAX-ACCESS  read-write
        STATUS  deprecated
        DESCRIPTION
            "The third remote SysLog Server 3."
        ::= { adTaSysLog 6 }

     adTaSysLogServer4 OBJECT-TYPE
        SYNTAX  DisplayString (SIZE(0..40))
        MAX-ACCESS  read-write
        STATUS  deprecated
        DESCRIPTION
            "The fourth remote SysLog Server."
        ::= { adTaSysLog 7 }

     --
     -- the adTaSysLogServer Translation table
     --

        adTaSysLogServerTable OBJECT-TYPE
               SYNTAX     SEQUENCE OF AdTaSysLogServerEntry
               MAX-ACCESS not-accessible
               STATUS     current
               DESCRIPTION
                      "Remote SysLog Server Table"
               ::= { adTaSysLog 10  }

        adTaSysLogServerEntry OBJECT-TYPE
               SYNTAX     AdTaSysLogServerEntry
               MAX-ACCESS not-accessible
               STATUS     current
               DESCRIPTION
                      "Each entry contains one Remote SysLog Server."
               INDEX       { adTaSysLogServerIndex}
               ::= { adTaSysLogServerTable 1 }

           AdTaSysLogServerEntry ::= SEQUENCE {
                   adTaSysLogServerIndex           Integer32,
                   adTaSysLogServerAddressType     InetAddressType,
                   adTaSysLogServerInetAddress      InetAddress
               }
    adTaSysLogServerIndex OBJECT-TYPE
       SYNTAX     Integer32
       MAX-ACCESS not-accessible
       STATUS     current
       DESCRIPTION
              "The index value that uniquely identifies Remote SysLog Server 1 to 4"
       ::= { adTaSysLogServerEntry 1 }

    adTaSysLogServerAddressType OBJECT-TYPE
        SYNTAX     InetAddressType
        MAX-ACCESS read-only
        STATUS     current
        DESCRIPTION
               "The type of adTaSysLogServerInetAddress."
        ::= { adTaSysLogServerEntry 2 }

    adTaSysLogServerInetAddress OBJECT-TYPE
        SYNTAX     InetAddress
        MAX-ACCESS read-write
        STATUS     current
        DESCRIPTION
               "Remote SysLog Server address."
        ::= { adTaSysLogServerEntry 3 }

    -- ***********************************************************************************
    --
    -- TA System Controller DHCP Server Configuration
    --
    --

    adTaDhcpNetworkInterface OBJECT-TYPE
        SYNTAX  DisplayString (SIZE(0..40))
        MAX-ACCESS  read-write
        STATUS  current
        DESCRIPTION
            "The ifIndex of the Controller Ethernet interface that the DHCP server runs on."
        ::= { adTaDhcpServer 10}

    adTaDhcpSubNetMask OBJECT-TYPE
        SYNTAX  IpAddress
        MAX-ACCESS  read-only
        STATUS  current
        DESCRIPTION
            "The Netmask of the DHCP interface address.
             A subnet mask defines how many bits of an IP address to use for the
             network/subnet ID and how many bits to use for the Host ID."
        ::= { adTaDhcpServer 12}

    adTaDhcpSubNetLength OBJECT-TYPE
        SYNTAX  INTEGER (24..32)
        MAX-ACCESS  read-only
        STATUS  current
        DESCRIPTION
            "The subnet mask by length.  See adTaDhcpSubNetMask."
        ::= { adTaDhcpServer 14}

    adTaDhcpStartIpAddress OBJECT-TYPE
        SYNTAX  IpAddress
        MAX-ACCESS  read-write
        STATUS  current
        DESCRIPTION
            "Send the system event log entries to syslog client (RFC 3164 syslog clients)."
        ::= { adTaDhcpServer 16}

    adTaDhcpEndIpAddress OBJECT-TYPE
        SYNTAX  IpAddress
        MAX-ACCESS  read-write
        STATUS  current
        DESCRIPTION
            "Send the system event log entries to syslog client (RFC 3164 syslog clients)."
        ::= { adTaDhcpServer 18}

    adTaDhcpSubNetAddress OBJECT-TYPE
        SYNTAX  IpAddress
        MAX-ACCESS  read-only
        STATUS  current
        DESCRIPTION
            "A subnet IP Address."
        ::= { adTaDhcpServer 20}

    adTaDhcpLeasDurationHours OBJECT-TYPE
        SYNTAX  INTEGER (0..24)
        MAX-ACCESS  read-write
        STATUS  current
        DESCRIPTION
            "DHCP lease duration hours.  If hours and minutes are set to zero
             the DHCP lease duration will be set to one hour.  The minimum
             lease duration will be 300 seconds."
        ::= { adTaDhcpServer 22}

    adTaDhcpLeasDurationMintues OBJECT-TYPE
        SYNTAX  INTEGER (0..59)
        MAX-ACCESS  read-write
        STATUS  current
        DESCRIPTION
            "DHCP lease duration minutes.  If hours and minutes are set to zero
             the DHCP lease duration will be set to one hour.   The minimum
             lease duration will be 300 seconds."
        ::= { adTaDhcpServer 24}

    adTaDhcpServerCommands OBJECT-TYPE
        SYNTAX  INTEGER
               {
                  startDhcpServer(1),
                  stopDhcpServer(2),
                  dhcpNoCommand(999)
               }
        MAX-ACCESS  read-write
        STATUS  current
        DESCRIPTION
            "DHCP Server command.
            startDhcpServer - restart DHCP server.
                              Only if the server was stoped.
            stopDhcpServer  - Stop the DhcpServer if it is running.
            dhcpNoCommand   - no Command was performed performed."
        ::= { adTaDhcpServer 26}

    adTaDhcpServerOperationStatus OBJECT-TYPE
        SYNTAX  DisplayString (SIZE(0..80))
        MAX-ACCESS  read-only
        STATUS  current
        DESCRIPTION
            "The DHCP server status."
        ::= { adTaDhcpServer 28}


    -- DHCP status Table
    adTaDhcpServerStatusTable OBJECT-TYPE
       SYNTAX    SEQUENCE OF AdTaDhcpServerStatusTableEntry
       MAX-ACCESS    not-accessible
       STATUS    current
       DESCRIPTION
              ""
      ::= { adTaDhcpServer 40 }


   adTaDhcpServerStatusTableEntry OBJECT-TYPE
     SYNTAX      AdTaDhcpServerStatusTableEntry
     MAX-ACCESS      not-accessible
     STATUS      current
     DESCRIPTION
             ""
     INDEX      { adTaSysCtrlSrmReleaseIndex,
                  adTaSysCtrlSrmRlsFilesIndex }
       ::= { adTaDhcpServerStatusTable 1 }

   AdTaDhcpServerStatusTableEntry ::=
        SEQUENCE {
            adTaDhcpServerStatusIndex
                Integer32,
            adTaDhcpServerStatus
                DisplayString
        }
    adTaDhcpServerStatusIndex OBJECT-TYPE
        SYNTAX  Integer32
        MAX-ACCESS  read-only
        STATUS  current
        DESCRIPTION
            "Index for a DHCP Server Status."
        ::= { adTaDhcpServerStatusTableEntry 1 }
    adTaDhcpServerStatus OBJECT-TYPE
        SYNTAX  DisplayString (SIZE(0..200))
        MAX-ACCESS  read-only
        STATUS  current
        DESCRIPTION
            "Dhcp Server Status."
        ::= { adTaDhcpServerStatusTableEntry 4}

    -- ***********************************************************************************
    adTaSSLKeySizeBits OBJECT-TYPE
     SYNTAX  INTEGER
            {
               bits512(512),
               bits1024(1024),
               bits2048(2048)
            }
            MAX-ACCESS  read-write
        STATUS  current
        DESCRIPTION
            "This specifies the key size in bits. If not specified then
             1024 is used."
        ::= { adTaSSLConfiguration 5}



    adTaSSLKeyType OBJECT-TYPE
     SYNTAX  INTEGER
            {
               rsa(1),
               dsa(2)
            }
            MAX-ACCESS  read-write
        STATUS  current
        DESCRIPTION
            "SSL key type to generate and use."
        ::= { adTaSSLConfiguration 7}


    adTaSSLInputPassword OBJECT-TYPE
        SYNTAX  DisplayString (SIZE(4..20))
        MAX-ACCESS  read-write
        STATUS  current
        DESCRIPTION
            "The passwords for the input private key file."
        ::= { adTaSSLConfiguration 9}


    adTaSSLOutputPassword OBJECT-TYPE
        SYNTAX  DisplayString (SIZE(4..20))
        MAX-ACCESS  read-write
        STATUS  current
        DESCRIPTION
            "The passwords for the output private key file."
        ::= { adTaSSLConfiguration 11}

    adTaSSLCertificateCountry OBJECT-TYPE
        SYNTAX  DisplayString (SIZE(2..2))
        MAX-ACCESS  read-write
        STATUS  current
        DESCRIPTION
            "SSL certificate country."
        ::= { adTaSSLConfiguration 13}

    adTaSSLCertificateStateOrProvince OBJECT-TYPE
        SYNTAX  DisplayString (SIZE(2..64))
        MAX-ACCESS  read-write
        STATUS  current
        DESCRIPTION
            "SSL certificate State or Province."
        ::= { adTaSSLConfiguration 15}

    adTaSSLCertificateChallengePassword OBJECT-TYPE
        SYNTAX  DisplayString (SIZE(4..20))
        MAX-ACCESS  read-write
        STATUS  current
        DESCRIPTION
            "SSL challenge password."
        ::= { adTaSSLConfiguration 17}

    adTaSSLCertificateLocality OBJECT-TYPE
        SYNTAX  DisplayString (SIZE(0..64))
        MAX-ACCESS  read-write
        STATUS  current
        DESCRIPTION
            "SSL certificate Locality (eg, city)."
        ::= { adTaSSLConfiguration 19}

    adTaSSLCertificateOrganization OBJECT-TYPE
        SYNTAX  DisplayString (SIZE(0..64))
        MAX-ACCESS  read-write
        STATUS  current
        DESCRIPTION
            "SSL certificate Organization."
        ::= { adTaSSLConfiguration 21}

    adTaSSLCertificateOrganizationalUnitName OBJECT-TYPE
        SYNTAX  DisplayString (SIZE(0..64))
        MAX-ACCESS  read-write
        STATUS  current
        DESCRIPTION
            "SSL certificate Organization Unit Name."
        ::= { adTaSSLConfiguration 23}

    adTaSSLCertificateCommonName OBJECT-TYPE
        SYNTAX  DisplayString (SIZE(0..64))
        MAX-ACCESS  read-write
        STATUS  current
        DESCRIPTION
            "SSL Common Name (e.g., fully qualified domain name of
             the server to be secured)'' since, the common name
             generally corresponds to the server's name when
             generating certificates."
        ::= { adTaSSLConfiguration 25}

    adTaSSLCertificateEmailAddress OBJECT-TYPE
        SYNTAX  DisplayString (SIZE(0..40))
        MAX-ACCESS  read-write
        STATUS  current
        DESCRIPTION
            "SSL Email address of the SSL certificate distinguished
             name"
        ::= { adTaSSLConfiguration 27}

    adTaGenerateNewSSLKeys OBJECT-TYPE
        SYNTAX  INTEGER
            {
               generateNewSSLKeys(1)
            }
        MAX-ACCESS  read-write
        STATUS  current
        DESCRIPTION
            "Reset the controller and genrerate new SSL keys using
             the current settings."
        ::= { adTaSSLConfiguration 29}

    adTaGenerateNewSSLCertificateRequest OBJECT-TYPE
        SYNTAX  INTEGER
            {
                generateNewSSLCertRequest(1)
            }
        MAX-ACCESS  read-write
        STATUS  current
        DESCRIPTION
            "Initiate generation of a new SSL Certificate Request."
        ::= { adTaSSLConfiguration 30}

    adTaSSLuseImportCertificate OBJECT-TYPE
        SYNTAX  INTEGER
            {
                enable(1),
                disable(2)
            }
        MAX-ACCESS  read-write
        STATUS  current
        DESCRIPTION
            "When set to disable, the controller will use the self-signed certificate. When set to
             enable, the controller will use the imported signed certificate (if available).
             Changing this setting will intiate a controller reboot."
        ::= { adTaSSLConfiguration 31}

     -- ***********************************************
     adTaSSLRemotePrivateKeyFileName OBJECT-TYPE
        SYNTAX  DisplayString (SIZE(0..64))
        MAX-ACCESS  read-write
        STATUS  current
        DESCRIPTION
            "SSL Remote Private key file name to download. This file
             will replace the controller generated SSL Private Key File."
        ::= { adTaSSLRemoteKeyDownload 3}
     adTaSSLRemotedPublicKeyFileName OBJECT-TYPE
        SYNTAX  DisplayString (SIZE(0..64))
        MAX-ACCESS  read-write
        STATUS  current
        DESCRIPTION
            "SSL Remote Private key file name to download. This file
             will replace the controller generated SSL Public Key File."
        ::= { adTaSSLRemoteKeyDownload 5}
     adTaSSLRemoteCertificateFileName OBJECT-TYPE
        SYNTAX  DisplayString (SIZE(0..64))
        MAX-ACCESS  read-write
        STATUS  current
        DESCRIPTION
            "SSL Remote Private key file name to download. This file
             will replace the controller generated SSL self signed
             Certificate Key File."
        ::= { adTaSSLRemoteKeyDownload 7}

     adTaSSLRemoteKeysDownLoadStatus OBJECT-TYPE
        SYNTAX  DisplayString
        MAX-ACCESS  read-write
        STATUS  current
        DESCRIPTION
            "SSL Remote keys download status."
        ::= { adTaSSLRemoteKeyDownload 8}

     adTaSSLCertificateRequestFileName OBJECT-TYPE
        SYNTAX  DisplayString (SIZE(0..64))
        MAX-ACCESS  read-write
        STATUS  current
        DESCRIPTION
            "File name to use while exporting a certificate request."
        ::= { adTaSSLRemoteKeyDownload 9}

     adTaSSLCertificateRequestExport OBJECT-TYPE
        SYNTAX  INTEGER
            {
                exportSSLCertificateRequest(1)
            }
        MAX-ACCESS  read-write
        STATUS  current
        DESCRIPTION
            "Used to initiate an certificate request export."
        ::= { adTaSSLRemoteKeyDownload 10}


     adTaSSLCertificateImport OBJECT-TYPE
        SYNTAX  INTEGER
            {
               importSSLCertificate(1)
            }
        MAX-ACCESS  read-write
        STATUS  current
        DESCRIPTION
            "Initiate the import operation for the signed certificate.
             The file indicated by adTaSSLRemoteCertificateFileName
             will be transferred to the controller using the selected
             designated file server, protocol, and credentials specified
             in the controller provisioning."
        ::= { adTaSSLRemoteKeyDownload 11}

     adTaSSLCertificateImportStatus OBJECT-TYPE
        SYNTAX  INTEGER
            {
                ready(1),
                notReady(2)
            }
        MAX-ACCESS  read-only
        STATUS  current
        DESCRIPTION
            "SSL Certificate Import status. This status indicates whether or not a
             certificate was imported successfully and is ready to be used, if desired."
        ::= { adTaSSLRemoteKeyDownload 12}

     adTaSSLDownLoadRemoteKeys OBJECT-TYPE
     SYNTAX  INTEGER
            {
               downloadRemoteSSLKeys(1)
            }
            MAX-ACCESS  read-write
        STATUS  current
        DESCRIPTION
            "SSL key type to generate and use."
        ::= { adTaSSLRemoteKeyDownload 13}

     adTaSSLCertificateSigningRequestStatus OBJECT-TYPE
        SYNTAX  INTEGER
            {
                ready(1),
                notReady(2)
            }
        MAX-ACCESS  read-only
        STATUS  current
        DESCRIPTION
            "SSL Certificate Signing Request Status. This status Indicates
             whether a certificate signing request is ready and available
             for export."
        ::= { adTaSSLRemoteKeyDownload 14}

     adTaSSLCertificateSignRequestExportStatus OBJECT-TYPE
        SYNTAX  DisplayString (SIZE(0..255))
        MAX-ACCESS  read-only
        STATUS  current
        DESCRIPTION
            "This OID will return a formatted string describing the most recent
             SSL Certificate Signing Request Remote File Export operation
             status."
        ::= { adTaSSLRemoteKeyDownload 15}

     adTaSSLSignedCertificateImportStatus OBJECT-TYPE
        SYNTAX  DisplayString (SIZE(0..255))
        MAX-ACCESS  read-only
        STATUS  current
        DESCRIPTION
            "This OID will return a formatted string describing the most recent
             SSL Signed Certificate Remote File Import operation status."
        ::= { adTaSSLRemoteKeyDownload 16}

    --
    -- Inband management VLAN bridging
    --
    adTaSysCtrlVLANBridgeMode OBJECT-TYPE
        SYNTAX  INTEGER { enable(1), disable(2) }
        MAX-ACCESS  read-write
        STATUS      current
        DESCRIPTION
          "Enable VLAN bridging mode."
        ::= { adTaSysCtrlVLANBridge 1 }

    adTaSysCtrlVLANBridgeInterface OBJECT-TYPE
        SYNTAX  INTEGER { enet(1), enet2(2) }
        MAX-ACCESS  read-write
        STATUS      current
        DESCRIPTION
          "Select the interface to perform bridging."
        ::= { adTaSysCtrlVLANBridge 2 }



    -- ***********************************************************************************
    --
    -- TA System Module Reset Control
    --
    --    Operating Instructions:
    --
    -- 0. We recommended that you first confirm all modules have been fully
    --    discovered and are stable by querying the standard GenSlot oids
    --    for every module in the system.
    --
    -- 1. Confirm the ModuleReset subsystem is in an idle/error state by
    --    reading the 'adTaModuleResetCtrl' oid.
    --
    -- 2. Write the 'RESERVE' (549) command to 'adTaModuleResetCtrl' oid.
    --
    -- 3. Confirm 'RESERVED' (1) state by reading 'adTaModuleResetCtrl' oid.
    --
    -- 4. Write the SNMP slot number to be reset to 'adTaModuleResetSlot'.
    --       Note: 0 = reset all modules EXCEPT the controller.
    --            -1 = reset all modules AND the controller.
    --
    -- 5. Confirm the 'ARMED' (3) state by reading 'adTaModuleResetCtrl' oid
    --       Note: may return 'BUSY' (2) for several seconds while we scan
    --             modules to determine capability/state.
    --       Note: operation may abort with 'NOT_SUPPORTED' (101) if we are
    --             told to reset a single module that does not support the
    --             RESET-DID or if any slot reports a BUSY state.
    --       Note: An error status will be returned if an invalid slot number
    --             is supplied or any other error condition is detected.
    --
    -- 6. Do not proceed to the next step until a read of
    --     'adTaModuleResetCtrl' returns the 'ARMED' (3) state.
    --
    -- 7. Write 'COMMIT' (666) command to 'adTaModuleResetCtrl' oid.
    --
    -- 8. Confirm 'RESETTING' (4) state by reading 'adTaModuleResetCtrl' oid.
    --
    -- Note: any deviation from this sequence may abort the entire operation and
    --       return an 'ABORTED' (102) status to a 'adTaModuleResetCtrl' query.
    --
    -- Note: The I/O values for adTaModuleResetCtrl may be thought of an an enumerated
    --       set.  Since zero (0) is used, its not technically a valid SNMP V1 enum,
    --       (it IS a valid SNMP V2 enum) so the values are represented as plain integers.
    --
    --       {
    --          adTaModuleResetIdle(0),
    --          adTaModuleResetReserved(1),
    --          adTaModuleResetBusy(2),
    --          adTaModuleResetArmed(3),
    --          adTaModuleResetResetting(4),
    --
    --          adTaModuleResetErrors(100),
    --          adTaModuleResetNotSupported(101),
    --          adTaModuleResetAborted(102),
    --
    --          adTaModuleResetCommands(500),
    --          adTaModuleResetReserve(549),
    --          adTaModuleResetCommit(666)
    --       }
    --
    -- ***********************************************************************************

    adTaModuleResetSlot OBJECT-TYPE
        SYNTAX  Integer32
        MAX-ACCESS  read-write
        STATUS  current
        DESCRIPTION
            "SNMP slot number of module to be reset, else 0 (zero) if all modules should
             be reset except the controller, -1 if all modules should be reset including
             controller.  This OID must be used in conjunction with the adTaModuleResetCtrl
             OID, refer to the above description for details."
        ::= { adTaModuleReset 10}

    adTaModuleResetCtrl OBJECT-TYPE
        SYNTAX  Integer32
        MAX-ACCESS  read-write
        STATUS  current
        DESCRIPTION
            "This OID must be used in conjunction with the adTaModuleResetSlot
             OID, refer to the above description for details."
        ::= { adTaModuleReset 12}

    -- ***********************************************************************************
    --
    -- TA System Traps Varbinds
    --
        adTaDataLossDescription OBJECT-TYPE
           SYNTAX  DisplayString (SIZE(0..80))
           MAX-ACCESS  accessible-for-notify
           STATUS  current
           DESCRIPTION
               "Description of SCM data loss or coruption."
           ::= { adTaSysAlarmVarbinds 3}
    -- ***********************************************************************************
    --
    -- TA System Controller Traps
    --

      adTaControllerMgmtTraps       OBJECT IDENTIFIER ::= { adTaControllerMgmt 0 }

    --
    -- service state msg fail alarms
    --

      adTASetSingleServiceStateMsgFail   NOTIFICATION-TYPE
                OBJECTS       {
                        adTrapInformSeqNum,
                        sysName,
                        adGenSlotInfoIndex,
                        adGenPortTrapIdentifier,
                        adGenSlotProdName
                        }
                STATUS          current
                DESCRIPTION
                        "Set single service state msg fail."
        --#TYPE      "Warning - set single service state msg fail"
        --#SUMMARY   "adTaControllerMgmtTraps 1006301: set single service state msg failed at slot %d.;"
        --#SUMMARY   "detected at chassis: %s"
        --#ARGUMENTS { 2,1}
        --#SEVERITY  WARNING
        --#GENERIC   6
        --#CATEGORY  "Set Single Service State Msg Failure"
        --#SOURCE_ID "A"
        --#TIMEINDEX 0
        ::= {adTaControllerMgmtTraps 1006301}

      adTAGetSingleServiceStateMsgFail   NOTIFICATION-TYPE
                OBJECTS       {
                        adTrapInformSeqNum,
                        sysName,
                        adGenSlotInfoIndex,
                        adGenPortTrapIdentifier,
                        adGenSlotProdName
                        }
                STATUS          current
                DESCRIPTION
                        "Get single service state msg fail."
        --#TYPE      "Warning - get single service state msg fail"
        --#SUMMARY   "adTaControllerMgmtTraps 1006303: get single service state msg failed at slot %d.;"
        --#SUMMARY   "detected at chassis: %s"
        --#ARGUMENTS { 2,1}
        --#SEVERITY  WARNING
        --#GENERIC   6
        --#CATEGORY  "Get Single Service State Msg Failure"
        --#SOURCE_ID "A"
        --#TIMEINDEX 0
        ::= {adTaControllerMgmtTraps 1006303}

      adTASetAllServiceStateMsgFail   NOTIFICATION-TYPE
                OBJECTS       {
                        adTrapInformSeqNum,
                        sysName,
                        adGenSlotInfoIndex,
                        adGenPortTrapIdentifier,
                        adGenSlotProdName
                        }
                STATUS          current
                DESCRIPTION
                        "Set all service state msg fail."
        --#TYPE      "Warning - set all service state msg fail"
        --#SUMMARY   "adTaControllerMgmtTraps 1006305: set all service state msg failed at slot %d.;"
        --#SUMMARY   "detected at chassis: %s"
        --#ARGUMENTS { 2,1}
        --#SEVERITY  WARNING
        --#GENERIC   6
        --#CATEGORY  "Set all Service State Msg Failure"
        --#SOURCE_ID "A"
        --#TIMEINDEX 0
        ::= {adTaControllerMgmtTraps 1006305}

      adTAGetAllServiceStateMsgFail   NOTIFICATION-TYPE
                OBJECTS       {
                        adTrapInformSeqNum,
                        sysName,
                        adGenSlotInfoIndex,
                        adGenPortTrapIdentifier,
                        adGenSlotProdName
                        }
                STATUS          current
                DESCRIPTION
                        "Get all service state msg fail."
        --#TYPE      "Warning - get all service state msg fail"
        --#SUMMARY   "adTaControllerMgmtTraps 1006307: get all service state msg failed at slot %d."
        --#SUMMARY   "detected at chassis: %s"
        --#ARGUMENTS { 2,1}
        --#SEVERITY  WARNING
        --#GENERIC   6
        --#CATEGORY  "Get all Service State Msg Failure"
        --#SOURCE_ID "A"
        --#TIMEINDEX 0
        ::= {adTaControllerMgmtTraps 1006307}

    --
    -- relay test alarms
    --

      adTACriticalAudibleRelayTestClear   NOTIFICATION-TYPE
                OBJECTS       {
                        adTrapInformSeqNum,
                        sysName
                }
                STATUS          current
                DESCRIPTION
                        "Alarm Relay Test. Toggle Critical Audible Relay clear alarm."
        --#TYPE      "Warning - Alarm Relay Test. Toggle Critical Audible Relay Clear"
        --#SUMMARY   "adTaControllerMgmtTraps 1006308: Menu Toggle Critical Audible Relay Clear alarm."
        --#SUMMARY   "detected at chassis: %s"
        --#ARGUMENTS {1}
        --#SEVERITY  CRITICAL
        --#GENERIC   6
        --#CATEGORY  "Alarm Relay Test"
        --#SOURCE_ID "A"
        --#TIMEINDEX 0
        ::= {adTaControllerMgmtTraps 1006308}

      adTACriticalAudibleRelayTestActive   NOTIFICATION-TYPE
                OBJECTS       {
                        adTrapInformSeqNum,
                        sysName
                }
                STATUS          current
                DESCRIPTION
                        "Alarm Relay Test. Toggle Critical Audible Relay active alarm."
        --#TYPE      "Warning - Alarm Relay Test. Toggle Critical Audible Relay active alarm"
        --#SUMMARY   "adTaControllerMgmtTraps 1006309: Menu Toggle Critical Audible Relay active alarm."
        --#SUMMARY   "detected at chassis: %s"
        --#ARGUMENTS {1}
        --#SEVERITY  CRITICAL
        --#GENERIC   6
        --#CATEGORY  "Alarm Relay Test"
        --#SOURCE_ID "A"
        --#TIMEINDEX 0
        ::= {adTaControllerMgmtTraps 1006309}

      adTACriticalVisualRelayTestClear   NOTIFICATION-TYPE
                OBJECTS       {
                        adTrapInformSeqNum,
                        sysName
                }
                STATUS          current
                DESCRIPTION
                        "Alarm Relay Test. Toggle Critical Visual Relay clear alarm."
        --#TYPE      "Warning - Alarm Relay Test. Toggle Critical Visual Relay clear alarm"
        --#SUMMARY   "adTaControllerMgmtTraps 1006310: Menu Toggle Critical Visual Relay clear alarm."
        --#SUMMARY   "detected at chassis: %s"
        --#ARGUMENTS {1}
        --#SEVERITY  CRITICAL
        --#GENERIC   6
        --#CATEGORY  "Alarm Relay Test"
        --#SOURCE_ID "A"
        --#TIMEINDEX 0
        ::= {adTaControllerMgmtTraps 1006310}

      adTACriticalVisualRelayTestActive   NOTIFICATION-TYPE
                OBJECTS       {
                        adTrapInformSeqNum,
                        sysName
                }
                STATUS          current
                DESCRIPTION
                        "Alarm Relay Test. Toggle Critical Visual Relay active alarm."
        --#TYPE      "Warning - Alarm Relay Test. Toggle Critical Visual Relay active alarm."
        --#SUMMARY   "adTaControllerMgmtTraps 1006311: Menu Alarm Relay Test. Toggle Critical Visual Relay active alarm."
        --#SUMMARY   "detected at chassis: %s"
        --#ARGUMENTS {1}
        --#SEVERITY  CRITICAL
        --#GENERIC   6
        --#CATEGORY  "Alarm Relay Test"
        --#SOURCE_ID "A"
        --#TIMEINDEX 0
        ::= { adTaControllerMgmtTraps 1006311 }

      adTAMajAudibleRelayTestClear   NOTIFICATION-TYPE
                OBJECTS       {
                        adTrapInformSeqNum,
                        sysName
                }
                STATUS          current
                DESCRIPTION
                        "Alarm Relay Test. Toggle Major Audible Relay alarm clear."
        --#TYPE      "Warning - Alarm Relay Test. Toggle Major Audible Relay alarm clear."
        --#SUMMARY   "adTaControllerMgmtTraps 1006312: Menu Alarm Relay Test. Toggle Major Audible Relay alarm clear."
        --#SUMMARY   "detected at chassis: %s"
        --#ARGUMENTS {1}
        --#SEVERITY  MAJOR
        --#GENERIC   6
        --#CATEGORY  "Alarm Relay Test"
        --#SOURCE_ID "A"
        --#TIMEINDEX 0
        ::= {adTaControllerMgmtTraps 1006312}

      adTAMajAudibleRelayTestActive   NOTIFICATION-TYPE
                OBJECTS       {
                        adTrapInformSeqNum,
                        sysName
                }
                STATUS          current
                DESCRIPTION
                        "Alarm Relay Test. Toggle Major Audible Relay alarm active."
        --#TYPE      "Warning - Alarm Relay Test. Toggle Major Audible Relay alarm active."
        --#SUMMARY   "adTaControllerMgmtTraps 1006313: Menu Alarm Relay Test. Toggle Major Audible Relay alarm active."
        --#SUMMARY   "detected at chassis: %s"
        --#ARGUMENTS {1}
        --#SEVERITY  MAJOR
        --#GENERIC   6
        --#CATEGORY  "Alarm Relay Test"
        --#SOURCE_ID "A"
        --#TIMEINDEX 0
        ::= {adTaControllerMgmtTraps 1006313}

      adTAMajVisualRelayTestClear   NOTIFICATION-TYPE
                OBJECTS       {
                        adTrapInformSeqNum,
                        sysName
                }
                STATUS          current
                DESCRIPTION
                        "Alarm Relay Test. Toggle Major Visual Relay alarm clear."
        --#TYPE      "Warning - Alarm Relay Test. Toggle Major Visual Relay alarm clear."
        --#SUMMARY   "adTaControllerMgmtTraps 1006314: Menu Alarm Relay Test. Toggle Major Visual Relay alarm clear."
        --#SUMMARY   "detected at chassis: %s"
        --#ARGUMENTS {1}
        --#SEVERITY  MAJOR
        --#GENERIC   6
        --#CATEGORY  "Alarm Relay Test"
        --#SOURCE_ID "A"
        --#TIMEINDEX 0
        ::= {adTaControllerMgmtTraps 1006314}

      adTAMajVisualRelayTestActive   NOTIFICATION-TYPE
                OBJECTS       {
                        adTrapInformSeqNum,
                        sysName
                }
                STATUS          current
                DESCRIPTION
                        "Alarm Relay Test. Toggle Major Visual Relay alarm active."
        --#TYPE      "Warning - Alarm Relay Test. Toggle Major Visual Relay alarm active."
        --#SUMMARY   "adTaControllerMgmtTraps 1006315: Menu Alarm Relay Test. Toggle Major Visual Relay alarm active."
        --#SUMMARY   "detected at chassis: %s"
        --#ARGUMENTS {1}
        --#SEVERITY  MAJOR
        --#GENERIC   6
        --#CATEGORY  "Alarm Relay Test"
        --#SOURCE_ID "A"
        --#TIMEINDEX 0
        ::= {adTaControllerMgmtTraps 1006315}

      adTAMinorAudibleRelayTestClear   NOTIFICATION-TYPE
                OBJECTS       {
                        adTrapInformSeqNum,
                        sysName
                }
                STATUS          current
                DESCRIPTION
                        "Alarm Relay Test. Toggle Minor Audible Relay alarm clear."
        --#TYPE      "Warning - Alarm Relay Test. Toggle Minor Audible Relay alarm clear."
        --#SUMMARY   "adTaControllerMgmtTraps 1006316: Menu Alarm Relay Test. Toggle Minor Audible Relay alarm clear."
        --#SUMMARY   "detected at chassis: %s"
        --#ARGUMENTS {1}
        --#SEVERITY  MINOR
        --#GENERIC   6
        --#CATEGORY  "Alarm Relay Test"
        --#SOURCE_ID "A"
        --#TIMEINDEX 0
        ::= {adTaControllerMgmtTraps 1006316}

      adTAMinorAudibleRelayTestActive   NOTIFICATION-TYPE
                OBJECTS       {
                        adTrapInformSeqNum,
                        sysName
                }
                STATUS          current
                DESCRIPTION
                        "Alarm Relay Test. Toggle Minor Audible Relay alarm active."
        --#TYPE      "Warning - Alarm Relay Test. Toggle Minor Audible Relay alarm active."
        --#SUMMARY   "adTaControllerMgmtTraps 1006317: Menu Alarm Relay Test. Toggle Minor Audible Relay alarm active."
        --#SUMMARY   "detected at chassis: %s"
        --#ARGUMENTS {1}
        --#SEVERITY  MINOR
        --#GENERIC   6
        --#CATEGORY  "Alarm Relay Test"
        --#SOURCE_ID "A"
        --#TIMEINDEX 0
        ::= {adTaControllerMgmtTraps 1006317}

      adTAMinorVisualRelayTestClear   NOTIFICATION-TYPE
                OBJECTS       {
                        adTrapInformSeqNum,
                        sysName
                }
                STATUS          current
                DESCRIPTION
                        "Alarm Relay Test. Toggle Minor Visual Relay alarm clear."
        --#TYPE      "Warning - Alarm Relay Test. Toggle Minor Visual Relay alarm clear."
        --#SUMMARY   "adTaControllerMgmtTraps 1006318: Menu Alarm Relay Test. Toggle Minor Visual Relay alarm clear."
        --#SUMMARY   "detected at chassis: %s"
        --#ARGUMENTS {1}
        --#SEVERITY  MINOR
        --#GENERIC   6
        --#CATEGORY  "Alarm Relay Test"
        --#SOURCE_ID "A"
        --#TIMEINDEX 0
        ::= {adTaControllerMgmtTraps 1006318}

      adTAMinorVisualRelayTestActive   NOTIFICATION-TYPE
                OBJECTS       {
                        adTrapInformSeqNum,
                        sysName
                }
                STATUS          current
                DESCRIPTION
                        "Alarm Relay Test. Toggle Minor Visual Relay alarm active active."
        --#TYPE      "Warning - Alarm Relay Test. Toggle Minor Visual Relay alarm active active."
        --#SUMMARY   "adTaControllerMgmtTraps 1006319: Menu Alarm Relay Test. Toggle Minor Visual Relay alarm active active."
        --#SUMMARY   "detected at chassis: %s"
        --#ARGUMENTS {1}
        --#SEVERITY  MINOR
        --#GENERIC   6
        --#CATEGORY  "Alarm Relay Test"
        --#SOURCE_ID "A"
        --#TIMEINDEX 0
        ::= {adTaControllerMgmtTraps 1006319}

      adTAAux1RelayTestClear   NOTIFICATION-TYPE
                OBJECTS       {
                        adTrapInformSeqNum,
                        sysName
                }
                STATUS          current
                DESCRIPTION
                        "Alarm Relay Test. Toggle Auxiliary #1 Relay Active alarm clear."
        --#TYPE      "Warning - Alarm Relay Test. Toggle Auxiliary #1 Relay Active alarm clear."
        --#SUMMARY   "adTaControllerMgmtTraps 1006320: Menu Alarm Relay Test. Toggle Auxiliary #1 Relay Active alarm clear."
        --#SUMMARY   "detected at chassis: %s"
        --#ARGUMENTS {1}
        --#SEVERITY  WARNING
        --#GENERIC   6
        --#CATEGORY  "Alarm Relay Test"
        --#SOURCE_ID "A"
        --#TIMEINDEX 0
        ::= {adTaControllerMgmtTraps 1006320}

      adTAAux1RelayTestActive   NOTIFICATION-TYPE
                OBJECTS       {
                        adTrapInformSeqNum,
                        sysName
                }
                STATUS          current
                DESCRIPTION
                        "Alarm Relay Test. Toggle Auxiliary #1 Relay Active alarm active."
        --#TYPE      "Warning - Alarm Relay Test. Toggle Auxiliary #1 Relay Active alarm active."
        --#SUMMARY   "adTaControllerMgmtTraps 1006321: Menu Alarm Relay Test. Toggle Auxiliary #1 Relay Active alarm active."
        --#SUMMARY   "detected at chassis: %s"
        --#ARGUMENTS {1}
        --#SEVERITY  WARNING
        --#GENERIC   6
        --#CATEGORY  "Alarm Relay Test"
        --#SOURCE_ID "A"
        --#TIMEINDEX 0
        ::= {adTaControllerMgmtTraps 1006321}

      adTAAux2RelayTestClear   NOTIFICATION-TYPE
                OBJECTS       {
                        adTrapInformSeqNum,
                        sysName
                }
                STATUS          current
                DESCRIPTION
                        "Alarm Relay Test. Toggle Auxiliary #2 Relay Active alarm clear."
        --#TYPE      "Warning - Alarm Relay Test. Toggle Auxiliary #2 Relay Active alarm clear."
        --#SUMMARY   "adTaControllerMgmtTraps 1006322: Menu Alarm Relay Test. Toggle Auxiliary #2 Relay Active alarm clear."
        --#SUMMARY   "detected at chassis: %s"
        --#ARGUMENTS {1}
        --#SEVERITY  WARNING
        --#GENERIC   6
        --#CATEGORY  "Alarm Relay Test"
        --#SOURCE_ID "A"
        --#TIMEINDEX 0
        ::= {adTaControllerMgmtTraps 1006322}

      adTAAux2RelayTestActive   NOTIFICATION-TYPE
                OBJECTS       {
                        adTrapInformSeqNum,
                        sysName
                }
                STATUS          current
                DESCRIPTION
                        "Alarm Relay Test. Toggle Auxiliary #2 Relay Active alarm active."
        --#TYPE      "Warning - Alarm Relay Test. Toggle Auxiliary #2 Relay Active alarm active."
        --#SUMMARY   "adTaControllerMgmtTraps 1006323: Menu Alarm Relay Test. Toggle Auxiliary #2 Relay Active alarm active."
        --#SUMMARY   "detected at chassis: %s"
        --#ARGUMENTS {1}
        --#SEVERITY  WARNING
        --#GENERIC   6
        --#CATEGORY  "Alarm Relay Test"
        --#SOURCE_ID "A"
        --#TIMEINDEX 0
        ::= {adTaControllerMgmtTraps 1006323}

    --
    -- clei code alarms
    --

      adTACleiCodeMisMatchClear  NOTIFICATION-TYPE
                OBJECTS       {
                        adTrapInformSeqNum,
                        sysName,
                        adGenSlotInfoIndex,
                        adGenSlotProdName,
                        adGenSlotProdCLEIcode
                        }
                STATUS          current
                DESCRIPTION
                        "CLEI code mis-match clear"
        --#TYPE      "Warning - CLEI code mis-match"
        --#SUMMARY   "adTaControllerMgmtTraps 1006324: CLEI code mis-match clear at slot %d."
        --#SUMMARY   "detected at chassis: %s"
        --#ARGUMENTS { 2,1}
        --#SEVERITY  WARNING
        --#GENERIC   6
        --#CATEGORY  "Card Insertion"
        --#SOURCE_ID "A"
        --#TIMEINDEX 0
        ::= {adTaControllerMgmtTraps 1006324}

        adTACleiCodeMisMatch   NOTIFICATION-TYPE
                OBJECTS       {
                        adTrapInformSeqNum,
                        sysName,
                        adGenSlotInfoIndex,
                        adGenSlotProdName,
                        adGenSlotProdCLEIcode
                        }
                STATUS          current
                DESCRIPTION
                        "CLEI code mis-match."
        --#TYPE      "Warning - CLEI code mis-match"
        --#SUMMARY   "adTaControllerMgmtTraps 1006325: CLEI code mis-match at slot %d."
        --#SUMMARY   "detected at chassis: %s"
        --#ARGUMENTS { 2,1}
        --#SEVERITY  WARNING
        --#GENERIC   6
        --#CATEGORY  "Card Insertion"
        --#SOURCE_ID "A"
        --#TIMEINDEX 0
        ::= {adTaControllerMgmtTraps 1006325}

    --
    -- power shedding alarms
    --

        adTAPowerSheddingInputDeAsserted  NOTIFICATION-TYPE
                OBJECTS       {
                        adTrapInformSeqNum,
                        sysName,
                        adTASysCtrlPowerShedAlmInput,
                        adTASysCtrlPowerShedACFailAlarmDescription,
                        adTASysCtrlPowerShedACFailAlarmSeverity,
                        adTASysCtrlPowerShedCountDown
                        }
                STATUS          current
                DESCRIPTION
                  "Power Shedding Input DeAsserted"
          --#TYPE      "Major - Power Shedding Input DeAsserted"
          --#SUMMARY   "adTaControllerMgmtTraps 1006328:  Power Shedding Input DeAsserted"
          --#SUMMARY   "detected at chassis: %s"
          --#ARGUMENTS { 1 }
          --#SEVERITY  MAJOR
          --#GENERIC   6
          --#CATEGORY  "Power Shedding Input DeAsserted"
          --#SOURCE_ID "A"
          --#TIMEINDEX 0
          ::= {adTaControllerMgmtTraps 1006328}


        adTAPowerSheddingInputAsserted  NOTIFICATION-TYPE
                OBJECTS       {
                        adTrapInformSeqNum,
                        sysName,
                        adTASysCtrlPowerShedAlmInput,
                        adTASysCtrlPowerShedACFailAlarmDescription,
                        adTASysCtrlPowerShedACFailAlarmSeverity,
                        adTASysCtrlPowerShedCountDown
                        }
                STATUS          current
                DESCRIPTION
                  "Power Shedding Input Asserted"
          --#TYPE      "Major - Power Shedding Input Asserted"
          --#SUMMARY   "adTaControllerMgmtTraps 1006329:  Power Shedding Input Asserted"
          --#SUMMARY   "detected at chassis: %s"
          --#ARGUMENTS { 1 }
          --#SEVERITY  MAJOR
          --#GENERIC   6
          --#CATEGORY  "Power Shedding Input Asserted"
          --#SOURCE_ID "A"
          --#TIMEINDEX 0
          ::= {adTaControllerMgmtTraps 1006329}


        adTAPowerSheddingDeActivated  NOTIFICATION-TYPE
                OBJECTS       {
                        adTrapInformSeqNum,
                        sysName,
                        adTASysCtrlPowerShedAlmInput,
                        adTASysCtrlPowerShedStatus,
                        adTASysCtrlPowerShedStateAlarmSeverity
                        }
                STATUS          current
                DESCRIPTION
                  "Power Shedding Currently Deactivated"
          --#TYPE      "Major - Power Shedding Deactivated"
          --#SUMMARY   "adTaControllerMgmtTraps 1006330:  Power Shedding Deactivated"
          --#SUMMARY   "detected at chassis: %s"
          --#ARGUMENTS { 1 }
          --#SEVERITY  MAJOR
          --#GENERIC   6
          --#CATEGORY  "Power Shedding Deactivated"
          --#SOURCE_ID "A"
          --#TIMEINDEX 0
          ::= {adTaControllerMgmtTraps 1006330}


        adTAPowerSheddingActivated  NOTIFICATION-TYPE
                OBJECTS       {
                        adTrapInformSeqNum,
                        sysName,
                        adTASysCtrlPowerShedAlmInput,
                        adTASysCtrlPowerShedStatus,
                        adTASysCtrlPowerShedStateAlarmSeverity
                        }
                STATUS          current
                DESCRIPTION
                  "Power Shedding Currently Activated"
          --#TYPE      "Major - Power Shedding Activated"
          --#SUMMARY   "adTaControllerMgmtTraps 1006331:  Power Shedding Activated"
          --#SUMMARY   "detected at chassis: %s"
          --#ARGUMENTS { 1 }
          --#SEVERITY  MAJOR
          --#GENERIC   6
          --#CATEGORY  "Power Shedding Activated"
          --#SOURCE_ID "A"
          --#TIMEINDEX 0
          ::= {adTaControllerMgmtTraps 1006331}

    --
    -- fan alarms
    --

        adTAFanMPowerAFailClear    NOTIFICATION-TYPE
                OBJECTS       {
                        adTrapInformSeqNum,
                        sysName,
                        adTAeSCUenvAlarmUserName,
                        adTAeSCUenvAlarmInputLevel
                        }
                STATUS          current
                DESCRIPTION
                        "FANM Bus A Power Failure Alarm clear"
        --#TYPE      "Informational - FANM Bus A Power Failure Alarm clear"
        --#SUMMARY   "adTaControllerMgmtTraps 1006332: FANM Bus A Power Failure Alarm clear;"
        --#SUMMARY   "detected at shelf: %s"
        --#ARGUMENTS { 1 }
        --#SEVERITY  MINOR
        --#GENERIC   6
        --#CATEGORY  "Error Events"
        --#SOURCE_ID "A"
        --#TIMEINDEX 0
        ::= {adTaControllerMgmtTraps 1006332}

        adTAFanMPowerAFail    NOTIFICATION-TYPE
                OBJECTS       {
                        adTrapInformSeqNum,
                        sysName,
                        adTAeSCUenvAlarmUserName,
                        adTAeSCUenvAlarmInputLevel
                        }
                STATUS          current
                DESCRIPTION
                        "FANM Bus A Power Failure Alarm active"
        --#TYPE      "Minor - FANM Bus A Power Failure Alarm active"
        --#SUMMARY   "adTaControllerMgmtTraps 1006333: FANM Bus A Power Failure Alarm active;"
        --#SUMMARY   "detected at shelf: %s"
        --#ARGUMENTS { 1 }
        --#SEVERITY  MINOR
        --#GENERIC   6
        --#CATEGORY  "Error Events"
        --#SOURCE_ID "A"
        --#TIMEINDEX 0
        ::= {adTaControllerMgmtTraps 1006333}

        adTAFanMPowerBFailClear    NOTIFICATION-TYPE
                OBJECTS       {
                        adTrapInformSeqNum,
                        sysName,
                        adTAeSCUenvAlarmUserName,
                        adTAeSCUenvAlarmInputLevel
                        }
                STATUS          current
                DESCRIPTION
                        "FANM Bus B Power Failure Alarm clear"
        --#TYPE      "Informational - FANM Bus B Power Failure Alarm clear"
        --#SUMMARY   "adTaControllerMgmtTraps 1006334: FANM Bus B Power Failure Alarm clear;"
        --#SUMMARY   "detected at shelf: %s"
        --#ARGUMENTS { 1 }
        --#SEVERITY  MINOR
        --#GENERIC   6
        --#CATEGORY  "Error Events"
        --#SOURCE_ID "A"
        --#TIMEINDEX 0
        ::= {adTaControllerMgmtTraps 1006334}

        adTAFanMPowerBFail    NOTIFICATION-TYPE
                OBJECTS       {
                        adTrapInformSeqNum,
                        sysName,
                        adTAeSCUenvAlarmUserName,
                        adTAeSCUenvAlarmInputLevel
                        }
                STATUS          current
                DESCRIPTION
                        "FANM Bus B Power Failure Alarm active"
        --#TYPE      "Minor - FANM Bus B Power Failure Alarm active"
        --#SUMMARY   "adTaControllerMgmtTraps 1006335: FANM Bus B Power Failure Alarm active;"
        --#SUMMARY   "detected at shelf: %s"
        --#ARGUMENTS { 1 }
        --#SEVERITY  MINOR
        --#GENERIC   6
        --#CATEGORY  "Error Events"
        --#SOURCE_ID "A"
        --#TIMEINDEX 0
        ::= {adTaControllerMgmtTraps 1006335}


    --
    -- System Release Management Alarms
    --

      adTASrmActiveRlsErrorClear   NOTIFICATION-TYPE
                OBJECTS   {
                            adTrapInformSeqNum,
                            sysName,
                            adTaSysCtrlSrmReleaseFilename,
                            adTaSysCtrlSrmReleaseStatus,
                            adTaSysCtrlSrmReleaseErrorBitmask
                            }
                STATUS          current
                DESCRIPTION
                "This trap is used to indicate that the previous
                 active system release error state has cleared."
        --#TYPE      "Warning - Active Release Error alarm clear."
        --#SUMMARY   "adTaControllerMgmtTraps 1006340: Active Release Error alarm clear for;"
        --#SUMMARY   "shelf: %s, release: %s, status: %s, error: %x"
        --#ARGUMENTS { 1, 2, 3, 4 }
        --#SEVERITY  WARNING
        --#GENERIC   6
        --#CATEGORY  "Information Events"
        --#SOURCE_ID "A"
        --#TIMEINDEX 0
        ::= {adTaControllerMgmtTraps 1006340}

      adTASrmActiveRlsErrorActive   NOTIFICATION-TYPE
                OBJECTS   {
                            adTrapInformSeqNum,
                            sysName,
                            adTaSysCtrlSrmReleaseFilename,
                            adTaSysCtrlSrmReleaseStatus,
                            adTaSysCtrlSrmReleaseErrorBitmask
                            }
                STATUS          current
                DESCRIPTION
                "This trap is used to indicate that the active system release has an error.
                 Walking the adTaSysCtrlSysRlsFilesTable will provide more detail for which
                 spacific files have an error."
        --#TYPE      "Warning - Active Release Error alarm active."
        --#SUMMARY   "adTaControllerMgmtTraps 1006341: Active Release Error alarm active for;"
        --#SUMMARY   "shelf: %s, release: %s, status: %s, error: %x"
        --#ARGUMENTS { 1, 2, 3, 4 }
        --#SEVERITY  WARNING
        --#GENERIC   6
        --#CATEGORY  "Information Events"
        --#SOURCE_ID "A"
        --#TIMEINDEX 0
        ::= {adTaControllerMgmtTraps 1006341}

      adTASrmBackupRlsErrorClear   NOTIFICATION-TYPE
                OBJECTS   {
                            adTrapInformSeqNum,
                            sysName,
                            adTaSysCtrlSrmReleaseFilename,
                            adTaSysCtrlSrmReleaseStatus,
                            adTaSysCtrlSrmReleaseErrorBitmask
                            }
                STATUS          current
                DESCRIPTION
                "This trap is used to indicate that the previous
                 backup system release error has cleared."
        --#TYPE      "Warning - Backup Release Error alarm clear."
        --#SUMMARY   "adTaControllerMgmtTraps 1006342: Backup Release Error alarm clear for;"
        --#SUMMARY   "shelf: %s, release: %s, status: %s, error: %x"
        --#ARGUMENTS { 1, 2, 3, 4 }
        --#SEVERITY  WARNING
        --#GENERIC   6
        --#CATEGORY  "Information Events"
        --#SOURCE_ID "A"
        --#TIMEINDEX 0
        ::= {adTaControllerMgmtTraps 1006342}

      adTASrmBackupRlsErrorActive   NOTIFICATION-TYPE
                OBJECTS   {
                            adTrapInformSeqNum,
                            sysName,
                            adTaSysCtrlSrmReleaseFilename,
                            adTaSysCtrlSrmReleaseStatus,
                            adTaSysCtrlSrmReleaseErrorBitmask
                            }
                STATUS          current
                DESCRIPTION
                "This trap is used to indicate that the backup system release has an error.
                 Walking the adTaSysCtrlSysRlsFilesTable will provide more detail for which
                 specific files have an error."
        --#TYPE      "Warning - Backup Release Error alarm active."
        --#SUMMARY   "adTaControllerMgmtTraps 1006343: Backup Release Error alarm active for;"
        --#SUMMARY   "shelf: %s, release: %s, status: %s, error: %d"
        --#ARGUMENTS { 1, 2, 3, 4 }
        --#SEVERITY  WARNING
        --#GENERIC   6
        --#CATEGORY  "Information Events"
        --#SOURCE_ID "A"
        --#TIMEINDEX 0
        ::= {adTaControllerMgmtTraps 1006343}

        adTASrmNewActiveRelease  NOTIFICATION-TYPE
                OBJECTS   {
                            adTrapInformSeqNum,
                            sysName,
                            adTaSysCtrlSrmReleaseFilename
                            }
                STATUS          current
                DESCRIPTION
                "This trap is used to indicate that there is a
                 new active system release, and the activate backup
                 system release operation has successfully completed."
        --#TYPE      "Warning - New Active System Release."
        --#SUMMARY   "adTaControllerMgmtTraps 1006344: New Active System Release;"
        --#SUMMARY   "shelf: %s, active release: %s"
        --#ARGUMENTS { 1, 2 }
        --#SEVERITY  WARNING
        --#GENERIC   6
        --#CATEGORY  "Information Events"
        --#SOURCE_ID "A"
        --#TIMEINDEX 0
        ::= {adTaControllerMgmtTraps 1006344}

        adTASrmRlsDownloadStarted  NOTIFICATION-TYPE
                OBJECTS   {
                            adTrapInformSeqNum,
                            sysName,
                            adTaSysCtrlSrmDownloadFilename
                            }
                STATUS          current
                DESCRIPTION
                "This trap is used to indicate that a system
                 release download operation has been started."
        --#TYPE      "Warning - System Release download operation started."
        --#SUMMARY   "adTaControllerMgmtTraps 1006346: System Release download operation started;"
        --#SUMMARY   "started at shelf: %s, release: %s"
        --#ARGUMENTS { 1, 2 }
        --#SEVERITY  WARNING
        --#GENERIC   6
        --#CATEGORY  "Information Events"
        --#SOURCE_ID "A"
        --#TIMEINDEX 0
        ::= {adTaControllerMgmtTraps 1006346}

        adTASrmRlsDownloadCompleted  NOTIFICATION-TYPE
                OBJECTS   {
                            adTrapInformSeqNum,
                            sysName,
                            adTaSysCtrlSrmDownloadFilename
                            }
                STATUS          current
                DESCRIPTION
                "This trap is used to indicate that a system
                 release download operation has successfully completed."
        --#TYPE      "Warning - System Release download operation has successfully completed."
        --#SUMMARY   "adTaControllerMgmtTraps 1006348: System Release download operation has successfully completed;"
        --#SUMMARY   "completed at shelf: %s, release: %s"
        --#ARGUMENTS { 1, 2 }
        --#SEVERITY  WARNING
        --#GENERIC   6
        --#CATEGORY  "Information Events"
        --#SOURCE_ID "A"
        --#TIMEINDEX 0
        ::= {adTaControllerMgmtTraps 1006348}

        adTASrmRlsDownloadFailed  NOTIFICATION-TYPE
                OBJECTS   {
                            adTrapInformSeqNum,
                            sysName,
                            adTaSysCtrlSrmDownloadFilename,
                            adTaSysCtrlSrmStatus
                            }
                STATUS          current
                DESCRIPTION
                "This trap is used to indicate that a system release
                 download operation has failed.  The EMS should perform
                 a 'get' on the adTaSysCtrlSrmStatus OID for further
                 information regarding the error condition."
        --#TYPE      "Warning - System Release download operation has failed."
        --#SUMMARY   "adTaControllerMgmtTraps 1006350: System release download operation has failed;"
        --#SUMMARY   "failed at shelf: %s, release: %s, (%s)"
        --#ARGUMENTS { 1, 2, 3 }
        --#SEVERITY  WARNING
        --#GENERIC   6
        --#CATEGORY  "Information Events"
        --#SOURCE_ID "A"
        --#TIMEINDEX 0
        ::= {adTaControllerMgmtTraps 1006350}

        adTASrmRlsBackupStarted  NOTIFICATION-TYPE
                OBJECTS   {
                            adTrapInformSeqNum,
                            sysName,
                            adTaSysCtrlSrmReleaseFilename
                            }
                STATUS          current
                DESCRIPTION
                "This trap is used to indicate that an Active
                 system release backup operation has been started."
        --#TYPE      "Warning - Active Release backup operation started."
        --#SUMMARY   "adTaControllerMgmtTraps 1006352: Active Release backup operation started;"
        --#SUMMARY   "started at shelf: %s, release: %s"
        --#ARGUMENTS { 1, 2 }
        --#SEVERITY  WARNING
        --#GENERIC   6
        --#CATEGORY  "Information Events"
        --#SOURCE_ID "A"
        --#TIMEINDEX 0
        ::= {adTaControllerMgmtTraps 1006352}

        adTASrmRlsBackupCompleted  NOTIFICATION-TYPE
                OBJECTS   {
                            adTrapInformSeqNum,
                            sysName,
                            adTaSysCtrlSrmReleaseFilename
                            }
                STATUS          current
                DESCRIPTION
                "This trap is used to indicate that an Active system
                release backup operation has successfully completed."
        --#TYPE      "Warning - Active Release backup operation has successfully completed."
        --#SUMMARY   "adTaControllerMgmtTraps 1006354: Active Release backup operation has successfully completed;"
        --#SUMMARY   "completed at shelf: %s, release: %s"
        --#ARGUMENTS { 1, 2 }
        --#SEVERITY  WARNING
        --#GENERIC   6
        --#CATEGORY  "Information Events"
        --#SOURCE_ID "A"
        --#TIMEINDEX 0
        ::= {adTaControllerMgmtTraps 1006354}

        adTASrmRlsBackupFailed  NOTIFICATION-TYPE
                OBJECTS   {
                            adTrapInformSeqNum,
                            sysName,
                            adTaSysCtrlSrmReleaseFilename,
                            adTaSysCtrlSrmStatus
                            }
                STATUS          current
                DESCRIPTION
                "This trap is used to indicate that an Active system
                release backup operation has failed.  The EMS should
                perform a 'get' on the adTaSysCtrlSrmStatus OID for
                further information regarding the error condition."
        --#TYPE      "Warning - Active Release backup operation has failed."
        --#SUMMARY   "adTaControllerMgmtTraps 1006356: Active Release backup operation has failed;"
        --#SUMMARY   "failed at shelf: %s, release: %s, (%s)"
        --#ARGUMENTS { 1, 2, 3 }
        --#SEVERITY  WARNING
        --#GENERIC   6
        --#CATEGORY  "Information Events"
        --#SOURCE_ID "A"
        --#TIMEINDEX 0
        ::= {adTaControllerMgmtTraps 1006356}

      --
      -- Alarm Severity
      --
        adTASysCtrlAlarmSeverityChanged   NOTIFICATION-TYPE
                OBJECTS   {
                            adTrapInformSeqNum,
                            sysName,
                            adTASysCtrlAlarmSeverityLevel
                            }
                STATUS          current
                DESCRIPTION
                "The highest active alarm severity has changed."
        --#TYPE      "Informational - The highest active alarm severity has changed."
        --#SUMMARY   "detected at shelf: %s"
        --#ARGUMENTS { 1 }
        --#SEVERITY  INFORMATIONAL
        --#GENERIC   6
        --#CATEGORY  "Error Events"
        --#SOURCE_ID "A"
        --#TIMEINDEX 0
        ::= {adTaControllerMgmtTraps 1006359}


      --
      -- Device Com Fail Alarm
      --
        adTASysCtrlDeviceComFail  NOTIFICATION-TYPE
                OBJECTS   {
                            adTrapInformSeqNum,
                            sysName,
                            adGenSlotInfoIndex,
                            adTAeSCUTrapAlarmLevel
                            }
                STATUS          current
                DESCRIPTION
                "This trap indicates that an RS485 client has failed to respond."
        --#TYPE      "Major - An RS485 client has failed to respond."
        --#SUMMARY   "An RS485 client has failed to respond to host: %s"
        --#SUMMARY   ""
        --#ARGUMENTS { 1 }
        --#SEVERITY  MAJOR
        --#GENERIC   6
        --#CATEGORY  "Error Events"
        --#SOURCE_ID "A"
        --#TIMEINDEX 0
        ::= {adTaControllerMgmtTraps 1006360}


      --
      -- SWDNLD
      --
        adTASysCtrlSwdnldStarted   NOTIFICATION-TYPE
                OBJECTS   {
                            adTrapInformSeqNum,
                            sysName,
                            adGenSlotInfoIndex,
                            adTAeSCUTrapAlarmLevel
                            }
                STATUS          current
                DESCRIPTION
                "Software download started."
        --#TYPE      "Informational - A software download has been initiated by a TL1 command."
        --#SUMMARY   "Detected at shelf: %s"
        --#ARGUMENTS { 1 }
        --#SEVERITY  INFORMATIONAL
        --#GENERIC   6
        --#CATEGORY  "Status Events"
        --#SOURCE_ID "A"
        --#TIMEINDEX 0
        ::= {adTaControllerMgmtTraps 1006363}

        adTASysCtrlSwdnldComplete   NOTIFICATION-TYPE
                OBJECTS   {
                            adTrapInformSeqNum,
                            sysName,
                            adGenSlotInfoIndex,
                            adTAeSCUTrapAlarmLevel
                            }
                STATUS          current
                DESCRIPTION
                "Software download complete."
        --#TYPE      "Informational - A TL1 initiated software download has completed."
        --#SUMMARY   "Detected at shelf: %s"
        --#ARGUMENTS { 1 }
        --#SEVERITY  INFORMATIONAL
        --#GENERIC   6
        --#CATEGORY  "Status Events"
        --#SOURCE_ID "A"
        --#TIMEINDEX 0
        ::= {adTaControllerMgmtTraps 1006365}

        adTASysCtrlSwdnldFailure   NOTIFICATION-TYPE
                OBJECTS   {
                            adTrapInformSeqNum,
                            sysName,
                            adGenSlotInfoIndex,
                            adTAeSCUTrapAlarmLevel
                            }
                STATUS          current
                DESCRIPTION
                "Software download failure."
        --#TYPE      "Informational - A TL1 initiated software download has failed."
        --#SUMMARY   "Detected at shelf: %s"
        --#ARGUMENTS { 1 }
        --#SEVERITY  INFORMATIONAL
        --#GENERIC   6
        --#CATEGORY  "Status Events"
        --#SOURCE_ID "A"
        --#TIMEINDEX 0
        ::= {adTaControllerMgmtTraps 1006367}


      --
      -- System Controlled Reboot Traps
      --

        adTaSysCtrlRebootTraps       OBJECT IDENTIFIER ::= { adTaSysCtrlReboot 0 }

        adTaSysCtrlRebootException  NOTIFICATION-TYPE
                OBJECTS   {
                            adTrapInformSeqNum,
                            sysName,
                            adTaSysCtrlRebootLastStatus
                            }
                STATUS          current
                DESCRIPTION
                "System Controlled Reboot exception."
        --#TYPE      "Informational - System Controlled Reboot operation could not be initiated or failed."
        --#SUMMARY   "detected at shelf: %s, status: %s"
        --#ARGUMENTS { 1, 2 }
        --#SEVERITY  WARNING
        --#GENERIC   6
        --#CATEGORY  "Error Events"
        --#SOURCE_ID "A"
        --#TIMEINDEX 0
        ::= {adTaSysCtrlRebootTraps 1006368}

        -- adTaSysCtrlSNMPProvChange  NOTIFICATION-TYPE
        --::= 1006370
        -- Do not use 1006370 for a trap number this is reserved for adTaSysCtrlSNMPProvChange
        -- !!! Do not use 1006370 for a trap number this is reserved for adTaSysCtrlSNMPProvChange

      --
      -- System Data Error
      --
        adTAeSysSystemDataError  NOTIFICATION-TYPE
                OBJECTS   {
                            adTrapInformSeqNum,
                            sysName,
                            adTaDataLossDescription
                            }
                STATUS          current
                DESCRIPTION
                "System Data Loss exception."
        --#TYPE      "Informational - Data loss or coruption error."
        --#SUMMARY   "detected at shelf: %s, status: %s : Error: %s"
        --#ARGUMENTS { 1, 2 , 3}
        --#SEVERITY  WARNING
        --#GENERIC   6
        --#CATEGORY  "Error Events"
        --#SOURCE_ID "A"
        --#TIMEINDEX 0
        ::= {adTaControllerMgmtTraps 1006372}


        adTAPowerSheddingServerTimeoutClear  NOTIFICATION-TYPE
                OBJECTS       {
                        adTrapInformSeqNum,
                        sysName,
                        adTASysCtrlPowerShedRemoteServerIP,
                        adTASysCtrlPowerShedStatus
                        }
                STATUS          current
                DESCRIPTION
                  "Power Shedding Server Timeout Clear"
          --#TYPE      "Major - Power Shedding Server Timeout Clear"
          --#SUMMARY   "adTaControllerMgmtTraps 1006373:  Power Shedding Server
          --#SUMMARY   "timeout clear at chassis: %s"
          --#ARGUMENTS { 1 }
          --#SEVERITY  MAJOR
          --#GENERIC   6
          --#CATEGORY  "Power Shedding Server Timeout Clear"
          --#SOURCE_ID "A"
          --#TIMEINDEX 0
          ::= {adTaControllerMgmtTraps 1006373}


        adTAPowerSheddingServerTimeout  NOTIFICATION-TYPE
                OBJECTS       {
                        adTrapInformSeqNum,
                        sysName,
                        adTASysCtrlPowerShedRemoteServerIP,
                        adTASysCtrlPowerShedStatus
                        }
                STATUS          current
                DESCRIPTION
                  "Power Shedding Server Timeout"
          --#TYPE      "Major - Power Shedding Server Timeout"
          --#SUMMARY   "adTaControllerMgmtTraps 1006373:  Power Shedding Server""
          --#SUMMARY   "timeout at chassis: %s"
          --#ARGUMENTS { 1 }
          --#SEVERITY  MAJOR
          --#GENERIC   6
          --#CATEGORY  "Power Shedding Server Timeout"
          --#SOURCE_ID "A"
          --#TIMEINDEX 0
          ::= {adTaControllerMgmtTraps 1006374}

        adTASysCtrlCardSensed   NOTIFICATION-TYPE
                OBJECTS       {
                        adTrapInformSeqNum,
                        sysName,
                        adGenSlotInfoIndex,
                        adTAeSCUTrapAlarmLevel
                        }
                STATUS          current
                DESCRIPTION
                        "A card has been sensed in the chassis."
        --#TYPE      "Informational - A card has been sensed in the chassis"
        --#SUMMARY   "Card sensed in chassis;"
        --#SUMMARY   "chassis: %s, slot: %d"
        --#ARGUMENTS { 1, 2 }
        --#SEVERITY  INFORMATIONAL
        --#GENERIC   6
        --#CATEGORY  "Configuration Events"
        --#SOURCE_ID "A"
        --#TIMEINDEX 0
        ::= { adTaControllerMgmtTraps 1006376 }


        adTASysCtrlCardNotSensed   NOTIFICATION-TYPE
                OBJECTS       {
                        adTrapInformSeqNum,
                        sysName,
                        adGenSlotInfoIndex,
                        adTAeSCUTrapAlarmLevel
                        }
                STATUS          current
                DESCRIPTION
                        "A card is no longer sensed in the chassis."
        --#TYPE      "Warning - A card not sensed in the chassis"
        --#SUMMARY   "Card not sensed in chassis;"
        --#SUMMARY   "chassis: %s, slot: %d"
        --#ARGUMENTS { 1, 2 }
        --#SEVERITY  INFORMATIONAL
        --#GENERIC   6
        --#CATEGORY  "Configuration Events"
        --#SOURCE_ID "A"
        --#TIMEINDEX 0
        ::= { adTaControllerMgmtTraps 1006377 }

        adTASysCtrlCardReady   NOTIFICATION-TYPE
                OBJECTS       {
                        adTrapInformSeqNum,
                        sysName,
                        adGenSlotInfoIndex,
                        adTAeSCUTrapAlarmLevel
                        }
                STATUS          current
                DESCRIPTION
                        "A card is ready to be managed."
        --#TYPE      "Informational - A card is ready to be managed."
        --#SUMMARY   "Card is ready to be managed;"
        --#SUMMARY   "chassis: %s, slot: %d"
        --#ARGUMENTS { 1, 2 }
        --#SEVERITY  INFORMATIONAL
        --#GENERIC   6
        --#CATEGORY  "Configuration Events"
        --#SOURCE_ID "A"
        --#TIMEINDEX 0
        ::= { adTaControllerMgmtTraps 1006378 }


        adTASysCtrlCardNotReady   NOTIFICATION-TYPE
                OBJECTS       {
                        adTrapInformSeqNum,
                        sysName,
                        adGenSlotInfoIndex,
                        adTAeSCUTrapAlarmLevel
                        }
                STATUS          current
                DESCRIPTION
                        "A card is not ready to be managed."
        --#TYPE      "Informational - A card is not ready to be managed."
        --#SUMMARY   "Card is not ready to be managed;"
        --#SUMMARY   "chassis: %s, slot: %d"
        --#ARGUMENTS { 1, 2 }
        --#SEVERITY  INFORMATIONAL
        --#GENERIC   6
        --#CATEGORY  "Configuration Events"
        --#SOURCE_ID "A"
        --#TIMEINDEX 0
        ::= { adTaControllerMgmtTraps 1006379 }


--
-- AutoUpgrade EOSS traps
--

        adTaSysCtrlAutoUpgradeEOSSWarningClear  NOTIFICATION-TYPE
                OBJECTS       {
                        adTrapInformSeqNum,
                        sysName,
                        adGenSlotInfoIndex
                        }
                STATUS  current
                DESCRIPTION
                       "Auto Upgrade End Of Software Support Warning (Clear)."
          --#TYPE      "Warning - Auto Upgrade End Of Software Support Warning"
          --#SUMMARY   "Auto Upgrade End Of Software Support Warning Clear"
          --#SUMMARY   "detected at chassis: %s, slot: %d"
          --#ARGUMENTS { 1,2 }
          --#SEVERITY  WARNING
          --#GENERIC   6
          --#CATEGORY  "Auto Upgrade End Of Software Support Warning"
          --#SOURCE_ID "A"
          --#TIMEINDEX 0
          ::=  { adTaControllerMgmtTraps 1006380 }

        adTaSysCtrlAutoUpgradeEOSSWarningActive  NOTIFICATION-TYPE
                OBJECTS       {
                        adTrapInformSeqNum,
                        sysName,
                        adGenSlotInfoIndex
                        }
                STATUS  current
                DESCRIPTION
                       "This trap is used to indicate the module may not be supported
                        by future SystemReleases.
                        Please contact Adtran customer support for further information."
          --#TYPE      "Warning - Auto Upgrade End Of Software Support Warning"
          --#SUMMARY   "Auto Upgrade End Of Software Support Warning Active"
          --#SUMMARY   "detected at chassis: %s, slot: %d"
          --#ARGUMENTS { 1,2 }
          --#SEVERITY  WARNING
          --#GENERIC   6
          --#CATEGORY  "Auto Upgrade End Of Software Support Warning"
          --#SOURCE_ID "A"
          --#TIMEINDEX 0
          ::=  { adTaControllerMgmtTraps 1006381 }


        adTaSysCtrlAutoUpgradeEOSSDeniedClear  NOTIFICATION-TYPE
                OBJECTS       {
                        adTrapInformSeqNum,
                        sysName,
                        adGenSlotInfoIndex
                        }
                STATUS  current
                DESCRIPTION
                       "Auto Upgrade End Of Software Support Denied (Clear)."
          --#TYPE      "Minor - Auto Upgrade End Of Software Support Denied"
          --#SUMMARY   "Auto Upgrade End Of Software Support Denied Clear"
          --#SUMMARY   "detected at chassis: %s, slot: %d"
          --#ARGUMENTS { 1,2 }
          --#SEVERITY  MINOR
          --#GENERIC   6
          --#CATEGORY  "Auto Upgrade End Of Software Support Denied"
          --#SOURCE_ID "A"
          --#TIMEINDEX 0
          ::=  { adTaControllerMgmtTraps 1006382 }

        adTaSysCtrlAutoUpgradeEOSSDeniedActive  NOTIFICATION-TYPE
                OBJECTS       {
                        adTrapInformSeqNum,
                        sysName,
                        adGenSlotInfoIndex
                        }
                STATUS  current
                DESCRIPTION
                       "This trap is used to indicate the module is not supported by the
                        SystemRelease of the provisioned AutoUpgrade configuration file.
                        AutoUpgrade cannot proceed until this is resolved.
                        Please contact Adtran customer support for further information."
          --#TYPE      "Minor - Auto Upgrade End Of Software Support Denied"
          --#SUMMARY   "Auto Upgrade End Of Software Support Denied Active"
          --#SUMMARY   "detected at chassis: %s, slot: %d"
          --#ARGUMENTS { 1,2 }
          --#SEVERITY  MINOR
          --#GENERIC   6
          --#CATEGORY  "Auto Upgrade End Of Software Support Denied"
          --#SOURCE_ID "A"
          --#TIMEINDEX 0
          ::=  { adTaControllerMgmtTraps 1006383 }

--
-- AutoUpgrade EOSS traps
--


        adTASysConfigurationChange   NOTIFICATION-TYPE
                OBJECTS       {
                        adTrapInformSeqNum,
                        sysName,
                        adTASysLastConfigChangeAlarmTime
                        }
                STATUS          current
                DESCRIPTION
                        "A system configuration change has occurred.
                         The frequency of this alarm is controlled by the
                         adTASysConfigurationChangeTimer OID."
        --#TYPE      "Informational - A system configuration change has occurred."
        --#SUMMARY   "System configuration change."
        --#SUMMARY   "chassis: %s"
        --#ARGUMENTS { 1 }
        --#SEVERITY  INFORMATIONAL
        --#GENERIC   6
        --#CATEGORY  "Configuration Events"
        --#SOURCE_ID "A"
        --#TIMEINDEX 0
        ::= { adTaControllerMgmtTraps 1006384 }

   END
