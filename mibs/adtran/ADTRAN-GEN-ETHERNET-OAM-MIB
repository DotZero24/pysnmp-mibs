ADTRAN-GEN-ETHERNET-OAM-MIB

  DEFINITIONS ::= BEGIN

  -- TITLE:     Adtran Ethernet OAM Group MIB
  -- DATE:      May 6, 2008
  --
  -- REVISION HISTORY: Date           Comments
  --                   05/06/2008     Created

  -- This MIB defines the generic MIB for Ethernet OAM.

    IMPORTS
        MODULE-IDENTITY
            FROM SNMPv2-SMI

      adShared,
      adIdentityShared
          FROM ADTRAN-MIB;

     adGenEthernetOAMIdentity MODULE-IDENTITY
        LAST-UPDATED "201106100800Z"
        ORGANIZATION
            "ADTRAN, Inc."
        CONTACT-INFO
            "CND Tech Support
                Postal: ADTRAN, Inc.
                        901 Explorer Blvd.
                        Huntsville, AL  35806
                        Tel: +1 800 726-8663
                        Fax: +1 256 963 6217
                        E-mail: support@adtran.com"
        DESCRIPTION
            "Ethernet OAM Shared Definitions MIB"

        REVISION "201106100800Z"
        DESCRIPTION
            "Added Y1731 Related OIDs"

        ::= { adIdentityShared 75 }


  -- OBJECT IDENTIFIERS

  adGenEthernetOAM           OBJECT IDENTIFIER ::= { adShared 75  }

  adGenEthernetCfm           OBJECT IDENTIFIER ::= { adGenEthernetOAM 1  }
  adGenEthernetCfmID         OBJECT IDENTIFIER ::= { adGenEthernetOAMIdentity 1 }
  adGenY1731                 OBJECT IDENTIFIER ::= { adGenEthernetOAM 2  }
  adGenY1731ID               OBJECT IDENTIFIER ::= { adGenEthernetOAMIdentity 2 }

  END
