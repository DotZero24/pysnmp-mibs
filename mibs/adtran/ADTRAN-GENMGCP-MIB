ADTRAN-GENMGCP-MIB

-- TITLE:     The ADTRAN Generic MGCP MIB
-- PRODUCT:   TA5000
-- VERSION:   1.0
-- DATE:      01/21/13
-- AUTHOR:    Subhra Saha, David Wachira, Timothy Myers
-- STATUS:    PRELIMINARY

-- This MIB defines the object identifiers (OIDs) for the
-- ADTRAN GENMGCP entities.

-- "DO NOT MAKE HISTORY COMMENTS HERE!!!! Revision history now in REVISION/DESCRIPTION clauses below"

-- *****************************************************************************
DEFINITIONS ::= BEGIN

IMPORTS

   adGenMgcp,
   adGenMgcpID
      FROM ADTRAN-SHARED-CND-SYSTEM-MIB

   OBJECT-TYPE,
   MODULE-IDENTITY,
   Integer32
      FROM SNMPv2-SMI

   DisplayString,
   RowStatus,
   TruthValue,
   TEXTUAL-CONVENTION
      FROM SNMPv2-TC

   AdGenVoipCodecProfileType,
   AdGenVoipCodecProfileName,
   AdGenVoipMediaProfileName
      FROM ADTRAN-GENVOIP-MIB

   ifIndex,
   InterfaceIndexOrZero
      FROM IF-MIB
   ;

adGenMgcpEntity MODULE-IDENTITY
   LAST-UPDATED "201702160000Z"
   ORGANIZATION "Adtran, Inc."
   CONTACT-INFO
     "CND Tech Support
         Postal: ADTRAN, Inc.
                 901 Explorer Blvd.
                 Huntsville, AL  35806
                 Tel: +1 800 726-8663
                 Fax: +1 256 963 6217
                 E-mail: support@adtran.com"
   DESCRIPTION
      "This MIB defines the objects for MGCP management."

   REVISION "201702160000Z"
   DESCRIPTION "Added new value 'connected_no_rqnt(4)' to oid adGenMgcpEndpointStatusState.
      This will help with troubleshooting in the field."

   REVISION "201403180000Z"
   DESCRIPTION "Added oids: adGenMgcpEndpointMediaProfile, adGenMgcpEndpointCodecListProfile,
                            adGenMgcpEndpointOperStatus, adGenMgcpEndpointStatusCodecInUse,
                            adGenMgcpEndpointLastError, adGenMgcpProfileRFC2833Signaling"

   REVISION "201307180000Z"
   DESCRIPTION "Added oid for forward disconnect provisioning on MGCP endpoints"

   REVISION "201305230000Z"
   DESCRIPTION "Added oids to enable MGCP restart operations as well as seeing
      the last error for those actions. Also removed the number of endpoints
      connected to each profile because that information is no longer centrally
      obtainable."

   REVISION "201301210000Z"
   DESCRIPTION "Created"
::= { adGenMgcpID 1 }

--==============================================================================
-- PROVISIONING
--==============================================================================

adGenMgcpProvisioning                OBJECT IDENTIFIER ::= {adGenMgcp 1}

-- *****************************************************************************
-- Groups in MGCP Provisioning
-- *****************************************************************************

adGenMgcpProfileProv          OBJECT IDENTIFIER  ::= { adGenMgcpProvisioning 1 }
adGenMgcpEndpointProv         OBJECT IDENTIFIER  ::= { adGenMgcpProvisioning 2 }

--==============================================================================
-- STATUS
--==============================================================================

adGenMgcpStatus                      OBJECT IDENTIFIER ::= {adGenMgcp 2}

-- *****************************************************************************
-- Groups in MGCP Status
-- *****************************************************************************

adGenMgcpEndpointStatus       OBJECT IDENTIFIER  ::= { adGenMgcpStatus 1 }

--==============================================================================
-- Actions
--==============================================================================

adGenMgcpActions                     OBJECT IDENTIFIER ::= {adGenMgcp 3}


--==============================================================================
-- TEXTUAL CONVENTION

AdGenMgcpProfileName ::= TEXTUAL-CONVENTION
   DISPLAY-HINT "40a"
   STATUS      current
   DESCRIPTION
     "The name for the MGCP profile table instance.
      Used to index the MGCP profile table (adGenMgcpProfileProvTable)."
   SYNTAX      OCTET STRING (SIZE(1..40))


--******************************************************************************
-- This table is for MGCP Profile provisioning.
--******************************************************************************

adGenMgcpProfileProvCurrentNumber OBJECT-TYPE
   SYNTAX      Integer32
   MAX-ACCESS  read-only
   STATUS      current
   DESCRIPTION
     "Current number of MGCP Profiles defined."
   ::= { adGenMgcpProfileProv 1 }

adGenMgcpProfileProvLastCreateError OBJECT-TYPE
   SYNTAX      DisplayString
   MAX-ACCESS  read-only
   STATUS      current
   DESCRIPTION
     "The reason for the last error that occured while attempting to create
      an entry in the MGCP Profile provisioning table (adGenMgcpProfileProvTable)."
   ::= { adGenMgcpProfileProv 2 }

adGenMgcpProfileProvTable OBJECT-TYPE
   SYNTAX      SEQUENCE OF AdGenMgcpProfileProvEntry
   MAX-ACCESS  not-accessible
   STATUS      current
   DESCRIPTION
     "This table supports provisioning of MGCP profile parameters for the MGCP
      stack."
   ::= { adGenMgcpProfileProv 3 }

adGenMgcpProfileProvEntry OBJECT-TYPE
   SYNTAX      AdGenMgcpProfileProvEntry
   MAX-ACCESS  not-accessible
   STATUS      current
   DESCRIPTION
     "An entry in the adGenMgcpProfileProvTable."
   INDEX { IMPLIED adGenMgcpProfileEntryIndex }
   ::= { adGenMgcpProfileProvTable 1 }

AdGenMgcpProfileProvEntry ::=
   SEQUENCE
   {
      adGenMgcpProfileEntryIndex                   AdGenMgcpProfileName,
      adGenMgcpProfileRowStatus                    RowStatus,
      adGenMgcpProfileLastErrorString              DisplayString,

      adGenMgcpProfileCallAgentPrimary             DisplayString,
      adGenMgcpProfileCallAgentPrimaryUdp          Integer32,
      adGenMgcpProfileCallAgentSecondary           DisplayString,
      adGenMgcpProfileCallAgentSecondaryUdp        Integer32,

      adGenMgcpProfileShutdown                     INTEGER,
      adGenMgcpProfileBracketedIp                  TruthValue,
      adGenMgcpProfileStandard                     INTEGER,

      adGenMgcpProfileMgcpDscp                     Integer32,
      adGenMgcpProfileRtpDscp	                     Integer32,

      adGenMgcpProfileGatewayUdp                   Integer32,
      adGenMgcpProfileRtpUdpOffset                 Integer32,

      adGenMgcpProfilePersistentNotifyHangDown     INTEGER,
      adGenMgcpProfilePersistentNotifyHangUp       INTEGER,
      adGenMgcpProfilePersistentNotifyHookFlash    INTEGER,

      adGenMgcpProfileRetransmitDelay              INTEGER,

      adGenMgcpProfileMax1                         Integer32,
      adGenMgcpProfileMax2                         Integer32,

      adGenMgcpProfileLocalDomainType              INTEGER,
      adGenMgcpProfileLocalDomainAddress           DisplayString,

      adGenMgcpProfileTerminationIdBase            DisplayString,
      adGenMgcpProfileRFC2833Signaling             INTEGER
   }

adGenMgcpProfileEntryIndex OBJECT-TYPE
   SYNTAX      AdGenMgcpProfileName
   MAX-ACCESS  not-accessible
   STATUS      current
   DESCRIPTION
     "The name of the MGCP Profile."
   ::= { adGenMgcpProfileProvEntry 1 }

adGenMgcpProfileRowStatus OBJECT-TYPE
   SYNTAX       RowStatus
   MAX-ACCESS   read-create
   STATUS       current
   DESCRIPTION
     "This object is used to create a new row or modify or delete an existing
      row in this table."
   ::= { adGenMgcpProfileProvEntry 2 }

adGenMgcpProfileLastErrorString OBJECT-TYPE
   SYNTAX       DisplayString
   MAX-ACCESS   read-only
   STATUS       current
   DESCRIPTION
     "The reason for the last error that occured while attempting to create or
      modify an entry in the MGCP Profile Prov Table."
   ::= { adGenMgcpProfileProvEntry 3 }

adGenMgcpProfileCallAgentPrimary OBJECT-TYPE
   SYNTAX      DisplayString
   MAX-ACCESS  read-create
   STATUS      current
   DESCRIPTION
     "The primary MGCP Call-Agent's IP address or host name."
   ::= { adGenMgcpProfileProvEntry 4 }

adGenMgcpProfileCallAgentPrimaryUdp OBJECT-TYPE
   SYNTAX      Integer32 (0..65535)
   MAX-ACCESS  read-create
   STATUS      current
   DESCRIPTION
     "The primary MGCP Call-Agent's UDP port. This signifies which UDP port MGCP
      endpoints connected to this profile will transmit signalling packets to."
   DEFVAL      { 2727 }
   ::= { adGenMgcpProfileProvEntry 5 }

adGenMgcpProfileCallAgentSecondary OBJECT-TYPE
   SYNTAX      DisplayString
   MAX-ACCESS  read-create
   STATUS      current
   DESCRIPTION
     "The secondary MGCP Call-Agent's IP address or host name."
   ::= { adGenMgcpProfileProvEntry 6 }

adGenMgcpProfileCallAgentSecondaryUdp OBJECT-TYPE
   SYNTAX      Integer32 (0..65535)
   MAX-ACCESS  read-create
   STATUS      current
   DESCRIPTION
     "The secondary MGCP Call-Agent's UDP port. This signifies which UDP port MGCP
      endpoints connected to this profile will transmit signalling packets to."
   DEFVAL      { 2727 }
   ::= { adGenMgcpProfileProvEntry 7 }

adGenMgcpProfileShutdown OBJECT-TYPE
   SYNTAX      INTEGER {
                  noShutdown(1),
                  shutdown(2)
                  }
   MAX-ACCESS  read-create
   STATUS      current
   DESCRIPTION
     "Set to shutdown the MGCP Stack.
     Permitted values: No Shutdown (1),
     Shutdown (2)."
   DEFVAL     { noShutdown }
   ::= { adGenMgcpProfileProvEntry 8 }

adGenMgcpProfileBracketedIp OBJECT-TYPE
   SYNTAX      TruthValue
   MAX-ACCESS  read-create
   STATUS      current
   DESCRIPTION
     "Set to enable use of bracketed IP format.
     Permitted values: Bracketed IP Enabled = True(1),
     Bracketed IP Disabled = False (2)."
   DEFVAL      { true }
   ::= { adGenMgcpProfileProvEntry 9 }

adGenMgcpProfileStandard OBJECT-TYPE
   SYNTAX      INTEGER {
                  rfc3435(1),
                  ncs(2)
                  }
   MAX-ACCESS  read-create
   STATUS      current
   DESCRIPTION
     "Use to specify the MGCP standard adherence for the MGCP stack.
         1 = rfc3435    Specifies RFC 3435.
         2 = ncs        Specifies version 1.0."
   DEFVAL      { rfc3435 }
   ::= { adGenMgcpProfileProvEntry 10 }

adGenMgcpProfileMgcpDscp OBJECT-TYPE
   SYNTAX      Integer32 (0..63)
   MAX-ACCESS  read-create
   STATUS      current
   DESCRIPTION
     "Used to set the Differentiated Services Code Point in the IP header for
     the MGCP protocol messages. Valid values defined in RFC2474."
   DEFVAL      { 46 }
   ::= { adGenMgcpProfileProvEntry 11 }

adGenMgcpProfileRtpDscp OBJECT-TYPE
   SYNTAX      Integer32 (0..63)
   MAX-ACCESS  read-create
   STATUS      current
   DESCRIPTION
     "Used to set the Differentiated Services Code Point in the IP header for
     the RTP protocol messages. Valid values defined in RFC2474."
   DEFVAL      { 46 }
   ::= { adGenMgcpProfileProvEntry 12 }

adGenMgcpProfileGatewayUdp OBJECT-TYPE
   SYNTAX      Integer32 (0..65535)
   MAX-ACCESS  read-create
   STATUS      current
   DESCRIPTION
     "Used to configure the UDP port for MGCP signaling on the Gateway.
      This signifies which UDP port the call-agent is sending MGCP signalling
      packets to for MGCP Endpoints connected to this profile."
  DEFVAL      { 2427 }
  ::= { adGenMgcpProfileProvEntry 13 }

adGenMgcpProfileRtpUdpOffset OBJECT-TYPE
   SYNTAX      Integer32 (0..65535)
   MAX-ACCESS  read-create
   STATUS      current
   DESCRIPTION
     "Used to configure a global starting User Datagram Protocol (UDP) port for
      Realtime Transport Protocol (RTP)."
   DEFVAL      { 10000 }
   ::= { adGenMgcpProfileProvEntry 14 }

adGenMgcpProfilePersistentNotifyHangDown OBJECT-TYPE
   SYNTAX      INTEGER {
                  disabled(1),
                  enbled(2)
                  }
   MAX-ACCESS  read-create
   STATUS      current
   DESCRIPTION
     "Set to send a persistent notification to the Call Agent on hang down.
     Permitted values: Persistent Notify Hang Down Disabled = disabled(1),
     Persistent Notify Hang Down Enabled = enabled(2)."
   DEFVAL      { disabled }
   ::= { adGenMgcpProfileProvEntry 15 }

adGenMgcpProfilePersistentNotifyHangUp OBJECT-TYPE
   SYNTAX      INTEGER {
                  disabled(1),
                  enbled(2)
                  }
   MAX-ACCESS  read-create
   STATUS      current
   DESCRIPTION
     "Set to send a persistent notification to the Call Agent on hang Up.
     Permitted values: Persistent Notify Hang Up Disabled = disabled(1),
     Persistent Notify Hang Up Enabled = enabled(2)."
   DEFVAL      { disabled }
   ::= { adGenMgcpProfileProvEntry 16 }

adGenMgcpProfilePersistentNotifyHookFlash OBJECT-TYPE
   SYNTAX      INTEGER {
                  disabled(1),
                  enbled(2)
                  }
   MAX-ACCESS  read-create
   STATUS      current
   DESCRIPTION
     "Set to send a persistent notification to the Call Agent on hookflash.
     Permitted values: Persistent Notify HookFlash Disabled = disabled(1),
     Persistent Notify HookFlash Enabled = enabled(2)."
   DEFVAL      { disabled }
   ::= { adGenMgcpProfileProvEntry 17 }

adGenMgcpProfileRetransmitDelay OBJECT-TYPE
   SYNTAX      INTEGER {
                  exponentialBackoff(1),
                  ms100(2),
                  ms250(3),
                  ms500(4),
                  sec1(5),
                  sec2(6),
                  sec4(7)
                  }
   MAX-ACCESS  read-create
   STATUS      current
   DESCRIPTION
     "The retransmit delay for MGCP signaling messages."
   DEFVAL      { exponentialBackoff }
   ::= { adGenMgcpProfileProvEntry 18 }

adGenMgcpProfileMax1 OBJECT-TYPE
   SYNTAX       Integer32 (1..255)
   MAX-ACCESS   read-create
   STATUS       current
   DESCRIPTION
     "The number of retries on expiry of max1 timer."
   DEFVAL       { 5 }
   ::= { adGenMgcpProfileProvEntry 19 }

adGenMgcpProfileMax2 OBJECT-TYPE
   SYNTAX       Integer32 (1..255)
   MAX-ACCESS   read-create
   STATUS       current
   DESCRIPTION
     "The number of retries on expiry of max2 timer."
   DEFVAL       { 7 }
   ::= { adGenMgcpProfileProvEntry 20 }

adGenMgcpProfileLocalDomainType OBJECT-TYPE
   SYNTAX      INTEGER {
                  mediaGateway(1),
                  userDefined(2)
                  }
   MAX-ACCESS  read-create
   STATUS      current
   DESCRIPTION
     "This indicates whether we are using the pre-configured Media Gateway
      as the domain address or we are using a manually defined value.
         1 = media-gateway    Use configured Media Gateway as domain.
         2 = user-defined     Use user-configured domain name."
   DEFVAL      { mediaGateway }
   ::= { adGenMgcpProfileProvEntry 21 }

adGenMgcpProfileLocalDomainAddress OBJECT-TYPE
   SYNTAX      DisplayString (SIZE(1..80))
   MAX-ACCESS  read-create
   STATUS      current
   DESCRIPTION
     "Configure the assigned domain address for host messages."
   ::= { adGenMgcpProfileProvEntry 22 }

adGenMgcpProfileTerminationIdBase OBJECT-TYPE
   SYNTAX      DisplayString (SIZE(1..25))
   MAX-ACCESS  read-create
   STATUS      current
   DESCRIPTION
      "This is the base for the MGCP name that is used on the MGCP switch.
       Ex.
         Termination Base Id is 'aaln/'.
         Mgcp Endpoint 1/1/24 is connected to this profile.
         The MGCP name used by endpoint 1/1/24 will be 'aaln/24'."
   DEFVAL      { "aaln/" }
   ::= { adGenMgcpProfileProvEntry 23 }

adGenMgcpProfileRFC2833Signaling OBJECT-TYPE
   SYNTAX      INTEGER {
                  disabled(1),
                  enbled(2)
                  }
   MAX-ACCESS  read-create
   STATUS      current
   DESCRIPTION
     "Enable or disable the rfc2833 signaling.
     Permitted values: RFC2833 signaling Disabled = disabled(1),
     RFC2833 signaling Enabled = enabled(2)."
   DEFVAL      { disabled }
   ::= { adGenMgcpProfileProvEntry 24 }

--******************************************************************************
-- This table is for MGCP Endpoint provisioning.
--******************************************************************************

adGenMgcpEndpointProvCurrentNumber OBJECT-TYPE
   SYNTAX      Integer32
   MAX-ACCESS  read-only
   STATUS      current
   DESCRIPTION
     "Current number of MGCP endpoints configured on entire shelf."
   ::= { adGenMgcpEndpointProv 1 }

adGenMgcpEndpointProvLastCreateError OBJECT-TYPE
   SYNTAX      DisplayString
   MAX-ACCESS  read-only
   STATUS      current
   DESCRIPTION
     "The reason for the last error that occured while attempting to create
      an entry in the MGCP endpoint provisioning table
      (adGenMgcpEndpointProvTable)."
   ::= { adGenMgcpEndpointProv 2 }

adGenMgcpEndpointProvTable OBJECT-TYPE
   SYNTAX      SEQUENCE OF AdGenMgcpEndpointProvEntry
   MAX-ACCESS  not-accessible
   STATUS      current
   DESCRIPTION
     "This table supports provisioning of MGCP user parameters for the
      MGCP client."
   ::= { adGenMgcpEndpointProv 3 }

adGenMgcpEndpointProvEntry OBJECT-TYPE
   SYNTAX      AdGenMgcpEndpointProvEntry
   MAX-ACCESS  not-accessible
   STATUS      current
   DESCRIPTION
     "An entry in the adGenMgcpEndpointProvTable."
   INDEX { adGenMgcpEndpointEntryIndex }
   ::= { adGenMgcpEndpointProvTable 1 }

AdGenMgcpEndpointProvEntry ::=
   SEQUENCE
   {
      adGenMgcpEndpointEntryIndex                   InterfaceIndexOrZero,
      adGenMgcpEndpointRowStatus                    RowStatus,
      adGenMgcpEndpointLastErrorString              DisplayString,

      adGenMgcpEndpointFxsPort                      InterfaceIndexOrZero,
      adGenMgcpEndpointMgcpProfile                  AdGenMgcpProfileName,
      adGenMgcpEndpointBlockCallerId                TruthValue,
      adGenMgcpEndpointDescription                  DisplayString,
      adGenMgcpEndpointDisplayString                DisplayString,
      adGenMgcpEndpointFwdDisconnect                INTEGER,
      adGenMgcpEndpointMediaProfile                 AdGenVoipMediaProfileName,
      adGenMgcpEndpointCodecListProfile             AdGenVoipCodecProfileName
   }

adGenMgcpEndpointEntryIndex OBJECT-TYPE
   SYNTAX      InterfaceIndexOrZero
   MAX-ACCESS  not-accessible
   STATUS      current
   DESCRIPTION
     "The MGCP endpoint index."
   ::= { adGenMgcpEndpointProvEntry 1 }

adGenMgcpEndpointRowStatus OBJECT-TYPE
   SYNTAX      RowStatus
   MAX-ACCESS  read-create
   STATUS      current
   DESCRIPTION
     "This object is used to create a new row or modify or delete an existing
      row in this table."
   ::= { adGenMgcpEndpointProvEntry 2 }

adGenMgcpEndpointLastErrorString OBJECT-TYPE
   SYNTAX      DisplayString
   MAX-ACCESS  read-only
   STATUS      current
   DESCRIPTION
     "The reason for the last error that occured while attempting to create an
      entry in the MGCP endpoint prov Table."
   ::= { adGenMgcpEndpointProvEntry 3 }


adGenMgcpEndpointFxsPort OBJECT-TYPE
   SYNTAX      InterfaceIndexOrZero
   MAX-ACCESS  read-create
   STATUS      current
   DESCRIPTION
     "The ifIndex of the FXS port which you want to connect to this MGCP Endpoint.
      This FXS port must be on the same device as the MGCP Endpoint.
      To 'disconnect' a user from its existing FXS port, write a value of '0'."
   DEFVAL      { 0 }
   ::= { adGenMgcpEndpointProvEntry 4 }

adGenMgcpEndpointMgcpProfile OBJECT-TYPE
   SYNTAX      AdGenMgcpProfileName
   MAX-ACCESS  read-create
   STATUS      current
   DESCRIPTION
     "The index of the MGCP profile class associated with the user."
   ::= { adGenMgcpEndpointProvEntry 5 }

adGenMgcpEndpointBlockCallerId OBJECT-TYPE
   SYNTAX      TruthValue
   MAX-ACCESS  read-create
   STATUS      current
   DESCRIPTION
     "Set to block incoming caller-id.
     Permitted values: Block Caller Id Disabled for user = True(1),
     Block Caller Id Enabled for user = False (2)."
   DEFVAL       { true }
   ::= { adGenMgcpEndpointProvEntry 6 }

adGenMgcpEndpointDescription OBJECT-TYPE
   SYNTAX      DisplayString (SIZE (0..80))
   MAX-ACCESS  read-create
   STATUS      current
   DESCRIPTION
     "An optional description of the MGCP endpoint."
   ::= { adGenMgcpEndpointProvEntry 7 }

adGenMgcpEndpointDisplayString OBJECT-TYPE
   SYNTAX      DisplayString (SIZE (0..40))
   MAX-ACCESS  read-only
   STATUS      current
   DESCRIPTION
     "An Adtran CLI String representation of the current MGCP Endpoint."
   ::= { adGenMgcpEndpointProvEntry 8 }

adGenMgcpEndpointFwdDisconnect OBJECT-TYPE
   SYNTAX      INTEGER {
                  delay250(1),
                  delay500(2),
                  delay750(3),
                  delay900(4),
                  delay1000(5),
                  delay2000(6)
                  }
   UNITS       "milliseconds"
   MAX-ACCESS  read-create
   STATUS      current
   DESCRIPTION
     "Specifies number of milliseconds the FXS module waits, after initiating a
     disconnect sequence caused by the remote end terminating the call, before
     returning to an idle condition."
   DEFVAL       { delay2000 }
   ::= { adGenMgcpEndpointProvEntry 9 }

   adGenMgcpEndpointMediaProfile  OBJECT-TYPE
   	SYNTAX		AdGenVoipMediaProfileName
   	MAX-ACCESS	read-create
   	STATUS		current
   	DESCRIPTION
   		"Sets the media profile for this user"
   	::= { adGenMgcpEndpointProvEntry 10 }

   adGenMgcpEndpointCodecListProfile  OBJECT-TYPE
   	SYNTAX		AdGenVoipCodecProfileName
   	MAX-ACCESS	read-create
   	STATUS		current
   	DESCRIPTION
   		"Sets the codec list for this user"
   	::= { adGenMgcpEndpointProvEntry 11 }

--******************************************************************************
-- This table is for MGCP Endpoint status.
--******************************************************************************

adGenMgcpEndpointStatusTable OBJECT-TYPE
   SYNTAX      SEQUENCE OF AdGenMgcpEndpointStatusEntry
   MAX-ACCESS  not-accessible
   STATUS      current
   DESCRIPTION
     "This table gives MGCP Endpoint status information for the MGCP client."
   ::= { adGenMgcpEndpointStatus 1 }

adGenMgcpEndpointStatusEntry OBJECT-TYPE
   SYNTAX      AdGenMgcpEndpointStatusEntry
   MAX-ACCESS  not-accessible
   STATUS      current
   DESCRIPTION
     "An entry in the adGenMgcpEndpointStatusTable.
      1) ifIndex: This is the the slot ifIndex for these MGCP Endpoints
      2) adGenMgcpEndpointEntryIndex: The Endpoint Id string"
   INDEX { ifIndex, adGenMgcpEndpointStatusEntryIndex }
   ::= { adGenMgcpEndpointStatusTable 1 }

AdGenMgcpEndpointStatusEntry ::=
   SEQUENCE
   {
      adGenMgcpEndpointStatusEntryIndex                   InterfaceIndexOrZero,
      adGenMgcpEndpointStatusFXSPort                      InterfaceIndexOrZero,
      adGenMgcpEndpointStatusName                         DisplayString,
      adGenMgcpEndpointStatusConnectedProfile             DisplayString,
      adGenMgcpEndpointStatusState                        INTEGER,
      adGenMgcpEndpointStatusStateDetail                  DisplayString,
      adGenMgcpEndpointOperStatus                         INTEGER,
      adGenMgcpEndpointStatusCodecInUse                   AdGenVoipCodecProfileType,
      adGenMgcpEndpointLastError                          DisplayString
   }

adGenMgcpEndpointStatusEntryIndex OBJECT-TYPE
   SYNTAX      InterfaceIndexOrZero
   MAX-ACCESS  not-accessible
   STATUS      current
   DESCRIPTION
     "The MGCP endpoint index."
   ::= { adGenMgcpEndpointStatusEntry 1 }

adGenMgcpEndpointStatusFXSPort OBJECT-TYPE
   SYNTAX      InterfaceIndexOrZero
   MAX-ACCESS  read-only
   STATUS      current
   DESCRIPTION
     "The ifIndex for the FXS port currently connected to this MGCP Endpoint,
      or 0 if none is connected currently. This FXS must be located on the same
      device as the Endpoint, as is seen in the Endpoint Id Index."
   ::= { adGenMgcpEndpointStatusEntry 2 }

adGenMgcpEndpointStatusName OBJECT-TYPE
   SYNTAX      DisplayString
   MAX-ACCESS  read-only
   STATUS      current
   DESCRIPTION
     "The full MGCP Endpoint name that is used on the MGCP switch. This read-only
      value is the combination of the termination id base from the connected MGCP
      Profile and MGCP Endpoint Id from this Endpoint.
      Ex.
         Termination Id Base in the connected profile is 'aaln/'.
         This is Mgcp Endpoint 1/1/24.
         The MGCP name used by endpoint 1/1/24 will be 'aaln/24'."
   ::= { adGenMgcpEndpointStatusEntry 3 }

adGenMgcpEndpointStatusConnectedProfile OBJECT-TYPE
   SYNTAX      DisplayString
   MAX-ACCESS  read-only
   STATUS      current
   DESCRIPTION
     "The name of the MGCP Profile to which this MGCP Endpoint is connected."
   ::= { adGenMgcpEndpointStatusEntry 4 }

adGenMgcpEndpointStatusState OBJECT-TYPE
   SYNTAX      INTEGER {
                  connected(1),
                  disconnected(2),
                  reconnecting(3),
                  connectedNoRqnt(4)
                  }
   MAX-ACCESS  read-only
   STATUS      current
   DESCRIPTION
     "The primary state of this MGCP Endpoint."
   ::= { adGenMgcpEndpointStatusEntry 5 }

adGenMgcpEndpointStatusStateDetail OBJECT-TYPE
   SYNTAX      DisplayString
   MAX-ACCESS  read-only
   STATUS      current
   DESCRIPTION
     "A string that indicates the detailed connection status of this MGCP endpoint \
      with regards to the MGCP switch."
   ::= { adGenMgcpEndpointStatusEntry 6 }

   adGenMgcpEndpointOperStatus OBJECT-TYPE
   	SYNTAX		INTEGER {
				up(1),        -- ready to pass packets
				down(2),
				testing(3),   -- in some test mode
				unknown(4)    -- status can not be determined
				}
   	MAX-ACCESS	read-only
   	STATUS		current
   	DESCRIPTION
   		"The current operational state of the MGCP endpoint."
   	::= { adGenMgcpEndpointStatusEntry 7 }

   adGenMgcpEndpointStatusCodecInUse OBJECT-TYPE
   	SYNTAX		AdGenVoipCodecProfileType
   	MAX-ACCESS	read-only
   	STATUS		current
   	DESCRIPTION
   		"The current codec in use."
   	::= { adGenMgcpEndpointStatusEntry 8 }

   adGenMgcpEndpointLastError  OBJECT-TYPE
   	SYNTAX		DisplayString
   	MAX-ACCESS	read-only
   	STATUS		current
   	DESCRIPTION
   		"The reason for the last error that occurred while attempting to modify
         an attribute in the current entry or change in the current running state."
   	::= { adGenMgcpEndpointStatusEntry 9 }

   --******************************************************************************
-- This table is for MGCP Actions.
--******************************************************************************

adGenMgcpActionsTable OBJECT-TYPE
   SYNTAX      SEQUENCE OF AdGenMgcpActionsEntry
   MAX-ACCESS  not-accessible
   STATUS      current
   DESCRIPTION
     "This table gives MGCP Endpoint status information for the MGCP client."
   ::= { adGenMgcpActions 1 }

adGenMgcpActionsEntry OBJECT-TYPE
   SYNTAX      AdGenMgcpActionsEntry
   MAX-ACCESS  not-accessible
   STATUS      current
   DESCRIPTION
     "An entry in the adGenMgcpActionsTable.
      1) ifIndex: This is the the slot ifIndex for a module in MGCP mode"
   INDEX { ifIndex }
   ::= { adGenMgcpActionsTable 1 }

AdGenMgcpActionsEntry ::=
   SEQUENCE
   {
      adGenMgcpActionsLastError       DisplayString,
      adGenMgcpActionsRestart         INTEGER
   }

adGenMgcpActionsLastError OBJECT-TYPE
   SYNTAX      DisplayString
   MAX-ACCESS  read-only
   STATUS      current
   DESCRIPTION
     "The reason for the last error that occured while attempting to force an
      action in the MGCP Actions Table."
   ::= { adGenMgcpActionsEntry 1 }

adGenMgcpActionsRestart OBJECT-TYPE
   SYNTAX      INTEGER {
                       restart(1)
                       }
   MAX-ACCESS  read-write
   STATUS      current
   DESCRIPTION
     "A set command will force all MGCP endpoints on this module to attempt
      a reconnection with the MGCP Media Gateway Controller. Get has no meaning
      and will always return restart (1)."
   ::= { adGenMgcpActionsEntry 2 }



END
