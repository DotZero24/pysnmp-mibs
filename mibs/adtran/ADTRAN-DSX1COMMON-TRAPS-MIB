ADTRAN-DSX1COMMON-TRAPS-MIB

DEFINITIONS ::= BEGIN

--  TITLE:   	THE ADTRAN GENERIC DSX TRAPS EXTENTION MIB
--  AUTHOR:		Kevin Welsch
--  PRODUCTS: 	Adtran Products with DSX and SLC 96 interfaces

--  VERSION:    3.0
--  DATE:       06/07/2004

--  DESCRIPTION
--  This is an extention mib to the generic DSX MIB for all variations of
--  Adtran DXS interface equipment.  The purpose of this MIB is to
--  supply generic DSX and SLC 96 interface traps that could not be
--  put into the original DSX common MIB due to Trap numbering constraints.

--  This MIB will be used in Conjunction with the standard DSX interface MIB,
--  RFC 1406.

--  HISTORY
--  11/13/01    first draft
--  01/25/02    MIB released - Version A01
--  04/16/02	added traps 1002948 to 1002961 to support loopback traps
--				and timing source OOS traps
--  12/16/02    MIB released - Version A.02
--  04/16/03    added traps 1002962 to 1002973
--  05/06/04    combined PHTL1 and PHTL2 into PHTL, combined ATB1 and ATB2
--              into ATB, and adjusted alarm numbers as necessary to keep
--              them sequential
--  06/07/04  standardize version numbering and set to 3.0
--  06/29/06  Phil B: corrected trap subsyntax errors for HP OV.
--  10/02/07  Converted to SMIv2.
--  12/14/07  Removed the adDSX1CommonTrapsPrefix node.
--  05/20/08  jlb - Changed dsx1loopbackcondition severity to WARNING
--  11/21/08  glf - Adding enhanced DSX1 Traps that contain the Alarm Level Varbind


    IMPORTS
        MODULE-IDENTITY,
        NOTIFICATION-TYPE
            FROM SNMPv2-SMI
        NOTIFICATION-GROUP
            FROM SNMPv2-CONF
        sysName
            FROM SNMPv2-MIB
    	adTrapInformSeqNum
            FROM ADTRAN-GENTRAPINFORM-MIB
        adIdentityShared,
	adShared
	    FROM ADTRAN-MIB
        ifIndex
            FROM IF-MIB
	adGenSlotInfoIndex,
	adGenSlotAlarmStatus
	    FROM ADTRAN-GENSLOT-MIB
    	adGenPortTrapIdentifier
	    FROM ADTRAN-GENPORT-MIB
     adTAeSCUTrapAlarmLevel
        FROM ADTRAN-TAeSCUEXT1-MIB;


adDSX1commonTrapsModuleIdentity MODULE-IDENTITY
   LAST-UPDATED "201402280000Z"
   ORGANIZATION "Adtran, Inc."
   CONTACT-INFO "http://www.adtran.com"
   DESCRIPTION
      "This MIB defines additional Adtran DSX generic interface traps."

   REVISION "201402280000Z"
   DESCRIPTION "Removed unneeded imports.
                Added dsx1SAalmLOSRemoteClear, dsx1SAalmLOSRemoteActive,
                dsx1SAalmLOFRemoteClear, dsx1SAalmLOFRemoteActive,
                dsx1SAalmAISRemoteClear, dsx1SAalmAISRemoteActive,
                dsx1NSAalmRAIRemoteClear, and dsx1SAalmNRAIRemoteActive."

   REVISION "200710020000Z"
   DESCRIPTION "Created"
::= { adIdentityShared 29 }

--  OBJECT IDENTIFIERS

	adDSX1CommonTraps  		OBJECT IDENTIFIER ::= { adShared 29 }

    	adDSX1CommonAlmTraps		OBJECT IDENTIFIER ::= {adDSX1CommonTraps 0}

	adDSX1CommonTrapsMibConformance OBJECT IDENTIFIER ::= { adDSX1CommonTraps 2 }
    	adDSX1CommonTrapsMibGroups	OBJECT IDENTIFIER ::= { adDSX1CommonTrapsMibConformance 1 }


	--  Generic DSX and SLC traps

    --  As of 12/13/01, this trap is not currently used, we have
    --   left it in for future considerations.
      dsx1almcondition  NOTIFICATION-TYPE
	    OBJECTS	{
	        adTrapInformSeqNum,
	        sysName,
	        adGenSlotInfoIndex,
	        adGenPortTrapIdentifier,
	        adGenSlotAlarmStatus
	        }
	    STATUS          current
	    DESCRIPTION
	    	"Indicates a change in the
	    	 alarm condition."
	    --#TYPE			"Status - Change in Alarm Condition"
        --#SUMMARY          "DSXcommonTraps 1002901: Change in Alarm Condition"
	    --#SUMMARY  	"shelf: %s, slot: %d, %s"
	    --#ARGUMENTS 	{1,2,3}
	    --#SEVERITY 	MINOR
	    --#GENERIC  	6
	    --#CATEGORY  	"Status events"
	    --#Source_ID    "A"
	    --#TIMEINDEX    0
    	    ::= {adDSX1CommonAlmTraps 1002901}


   dsx1SAalmLOSClear  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates LOS SA Alarm Clear"
        --#TYPE         "Status - LOS SA Alarm Clear"
        --#SUMMARY      "DSXcommonTraps 1002902: LOS SA Alarm Clear"
	    --#SUMMARY  	"shelf: %s, slot: %d, %s"
	    --#ARGUMENTS 	{1,2,3}
	    --#SEVERITY 	MAJOR
	    --#GENERIC  	6
	    --#CATEGORY  	"Status events"
	    --#Source_ID    "A"
	    --#TIMEINDEX    0
    	    ::= {adDSX1CommonAlmTraps 1002902}

    dsx1SAalmLOSActive  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates LOS SA Alarm Active"
        --#TYPE         "Status - LOS SA Alarm Active"
        --#SUMMARY      "DSXcommonTraps 1002903: LOS SA Alarm Active"
	    --#SUMMARY  	"shelf: %s, slot: %d, %s"
	    --#ARGUMENTS 	{1,2,3}
	    --#SEVERITY 	MAJOR
	    --#GENERIC  	6
	    --#CATEGORY  	"Status events"
	    --#Source_ID    "A"
	    --#TIMEINDEX    0
    	    ::= {adDSX1CommonAlmTraps 1002903}

    dsx1SAalmLOFClear  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates LOF SA Alarm Clear"
        --#TYPE         "Status - LOF SA Alarm Clear"
        --#SUMMARY      "DSXcommonTraps 1002904: LOF SA Alarm Clear"
	    --#SUMMARY  	"shelf: %s, slot: %d, %s"
	    --#ARGUMENTS 	{1,2,3}
	    --#SEVERITY 	MAJOR
	    --#GENERIC  	6
	    --#CATEGORY  	"Status events"
	    --#Source_ID    "A"
	    --#TIMEINDEX    0
    	    ::= {adDSX1CommonAlmTraps 1002904}

    dsx1SAalmLOFActive  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates LOF SA Alarm Active"
        --#TYPE         "Status - LOF SA Alarm Active"
        --#SUMMARY      "DSXcommonTraps 1002905: LOF SA Alarm Active"
	    --#SUMMARY  	"shelf: %s, slot: %d, %s"
	    --#ARGUMENTS 	{1,2,3}
	    --#SEVERITY 	MAJOR
	    --#GENERIC  	6
	    --#CATEGORY  	"Status events"
	    --#Source_ID    "A"
	    --#TIMEINDEX    0
    	    ::= {adDSX1CommonAlmTraps 1002905}

    dsx1SAalmAISClear  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates AIS SA Alarm Clear"
        --#TYPE         "Status - AIS SA Alarm Clear"
        --#SUMMARY      "DSXcommonTraps 1002906: AIS SA Alarm Clear"
	    --#SUMMARY  	"shelf: %s, slot: %d, %s"
	    --#ARGUMENTS 	{1,2,3}
	    --#SEVERITY 	MAJOR
	    --#GENERIC  	6
	    --#CATEGORY  	"Status events"
	    --#Source_ID    "A"
	    --#TIMEINDEX    0
    	    ::= {adDSX1CommonAlmTraps 1002906}

    dsx1SAalmAISActive  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates AIS SA Alarm Active"
        --#TYPE         "Status - AIS SA Alarm Active"
        --#SUMMARY      "DSXcommonTraps 1002907: AIS SA Alarm Active"
	    --#SUMMARY  	"shelf: %s, slot: %d, %s"
	    --#ARGUMENTS 	{1,2,3}
	    --#SEVERITY 	MAJOR
	    --#GENERIC  	6
	    --#CATEGORY  	"Status events"
	    --#Source_ID    "A"
	    --#TIMEINDEX    0
    	    ::= {adDSX1CommonAlmTraps 1002907}

    dsx1SAalmRAIClear  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates RAI SA Alarm Clear"
        --#TYPE         "Status - RAI SA Alarm Clear"
        --#SUMMARY      "DSXcommonTraps 1002908: RAI SA Alarm Clear"
	    --#SUMMARY  	"shelf: %s, slot: %d, %s"
	    --#ARGUMENTS 	{1,2,3}
            --#SEVERITY         MINOR
	    --#GENERIC  	6
	    --#CATEGORY  	"Status events"
	    --#Source_ID    "A"
	    --#TIMEINDEX    0
    	    ::= {adDSX1CommonAlmTraps 1002908}

    dsx1SAalmRAIActive  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates RAI SA Alarm Active"
        --#TYPE         "Status - RAI SA Alarm Active"
        --#SUMMARY      "DSXcommonTraps 1002909: RAI SA Alarm Active"
	    --#SUMMARY  	"shelf: %s, slot: %d, %s"
	    --#ARGUMENTS 	{1,2,3}
            --#SEVERITY         MINOR
	    --#GENERIC  	6
	    --#CATEGORY  	"Status events"
	    --#Source_ID    "A"
	    --#TIMEINDEX    0
    	    ::= {adDSX1CommonAlmTraps 1002909}

	dsx1loopbackcondition  NOTIFICATION-TYPE
	    OBJECTS	{
	        adTrapInformSeqNum,
	        sysName,
	        adGenSlotInfoIndex,
	        adGenPortTrapIdentifier,
	        adGenSlotAlarmStatus
	        }
	    STATUS          current
	    DESCRIPTION
	    	"Indicates a change in
	    	 loopback condition."
	    --#TYPE			"Status - Change in Loopback Condition"
        --#SUMMARY      "DSXcommonTraps 1002911: Change in LoopBack Condition"
	    --#SUMMARY  	"shelf: %s, slot: %d, %s"
	    --#ARGUMENTS 	{1,2,3}
            --#SEVERITY         WARNING
	    --#GENERIC  	6
	    --#CATEGORY  	"Status events"
	    --#Source_ID    "A"
	    --#TIMEINDEX    0
    	    ::= {adDSX1CommonAlmTraps 1002911}

	dsx1NSAINFOFarShelfRFIClear  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates Far Shelf RFI
             NSA warning Clear"
        --#TYPE         "Status - Far Shelf RFI WARNING Clear"
        --#SUMMARY      "DSXcommonTraps 1002912: Far Shelf RFI WARNING Clear"
	    --#SUMMARY  	"shelf: %s, slot: %d, %s"
	    --#ARGUMENTS 	{1,2,3}
	    --#SEVERITY 	WARNING
	    --#GENERIC  	6
	    --#CATEGORY  	"Status events"
	    --#Source_ID    "A"
	    --#TIMEINDEX    0
    	    ::= {adDSX1CommonAlmTraps 1002912}

    dsx1NSAINFOFarShelfRFIActive  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates Far Shelf RFI
             NSA warning Active"
        --#TYPE         "Status - Far Shelf RFI WARNING Active"
        --#SUMMARY      "DSXcommonTraps 1002913: Far Shelf RFI WARNING Active"
	    --#SUMMARY  	"shelf: %s, slot: %d, %s"
	    --#ARGUMENTS 	{1,2,3}
	    --#SEVERITY 	WARNING
	    --#GENERIC  	6
	    --#CATEGORY  	"Status events"
	    --#Source_ID    "A"
	    --#TIMEINDEX    0
    	    ::= {adDSX1CommonAlmTraps 1002913}

     dsx1NSAINFODTLKFailINCClear  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates Data Link Fail, INC
             NSA warning Clear"
        --#TYPE         "Status - Data Link Fail, INC NSA WARNING Clear"
        --#SUMMARY      "DSXcommonTraps 1002914: Data Link Fail, INC NSA WARNING Clear"
	    --#SUMMARY  	"shelf: %s, slot: %d, %s"
	    --#ARGUMENTS 	{1,2,3}
	    --#SEVERITY 	WARNING
	    --#GENERIC  	6
	    --#CATEGORY  	"Status events"
	    --#Source_ID    "A"
	    --#TIMEINDEX    0
    	    ::= {adDSX1CommonAlmTraps 1002914}

    dsx1NSAINFODTLKFailINCActive  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates Data Link Fail, INC
             NSA warning Active"
        --#TYPE         "Status - Data Link Fail, INC NSA WARNING Active"
        --#SUMMARY      "DSXcommonTraps 1002915: Data Link Fail, INC NSA WARNING Active"
	    --#SUMMARY  	"shelf: %s, slot: %d, %s"
	    --#ARGUMENTS 	{1,2,3}
	    --#SEVERITY 	WARNING
	    --#GENERIC  	6
	    --#CATEGORY  	"Status events"
	    --#Source_ID    "A"
	    --#TIMEINDEX    0
    	    ::= {adDSX1CommonAlmTraps 1002915}

     dsx1SAalmBPVClear  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates BPV SA Alarm Clear"
        --#TYPE         "Status - BPV SA Alarm Clear"
        --#SUMMARY      "DSXcommonTraps 1002916: BPV SA Alarm Clear"
	    --#SUMMARY  	"shelf: %s, slot: %d, %s"
	    --#ARGUMENTS 	{1,2,3}
	    --#SEVERITY 	MAJOR
	    --#GENERIC  	6
	    --#CATEGORY  	"Status events"
	    --#Source_ID    "A"
	    --#TIMEINDEX    0
    	    ::= {adDSX1CommonAlmTraps 1002916}

    dsx1SAalmBPVActive  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates BPV SA Alarm Active"
        --#TYPE         "Status - BPV SA Alarm Active"
        --#SUMMARY      "DSXcommonTraps 1002917: BPV SA Alarm Active"
	    --#SUMMARY  	"shelf: %s, slot: %d, %s"
	    --#ARGUMENTS 	{1,2,3}
	    --#SEVERITY 	MAJOR
	    --#GENERIC  	6
	    --#CATEGORY  	"Status events"
	    --#Source_ID    "A"
	    --#TIMEINDEX    0
    	    ::= {adDSX1CommonAlmTraps 1002917}

     dsx1SAalmFarShelfRFIClear  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates Far Shelf RFI
             SA Alarm Clear"
        --#TYPE         "Status - Far Shelf RFI SA Alarm Clear"
        --#SUMMARY      "DSXcommonTraps 1002918: Far Shelf RFI SA Alarm Clear"
	    --#SUMMARY  	"shelf: %s, slot: %d, %s"
	    --#ARGUMENTS 	{1,2,3}
	    --#SEVERITY 	MAJOR
	    --#GENERIC  	6
	    --#CATEGORY  	"Status events"
	    --#Source_ID    "A"
	    --#TIMEINDEX    0
    	    ::= {adDSX1CommonAlmTraps 1002918}

    dsx1SAalmFarShelfRFIActive  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates Far Shelf RFI
             SA Alarm Active"
        --#TYPE         "Status - Far Shelf RFI SA Alarm Active"
        --#SUMMARY      "DSXcommonTraps 1002919: Far Shelf SA Alarm Alarm Active"
	    --#SUMMARY  	"shelf: %s, slot: %d, %s"
	    --#ARGUMENTS 	{1,2,3}
	    --#SEVERITY 	MAJOR
	    --#GENERIC  	6
	    --#CATEGORY  	"Status events"
	    --#Source_ID    "A"
	    --#TIMEINDEX    0
    	    ::= {adDSX1CommonAlmTraps 1002919}

     dsx1SAalmDTLKFailINCClear  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates Data Link Fail, INC
             SA Alarm Clear"
        --#TYPE         "Status - Data Link Fail, INC SA Alarm Clear"
        --#SUMMARY      "DSXcommonTraps 1002920: Data Link Fail, INC SA Alarm Clear"
	    --#SUMMARY  	"shelf: %s, slot: %d, %s"
	    --#ARGUMENTS 	{1,2,3}
	    --#SEVERITY 	MAJOR
	    --#GENERIC  	6
	    --#CATEGORY  	"Status events"
	    --#Source_ID    "A"
	    --#TIMEINDEX    0
    	    ::= {adDSX1CommonAlmTraps 1002920}

    dsx1SAalmDTLKFailINCActive  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates Data Link Fail, INC
             SA Alarm Active"
        --#TYPE         "Status - Data Link Fail, INC SA Alarm Active"
        --#SUMMARY      "DSXcommonTraps 1002921: Data Link Fail, INC SA Alarm Active"
	    --#SUMMARY  	"shelf: %s, slot: %d, %s"
	    --#ARGUMENTS 	{1,2,3}
	    --#SEVERITY 	MAJOR
	    --#GENERIC  	6
	    --#CATEGORY  	"Status events"
	    --#Source_ID    "A"
	    --#TIMEINDEX    0
    	    ::= {adDSX1CommonAlmTraps 1002921}

     dsx1NSAalmLOSClear  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates LOS NSA Alarm Clear"
        --#TYPE         "Status - LOS NSA Alarm Clear"
        --#SUMMARY      "DSXcommonTraps 1002922: LOS NSA Alarm Clear"
	    --#SUMMARY  	"shelf: %s, slot: %d, %s"
	    --#ARGUMENTS 	{1,2,3}
	    --#SEVERITY 	MINOR
	    --#GENERIC  	6
	    --#CATEGORY  	"Status events"
	    --#Source_ID    "A"
	    --#TIMEINDEX    0
    	    ::= {adDSX1CommonAlmTraps 1002922}

    dsx1NSAalmLOSActive  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates LOS NSA Alarm Active"
        --#TYPE         "Status - LOS NSA Alarm Active"
        --#SUMMARY      "DSXcommonTraps 1002923: LOS NSA Alarm Active"
	    --#SUMMARY  	"shelf: %s, slot: %d, %s"
	    --#ARGUMENTS 	{1,2,3}
	    --#SEVERITY 	MINOR
	    --#GENERIC  	6
	    --#CATEGORY  	"Status events"
	    --#Source_ID    "A"
	    --#TIMEINDEX    0
    	    ::= {adDSX1CommonAlmTraps 1002923}

    dsx1NSAalmLOFClear  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates LOF NSA Alarm Clear"
        --#TYPE         "Status - LOF NSA Alarm Clear"
        --#SUMMARY      "DSXcommonTraps 1002924: LOF NSA Alarm Clear"
	    --#SUMMARY  	"shelf: %s, slot: %d, %s"
	    --#ARGUMENTS 	{1,2,3}
	    --#SEVERITY 	MINOR
	    --#GENERIC  	6
	    --#CATEGORY  	"Status events"
	    --#Source_ID    "A"
	    --#TIMEINDEX    0
    	    ::= {adDSX1CommonAlmTraps 1002924}

    dsx1NSAalmLOFActive  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates LOF NSA Alarm Active"
        --#TYPE         "Status - LOF NSA Alarm Active"
        --#SUMMARY      "DSXcommonTraps 1002925: LOF NSA Alarm Active"
	    --#SUMMARY  	"shelf: %s, slot: %d, %s"
	    --#ARGUMENTS 	{1,2,3}
	    --#SEVERITY 	MINOR
	    --#GENERIC  	6
	    --#CATEGORY  	"Status events"
	    --#Source_ID    "A"
	    --#TIMEINDEX    0
    	    ::= {adDSX1CommonAlmTraps 1002925}

    dsx1NSAalmAISClear  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates AIS NSA Alarm Clear"
        --#TYPE         "Status - AIS Alarm Clear"
        --#SUMMARY      "DSXcommonTraps 1002926: AIS NSA Alarm Clear"
	    --#SUMMARY  	"shelf: %s, slot: %d, %s"
	    --#ARGUMENTS 	{1,2,3}
	    --#SEVERITY 	MINOR
	    --#GENERIC  	6
	    --#CATEGORY  	"Status events"
	    --#Source_ID    "A"
	    --#TIMEINDEX    0
    	    ::= {adDSX1CommonAlmTraps 1002926}

    dsx1NSAalmAISActive  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates AIS NSA Alarm Active"
        --#TYPE         "Status - AIS NSA Alarm Active"
        --#SUMMARY      "DSXcommonTraps 1002927: AIS NSA Alarm Active"
	    --#SUMMARY  	"shelf: %s, slot: %d, %s"
	    --#ARGUMENTS 	{1,2,3}
	    --#SEVERITY 	MINOR
	    --#GENERIC  	6
	    --#CATEGORY  	"Status events"
	    --#Source_ID    "A"
	    --#TIMEINDEX    0
    	    ::= {adDSX1CommonAlmTraps 1002927}

    dsx1NSAalmRAIClear  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates RAI NSA Alarm Clear"
        --#TYPE         "Status - RAI NSA Alarm Clear"
        --#SUMMARY      "DSXcommonTraps 1002928: RAI NSA Alarm Clear"
	    --#SUMMARY  	"shelf: %s, slot: %d, %s"
	    --#ARGUMENTS 	{1,2,3}
	    --#SEVERITY 	MINOR
	    --#GENERIC  	6
	    --#CATEGORY  	"Status events"
	    --#Source_ID    "A"
	    --#TIMEINDEX    0
    	    ::= {adDSX1CommonAlmTraps 1002928}

    dsx1NSAalmRAIActive  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates RAI NSA Alarm Active"
        --#TYPE         "Status - RAI NSA Alarm Active"
        --#SUMMARY      "DSXcommonTraps 1002929: RAI NSA Alarm Active"
	    --#SUMMARY  	"shelf: %s, slot: %d, %s"
	    --#ARGUMENTS 	{1,2,3}
	    --#SEVERITY 	MINOR
	    --#GENERIC  	6
	    --#CATEGORY  	"Status events"
	    --#Source_ID    "A"
	    --#TIMEINDEX    0
    	    ::= {adDSX1CommonAlmTraps 1002929}

    dsx1SAFarLoopLPBKDS1FEACClear  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates Far Shelf, DS1
             FEAC Loopback, SA Cleared"
        --#TYPE         "Status - Far Shelf, DS1 FEAC Loopback, SA Clear"
        --#SUMMARY      "DSXcommonTraps 1002932: Far Shelf, DS1 FEAC Loopback, SA Clear"
	    --#SUMMARY  	"shelf: %s, slot: %d, %s"
	    --#ARGUMENTS 	{1,2,3}
	    --#SEVERITY 	MINOR
	    --#GENERIC  	6
	    --#CATEGORY  	"Status events"
	    --#Source_ID    "A"
	    --#TIMEINDEX    0
    	    ::= {adDSX1CommonAlmTraps 1002932}

     dsx1SAFarLoopLPBKDS1FEACActive  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates Far Shelf, DS1
             FEAC Loopback, SA Active"
        --#TYPE         "Status - Far Shelf, DS1 FEAC Loopback, SA Active"
        --#SUMMARY      "DSXcommonTraps 1002933: Far Shelf, DS1 FEAC Loopback, SA Active"
	    --#SUMMARY  	"shelf: %s, slot: %d, %s"
	    --#ARGUMENTS 	{1,2,3}
	    --#SEVERITY 	MINOR
	    --#GENERIC  	6
	    --#CATEGORY  	"Status events"
	    --#Source_ID    "A"
	    --#TIMEINDEX    0
    	    ::= {adDSX1CommonAlmTraps 1002933}

     dsx1NSAalmBPVClear  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates BPV NSA Alarm Clear"
        --#TYPE         "Status - BPV NSA Alarm Clear"
        --#SUMMARY      "DSXcommonTraps 1002936: BPV NSA Alarm Clear"
	    --#SUMMARY  	"shelf: %s, slot: %d, %s"
	    --#ARGUMENTS 	{1,2,3}
	    --#SEVERITY 	MINOR
	    --#GENERIC  	6
	    --#CATEGORY  	"Status events"
	    --#Source_ID    "A"
	    --#TIMEINDEX    0
    	    ::= {adDSX1CommonAlmTraps 1002936}

    dsx1NSAalmBPVActive  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates BPV NSA Alarm Active"
        --#TYPE         "Status - BPV NSA Alarm Active"
        --#SUMMARY      "DSXcommonTraps 1002937: BPV NSA Alarm Active"
	    --#SUMMARY  	"shelf: %s, slot: %d, %s"
	    --#ARGUMENTS 	{1,2,3}
	    --#SEVERITY 	MINOR
	    --#GENERIC  	6
	    --#CATEGORY  	"Status events"
	    --#Source_ID    "A"
	    --#TIMEINDEX    0
    	    ::= {adDSX1CommonAlmTraps 1002937}

     dsx1NSAalmFarShelfRFIClear  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates Far Shelf RFI
             NSA Alarm Clear"
        --#TYPE         "Status - Far Shelf RFI NSA Alarm Clear"
        --#SUMMARY      "DSXcommonTraps 1002938: Far Shelf RFI NSA Alarm Clear"
	    --#SUMMARY  	"shelf: %s, slot: %d, %s"
	    --#ARGUMENTS 	{1,2,3}
	    --#SEVERITY 	MINOR
	    --#GENERIC  	6
	    --#CATEGORY  	"Status events"
	    --#Source_ID    "A"
	    --#TIMEINDEX    0
    	    ::= {adDSX1CommonAlmTraps 1002938}

    dsx1NSAalmFarShelfRFIActive  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates Far Shelf RFI
             NSA Alarm Active"
        --#TYPE         "Status - Far Shelf RFI NSA Alarm Active"
        --#SUMMARY      "DSXcommonTraps 1002939: Far Shelf NSA Alarm Alarm Active"
	    --#SUMMARY  	"shelf: %s, slot: %d, %s"
	    --#ARGUMENTS 	{1,2,3}
	    --#SEVERITY 	MINOR
	    --#GENERIC  	6
	    --#CATEGORY  	"Status events"
	    --#Source_ID    "A"
	    --#TIMEINDEX    0
    	    ::= {adDSX1CommonAlmTraps 1002939}

     dsx1NSAalmDTLKFailINCClear  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates Data Link Fail, INC
             NSA Alarm Clear"
        --#TYPE         "Status - Data Link Fail, INC NSA Alarm Clear"
        --#SUMMARY      "DSXcommonTraps 1002940: Data Link Fail, INC NSA Alarm Clear"
	    --#SUMMARY  	"shelf: %s, slot: %d, %s"
	    --#ARGUMENTS 	{1,2,3}
	    --#SEVERITY 	MINOR
	    --#GENERIC  	6
	    --#CATEGORY  	"Status events"
	    --#Source_ID    "A"
	    --#TIMEINDEX    0
    	    ::= {adDSX1CommonAlmTraps 1002940}

    dsx1NSAalmDTLKFailINCActive  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates Data Link Fail, INC
             NSA Alarm Active"
        --#TYPE         "Status - Data Link Fail, INC NSA Alarm Active"
        --#SUMMARY      "DSXcommonTraps 1002941: Data Link Fail, INC NSA Alarm Active"
	    --#SUMMARY  	"shelf: %s, slot: %d, %s"
	    --#ARGUMENTS 	{1,2,3}
	    --#SEVERITY 	MINOR
	    --#GENERIC  	6
	    --#CATEGORY  	"Status events"
	    --#Source_ID    "A"
	    --#TIMEINDEX    0
    	    ::= {adDSX1CommonAlmTraps 1002941}

    dsx1NSAT1WKSWPRClear  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates T1 Switch To
             Protect Clear"
        --#TYPE         "Status - T1 Switch To Protect Clear"
        --#SUMMARY      "DSXcommonTraps 1002942: T1 Switch To Protect Clear"
	    --#SUMMARY  	"shelf: %s, slot: %d, %s"
	    --#ARGUMENTS 	{1,2,3}
	    --#SEVERITY 	MINOR
	    --#GENERIC  	6
	    --#CATEGORY  	"Status events"
	    --#Source_ID    "A"
	    --#TIMEINDEX    0
    	    ::= {adDSX1CommonAlmTraps 1002942}

    dsx1NSAT1WKSWPRActive  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates T1 Switch To
             Protect Active"
        --#TYPE         "Status - T1 Switch To Protect Active"
        --#SUMMARY      "DSXcommonTraps 1002943: T1 Switch To Protect Active"
	    --#SUMMARY  	"shelf: %s, slot: %d, %s"
	    --#ARGUMENTS 	{1,2,3}
	    --#SEVERITY 	MINOR
	    --#GENERIC  	6
	    --#CATEGORY  	"Status events"
	    --#Source_ID    "A"
	    --#TIMEINDEX    0
    	    ::= {adDSX1CommonAlmTraps 1002943}

     dsx1NSAalmSYNCPRIClear  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates Primary Timing
             Source NSA Clear"
        --#TYPE         "Status - Primary Timing Source NSA Alarm Clear"
        --#SUMMARY      "DSXcommonTraps 1002944: Primary Timing Source NSA Alarm Clear"
	    --#SUMMARY  	"shelf: %s, slot: %d, %s"
	    --#ARGUMENTS 	{1,2,3}
	    --#SEVERITY 	MINOR
	    --#GENERIC  	6
	    --#CATEGORY  	"Status events"
	    --#Source_ID    "A"
	    --#TIMEINDEX    0
    	    ::= {adDSX1CommonAlmTraps 1002944}

    dsx1NSAalmSYNCPRIActive  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates Primary Timing
             Source NSA Active"
        --#TYPE         "Status - Primary Timing Source NSA Alarm Active"
        --#SUMMARY      "DSXcommonTraps 1002945: Primary Timing Source NSA Alarm Active"
	    --#SUMMARY  	"shelf: %s, slot: %d, %s"
	    --#ARGUMENTS 	{1,2,3}
	    --#SEVERITY 	MINOR
	    --#GENERIC  	6
	    --#CATEGORY  	"Status events"
	    --#Source_ID    "A"
	    --#TIMEINDEX    0
    	    ::= {adDSX1CommonAlmTraps 1002945}

     dsx1NSAalmSYNCSECClear  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates Secondary Timing
             Source NSA Clear"
        --#TYPE         "Status - Secondary Timing Source NSA Alarm Clear"
        --#SUMMARY      "DSXcommonTraps 1002946: Secondary Timing Source NSA Alarm Clear"
	    --#SUMMARY  	"shelf: %s, slot: %d, %s"
	    --#ARGUMENTS 	{1,2,3}
	    --#SEVERITY 	MINOR
	    --#GENERIC  	6
	    --#CATEGORY  	"Status events"
	    --#Source_ID    "A"
	    --#TIMEINDEX    0
    	    ::= {adDSX1CommonAlmTraps 1002946}

    dsx1NSAalmSYNCSECActive  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates Secondary Timing
             Source NSA Active"
        --#TYPE         "Status - Secondary Timing Source NSA Alarm Active"
        --#SUMMARY      "DSXcommonTraps 1002947: Secondary Timing Source NSA Alarm Active"
	    --#SUMMARY  	"shelf: %s, slot: %d, %s"
	    --#ARGUMENTS 	{1,2,3}
	    --#SEVERITY 	MINOR
	    --#GENERIC  	6
	    --#CATEGORY  	"Status events"
	    --#Source_ID    "A"
	    --#TIMEINDEX    0
    	    ::= {adDSX1CommonAlmTraps 1002947}

    dsx1SAalmLPBKLOCALClear  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates a SA local loopback
             has cleared"
        --#TYPE         "Status - SA Local Loopback Clear"
        --#SUMMARY      "DSXcommonTraps 1002948: SA Local Loopback Clear"
	    --#SUMMARY  	"shelf: %s, slot: %d, %s"
	    --#ARGUMENTS 	{1,2,3}
            --#SEVERITY         WARNING
	    --#GENERIC  	6
	    --#CATEGORY  	"Status events"
	    --#Source_ID    "A"
	    --#TIMEINDEX    0
    	    ::= {adDSX1CommonAlmTraps 1002948}

    dsx1SAalmLPBKLOCALActive  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates a SA local loopback
             is active"
        --#TYPE         "Status - SA Local Loopback Active"
        --#SUMMARY      "DSXcommonTraps 1002949: SA Local Loopback Active"
	    --#SUMMARY  	"shelf: %s, slot: %d, %s"
	    --#ARGUMENTS 	{1,2,3}
            --#SEVERITY         WARNING
	    --#GENERIC  	6
	    --#CATEGORY  	"Status events"
	    --#Source_ID    "A"
	    --#TIMEINDEX    0
    	    ::= {adDSX1CommonAlmTraps 1002949}

    dsx1SAalmLPBKLINEClear  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates a SA line loopback
             has cleared"
        --#TYPE         "Status - SA Line Loopback Clear"
        --#SUMMARY      "DSXcommonTraps 1002950: SA Line Loopback Clear"
	    --#SUMMARY  	"shelf: %s, slot: %d, %s"
	    --#ARGUMENTS 	{1,2,3}
	    --#SEVERITY 	MAJOR
	    --#GENERIC  	6
	    --#CATEGORY  	"Status events"
	    --#Source_ID    "A"
	    --#TIMEINDEX    0
    	    ::= {adDSX1CommonAlmTraps 1002950}

    dsx1SAalmLPBKLINEActive  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates a SA line loopback
             is active"
        --#TYPE         "Status - SA Line Loopback Active"
        --#SUMMARY      "DSXcommonTraps 1002951: SA Line Loopback Active"
	    --#SUMMARY  	"shelf: %s, slot: %d, %s"
	    --#ARGUMENTS 	{1,2,3}
	    --#SEVERITY 	MAJOR
	    --#GENERIC  	6
	    --#CATEGORY  	"Status events"
	    --#Source_ID    "A"
	    --#TIMEINDEX    0
    	    ::= {adDSX1CommonAlmTraps 1002951}

    dsx1SAalmLPBKPAYLOADClear  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates a SA payload loopback
             has cleared"
        --#TYPE         "Status - SA Payload Loopback Clear"
        --#SUMMARY      "DSXcommonTraps 1002952: SA Payload Loopback Clear"
	    --#SUMMARY  	"shelf: %s, slot: %d, %s"
	    --#ARGUMENTS 	{1,2,3}
	    --#SEVERITY 	MAJOR
	    --#GENERIC  	6
	    --#CATEGORY  	"Status events"
	    --#Source_ID    "A"
	    --#TIMEINDEX    0
    	    ::= {adDSX1CommonAlmTraps 1002952}

    dsx1SAalmLPBKPAYLOADActive  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates a SA payload loopback
             is active"
        --#TYPE         "Status - SA Payload Loopback Active"
        --#SUMMARY      "DSXcommonTraps 1002953: SA Payload Loopback Active"
	    --#SUMMARY  	"shelf: %s, slot: %d, %s"
	    --#ARGUMENTS 	{1,2,3}
	    --#SEVERITY 	MAJOR
	    --#GENERIC  	6
	    --#CATEGORY  	"Status events"
	    --#Source_ID    "A"
	    --#TIMEINDEX    0
    	    ::= {adDSX1CommonAlmTraps 1002953}

    dsx1NSAalmLPBKLOCALClear  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates a NSA local loopback
             has cleared"
        --#TYPE         "Status - NSA Local Loopback Clear"
        --#SUMMARY      "DSXcommonTraps 1002954: NSA Local Loopback Clear"
	    --#SUMMARY  	"shelf: %s, slot: %d, %s"
	    --#ARGUMENTS 	{1,2,3}
	    --#SEVERITY 	MINOR
	    --#GENERIC  	6
	    --#CATEGORY  	"Status events"
	    --#Source_ID    "A"
	    --#TIMEINDEX    0
    	    ::= {adDSX1CommonAlmTraps 1002954}

    dsx1NSAalmLPBKLOCALActive  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates a NSA local loopback
             is active"
        --#TYPE         "Status - NSA Local Loopback Active"
        --#SUMMARY      "DSXcommonTraps 1002955: NSA Local Loopback Active"
	    --#SUMMARY  	"shelf: %s, slot: %d, %s"
	    --#ARGUMENTS 	{1,2,3}
	    --#SEVERITY 	MINOR
	    --#GENERIC  	6
	    --#CATEGORY  	"Status events"
	    --#Source_ID    "A"
	    --#TIMEINDEX    0
    	    ::= {adDSX1CommonAlmTraps 1002955}

    dsx1NSAalmLPBKLINEClear  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates a NSA line loopback
             has cleared"
        --#TYPE         "Status - NSA Line Loopback Clear"
        --#SUMMARY      "DSXcommonTraps 1002956: NSA Line Loopback Clear"
	    --#SUMMARY  	"shelf: %s, slot: %d, %s"
	    --#ARGUMENTS 	{1,2,3}
	    --#SEVERITY 	MINOR
	    --#GENERIC  	6
	    --#CATEGORY  	"Status events"
	    --#Source_ID    "A"
	    --#TIMEINDEX    0
    	    ::= {adDSX1CommonAlmTraps 1002956}

    dsx1NSAalmLPBKLINEActive  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates a NSA line loopback
             is active"
        --#TYPE         "Status - NSA Line Loopback Active"
        --#SUMMARY      "DSXcommonTraps 1002957: NSA Line Loopback Active"
	    --#SUMMARY  	"shelf: %s, slot: %d, %s"
	    --#ARGUMENTS 	{1,2,3}
	    --#SEVERITY 	MINOR
	    --#GENERIC  	6
	    --#CATEGORY  	"Status events"
	    --#Source_ID    "A"
	    --#TIMEINDEX    0
    	    ::= {adDSX1CommonAlmTraps 1002957}

    dsx1NSAalmLPBKPAYLOADClear  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates a NSA payload loopback
             has cleared"
        --#TYPE         "Status - NSA Payload Loopback Clear"
        --#SUMMARY      "DSXcommonTraps 1002958: NSA Payload Loopback Clear"
	    --#SUMMARY  	"shelf: %s, slot: %d, %s"
	    --#ARGUMENTS 	{1,2,3}
	    --#SEVERITY 	MINOR
	    --#GENERIC  	6
	    --#CATEGORY  	"Status events"
	    --#Source_ID    "A"
	    --#TIMEINDEX    0
    	    ::= {adDSX1CommonAlmTraps 1002958}

    dsx1NSAalmLPBKPAYLOADActive  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates a NSA payload loopback
             is active"
        --#TYPE         "Status - NSA Payload Loopback Active"
        --#SUMMARY      "DSXcommonTraps 1002959: NSA Payload Loopback Active"
	    --#SUMMARY  	"shelf: %s, slot: %d, %s"
	    --#ARGUMENTS 	{1,2,3}
	    --#SEVERITY 	MINOR
	    --#GENERIC  	6
	    --#CATEGORY  	"Status events"
	    --#Source_ID    "A"
	    --#TIMEINDEX    0
    	    ::= {adDSX1CommonAlmTraps 1002959}

    dsx1SAalmSYNCOOSClear  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates the timing source
             OOS SA condition cleared"
        --#TYPE         "Status - SA Timing Src OOS Clear"
        --#SUMMARY      "DSXcommonTraps 1002960: SA Timing Src OOS Clear"
	    --#SUMMARY  	"shelf: %s, slot: %d, %s"
	    --#ARGUMENTS 	{1,2,3}
	    --#SEVERITY 	MAJOR
	    --#GENERIC  	6
	    --#CATEGORY  	"Status events"
	    --#Source_ID    "A"
	    --#TIMEINDEX    0
    	    ::= {adDSX1CommonAlmTraps 1002960}

    dsx1SAalmSYNCOOSActive  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates a timing source
             OOS SA condition is active"
        --#TYPE         "Status - SA Timing Src OOS Active"
        --#SUMMARY      "DSXcommonTraps 1002961: SA Timing Src OOS Active"
	    --#SUMMARY  	"shelf: %s, slot: %d, %s"
	    --#ARGUMENTS 	{1,2,3}
	    --#SEVERITY 	MAJOR
	    --#GENERIC  	6
	    --#CATEGORY  	"Status events"
	    --#Source_ID    "A"
	    --#TIMEINDEX    0
    	    ::= {adDSX1CommonAlmTraps 1002961}

      dsx1NSAalmPHTLClear  NOTIFICATION-TYPE
	    OBJECTS	{
	        adTrapInformSeqNum,
	        sysName,
	        adGenSlotInfoIndex,
	        adGenPortTrapIdentifier,
	        adGenSlotAlarmStatus
	        }
	    STATUS          current
	    DESCRIPTION
           "Indicates a PHTL alarm has cleared"
        --#TYPE         "Status - PHTL Clear"
        --#SUMMARY      "DSXcommonTraps 1002962: NSA PHTL Clear"
	    --#SUMMARY  	"shelf: %s, slot: %d, %s"
	    --#ARGUMENTS 	{1,2,3}
	    --#SEVERITY 	ALERT
	    --#GENERIC  	6
	    --#CATEGORY  	"Status events"
	    --#Source_ID    "A"
	    --#TIMEINDEX    0
    	    ::= {adDSX1CommonAlmTraps 1002962}

    dsx1NSAalmPHTLActive  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates a PHTL alarm is active"
        --#TYPE         "Status - PHTL Active"
        --#SUMMARY      "DSXcommonTraps 1002963: PHTL Active"
	    --#SUMMARY  	"shelf: %s, slot: %d, %s"
	    --#ARGUMENTS 	{1,2,3}
	    --#SEVERITY 	ALERT
	    --#GENERIC  	6
	    --#CATEGORY  	"Status events"
	    --#Source_ID    "A"
	    --#TIMEINDEX    0
    	    ::= {adDSX1CommonAlmTraps 1002963}


    dsx1NSAalmATBClear  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates an ATB alarm has cleared"
        --#TYPE         "Status - ATB Clear"
        --#SUMMARY      "DSXcommonTraps 1002964: ATB Clear"
	    --#SUMMARY  	"shelf: %s, slot: %d, %s"
	    --#ARGUMENTS 	{1,2,3}
	    --#SEVERITY 	ALERT
	    --#GENERIC  	6
	    --#CATEGORY  	"Status events"
	    --#Source_ID    "A"
	    --#TIMEINDEX    0
    	    ::= {adDSX1CommonAlmTraps 1002964}

    dsx1NSAalmATBActive  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates an ATB alarm is active"
        --#TYPE         "Status - ATB Active"
        --#SUMMARY      "DSXcommonTraps 1002965: ATB Active"
	    --#SUMMARY  	"shelf: %s, slot: %d, %s"
	    --#ARGUMENTS 	{1,2,3}
	    --#SEVERITY 	ALERT
	    --#GENERIC  	6
	    --#CATEGORY  	"Status events"
	    --#Source_ID    "A"
	    --#TIMEINDEX    0
    	    ::= {adDSX1CommonAlmTraps 1002965}

    dsx1NSAalmNoDS0AvailableClear  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates a NoDS0Available alarm has cleared"
        --#TYPE         "Status - NoDS0Available Clear"
        --#SUMMARY      "DSXcommonTraps 1002966: NoDS0Available Clear"
	    --#SUMMARY  	"shelf: %s, slot: %d, %s"
	    --#ARGUMENTS 	{1,2,3}
	    --#SEVERITY 	MINOR
	    --#GENERIC  	6
	    --#CATEGORY  	"Status events"
	    --#Source_ID    "A"
	    --#TIMEINDEX    0
    	    ::= {adDSX1CommonAlmTraps 1002966}

    dsx1NSAalmNoDS0AvailableActive  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates a NoDS0 Available alarm is active"
        --#TYPE         "Status - NoDS0Available Active"
        --#SUMMARY      "DSXcommonTraps 1002967: NoDS0Available Active"
	    --#SUMMARY  	"shelf: %s, slot: %d, %s"
	    --#ARGUMENTS 	{1,2,3}
	    --#SEVERITY 	MINOR
	    --#GENERIC  	6
	    --#CATEGORY  	"Status events"
	    --#Source_ID    "A"
	    --#TIMEINDEX    0
    	    ::= {adDSX1CommonAlmTraps 1002967}

    dsx1NSAalmInvalidSlotClear  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates an Invalid Slot alarm
             has cleared"
        --#TYPE         "Status - Invalid Slot Clear"
        --#SUMMARY      "DSXcommonTraps 1002968: Invalid Slot Clear"
	    --#SUMMARY  	"shelf: %s, slot: %d, %s"
	    --#ARGUMENTS 	{1,2,3}
	    --#SEVERITY 	MINOR
	    --#GENERIC  	6
	    --#CATEGORY  	"Status events"
	    --#Source_ID    "A"
	    --#TIMEINDEX    0
    	    ::= {adDSX1CommonAlmTraps 1002968}

    dsx1NSAalmInvalidSlotActive  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates an Invalid Slot alarm
             is active"
        --#TYPE         "Status - Invalid Slot Active"
        --#SUMMARY      "DSXcommonTraps 1002969: Invalid Slot Active"
	    --#SUMMARY  	"shelf: %s, slot: %d, %s"
	    --#ARGUMENTS 	{1,2,3}
	    --#SEVERITY 	ALERT
	    --#GENERIC  	6
	    --#CATEGORY  	"Status events"
	    --#Source_ID    "A"
	    --#TIMEINDEX    0
    	    ::= {adDSX1CommonAlmTraps 1002969}

    dsx1SAalmTAUFailureClear  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates a TAU Failure Alarm has cleared"
        --#TYPE         "Status - TAU Failure Alarm Clear"
        --#SUMMARY      "DSXcommonTraps 1002970: TAU Failure Alarm Clear"
	    --#SUMMARY  	"shelf: %s, slot: %d, %s"
	    --#ARGUMENTS 	{1,2,3}
	    --#SEVERITY 	MAJOR
	    --#GENERIC  	6
	    --#CATEGORY  	"Status events"
	    --#Source_ID    "A"
	    --#TIMEINDEX    0
    	    ::= {adDSX1CommonAlmTraps 1002970}

    dsx1SAalmTAUFailureActive  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates a TAU Failure Alarm is Active"
        --#TYPE         "Status - TAU Failure Alarm Active"
        --#SUMMARY      "DSXcommonTraps 1002971: TAU Failure Alarm Active"
	    --#SUMMARY  	"shelf: %s, slot: %d, %s"
	    --#ARGUMENTS 	{1,2,3}
	    --#SEVERITY 	MAJOR
	    --#GENERIC  	6
	    --#CATEGORY  	"Status events"
	    --#Source_ID    "A"
	    --#TIMEINDEX    0
    	    ::= {adDSX1CommonAlmTraps 1002971}

     dsx1SAalmPCMFailureClear  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates a PCM Failure Alarm has cleared"
        --#TYPE         "Status - PCM Failure Alarm Clear"
        --#SUMMARY      "DSXcommonTraps 1002972: PCM Failure Alarm Clear"
	    --#SUMMARY  	"shelf: %s, slot: %d, %s"
	    --#ARGUMENTS 	{1,2,3}
	    --#SEVERITY 	MAJOR
	    --#GENERIC  	6
	    --#CATEGORY  	"Status events"
	    --#Source_ID    "A"
	    --#TIMEINDEX    0
    	    ::= {adDSX1CommonAlmTraps 1002972}

    dsx1SAalmPCMFailureActive  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates a PCM Failure Alarm is Active"
        --#TYPE         "Status - PCM Failure Alarm Active"
        --#SUMMARY      "DSXcommonTraps 1002973: PCM Failure Alarm Active"
	    --#SUMMARY  	"shelf: %s, slot: %d, %s"
	    --#ARGUMENTS 	{1,2,3}
	    --#SEVERITY 	MAJOR
	    --#GENERIC  	6
	    --#CATEGORY  	"Status events"
	    --#Source_ID    "A"
	    --#TIMEINDEX    0
    	    ::= {adDSX1CommonAlmTraps 1002973}

    dsx1SAalmLOMFClear  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates LOMF SA Alarm Clear"
        --#TYPE         "Status - LOMF SA Alarm Clear"
        --#SUMMARY      "DSXcommonTraps 1002974: LOMF SA Alarm Clear"
	    --#SUMMARY  	"shelf: %s, slot: %d, %s"
	    --#ARGUMENTS 	{1,2,3}
	    --#SEVERITY 	MAJOR
	    --#GENERIC  	6
	    --#CATEGORY  	"Status events"
	    --#Source_ID    "A"
	    --#TIMEINDEX    0
    	    ::= {adDSX1CommonAlmTraps 1002974}

    dsx1SAalmLOMFActive  NOTIFICATION-TYPE
	    OBJECTS	{
	        adTrapInformSeqNum,
	        sysName,
	        adGenSlotInfoIndex,
	        adGenPortTrapIdentifier,
	        adGenSlotAlarmStatus
	        }
	    STATUS          current
	    DESCRIPTION
            "Indicates LOMF SA Alarm Active"
        --#TYPE         "Status - LOMF SA Alarm Active"
        --#SUMMARY      "DSXcommonTraps 1002975: LOMF SA Alarm Active"
	    --#SUMMARY  	"shelf: %s, slot: %d, %s"
	    --#ARGUMENTS 	{1,2,3}
	    --#SEVERITY 	MAJOR
	    --#GENERIC  	6
	    --#CATEGORY  	"Status events"
	    --#Source_ID    "A"
	    --#TIMEINDEX    0
    	    ::= {adDSX1CommonAlmTraps 1002975}

	dsx1EnhancedSAalmLOSClear  NOTIFICATION-TYPE
	    OBJECTS	{
	        adTrapInformSeqNum,
	        sysName,
	        adGenSlotInfoIndex,
	        adGenPortTrapIdentifier,
   	        adGenSlotAlarmStatus,
	        adTAeSCUTrapAlarmLevel
	        }
	    STATUS          current
	    DESCRIPTION
            "Indicates LOS SA Alarm Clear"
        --#TYPE         "Status - LOS SA Alarm Clear"
        --#SUMMARY      "DSXcommonTraps 1002976: Enhanced LOS SA Alarm Clear"
	    --#SUMMARY  	"shelf: %s, slot: %d, %s"
	    --#ARGUMENTS 	{1,2,3}
	    --#SEVERITY 	MAJOR
	    --#GENERIC  	6
	    --#CATEGORY  	"Status events"
	    --#Source_ID    "A"
	    --#TIMEINDEX    0
    	    ::= {adDSX1CommonAlmTraps 1002976}

    dsx1EnhancedSAalmLOSActive  NOTIFICATION-TYPE
	    OBJECTS	{
	        adTrapInformSeqNum,
	        sysName,
	        adGenSlotInfoIndex,
	        adGenPortTrapIdentifier,
	        adGenSlotAlarmStatus,
	        adTAeSCUTrapAlarmLevel
	        }
	    STATUS          current
	    DESCRIPTION
            "Indicates LOS SA Alarm Active"
        --#TYPE         "Status - LOS SA Alarm Active"
        --#SUMMARY      "DSXcommonTraps 1002977: Enhanced LOS SA Alarm Active"
	    --#SUMMARY  	"shelf: %s, slot: %d, %s"
	    --#ARGUMENTS 	{1,2,3}
	    --#SEVERITY 	MAJOR
	    --#GENERIC  	6
	    --#CATEGORY  	"Status events"
	    --#Source_ID    "A"
	    --#TIMEINDEX    0
    	    ::= {adDSX1CommonAlmTraps 1002977}

    dsx1EnhancedSAalmLOFClear  NOTIFICATION-TYPE
	    OBJECTS	{
	        adTrapInformSeqNum,
	        sysName,
	        adGenSlotInfoIndex,
	        adGenPortTrapIdentifier,
	        adGenSlotAlarmStatus,
	        adTAeSCUTrapAlarmLevel
	        }
	    STATUS          current
	    DESCRIPTION
            "Indicates LOF SA Alarm Clear"
        --#TYPE         "Status - LOF SA Alarm Clear"
        --#SUMMARY      "DSXcommonTraps 1002978: Enhanced LOF SA Alarm Clear"
	    --#SUMMARY  	"shelf: %s, slot: %d, %s"
	    --#ARGUMENTS 	{1,2,3}
	    --#SEVERITY 	MAJOR
	    --#GENERIC  	6
	    --#CATEGORY  	"Status events"
	    --#Source_ID    "A"
	    --#TIMEINDEX    0
    	    ::= {adDSX1CommonAlmTraps 1002978}

    dsx1EnhancedSAalmLOFActive  NOTIFICATION-TYPE
	    OBJECTS	{
	        adTrapInformSeqNum,
	        sysName,
	        adGenSlotInfoIndex,
	        adGenPortTrapIdentifier,
	        adGenSlotAlarmStatus,
	        adTAeSCUTrapAlarmLevel
	        }
	    STATUS          current
	    DESCRIPTION
            "Indicates LOF SA Alarm Active"
        --#TYPE         "Status - LOF SA Alarm Active"
        --#SUMMARY      "DSXcommonTraps 1002979: Enhanced LOF SA Alarm Active"
	    --#SUMMARY  	"shelf: %s, slot: %d, %s"
	    --#ARGUMENTS 	{1,2,3}
	    --#SEVERITY 	MAJOR
	    --#GENERIC  	6
	    --#CATEGORY  	"Status events"
	    --#Source_ID    "A"
	    --#TIMEINDEX    0
    	    ::= {adDSX1CommonAlmTraps 1002979}

    dsx1EnhancedSAalmAISClear  NOTIFICATION-TYPE
	    OBJECTS	{
	        adTrapInformSeqNum,
	        sysName,
	        adGenSlotInfoIndex,
	        adGenPortTrapIdentifier,
	        adGenSlotAlarmStatus,
	        adTAeSCUTrapAlarmLevel
	        }
	    STATUS          current
	    DESCRIPTION
            "Indicates AIS SA Alarm Clear"
        --#TYPE         "Status - AIS SA Alarm Clear"
        --#SUMMARY      "DSXcommonTraps 1002980: Enhanced AIS SA Alarm Clear"
	    --#SUMMARY  	"shelf: %s, slot: %d, %s"
	    --#ARGUMENTS 	{1,2,3}
	    --#SEVERITY 	MAJOR
	    --#GENERIC  	6
	    --#CATEGORY  	"Status events"
	    --#Source_ID    "A"
	    --#TIMEINDEX    0
    	    ::= {adDSX1CommonAlmTraps 1002980}

    dsx1EnhancedSAalmAISActive  NOTIFICATION-TYPE
	    OBJECTS	{
	        adTrapInformSeqNum,
	        sysName,
	        adGenSlotInfoIndex,
	        adGenPortTrapIdentifier,
	        adGenSlotAlarmStatus,
	        adTAeSCUTrapAlarmLevel
	        }
	    STATUS          current
	    DESCRIPTION
            "Indicates AIS SA Alarm Active"
        --#TYPE         "Status - AIS SA Alarm Active"
        --#SUMMARY      "DSXcommonTraps 1002981: Enhanced AIS SA Alarm Active"
	    --#SUMMARY  	"shelf: %s, slot: %d, %s"
	    --#ARGUMENTS 	{1,2,3}
	    --#SEVERITY 	MAJOR
	    --#GENERIC  	6
	    --#CATEGORY  	"Status events"
	    --#Source_ID    "A"
	    --#TIMEINDEX    0
    	    ::= {adDSX1CommonAlmTraps 1002981}

    dsx1EnhancedSAalmRAIClear  NOTIFICATION-TYPE
	    OBJECTS	{
	        adTrapInformSeqNum,
	        sysName,
	        adGenSlotInfoIndex,
	        adGenPortTrapIdentifier,
	        adGenSlotAlarmStatus,
	        adTAeSCUTrapAlarmLevel
	        }
	    STATUS          current
	    DESCRIPTION
            "Indicates RAI SA Alarm Clear"
        --#TYPE         "Status - RAI SA Alarm Clear"
        --#SUMMARY      "DSXcommonTraps 1002982: Enhanced RAI SA Alarm Clear"
	    --#SUMMARY  	"shelf: %s, slot: %d, %s"
	    --#ARGUMENTS 	{1,2,3}
            --#SEVERITY         MINOR
	    --#GENERIC  	6
	    --#CATEGORY  	"Status events"
	    --#Source_ID    "A"
	    --#TIMEINDEX    0
    	    ::= {adDSX1CommonAlmTraps 1002982}

    dsx1EnhancedSAalmRAIActive  NOTIFICATION-TYPE
	    OBJECTS	{
	        adTrapInformSeqNum,
	        sysName,
	        adGenSlotInfoIndex,
	        adGenPortTrapIdentifier,
	        adGenSlotAlarmStatus,
	        adTAeSCUTrapAlarmLevel
	        }
	    STATUS          current
	    DESCRIPTION
            "Indicates RAI SA Alarm Active"
        --#TYPE         "Status - RAI SA Alarm Active"
        --#SUMMARY      "DSXcommonTraps 1002983: Enhanced RAI SA Alarm Active"
	    --#SUMMARY  	"shelf: %s, slot: %d, %s"
	    --#ARGUMENTS 	{1,2,3}
            --#SEVERITY         MINOR
	    --#GENERIC  	6
	    --#CATEGORY  	"Status events"
	    --#Source_ID    "A"
	    --#TIMEINDEX    0
    	    ::= {adDSX1CommonAlmTraps 1002983}

    dsx1SAalmLOSRemoteClear  NOTIFICATION-TYPE
        OBJECTS	{
                adTrapInformSeqNum,
                sysName,
                ifIndex,
                adTAeSCUTrapAlarmLevel
                }
        STATUS          current
        DESCRIPTION
        "Indicates LOS Alarm Clear"
        --#TYPE         "Status - LOS SA Alarm from Remote Device Clear"
        --#SUMMARY      "DSXcommonTraps 1002984: LOS SA Alarm from Remote Device Clear"
        --#SUMMARY  	"shelf: %s, Interface: %d"
        --#ARGUMENTS 	{1,2}
        --#SEVERITY 	MAJOR
        --#GENERIC  	6
        --#CATEGORY  	"Status events"
        --#Source_ID    "A"
        --#TIMEINDEX    0
        ::= {adDSX1CommonAlmTraps 1002984}

    dsx1SAalmLOSRemoteActive  NOTIFICATION-TYPE
        OBJECTS	{
                adTrapInformSeqNum,
                sysName,
                ifIndex,
                adTAeSCUTrapAlarmLevel
                }
        STATUS          current
        DESCRIPTION
        "Indicates LOS Alarm Active"
        --#TYPE         "Status - LOS SA Alarm from Remote Device Active"
        --#SUMMARY      "DSXcommonTraps 1002985: LOS SA Alarm from Remote Device Active"
        --#SUMMARY  	"shelf: %s, Interface: %d"
        --#ARGUMENTS 	{1,2}
        --#SEVERITY 	MAJOR
        --#GENERIC  	6
        --#CATEGORY  	"Status events"
        --#Source_ID    "A"
        --#TIMEINDEX    0
        ::= {adDSX1CommonAlmTraps 1002985}

    dsx1SAalmLOFRemoteClear  NOTIFICATION-TYPE
        OBJECTS	{
                adTrapInformSeqNum,
                sysName,
                ifIndex,
                adTAeSCUTrapAlarmLevel
                }
        STATUS          current
        DESCRIPTION
        "Indicates LOF Alarm Clear"
        --#TYPE         "Status - LOF SA Alarm from Remote Device Clear"
        --#SUMMARY      "DSXcommonTraps 1002986: LOF SA Alarm from Remote Device Clear"
        --#SUMMARY  	"shelf: %s, Interface: %d"
        --#ARGUMENTS 	{1,2}
        --#SEVERITY 	MAJOR
        --#GENERIC  	6
        --#CATEGORY  	"Status events"
        --#Source_ID    "A"
        --#TIMEINDEX    0
        ::= {adDSX1CommonAlmTraps 1002986}

    dsx1SAalmLOFRemoteActive  NOTIFICATION-TYPE
        OBJECTS	{
                adTrapInformSeqNum,
                sysName,
                ifIndex,
                adTAeSCUTrapAlarmLevel
                }
        STATUS          current
        DESCRIPTION
        "Indicates LOF Alarm Active"
        --#TYPE         "Status - LOF SA Alarm from Remote Device Active"
        --#SUMMARY      "DSXcommonTraps 1002987: LOF SA Alarm from Remote Device Active"
        --#SUMMARY  	"shelf: %s, Interface: %d"
        --#ARGUMENTS 	{1,2}
        --#SEVERITY 	MAJOR
        --#GENERIC  	6
        --#CATEGORY  	"Status events"
        --#Source_ID    "A"
        --#TIMEINDEX    0
        ::= {adDSX1CommonAlmTraps 1002987}

    dsx1SAalmAISRemoteClear  NOTIFICATION-TYPE
        OBJECTS	{
                adTrapInformSeqNum,
                sysName,
                ifIndex,
                adTAeSCUTrapAlarmLevel
                }
        STATUS          current
        DESCRIPTION
        "Indicates AIS Alarm Clear"
        --#TYPE         "Status - AIS SA Alarm from Remote Device Clear"
        --#SUMMARY      "DSXcommonTraps 1002988: AIS SA Alarm from Remote Device Clear"
        --#SUMMARY  	"shelf: %s, Interface: %d"
        --#ARGUMENTS 	{1,2}
        --#SEVERITY 	MAJOR
        --#GENERIC  	6
        --#CATEGORY  	"Status events"
        --#Source_ID    "A"
        --#TIMEINDEX    0
        ::= {adDSX1CommonAlmTraps 1002988}

    dsx1SAalmAISRemoteActive  NOTIFICATION-TYPE
        OBJECTS	{
                adTrapInformSeqNum,
                sysName,
                ifIndex,
                adTAeSCUTrapAlarmLevel
                }
        STATUS          current
        DESCRIPTION
        "Indicates AIS Alarm Active"
        --#TYPE         "Status - AIS SA Alarm from Remote Device Active"
        --#SUMMARY      "DSXcommonTraps 1002989: AIS SA Alarm from Remote Device Active"
        --#SUMMARY  	"shelf: %s, Interface: %d"
        --#ARGUMENTS 	{1,2}
        --#SEVERITY 	MAJOR
        --#GENERIC  	6
        --#CATEGORY  	"Status events"
        --#Source_ID    "A"
        --#TIMEINDEX    0
        ::= {adDSX1CommonAlmTraps 1002989}

    dsx1NSAalmRAIRemoteClear  NOTIFICATION-TYPE
        OBJECTS	{
                adTrapInformSeqNum,
                sysName,
                ifIndex,
                adTAeSCUTrapAlarmLevel
                }
        STATUS          current
        DESCRIPTION
        "Indicates RAI Alarm Clear"
        --#TYPE         "Status - RAI NSA Alarm from Remote Device Clear"
        --#SUMMARY      "DSXcommonTraps 1002990: RAI NSA Alarm from Remote Device Clear"
        --#SUMMARY  	"shelf: %s, Interface: %d"
        --#ARGUMENTS 	{1,2}
        --#SEVERITY     MINOR
        --#GENERIC  	6
        --#CATEGORY  	"Status events"
        --#Source_ID    "A"
        --#TIMEINDEX    0
        ::= {adDSX1CommonAlmTraps 1002990}

    dsx1NSAalmRAIRemoteActive  NOTIFICATION-TYPE
        OBJECTS	{
                adTrapInformSeqNum,
                sysName,
                ifIndex,
                adTAeSCUTrapAlarmLevel
                }
        STATUS          current
        DESCRIPTION
        "Indicates RAI Alarm Active"
        --#TYPE         "Status - RAI NSA Alarm from Remote Device Active"
        --#SUMMARY      "DSXcommonTraps 1002991: RAI NSA Alarm from Remote Device Active"
        --#SUMMARY  	"shelf: %s, Interface: %d"
        --#ARGUMENTS 	{1,2}
        --#SEVERITY     MINOR
        --#GENERIC  	6
        --#CATEGORY  	"Status events"
        --#Source_ID    "A"
        --#TIMEINDEX    0
        ::= {adDSX1CommonAlmTraps 1002991}

adDSX1CommonTrapsEventGroup NOTIFICATION-GROUP
   NOTIFICATIONS
   {
	dsx1almcondition,
        dsx1SAalmLOSClear,
    	dsx1SAalmLOSActive,
    	dsx1SAalmLOFClear,
    	dsx1SAalmLOFActive,
    	dsx1SAalmAISClear,
    	dsx1SAalmAISActive,
    	dsx1SAalmRAIClear,
    	dsx1SAalmRAIActive,
    	dsx1loopbackcondition,
    	dsx1NSAINFOFarShelfRFIClear,
    	dsx1NSAINFOFarShelfRFIActive,
    	dsx1NSAINFODTLKFailINCClear,
    	dsx1NSAINFODTLKFailINCActive,
    	dsx1SAalmBPVClear,
    	dsx1SAalmBPVActive,
    	dsx1SAalmFarShelfRFIClear,
    	dsx1SAalmFarShelfRFIActive,
    	dsx1SAalmDTLKFailINCClear,
    	dsx1SAalmDTLKFailINCActive,
    	dsx1NSAalmLOSClear,
    	dsx1NSAalmLOSActive,
    	dsx1NSAalmLOFClear,
    	dsx1NSAalmLOFActive,
    	dsx1NSAalmAISClear,
    	dsx1NSAalmAISActive,
    	dsx1NSAalmRAIClear,
    	dsx1NSAalmRAIActive,
    	dsx1SAFarLoopLPBKDS1FEACClear,
    	dsx1SAFarLoopLPBKDS1FEACActive,
    	dsx1NSAalmBPVClear,
    	dsx1NSAalmBPVActive,
    	dsx1NSAalmFarShelfRFIClear,
    	dsx1NSAalmFarShelfRFIActive,
    	dsx1NSAalmDTLKFailINCClear,
    	dsx1NSAalmDTLKFailINCActive,
    	dsx1NSAT1WKSWPRClear,
    	dsx1NSAT1WKSWPRActive,
    	dsx1NSAalmSYNCPRIClear,
    	dsx1NSAalmSYNCPRIActive ,
    	dsx1NSAalmSYNCSECClear,
    	dsx1NSAalmSYNCSECActive,
    	dsx1SAalmLPBKLOCALClear,
    	dsx1SAalmLPBKLOCALActive,
    	dsx1SAalmLPBKLINEClear,
    	dsx1SAalmLPBKLINEActive,
    	dsx1SAalmLPBKPAYLOADClear,
    	dsx1SAalmLPBKPAYLOADActive,
    	dsx1NSAalmLPBKLOCALClear,
    	dsx1NSAalmLPBKLOCALActive,
    	dsx1NSAalmLPBKLINEClear,
    	dsx1NSAalmLPBKLINEActive,
		dsx1NSAalmLPBKPAYLOADClear,
    	dsx1NSAalmLPBKPAYLOADActive,
    	dsx1SAalmSYNCOOSClear,
    	dsx1SAalmSYNCOOSActive,
    	dsx1NSAalmPHTLClear,
    	dsx1NSAalmPHTLActive,
    	dsx1NSAalmATBClear,
    	dsx1NSAalmATBActive,
    	dsx1NSAalmNoDS0AvailableClear,
    	dsx1NSAalmNoDS0AvailableActive,
    	dsx1NSAalmInvalidSlotClear,
    	dsx1NSAalmInvalidSlotActive,
    	dsx1SAalmTAUFailureClear,
    	dsx1SAalmTAUFailureActive,
    	dsx1SAalmPCMFailureClear,
    	dsx1SAalmPCMFailureActive,
		dsx1SAalmLOMFClear,
		dsx1SAalmLOMFActive,
	    dsx1EnhancedSAalmLOSClear,
    	dsx1EnhancedSAalmLOSActive,
    	dsx1EnhancedSAalmLOFClear,
    	dsx1EnhancedSAalmLOFActive,
    	dsx1EnhancedSAalmAISClear,
    	dsx1EnhancedSAalmAISActive,
    	dsx1EnhancedSAalmRAIClear,
    	dsx1EnhancedSAalmRAIActive,
        dsx1SAalmLOSRemoteClear,
        dsx1SAalmLOSRemoteActive,
        dsx1SAalmLOFRemoteClear,
        dsx1SAalmLOFRemoteActive,
        dsx1SAalmAISRemoteClear,
        dsx1SAalmAISRemoteActive,
        dsx1NSAalmRAIRemoteClear,
        dsx1NSAalmRAIRemoteActive

   }
   STATUS current
   DESCRIPTION
      "adDSX1CommonTraps Notification Group"
   ::= { adDSX1CommonTrapsMibGroups 1 }

END
