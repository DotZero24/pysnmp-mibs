ADTRAN-GENVDSL2-LINE-MIB
-- TITLE:     The ADTRAN VDSL2 MIB
-- PRODUCT:   ADTRAN VDSL2 PRODUCTS
-- VERSION:   1.0
-- DATE:      07/08/2008
-- AUTHOR:    Craye Hall
-- STATUS:    PRELIMINARY

-- This MIB defines the object identifier (OID) for the
-- ADTRAN VDSL2 MIB objects

-- HISTORY:
-- 07/08/2008 och created PRELIMINARY MIB.
-- 07/23/2008 ltg fixed enumerations for adGenVdsl2ConfSpecificPsdSelect
--     vdsl2-b8-998ade17-m2x-m and vdsl2-b8-998e17-m2x-a.
-- 08/04/2008 ltg added enumerations to adGenVdsl2ConfServiceMode for
--     VDSL2 multimode/XTSE entries.
-- 08/12/2008 ltg Moved adGenVdsl2LineCircuitID from
--     adGenVdsl2LineConfProfileTable to adGenVdsl2ConfProfileExtTable since
--     it is indexed off ifIndex and not profile name.  Re-numbered
--     adGenVdsl2LineConfProfileTable since still preliminary.
-- 08/12/2008 ltg removed from adGenVdsl2LineLinkdownAlrm entry from
--     adGenVdsl2LineAlarmConfProfileTable since it will be part of IF-MIB
--     (rfc2863). Re-numbered  adGenVdsl2LineAlarmConfProfileTable since
--     still preliminary.
-- 09/12/2008 ltg Changed several Integer to Integer32 since that's what
--     driver returns. Changed read-write types in possible dynamic profiles
--     to read-create.
-- 09/13/2008 ltg Added LpType entries. Modified RateMode selections.
--     Added adGenVdsl2LineBandConfProfileTable.
-- 09/16/2008 ltg Added BandStatus and ScStatus tables.  Also, revised range
--     limits on several items.  Added UPBO provisioning.
-- 10/08/2008 ltg Revised threshold trap definitions and organization.
-- 10/17/2008 ltg Added HP open comments var-binds for all traps.
-- 10/20/2008 ltg Revised ES,SES,UAS entry/trap names to remove redundant 's'.
-- 10/24/2008 ltg Added new 1Day PM tables and moved some entries from
--     IntervalTables to these new 1DayIntervalTables.
-- 12/11/2008 ltg Added TC packet/cell entries.  Revised band-profile enums.
--     Added counter reset item and line retrain items. Fixed the
--     adGenVdsl2PMGroup items to include adGenVdsl2VturPerfDataTable entires.
-- 12/17/2008 ltg Fixed units on ChanINP and InterleaveDelay.
-- 05/29/2009 twc Updated adGenVdsl2LineConfProfileName and adGenVdsl2LineAlarmConfProfileName
--     indices to conform to RFC2578 where possible. I could not add the "IMPLIED" keyword to
--     adGenVdsl2LineConfProfileName in adGenVdsl2BandConfProfileTable because it is not the last
--     index.
-- 06/02/09 twc	  Added 1..10 SIZE modifier to  adGenVdsl2LineConfProfileName and adGenVdsl2LineAlarmConfProfileName.
-- 08/13/2009 och added adProducts to display the VDSL cards (Sparta 57749)
-- 08/09/2010 gdo Added daily channel PM tables.
-- 08/16/2010 rab added DsCustomPbo options
-- 09/09/2010 jlb Removed adTA5k24pVDSL2AM.  It was a duplicate OBJECT IDENTIFIER that wasn't being used.
-- 10/05/2010 rab added AnfpCalValue to AdGenVdsl2LineConfProfileEntry
-- 11/09/2010 rab added anfp entries to adGenVdsl2ConfSpecificPsdSelect, adGenVdsl2ConfUsPboSetting, and adGenVdsl2ConfDsPboSetting
--
--  DO NOT MAKE HISTORY COMMENTS HERE!!!! Revision history now in REVISION/DESCRIPTION clauses below
--
-- ***************************************************************************


DEFINITIONS ::= BEGIN

    IMPORTS
        Integer32,
        Unsigned32,
        Counter32,
        Gauge32,
        NOTIFICATION-TYPE,
        OBJECT-TYPE,
        enterprises,
         MODULE-IDENTITY
           FROM SNMPv2-SMI
         OBJECT-GROUP
             FROM SNMPv2-CONF
        ifIndex
           FROM IF-MIB
        RowStatus,
        DisplayString,
        TEXTUAL-CONVENTION,
        TimeStamp
          FROM SNMPv2-TC
        sysName
            FROM SNMPv2-MIB
-- from [RFC2579]
        adGenPortTrapIdentifier
            FROM ADTRAN-GENPORT-MIB
        adTrapInformSeqNum
            FROM ADTRAN-GENTRAPINFORM-MIB
	adGenSlotInfoIndex
            FROM ADTRAN-GENSLOT-MIB
        adGenVdsl2,
--	adtran,
--	adProducts,
        adGenVdsl2ID
            FROM ADTRAN-SHARED-VDSL2-MIB
        ;

adGenVdsl2MIB MODULE-IDENTITY
   LAST-UPDATED "202005110000Z"
   ORGANIZATION "Adtran, Inc."
   CONTACT-INFO "http://www.adtran.com"
   DESCRIPTION
      "This MIB defines the objects for the VDSL2 MIB."

   REVISION "202005110000Z"
   DESCRIPTION
      "Add all severities to the adGenVdsl2AlarmSlotProvTable"

   REVISION "201802260000Z"
   DESCRIPTION
      "Add adGenVdsl2ConfRateAdaptConfigMode"

   REVISION "201710260000Z"
   DESCRIPTION
      "Removing unneeded item g9932q(29)from adGenVdsl2LineCurrTransSysMode."

   REVISION "201710130000Z"
   DESCRIPTION
      "Adding annex A PSDs for band profile 35B."

   REVISION "201709060000Z"
   DESCRIPTION
      "Adding new band profile 35B PSDs. Changing upper rate limits for downstream payload rates
      as well as downstream retransmission Max NDR. Changed 35B band profile enum values to
      account for older profile 30A and 17B profiles."

   REVISION "201708040000Z"
   DESCRIPTION
      "Adding support for new 35B band profile."

   REVISION "201509160000Z"
   DESCRIPTION
      "Added support for QLN and HLOG VDSL sub-carrier status via adGenVdsl2ScStatusUsQln, adGenVdsl2ScStatusDsQln,
       adGenVdsl2ScStatusUsHlog, adGenVdsl2ScStatusDsHlog"

   REVISION "201506030000Z"
   DESCRIPTION
      "Add adGenVdsl2ConfMemorySplitRatio"

   REVISION "201503170000Z"
   DESCRIPTION
      "Add adGenVdsl2AlarmSlotProvTable"

   REVISION "201501140000Z"
   DESCRIPTION
      "Add support for AM radio station carrier masking provisioning"

   REVISION "201401240000Z"
   DESCRIPTION
      "Add rolling counter option to enum for adGenVdsl2LineResetCounters"

   REVISION "201312120000Z"
   DESCRIPTION
      "Added New set of Vtuc and Vtur Threshold Crossing alarms to be used for Remote Devices."

   REVISION "201309180000Z"
   DESCRIPTION
      "Add support for SRA and G.INP (status, PM, and provisioning)"

   REVISION "201307170000Z"
   DESCRIPTION
      "Add enums, g9935 and g9932y, for vectoring to adGenVdsl2LineCurrTransSysMode"

   REVISION "201303060000Z"
   DESCRIPTION
      "Added new enumerated type to service modes for PTM Fallback"
   REVISION "201210080000Z"
   DESCRIPTION
      "Added adGenVdsl2ReserveInstanceBulkVDSLSlotInstance, adGenVdsl2BulkVDSLTlvType, adGenVdsl2BulkVDSLTlvPort, and adGenVdsl2BulkVDLSTlvCreate need to get
      Bit Allocation Table and SNR values through a TLV block"

   REVISION "201209250000Z"
   DESCRIPTION
      "Added adGenVdsl2VtucCircuitProviderCode, adGenVdsl2VturCircuitProviderCode, and adGenVdsl2VturCircuitCapabilities."

   REVISION "201109190000Z"
   DESCRIPTION
      "Added adGenVdsl2VtucCurrTxLineRate, adGenVdsl2VtucPrevTxLineRate, adGenVdsl2VturCurrTxLineRate, adGenVdsl2VturPrevTxLineRate to fix CN-1947
        changed the description of adGenVdsl2VtucCurrTxRate, adGenVdsl2VtucPrevTxRate, adGenVdsl2VturCurrTxRate and adGenVdsl2VturPrevTxRate"
   REVISION "201106020000Z"
   DESCRIPTION
      "Changed type of OID adGenVdsl2ConfUsCustomPboElecLenKL from Unsigned32 to INTEGER"
   REVISION "201009090000Z"
   DESCRIPTION
      "Removed adTA5k24pVDSL2AM.  It was a duplicate OBJECT IDENTIFIER
       that wasn't being used."
   REVISION "201008160000Z"
   DESCRIPTION
      "Add DsCustomPbo options."
   REVISION "201008090000Z"
   DESCRIPTION
      "Add daily channel PM tables."
   REVISION "200807080000Z"
   DESCRIPTION
      "The MIB module defining objects for the management of a pair of
       Very High Speed Digital Subscriber Line (VDSL2) modems conforming
       to the ITU-T G.993.2 standard at the ends of a physical VDSL2 line.
       These objects are also applicable for managing legacy fallback modes
       of ADSL, ADSL2, and ADSL2+ modulations.  Each VDSL2 line has
       an entry in an ifTable.  An agent may reside at either end of the
       VDSL line however the MIB is designed to require no management
       communication between them beyond that inherent in the low-level
       VDSL2 line protocol. The agent may monitor and control this
       protocol for its needs.

       At the physical layer, VDSL2 modems divide the usable spectrum into
       multiple frequency bands in each direction US0 - US4 and DS1 - DS4.
       Information about status and performance of each of these bands can
       be found in the band indexed tables.  VDSL2 modems further divide the
       frequency bands using sub-carriers.  There are 4096 possible sub-
       carriers in the upstream direction and 4096 possible sub-carriers in
       the downstream direction. Information about status and performance of
       each of these sub-carriers can be found in the sub-carrier indexed
       tables.

       At the data interface layer, VDSL2 devices may support up to 4 optional
       channels (Latency Paths LP0-LP3), each of which can be configured as
       fast or interleave types. Prior ADSL/ADSL2/ADSL2+ provisioning models
       referred to separate interfaces for fast and interleave channels. In the
       legacy Adtran ADSL/ADSL2/ADSL2+ implementations, fast only or interleave
       only line types were the valid selections allowed so these interfaces
       shall be both be mapped to LP0 for consistent operation.


       Naming Conventions:
             Chan -- One of logical
             Vtuc -- (VTUC) modem at near (Central) end of line
             Vtur -- (VTUR) modem at Remote end of line
             Line -- A physical connection between a Vtuc and Vtur unit
             Curr -- Current
             Prev -- Previous
             PM  -- Performance Monitoring
             Rx  -- Receive
             Tx  -- Transmit
             ES  -- Errored Second.
             LCS -- Line Code Specific
             Lof -- Loss of Frame
             Lol -- Loss of Link
             Los -- Loss of Signal
             Lpr -- Loss of Power
             xxxs-- interval of Seconds in which xxx occurs
                     (e.g., xxx=Lof, Los, Lpr)
             Max -- Maximum
             Mgn -- Margin
             Min -- Minimum
             Ds  -- Downstream (Tx Towards Vtur)
             Us  -- Upstream (Tx Towards Vtuc)
             Ne  -- Near-End
             Fe  -- Near-End
             Psd -- Power Spectral Density
             Snr -- Signal to Noise Ratio
             Atn -- Attenuation
             PTM -- Packet Transfer Mode
             EFM -- Ethernet first Mile
             DELT -- Dual Ended Loop Test
             SELT -- Single Ended Loop Test
             Diag -- Diagnostic modes of operation
             Blks-- Blocks, a data unit or packet
         "
::= { adGenVdsl2ID 1 }

-- OBJECT IDENTIFIERS
   adtran			OBJECT IDENTIFIER ::= { enterprises 664 }
   adProducts       		OBJECT IDENTIFIER ::= { adtran 1 }
   adTA5k24pVDSL2Combo      	OBJECT IDENTIFIER ::= { adProducts 891 }
   adTA5k32pVDSL2		OBJECT IDENTIFIER ::= { adProducts 892}
   adTA5k32pVDSL2Spltr      	OBJECT IDENTIFIER ::= { adProducts 893 }

   adGenVdsl2Prov               OBJECT IDENTIFIER ::= { adGenVdsl2 1 }
   adGenVdsl2Status             OBJECT IDENTIFIER ::= { adGenVdsl2 2 }
   adGenVdsl2PM                 OBJECT IDENTIFIER ::= { adGenVdsl2 3 }
   adGenVdsl2Traps              OBJECT IDENTIFIER ::= { adGenVdsl2 4 }
   adGenVdsl2ExtConfig          OBJECT IDENTIFIER ::= { adGenVdsl2 5 }
   adGenVdsl2Test               OBJECT IDENTIFIER ::= { adGenVdsl2 6 }
   adGenVdsl2MibConformance     OBJECT IDENTIFIER ::= { adGenVdsl2 7 }
   adGenVdsl2MibGroups          OBJECT IDENTIFIER ::= { adGenVdsl2MibConformance 1 }


   adGenVdsl2VtucTrapPrefix OBJECT IDENTIFIER ::= { adGenVdsl2Traps 1 }
   adGenVdsl2VturTrapPrefix OBJECT IDENTIFIER ::= { adGenVdsl2Traps 2 }
   adGenVdsl2VtucTrapPrefixRemote OBJECT IDENTIFIER ::= { adGenVdsl2Traps 3 }
   adGenVdsl2VturTrapPrefixRemote OBJECT IDENTIFIER ::= { adGenVdsl2Traps 4 }

   -- objects



         -- ******************************************************************
         -- Group: Provisioning
         --   The Provisioning Group consists of the tables of entries
         --   necessary to maintain the persistence profiles for each
         --   VDSL2 modem.  There are two tables of profiles. The Line
         --   profile and the Alarm profile. Since these profiles can
         --   be made dynamic, they are indexed off their names and not
         --   the ifIndex (ie Port).
         -- ******************************************************************

         -- ============ Prov Group (Line Profile) ===========================
         adGenVdsl2LineConfProfileTable    OBJECT-TYPE
             SYNTAX          SEQUENCE OF AdGenVdsl2LineConfProfileEntry
             MAX-ACCESS      not-accessible
             STATUS          current
             DESCRIPTION
                "This table contains information on the VDSL2 line
                 configuration.  One entry in this table reflects a
                 profile defined by a manager which can be used to
                 configure the VDSL2 line.
                "
         ::= { adGenVdsl2Prov 1 }

         adGenVdsl2LineConfProfileEntry    OBJECT-TYPE
             SYNTAX          AdGenVdsl2LineConfProfileEntry
             MAX-ACCESS      not-accessible
             STATUS          current
             DESCRIPTION
                "Each entry consists of a list of parameters that
                 represents the configuration of an VDSL2 modem.

                 `Static' profiles -  profiles are automaticly
		 created or destroyed as VDSL2 physical lines
		 are discovered and removed by the system.
		 The name of the profile will be equivalent to
                 the decimal value of the line's interface index.
                "
             INDEX { IMPLIED adGenVdsl2LineConfProfileName }
         ::= { adGenVdsl2LineConfProfileTable 1}

         AdGenVdsl2LineConfProfileEntry ::=
             SEQUENCE {
                 adGenVdsl2LineConfProfileName               DisplayString,

                 adGenVdsl2ConfDsRateMode                    INTEGER,
                 adGenVdsl2ConfDsTargetSnrMgn                Integer32,
                 adGenVdsl2ConfDsMaxSnrMgn                   Integer32,
                 adGenVdsl2ConfDsMinSnrMgn                   Integer32,
                 adGenVdsl2ConfUsTargetSnrMgn                Integer32,
                 adGenVdsl2ConfUsMaxSnrMgn                   Integer32,
                 adGenVdsl2ConfUsMinSnrMgn                   Integer32,
                 adGenVdsl2LineConfProfileRowStatus          RowStatus,

                 adGenVdsl2ConfServiceMode                   INTEGER,
                 adGenVdsl2ConfMultiModeDmtTse               Unsigned32,
                 adGenVdsl2ConfBandProfiles                  Unsigned32,
                 adGenVdsl2ConfSpecificPsdSelect             INTEGER,
                 adGenVdsl2ConfUsPsdMaskU0Select             INTEGER,
                 adGenVdsl2ConfUsTrellis                     INTEGER,
                 adGenVdsl2ConfDsTrellis                     INTEGER,
                 adGenVdsl2ConfUsPboSetting                  INTEGER,
                 adGenVdsl2ConfDsPboSetting                  INTEGER,
                 adGenVdsl2ConfUsVnoiseSetting               INTEGER,
                 adGenVdsl2ConfDsVnoiseSetting               INTEGER,
                 adGenVdsl2ConfUsBitSwap                     INTEGER,
                 adGenVdsl2ConfDsBitSwap                     INTEGER,
                 adGenVdsl2ConfHamBandNotches                Unsigned32,
                 adGenVdsl2ConfUsNomAggTxPwr                 Integer32,
                 adGenVdsl2ConfDsNomAggTxPwr                 Integer32,
                 adGenVdsl2ConfUsMaxNomTxPsd                 Integer32,
                 adGenVdsl2ConfDsMaxNomTxPsd                 Integer32,
                 adGenVdsl2ConfUsMaxAggRxPwr                 Integer32,
                 adGenVdsl2ConfFramingMode                   INTEGER,

                 adGenVdsl2ConfUsLp0MaxPayloadRate           Unsigned32,
                 adGenVdsl2ConfUsLp0MinPayloadRate           Unsigned32,
                 adGenVdsl2ConfUsLp0MaxDelay                 Unsigned32,
                 adGenVdsl2ConfUsLp0MinProtection            Unsigned32,
                 adGenVdsl2ConfUsLp0RaRatio                  Integer32,
                 adGenVdsl2ConfUsLp0InitPolicy               INTEGER,
                 adGenVdsl2ConfDsLp0MaxPayloadRate           Unsigned32,
                 adGenVdsl2ConfDsLp0MinPayloadRate           Unsigned32,
                 adGenVdsl2ConfDsLp0MaxDelay                 Unsigned32,
                 adGenVdsl2ConfDsLp0MinProtection            Unsigned32,
                 adGenVdsl2ConfDsLp0RaRatio                  Integer32,
                 adGenVdsl2ConfDsLp0InitPolicy               INTEGER,

                 adGenVdsl2ConfUsLp1MaxPayloadRate           Unsigned32,
                 adGenVdsl2ConfUsLp1MinPayloadRate           Unsigned32,
                 adGenVdsl2ConfUsLp1MaxDelay                 Unsigned32,
                 adGenVdsl2ConfUsLp1MinProtection            Unsigned32,
                 adGenVdsl2ConfUsLp1RaRatio                  Integer32,
                 adGenVdsl2ConfUsLp1InitPolicy               INTEGER,
                 adGenVdsl2ConfDsLp1MaxPayloadRate           Unsigned32,
                 adGenVdsl2ConfDsLp1MinPayloadRate           Unsigned32,
                 adGenVdsl2ConfDsLp1MaxDelay                 Unsigned32,
                 adGenVdsl2ConfDsLp1MinProtection            Unsigned32,
                 adGenVdsl2ConfDsLp1RaRatio                  Integer32,
                 adGenVdsl2ConfDsLp1InitPolicy               INTEGER,

                 adGenVdsl2ConfUsLp0Type                     INTEGER,
                 adGenVdsl2ConfDsLp0Type                     INTEGER,
                 adGenVdsl2ConfUsLp1Type                     INTEGER,
                 adGenVdsl2ConfDsLp1Type                     INTEGER,

                 adGenVdsl2ConfUsRateMode                    INTEGER,

                 adGenVdsl2ConfUsCustomPboElecLenKL          INTEGER,
                 adGenVdsl2ConfUsCustomPboForceLen           INTEGER,
                 adGenVdsl2ConfUsCustomPboBoostMode          INTEGER,

                 adGenVdsl2ConfDsCustomPboElecLen            INTEGER,
                 adGenVdsl2ConfDsCustomPboCableA             INTEGER,
                 adGenVdsl2ConfDsCustomPboCableB             INTEGER,
                 adGenVdsl2ConfDsCustomPboCableC             INTEGER,
                 adGenVdsl2ConfDsCustomPboMinSignal          INTEGER,
                 adGenVdsl2ConfDsCustomPboMinFreq            INTEGER,
                 adGenVdsl2ConfDsCustomPboMaxFreq            INTEGER,
                 adGenVdsl2ConfAnfpCalValue                  INTEGER,

                 adGenVdsl2ConfDsDownshiftSnrMgn             Integer32,
                 adGenVdsl2ConfDsUpshiftSnrMgn               Integer32,
                 adGenVdsl2ConfDsMinUpshiftTime              Unsigned32,
                 adGenVdsl2ConfDsMinDownshiftTime            Unsigned32,
                 adGenVdsl2ConfUsDownshiftSnrMgn             Integer32,
                 adGenVdsl2ConfUsUpshiftSnrMgn               Integer32,
                 adGenVdsl2ConfUsMinUpshiftTime              Unsigned32,
                 adGenVdsl2ConfUsMinDownshiftTime            Unsigned32,

                 adGenVdsl2ConfUsLp0RtxSetting               INTEGER,
                 adGenVdsl2ConfUsLp0CustomRtxMaxNdr          Unsigned32,
                 adGenVdsl2ConfUsLp0CustomRtxMinDelay        INTEGER,
                 adGenVdsl2ConfUsLp0CustomRtxMaxDelay        INTEGER,
                 adGenVdsl2ConfUsLp0CustomRtxInpMinShine     INTEGER,
                 adGenVdsl2ConfUsLp0CustomRtxInpMinRein      INTEGER,
                 adGenVdsl2ConfUsLp0CustomRtxIatRein         INTEGER,
                 adGenVdsl2ConfUsLp0CustomRtxLeftrThresh     INTEGER,

                 adGenVdsl2ConfDsLp0RtxSetting               INTEGER,
                 adGenVdsl2ConfDsLp0CustomRtxMaxNdr          Unsigned32,
                 adGenVdsl2ConfDsLp0CustomRtxMinDelay        INTEGER,
                 adGenVdsl2ConfDsLp0CustomRtxMaxDelay        INTEGER,
                 adGenVdsl2ConfDsLp0CustomRtxInpMinShine     INTEGER,
                 adGenVdsl2ConfDsLp0CustomRtxInpMinRein      INTEGER,
                 adGenVdsl2ConfDsLp0CustomRtxIatRein         INTEGER,
                 adGenVdsl2ConfDsLp0CustomRtxLeftrThresh     INTEGER,

                 adGenVdsl2ConfUsLp1RtxSetting               INTEGER,
                 adGenVdsl2ConfUsLp1CustomRtxMaxNdr          Unsigned32,
                 adGenVdsl2ConfUsLp1CustomRtxMinDelay        INTEGER,
                 adGenVdsl2ConfUsLp1CustomRtxMaxDelay        INTEGER,
                 adGenVdsl2ConfUsLp1CustomRtxInpMinShine     INTEGER,
                 adGenVdsl2ConfUsLp1CustomRtxInpMinRein      INTEGER,
                 adGenVdsl2ConfUsLp1CustomRtxIatRein         INTEGER,
                 adGenVdsl2ConfUsLp1CustomRtxLeftrThresh     INTEGER,

                 adGenVdsl2ConfDsLp1RtxSetting               INTEGER,
                 adGenVdsl2ConfDsLp1CustomRtxMaxNdr          Unsigned32,
                 adGenVdsl2ConfDsLp1CustomRtxMinDelay        INTEGER,
                 adGenVdsl2ConfDsLp1CustomRtxMaxDelay        INTEGER,
                 adGenVdsl2ConfDsLp1CustomRtxInpMinShine     INTEGER,
                 adGenVdsl2ConfDsLp1CustomRtxInpMinRein      INTEGER,
                 adGenVdsl2ConfDsLp1CustomRtxIatRein         INTEGER,
                 adGenVdsl2ConfDsLp1CustomRtxLeftrThresh     INTEGER,

                 adGenVdsl2ConfAmRadioFreqMask1              INTEGER,
                 adGenVdsl2ConfAmRadioFreqMask2              INTEGER,
                 adGenVdsl2ConfAmRadioFreqMask3              INTEGER,
                 adGenVdsl2ConfAmRadioFreqMask4              INTEGER,
                 adGenVdsl2ConfAmRadioFreqMask5              INTEGER,
                 adGenVdsl2ConfAmRadioFreqMask6              INTEGER,

                 adGenVdsl2ConfMemorySplitRatio              INTEGER,
                 adGenVdsl2ConfRateAdaptConfigMode           INTEGER
         }

         adGenVdsl2LineConfProfileName    OBJECT-TYPE
             SYNTAX          DisplayString (SIZE (1..10))
             MAX-ACCESS      not-accessible
             STATUS          current
             DESCRIPTION
                "This object is used by the line configuration table
                 in order to identify a row of this table.

                 This value cannot be user-specified and is not dynamic.

                 There is a one-to-one relationship between each line and
                 its profile.  The profile name algorithmicly represents
		 the Line's ifIndex.

                 Therefore, the profile's name is a decimalized string
                 of the ifIndex that is fixed-length (10) with
                 leading zero(s).  For example, the profile name for
                 ifIndex which equals '15' will be '0000000015'.
                "
         ::= { adGenVdsl2LineConfProfileEntry 1 }

         adGenVdsl2ConfDsRateMode OBJECT-TYPE
             SYNTAX    INTEGER {
                 fixed (1),              -- no rate adaptation
                 adaptAtStartup (2),     -- perform rate adaptation
                                         -- only at initialization
                 adaptAtRuntime (3)      -- perform rate adaptation at
                                         -- any time
             }
             MAX-ACCESS  read-create
             STATUS      current
             DESCRIPTION
                "Defines what form of downstream rate adaptation is
                 configured on this modem.
                "
         ::= { adGenVdsl2LineConfProfileEntry 2 }

         adGenVdsl2ConfDsTargetSnrMgn OBJECT-TYPE
             SYNTAX      Integer32 (0..310)
             UNITS       "tenth dB"
             MAX-ACCESS  read-create
             STATUS      current
             DESCRIPTION
                "Configured Target Signal/Noise Margin.  This is the noise
                 margin the modem must achieve with the target BER (10-7)
                 or better to successfully complete initialization.  The
                 noise margin ranges from 0 to 31 dB with 0.1 dB steps
                 (0..310). This margin should be above the minimum margin
                 and below the maximum margin.
                "
         ::= { adGenVdsl2LineConfProfileEntry 3 }

         adGenVdsl2ConfDsMaxSnrMgn OBJECT-TYPE
             SYNTAX      Integer32 (0..310)
             UNITS       "tenth dB"
             MAX-ACCESS  read-create
             STATUS      current
             DESCRIPTION
                "Configured Maximum acceptable Signal/Noise Margin.
                 If the Noise Margin is above this the modem should
                 attempt to reduce its power output to optimize its
                 operation.  The noise margin ranges from 0 to 31 dB
                 with 0.1 dB steps (0..310). This margin should be
                 above the target and minimum margins.
                "
         ::= { adGenVdsl2LineConfProfileEntry 4 }

         adGenVdsl2ConfDsMinSnrMgn  OBJECT-TYPE
             SYNTAX      Integer32 (0..310)
             UNITS       "tenth dB"
             MAX-ACCESS  read-create
             STATUS      current
             DESCRIPTION
                "Configured Minimum acceptable Signal/Noise Margin.
                 If the noise margin falls below this level, the modem
                 should attempt to increase its power output.  If that
                 is not possible the modem will attempt to re-initialize
                 or shut down. The noise margin ranges from 0 to 31 dB
                 with 0.1 dB steps (0..310).  This margin should be
                 below the target and maximum margins.
                "
         ::= { adGenVdsl2LineConfProfileEntry 5 }

         adGenVdsl2ConfUsTargetSnrMgn OBJECT-TYPE
             SYNTAX      Integer32 (0..310)
             UNITS       "tenth dB"
             MAX-ACCESS  read-create
             STATUS      current
             DESCRIPTION
                "Configured Target Signal/Noise Margin.  This is the noise
                 margin the modem must achieve with the target BER (10-7)
                 or better to successfully complete initialization.  The
                 noise margin ranges from 0 to 31 dB with 0.1 dB steps
                 (0..310). This margin should be above the minimum margin
                 and below the maximum margin.
                "
         ::= { adGenVdsl2LineConfProfileEntry 6 }

         adGenVdsl2ConfUsMaxSnrMgn OBJECT-TYPE
             SYNTAX      Integer32 (0..310)
             UNITS       "tenth dB"
             MAX-ACCESS  read-create
             STATUS      current
             DESCRIPTION
                "Configured Maximum acceptable Signal/Noise Margin.
                 If the Noise Margin is above this the modem should
                 attempt to reduce its power output to optimize its
                 operation.  The noise margin ranges from 0 to 31 dB
                 with 0.1 dB steps (0..310). This margin should be
                 above the target and minimum margins.
                "
         ::= { adGenVdsl2LineConfProfileEntry 7 }

         adGenVdsl2ConfUsMinSnrMgn  OBJECT-TYPE
             SYNTAX      Integer32 (0..310)
             UNITS       "tenth dB"
             MAX-ACCESS  read-create
             STATUS      current
             DESCRIPTION
                "Configured Minimum acceptable Signal/Noise Margin.
                 If the noise margin falls below this level, the modem
                 should attempt to increase its power output.  If that
                 is not possible the modem will attempt to re-initialize
                 or shut down. The noise margin ranges from 0 to 31 dB
                 with 0.1 dB steps (0..310).  This margin should be
                 below the target and maximum margins.
                "
         ::= { adGenVdsl2LineConfProfileEntry 8 }

         adGenVdsl2LineConfProfileRowStatus OBJECT-TYPE
             SYNTAX          RowStatus
             MAX-ACCESS      read-only
             STATUS          current
             DESCRIPTION
                "This object is used to create a new row or modify or
                 delete an existing row in this table.

                 A profile activated by setting this object to
                 `active'.  When `active' is set, the system
                 will validate the profile.

                 Before a profile can be deleted or taken out of
                 service, (by setting this object to `destroy' or
                 `outOfService') it must be first unreferenced
                 from all associated lines.

                 If the implementator of this MIB has chosen not
                 to implement `dynamic assignment' of profiles, this
                 object's MIN-ACCESS is read-only and its value
                 is always to be `active'.
                "
         ::= { adGenVdsl2LineConfProfileEntry 9 }


         adGenVdsl2ConfServiceMode OBJECT-TYPE
             SYNTAX             INTEGER {
                 multiMode        (1),  -- adapt to the ATUR's mode,
                                        -- assuming T1.413, G.dmt, or G.lite
                                        -- **NOTE**  For adsl2+ line cards,
                                        -- this is adsl2+ multimode
                 t1413            (2),  -- T1.413 Mode
                 gDMT             (3),  -- G.dmt Mode
                 gLite            (4),  -- G.lite Mode
                 g9923            (5),  -- ADSL2 Mode
                 g9924            (6),  -- ADSL2-lite Mode
                 g9925            (7),  -- ADSL2+ Mode
                 readsl           (8),  -- READSL Mode
                 adsl1MultiMode   (9),  -- adsl legacy multimode, to be used
                                        -- by adsl2+ line cards to enable
                                        -- multimode equivalent to that of
                                        -- adsl line cards
                 g9925AnxM        (10), -- ADSL2+ Annex M Mode
                 g9931            (11), -- VDSL1 Mode
                 g9932            (12), -- VDSL2 Mode
                 vdsl2MultiMode   (13), -- Multimode including VDSL2
                 vdsl2PtmFallback (14), -- PTM Fallback mode
                 tseMultimode     (255) -- Multimode according to DMT TSE enables
               }
             MAX-ACCESS         read-create
             STATUS             current
             DESCRIPTION
                "The configuration parameter sets the modem service mode."
         ::= { adGenVdsl2LineConfProfileEntry 10 }

         adGenVdsl2ConfMultiModeDmtTse OBJECT-TYPE
             SYNTAX  Unsigned32
             MAX-ACCESS         read-create
             STATUS             current
             DESCRIPTION
                "Multimode DMT Transmission System Enabling (XTSE).  A list of the
                 different modulation types enabled in this profile for multimode.
                 It is coded in a bit-map representation with 1 or more bits set.
                 A bit set to  '1' means that the VTUs may train in the respective
                 mode for the DSL line.  A bit set to '0' means that the VTUs cannot
                 train in the respective mode for the line.  All 'reserved' bits
                 should be set to '0'.

                     Bit Assignments:
                     Bit 00:         T1E1 ADSL Issue 2
                     Bit 01:         Full Rate ADSL Over POTS
                     Bit 02:         Full Rate ADSL Over ISDN
                     Bit 03:         Full Rate ADSL in TCM-ISDN
                     Bit 04:         Full Rate SSDSL in ISDN Binder
                     Bit 05:         All Digital ADSL
                     Bit 06:         Lite ADSL Over POTS/ISDN
                     Bit 07:         Lite ADSL in TCM-ISDN
                     Bit 08:         ADSL2 Over POTS
                     Bit 09:         ADSL2 Over ISDN
                     Bit 10:         All Digital ADSL2 (POTS)
                     Bit 11:         All Digital ADSL2 (ISDN)
                     Bit 12:         Double Upstream ADSL2
                     Bit 13:         RE-ADSL2 Over POTS
                     Bit 14:         ADSL2 Lite Over POTS
                     Bit 15:         All Digital ADSL2 Lite
                     Bit 16:         ADSL2+ over POTS
                     Bit 17:         ADSL2+ over ISDN
                     Bit 18:         All Digital ADSL2+ (POTS)
                     Bit 19:         All Digital ADSL2+ (ISDN)
                     Bit 20:         Double Upstream ADSL2+
                     Bit 21:         VDSL1
                     Bit 22:         VDSL2 Annex A
                     Bit 23:         VDSL2 Annex B
                     Bit 24:         VDSL2 Annex C
                "
         ::= { adGenVdsl2LineConfProfileEntry 11 }

         adGenVdsl2ConfBandProfiles OBJECT-TYPE
             SYNTAX             Unsigned32
             MAX-ACCESS         read-create
             STATUS             current
             DESCRIPTION
                "Bit-map of ITU-T G.993.2 implementation profiles supported by
                 an VTU-x and can be provisioned on the VDSL2 line.

                     Bit Assignments:
                     Bit 00:         Profile 8A
                     Bit 01:         Profile 8B
                     Bit 02:         Profile 8C
                     Bit 03:         Profile 8D
                     Bit 04:         Profile 12A
                     Bit 05:         Profile 12B
                     Bit 06:         Profile 17A
                     Bit 07:         Profile 30A
                     Bit 08:         Profile 17B (Deprecated)
                     Bit 09:         Profile 35B
               "
         ::= { adGenVdsl2LineConfProfileEntry 12 }

         adGenVdsl2ConfSpecificPsdSelect OBJECT-TYPE
             SYNTAX  INTEGER {
                 vdsl1-ansi-fttcab-m1             (21),
                 vdsl1-ansi-fttcab-m2             (22),
                 vdsl1-ansi-fttex-m1              (23),
                 vdsl1-ansi-fttex-m2              (24),
                 vdsl1-etsi-fttcab-pcab-m1        (41),
                 vdsl1-etsi-fttcab-pcab-m2        (42),
                 vdsl1-etsi-fttex-p1-m1-o-isdn    (43),
                 vdsl1-etsi-fttex-p1-m2-o-isdn    (44),
                 vdsl1-etsi-fttex-p2-m1-o-pots    (45),
                 vdsl1-etsi-fttex-p2-m2-o-pots    (46),
                 vdsl2-a-m1-eu32                  (101),
                 vdsl2-a-m2-eu36                  (102),
                 vdsl2-a-m3-eu40                  (103),
                 vdsl2-a-m4-eu44                  (104),
                 vdsl2-a-m5-eu48                  (105),
                 vdsl2-a-m6-eu52                  (106),
                 vdsl2-a-m7-eu56                  (107),
                 vdsl2-a-m8-eu60                  (108),
                 vdsl2-a-m9-eu64                  (109),
                 vdsl2-a-eu128                    (110),
                 vdsl2-a-m1-998-35b-eu32          (121),
                 vdsl2-a-m9-998-35b-eu64          (129),
                 vdsl2-a-m1-adlu32                (201),
                 vdsl2-a-m2-adlu36                (202),
                 vdsl2-a-m3-adlu40                (203),
                 vdsl2-a-m4-adlu44                (204),
                 vdsl2-a-m5-adlu48                (205),
                 vdsl2-a-m6-adlu52                (206),
                 vdsl2-a-m7-adlu56                (207),
                 vdsl2-a-m8-adlu60                (208),
                 vdsl2-a-m9-adlu64                (209),
                 vdsl2-a-adlu128                  (210),
                 vdsl2-b7-1-997-m1c-a-7           (301),
                 vdsl2-b7-2-997-m1x-m-8           (302),
                 vdsl2-b7-3-997-m1x-m             (303),
                 vdsl2-b7-4-997-m2x-m-8           (304),
                 vdsl2-b7-5-997-m2x-a             (305),
                 vdsl2-b7-6-997-m2x-m             (306),
                 vdsl2-b7-7-hpe17-m1-nus0         (307),
                 vdsl2-b7-8-hpe30-m1-nus0         (308),
                 vdsl2-b7-9-997e17-m2x-nus0       (309),
                 vdsl2-b7-10-997e30-m2x-nus0      (310),
                 vdsl2-b8-1-998-m1x-a             (401),
                 vdsl2-b8-2-998-m1x-b             (402),
                 vdsl2-b8-3-998-m1x-nus0          (403),
                 vdsl2-b8-4-998-m2x-a             (404),
                 vdsl2-b8-5-998-m2x-m             (405),
                 vdsl2-b8-6-998-m2x-b             (406),
                 vdsl2-b8-7-998-m2x-nus0          (407),
                 vdsl2-b8-8-998e17-m2x-nus0       (408),
                 vdsl2-b8-9-998e17-m2x-nus0-m     (409),
                 vdsl2-b8-10-998ade17-m2x-nus0-m  (410),
                 vdsl2-b8-11-998ade17-m2x-a       (411),
                 vdsl2-b8-12-998ade17-m2x-b       (412),
                 vdsl2-b8-13-998e30-m2x-nus0      (413),
                 vdsl2-b8-14-998e30-m2x-nus0-m    (414),
                 vdsl2-b8-15-998ade30-m2x-nus0-m  (415),
                 vdsl2-b8-16-998ade30-m2x-nus0-a  (416),
                 vdsl2-b8-19-998e35-m2x-a         (419),
                 vdsl2-b8-20-998ade35-m2x-a       (420),
                 vdsl2-b8-21-998ade35-m2x-b       (421),
                 vdsl2-b8-22-998ade35-m2x-m       (422),
                 vdsl2-b8-998ade17-m2x-m          (431),
                 vdsl2-b8-998e17-m2x-a            (432),
                 vdsl2-c-fttcab-a                 (501),
                 vdsl2-c-fttcab-m                 (502),
                 vdsl2-c-fttex-a                  (503),
                 vdsl2-c-fttex-m                  (504),
                 vdsl2-c-o-adsl                   (505),
                 vdsl2-c-o-tcmisdn                (506),
                 vdsl2-c-anfp                     (601)
             }
             MAX-ACCESS         read-create
             STATUS             current
             DESCRIPTION
                "The VDSL2 specific PSD selections to be used in the upstream
                 and downstream directions.  The validity of these selections
                 is dependent of the VDSL2 band profile selection.
                "
         ::= { adGenVdsl2LineConfProfileEntry 13 }

         adGenVdsl2ConfUsPsdMaskU0Select OBJECT-TYPE
             SYNTAX  INTEGER {
                 enable  (1),
                 disable (2)
             }
             MAX-ACCESS         read-create
             STATUS             current
             DESCRIPTION
                "Enable or disable of the use of the VDSL2 U0 band in the
                 upstream direction.  U0 is a relatively small frequency band
                 of operation used by ADSL2+/ADSL2/ADSL modems.  It is optional
                 depending on the selected band profile for VDSL2."
         ::= { adGenVdsl2LineConfProfileEntry 14 }

         adGenVdsl2ConfUsTrellis OBJECT-TYPE
             SYNTAX  INTEGER {
                 enable  (1),
                 disable (2)
             }
             MAX-ACCESS         read-create
             STATUS             current
             DESCRIPTION
                "Enable or disable Upstream Trellis Encoding."
         ::= { adGenVdsl2LineConfProfileEntry 15 }

         adGenVdsl2ConfDsTrellis OBJECT-TYPE
             SYNTAX             INTEGER {
                 enable  (1),
                 disable (2)
                 }
             MAX-ACCESS         read-create
             STATUS             current
             DESCRIPTION
                "Enable or disable Downstream Trellis Encoding."
         ::= { adGenVdsl2LineConfProfileEntry 16 }

         adGenVdsl2ConfUsPboSetting OBJECT-TYPE
             SYNTAX             INTEGER {
                 pboOff          (0),
                 pboEnvA         (1),
                 pboEnvB         (2),
                 pboEnvC         (3),
                 pboEnvD         (4),
                 pboEnvE         (5),
                 pboEnvF         (6),
                 pboANFP         (7),
                 pboAuto         (254),
                 pboCustom       (255)
                 }
             MAX-ACCESS         read-create
             STATUS             current
             DESCRIPTION
                "Defines the Upstream Power Backoff mode setting."
         ::= { adGenVdsl2LineConfProfileEntry 17 }

         adGenVdsl2ConfDsPboSetting OBJECT-TYPE
             SYNTAX        INTEGER {
                 pboOff       (0),
                 pboEnvA      (1),
                 pboEnvB      (2),
                 pboEnvC      (3),
                 pboEnvD      (4),
                 pboEnvE      (5),
                 pboEnvF      (6),
                 pboANFP      (7),
                 pboAuto    (254),
                 pboCustom  (255)
                 }
             MAX-ACCESS         read-create
             STATUS             current
             DESCRIPTION
                "Defines the Downstream Power Backoff mode setting."
         ::= { adGenVdsl2LineConfProfileEntry 18 }

         adGenVdsl2ConfUsVnoiseSetting OBJECT-TYPE
             SYNTAX        INTEGER {
                 off          (0),
                 low          (1),
                 med          (2),
                 high         (3),
                 auto       (254),
                 custom     (255)
                 }
             MAX-ACCESS         read-create
             STATUS             current
             DESCRIPTION
                "Defines upstream virtual noise setting."
         ::= { adGenVdsl2LineConfProfileEntry 19 }

         adGenVdsl2ConfDsVnoiseSetting OBJECT-TYPE
             SYNTAX        INTEGER {
                 off          (0),
                 low          (1),
                 med          (2),
                 high         (3),
                 auto       (254),
                 custom     (255)
                 }
             MAX-ACCESS         read-create
             STATUS             current
             DESCRIPTION
                "Defines downstream virtual noise setting."
         ::= { adGenVdsl2LineConfProfileEntry 20 }

         adGenVdsl2ConfUsBitSwap OBJECT-TYPE
             SYNTAX  INTEGER {
                 enable  (1),
                 disable (2)
             }
             MAX-ACCESS         read-create
             STATUS             current
             DESCRIPTION
                "Defines upstream Bit Swap to be enabled or not."
         ::= { adGenVdsl2LineConfProfileEntry 21 }

         adGenVdsl2ConfDsBitSwap OBJECT-TYPE
             SYNTAX  INTEGER {
                 enable  (1),
                 disable (2)
             }
             MAX-ACCESS         read-create
             STATUS             current
             DESCRIPTION
                "Defines downstream Bit Swap to be enabled or not."
         ::= { adGenVdsl2LineConfProfileEntry 22 }

         adGenVdsl2ConfHamBandNotches OBJECT-TYPE
             SYNTAX             Unsigned32
             MAX-ACCESS         read-create
             STATUS             current
             DESCRIPTION
                "A bit-map of transmit power spectral density mask code, used
                 to avoid interference with HAM (Handheld Amateur Radio)
                 radio bands by introducing power control (notching) in one
                 or more of these bands. A bit set indicates notching is enabled.

                     Bit Assignments:
                     Bit 00:    Hamband 1800
                     Bit 01:    Hamband 3500
                     Bit 02:    Hamband 7000
                     Bit 03:    Hamband 10100
                     Bit 04:    Hamband 14000
                     Bit 05:    Hamband 18068
                     Bit 06:    Hamband 21000
                     Bit 07:    Hamband 24890
                     Bit 08:    Hamband 28000
                "
         ::= { adGenVdsl2LineConfProfileEntry 23 }

         adGenVdsl2ConfUsNomAggTxPwr OBJECT-TYPE
             SYNTAX             Integer32 (0..255)
             MAX-ACCESS         read-create
             STATUS             current
             DESCRIPTION
                "The maximum nominal aggregate transmit power in the upstream
                 direction during initialization and Showtime.  It ranges from
                 0 to 255 units of 0.1 dBm (physical values are 0 to 25.5 dBm).
                "
         ::= { adGenVdsl2LineConfProfileEntry 24 }

         adGenVdsl2ConfDsNomAggTxPwr OBJECT-TYPE
             SYNTAX             Integer32
             MAX-ACCESS         read-create
             STATUS             current
             DESCRIPTION
                "The maximum nominal aggregate transmit power in the
                 downstream direction during initialization and Showtime.  It
                 ranges from 0 to 255 units of 0.1 dBm (physical values are 0
                 to 25.5 dBm).
                "
         ::= { adGenVdsl2LineConfProfileEntry 25 }

         adGenVdsl2ConfUsMaxNomTxPsd OBJECT-TYPE
             SYNTAX             Integer32 (-600..300)
             MAX-ACCESS         read-create
             STATUS             current
             DESCRIPTION
                "This parameter represents the maximum nominal transmit PSD in
                 the upstream direction during initialization and showtime
                 (in dBm/Hz). It ranges from -60 to -30 dBm/Hz, with 0.1 dB steps
                 (-600..-300).
                "
         ::= { adGenVdsl2LineConfProfileEntry 26 }

         adGenVdsl2ConfDsMaxNomTxPsd OBJECT-TYPE
             SYNTAX             Integer32 (-600..300)
             MAX-ACCESS         read-create
             STATUS             current
             DESCRIPTION
                "This parameter represents the maximum nominal transmit PSD in
                 the downstream direction during initialization and showtime
                 (in dBm/Hz). It ranges from -60 to -30 dBm/Hz, with 0.1 dB steps
                 (-600..-300).
                "
         ::= { adGenVdsl2LineConfProfileEntry 27 }

         adGenVdsl2ConfUsMaxAggRxPwr OBJECT-TYPE
             SYNTAX             Integer32  (-255..255)
             MAX-ACCESS         read-create
             STATUS             current
             DESCRIPTION
                "The maximum upstream aggregate receive power over the relevant
                 set of sub-carriers.  The xTU-C should verify that the
                 upstream power cutback is such that this maximum aggregate
                 receive power value is honored.  It ranges from -255 to 255
                 units of 0.1 dBm (physical values are -25.5 to 25.5 dBm).
                "
         ::= { adGenVdsl2LineConfProfileEntry 28 }

         adGenVdsl2ConfFramingMode OBJECT-TYPE
             SYNTAX  INTEGER {
                 auto     (0),
                 atm      (1),
                 efm      (2),
                 hdlc     (3)
             }
             MAX-ACCESS         read-create
             STATUS             current
             DESCRIPTION
                 "This is the PMS-TC layer Framing mode setting."
         ::= { adGenVdsl2LineConfProfileEntry 29 }

         adGenVdsl2ConfUsLp0MaxPayloadRate OBJECT-TYPE
             SYNTAX             Unsigned32 (0..96000000)
             UNITS              "bps"
             MAX-ACCESS         read-create
             STATUS             current
             DESCRIPTION
                 "Latency Path 0 upstream maximum payload data rate."
         ::= { adGenVdsl2LineConfProfileEntry 30 }

         adGenVdsl2ConfUsLp0MinPayloadRate OBJECT-TYPE
             SYNTAX             Unsigned32 (0..96000000)
             UNITS              "bps"
             MAX-ACCESS         read-create
             STATUS             current
             DESCRIPTION
                 "Latency Path 0 upstream minimum payload data rate."
         ::= { adGenVdsl2LineConfProfileEntry 31 }

         adGenVdsl2ConfUsLp0MaxDelay OBJECT-TYPE
             SYNTAX             Unsigned32 (0..63)
             UNITS              "msec"
             MAX-ACCESS         read-create
             STATUS             current
             DESCRIPTION
                "Latency Path 0 upstream maximum Interleave Delay.
                 This parameter is the maximum one-way interleaving delay
                 in milli-seconds introduced by the PMS-TC between the
                 alfa and the beta reference points, in the direction of
                 the latency path.  A delay of 0 indicates no maximum delay
                 restrictions are imposed.
                "
         ::= { adGenVdsl2LineConfProfileEntry 32 }

         adGenVdsl2ConfUsLp0MinProtection OBJECT-TYPE
             SYNTAX             Unsigned32 (0..32)
             UNITS              "0.5 Sym"
             MAX-ACCESS         read-create
             STATUS             current
             DESCRIPTION
                "Latency Path 0 upstream Minimum Impulse Noise Protection.
                 This parameter specifies the minimum impulse noise
                 protection for the latency path in 0.5 fractions of DMT
                 symbols.  A value of 0 indicates no minimum bound.
                "
         ::= { adGenVdsl2LineConfProfileEntry 33 }

         adGenVdsl2ConfUsLp0RaRatio OBJECT-TYPE
             SYNTAX             Integer32 (0..100)
             UNITS              "%"
             MAX-ACCESS         read-create
             STATUS             current
             DESCRIPTION
                "This parameter (expressed in %) specifies the ratio that
                 should be taken into account for the latency path when
                 performing rate adaptation in the direction of the
                 channel. The ratio is defined as a percentage in the
                 0 to 100 range.  The sum of all active latency path
                 in a given direction ratios shall add up to 100%.
                "
         ::= { adGenVdsl2LineConfProfileEntry 34 }

         adGenVdsl2ConfUsLp0InitPolicy OBJECT-TYPE
             SYNTAX  INTEGER {
                 ndr (0),
                 inp (1)
             }
             MAX-ACCESS         read-create
             STATUS             current
             DESCRIPTION
                "Selects the US latency path 0 channel framing parameter
                 policy during initialization. The options are to
                 maximize net data rate (ndr) or impulse noise
                 protection (inp).
                "
         ::= { adGenVdsl2LineConfProfileEntry 35 }

         adGenVdsl2ConfDsLp0MaxPayloadRate OBJECT-TYPE
             SYNTAX             Unsigned32 (0..350000000)
             UNITS              "bps"
             MAX-ACCESS         read-create
             STATUS             current
             DESCRIPTION
                 "Latency Path 0 downstream maximum payload data rate."
         ::= { adGenVdsl2LineConfProfileEntry 36 }

         adGenVdsl2ConfDsLp0MinPayloadRate OBJECT-TYPE
             SYNTAX             Unsigned32 (0..350000000)
             UNITS              "bps"
             MAX-ACCESS         read-create
             STATUS             current
             DESCRIPTION
                 "Latency Path 0 downstream minimum payload data rate."
         ::= { adGenVdsl2LineConfProfileEntry 37 }

         adGenVdsl2ConfDsLp0MaxDelay OBJECT-TYPE
             SYNTAX             Unsigned32 (0..63)
             UNITS              "msec"
             MAX-ACCESS         read-create
             STATUS             current
             DESCRIPTION
                "Latency Path 0 downstream maximum Interleave Delay.
                 This parameter is the maximum one-way interleaving delay
                 in milli-seconds introduced by the PMS-TC between the
                 alfa and the beta reference points, in the direction of
                 the latency path.  A delay of 0 indicates no maximum delay
                 restrictions are imposed.
                "
         ::= { adGenVdsl2LineConfProfileEntry 38 }

         adGenVdsl2ConfDsLp0MinProtection OBJECT-TYPE
             SYNTAX             Unsigned32 (0..32)
             UNITS              "0.5 Sym"
             MAX-ACCESS         read-create
             STATUS             current
             DESCRIPTION
                "Latency Path 0 downstream Minimum Impulse Noise Protection.
                 This parameter specifies the minimum impulse noise
                 protection for the latency path in 0.5 fractions of DMT
                 symbols.  A value of 0 indicates no minimum bound.
                "
         ::= { adGenVdsl2LineConfProfileEntry 39 }

         adGenVdsl2ConfDsLp0RaRatio OBJECT-TYPE
             SYNTAX             Integer32 (0..100)
             UNITS              "%"
             MAX-ACCESS         read-create
             STATUS             current
             DESCRIPTION
                "This parameter (expressed in %) specifies the ratio that
                 should be taken into account for the latency path when
                 performing rate adaptation in the direction of the
                 channel. The ratio is defined as a percentage in the
                 0 to 100 range.  The sum of all active latency path
                 in a given direction ratios shall add up to 100%.
                "
         ::= { adGenVdsl2LineConfProfileEntry 40 }

         adGenVdsl2ConfDsLp0InitPolicy OBJECT-TYPE
             SYNTAX  INTEGER {
                 ndr (0),
                 inp (1)
             }
             MAX-ACCESS         read-create
             STATUS             current
             DESCRIPTION
                "Selects the DS latency path 0 channel framing parameter
                 policy during initialization. The options are to
                 maximize net data rate (ndr) or impulse noise
                 protection (inp).
                "
         ::= { adGenVdsl2LineConfProfileEntry 41 }

         adGenVdsl2ConfUsLp1MaxPayloadRate OBJECT-TYPE
             SYNTAX             Unsigned32 (0..96000000)
             UNITS              "bps"
             MAX-ACCESS         read-create
             STATUS             current
             DESCRIPTION
                 "Latency Path 1 upstream maximum payload data rate."
         ::= { adGenVdsl2LineConfProfileEntry 42 }

         adGenVdsl2ConfUsLp1MinPayloadRate OBJECT-TYPE
             SYNTAX             Unsigned32 (0..96000000)
             UNITS              "bps"
             MAX-ACCESS         read-create
             STATUS             current
             DESCRIPTION
                 "Latency Path 1 upstream minimum payload data rate."
         ::= { adGenVdsl2LineConfProfileEntry 43 }

         adGenVdsl2ConfUsLp1MaxDelay OBJECT-TYPE
             SYNTAX             Unsigned32 (0..63)
             UNITS              "msec"
             MAX-ACCESS         read-create
             STATUS             current
             DESCRIPTION
                "Latency Path 1 upstream maximum Interleave Delay.
                 This parameter is the maximum one-way interleaving delay
                 in milli-seconds introduced by the PMS-TC between the
                 alfa and the beta reference points, in the direction of
                 the latency path.  A delay of 0 indicates no maximum delay
                 restrictions are imposed.
                "
         ::= { adGenVdsl2LineConfProfileEntry 44 }

         adGenVdsl2ConfUsLp1MinProtection OBJECT-TYPE
             SYNTAX             Unsigned32 (0..32)
             UNITS              "0.5 Sym"
             MAX-ACCESS         read-create
             STATUS             current
             DESCRIPTION
                "Latency Path 1 upstream Minimum Impulse Noise Protection.
                 This parameter specifies the minimum impulse noise
                 protection for the latency path in 0.5 fractions of DMT
                 symbols.  A value of 0 indicates no minimum bound.
                "
         ::= { adGenVdsl2LineConfProfileEntry 45 }

         adGenVdsl2ConfUsLp1RaRatio OBJECT-TYPE
             SYNTAX             Integer32 (0..100)
             UNITS              "%"
             MAX-ACCESS         read-create
             STATUS             current
             DESCRIPTION
                "This parameter (expressed in %) specifies the ratio that
                 should be taken into account for the latency path when
                 performing rate adaptation in the direction of the
                 channel. The ratio is defined as a percentage in the
                 0 to 100 range.  The sum of all active latency path
                 in a given direction ratios shall add up to 100%.
                "
         ::= { adGenVdsl2LineConfProfileEntry 46 }

         adGenVdsl2ConfUsLp1InitPolicy OBJECT-TYPE
             SYNTAX  INTEGER {
                 ndr (0),
                 inp (1)
             }
             MAX-ACCESS         read-create
             STATUS             current
             DESCRIPTION
                "Selects the US latency path 1 channel framing parameter
                 policy during initialization. The options are to
                 maximize net data rate (ndr) or impulse noise
                 protection (inp).
                "
         ::= { adGenVdsl2LineConfProfileEntry 47 }

         adGenVdsl2ConfDsLp1MaxPayloadRate OBJECT-TYPE
             SYNTAX             Unsigned32 (0..350000000)
             UNITS              "bps"
             MAX-ACCESS         read-create
             STATUS             current
             DESCRIPTION
                 "Latency Path 1 downstream maximum payload data rate."
         ::= { adGenVdsl2LineConfProfileEntry 48 }

         adGenVdsl2ConfDsLp1MinPayloadRate OBJECT-TYPE
             SYNTAX             Unsigned32 (0..350000000)
             UNITS              "bps"
             MAX-ACCESS         read-create
             STATUS             current
             DESCRIPTION
                 "Latency Path 1 downstream minimum payload data rate."
         ::= { adGenVdsl2LineConfProfileEntry 49 }

         adGenVdsl2ConfDsLp1MaxDelay OBJECT-TYPE
             SYNTAX             Unsigned32 (0..63)
             UNITS              "msec"
             MAX-ACCESS         read-create
             STATUS             current
             DESCRIPTION
                "Latency Path 1 downstream maximum Interleave Delay.
                 This parameter is the maximum one-way interleaving delay
                 in milli-seconds introduced by the PMS-TC between the
                 alfa and the beta reference points, in the direction of
                 the latency path.  A delay of 0 indicates no maximum delay
                 restrictions are imposed.
                "
         ::= { adGenVdsl2LineConfProfileEntry 50 }

         adGenVdsl2ConfDsLp1MinProtection OBJECT-TYPE
             SYNTAX             Unsigned32 (0..32)
             UNITS              "0.5 Sym"
             MAX-ACCESS         read-create
             STATUS             current
             DESCRIPTION
                "Latency Path 1 downstream Minimum Impulse Noise Protection.
                 This parameter specifies the minimum impulse noise
                 protection for the latency path in 0.5 fractions of DMT
                 symbols.  A value of 0 indicates no minimum bound.
                "
         ::= { adGenVdsl2LineConfProfileEntry 51 }

         adGenVdsl2ConfDsLp1RaRatio OBJECT-TYPE
             SYNTAX             Integer32 (0..100)
             UNITS              "%"
             MAX-ACCESS         read-create
             STATUS             current
             DESCRIPTION
                "This parameter (expressed in %) specifies the ratio that
                 should be taken into account for the latency path when
                 performing rate adaptation in the direction of the
                 channel. The ratio is defined as a percentage in the
                 0 to 100 range.  The sum of all active latency paths
                 in a given direction ratios shall add up to 100%.
                "
         ::= { adGenVdsl2LineConfProfileEntry 52 }

         adGenVdsl2ConfDsLp1InitPolicy OBJECT-TYPE
             SYNTAX  INTEGER {
                 ndr (0),
                 inp (1)
             }
             MAX-ACCESS         read-create
             STATUS             current
             DESCRIPTION
                "Selects the DS latency path 1 channel framing parameter
                 policy during initialization. The options are to
                 maximize net data rate (ndr) or impulse noise
                 protection (inp).
                "
         ::= { adGenVdsl2LineConfProfileEntry 53 }

         adGenVdsl2ConfUsLp0Type OBJECT-TYPE
             SYNTAX  INTEGER {
                 noChannel (1),        -- channel is disabled
                 fastOnly (2),         -- fast channel
                 interleavedOnly (3)   -- interleaved channel
             }
             MAX-ACCESS         read-create
             STATUS             current
             DESCRIPTION
                "Selects the US latency path 0 channel type options.
                "
         ::= { adGenVdsl2LineConfProfileEntry 54 }

         adGenVdsl2ConfDsLp0Type OBJECT-TYPE
             SYNTAX  INTEGER {
                 noChannel (1),        -- channel is disabled
                 fastOnly (2),         -- fast channel
                 interleavedOnly (3)   -- interleaved channel
             }
             MAX-ACCESS         read-create
             STATUS             current
             DESCRIPTION
                "Selects the DS latency path 0 channel type options.
                "
         ::= { adGenVdsl2LineConfProfileEntry 55 }

         adGenVdsl2ConfUsLp1Type OBJECT-TYPE
             SYNTAX  INTEGER {
                 noChannel (1),        -- channel is disabled
                 fastOnly (2),         -- fast channel
                 interleavedOnly (3)   -- interleaved channel
             }
             MAX-ACCESS         read-create
             STATUS             current
             DESCRIPTION
                "Selects the US latency path 1 channel type options.
                "
         ::= { adGenVdsl2LineConfProfileEntry 56 }

         adGenVdsl2ConfDsLp1Type OBJECT-TYPE
             SYNTAX  INTEGER {
                 noChannel (1),        -- channel is disabled
                 fastOnly (2),         -- fast channel
                 interleavedOnly (3)   -- interleaved channel
                                       -- only
             }
             MAX-ACCESS         read-create
             STATUS             current
             DESCRIPTION
                "Selects the DS latency path 1 channel type options.
                "
         ::= { adGenVdsl2LineConfProfileEntry 57 }

         adGenVdsl2ConfUsRateMode OBJECT-TYPE
             SYNTAX    INTEGER {
                 fixed (1),              -- no rate adaptation
                 adaptAtStartup (2),     -- perform rate adaptation
                                         -- only at initialization
                 adaptAtRuntime (3)      -- perform rate adaptation at
                                         -- any time
             }
             MAX-ACCESS  read-create
             STATUS      current
             DESCRIPTION
                "Defines what form of upstream rate adaptation is
                 configured on this modem.
                "
         ::= { adGenVdsl2LineConfProfileEntry 58 }

         adGenVdsl2ConfUsCustomPboElecLenKL OBJECT-TYPE
             SYNTAX             INTEGER (0..1280)
             UNITS              "0.1 dB"
             MAX-ACCESS         read-create
             STATUS             current
             DESCRIPTION
                 "Upstream power back-off electrical length (KL0)."
         ::= { adGenVdsl2LineConfProfileEntry 59 }

         adGenVdsl2ConfUsCustomPboForceLen OBJECT-TYPE
             SYNTAX  INTEGER {
                 enable  (1),
                 disable (2)
             }
             MAX-ACCESS         read-create
             STATUS             current
             DESCRIPTION
                 "Upstream power back-off force electrical length."
         ::= { adGenVdsl2LineConfProfileEntry 60 }

         adGenVdsl2ConfUsCustomPboBoostMode OBJECT-TYPE
             SYNTAX  INTEGER {
                 enable  (1),
                 disable (2)
             }
             MAX-ACCESS         read-create
             STATUS             current
             DESCRIPTION
                 "Upstream power back-off boost mode."
         ::= { adGenVdsl2LineConfProfileEntry 61 }


         adGenVdsl2ConfDsCustomPboElecLen OBJECT-TYPE
             SYNTAX             INTEGER (0..2555)
             UNITS              "0.1 dB"
             MAX-ACCESS         read-create
             STATUS             current
             DESCRIPTION
                 "Downstream G997.1 Exchange side electrical length. only multiples of .5 are valid"
         ::= { adGenVdsl2LineConfProfileEntry 62 }

         adGenVdsl2ConfDsCustomPboCableA OBJECT-TYPE
             SYNTAX             INTEGER (0..640)
             UNITS              "scalar"
             MAX-ACCESS         read-create
             STATUS             current
             DESCRIPTION
                 "Downstream G997.1 Exchange side cable parameter A."
         ::= { adGenVdsl2LineConfProfileEntry 63 }

         adGenVdsl2ConfDsCustomPboCableB OBJECT-TYPE
             SYNTAX             INTEGER (0..640)
             UNITS              "scalar"
             MAX-ACCESS         read-create
             STATUS             current
             DESCRIPTION
                 "Downstream G997.1 Exchange side cable parameter B."
         ::= { adGenVdsl2LineConfProfileEntry 64 }

         adGenVdsl2ConfDsCustomPboCableC OBJECT-TYPE
             SYNTAX             INTEGER (0..640)
             UNITS              "scalar"
             MAX-ACCESS         read-create
             STATUS             current
             DESCRIPTION
                 "Downstream G997.1 Exchange side cable parameter C."
         ::= { adGenVdsl2LineConfProfileEntry 65 }

         adGenVdsl2ConfDsCustomPboMinSignal OBJECT-TYPE
             SYNTAX             INTEGER (0..1275)
             UNITS              "0.1 dB"
             MAX-ACCESS         read-create
             STATUS             current
             DESCRIPTION
                 "Downstream G997.1 Minimum Usable Signal. only multiples of .5 are valid"
         ::= { adGenVdsl2LineConfProfileEntry 66 }

         adGenVdsl2ConfDsCustomPboMinFreq OBJECT-TYPE
             SYNTAX             INTEGER (0..2048)
             UNITS              "4.3125kHz tones"
             MAX-ACCESS         read-create
             STATUS             current
             DESCRIPTION
                 "Downstream G997.1 Minimum Power Backoff Frequency"
         ::= { adGenVdsl2LineConfProfileEntry 67 }

         adGenVdsl2ConfDsCustomPboMaxFreq OBJECT-TYPE
             SYNTAX             INTEGER (32..4095)
             UNITS              "4.3125kHz tones"
             MAX-ACCESS         read-create
             STATUS             current
             DESCRIPTION
                 "Downstream G997.1 Maximum Power Backoff Frequency"
         ::= { adGenVdsl2LineConfProfileEntry 68 }


         adGenVdsl2ConfAnfpCalValue OBJECT-TYPE
             SYNTAX             INTEGER (0..52)
             UNITS              "dB"
             MAX-ACCESS         read-create
             STATUS             current
             DESCRIPTION
                 "ANFP loss calibration value"
         ::= { adGenVdsl2LineConfProfileEntry 69 }

         adGenVdsl2ConfDsDownshiftSnrMgn OBJECT-TYPE
             SYNTAX             Integer32 (0..310)
             UNITS              "tenth dB"
             MAX-ACCESS         read-create
             STATUS             current
             DESCRIPTION
                 "Threshold SNR margin to trigger a downstream downshift."
             DEFVAL { 50 }
         ::= { adGenVdsl2LineConfProfileEntry 70 }

         adGenVdsl2ConfDsUpshiftSnrMgn OBJECT-TYPE
             SYNTAX             Integer32 (0..310)
             UNITS              "tenth dB"
             MAX-ACCESS         read-create
             STATUS             current
             DESCRIPTION
                 "Threshold SNR margin to trigger a downstream upshift."
             DEFVAL { 70 }
         ::= { adGenVdsl2LineConfProfileEntry 71 }

         adGenVdsl2ConfDsMinUpshiftTime OBJECT-TYPE
             SYNTAX             Unsigned32 (0..16383)
             UNITS              "seconds"
             MAX-ACCESS         read-create
             STATUS             current
             DESCRIPTION
                 "Minimum configured time that must elapse
                 between downstream upshifts.  A value of 2
                 indicates a downshift cannot occur unless 2
                 seconds have elapsed since the previous
                 downshift."
             DEFVAL { 2 }
         ::= { adGenVdsl2LineConfProfileEntry 72 }

         adGenVdsl2ConfDsMinDownshiftTime OBJECT-TYPE
             SYNTAX             Unsigned32 (0..16383)
             UNITS              "seconds"
             MAX-ACCESS         read-create
             STATUS             current
             DESCRIPTION
                 "Minimum configured time that must elapse
                 between downstream downshifts.  A value of 2
                 indicates a downshift cannot occur unless 2
                 seconds have elapsed since the previous
                 downshift."
             DEFVAL { 2 }
         ::= { adGenVdsl2LineConfProfileEntry 73 }

         adGenVdsl2ConfUsDownshiftSnrMgn OBJECT-TYPE
             SYNTAX             Integer32 (0..310)
             UNITS              "tenth dB"
             MAX-ACCESS         read-create
             STATUS             current
             DESCRIPTION
                 "Threshold SNR margin to trigger a upstream downshift."
             DEFVAL { 50 }
         ::= { adGenVdsl2LineConfProfileEntry 74 }

         adGenVdsl2ConfUsUpshiftSnrMgn OBJECT-TYPE
             SYNTAX             Integer32 (0..310)
             UNITS              "tenth dB"
             MAX-ACCESS         read-create
             STATUS             current
             DESCRIPTION
                 "Threshold SNR margin to trigger a upstream upshift."
             DEFVAL { 70 }
         ::= { adGenVdsl2LineConfProfileEntry 75 }

         adGenVdsl2ConfUsMinUpshiftTime OBJECT-TYPE
             SYNTAX             Unsigned32 (0..16383)
             UNITS              "seconds"
             MAX-ACCESS         read-create
             STATUS             current
             DESCRIPTION
                 "Minimum configured time that must elapse
                 between upstream upshifts.  A value of 2
                 indicates a downshift cannot occur unless 2
                 seconds have elapsed since the previous
                 downshift."
             DEFVAL { 2 }
         ::= { adGenVdsl2LineConfProfileEntry 76 }

         adGenVdsl2ConfUsMinDownshiftTime OBJECT-TYPE
             SYNTAX             Unsigned32 (0..16383)
             UNITS              "seconds"
             MAX-ACCESS         read-create
             STATUS             current
             DESCRIPTION
                 "Minimum configured time that must elapse
                 between upstream downshifts.  A value of 2
                 indicates a downshift cannot occur unless 2
                 seconds have elapsed since the previous
                 downshift."
             DEFVAL { 2 }
         ::= { adGenVdsl2LineConfProfileEntry 77 }

         adGenVdsl2ConfUsLp0RtxSetting OBJECT-TYPE
             SYNTAX             INTEGER {
                 rtxOff         (0),
                 rtxCustom      (255)
                 }
             MAX-ACCESS         read-create
             STATUS             current
             DESCRIPTION
                 "Retransmission setting"
             DEFVAL { rtxOff }
         ::= { adGenVdsl2LineConfProfileEntry 78 }

         adGenVdsl2ConfUsLp0CustomRtxMaxNdr OBJECT-TYPE
             SYNTAX             Unsigned32 (0..96000000)
             UNITS              "bps"
             MAX-ACCESS         read-create
             STATUS             current
             DESCRIPTION
                 "Retransmission maximum allowed net data rate.
                  Valid values are in 8000 bps increments."
             DEFVAL { 50000000 }
         ::= { adGenVdsl2LineConfProfileEntry 79 }

         adGenVdsl2ConfUsLp0CustomRtxMinDelay OBJECT-TYPE
             SYNTAX             INTEGER (0..63)
             UNITS              "ms"
             MAX-ACCESS         read-create
             STATUS             current
             DESCRIPTION
                 "Retransmission minimum allowed delay"
             DEFVAL { 0 }
         ::= { adGenVdsl2LineConfProfileEntry 80 }

         adGenVdsl2ConfUsLp0CustomRtxMaxDelay OBJECT-TYPE
             SYNTAX             INTEGER (1..63)
             UNITS              "ms"
             MAX-ACCESS         read-create
             STATUS             current
             DESCRIPTION
                 "Retransmission maximum allowed delay"
             DEFVAL { 10 }
         ::= { adGenVdsl2LineConfProfileEntry 81 }

         adGenVdsl2ConfUsLp0CustomRtxInpMinShine OBJECT-TYPE
             SYNTAX             INTEGER (0..63)
             UNITS              "DMT symbols"
             MAX-ACCESS         read-create
             STATUS             current
             DESCRIPTION
                 "Retransmission minimum impulse noise protection against
                  SHINE when subcarrier spacing is 4.3125Khz"
             DEFVAL { 1 }
         ::= { adGenVdsl2LineConfProfileEntry 82 }

         adGenVdsl2ConfUsLp0CustomRtxInpMinRein OBJECT-TYPE
             SYNTAX             INTEGER (0..7)
             UNITS              "DMT symbols"
             MAX-ACCESS         read-create
             STATUS             current
             DESCRIPTION
                 "Retransmission minimum impulse noise protection against
                  REIN when subcarrier spacing is 4.3125Khz"
             DEFVAL { 1 }
         ::= { adGenVdsl2LineConfProfileEntry 83 }

         adGenVdsl2ConfUsLp0CustomRtxIatRein OBJECT-TYPE
             SYNTAX             INTEGER {
                 rtxRein100Hz   (1),
                 rtxRein120Hz   (2)
                 }
             MAX-ACCESS         read-create
             STATUS             current
             DESCRIPTION
                 "Retransmission inter-arrival time for REIN"
             DEFVAL { rtxRein120Hz }
         ::= { adGenVdsl2LineConfProfileEntry 84 }

         adGenVdsl2ConfUsLp0CustomRtxLeftrThresh OBJECT-TYPE
             SYNTAX             INTEGER (0..99)
             UNITS              "Percent of NDR"
             MAX-ACCESS         read-create
             STATUS             current
             DESCRIPTION
                 "Retransmission parameter that specifies the fraction of
                  the NDR used as the threshold to declare leftr defects.
                  A minimum value of ETR/2 is required. A special value
                  of 0 sets the threshold to ETR.
                     NDR - net data rate
                     ETR - expected throughput"
             DEFVAL { 0 }
         ::= { adGenVdsl2LineConfProfileEntry 85 }

         adGenVdsl2ConfDsLp0RtxSetting OBJECT-TYPE
             SYNTAX             INTEGER {
                 rtxOff         (0),
                 rtxCustom      (255)
                 }
             MAX-ACCESS         read-create
             STATUS             current
             DESCRIPTION
                 "Retransmission setting"
             DEFVAL { rtxOff }
         ::= { adGenVdsl2LineConfProfileEntry 86 }

         adGenVdsl2ConfDsLp0CustomRtxMaxNdr OBJECT-TYPE
             SYNTAX             Unsigned32 (0..350000000)
             UNITS              "bps"
             MAX-ACCESS         read-create
             STATUS             current
             DESCRIPTION
                 "Retransmission maximum allowed net data rate.
                  Valid values are in 8000 bps increments."
             DEFVAL { 100000000 }
         ::= { adGenVdsl2LineConfProfileEntry 87 }

         adGenVdsl2ConfDsLp0CustomRtxMinDelay OBJECT-TYPE
             SYNTAX             INTEGER (0..63)
             UNITS              "ms"
             MAX-ACCESS         read-create
             STATUS             current
             DESCRIPTION
                 "Retransmission minimum allowed delay"
             DEFVAL { 0 }
         ::= { adGenVdsl2LineConfProfileEntry 88 }

         adGenVdsl2ConfDsLp0CustomRtxMaxDelay OBJECT-TYPE
             SYNTAX             INTEGER (1..63)
             UNITS              "ms"
             MAX-ACCESS         read-create
             STATUS             current
             DESCRIPTION
                 "Retransmission maximum allowed delay"
             DEFVAL { 10 }
         ::= { adGenVdsl2LineConfProfileEntry 89 }

         adGenVdsl2ConfDsLp0CustomRtxInpMinShine OBJECT-TYPE
             SYNTAX             INTEGER (0..63)
             UNITS              "DMT symbols"
             MAX-ACCESS         read-create
             STATUS             current
             DESCRIPTION
                 "Retransmission minimum impulse noise protection against
                  SHINE when subcarrier spacing is 4.3125Khz"
             DEFVAL { 2 }
         ::= { adGenVdsl2LineConfProfileEntry 90 }

         adGenVdsl2ConfDsLp0CustomRtxInpMinRein OBJECT-TYPE
             SYNTAX             INTEGER (0..7)
             UNITS              "DMT symbols"
             MAX-ACCESS         read-create
             STATUS             current
             DESCRIPTION
                 "Retransmission minimum impulse noise protection against
                  REIN when subcarrier spacing is 4.3125Khz"
             DEFVAL { 2 }
         ::= { adGenVdsl2LineConfProfileEntry 91 }

         adGenVdsl2ConfDsLp0CustomRtxIatRein OBJECT-TYPE
             SYNTAX             INTEGER {
                 rtxRein100Hz   (1),
                 rtxRein120Hz   (2)
                 }
             MAX-ACCESS         read-create
             STATUS             current
             DESCRIPTION
                 "Retransmission inter-arrival time for REIN"
             DEFVAL { rtxRein120Hz }
         ::= { adGenVdsl2LineConfProfileEntry 92 }

         adGenVdsl2ConfDsLp0CustomRtxLeftrThresh OBJECT-TYPE
             SYNTAX             INTEGER (0..99)
             UNITS              "Percent of NDR"
             MAX-ACCESS         read-create
             STATUS             current
             DESCRIPTION
                 "Retransmission parameter that specifies the fraction of
                  the NDR used as the threshold to declare leftr defects.
                  A minimum value of ETR/2 is required. A special value
                  of 0 sets the threshold to ETR.
                     NDR - net data rate
                     ETR - expected throughput"
             DEFVAL { 0 }
         ::= { adGenVdsl2LineConfProfileEntry 93 }

         adGenVdsl2ConfUsLp1RtxSetting OBJECT-TYPE
             SYNTAX             INTEGER {
                 rtxOff         (0),
                 rtxCustom      (255)
                 }
             MAX-ACCESS         read-create
             STATUS             current
             DESCRIPTION
                 "Retransmission setting"
             DEFVAL { rtxOff }
         ::= { adGenVdsl2LineConfProfileEntry 94 }

         adGenVdsl2ConfUsLp1CustomRtxMaxNdr OBJECT-TYPE
             SYNTAX             Unsigned32 (0..96000000)
             UNITS              "bps"
             MAX-ACCESS         read-create
             STATUS             current
             DESCRIPTION
                 "Retransmission maximum allowed net data rate.
                  Valid values are in 8000 bps increments."
             DEFVAL { 50000000 }
         ::= { adGenVdsl2LineConfProfileEntry 95 }

         adGenVdsl2ConfUsLp1CustomRtxMinDelay OBJECT-TYPE
             SYNTAX             INTEGER (0..63)
             UNITS              "ms"
             MAX-ACCESS         read-create
             STATUS             current
             DESCRIPTION
                 "Retransmission minimum allowed delay"
             DEFVAL { 0 }
         ::= { adGenVdsl2LineConfProfileEntry 96 }

         adGenVdsl2ConfUsLp1CustomRtxMaxDelay OBJECT-TYPE
             SYNTAX             INTEGER (1..63)
             UNITS              "ms"
             MAX-ACCESS         read-create
             STATUS             current
             DESCRIPTION
                 "Retransmission maximum allowed delay"
             DEFVAL { 10 }
         ::= { adGenVdsl2LineConfProfileEntry 97 }

         adGenVdsl2ConfUsLp1CustomRtxInpMinShine OBJECT-TYPE
             SYNTAX             INTEGER (0..63)
             UNITS              "DMT symbols"
             MAX-ACCESS         read-create
             STATUS             current
             DESCRIPTION
                 "Retransmission minimum impulse noise protection against
                  SHINE when subcarrier spacing is 4.3125Khz"
             DEFVAL { 1 }
         ::= { adGenVdsl2LineConfProfileEntry 98 }

         adGenVdsl2ConfUsLp1CustomRtxInpMinRein OBJECT-TYPE
             SYNTAX             INTEGER (0..7)
             UNITS              "DMT symbols"
             MAX-ACCESS         read-create
             STATUS             current
             DESCRIPTION
                 "Retransmission minimum impulse noise protection against
                  REIN when subcarrier spacing is 4.3125Khz"
             DEFVAL { 1 }
         ::= { adGenVdsl2LineConfProfileEntry 99 }

         adGenVdsl2ConfUsLp1CustomRtxIatRein OBJECT-TYPE
             SYNTAX             INTEGER {
                 rtxRein100Hz   (1),
                 rtxRein120Hz   (2)
                 }
             MAX-ACCESS         read-create
             STATUS             current
             DESCRIPTION
                 "Retransmission inter-arrival time for REIN"
             DEFVAL { rtxRein120Hz }
         ::= { adGenVdsl2LineConfProfileEntry 100 }

         adGenVdsl2ConfUsLp1CustomRtxLeftrThresh OBJECT-TYPE
             SYNTAX             INTEGER (0..99)
             UNITS              "Percent of NDR"
             MAX-ACCESS         read-create
             STATUS             current
             DESCRIPTION
                 "Retransmission parameter that specifies the fraction of
                  the NDR used as the threshold to declare leftr defects.
                  A minimum value of ETR/2 is required. A special value
                  of 0 sets the threshold to ETR.
                     NDR - net data rate
                     ETR - expected throughput"
             DEFVAL { 0 }
         ::= { adGenVdsl2LineConfProfileEntry 101 }

         adGenVdsl2ConfDsLp1RtxSetting OBJECT-TYPE
             SYNTAX             INTEGER {
                 rtxOff         (0),
                 rtxCustom      (255)
                 }
             MAX-ACCESS         read-create
             STATUS             current
             DESCRIPTION
                 "Retransmission setting"
             DEFVAL { rtxOff }
         ::= { adGenVdsl2LineConfProfileEntry 102 }

         adGenVdsl2ConfDsLp1CustomRtxMaxNdr OBJECT-TYPE
             SYNTAX             Unsigned32 (0..350000000)
             UNITS              "bps"
             MAX-ACCESS         read-create
             STATUS             current
             DESCRIPTION
                 "Retransmission maximum allowed net data rate.
                  Valid values are in 8000 bps increments."
             DEFVAL { 100000000 }
         ::= { adGenVdsl2LineConfProfileEntry 103 }

         adGenVdsl2ConfDsLp1CustomRtxMinDelay OBJECT-TYPE
             SYNTAX             INTEGER (0..63)
             UNITS              "ms"
             MAX-ACCESS         read-create
             STATUS             current
             DESCRIPTION
                 "Retransmission minimum allowed delay"
             DEFVAL { 0 }
         ::= { adGenVdsl2LineConfProfileEntry 104 }

         adGenVdsl2ConfDsLp1CustomRtxMaxDelay OBJECT-TYPE
             SYNTAX             INTEGER (1..63)
             UNITS              "ms"
             MAX-ACCESS         read-create
             STATUS             current
             DESCRIPTION
                 "Retransmission maximum allowed delay"
             DEFVAL { 10 }
         ::= { adGenVdsl2LineConfProfileEntry 105 }

         adGenVdsl2ConfDsLp1CustomRtxInpMinShine OBJECT-TYPE
             SYNTAX             INTEGER (0..63)
             UNITS              "DMT symbols"
             MAX-ACCESS         read-create
             STATUS             current
             DESCRIPTION
                 "Retransmission minimum impulse noise protection against
                  SHINE when subcarrier spacing is 4.3125Khz"
             DEFVAL { 2 }
         ::= { adGenVdsl2LineConfProfileEntry 106 }

         adGenVdsl2ConfDsLp1CustomRtxInpMinRein OBJECT-TYPE
             SYNTAX             INTEGER (0..7)
             UNITS              "DMT symbols"
             MAX-ACCESS         read-create
             STATUS             current
             DESCRIPTION
                 "Retransmission minimum impulse noise protection against
                  REIN when subcarrier spacing is 4.3125Khz"
             DEFVAL { 2 }
         ::= { adGenVdsl2LineConfProfileEntry 107 }

         adGenVdsl2ConfDsLp1CustomRtxIatRein OBJECT-TYPE
             SYNTAX             INTEGER {
                 rtxRein100Hz   (1),
                 rtxRein120Hz   (2)
                 }
             MAX-ACCESS         read-create
             STATUS             current
             DESCRIPTION
                 "Retransmission inter-arrival time for REIN"
             DEFVAL { rtxRein120Hz }
         ::= { adGenVdsl2LineConfProfileEntry 108 }

         adGenVdsl2ConfDsLp1CustomRtxLeftrThresh OBJECT-TYPE
             SYNTAX             INTEGER (0..99)
             UNITS              "Percent of NDR"
             MAX-ACCESS         read-create
             STATUS             current
             DESCRIPTION
                 "Retransmission parameter that specifies the fraction of
                  the NDR used as the threshold to declare leftr defects.
                  A minimum value of ETR/2 is required. A special value
                  of 0 sets the threshold to ETR.
                     NDR - net data rate
                     ETR - expected throughput"
             DEFVAL { 0 }
         ::= { adGenVdsl2LineConfProfileEntry 109 }

         adGenVdsl2ConfAmRadioFreqMask1 OBJECT-TYPE
             SYNTAX             INTEGER (0|540..1700)
             UNITS              "kHz"
             MAX-ACCESS         read-create
             STATUS             current
             DESCRIPTION
                 "AM radio station 1 center frequency in kHz. Carrier
                 frequencies around this center frequency will be masked
                 off. The value 0 will disable the masking of the carrier
                 frequencies around radio station 1 center frequency."
             DEFVAL { 0 }
         ::= { adGenVdsl2LineConfProfileEntry 110 }

         adGenVdsl2ConfAmRadioFreqMask2 OBJECT-TYPE
             SYNTAX             INTEGER (0|540..1700)
             UNITS              "kHz"
             MAX-ACCESS         read-create
             STATUS             current
             DESCRIPTION
                 "AM radio station 2 center frequency in kHz. Carrier
                 frequencies around this center frequency will be masked
                 off. The value 0 will disable the masking of the carrier
                 frequencies around radio station 2 center frequency."
             DEFVAL { 0 }
         ::= { adGenVdsl2LineConfProfileEntry 111 }

         adGenVdsl2ConfAmRadioFreqMask3 OBJECT-TYPE
             SYNTAX             INTEGER (0|540..1700)
             UNITS              "kHz"
             MAX-ACCESS         read-create
             STATUS             current
             DESCRIPTION
                 "AM radio station 3 center frequency in kHz. Carrier
                 frequencies around this center frequency will be masked
                 off. The value 0 will disable the masking of the carrier
                 frequencies around radio station 3 center frequency."
             DEFVAL { 0 }
         ::= { adGenVdsl2LineConfProfileEntry 112 }

         adGenVdsl2ConfAmRadioFreqMask4 OBJECT-TYPE
             SYNTAX             INTEGER (0|540..1700)
             UNITS              "kHz"
             MAX-ACCESS         read-create
             STATUS             current
             DESCRIPTION
                 "AM radio station 4 center frequency in kHz. Carrier
                 frequencies around this center frequency will be masked
                 off. The value 0 will disable the masking of the carrier
                 frequencies around radio station 4 center frequency."
             DEFVAL { 0 }
         ::= { adGenVdsl2LineConfProfileEntry 113 }

         adGenVdsl2ConfAmRadioFreqMask5 OBJECT-TYPE
             SYNTAX             INTEGER (0|540..1700)
             UNITS              "kHz"
             MAX-ACCESS         read-create
             STATUS             current
             DESCRIPTION
                 "AM radio station 5 center frequency in kHz. Carrier
                 frequencies around this center frequency will be masked
                 off. The value 0 will disable the masking of the carrier
                 frequencies around radio station 5 center frequency."
             DEFVAL { 0 }
         ::= { adGenVdsl2LineConfProfileEntry 114 }

         adGenVdsl2ConfAmRadioFreqMask6 OBJECT-TYPE
             SYNTAX             INTEGER (0|540..1700)
             UNITS              "kHz"
             MAX-ACCESS         read-create
             STATUS             current
             DESCRIPTION
                 "AM radio station 6 center frequency in kHz. Carrier
                 frequencies around this center frequency will be masked
                 off. The value 0 will disable the masking of the carrier
                 frequencies around radio station 6 center frequency."
             DEFVAL { 0 }
         ::= { adGenVdsl2LineConfProfileEntry 115 }

         adGenVdsl2ConfMemorySplitRatio OBJECT-TYPE
             SYNTAX  INTEGER {
                 oneToOne  (1),       -- DS:US interleaver memory allocation ratio of 1:1
                 twoToOne  (2),       -- DS:US interleaver memory allocation ratio of 2:1
                 threeToOne(3),       -- DS:US interleaver memory allocation ratio of 3:1
                 fourToOne (4),       -- DS:US interleaver memory allocation ratio of 4:1
                 fiveToOne (5)        -- DS:US interleaver memory allocation ratio of 5:1
             }
             MAX-ACCESS         read-create
             STATUS             current
             DESCRIPTION
                 "This parameter defines the ratio of how the interleaver memory
		  is allocated between the downstream and upstream directions.
		  For example a ratio of 2:1 will assign twice as much interleaver
		  memory to the downstream path than the upstream."
             DEFVAL { twoToOne }
         ::= { adGenVdsl2LineConfProfileEntry 116 }

         adGenVdsl2ConfRateAdaptConfigMode OBJECT-TYPE
             SYNTAX  INTEGER {
                 manual  (1),       -- user inputs for shift margins and times are used for SRA.
                 auto    (2),       -- automatic settings based on target margin and fixed times are used for SRA.
             }
             MAX-ACCESS         read-create
             STATUS             current
             DESCRIPTION
                 "This parameter determines how the upshift and downshift margins and times
                  are configured when the rate mode is set to adaptAtRuntime."
             DEFVAL { manual }
         ::= { adGenVdsl2LineConfProfileEntry 117 }

         -- ============ Prov Group (Alarm Profile) ==========================
         adGenVdsl2LineAlarmConfProfileTable    OBJECT-TYPE
             SYNTAX          SEQUENCE OF AdGenVdsl2LineAlarmConfProfileEntry
             MAX-ACCESS      not-accessible
             STATUS          current
             DESCRIPTION
                 "This table contains information on the VDSL2 line
                 configuration.  One entry in this table reflects a
                 profile defined by a manager which can be used to
                 configure the modem for a physical line"
         ::= { adGenVdsl2Prov 2 }

         adGenVdsl2LineAlarmConfProfileEntry    OBJECT-TYPE
             SYNTAX          AdGenVdsl2LineAlarmConfProfileEntry
             MAX-ACCESS      not-accessible
             STATUS          current
             DESCRIPTION
                "Each entry consists of a list of parameters that
                 represents the configuration of an VDSL2 modem.

                 `Static' profiles -  profiles are automaticly
		 created or destroyed as VDSL2 physical lines
		 are discovered and removed by the system.
		 The name of the profile will be equivalent to
                 the decimal value of the line's interface index.
                "
             INDEX { IMPLIED adGenVdsl2LineAlarmConfProfileName }

         ::= { adGenVdsl2LineAlarmConfProfileTable 1}

         AdGenVdsl2LineAlarmConfProfileEntry ::=
             SEQUENCE {
                 adGenVdsl2LineAlarmConfProfileName          DisplayString,
                 adGenVdsl2VtucThreshSnrMgn                  Integer32,
                 adGenVdsl2VtucThresh15MinLofs               Gauge32,
                 adGenVdsl2VtucThresh15MinLoss               Gauge32,
                 adGenVdsl2VtucThresh15MinLols               Gauge32,
                 adGenVdsl2VtucThresh15MinLprs               Gauge32,
                 adGenVdsl2VtucThresh15MinEs                 Gauge32,
                 adGenVdsl2VtucThresh15MinSes                Gauge32,
                 adGenVdsl2VtucThresh15MinUas                Gauge32,
                 adGenVdsl2VturThreshSnrMgn                  Integer32,
                 adGenVdsl2VturThresh15MinLofs               Gauge32,
                 adGenVdsl2VturThresh15MinLoss               Gauge32,
                 adGenVdsl2VturThresh15MinLprs               Gauge32,
                 adGenVdsl2VturThresh15MinEs                 Gauge32,
                 adGenVdsl2VturThresh15MinSes                Gauge32,
                 adGenVdsl2VturThresh15MinUas                Gauge32,
                 adGenVdsl2LineAlarmConfProfileRowStatus     RowStatus,
                 adGenVdsl2ThreshUsLp0RateUp                 Gauge32,
                 adGenVdsl2ThreshUsLp0RateDown               Gauge32,
                 adGenVdsl2ThreshDsLp0RateUp                 Gauge32,
                 adGenVdsl2ThreshDsLp0RateDown               Gauge32,
                 adGenVdsl2ThreshUsLp1RateUp                 Gauge32,
                 adGenVdsl2ThreshUsLp1RateDown               Gauge32,
                 adGenVdsl2ThreshDsLp1RateUp                 Gauge32,
                 adGenVdsl2ThreshDsLp1RateDown               Gauge32
             }

         adGenVdsl2LineAlarmConfProfileName    OBJECT-TYPE
             SYNTAX          DisplayString (SIZE (1..10))
             MAX-ACCESS      not-accessible
             STATUS          current
             DESCRIPTION
                "This object is used by the line configuration table
                 in order to identify a row of this table.

                 This value cannot be user-specified and is not dynamic.

                 There is a one-to-one relationship between each line and
                 its profile.  The profile name algorithmicly represents
		 the Line's ifIndex.

                 Therefore, the profile's name is a decimalized string
                 of the ifIndex that is fixed-length (10) with
                 leading zero(s).  For example, the profile name for
                 ifIndex which equals '15' will be '0000000015'.
                "
         ::= { adGenVdsl2LineAlarmConfProfileEntry 1}

         adGenVdsl2VtucThreshSnrMgn OBJECT-TYPE
             SYNTAX      Integer32(0..99)
             UNITS       "dB"
             MAX-ACCESS  read-create
             STATUS      current
             DESCRIPTION
                "The SNR margin on the VDSL2 interface below which
                 the SNMP agent sends an adGenVdsl2USPerfSNRThresTrap.
                 One trap will be sent per interval per interface.
                 A value of '0' will disable the trap.
                "
         ::= { adGenVdsl2LineAlarmConfProfileEntry 2}

         adGenVdsl2VtucThresh15MinLofs OBJECT-TYPE
             SYNTAX      Gauge32(0..900)
             UNITS       "seconds"
             MAX-ACCESS  read-create
             STATUS      current
             DESCRIPTION
                "The number of Loss of Frame Seconds
                 encountered by an VDSL2 interface within any given 15
                 minutes performance data collection period, which
                 causes the SNMP agent to send an
                 adGenVdsl2VtucPerfLofsThreshTrap.
                 One trap will be sent per interval per interface.
                 A value of `0' will disable the trap.
                "
         ::= { adGenVdsl2LineAlarmConfProfileEntry 3}

         adGenVdsl2VtucThresh15MinLoss  OBJECT-TYPE
             SYNTAX      Gauge32(0..900)
             UNITS       "seconds"
             MAX-ACCESS  read-create
             STATUS      current
             DESCRIPTION
                "The number of Loss of Signal Seconds
                 encountered by VDSL2 interface within any given 15
                 minutes performance data collection period, which
                 causes the SNMP agent to send an
                 adGenVdsl2VtucPerfLossThreshTrap.
                 One trap will be sent per interval per interface.
                 A value of `0' will disable the trap.
                "
         ::= { adGenVdsl2LineAlarmConfProfileEntry 4}

         adGenVdsl2VtucThresh15MinLols  OBJECT-TYPE
             SYNTAX      Gauge32(0..900)
             UNITS       "seconds"
             MAX-ACCESS  read-create
             STATUS      current
             DESCRIPTION
                "The number of Loss of Link Seconds
                 encountered by VDSL2 interface within any given 15
                 minutes performance data collection period, which
                 causes the SNMP agent to send an
                 adGenVdsl2VtucPerfLolsThreshTrap.
                 One trap will be sent per interval per interface.
                 A value of `0' will disable the trap.
                "
         ::= { adGenVdsl2LineAlarmConfProfileEntry 5}

         adGenVdsl2VtucThresh15MinLprs  OBJECT-TYPE
             SYNTAX      Gauge32(0..900)
             UNITS       "seconds"
             MAX-ACCESS  read-create
             STATUS      current
             DESCRIPTION
                "The number of Loss of Power Seconds
                 encountered by an VDSL2 interface within any given 15
                 minutes performance data collection period, which
                 causes the SNMP agent to send an
                 adGenVdsl2VtucPerfLprsThreshTrap.
                 One trap will be sent per interval per interface.
                 A value of `0' will disable the trap.
                "
         ::= { adGenVdsl2LineAlarmConfProfileEntry 6}

         adGenVdsl2VtucThresh15MinEs  OBJECT-TYPE
             SYNTAX      Gauge32
             UNITS       "seconds"
             MAX-ACCESS  read-create
             STATUS      current
             DESCRIPTION
                "The number of Errored Seconds
                 encountered by an VDSL2 interface within any given 15
                 minutes performance data collection period, which
                 causes the SNMP agent to send an
                 adGenVdsl2VtucPerfESThreshTrap.
                 One trap will be sent per interval per interface.
                 A value of `0' will disable the trap.
                "
         ::= { adGenVdsl2LineAlarmConfProfileEntry 7}

         adGenVdsl2VtucThresh15MinSes  OBJECT-TYPE
             SYNTAX      Gauge32(0..900)
             UNITS       "seconds"
             MAX-ACCESS  read-create
             STATUS      current
             DESCRIPTION
                "The number of Errored Seconds
                 encountered by an VDSL2 interface within any given 15
                 minutes performance data collection period, which
                 causes the SNMP agent to send an
                 adGenVdsl2VtucPerfSESThreshTrap.
                 One trap will be sent per interval per interface.
                 A value of `0' will disable the trap.
                "
         ::= { adGenVdsl2LineAlarmConfProfileEntry 8}

         adGenVdsl2VtucThresh15MinUas  OBJECT-TYPE
             SYNTAX      Gauge32(0..900)
             UNITS       "seconds"
             MAX-ACCESS  read-create
             STATUS      current
             DESCRIPTION
                "The number of Errored Seconds
                 encountered by an VDSL2 interface within any given 15
                 minutes performance data collection period, which
                 causes the SNMP agent to send an
                 adGenVdsl2VtucPerfUASThreshTrap.
                 One trap will be sent per interval per interface.
                 A value of `0' will disable the trap.
                "
         ::= { adGenVdsl2LineAlarmConfProfileEntry 9}

         adGenVdsl2VturThreshSnrMgn OBJECT-TYPE
             SYNTAX      Integer32(0..99)
             UNITS       "dB"
             MAX-ACCESS  read-create
             STATUS      current
             DESCRIPTION
                "The SNR Margin on the VDSL2 interface below which
                 the SNMP agent sends an adGenVdsl2DSPerfSNRThresTrap.
                 One trap will be sent per interval per interface.
                 A value of '0' will disable the trap.
                "
         ::= { adGenVdsl2LineAlarmConfProfileEntry 10}

         adGenVdsl2VturThresh15MinLofs OBJECT-TYPE
             SYNTAX      Gauge32(0..900)
             UNITS       "seconds"
             MAX-ACCESS  read-create
             STATUS      current
             DESCRIPTION
                "The number of Loss of Frame Seconds
                 encountered by an VDSL2 interface within any given 15
                 minutes performance data collection period, which
                 causes the SNMP agent to send an
                 adGenVdsl2VturPerfLofsThreshTrap.
                 One trap will be sent per interval per interface.
                 A value of `0' will disable the trap.
                "
         ::= { adGenVdsl2LineAlarmConfProfileEntry 11 }

         adGenVdsl2VturThresh15MinLoss  OBJECT-TYPE
             SYNTAX      Gauge32(0..900)
             UNITS       "seconds"
             MAX-ACCESS  read-create
             STATUS      current
             DESCRIPTION
                "The number of Loss of Signal Seconds
                 encountered by an VDSL2 interface within any given 15
                 minutes performance data collection period, which
                 causes the SNMP agent to send an
                 adGenVdsl2VturPerfLossThreshTrap.
                 One trap will be sent per interval per interface.
                 A value of `0' will disable the trap.
                "
         ::= { adGenVdsl2LineAlarmConfProfileEntry 12 }

         adGenVdsl2VturThresh15MinLprs  OBJECT-TYPE
             SYNTAX      Gauge32(0..900)
             UNITS       "seconds"
             MAX-ACCESS  read-create
             STATUS      current
             DESCRIPTION
                "The number of Loss of Power Seconds
                 encountered by an VDSL2 interface within any given 15
                 minutes performance data collection period, which
                 causes the SNMP agent to send an
                 adGenVdsl2VturPerfLprsThreshTrap.
                 One trap will be sent per interval per interface.
                 A value of `0' will disable the trap.
                "
         ::= { adGenVdsl2LineAlarmConfProfileEntry 13 }

         adGenVdsl2VturThresh15MinEs  OBJECT-TYPE
             SYNTAX      Gauge32(0..65535)
             UNITS       "seconds"
             MAX-ACCESS  read-create
             STATUS      current
             DESCRIPTION
                "The number of Errored Seconds
                 encountered by an VDSL2 interface within any given 15
                 minutes performance data collection period, which
                 causes the SNMP agent to send an
                 adGenVdsl2VturPerfESThreshTrap.
                 One trap will be sent per interval per interface.
                 A value of `0' will disable the trap.
                "
         ::= { adGenVdsl2LineAlarmConfProfileEntry 14 }

         adGenVdsl2VturThresh15MinSes  OBJECT-TYPE
             SYNTAX      Gauge32(0..900)
             UNITS       "seconds"
             MAX-ACCESS  read-create
             STATUS      current
             DESCRIPTION
                "The number of Errored Seconds
                 encountered by an VDSL2 interface within any given 15
                 minutes performance data collection period, which
                 causes the SNMP agent to send an
                 adGenVdsl2VturPerfSESThreshTrap.
                 One trap will be sent per interval per interface.
                 A value of `0' will disable the trap.
                "
         ::= { adGenVdsl2LineAlarmConfProfileEntry 15 }

         adGenVdsl2VturThresh15MinUas  OBJECT-TYPE
             SYNTAX      Gauge32(0..900)
             UNITS       "seconds"
             MAX-ACCESS  read-create
             STATUS      current
             DESCRIPTION
                "The number of Errored Seconds
                 encountered by an VDSL2 interface within any given 15
                 minutes performance data collection period, which
                 causes the SNMP agent to send an
                 adGenVdsl2VturPerfUASThreshTrap.
                 One trap will be sent per interval per interface.
                 A value of `0' will disable the trap.
                "
         ::= { adGenVdsl2LineAlarmConfProfileEntry 16 }

         adGenVdsl2LineAlarmConfProfileRowStatus OBJECT-TYPE
             SYNTAX          RowStatus
             MAX-ACCESS      read-create
             STATUS          current
             DESCRIPTION
                "This object is used to create a new row or modify or
                 delete an existing row in this table.

                 A profile activated by setting this object to
                 `active'.  When `active' is set, the system
                 will validate the profile.

                 Before a profile can be deleted or taken out of
                 service, (by setting this object to `destroy' or
                 `outOfService') it must be first unreferenced
                 from all associated lines.

                 If the implementator of this MIB has chosen not
                 to implement `dynamic assignment' of profiles, this
                 object's MIN-ACCESS is read-only and its value
                 is always to be `active'.
                "
         ::= { adGenVdsl2LineAlarmConfProfileEntry 17 }

         adGenVdsl2ThreshUsLp0RateUp OBJECT-TYPE
             SYNTAX      Gauge32
             UNITS       "bps"
             MAX-ACCESS  read-create
             STATUS      current
             DESCRIPTION
                "Configured change in rate on the latency path causing an
                 adGenVdsl2VtucRateChangeTrap. A trap is produced when:
                 ChanCurrTxRate >= ChanPrevTxRate plus the value of
                 this object. A value of `0' will disable the trap.
                "
         ::= { adGenVdsl2LineAlarmConfProfileEntry 18 }

         adGenVdsl2ThreshUsLp0RateDown OBJECT-TYPE
             SYNTAX      Gauge32
             UNITS       "bps"
             MAX-ACCESS  read-create
             STATUS      current
             DESCRIPTION
                "Configured change in rate on the latency path causing an
                 adGenVdsl2VtucRateChangeTrap. A trap is produced when:
                 ChanCurrTxRate <= ChanPrevTxRate plus the value of
                 this object. A value of `0' will disable the trap.
                "
         ::= { adGenVdsl2LineAlarmConfProfileEntry 19 }

         adGenVdsl2ThreshDsLp0RateUp OBJECT-TYPE
             SYNTAX      Gauge32
             UNITS       "bps"
             MAX-ACCESS  read-create
             STATUS      current
             DESCRIPTION
                "Configured change in rate on the latency path causing an
                 adGenVdsl2VtucRateChangeTrap. A trap is produced when:
                 ChanCurrTxRate >= ChanPrevTxRate plus the value of
                 this object. A value of `0' will disable the trap.
                "
         ::= { adGenVdsl2LineAlarmConfProfileEntry 20 }

         adGenVdsl2ThreshDsLp0RateDown OBJECT-TYPE
             SYNTAX      Gauge32
             UNITS       "bps"
             MAX-ACCESS  read-create
             STATUS      current
             DESCRIPTION
                "Configured change in rate on the latency path causing an
                 adGenVdsl2VtucRateChangeTrap. A trap is produced when:
                 ChanCurrTxRate <= ChanPrevTxRate plus the value of
                 this object. A value of `0' will disable the trap.
                "
         ::= { adGenVdsl2LineAlarmConfProfileEntry 21 }

         adGenVdsl2ThreshUsLp1RateUp OBJECT-TYPE
             SYNTAX      Gauge32
             UNITS       "bps"
             MAX-ACCESS  read-create
             STATUS      current
             DESCRIPTION
                "Configured change in rate on the latency path causing an
                 adGenVdsl2VtucRateChangeTrap. A trap is produced when:
                 ChanCurrTxRate >= ChanPrevTxRate plus the value of
                 this object. A value of `0' will disable the trap.
                "
         ::= { adGenVdsl2LineAlarmConfProfileEntry 22 }

         adGenVdsl2ThreshUsLp1RateDown OBJECT-TYPE
             SYNTAX      Gauge32
             UNITS       "bps"
             MAX-ACCESS  read-create
             STATUS      current
             DESCRIPTION
                "Configured change in rate on the latency path causing an
                 adGenVdsl2VtucRateChangeTrap. A trap is produced when:
                 ChanCurrTxRate <= ChanPrevTxRate plus the value of
                 this object. A value of `0' will disable the trap.
                "
         ::= { adGenVdsl2LineAlarmConfProfileEntry 23 }

         adGenVdsl2ThreshDsLp1RateUp OBJECT-TYPE
             SYNTAX      Gauge32
             UNITS       "bps"
             MAX-ACCESS  read-create
             STATUS      current
             DESCRIPTION
                "Configured change in rate on the latency path causing an
                 adGenVdsl2VtucRateChangeTrap. A trap is produced when:
                 ChanCurrTxRate >= ChanPrevTxRate plus the value of
                 this object. A value of `0' will disable the trap.
                "
         ::= { adGenVdsl2LineAlarmConfProfileEntry 24 }

         adGenVdsl2ThreshDsLp1RateDown OBJECT-TYPE
             SYNTAX      Gauge32
             UNITS       "bps"
             MAX-ACCESS  read-create
             STATUS      current
             DESCRIPTION
                "Configured change in rate on the latency path causing an
                 adGenVdsl2VtucRateChangeTrap. A trap is produced when:
                 ChanCurrTxRate <= ChanPrevTxRate plus the value of
                 this object. A value of `0' will disable the trap.
                "
         ::= { adGenVdsl2LineAlarmConfProfileEntry 25 }


         -- ========== Prov Group (RestoreDefaultTable) =======================
         adGenVdsl2RestoreDefaultTable    OBJECT-TYPE
             SYNTAX          SEQUENCE OF AdGenVdsl2RestoreDefaultEntry
             MAX-ACCESS      not-accessible
             STATUS          current
             DESCRIPTION
                 "This table contains items to restore line and/or
                  alarm provisioning to their default values."
         ::= { adGenVdsl2Prov 3 }

         adGenVdsl2RestoreDefaultEntry    OBJECT-TYPE
             SYNTAX          AdGenVdsl2RestoreDefaultEntry
             MAX-ACCESS      not-accessible
             STATUS          current
             DESCRIPTION
                 "For later"
             INDEX { adGenSlotInfoIndex }

         ::= { adGenVdsl2RestoreDefaultTable 1}

         AdGenVdsl2RestoreDefaultEntry ::=
             SEQUENCE {
             adGenVdsl2ConfRestoreDefaults    INTEGER
             }

         adGenVdsl2ConfRestoreDefaults    OBJECT-TYPE
             SYNTAX      INTEGER {
                 restoreProvisioning(1),  -- restore only line provisiong
                 restoreAlarms(2),        -- restore alarm provisioning
                 restoreAll(3)            -- restore all provisiong
             }
             MAX-ACCESS      read-write
             STATUS          current
             DESCRIPTION
                 "This object is used to restore the set of provisioning
                  indicated.  A read will always return a value of 1."

         ::= { adGenVdsl2RestoreDefaultEntry 1}



         -- ******************************************************************
         -- Group: Status
         --   The Status Group consists of the tables of entries
         --   to determine modem status and inventory of parameters
         --   specific to the overall line, and current physical Vtur/Vtuc
         --   attributes.
         -- ******************************************************************

         -- ============ Status Group (LineTable) ============================
         adGenVdsl2LineTable   OBJECT-TYPE
             SYNTAX          SEQUENCE OF AdGenVdsl2LineEntry
             MAX-ACCESS      not-accessible
             STATUS          current
             DESCRIPTION
                "This table includes common attributes describing
                 both ends of the line.  It is required for all VDSL2
                 physical interfaces.  VDSL2 physical interfaces are
                 those ifEntries where ifType is equal to vdsl(97).
                "
         ::= { adGenVdsl2Status 1 }

         adGenVdsl2LineEntry   OBJECT-TYPE
             SYNTAX          AdGenVdsl2LineEntry
             MAX-ACCESS      not-accessible
             STATUS          current
             DESCRIPTION     "An entry in adGenVdsl2LineTable."
             INDEX           { ifIndex }
         ::= { adGenVdsl2LineTable 1 }

         AdGenVdsl2LineEntry ::=
             SEQUENCE {
                 adGenVdsl2LineCoding                       INTEGER,
                 adGenVdsl2LinePortServiceState             INTEGER,
                 adGenVdsl2LineStatus                       INTEGER,
                 adGenVdsl2LineUpTime                       Gauge32,

                 adGenVdsl2LineCurrTransSysMode             INTEGER,
                 adGenVdsl2LineCurrBandProfile              INTEGER,
                 adGenVdsl2LineCurrEstimatedLength          Gauge32,
                 adGenVdsl2LineCurrTpsTcFramingMode         INTEGER

--               Loop diagnostics for future implementaion
--               adGenVdsl2LineLoopDiagMode                 INTEGER,
--               adGenVdsl2LineLoopDiagStatus               INTEGER
             }

         adGenVdsl2LineCoding OBJECT-TYPE
             SYNTAX  INTEGER {
                 other(1),-- none of the following
                 dmt (2), -- Discrete MultiTone
                 cap (3), -- Carrierless Amplitude & Phase modulation
                 qam (4)  -- QuadrVture Amplitude Modulation
             }
             MAX-ACCESS  read-only
             STATUS      current
             DESCRIPTION
                 "Specifies the VDSL2 coding type used on this
                 line."
         ::= { adGenVdsl2LineEntry 1 }

        adGenVdsl2LinePortServiceState OBJECT-TYPE
             SYNTAX  INTEGER {
                 is(1),          -- In Service
                 oosUas(2),      -- Out of Service, Unassigned
                 oosMA(3)        -- Out of Service, Maintenance mode
             }
             MAX-ACCESS  read-write
             STATUS  current
             DESCRIPTION
                 "VDSL2 port service state."
         ::= { adGenVdsl2LineEntry 3 }

        adGenVdsl2LineStatus OBJECT-TYPE
             SYNTAX  INTEGER {
                 portDown(1),
                 portTraining(2),
                 showtime(3)
             }
             MAX-ACCESS  read-only
             STATUS      current
             DESCRIPTION
                 "Indicates current state of the dsl line."
         ::= { adGenVdsl2LineEntry 6 }

        adGenVdsl2LineUpTime OBJECT-TYPE
             SYNTAX      Gauge32
             UNITS       "seconds"
             MAX-ACCESS  read-only
             STATUS      current
             DESCRIPTION
                 "Indicates the amount of time the line has
                  been in showtime."
         ::= { adGenVdsl2LineEntry 7 }

        adGenVdsl2LineCurrTransSysMode OBJECT-TYPE
             SYNTAX  INTEGER {
                 unknown(0),
                 multimode(1),
                 t1413(2),
                 g9921a(3),
                 g9921b(4),
                 g9921c(5),
                 g9921h(6),
                 g9921i(7),
                 g9922(8),
                 g9922c(9),
                 g9923a(10),
                 g9923b(11),
                 g9923i(12),
                 g9923j(13),
                 g9923m(14),
                 g9923l(15),
                 g9924a(16),
                 g9924i(17),
                 g9925a(18),
                 g9925b(19),
                 g9925i(20),
                 g9925j(21),
                 g9925m(22),
                 g9931(23),
                 g9932a(24),
                 g9932b(25),
                 g9932c(26),
                 g9935(27),
                 g9932y(28)
             }
        MAX-ACCESS  read-only
             STATUS      current
             DESCRIPTION
                 "A report of the current operating xDSL line transmission mode.
                       offline     (0)      -- Unknow mode (not connected)
                       multiMode   (1)      -- Automatic mode selection
                       t1413       (2),     -- T1.413 Mode
                       g9921a      (3),     -- Full Rate ADSL Over POTS
                       g9921b      (4),     -- Full Rate ADSL Over ISDN
                       g9921c      (5),     -- Full Rate ADSL in TCM-ISDN
                       g9921h      (6),     -- Full Rate SSDSL in ISDN Binder
                       g9921i      (7),     -- All Digital ADSL
                       g9922       (8),     -- ADSL Lite Over POTS/ISDN
                       g9922c      (9),     -- ADSL Lite in TCM-ISDN
                       g9923a      (10),    -- ADSL2 Over POTS
                       g9923b      (11),    -- ADSL2 Over POTS
                       g9923i      (12),    -- ADSL2 Over ISDN
                       g9923j      (13),    -- All Digital ADSL2 Over POTS
                       g9923m      (14),    --Double Upstream ADLS2
                       g9923l      (15),    -- RE-ADSL2 over POTS
                       g9924a      (16),    -- ADSL2 Lite Over POTS
                       g9924i      (17),    -- All Digital ADSL2 Lite
                       g9925a      (18),    -- ADSL2+ Over POTS
                       g9925b      (19),    -- ADSL2+ Over ISDN
                       g9925i      (20),    -- All Digital ADSL2+ Over POTS
                       g9925j      (21),    -- All Digital ADSL2+ Over POTS
                       g9925m      (22),    -- Double Upstream ADSL2+
                       g9931       (23),    -- VDSL1
                       g9932a      (24),    -- VDSL2 Annex A
                       g9932b      (25),    -- VDSL2 Annex B
                       g9932c      (26),    -- VDSL2 Annex C
                       g9935       (27),    -- VDSL2 Vectoring
                       g9932y      (28),    -- VDSL2 Annex Y, Bi-Directional Vectoring Friendly
                       g9932q      (29)     -- VDSL2 Annex Q, Profile 35B (35Mhz VDSL2)
                 "
         ::= { adGenVdsl2LineEntry 8 }

        adGenVdsl2LineCurrBandProfile OBJECT-TYPE
             SYNTAX  INTEGER {
                 unknown(0),
                 g99328a(1),
                 g99328b(2),
                 g99328c(3),
                 g99328d(4),
                 g993212a(5),
                 g993212b(6),
                 g993217a(7),
                 g993230a(8),
                 g993217b(9),
                 g993235b(10)
             }
             MAX-ACCESS  read-only
             STATUS      current
             DESCRIPTION
                 "The current VDSL2 band profile in use."
         ::= { adGenVdsl2LineEntry 9 }

        adGenVdsl2LineCurrEstimatedLength OBJECT-TYPE    -- Subbu ??
             SYNTAX      Gauge32
             MAX-ACCESS  read-only
             STATUS      current
             DESCRIPTION
                 ""
         ::= { adGenVdsl2LineEntry 10 }

        adGenVdsl2LineCurrTpsTcFramingMode OBJECT-TYPE
             SYNTAX  INTEGER {
                 auto(0),
                 atm(1),
                 efm(2),
                 hdlc(3)
             }
             MAX-ACCESS  read-only
             STATUS      current
             DESCRIPTION
                 "Parameter that indicates the application-specific
                  Transport Protocol Specific Transmission
                  Convergence (TPS-TC) type."
         ::= { adGenVdsl2LineEntry 11 }


         -- ============ Status Group (VtucPhysTable) ========================
         adGenVdsl2VtucPhysTable       OBJECT-TYPE
             SYNTAX          SEQUENCE OF AdGenVdsl2VtucPhysEntry
             MAX-ACCESS      not-accessible
             STATUS          current
             DESCRIPTION
                 "This table provides one row for each Vtuc.
                 Each row contains the Physical Layer Parameters
                 table for that Vtuc. VDSL2 physical interfaces are
                 those ifEntries where ifType is equal to vdsl(97)."
         ::= { adGenVdsl2Status 2 }

         adGenVdsl2VtucPhysEntry       OBJECT-TYPE
             SYNTAX          AdGenVdsl2VtucPhysEntry
             MAX-ACCESS      not-accessible
             STATUS          current
             DESCRIPTION     "An entry in the adGenVdsl2VtucPhysTable."
             INDEX           { ifIndex }
         ::= { adGenVdsl2VtucPhysTable 1 }

         AdGenVdsl2VtucPhysEntry ::=
             SEQUENCE {
                 adGenVdsl2VtucInvSerialNumber         DisplayString,
                 adGenVdsl2VtucInvVendorID             DisplayString,
                 adGenVdsl2VtucInvVersionNumber        DisplayString,
                 adGenVdsl2CurrUSSnrMgn                Integer32,
                 adGenVdsl2CurrUSAtn                   Integer32,
                 adGenVdsl2VtucCurrStatus              Unsigned32,
                 adGenVdsl2VtucCurrOutputPwr           Integer32,
                 adGenVdsl2VtucCurrAttainableRate      Gauge32,
                 adGenVdsl2VtucCurrTxRate              Gauge32,
                 adGenVdsl2VtucPrevTxRate              Gauge32,
                 adGenVdsl2VtucActTxPsd                Integer32,
                 adGenVdsl2VtucCurrTpsTcStatus         INTEGER,
                 adGenVdsl2VtucCurrTxLineRate          Gauge32,
                 adGenVdsl2VtucPrevTxLineRate          Gauge32,
                 adGenVdsl2VtucCircuitProviderCode     DisplayString,
                 adGenVdsl2VtucCurrTxRateMax           Gauge32,
                 adGenVdsl2VtucCurrTxRateMin           Gauge32,
                 adGenVdsl2VtucLastSraDownshift        TimeStamp,
                 adGenVdsl2VtucLastSraUpshift          TimeStamp,
                 adGenVdsl2VtucRtxUsed                 INTEGER,
                 adGenVdsl2VtucRtxEtr                  Gauge32
             }

         -- inventory group
         -- These items should describe the lowest level identifiable
         -- component, be it a stand-alone modem, a card in a rack,
         -- a child-board, etc.
         --
         adGenVdsl2VtucInvSerialNumber OBJECT-TYPE
             SYNTAX      DisplayString --(SIZE (0..32))
             MAX-ACCESS  read-only
             STATUS      current
             DESCRIPTION
                 "The vendor specific string that identifies the
                 vendor equipment."
         ::= { adGenVdsl2VtucPhysEntry 1 }

         adGenVdsl2VtucInvVendorID OBJECT-TYPE
             SYNTAX      DisplayString --(SIZE (0..16))
             MAX-ACCESS  read-only
             STATUS      current
             DESCRIPTION
                 "The vendor ID code is a copy of the binary
                 vendor identification field defined by the
                 PHY[10] and expressed as readable characters."

             REFERENCE "ANSI T1.413[10]"
         ::= { adGenVdsl2VtucPhysEntry 2 }

         adGenVdsl2VtucInvVersionNumber OBJECT-TYPE
             SYNTAX      DisplayString --(SIZE (0..16))
             MAX-ACCESS  read-only
             STATUS      current
             DESCRIPTION
                 "The vendor specific version number sent by this ATU
                 as part of the initialization messages.  It is a copy
                 of the binary version number field defined by the
                 PHY[10] and expressed as readable characters."
             REFERENCE "ANSI T1.413[10]"
         ::= { adGenVdsl2VtucPhysEntry 3 }

         -- current status group
         --
         adGenVdsl2CurrUSSnrMgn OBJECT-TYPE
             SYNTAX      Integer32 (-640..640)
             UNITS       "tenth dB"
             MAX-ACCESS  read-only
             STATUS      current
             DESCRIPTION
                 "Noise Margin as seen by this ATU with respect to its
                 received signal in tenth dB."

         ::= { adGenVdsl2VtucPhysEntry 4 }

         adGenVdsl2CurrUSAtn OBJECT-TYPE
             SYNTAX      Integer32(0..630)
             UNITS       "tenth dB"
             MAX-ACCESS  read-only
             STATUS      current
             DESCRIPTION
                 "Measured difference in the total power transmitted by
                 the peer ATU and the total power received by this ATU."
         ::= { adGenVdsl2VtucPhysEntry 5 }

        adGenVdsl2VtucCurrStatus OBJECT-TYPE
             SYNTAX      Unsigned32
             MAX-ACCESS  read-only
             STATUS      current
             DESCRIPTION
                 "Indicates current state of the Vtuc line.  This is a
                 bit-map of possible conditions.  The various bit
                 positions are:

                        Bit 00 :        There no defects on the line

                        Bit 01 :        Vtuc failure due to not
                                        receiving valid frame.

                        Bit 02 :        Vtuc failure due to not
                                        receiving signal.

                        Bit 03 :        Vtuc failure due to loss of
                                        power.
                                        Note: the Agent may still
                                        function.

                        Bit 04 :        Loss of Signal Quality is
                                        declared when the Noise Margin
                                        falls below the Minimum Noise
                                        Margin, or the bit-error-rate
                                        exceeds 10^-7.

                        Bit 05 :        Vtuc failure due to inability
                                        to link with Vtur.

                        Bit 06 :        Vtuc failure during
                                        initialization due to bit
                                        errors corrupting startup
                                        exchange data.

                        Bit 07 :        Vtuc failure during
                                        initialization due to peer
                                        ATU not able to support
                                        requested configuration

                        Bit 08 :        Vtuc failure during
                                        initialization due to
                                        incompatible protocol used by
                                        the peer ATU.

                        Bit 09 :        Vtuc failure during
                                        initialization due to no
                                        activation sequence detected
                                        from peer ATU.

                 This is intended to supplement ifOperStatus."
         ::= { adGenVdsl2VtucPhysEntry 6 }

         adGenVdsl2VtucCurrOutputPwr OBJECT-TYPE
             SYNTAX      Integer32 (-310..310)
             UNITS       "tenth dBm"
             MAX-ACCESS  read-only
             STATUS      current
             DESCRIPTION
                 "Measured total output power transmitted by this ATU.
                 This is the measurement that was reported during
                 the last activation sequence."
         ::= { adGenVdsl2VtucPhysEntry 7 }

         adGenVdsl2VtucCurrAttainableRate OBJECT-TYPE
             SYNTAX      Gauge32
             UNITS       "bps"
             MAX-ACCESS  read-only
             STATUS      current
             DESCRIPTION
                 "Indicates the maximum currently attainable data rate
                 by the ATU.  This value will be equal or greater than
                 the current line rate."
         ::= { adGenVdsl2VtucPhysEntry 8 }

         adGenVdsl2VtucCurrTxRate  OBJECT-TYPE
             SYNTAX      Gauge32
             UNITS       "bps"
             MAX-ACCESS  read-only
             STATUS      current
             DESCRIPTION
                 "The payload rate of the last successful train."
         ::= { adGenVdsl2VtucPhysEntry 9 }

         adGenVdsl2VtucPrevTxRate  OBJECT-TYPE
             SYNTAX      Gauge32
             UNITS       "bps"
             MAX-ACCESS  read-only
             STATUS      current
             DESCRIPTION
                 "The payload rate of the previous successful train."
         ::= { adGenVdsl2VtucPhysEntry 10 }

         adGenVdsl2VtucActTxPsd  OBJECT-TYPE
             SYNTAX      Integer32 (-900..0 | 2147483647)
             UNITS       "0.1 dB"
             MAX-ACCESS  read-only
             STATUS      current
             DESCRIPTION
                 "Actual Power Spectrum Density (PSD) transmitted.  The average
                  transmit PSD over the sub-carriers.
                  It ranges from -900 to 0 units of 0.1 dB
                  (Physical values are -90 to 0 dBm/Hz).
                  A value of 0x7FFFFFFF (2147483647) indicates the measurement
                  is out of range to be represented."
         ::= { adGenVdsl2VtucPhysEntry 11 }

         adGenVdsl2VtucCurrTpsTcStatus  OBJECT-TYPE
             SYNTAX INTEGER {
                 noDefect(0),
                 outOfSync(1)
                 }
             MAX-ACCESS  read-only
             STATUS      current
             DESCRIPTION
                "Attributes with this syntax are status parameters that
                 reflect the failure status for Transmission Convergence (TC)
                 layer of a given data layer interface (data path over a VDSL2
                 /ADSL/ADSL2 or ADSL2+ link)."
         ::= { adGenVdsl2VtucPhysEntry 12 }

         adGenVdsl2VtucCurrTxLineRate  OBJECT-TYPE
             SYNTAX      Gauge32
             UNITS       "bps"
             MAX-ACCESS  read-only
             STATUS      current
             DESCRIPTION
                 "The line rate, including all payload and
                 overhead rates."
         ::= { adGenVdsl2VtucPhysEntry 13 }

         adGenVdsl2VtucPrevTxLineRate  OBJECT-TYPE
             SYNTAX      Gauge32
             UNITS       "bps"
             MAX-ACCESS  read-only
             STATUS      current
             DESCRIPTION
                 "The line rate, including all payload and
                 overhead rates, of the previous successful train."
         ::= { adGenVdsl2VtucPhysEntry 14 }

         adGenVdsl2VtucCircuitProviderCode  OBJECT-TYPE
             SYNTAX      DisplayString
             MAX-ACCESS  read-only
             STATUS      current
             DESCRIPTION
                 "Returns local circuit provider code"
         ::= { adGenVdsl2VtucPhysEntry 15 }

         adGenVdsl2VtucCurrTxRateMax  OBJECT-TYPE
             SYNTAX      Gauge32
             MAX-ACCESS  read-only
             STATUS      current
             DESCRIPTION
                 "Returns max payload rate since last successful
                 train."
         ::= { adGenVdsl2VtucPhysEntry 16 }

         adGenVdsl2VtucCurrTxRateMin  OBJECT-TYPE
             SYNTAX      Gauge32
             MAX-ACCESS  read-only
             STATUS      current
             DESCRIPTION
                 "Returns min payload rate since last successful
                 train."
         ::= { adGenVdsl2VtucPhysEntry 17 }

         adGenVdsl2VtucLastSraDownshift  OBJECT-TYPE
             SYNTAX      TimeStamp
             MAX-ACCESS  read-only
             STATUS      current
             DESCRIPTION
                 "Returns system uptime of last SRA downshift
                 since last successful train."
         ::= { adGenVdsl2VtucPhysEntry 18 }

         adGenVdsl2VtucLastSraUpshift  OBJECT-TYPE
             SYNTAX      TimeStamp
             MAX-ACCESS  read-only
             STATUS      current
             DESCRIPTION
                 "Returns system uptime of last SRA upshift
                 since last successful train."
         ::= { adGenVdsl2VtucPhysEntry 19 }

         adGenVdsl2VtucRtxUsed  OBJECT-TYPE
             SYNTAX  INTEGER {
                 rtxInUse                            (1),
                 rtxNotInUseForbidden                (2),
                 rtxNotInUseNotSupportedXTUC         (3),
                 rtxNotInUseNotSupportedXTUR         (4),
                 rtxNotInUseNotSupportedXTUCAndXTUR  (5)
             }
             MAX-ACCESS  read-only
             STATUS      current
             DESCRIPTION
                 "Specifies whether retransmission is active in the
                  transmit direction."
             REFERENCE "Recommendation ITU-T G.997.1, Clause 7.5.1.38"
         ::= { adGenVdsl2VtucPhysEntry 20 }

         adGenVdsl2VtucRtxEtr  OBJECT-TYPE
             SYNTAX      Gauge32
             UNITS       "bps"
             MAX-ACCESS  read-only
             STATUS      current
             DESCRIPTION
                 "Expected throughput rate calculated from combined effect of
                  impulse noise protection against worst-case REIN and worst-case
                  SHINE and overhead from correction of stationary noise errors."
             REFERENCE "Recommendation ITU-T G.998.4, Clause 11.2.1"
         ::= { adGenVdsl2VtucPhysEntry 21 }


         -- ============ Status Group (VturPhysTable) ========================
         adGenVdsl2VturPhysTable        OBJECT-TYPE
             SYNTAX          SEQUENCE OF AdGenVdsl2VturPhysEntry
             MAX-ACCESS      not-accessible
             STATUS          current
             DESCRIPTION
                 "This table provides one row for each Vtur.
                 Each row contains the Physical Layer Parameters
                 table for that Vtur. VDSL2 physical interfaces are
                 those ifEntries where ifType is equal to vdsl(97)."
         ::= { adGenVdsl2Status 3 }

         adGenVdsl2VturPhysEntry       OBJECT-TYPE
             SYNTAX          AdGenVdsl2VturPhysEntry
             MAX-ACCESS      not-accessible
             STATUS          current
             DESCRIPTION     "An entry in the adGenVdsl2VturPhysTable."
             INDEX           { ifIndex }
         ::= { adGenVdsl2VturPhysTable 1 }

         AdGenVdsl2VturPhysEntry ::=
             SEQUENCE {
                 adGenVdsl2VturInvSerialNumber         DisplayString,
                 adGenVdsl2VturInvVendorID             DisplayString,
                 adGenVdsl2VturInvVersionNumber        DisplayString,
                 adGenVdsl2CurrDSSnrMgn                Integer32,
                 adGenVdsl2CurrDSAtn                   Integer32,
                 adGenVdsl2VturCurrStatus              Unsigned32,
                 adGenVdsl2VturCurrOutputPwr           Integer32,
                 adGenVdsl2VturCurrAttainableRate      Gauge32,
                 adGenVdsl2VturCurrTxRate              Gauge32,
                 adGenVdsl2VturPrevTxRate              Gauge32,
                 adGenVdsl2VturActTxPsd                Integer32,
                 adGenVdsl2VturCurrTxLineRate          Gauge32,
                 adGenVdsl2VturPrevTxLineRate          Gauge32,
                 adGenVdsl2VturCircuitProviderCode     DisplayString,
                 adGenVdsl2VturCircuitCapabilities     OCTET STRING,
                 adGenVdsl2VturCurrTxRateMax           Gauge32,
                 adGenVdsl2VturCurrTxRateMin           Gauge32,
                 adGenVdsl2VturLastSraDownshift        TimeStamp,
                 adGenVdsl2VturLastSraUpshift          TimeStamp,
                 adGenVdsl2VturRtxUsed                 INTEGER,
                 adGenVdsl2VturRtxEtr                  Gauge32
             }

         -- inventory group
         --
         adGenVdsl2VturInvSerialNumber OBJECT-TYPE
             SYNTAX      DisplayString --(SIZE (0..32))
             MAX-ACCESS  read-only
             STATUS      current
             DESCRIPTION
                 "The vendor specific string that identifies the
                 vendor equipment."
         ::= { adGenVdsl2VturPhysEntry 1 }

         adGenVdsl2VturInvVendorID OBJECT-TYPE
             SYNTAX      DisplayString --(SIZE (0..16))
             MAX-ACCESS  read-only


             STATUS      current
             DESCRIPTION
                 "The vendor ID code is a copy of the binary
                 vendor identification field defined by the
                 PHY[10] and expressed as readable characters."
             REFERENCE "ANSI T1.413"
         ::= { adGenVdsl2VturPhysEntry 2 }

         adGenVdsl2VturInvVersionNumber OBJECT-TYPE
             SYNTAX      DisplayString --(SIZE (0..16))
             MAX-ACCESS  read-only
             STATUS      current
             DESCRIPTION
                 "The vendor specific version number sent by this ATU
                 as part of the initialization messages.  It is a copy
                 of the binary version number field defined by the
                 PHY[10] and expressed as readable characters."
             REFERENCE "ANSI T1.413"
         ::= { adGenVdsl2VturPhysEntry 3 }

         -- current status group
         --
         adGenVdsl2CurrDSSnrMgn OBJECT-TYPE
             SYNTAX      Integer32 (-640..640)
             UNITS       "tenth dB"
             MAX-ACCESS  read-only
             STATUS      current
             DESCRIPTION
                 "Noise Margin as seen by this ATU with respect to its
                 received signal in tenth dB."
         ::= { adGenVdsl2VturPhysEntry 4 }

         adGenVdsl2CurrDSAtn OBJECT-TYPE
             SYNTAX      Integer32(0..630)
             UNITS       "tenth dB"
             MAX-ACCESS  read-only
             STATUS      current
             DESCRIPTION
                 "Measured difference in the total power transmitted by
                 the peer ATU and the total power received by this ATU."
         ::= { adGenVdsl2VturPhysEntry 5 }

        adGenVdsl2VturCurrStatus OBJECT-TYPE
             SYNTAX     Unsigned32
             MAX-ACCESS  read-only
             STATUS      current
             DESCRIPTION
                 "Indicates current state of the Vtur line.  This is a
                 bit-map of possible conditions.  Due to the isolation
                 of the Vtur when line problems occur, many state
                 conditions like loss of power, loss of quality signal,
                 and initialization errors,  can not be determined.
                 While trouble shooting Vtur, also use object,
                 adGenVdsl2VtucCurrStatus.  The various bit positions are:

                        Bit 00 :        There no defects on the line

                        Bit 01 :        Vtur failure due to not
                                        receiving valid frame.

                        Bit 02 :        Vtur failure due to not
                                        receiving signal.

                        Bit 03 :        Vtur failure due to loss of
                                        power.
                                        Note: the Agent may still
                                        function.

                        Bit 04 :        Loss of Signal Quality is
                                        declared when the Noise Margin
                                        falls below the Minimum Noise
                                        Margin, or the bit-error-rate
                                        exceeds 10^-7.


                 This is intended to supplement ifOperStatus."
         ::= { adGenVdsl2VturPhysEntry 6 }

         adGenVdsl2VturCurrOutputPwr OBJECT-TYPE
             SYNTAX      Integer32 (-310..310)
             UNITS       "tenth dBm"
             MAX-ACCESS  read-only
             STATUS      current
             DESCRIPTION
                 "Measured total output power transmitted by this ATU.
                 This is the measurement that was reported during
                 the last activation sequence."
         ::= { adGenVdsl2VturPhysEntry 7 }

         adGenVdsl2VturCurrAttainableRate OBJECT-TYPE
             SYNTAX      Gauge32
             UNITS       "bps"
             MAX-ACCESS  read-only
             STATUS      current
             DESCRIPTION
                 "Indicates the maximum currently attainable data rate
                 by the ATU.  This value will be equal or greater than
                 the current line rate."
         ::= { adGenVdsl2VturPhysEntry 8 }


         adGenVdsl2VturCurrTxRate  OBJECT-TYPE
             SYNTAX      Gauge32
             UNITS       "bps"
             MAX-ACCESS  read-only
             STATUS      current
             DESCRIPTION
                 "The payload rate of the last successful train."
         ::= { adGenVdsl2VturPhysEntry 9 }

         adGenVdsl2VturPrevTxRate  OBJECT-TYPE
             SYNTAX      Gauge32
             UNITS       "bps"
             MAX-ACCESS  read-only
             STATUS      current
             DESCRIPTION
                 "The payload rate of the previous successful train."
         ::= { adGenVdsl2VturPhysEntry 10 }

         adGenVdsl2VturActTxPsd  OBJECT-TYPE
             SYNTAX      Integer32 (-900..0 | 2147483647)
             UNITS       "0.1 dB"
             MAX-ACCESS  read-only
             STATUS      current
             DESCRIPTION
                 "Actual Power Spectrum Density (PSD) transmitted.  The average
                  transmit PSD over the sub-carriers.
                  It ranges from -900 to 0 units of 0.1 dB
                  (Physical values are -90 to 0 dBm/Hz).
                  A value of 0x7FFFFFFF (2147483647) indicates the measurement
                  is out of range to be represented."
         ::= { adGenVdsl2VturPhysEntry 11 }

         adGenVdsl2VturCurrTxLineRate  OBJECT-TYPE
             SYNTAX      Gauge32
             UNITS       "bps"
             MAX-ACCESS  read-only
             STATUS      current
             DESCRIPTION
                 "The line rate, including all payload and
                 overhead rates."
         ::= { adGenVdsl2VturPhysEntry 12 }

         adGenVdsl2VturPrevTxLineRate  OBJECT-TYPE
             SYNTAX      Gauge32
             UNITS       "bps"
             MAX-ACCESS  read-only
             STATUS      current
             DESCRIPTION
                 "The line rate, including all payload and
                 overhead rates, of the previous successful train."
         ::= { adGenVdsl2VturPhysEntry 13 }

         adGenVdsl2VturCircuitProviderCode  OBJECT-TYPE
             SYNTAX      DisplayString
             MAX-ACCESS  read-only
             STATUS      current
             DESCRIPTION
                 "Returns remote circuit provider code"
         ::= { adGenVdsl2VturPhysEntry 14 }

         adGenVdsl2VturCircuitCapabilities  OBJECT-TYPE
             SYNTAX      OCTET STRING (SIZE (8))
             MAX-ACCESS  read-only
             STATUS      current
             DESCRIPTION
                 "Returns remote circuit capabilities in bit masks with following order:
                 0 - Disabled, 1 - Enabled
                 Byte Order of octet string:
                 Byte 0. Byte 1. Byte 2. Byte 3. Byte 4. Byte 5. Byte 6. Byte 7

                 Byte 0: Bit 2 - G992.1 Annex A (Full Rate ADSL over POTS)
                         Bit 4 - G992.1 Annex B (Full Rate ADSL over ISDN)
                         Bit 6 - G992.1 Annex C (Full Rate ADSL in TCM-ISDN)
                 Byte 1: Bit 0 - G992.2 Annex A/B (Lite ADSL Over POTS/ISDN)
                         Bit 2 - G992.2 Annex C (Lite ADSL in TCM-ISDN)
                 Byte 2: Bit 2 - G992.3 Annex A/L (ADSL2 over POTS)
                         Bit 4 - G992.3 Annex B   (ADSL2 over ISDN)
                 Byte 3: Bit 0 - G992.4 Annex A   (ADSL2 Lite Over POTS)
                         Bit 4 - G992.3 Annex I   (All Digital ADSL2 (POTS))
                         Bit 6 - G992.3 Annex J   (All Digital ADSL2 (ISDN))
                 Byte 4: Bit 0 - G992.4 Annex I   (All Digital ADSL2 Lite)
                         Bit 2 - G992.3 Annex L Mode 1 Wide Upstream (RE-ADSL2 Over POTS)
                         Bit 6 - G992.3 Annex M   (Double Upstream ADSL2)
                 Byte 5: Bit 0 - G992.5 Annex A   (ADSL2+ over POTS)
                         Bit 2 - G992.5 Annex B   (ADSL2+ Over ISDN)
                         Bit 6 - G992.5 Annex I   (All Digital ADSL2+ (POTS))
                 Byte 6: Bit 0 - G992.5 Annex J   (All Digital ADSL2+ (ISDN))
                         Bit 2 - G992.5 Annex M   (Double Upstream ADSL2+)
                 Byte 7: Bit 0 - VDSL2 (North America)
                         Bit 1 - VDSL2 (Europe)
                         Bit 2 - VDSL2 (Japan)

                 "
         ::= { adGenVdsl2VturPhysEntry 15 }

         adGenVdsl2VturCurrTxRateMax  OBJECT-TYPE
             SYNTAX      Gauge32
             MAX-ACCESS  read-only
             STATUS      current
             DESCRIPTION
                 "Returns max payload rate since last successful
                 train."

         ::= { adGenVdsl2VturPhysEntry 16 }

         adGenVdsl2VturCurrTxRateMin  OBJECT-TYPE
             SYNTAX      Gauge32
             MAX-ACCESS  read-only
             STATUS      current
             DESCRIPTION
                 "Returns min payload rate since last successful
                 train."

         ::= { adGenVdsl2VturPhysEntry 17 }

         adGenVdsl2VturLastSraDownshift  OBJECT-TYPE
             SYNTAX      TimeStamp
             MAX-ACCESS  read-only
             STATUS      current
             DESCRIPTION
                 "Returns system uptime of last SRA downshift
                 since last successful train."

         ::= { adGenVdsl2VturPhysEntry 18 }

         adGenVdsl2VturLastSraUpshift  OBJECT-TYPE
             SYNTAX      TimeStamp
             MAX-ACCESS  read-only
             STATUS      current
             DESCRIPTION
                 "Returns system uptime of last SRA upshift
                 since last successful train."

         ::= { adGenVdsl2VturPhysEntry 19 }

         adGenVdsl2VturRtxUsed  OBJECT-TYPE
             SYNTAX  INTEGER {
                 rtxInUse                            (1),
                 rtxNotInUseForbidden                (2),
                 rtxNotInUseNotSupportedXTUC         (3),
                 rtxNotInUseNotSupportedXTUR         (4),
                 rtxNotInUseNotSupportedXTUCAndXTUR  (5)
             }
             MAX-ACCESS  read-only
             STATUS      current
             DESCRIPTION
                 "Specifies whether retransmission is active in the
                  transmit direction."
             REFERENCE "Recommendation ITU-T G.997.1, Clause 7.5.1.38"
         ::= { adGenVdsl2VturPhysEntry 20 }

         adGenVdsl2VturRtxEtr  OBJECT-TYPE
             SYNTAX      Gauge32
             UNITS       "bps"
             MAX-ACCESS  read-only
             STATUS      current
             DESCRIPTION
                 "Expected throughput rate calculated from combined effect of
                  impulse noise protection against worst-case REIN and worst-case
                  SHINE and overhead from correction of stationary noise errors."
             REFERENCE "Recommendation ITU-T G.998.4, Clause 11.2.1"
         ::= { adGenVdsl2VturPhysEntry 21 }


         -- ============ Status Group (VtucChanTable) ========================
         adGenVdsl2VtucChanTable       OBJECT-TYPE
             SYNTAX          SEQUENCE OF AdGenVdsl2VtucChanEntry
             MAX-ACCESS      not-accessible
             STATUS          current
             DESCRIPTION
                "This table provides one row for each Vtuc channel.
                 VDSL2 channel interfaces are those ifEntries
                 where ifType is equal to channel.
                "
         ::= { adGenVdsl2Status 4 }

         adGenVdsl2VtucChanEntry       OBJECT-TYPE
             SYNTAX          AdGenVdsl2VtucChanEntry
             MAX-ACCESS      not-accessible
             STATUS          current
             DESCRIPTION     "An entry in the adGenVdsl2VtucChanTable."
             INDEX           { ifIndex, adGenVdsl2VtucChannelNumber}
         ::= { adGenVdsl2VtucChanTable 1 }

         AdGenVdsl2VtucChanEntry ::=
             SEQUENCE {
                 adGenVdsl2VtucChannelNumber           Integer32,
                 adGenVdsl2VtucChanInterleaveDelay     Gauge32,
                 adGenVdsl2VtucChanCurrTxRate          Gauge32,
                 adGenVdsl2VtucChanPrevTxRate          Gauge32,
                 adGenVdsl2VtucChanCrcBlockLength      Gauge32,
                 adGenVdsl2VtucChanINP                 Gauge32,
                 adGenVdsl2VtucChanINPRein             Gauge32
             }

         adGenVdsl2VtucChannelNumber OBJECT-TYPE
             SYNTAX      Integer32(1..4)
             MAX-ACCESS  read-only
             STATUS      current
             DESCRIPTION
                 "VDSL2 logical channel. Channel values are 1 - 4."
         ::= { adGenVdsl2VtucChanEntry 1 }

         adGenVdsl2VtucChanInterleaveDelay OBJECT-TYPE
             SYNTAX      Gauge32
             UNITS       "0.1 milli-seconds"
             MAX-ACCESS  read-only
             STATUS      current
             DESCRIPTION
                 "Interleave Delay for this channel.

                 Interleave delay applies only to the
                 interleave channel and defines the mapping
                 (relative spacing) between subsequent input
                 bytes at the interleaver input and their placement
                 in the bit stream at the interleaver output.

                 Larger numbers provide greater separation between
                 consecutive input bytes in the output bit stream
                 allowing for improved impulse noise immunity at
                 the expense of payload latency.

                 In the case where the ifType is Fast(125), use
                 noSuchObject."
         ::= { adGenVdsl2VtucChanEntry 2 }

         adGenVdsl2VtucChanCurrTxRate  OBJECT-TYPE
             SYNTAX      Gauge32
             UNITS       "bps"
             MAX-ACCESS  read-only
             STATUS      current
             DESCRIPTION
                 "Actual transmit rate on this channel."
         ::= { adGenVdsl2VtucChanEntry 3 }

         adGenVdsl2VtucChanPrevTxRate  OBJECT-TYPE
             SYNTAX      Gauge32
             UNITS       "bps"
             MAX-ACCESS  read-only
             STATUS      current
             DESCRIPTION
                 "The rate at the time of the last
                 adGenVdsl2VtucRateChangeTrap event. It is also set at
                 initialization to prevent a trap being sent.
                 Rate changes less than adGenVdsl2VtucThresh(*)RateDown
                 or less than adGenVdsl2VtucThresh(*)RateUp will not
                 cause a trap or cause this object to change.
                 (*) == Fast or Interleave.
                 See AdGenVdsl2LineAlarmConfProfileEntry."
         ::= { adGenVdsl2VtucChanEntry 4 }

         adGenVdsl2VtucChanCrcBlockLength OBJECT-TYPE
             SYNTAX      Gauge32
             UNITS        "byte"
             MAX-ACCESS  read-only
             STATUS      current
             DESCRIPTION
                 "Indicates the length of the channel data-block
                 on which the CRC operates.  Refer to Line Code
                 Specific MIBs, [11] and [12] for more
                 information."
         ::= { adGenVdsl2VtucChanEntry 5 }

         adGenVdsl2VtucChanINP OBJECT-TYPE
             SYNTAX      Gauge32
             UNITS       "0.1 dmt symbols"
             MAX-ACCESS  read-only
             STATUS      current
             DESCRIPTION
                 "Current impulse noise protection on this channel,
                 measured in increments of 0.1 DMT symbols."
         ::= { adGenVdsl2VtucChanEntry 6 }

         adGenVdsl2VtucChanINPRein OBJECT-TYPE
             SYNTAX      Gauge32
             UNITS       "0.1 dmt symbols"
             MAX-ACCESS  read-only
             STATUS      current
             DESCRIPTION
                 "Current impulse noise protection against REIN on this
                 channel, measured in increments of 0.1 DMT symbols."
         ::= { adGenVdsl2VtucChanEntry 7 }


         -- ============ Status Group (VturChanTable) ========================
        adGenVdsl2VturChanTable       OBJECT-TYPE
             SYNTAX          SEQUENCE OF AdGenVdsl2VturChanEntry
             MAX-ACCESS      not-accessible
             STATUS          current
             DESCRIPTION
                "This table provides one row for each Vtur channel.
                 VDSL2 channel interfaces are those ifEntries
                 where ifType is equal to channel.
                "
         ::= { adGenVdsl2Status 5 }

         adGenVdsl2VturChanEntry       OBJECT-TYPE
             SYNTAX          AdGenVdsl2VturChanEntry
             MAX-ACCESS      not-accessible
             STATUS          current
             DESCRIPTION     "An entry in the adGenVdsl2VturChanTable."
             INDEX           { ifIndex, adGenVdsl2VturChannelNumber }
         ::= { adGenVdsl2VturChanTable 1 }

         AdGenVdsl2VturChanEntry ::=
             SEQUENCE {
                 adGenVdsl2VturChannelNumber           Integer32,
                 adGenVdsl2VturChanInterleaveDelay     Gauge32,
                 adGenVdsl2VturChanCurrTxRate          Gauge32,
                 adGenVdsl2VturChanPrevTxRate          Gauge32,
                 adGenVdsl2VturChanCrcBlockLength      Gauge32,
                 adGenVdsl2VturChanINP                 Gauge32,
                 adGenVdsl2VturChanINPRein             Gauge32
             }

         adGenVdsl2VturChannelNumber OBJECT-TYPE
             SYNTAX      Integer32(1..4)
             MAX-ACCESS  read-only
             STATUS      current
             DESCRIPTION
                 "VDSL2 logical channel. Channel values are 1 - 4."
         ::= { adGenVdsl2VturChanEntry 1 }

         adGenVdsl2VturChanInterleaveDelay OBJECT-TYPE
             SYNTAX      Gauge32
             UNITS       "0.1 milli-seconds"
             MAX-ACCESS  read-only
             STATUS      current
             DESCRIPTION
                 "Interleave Delay for this channel.

                 Interleave delay applies only to the
                 interleave channel and defines the mapping
                 (relative spacing) between subsequent input
                 bytes at the interleaver input and their placement
                 in the bit stream at the interleaver output.
                 Larger numbers provide greater separation between
                 consecutive input bytes in the output bit stream
                 allowing for improved impulse noise immunity at
                 the expense of payload latency.

                 In the case where the ifType is Fast(125), use


                 noSuchObject."
         ::= { adGenVdsl2VturChanEntry 2 }

         adGenVdsl2VturChanCurrTxRate  OBJECT-TYPE
             SYNTAX      Gauge32
             UNITS       "bps"
             MAX-ACCESS  read-only
             STATUS      current
             DESCRIPTION
                 "Actual transmit rate on this channel."
         ::= { adGenVdsl2VturChanEntry 3 }

         adGenVdsl2VturChanPrevTxRate  OBJECT-TYPE
             SYNTAX      Gauge32
             UNITS       "bps"
             MAX-ACCESS  read-only
             STATUS      current
             DESCRIPTION
                "The rate at the time of the last
                 adGenVdsl2VturRateChangeTrap event. It is also set at
                 initialization to prevent a trap being sent.
                 Rate changes less than adGenVdsl2VturThresh(*)RateDown
                 or less than adGenVdsl2VturThresh(*)RateUp will not
                 cause a trap or cause this object to change.
                 (*) == Fast or Interleave.
                 See AdGenVdsl2LineAlarmConfProfileEntry."
         ::= { adGenVdsl2VturChanEntry 4 }

         adGenVdsl2VturChanCrcBlockLength OBJECT-TYPE
             SYNTAX      Gauge32
             MAX-ACCESS  read-only
             STATUS      current
             DESCRIPTION
                 "Indicates the length of the channel data-block
                 on which the CRC operates.  Refer to Line Code
                 Specific MIBs, [11] and [12] for more
                 information."
         ::= { adGenVdsl2VturChanEntry 5 }

         adGenVdsl2VturChanINP OBJECT-TYPE
             SYNTAX      Gauge32
             UNITS       "0.1 dmt symbols"
             MAX-ACCESS  read-only
             STATUS      current
             DESCRIPTION
                 "Current impulse noise protection on this channel,
                 measured in increments of 0.1 DMT symbols."
         ::= { adGenVdsl2VturChanEntry 6 }

         adGenVdsl2VturChanINPRein OBJECT-TYPE
             SYNTAX      Gauge32
             UNITS       "0.1 dmt symbols"
             MAX-ACCESS  read-only
             STATUS      current
             DESCRIPTION
                 "Current impulse noise protection against REIN on this
                 channel, measured in increments of 0.1 DMT symbols."
         ::= { adGenVdsl2VturChanEntry 7 }


         -- ******************************************************************
         -- Group: PM
         --   The PM Group consists of the tables of entries necessary
         --   to monitor the performance and interval statistics for the
         --   VDSL2 physical and channel interfaces.
         -- ******************************************************************

         -- ========= PM Group (adGenVdsl2VtucPerfDataTable) =================
         adGenVdsl2VtucPerfDataTable   OBJECT-TYPE
             SYNTAX          SEQUENCE OF AdGenVdsl2VtucPerfDataEntry
             MAX-ACCESS      not-accessible
             STATUS          current
             DESCRIPTION
                 "This table provides one row for each Vtuc.
                 VDSL2 physical interfaces are
                 those ifEntries where ifType is equal to vdsl(97)."
         ::= { adGenVdsl2PM 1}

         adGenVdsl2VtucPerfDataEntry       OBJECT-TYPE
             SYNTAX          AdGenVdsl2VtucPerfDataEntry
             MAX-ACCESS      not-accessible
             STATUS          current
             DESCRIPTION     "An entry in adGenVdsl2VtucPerfDataTable."


             INDEX { ifIndex }
         ::= { adGenVdsl2VtucPerfDataTable 1 }

         AdGenVdsl2VtucPerfDataEntry ::=
             SEQUENCE {
                 adGenVdsl2VtucPerfLofs                    Counter32,
                 adGenVdsl2VtucPerfLoss                    Counter32,
                 adGenVdsl2VtucPerfLols                    Counter32,
                 adGenVdsl2VtucPerfLprs                    Counter32,
                 adGenVdsl2VtucPerfEs                      Counter32,
                 adGenVdsl2VtucPerfInits                   Counter32,
                 adGenVdsl2VtucPerfSes                     Counter32,
                 adGenVdsl2VtucPerfUas                     Counter32,
                 adGenVdsl2VtucPerfFecs                    Counter32,
                 adGenVdsl2VtucPerfCrc                     Counter32,
                 adGenVdsl2VtucPerfFec                     Counter32,
                 adGenVdsl2VtucPerfValidIntervals          Integer32,
                 adGenVdsl2VtucPerfInvalidIntervals        Integer32,
                 adGenVdsl2VtucPerfCurr15MinTimeElapsed    Gauge32,
                 adGenVdsl2VtucPerfCurr15MinLofs           Counter32,
                 adGenVdsl2VtucPerfCurr15MinLoss           Counter32,
                 adGenVdsl2VtucPerfCurr15MinLols           Counter32,
                 adGenVdsl2VtucPerfCurr15MinLprs           Counter32,
                 adGenVdsl2VtucPerfCurr15MinEs             Counter32,
                 adGenVdsl2VtucPerfCurr15MinInits          Counter32,
                 adGenVdsl2VtucPerfCurr15MinSes            Counter32,
                 adGenVdsl2VtucPerfCurr15MinUas            Counter32,
                 adGenVdsl2VtucPerfCurr15MinFecs           Counter32,
                 adGenVdsl2VtucPerfCurr15MinCrc            Counter32,
                 adGenVdsl2VtucPerfCurr15MinFec            Counter32,
                 adGenVdsl2VtucPerfCurr1DayTimeElapsed     Gauge32,
                 adGenVdsl2VtucPerfCurr1DayLofs            Counter32,
                 adGenVdsl2VtucPerfCurr1DayLoss            Counter32,
                 adGenVdsl2VtucPerfCurr1DayLols            Counter32,
                 adGenVdsl2VtucPerfCurr1DayLprs            Counter32,
                 adGenVdsl2VtucPerfCurr1DayEs              Counter32,
                 adGenVdsl2VtucPerfCurr1DayInits           Counter32,
                 adGenVdsl2VtucPerfCurr1DaySes             Counter32,
                 adGenVdsl2VtucPerfCurr1DayUas             Counter32,
                 adGenVdsl2VtucPerfCurr1DayFecs            Counter32,
                 adGenVdsl2VtucPerfCurr1DayCrc             Counter32,
                 adGenVdsl2VtucPerfCurr1DayFec             Counter32,
                 adGenVdsl2VtucPerfTcTxUnits               Counter32,
                 adGenVdsl2VtucPerfTcTxDataUnits           Counter32,
                 adGenVdsl2VtucPerfTcTxDataOctets          Counter32,
                 adGenVdsl2VtucPerfTcTxIdleUnits           Counter32,
                 adGenVdsl2VtucPerfTcRxUnits               Counter32,
                 adGenVdsl2VtucPerfTcRxDataUnits           Counter32,
                 adGenVdsl2VtucPerfTcRxDataOctets          Counter32,
                 adGenVdsl2VtucPerfTcRxIdleUnits           Counter32,
                 adGenVdsl2VtucPerfTcRxErroredUnits        Counter32,
                 adGenVdsl2VtucPerfSraDownshifts           Counter32,
                 adGenVdsl2VtucPerfSraUpshifts             Counter32,
                 adGenVdsl2VtucPerfCurr15MinSraDownshifts  Counter32,
                 adGenVdsl2VtucPerfCurr15MinSraUpshifts    Counter32,
                 adGenVdsl2VtucPerfCurr15MinSraRateMax     Gauge32,
                 adGenVdsl2VtucPerfCurr15MinSraRateMin     Gauge32,
                 adGenVdsl2VtucPerfCurr1DaySraDownshifts   Counter32,
                 adGenVdsl2VtucPerfCurr1DaySraUpshifts     Counter32,
                 adGenVdsl2VtucPerfCurr1DaySraRateMax      Gauge32,
                 adGenVdsl2VtucPerfCurr1DaySraRateMin      Gauge32,
                 adGenVdsl2VtucPerfRtxMinEftr              Gauge32,
                 adGenVdsl2VtucPerfRtxLeftrs               Counter32,
                 adGenVdsl2VtucPerfCurr15MinRtxMinEftr     Gauge32,
                 adGenVdsl2VtucPerfCurr15MinRtxLeftrs      Counter32,
                 adGenVdsl2VtucPerfCurr1DayRtxMinEftr      Gauge32,
                 adGenVdsl2VtucPerfCurr1DayRtxLeftrs       Counter32
             }

         adGenVdsl2VtucPerfLofs OBJECT-TYPE
             SYNTAX      Counter32
             MAX-ACCESS  read-only
             STATUS      current
             DESCRIPTION
                 "Count of the number of Loss of Framing failures since
                 agent reset."
         ::= { adGenVdsl2VtucPerfDataEntry 1 }

         adGenVdsl2VtucPerfLoss  OBJECT-TYPE
             SYNTAX      Counter32
             MAX-ACCESS  read-only
             STATUS      current


             DESCRIPTION
                 "Count of the number of Loss of Signal failures since
                 agent reset."
         ::= { adGenVdsl2VtucPerfDataEntry 2 }

         adGenVdsl2VtucPerfLols  OBJECT-TYPE
             SYNTAX      Counter32
             MAX-ACCESS  read-only
             STATUS      current


             DESCRIPTION
                 "Count of the number of Loss of Link failures since
                 agent reset."
         ::= { adGenVdsl2VtucPerfDataEntry 3 }

        adGenVdsl2VtucPerfLprs  OBJECT-TYPE
             SYNTAX      Counter32
             MAX-ACCESS  read-only
             STATUS      current
             DESCRIPTION
                 "Count of the number of Loss of Power failures since
                 agent reset."
         ::= { adGenVdsl2VtucPerfDataEntry 4 }

         adGenVdsl2VtucPerfEs  OBJECT-TYPE
             SYNTAX      Counter32
             MAX-ACCESS  read-only
             STATUS      current
             DESCRIPTION
                 "Count of Errored Seconds since the unit was last reset.
                 An Errored Second is a one-second interval containing one
                 or more CRC anomalies, or one or more LOS or LOF defects."
             REFERENCE    "T1E1.4/2000-009R3, Part 1, common spec"
         ::= { adGenVdsl2VtucPerfDataEntry 5 }

         adGenVdsl2VtucPerfInits OBJECT-TYPE
             SYNTAX      Counter32
             MAX-ACCESS  read-only
             STATUS      current
             DESCRIPTION
                 "Count of the line initialization attempts since
                 agent reset. Includes both successful and failed
                 attempts."
         ::= { adGenVdsl2VtucPerfDataEntry 6 }

         adGenVdsl2VtucPerfSes  OBJECT-TYPE
             SYNTAX      Counter32
             MAX-ACCESS  read-only
             STATUS      current
             DESCRIPTION
                 "Count of Severely Errored Seconds since the unit was last
                  reset."
         ::= { adGenVdsl2VtucPerfDataEntry 7 }

         adGenVdsl2VtucPerfUas  OBJECT-TYPE
             SYNTAX      Counter32
             MAX-ACCESS  read-only
             STATUS      current
             DESCRIPTION
                 "Count of Unavailable Seconds since the unit was last
                  reset."
         ::= { adGenVdsl2VtucPerfDataEntry 8 }

         adGenVdsl2VtucPerfFecs  OBJECT-TYPE
             SYNTAX      Counter32
             MAX-ACCESS  read-only
             STATUS      current
             DESCRIPTION
                 "Count of the number of FEC Seconds since agent
                 reset."
         ::= { adGenVdsl2VtucPerfDataEntry 9 }

         adGenVdsl2VtucPerfCrc  OBJECT-TYPE
             SYNTAX      Counter32
             MAX-ACCESS  read-only
             STATUS      current
             DESCRIPTION
                 "Count of the number of CRC anomolies since agent
                 reset."
         ::= { adGenVdsl2VtucPerfDataEntry 10 }

         adGenVdsl2VtucPerfFec  OBJECT-TYPE
             SYNTAX      Counter32
             MAX-ACCESS  read-only
             STATUS      current
             DESCRIPTION
                 "Count of the number of FEC anomolies since agent
                 reset."
         ::= { adGenVdsl2VtucPerfDataEntry 11 }

         adGenVdsl2VtucPerfValidIntervals OBJECT-TYPE
             SYNTAX      Integer32(0..96)
             MAX-ACCESS  read-only
             STATUS      current
             DESCRIPTION
                 "The number of previous 15-minute intervals in the
                 interval table for which data was collected.  Given
                 that <n> is the maximum # of intervals supported.
                 The value will be <n> unless the measurement was
                 (re-)started within the last (<n>*15) minutes, in which
                 case the value will be the number of complete 15
                 minute intervals for which the agent has at least
                 some data. In certain cases (e.g., in the case
                 where the agent is a proxy) it is possible that some
                 intervals are unavailable.  In this case, this
                 interval is the maximum interval number for
                 which data is available."
         ::= { adGenVdsl2VtucPerfDataEntry 12 }

         adGenVdsl2VtucPerfInvalidIntervals OBJECT-TYPE
             SYNTAX      Integer32(0..96)
             MAX-ACCESS  read-only
             STATUS      current
             DESCRIPTION
                 "The number of intervals in the range from
                 0 to the value of adGenVdsl2VtucPerfValidIntervals
                 for which no data is available. This object
                 will typically be zero except in cases where
                 the data for some intervals are not available
                 (e.g., in proxy situations)."
         ::= { adGenVdsl2VtucPerfDataEntry 13 }

         adGenVdsl2VtucPerfCurr15MinTimeElapsed OBJECT-TYPE
             SYNTAX      Gauge32(0..899)
             UNITS       "seconds"
             MAX-ACCESS  read-only
             STATUS      current
             DESCRIPTION
                 "Total elapsed seconds in this interval."
         ::= { adGenVdsl2VtucPerfDataEntry 14 }

         adGenVdsl2VtucPerfCurr15MinLofs OBJECT-TYPE
             SYNTAX      Counter32
             UNITS       "seconds"
             MAX-ACCESS  read-only
             STATUS      current
             DESCRIPTION
                 "Count of seconds in the current 15 minute interval
                 when there was Loss of Framing."
         ::= { adGenVdsl2VtucPerfDataEntry 15 }

         adGenVdsl2VtucPerfCurr15MinLoss  OBJECT-TYPE
             SYNTAX      Counter32
             UNITS       "seconds"
             MAX-ACCESS  read-only
             STATUS      current
             DESCRIPTION
                 "Count of seconds in the current 15 minute interval
                 when there was Loss of Signal."
         ::= { adGenVdsl2VtucPerfDataEntry 16 }

         adGenVdsl2VtucPerfCurr15MinLols  OBJECT-TYPE
             SYNTAX      Counter32
             UNITS       "seconds"
             MAX-ACCESS  read-only
             STATUS      current
             DESCRIPTION
                 "Count of seconds in the current 15 minute interval
                 when there was Loss of Link."
         ::= { adGenVdsl2VtucPerfDataEntry 17 }

         adGenVdsl2VtucPerfCurr15MinLprs  OBJECT-TYPE
             SYNTAX      Counter32
             UNITS       "seconds"
             MAX-ACCESS  read-only
             STATUS      current
             DESCRIPTION
                 "Count of seconds in the current 15 minute interval
                 when there was Loss of Power."
         ::= { adGenVdsl2VtucPerfDataEntry 18 }

         adGenVdsl2VtucPerfCurr15MinEs OBJECT-TYPE
             SYNTAX      Counter32
             UNITS       "seconds"
             MAX-ACCESS  read-only
             STATUS      current
             DESCRIPTION
                "Count of Errored Seconds during this interval.  An Errored
                 Second is a one-second interval containing one or more CRC
                 anomalies, or one or more LOS or LOF defects."
             REFERENCE    "T1E1.4/2000-009R3, Part 1, common spec"
         ::= { adGenVdsl2VtucPerfDataEntry 19 }

         adGenVdsl2VtucPerfCurr15MinInits  OBJECT-TYPE
             SYNTAX      Counter32
             MAX-ACCESS  read-only
             STATUS      current
             DESCRIPTION
                 "Count of the line initialization attempts in the
                 current 15 minute interval. Includes both successful
                 and failed attempts."
         ::= { adGenVdsl2VtucPerfDataEntry 20 }

         adGenVdsl2VtucPerfCurr15MinSes OBJECT-TYPE
             SYNTAX      Counter32
             UNITS       "seconds"
             MAX-ACCESS  read-only
             STATUS      current
             DESCRIPTION
                 "Count of Severely Errored Seconds in the current 15
                 minute interval."
         ::= { adGenVdsl2VtucPerfDataEntry 21 }

         adGenVdsl2VtucPerfCurr15MinUas OBJECT-TYPE
             SYNTAX      Counter32
             UNITS       "seconds"
             MAX-ACCESS  read-only
             STATUS      current
             DESCRIPTION
                 "Count of Unavailable Seconds in the current 15
                  minute interval."
         ::= { adGenVdsl2VtucPerfDataEntry 22 }

         adGenVdsl2VtucPerfCurr15MinFecs OBJECT-TYPE
             SYNTAX      Counter32
             UNITS       "seconds"
             MAX-ACCESS  read-only
             STATUS      current
             DESCRIPTION
                 "Count of FEC Seconds in the current 15 minute interval."
         ::= { adGenVdsl2VtucPerfDataEntry 23 }

         adGenVdsl2VtucPerfCurr15MinCrc OBJECT-TYPE
             SYNTAX      Counter32
             UNITS       "seconds"
             MAX-ACCESS  read-only
             STATUS      current
             DESCRIPTION
                 "Count of CRC anomolies in the current 15 minute interval."
         ::= { adGenVdsl2VtucPerfDataEntry 24 }

         adGenVdsl2VtucPerfCurr15MinFec OBJECT-TYPE
             SYNTAX      Counter32
             UNITS       "seconds"
             MAX-ACCESS  read-only
             STATUS      current
             DESCRIPTION
                 "Count of FEC anomolies in the current 15 minute interval."
         ::= { adGenVdsl2VtucPerfDataEntry 25 }

         adGenVdsl2VtucPerfCurr1DayTimeElapsed OBJECT-TYPE
             SYNTAX      Gauge32(0..86399)
             UNITS       "seconds"
             MAX-ACCESS  read-only
             STATUS      current
             DESCRIPTION
                 "Number of seconds that have elapsed since the
                 beginning of the current 1-day interval."
         ::= { adGenVdsl2VtucPerfDataEntry 26 }

         adGenVdsl2VtucPerfCurr1DayLofs  OBJECT-TYPE
             SYNTAX      Counter32
             UNITS       "seconds"
             MAX-ACCESS  read-only
             STATUS      current
             DESCRIPTION
                 "Count of the number of seconds when there was Loss
                 of Framing during the current day as measured by
                 adGenVdsl2VtucPerfCurr1DayTimeElapsed."
         ::= { adGenVdsl2VtucPerfDataEntry 27 }

         adGenVdsl2VtucPerfCurr1DayLoss  OBJECT-TYPE
             SYNTAX      Counter32
             UNITS       "seconds"
             MAX-ACCESS  read-only
             STATUS      current
             DESCRIPTION
                 "Count of the number of seconds when there was Loss
                 of Signal during the current day as measured by
                 adGenVdsl2VtucPerfCurr1DayTimeElapsed."
         ::= { adGenVdsl2VtucPerfDataEntry 28 }

         adGenVdsl2VtucPerfCurr1DayLols  OBJECT-TYPE
             SYNTAX      Counter32
             UNITS       "seconds"
             MAX-ACCESS  read-only
             STATUS      current
             DESCRIPTION
                 "Count of the number of seconds when there was Loss
                 of Link during the current day as measured by
                 adGenVdsl2VtucPerfCurr1DayTimeElapsed."
         ::= { adGenVdsl2VtucPerfDataEntry 29 }

         adGenVdsl2VtucPerfCurr1DayLprs  OBJECT-TYPE
             SYNTAX      Counter32
             UNITS       "seconds"
             MAX-ACCESS  read-only
             STATUS      current
             DESCRIPTION
                 "Count of the number of seconds when there was Loss
                 of Power during the current day as measured by
                 adGenVdsl2VtucPerfCurr1DayTimeElapsed."
         ::= { adGenVdsl2VtucPerfDataEntry 30 }

         adGenVdsl2VtucPerfCurr1DayEs OBJECT-TYPE
             SYNTAX      Counter32
             UNITS       "seconds"
             MAX-ACCESS  read-only
             STATUS      current
             DESCRIPTION
                 "Count of Errored Seconds (ES) since the beginning
                  of the current 1-day interval."
         ::= { adGenVdsl2VtucPerfDataEntry 31 }

         adGenVdsl2VtucPerfCurr1DayInits  OBJECT-TYPE
             SYNTAX      Counter32
             MAX-ACCESS  read-only
             STATUS      current
             DESCRIPTION
                 "Count of the line initialization attempts in the
                 day as measured by adGenVdsl2VtucPerfCurr1DayTimeElapsed.
                 Includes both successful and failed attempts."
         ::= { adGenVdsl2VtucPerfDataEntry 32 }

         adGenVdsl2VtucPerfCurr1DaySes OBJECT-TYPE
             SYNTAX      Counter32
             UNITS       "seconds"
             MAX-ACCESS  read-only
             STATUS      current
             DESCRIPTION
                 "Count of Severely Errored Seconds during the current day as
                 measured by adGenVdsl2VtucPerfCurr1DayTimeElapsed."
         ::= { adGenVdsl2VtucPerfDataEntry 33 }

         adGenVdsl2VtucPerfCurr1DayUas OBJECT-TYPE
             SYNTAX      Counter32
             UNITS       "seconds"
             MAX-ACCESS  read-only
             STATUS      current
             DESCRIPTION
                 "Count of Unavailable Seconds during the current day as
                 measured by adGenVdsl2VtucPerfCurr1DayTimeElapsed."
         ::= { adGenVdsl2VtucPerfDataEntry 34 }

         adGenVdsl2VtucPerfCurr1DayFecs OBJECT-TYPE
             SYNTAX      Counter32
             UNITS       "seconds"
             MAX-ACCESS  read-only
             STATUS      current
             DESCRIPTION
                 "Count of FEC Seconds during the current day as
                 measured by adGenVdsl2VtucPerfCurr1DayTimeElapsed."
         ::= { adGenVdsl2VtucPerfDataEntry 35 }

         adGenVdsl2VtucPerfCurr1DayCrc OBJECT-TYPE
             SYNTAX      Counter32
             UNITS       "seconds"
             MAX-ACCESS  read-only
             STATUS      current
             DESCRIPTION
                 "Count of CRC anomolies during the current day as
                 measured by adGenVdsl2VtucPerfCurr1DayTimeElapsed."
         ::= { adGenVdsl2VtucPerfDataEntry 36 }

         adGenVdsl2VtucPerfCurr1DayFec OBJECT-TYPE
             SYNTAX      Counter32
             UNITS       "seconds"
             MAX-ACCESS  read-only
             STATUS      current
             DESCRIPTION
                 "Count of FEC anomolies during the current day as
                 measured by adGenVdsl2VtucPerfCurr1DayTimeElapsed."
         ::= { adGenVdsl2VtucPerfDataEntry 37 }

         adGenVdsl2VtucPerfTcTxUnits OBJECT-TYPE
             SYNTAX      Counter32
             UNITS       "pkts/cells"
             MAX-ACCESS  read-only
             STATUS      current
             DESCRIPTION
                 "Count of total transmitted transmission convergence layer
                  (TC) cells (ATM framing mode) or packets (other framing
                  modes)."
         ::= { adGenVdsl2VtucPerfDataEntry 38 }

         adGenVdsl2VtucPerfTcTxDataUnits OBJECT-TYPE
             SYNTAX      Counter32
             UNITS       "pkts/cells"
             MAX-ACCESS  read-only
             STATUS      current
             DESCRIPTION
                 "Count of data carrying transmitted transmission convergence
                  layer (TC) cells (ATM framing mode) or packets (other
                  framing modes)."
         ::= { adGenVdsl2VtucPerfDataEntry 39 }

         adGenVdsl2VtucPerfTcTxDataOctets OBJECT-TYPE
             SYNTAX      Counter32
             UNITS       "octets"
             MAX-ACCESS  read-only
             STATUS      current
             DESCRIPTION
                 "Count of octets in data carrying transmitted transmission
                  convergence layer (TC) cells (ATM framing mode) or packets
                  (other framing modes)."
         ::= { adGenVdsl2VtucPerfDataEntry 40 }

         adGenVdsl2VtucPerfTcTxIdleUnits OBJECT-TYPE
             SYNTAX      Counter32
             UNITS       "pkts/cells"
             MAX-ACCESS  read-only
             STATUS      current
             DESCRIPTION
                 "Count of idle/pause transmitted transmission convergence
                  layer (TC) cells (ATM framing mode) or packets (other
                  framing modes)."
         ::= { adGenVdsl2VtucPerfDataEntry 41 }

         adGenVdsl2VtucPerfTcRxUnits OBJECT-TYPE
             SYNTAX      Counter32
             UNITS       "pkts/cells"
             MAX-ACCESS  read-only
             STATUS      current
             DESCRIPTION
                 "Count of total transmitted transmission convergence layer
                  (TC) cells (ATM framing mode) or packets (other framing
                  modes)."
         ::= { adGenVdsl2VtucPerfDataEntry 42 }

         adGenVdsl2VtucPerfTcRxDataUnits OBJECT-TYPE
             SYNTAX      Counter32
             UNITS       "pkts/cells"
             MAX-ACCESS  read-only
             STATUS      current
             DESCRIPTION
                 "Count of data carrying received transmission convergence
                  layer (TC) cells (ATM framing mode) or packets (other
                  framing modes)."
         ::= { adGenVdsl2VtucPerfDataEntry 43 }

         adGenVdsl2VtucPerfTcRxDataOctets OBJECT-TYPE
             SYNTAX      Counter32
             UNITS       "octets"
             MAX-ACCESS  read-only
             STATUS      current
             DESCRIPTION
                 "Count of octets in data carrying received transmission
                  convergence layer (TC) cells (ATM framing mode) or packets
                  (other framing modes)."
         ::= { adGenVdsl2VtucPerfDataEntry 44 }

         adGenVdsl2VtucPerfTcRxIdleUnits OBJECT-TYPE
             SYNTAX      Counter32
             UNITS       "pkts/cells"
             MAX-ACCESS  read-only
             STATUS      current
             DESCRIPTION
                 "Count of idle/pause received transmission convergence
                  layer (TC) cells (ATM framing mode) or packets (other
                  framing modes)."
         ::= { adGenVdsl2VtucPerfDataEntry 45 }

         adGenVdsl2VtucPerfTcRxErroredUnits OBJECT-TYPE
             SYNTAX      Counter32
             UNITS       "pkts/cells"
             MAX-ACCESS  read-only
             STATUS      current
             DESCRIPTION
                 "Count of errored received transmission convergence
                  layer (TC) cells (ATM framing mode) or packets (other
                  framing modes)."
         ::= { adGenVdsl2VtucPerfDataEntry 46 }

         adGenVdsl2VtucPerfSraDownshifts OBJECT-TYPE
             SYNTAX      Counter32
             UNITS       "downshifts"
             MAX-ACCESS  read-only
             STATUS      current
             DESCRIPTION
                 "Free-rolling count of SRA payload rate downshifts
                 since last successful train."
         ::= { adGenVdsl2VtucPerfDataEntry 47 }

         adGenVdsl2VtucPerfSraUpshifts OBJECT-TYPE
             SYNTAX      Counter32
             UNITS       "upshifts"
             MAX-ACCESS  read-only
             STATUS      current
             DESCRIPTION
                 "Free-rolling count of SRA payload rate upshifts
                 since last successful train."
         ::= { adGenVdsl2VtucPerfDataEntry 48 }

         adGenVdsl2VtucPerfCurr15MinSraDownshifts OBJECT-TYPE
             SYNTAX      Counter32
             UNITS       "downshifts"
             MAX-ACCESS  read-only
             STATUS      current
             DESCRIPTION
                 "Count of SRA payload rate downshifts since last
                 successful train in the current 15-min interval"
         ::= { adGenVdsl2VtucPerfDataEntry 49 }

         adGenVdsl2VtucPerfCurr15MinSraUpshifts OBJECT-TYPE
             SYNTAX      Counter32
             UNITS       "upshifts"
             MAX-ACCESS  read-only
             STATUS      current
             DESCRIPTION
                 "Count of SRA payload rate upshifts since last
                 successful train in the current 15-min interval"
         ::= { adGenVdsl2VtucPerfDataEntry 50 }

         adGenVdsl2VtucPerfCurr15MinSraRateMax OBJECT-TYPE
             SYNTAX      Gauge32
             UNITS       "bps"
             MAX-ACCESS  read-only
             STATUS      current
             DESCRIPTION
                 "Max payload rate in the current 15-min interval
                 since last successful train. Min and max rate
                 should only be different in the case of an SRA
                 event."
         ::= { adGenVdsl2VtucPerfDataEntry 51 }

         adGenVdsl2VtucPerfCurr15MinSraRateMin OBJECT-TYPE
             SYNTAX      Gauge32
             UNITS       "bps"
             MAX-ACCESS  read-only
             STATUS      current
             DESCRIPTION
                 "Min payload rate in the current 15-min interval
                 since last successful train. Min and max rate
                 should only be different in the case of an SRA
                 event."
         ::= { adGenVdsl2VtucPerfDataEntry 52 }

         adGenVdsl2VtucPerfCurr1DaySraDownshifts OBJECT-TYPE
             SYNTAX      Counter32
             UNITS       "downshifts"
             MAX-ACCESS  read-only
             STATUS      current
             DESCRIPTION
                 "Count of SRA payload rate downshifts since last
                 successful train in the current 24-hr interval"
         ::= { adGenVdsl2VtucPerfDataEntry 53 }

         adGenVdsl2VtucPerfCurr1DaySraUpshifts OBJECT-TYPE
             SYNTAX      Counter32
             UNITS       "upshifts"
             MAX-ACCESS  read-only
             STATUS      current
             DESCRIPTION
                 "Count of SRA payload rate upshifts since last
                 successful train in the current 24-hr interval"
         ::= { adGenVdsl2VtucPerfDataEntry 54 }

         adGenVdsl2VtucPerfCurr1DaySraRateMax OBJECT-TYPE
             SYNTAX      Gauge32
             UNITS       "bps"
             MAX-ACCESS  read-only
             STATUS      current
             DESCRIPTION
                 "Max payload rate in the current 24-hr interval
                 since last successful train. Min and max rate
                 should only be different in the case of an SRA
                 event."
         ::= { adGenVdsl2VtucPerfDataEntry 55 }

         adGenVdsl2VtucPerfCurr1DaySraRateMin OBJECT-TYPE
             SYNTAX      Gauge32
             UNITS       "bps"
             MAX-ACCESS  read-only
             STATUS      current
             DESCRIPTION
                 "Min payload rate in the current 24-hr interval
                 since last successful train. Min and max rate
                 should only be different in the case of an SRA
                 event."
         ::= { adGenVdsl2VtucPerfDataEntry 56 }

         adGenVdsl2VtucPerfRtxMinEftr OBJECT-TYPE
             SYNTAX      Gauge32
             UNITS       "bps"
             MAX-ACCESS  read-only
             STATUS      current
             DESCRIPTION
                 "Retransmission parameter defined as the minimum of
                  the error-free throughput rate observed since reset."
             REFERENCE "Recommendation ITU-T G.998.4, Clause 11.4.3"
         ::= { adGenVdsl2VtucPerfDataEntry 57 }

         adGenVdsl2VtucPerfRtxLeftrs OBJECT-TYPE
             SYNTAX      Counter32
             UNITS       "seconds"
             MAX-ACCESS  read-only
             STATUS      current
             DESCRIPTION
                 "Count of low error-free throughput rate defect
                  seconds since reset."
             REFERENCE "Recommendation ITU-T G.998.4, Clause 11.4.1"
         ::= { adGenVdsl2VtucPerfDataEntry 58 }

         adGenVdsl2VtucPerfCurr15MinRtxMinEftr OBJECT-TYPE
             SYNTAX      Gauge32
             UNITS       "bps"
             MAX-ACCESS  read-only
             STATUS      current
             DESCRIPTION
                 "Retransmission parameter defined as the minimum of
                  the error-free throughput rate observed in the
                  current 15-min interval."
             REFERENCE "Recommendation ITU-T G.998.4, Clause 11.4.3"
         ::= { adGenVdsl2VtucPerfDataEntry 59 }

         adGenVdsl2VtucPerfCurr15MinRtxLeftrs OBJECT-TYPE
             SYNTAX      Counter32
             UNITS       "seconds"
             MAX-ACCESS  read-only
             STATUS      current
             DESCRIPTION
                 "Count of low error-free throughput rate defect
                  seconds in the current 15-min interval."
             REFERENCE "Recommendation ITU-T G.998.4, Clause 11.4.1"
         ::= { adGenVdsl2VtucPerfDataEntry 60 }

         adGenVdsl2VtucPerfCurr1DayRtxMinEftr OBJECT-TYPE
             SYNTAX      Gauge32
             UNITS       "bps"
             MAX-ACCESS  read-only
             STATUS      current
             DESCRIPTION
                 "Retransmission parameter showing the minimum of
                  the error-free throughput rate observed in the
                  current 24-hr interval."
             REFERENCE "Recommendation ITU-T G.998.4, Clause 11.4.3"
         ::= { adGenVdsl2VtucPerfDataEntry 61 }

         adGenVdsl2VtucPerfCurr1DayRtxLeftrs OBJECT-TYPE
             SYNTAX      Counter32
             UNITS       "seconds"
             MAX-ACCESS  read-only
             STATUS      current
             DESCRIPTION
                 "Count of low error-free throughput rate defect
                  seconds in the current 24-hr interval."
             REFERENCE "Recommendation ITU-T G.998.4, Clause 11.4.1"
         ::= { adGenVdsl2VtucPerfDataEntry 62 }


         -- ========= PM Group (adGenVdsl2VturPerfDataTable) =================
         adGenVdsl2VturPerfDataTable   OBJECT-TYPE
             SYNTAX          SEQUENCE OF AdGenVdsl2VturPerfDataEntry
             MAX-ACCESS      not-accessible
             STATUS          current
             DESCRIPTION
                 "This table provides one row for each Vtur.
                 VDSL2 physical interfaces are
                 those ifEntries where ifType is equal to vdsl(97)."
         ::= { adGenVdsl2PM 2 }

         adGenVdsl2VturPerfDataEntry       OBJECT-TYPE
             SYNTAX          AdGenVdsl2VturPerfDataEntry
             MAX-ACCESS      not-accessible
             STATUS          current
             DESCRIPTION     "An entry in adGenVdsl2VturPerfDataTable."


             INDEX { ifIndex }
         ::= { adGenVdsl2VturPerfDataTable 1 }

         AdGenVdsl2VturPerfDataEntry ::=
             SEQUENCE {
                 adGenVdsl2VturPerfLofs                    Counter32,
                 adGenVdsl2VturPerfLoss                    Counter32,
                 adGenVdsl2VturPerfLprs                    Counter32,
                 adGenVdsl2VturPerfEs                      Counter32,
                 adGenVdsl2VturPerfSes                     Counter32,
                 adGenVdsl2VturPerfUas                     Counter32,
                 adGenVdsl2VturPerfFecs                    Counter32,
                 adGenVdsl2VturPerfCrc                     Counter32,
                 adGenVdsl2VturPerfFec                     Counter32,
                 adGenVdsl2VturPerfValidIntervals          Integer32,
                 adGenVdsl2VturPerfInvalidIntervals        Integer32,
                 adGenVdsl2VturPerfCurr15MinTimeElapsed    Gauge32,
                 adGenVdsl2VturPerfCurr15MinLofs           Counter32,
                 adGenVdsl2VturPerfCurr15MinLoss           Counter32,
                 adGenVdsl2VturPerfCurr15MinLprs           Counter32,
                 adGenVdsl2VturPerfCurr15MinEs             Counter32,
                 adGenVdsl2VturPerfCurr15MinSes            Counter32,
                 adGenVdsl2VturPerfCurr15MinUas            Counter32,
                 adGenVdsl2VturPerfCurr15MinFecs           Counter32,
                 adGenVdsl2VturPerfCurr15MinCrc            Counter32,
                 adGenVdsl2VturPerfCurr15MinFec            Counter32,
                 adGenVdsl2VturPerfCurr1DayTimeElapsed     Gauge32,
                 adGenVdsl2VturPerfCurr1DayLofs            Counter32,
                 adGenVdsl2VturPerfCurr1DayLoss            Counter32,
                 adGenVdsl2VturPerfCurr1DayLprs            Counter32,
                 adGenVdsl2VturPerfCurr1DayEs              Counter32,
                 adGenVdsl2VturPerfCurr1DaySes             Counter32,
                 adGenVdsl2VturPerfCurr1DayUas             Counter32,
                 adGenVdsl2VturPerfCurr1DayFecs            Counter32,
                 adGenVdsl2VturPerfCurr1DayCrc             Counter32,
                 adGenVdsl2VturPerfCurr1DayFec             Counter32,
                 adGenVdsl2VturPerfTcTxUnits               Counter32,
                 adGenVdsl2VturPerfTcTxDataUnits           Counter32,
                 adGenVdsl2VturPerfTcTxDataOctets          Counter32,
                 adGenVdsl2VturPerfTcTxIdleUnits           Counter32,
                 adGenVdsl2VturPerfTcRxUnits               Counter32,
                 adGenVdsl2VturPerfTcRxDataUnits           Counter32,
                 adGenVdsl2VturPerfTcRxDataOctets          Counter32,
                 adGenVdsl2VturPerfTcRxIdleUnits           Counter32,
                 adGenVdsl2VturPerfTcRxErroredUnits        Counter32,
                 adGenVdsl2VturPerfSraDownshifts           Counter32,
                 adGenVdsl2VturPerfSraUpshifts             Counter32,
                 adGenVdsl2VturPerfCurr15MinSraDownshifts  Counter32,
                 adGenVdsl2VturPerfCurr15MinSraUpshifts    Counter32,
                 adGenVdsl2VturPerfCurr15MinSraRateMax     Gauge32,
                 adGenVdsl2VturPerfCurr15MinSraRateMin     Gauge32,
                 adGenVdsl2VturPerfCurr1DaySraDownshifts   Counter32,
                 adGenVdsl2VturPerfCurr1DaySraUpshifts     Counter32,
                 adGenVdsl2VturPerfCurr1DaySraRateMax      Gauge32,
                 adGenVdsl2VturPerfCurr1DaySraRateMin      Gauge32,
                 adGenVdsl2VturPerfRtxMinEftr              Gauge32,
                 adGenVdsl2VturPerfRtxLeftrs               Counter32,
                 adGenVdsl2VturPerfCurr15MinRtxMinEftr     Gauge32,
                 adGenVdsl2VturPerfCurr15MinRtxLeftrs      Counter32,
                 adGenVdsl2VturPerfCurr1DayRtxMinEftr      Gauge32,
                 adGenVdsl2VturPerfCurr1DayRtxLeftrs       Counter32
              }

         adGenVdsl2VturPerfLofs OBJECT-TYPE
             SYNTAX      Counter32
             MAX-ACCESS  read-only
             STATUS      current
             DESCRIPTION
                 "Count of the number of Loss of Framing failures since
                 agent reset."
         ::= { adGenVdsl2VturPerfDataEntry 1 }

         adGenVdsl2VturPerfLoss  OBJECT-TYPE
             SYNTAX      Counter32
             MAX-ACCESS  read-only
             STATUS      current
             DESCRIPTION
                 "Count of the number of Loss of Signal failures since
                 agent reset."
         ::= { adGenVdsl2VturPerfDataEntry 2 }

        adGenVdsl2VturPerfLprs  OBJECT-TYPE
             SYNTAX      Counter32
             MAX-ACCESS  read-only
             STATUS      current
             DESCRIPTION
                 "Count of the number of Loss of Power failures since
                 agent reset."
         ::= { adGenVdsl2VturPerfDataEntry 3 }

         adGenVdsl2VturPerfEs  OBJECT-TYPE
             SYNTAX      Counter32
             MAX-ACCESS  read-only
             STATUS      current
             DESCRIPTION
                 "Count of Errored Seconds since the unit was last reset.
                 An Errored Second is a one-second interval containing one
                 or more CRC anomalies, or one or more LOS or LOF defects."
             REFERENCE    "T1E1.4/2000-009R3, Part 1, common spec"
         ::= { adGenVdsl2VturPerfDataEntry 4 }

         adGenVdsl2VturPerfSes  OBJECT-TYPE
             SYNTAX      Counter32
             MAX-ACCESS  read-only
             STATUS      current
             DESCRIPTION
                 "Count of Severely Errored Seconds since the unit was last
                  reset."
         ::= { adGenVdsl2VturPerfDataEntry 5 }

         adGenVdsl2VturPerfUas  OBJECT-TYPE
             SYNTAX      Counter32
             MAX-ACCESS  read-only
             STATUS      current
             DESCRIPTION
                 "Count of Unavailable Seconds since the unit was last reset."
         ::= { adGenVdsl2VturPerfDataEntry 6 }

         adGenVdsl2VturPerfFecs  OBJECT-TYPE
             SYNTAX      Counter32
             MAX-ACCESS  read-only
             STATUS      current
             DESCRIPTION
                 "Count of the number of FEC Seconds since agent reset."
         ::= { adGenVdsl2VturPerfDataEntry 7 }

         adGenVdsl2VturPerfCrc  OBJECT-TYPE
             SYNTAX      Counter32
             MAX-ACCESS  read-only
             STATUS      current
             DESCRIPTION
                 "Count of the number of CRC anomolies since agent reset."
         ::= { adGenVdsl2VturPerfDataEntry 8 }

         adGenVdsl2VturPerfFec  OBJECT-TYPE
             SYNTAX      Counter32
             MAX-ACCESS  read-only
             STATUS      current
             DESCRIPTION
                 "Count of the number of FEC anomolies since agent reset."
         ::= { adGenVdsl2VturPerfDataEntry 9 }

         -- general 15 min interval information
         --
         adGenVdsl2VturPerfValidIntervals OBJECT-TYPE
             SYNTAX      Integer32(0..96)
             MAX-ACCESS  read-only
             STATUS      current
             DESCRIPTION
                 "The number of previous 15-minute intervals in the
                 interval table for which data was collected.  Given
                 that <n> is the maximum # of intervals supported.
                 The value will be <n> unless the measurement was
                 (re-)started within the last (<n>*15) minutes, in which
                 case the value will be the number of complete 15
                 minute intervals for which the agent has at least
                 some data. In certain cases (e.g., in the case
                 where the agent is a proxy) it is possible that some
                 intervals are unavailable.  In this case, this
                 interval is the maximum interval number for
                 which data is available."
         ::= { adGenVdsl2VturPerfDataEntry 10 }

         adGenVdsl2VturPerfInvalidIntervals OBJECT-TYPE
             SYNTAX      Integer32(0..96)
             MAX-ACCESS  read-only
             STATUS      current
             DESCRIPTION
                 "The number of intervals in the range from
                 0 to the value of adGenVdsl2VturPerfValidIntervals
                 for which no data is available. This object
                 will typically be zero except in cases where
                 the data for some intervals are not available
                 (e.g., in proxy situations)."
         ::= { adGenVdsl2VturPerfDataEntry 11 }

         adGenVdsl2VturPerfCurr15MinTimeElapsed OBJECT-TYPE
             SYNTAX      Gauge32(0..899)
             UNITS       "seconds"
             MAX-ACCESS  read-only
             STATUS      current
             DESCRIPTION
                 "Total elapsed seconds in this interval."
         ::= { adGenVdsl2VturPerfDataEntry 12 }

         adGenVdsl2VturPerfCurr15MinLofs OBJECT-TYPE
             SYNTAX      Counter32
             UNITS       "seconds"
             MAX-ACCESS  read-only
             STATUS      current
             DESCRIPTION
                 "Count of seconds in the current 15 minute interval
                 when there was Loss of Framing."
         ::= { adGenVdsl2VturPerfDataEntry 13 }

         adGenVdsl2VturPerfCurr15MinLoss  OBJECT-TYPE
             SYNTAX      Counter32
             UNITS       "seconds"
             MAX-ACCESS  read-only
             STATUS      current
             DESCRIPTION
                 "Count of seconds in the current 15 minute interval
                 when there was Loss of Signal."
         ::= { adGenVdsl2VturPerfDataEntry 14 }

         adGenVdsl2VturPerfCurr15MinLprs  OBJECT-TYPE
             SYNTAX      Counter32
             UNITS       "seconds"
             MAX-ACCESS  read-only
             STATUS      current
             DESCRIPTION
                 "Count of seconds in the current 15 minute interval
                 when there was Loss of Power."
         ::= { adGenVdsl2VturPerfDataEntry 15 }

         adGenVdsl2VturPerfCurr15MinEs OBJECT-TYPE
             SYNTAX      Counter32
             UNITS       "seconds"
             MAX-ACCESS  read-only
             STATUS      current
             DESCRIPTION
                "Count of Errored Seconds in the current 15 minute interval.
                 An Errored Second is a one-second interval containing one or
                 more CRC anomalies, or one or more LOS or LOF defects."
             REFERENCE    "T1E1.4/2000-009R3, Part 1, common spec"
         ::= { adGenVdsl2VturPerfDataEntry 16 }

         adGenVdsl2VturPerfCurr15MinSes OBJECT-TYPE
             SYNTAX      Counter32
             UNITS       "seconds"
             MAX-ACCESS  read-only
             STATUS      current
             DESCRIPTION
                 "Count of Severely Errored Seconds in the current 15
                  minute interval."
         ::= { adGenVdsl2VturPerfDataEntry 17 }

         adGenVdsl2VturPerfCurr15MinUas OBJECT-TYPE
             SYNTAX      Counter32
             UNITS       "seconds"
             MAX-ACCESS  read-only
             STATUS      current
             DESCRIPTION
                 "Count of Unavailable Seconds in the current 15
                  minute interval."
         ::= { adGenVdsl2VturPerfDataEntry 18 }

         adGenVdsl2VturPerfCurr15MinFecs OBJECT-TYPE
             SYNTAX      Counter32
             UNITS       "seconds"
             MAX-ACCESS  read-only
             STATUS      current
             DESCRIPTION
                 "Count of FEC Seconds in the current 15 minute interval."
         ::= { adGenVdsl2VturPerfDataEntry 19 }

         adGenVdsl2VturPerfCurr15MinCrc OBJECT-TYPE
             SYNTAX      Counter32
             UNITS       "seconds"
             MAX-ACCESS  read-only
             STATUS      current
             DESCRIPTION
                 "Count of CRC anomolies in the current 15 minute interval."
         ::= { adGenVdsl2VturPerfDataEntry 20 }

         adGenVdsl2VturPerfCurr15MinFec OBJECT-TYPE
             SYNTAX      Counter32
             UNITS       "seconds"
             MAX-ACCESS  read-only
             STATUS      current
             DESCRIPTION
                 "Count of FEC anomolies in the current 15 minute interval."
         ::= { adGenVdsl2VturPerfDataEntry 21 }

         adGenVdsl2VturPerfCurr1DayTimeElapsed OBJECT-TYPE
             SYNTAX      Gauge32(0..86399)
             UNITS       "seconds"
             MAX-ACCESS  read-only
             STATUS      current
             DESCRIPTION
                 "Number of seconds that have elapsed since the
                 beginning of the current 1-day interval."
         ::= { adGenVdsl2VturPerfDataEntry 22 }

         adGenVdsl2VturPerfCurr1DayLofs  OBJECT-TYPE
             SYNTAX      Counter32
             UNITS       "seconds"
             MAX-ACCESS  read-only
             STATUS      current
             DESCRIPTION
                 "Count of the number of seconds when there was Loss
                 of Framing during the current day as measured by
                 adGenVdsl2VturPerfCurr1DayTimeElapsed."
         ::= { adGenVdsl2VturPerfDataEntry 23 }

         adGenVdsl2VturPerfCurr1DayLoss  OBJECT-TYPE
             SYNTAX      Counter32
             UNITS       "seconds"
             MAX-ACCESS  read-only
             STATUS      current
             DESCRIPTION
                 "Count of the number of seconds when there was Loss
                 of Signal during the current day as measured by
                 adGenVdsl2VturPerfCurr1DayTimeElapsed."
         ::= { adGenVdsl2VturPerfDataEntry 24 }

         adGenVdsl2VturPerfCurr1DayLprs  OBJECT-TYPE
             SYNTAX      Counter32
             UNITS       "seconds"
             MAX-ACCESS  read-only
             STATUS      current
             DESCRIPTION
                 "Count of the number of seconds when there was Loss
                 of Power during the current day as measured by
                 adGenVdsl2VturPerfCurr1DayTimeElapsed."
         ::= { adGenVdsl2VturPerfDataEntry 25 }

         adGenVdsl2VturPerfCurr1DayEs OBJECT-TYPE
             SYNTAX      Counter32
             UNITS       "seconds"
             MAX-ACCESS  read-only
             STATUS      current
             DESCRIPTION
                 "Count of the number of seconds when there was Errored Seconds
                  during the current day as measured by
                  adGenVdsl2VturPerfCurr1DayTimeElapsed."
         ::= { adGenVdsl2VturPerfDataEntry 26 }

         adGenVdsl2VturPerfCurr1DaySes OBJECT-TYPE
             SYNTAX      Counter32
             UNITS       "seconds"
             MAX-ACCESS  read-only
             STATUS      current
             DESCRIPTION
                 "Count of Severely Errored Seconds during the current day as
                 measured by adGenVdsl2VturPerfCurr1DayTimeElapsed."
         ::= { adGenVdsl2VturPerfDataEntry 27 }

         adGenVdsl2VturPerfCurr1DayUas OBJECT-TYPE
             SYNTAX      Counter32
             UNITS       "seconds"
             MAX-ACCESS  read-only
             STATUS      current
             DESCRIPTION
                 "Count of Unavailable Seconds during the current day as
                 measured by adGenVdsl2VturPerfCurr1DayTimeElapsed."
         ::= { adGenVdsl2VturPerfDataEntry 28 }

         adGenVdsl2VturPerfCurr1DayFecs OBJECT-TYPE
             SYNTAX      Counter32
             UNITS       "seconds"
             MAX-ACCESS  read-only
             STATUS      current
             DESCRIPTION
                 "Count of FEC Seconds during the current day as
                 measured by adGenVdsl2VturPerfCurr1DayTimeElapsed."
         ::= { adGenVdsl2VturPerfDataEntry 29 }

         adGenVdsl2VturPerfCurr1DayCrc OBJECT-TYPE
             SYNTAX      Counter32
             UNITS       "seconds"
             MAX-ACCESS  read-only
             STATUS      current
             DESCRIPTION
                 "Count of CRC anomolies during the current day as
                 measured by adGenVdsl2VturPerfCurr1DayTimeElapsed."
         ::= { adGenVdsl2VturPerfDataEntry 30 }

         adGenVdsl2VturPerfCurr1DayFec OBJECT-TYPE
             SYNTAX      Counter32
             UNITS       "seconds"
             MAX-ACCESS  read-only
             STATUS      current
             DESCRIPTION
                 "Count of FEC anomolies during the current day as
                 measured by adGenVdsl2VturPerfCurr1DayTimeElapsed."
         ::= { adGenVdsl2VturPerfDataEntry 31 }

         adGenVdsl2VturPerfTcTxUnits OBJECT-TYPE
             SYNTAX      Counter32
             UNITS       "pkts/cells"
             MAX-ACCESS  read-only
             STATUS      current
             DESCRIPTION
                 "Count of total transmitted transmission convergence layer
                  (TC) cells (ATM framing mode) or packets (other framing
                  modes)."
         ::= { adGenVdsl2VturPerfDataEntry 32 }

         adGenVdsl2VturPerfTcTxDataUnits OBJECT-TYPE
             SYNTAX      Counter32
             UNITS       "pkts/cells"
             MAX-ACCESS  read-only
             STATUS      current
             DESCRIPTION
                 "Count of data carrying transmitted transmission convergence
                  layer (TC) cells (ATM framing mode) or packets (other
                  framing modes)."
         ::= { adGenVdsl2VturPerfDataEntry 33 }

         adGenVdsl2VturPerfTcTxDataOctets OBJECT-TYPE
             SYNTAX      Counter32
             UNITS       "octets"
             MAX-ACCESS  read-only
             STATUS      current
             DESCRIPTION
                 "Count of octets in data carrying transmitted transmission
                  convergence layer (TC) cells (ATM framing mode) or packets
                  (other framing modes)."
         ::= { adGenVdsl2VturPerfDataEntry 34 }

         adGenVdsl2VturPerfTcTxIdleUnits OBJECT-TYPE
             SYNTAX      Counter32
             UNITS       "pkts/cells"
             MAX-ACCESS  read-only
             STATUS      current
             DESCRIPTION
                 "Count of idle/pause transmitted transmission convergence
                  layer (TC) cells (ATM framing mode) or packets (other
                  framing modes)."
         ::= { adGenVdsl2VturPerfDataEntry 35 }

         adGenVdsl2VturPerfTcRxUnits OBJECT-TYPE
             SYNTAX      Counter32
             UNITS       "pkts/cells"
             MAX-ACCESS  read-only
             STATUS      current
             DESCRIPTION
                 "Count of total transmitted transmission convergence layer
                  (TC) cells (ATM framing mode) or packets (other framing
                  modes)."
         ::= { adGenVdsl2VturPerfDataEntry 36 }

         adGenVdsl2VturPerfTcRxDataUnits OBJECT-TYPE
             SYNTAX      Counter32
             UNITS       "pkts/cells"
             MAX-ACCESS  read-only
             STATUS      current
             DESCRIPTION
                 "Count of data carrying received transmission convergence
                  layer (TC) cells (ATM framing mode) or packets (other
                  framing modes)."
         ::= { adGenVdsl2VturPerfDataEntry 37 }

         adGenVdsl2VturPerfTcRxDataOctets OBJECT-TYPE
             SYNTAX      Counter32
             UNITS       "octets"
             MAX-ACCESS  read-only
             STATUS      current
             DESCRIPTION
                 "Count of octets in data carrying received transmission
                  convergence layer (TC) cells (ATM framing mode) or packets
                  (other framing modes)."
         ::= { adGenVdsl2VturPerfDataEntry 38 }

         adGenVdsl2VturPerfTcRxIdleUnits OBJECT-TYPE
             SYNTAX      Counter32
             UNITS       "pkts/cells"
             MAX-ACCESS  read-only
             STATUS      current
             DESCRIPTION
                 "Count of idle/pause received transmission convergence
                  layer (TC) cells (ATM framing mode) or packets (other
                  framing modes)."
         ::= { adGenVdsl2VturPerfDataEntry 39 }

         adGenVdsl2VturPerfTcRxErroredUnits OBJECT-TYPE
             SYNTAX      Counter32
             UNITS       "pkts/cells"
             MAX-ACCESS  read-only
             STATUS      current
             DESCRIPTION
                 "Count of errored received transmission convergence
                  layer (TC) cells (ATM framing mode) or packets (other
                  framing modes)."
         ::= { adGenVdsl2VturPerfDataEntry 40 }

         adGenVdsl2VturPerfSraDownshifts OBJECT-TYPE
             SYNTAX      Counter32
             UNITS       "downshifts"
             MAX-ACCESS  read-only
             STATUS      current
             DESCRIPTION
                 "Free-rolling count of SRA payload rate downshifts
                 since last successful train."
         ::= { adGenVdsl2VturPerfDataEntry 41 }

         adGenVdsl2VturPerfSraUpshifts OBJECT-TYPE
             SYNTAX      Counter32
             UNITS       "upshifts"
             MAX-ACCESS  read-only
             STATUS      current
             DESCRIPTION
                 "Free-rolling count of SRA payload rate upshifts
                 since last successful train."
         ::= { adGenVdsl2VturPerfDataEntry 42 }

         adGenVdsl2VturPerfCurr15MinSraDownshifts OBJECT-TYPE
             SYNTAX      Counter32
             UNITS       "downshifts"
             MAX-ACCESS  read-only
             STATUS      current
             DESCRIPTION
                 "Count of SRA payload rate downshifts since last
                 successful train in the current 15-min interval"
         ::= { adGenVdsl2VturPerfDataEntry 43 }

         adGenVdsl2VturPerfCurr15MinSraUpshifts OBJECT-TYPE
             SYNTAX      Counter32
             UNITS       "upshifts"
             MAX-ACCESS  read-only
             STATUS      current
             DESCRIPTION
                 "Count of SRA payload rate upshifts since last
                 successful train in the current 15-min interval"
         ::= { adGenVdsl2VturPerfDataEntry 44 }

         adGenVdsl2VturPerfCurr15MinSraRateMax OBJECT-TYPE
             SYNTAX      Gauge32
             UNITS       "bps"
             MAX-ACCESS  read-only
             STATUS      current
             DESCRIPTION
                 "Max payload rate in the current 15-min interval
                 since last successful train. Min and max rate
                 should only be different in the case of an SRA
                 event."
         ::= { adGenVdsl2VturPerfDataEntry 45 }

         adGenVdsl2VturPerfCurr15MinSraRateMin OBJECT-TYPE
             SYNTAX      Gauge32
             UNITS       "bps"
             MAX-ACCESS  read-only
             STATUS      current
             DESCRIPTION
                 "Min payload rate in the current 15-min interval
                 since last successful train. Min and max rate
                 should only be different in the case of an SRA
                 event."
         ::= { adGenVdsl2VturPerfDataEntry 46 }

         adGenVdsl2VturPerfCurr1DaySraDownshifts OBJECT-TYPE
             SYNTAX      Counter32
             UNITS       "downshifts"
             MAX-ACCESS  read-only
             STATUS      current
             DESCRIPTION
                 "Count of SRA payload rate downshifts since last
                 successful train in the current 24-hr interval"
         ::= { adGenVdsl2VturPerfDataEntry 47 }

         adGenVdsl2VturPerfCurr1DaySraUpshifts OBJECT-TYPE
             SYNTAX      Counter32
             UNITS       "upshifts"
             MAX-ACCESS  read-only
             STATUS      current
             DESCRIPTION
                 "Count of SRA payload rate upshifts since last
                 successful train in the current 24-hr interval"
         ::= { adGenVdsl2VturPerfDataEntry 48 }

         adGenVdsl2VturPerfCurr1DaySraRateMax OBJECT-TYPE
             SYNTAX      Gauge32
             UNITS       "bps"
             MAX-ACCESS  read-only
             STATUS      current
             DESCRIPTION
                 "Max payload rate in the current 24-hr interval
                 since last successful train. Min and max rate
                 should only be different in the case of an SRA
                 event."
         ::= { adGenVdsl2VturPerfDataEntry 49 }

         adGenVdsl2VturPerfCurr1DaySraRateMin OBJECT-TYPE
             SYNTAX      Gauge32
             UNITS       "bps"
             MAX-ACCESS  read-only
             STATUS      current
             DESCRIPTION
                 "Min payload rate in the current 24-hr interval
                 since last successful train. Min and max rate
                 should only be different in the case of an SRA
                 event."
         ::= { adGenVdsl2VturPerfDataEntry 50 }

         adGenVdsl2VturPerfRtxMinEftr OBJECT-TYPE
             SYNTAX      Gauge32
             UNITS       "bps"
             MAX-ACCESS  read-only
             STATUS      current
             DESCRIPTION
                 "Retransmission parameter defined as the minimum of
                  the error-free throughput rate observed since reset."
             REFERENCE "Recommendation ITU-T G.998.4, Clause 11.4.3"
         ::= { adGenVdsl2VturPerfDataEntry 51 }

         adGenVdsl2VturPerfRtxLeftrs OBJECT-TYPE
             SYNTAX      Counter32
             UNITS       "seconds"
             MAX-ACCESS  read-only
             STATUS      current
             DESCRIPTION
                 "Count of low error-free throughput rate defect
                  seconds since reset."
             REFERENCE "Recommendation ITU-T G.998.4, Clause 11.4.1"
         ::= { adGenVdsl2VturPerfDataEntry 52 }

         adGenVdsl2VturPerfCurr15MinRtxMinEftr OBJECT-TYPE
             SYNTAX      Gauge32
             UNITS       "bps"
             MAX-ACCESS  read-only
             STATUS      current
             DESCRIPTION
                 "Retransmission parameter defined as the minimum of
                  the error-free throughput rate observed in the
                  current 15-min interval."
             REFERENCE "Recommendation ITU-T G.998.4, Clause 11.4.3"
         ::= { adGenVdsl2VturPerfDataEntry 53 }

         adGenVdsl2VturPerfCurr15MinRtxLeftrs OBJECT-TYPE
             SYNTAX      Counter32
             UNITS       "seconds"
             MAX-ACCESS  read-only
             STATUS      current
             DESCRIPTION
                 "Count of low error-free throughput rate defect
                  seconds in the current 15-min interval."
             REFERENCE "Recommendation ITU-T G.998.4, Clause 11.4.1"
         ::= { adGenVdsl2VturPerfDataEntry 54 }

         adGenVdsl2VturPerfCurr1DayRtxMinEftr OBJECT-TYPE
             SYNTAX      Gauge32
             UNITS       "bps"
             MAX-ACCESS  read-only
             STATUS      current
             DESCRIPTION
                 "Retransmission parameter showing the minimum of
                  the error-free throughput rate observed in the
                  current 24-hr interval."
             REFERENCE "Recommendation ITU-T G.998.4, Clause 11.4.3"
         ::= { adGenVdsl2VturPerfDataEntry 55 }

         adGenVdsl2VturPerfCurr1DayRtxLeftrs OBJECT-TYPE
             SYNTAX      Counter32
             UNITS       "seconds"
             MAX-ACCESS  read-only
             STATUS      current
             DESCRIPTION
                 "Count of low error-free throughput rate defect
                  seconds in the current 24-hr interval."
             REFERENCE "Recommendation ITU-T G.998.4, Clause 11.4.1"
         ::= { adGenVdsl2VturPerfDataEntry 56 }


         -- ========= PM Group (adGenVdsl2VtucIntervalTable) =================
         adGenVdsl2VtucIntervalTable   OBJECT-TYPE
             SYNTAX          SEQUENCE OF AdGenVdsl2VtucIntervalEntry
             MAX-ACCESS      not-accessible
             STATUS          current
             DESCRIPTION
                 "This table provides one row for each Vtuc
                 performance data collection interval.
                 VDSL2 physical interfaces are
                 those ifEntries where ifType is equal to vdsl(97)."
         ::= { adGenVdsl2PM 3 }

         adGenVdsl2VtucIntervalEntry   OBJECT-TYPE
             SYNTAX          AdGenVdsl2VtucIntervalEntry
             MAX-ACCESS      not-accessible
             STATUS          current
             DESCRIPTION     "An entry in the adGenVdsl2VtucIntervalTable."
             INDEX           { ifIndex, adGenVdsl2VtucIntervalNumber }
         ::= { adGenVdsl2VtucIntervalTable 1 }

         AdGenVdsl2VtucIntervalEntry ::=
             SEQUENCE {
                 adGenVdsl2VtucIntervalNumber          Integer32,
                 adGenVdsl2VtucIntervalLofs            Counter32,
                 adGenVdsl2VtucIntervalLoss            Counter32,
                 adGenVdsl2VtucIntervalLols            Counter32,
                 adGenVdsl2VtucIntervalLprs            Counter32,
                 adGenVdsl2VtucIntervalES              Counter32,
                 adGenVdsl2VtucIntervalInits           Counter32,
                 adGenVdsl2VtucIntervalValidData         INTEGER,
                 adGenVdsl2VtucIntervalSES             Counter32,
                 adGenVdsl2VtucIntervalUAS             Counter32,
                 adGenVdsl2VtucIntervalFECs            Counter32,
                 adGenVdsl2VtucIntervalFEC             Counter32,
                 adGenVdsl2VtucIntervalCRC             Counter32,
                 adGenVdsl2VtucIntervalSraDownshifts   Counter32,
                 adGenVdsl2VtucIntervalSraUpshifts     Counter32,
                 adGenVdsl2VtucIntervalSraRateMax        Gauge32,
                 adGenVdsl2VtucIntervalSraRateMin        Gauge32,
                 adGenVdsl2VtucIntervalRtxMinEftr        Gauge32,
                 adGenVdsl2VtucIntervalRtxLeftrs       Counter32
             }

         adGenVdsl2VtucIntervalNumber OBJECT-TYPE
             SYNTAX      Integer32(1..96)
             MAX-ACCESS  read-only
             STATUS      current
             DESCRIPTION
                 "Performance Data Interval number 1 is the
                 the most recent previous interval; interval
                 96 is 24 hours ago.  Intervals 2..96 are
                 optional."
         ::= { adGenVdsl2VtucIntervalEntry 1 }

         adGenVdsl2VtucIntervalLofs OBJECT-TYPE
             SYNTAX      Counter32
             UNITS       "seconds"
             MAX-ACCESS  read-only
             STATUS      current
             DESCRIPTION
                 "Count of seconds in the interval when there was Loss
                 of Framing."
         ::= { adGenVdsl2VtucIntervalEntry 2 }

         adGenVdsl2VtucIntervalLoss  OBJECT-TYPE
             SYNTAX      Counter32
             UNITS       "seconds"
             MAX-ACCESS  read-only
             STATUS      current
             DESCRIPTION
                 "Count of seconds in the interval when there was Loss
                  of Signal."
         ::= { adGenVdsl2VtucIntervalEntry 3 }

         adGenVdsl2VtucIntervalLols  OBJECT-TYPE
             SYNTAX      Counter32
             UNITS       "seconds"
             MAX-ACCESS  read-only
             STATUS      current
             DESCRIPTION
                 "Count of seconds in the interval when there was Loss of Link."
         ::= { adGenVdsl2VtucIntervalEntry 4 }

         adGenVdsl2VtucIntervalLprs  OBJECT-TYPE
             SYNTAX      Counter32
             UNITS       "seconds"
             MAX-ACCESS  read-only
             STATUS      current
             DESCRIPTION
                 "Count of seconds in the interval when there was Loss
                  of Power."
         ::= { adGenVdsl2VtucIntervalEntry 5 }

         adGenVdsl2VtucIntervalES OBJECT-TYPE
             SYNTAX      Counter32
             UNITS       "seconds"
             MAX-ACCESS  read-only
             STATUS      current
             DESCRIPTION
                 "Count of Errored Seconds in the interval."
         ::= { adGenVdsl2VtucIntervalEntry 6 }

         adGenVdsl2VtucIntervalInits  OBJECT-TYPE
             SYNTAX      Counter32
             MAX-ACCESS  read-only
             STATUS      current
             DESCRIPTION
                 "Count of the line initialization attempts
                 during the interval. Includes both successful
                 and failed attempts."
         ::= { adGenVdsl2VtucIntervalEntry 7 }

         adGenVdsl2VtucIntervalValidData OBJECT-TYPE
             SYNTAX      INTEGER {
                 valid (1),            -- no channels exist
                 notValid (2)          -- fast channel exists only
             }
             MAX-ACCESS read-only
             STATUS current
             DESCRIPTION
                 "This variable indicates if the data for this
                 interval is valid."
         ::= { adGenVdsl2VtucIntervalEntry 8 }

         adGenVdsl2VtucIntervalSES OBJECT-TYPE
             SYNTAX      Counter32
             UNITS       "seconds"
             MAX-ACCESS  read-only
             STATUS      current
             DESCRIPTION
                 "Count of Severely Errored Seconds in the interval."
         ::= { adGenVdsl2VtucIntervalEntry 9 }

         adGenVdsl2VtucIntervalUAS OBJECT-TYPE
             SYNTAX      Counter32
             UNITS       "seconds"
             MAX-ACCESS  read-only
             STATUS      current
             DESCRIPTION
                 "Count of Unavailable Seconds in the interval."
         ::= { adGenVdsl2VtucIntervalEntry 10 }

         adGenVdsl2VtucIntervalFECs OBJECT-TYPE
             SYNTAX      Counter32
             UNITS       "seconds"
             MAX-ACCESS  read-only
             STATUS      current
             DESCRIPTION
                 "Count of seconds in the interval during which at
                 least one forward error correction event took
                 place."
         ::= { adGenVdsl2VtucIntervalEntry 11 }

         adGenVdsl2VtucIntervalFEC OBJECT-TYPE
             SYNTAX      Counter32
             UNITS       "seconds"
             MAX-ACCESS  read-only
             STATUS      current
             DESCRIPTION
                 "Count of forward error correction events that
                 took place in the interval."
         ::= { adGenVdsl2VtucIntervalEntry 12 }

         adGenVdsl2VtucIntervalCRC OBJECT-TYPE
             SYNTAX      Counter32
             UNITS       "seconds"
             MAX-ACCESS  read-only
             STATUS      current
             DESCRIPTION
                 "Count of CRC anomolies that took place in the interval."
         ::= { adGenVdsl2VtucIntervalEntry 13 }

         adGenVdsl2VtucIntervalSraDownshifts OBJECT-TYPE
             SYNTAX      Counter32
             UNITS       "downshifts"
             MAX-ACCESS  read-only
             STATUS      current
             DESCRIPTION
                 "Count of SRA payload rate downshifts since last
                 successful train in the specified 15-min interval"
         ::= { adGenVdsl2VtucIntervalEntry 14 }

         adGenVdsl2VtucIntervalSraUpshifts OBJECT-TYPE
             SYNTAX      Counter32
             UNITS       "upshifts"
             MAX-ACCESS  read-only
             STATUS      current
             DESCRIPTION
                 "Count of SRA payload rate upshifts since last
                 successful train in the specified 15-min interval"
         ::= { adGenVdsl2VtucIntervalEntry 15 }

         adGenVdsl2VtucIntervalSraRateMax OBJECT-TYPE
             SYNTAX      Gauge32
             UNITS       "bps"
             MAX-ACCESS  read-only
             STATUS      current
             DESCRIPTION
                 "Max payload rate in the specified 15-min interval
                 since last successful train."
         ::= { adGenVdsl2VtucIntervalEntry 16 }

         adGenVdsl2VtucIntervalSraRateMin OBJECT-TYPE
             SYNTAX      Gauge32
             UNITS       "bps"
             MAX-ACCESS  read-only
             STATUS      current
             DESCRIPTION
                 "Min payload rate in the specified 15-min interval
                 since last successful train."
         ::= { adGenVdsl2VtucIntervalEntry 17 }

         adGenVdsl2VtucIntervalRtxMinEftr OBJECT-TYPE
             SYNTAX      Gauge32
             UNITS       "bps"
             MAX-ACCESS  read-only
             STATUS      current
             DESCRIPTION
                 "Retransmission parameter defined as the minimum of
                  the error-free throughput rate observed in the specified
                  15-min interval."
             REFERENCE "Recommendation ITU-T G.998.4, Clause 11.4.3"
         ::= { adGenVdsl2VtucIntervalEntry 18 }

         adGenVdsl2VtucIntervalRtxLeftrs OBJECT-TYPE
             SYNTAX      Counter32
             UNITS       "seconds"
             MAX-ACCESS  read-only
             STATUS      current
             DESCRIPTION
                 "Count of low error-free throughput rate defect
                  seconds in the specified 15-min interval."
             REFERENCE "Recommendation ITU-T G.998.4, Clause 11.4.1"
         ::= { adGenVdsl2VtucIntervalEntry 19 }


         -- ========= PM Group (adGenVdsl2VturIntervalTable) =================
         adGenVdsl2VturIntervalTable   OBJECT-TYPE
             SYNTAX          SEQUENCE OF AdGenVdsl2VturIntervalEntry
             MAX-ACCESS      not-accessible
             STATUS          current
             DESCRIPTION
                 "This table provides one row for each Vtur
                 performance data collection 1 Day interval.
                 VDSL2 physical interfaces are those
                 ifEntries where ifType is equal to vdsl(97)."
         ::= { adGenVdsl2PM 4 }

         adGenVdsl2VturIntervalEntry   OBJECT-TYPE
             SYNTAX          AdGenVdsl2VturIntervalEntry
             MAX-ACCESS      not-accessible
             STATUS          current
             DESCRIPTION     "An entry in the adGenVdsl2VturIntervalTable."
             INDEX           { ifIndex, adGenVdsl2VturIntervalNumber }
         ::= { adGenVdsl2VturIntervalTable 1 }

         AdGenVdsl2VturIntervalEntry ::=
             SEQUENCE {
                 adGenVdsl2VturIntervalNumber          Integer32,
                 adGenVdsl2VturIntervalLofs            Counter32,
                 adGenVdsl2VturIntervalLoss            Counter32,
                 adGenVdsl2VturIntervalLprs            Counter32,
                 adGenVdsl2VturIntervalES              Counter32,
                 adGenVdsl2VturIntervalValidData         INTEGER,
                 adGenVdsl2VturIntervalSES             Counter32,
                 adGenVdsl2VturIntervalUAS             Counter32,
                 adGenVdsl2VturIntervalFECs            Counter32,
                 adGenVdsl2VturIntervalFEC             Counter32,
                 adGenVdsl2VturIntervalCRC             Counter32,
                 adGenVdsl2VturIntervalSraDownshifts   Counter32,
                 adGenVdsl2VturIntervalSraUpshifts     Counter32,
                 adGenVdsl2VturIntervalSraRateMax        Gauge32,
                 adGenVdsl2VturIntervalSraRateMin        Gauge32,
                 adGenVdsl2VturIntervalRtxMinEftr        Gauge32,
                 adGenVdsl2VturIntervalRtxLeftrs       Counter32
             }

         adGenVdsl2VturIntervalNumber OBJECT-TYPE
             SYNTAX      Integer32(1..96)
             MAX-ACCESS  read-only
             STATUS      current
             DESCRIPTION
                 "Performance Data Interval number 1 is the
                 the most recent previous interval; interval
                 96 is 24 hours ago.  Intervals 2..96 are
                 optional."
         ::= { adGenVdsl2VturIntervalEntry 1 }

         adGenVdsl2VturIntervalLofs OBJECT-TYPE
             SYNTAX      Counter32
             UNITS       "seconds"
             MAX-ACCESS  read-only
             STATUS      current
             DESCRIPTION
                 "Count of seconds in the interval when there was
                 Loss of Framing."
         ::= { adGenVdsl2VturIntervalEntry 2 }

         adGenVdsl2VturIntervalLoss  OBJECT-TYPE
             SYNTAX      Counter32
             UNITS       "seconds"
             MAX-ACCESS  read-only
             STATUS      current
             DESCRIPTION
                 "Count of seconds in the interval when there was
                 Loss of Signal."
         ::= { adGenVdsl2VturIntervalEntry 3 }

         adGenVdsl2VturIntervalLprs  OBJECT-TYPE
             SYNTAX      Counter32
             UNITS       "seconds"
             MAX-ACCESS  read-only
             STATUS      current
             DESCRIPTION
                 "Count of seconds in the interval when there was
                 Loss of Power."
         ::= { adGenVdsl2VturIntervalEntry 4 }

         adGenVdsl2VturIntervalES OBJECT-TYPE
             SYNTAX      Counter32
             UNITS       "seconds"
             MAX-ACCESS  read-only
             STATUS      current
             DESCRIPTION
                 "Count of Errored Seconds in the interval."
         ::= { adGenVdsl2VturIntervalEntry 5 }

         adGenVdsl2VturIntervalValidData OBJECT-TYPE
             SYNTAX      INTEGER {
                 valid (1),
                 notValid (2)
             }
             MAX-ACCESS read-only
             STATUS current
             DESCRIPTION
                 "This variable indicates if the data for this
                  interval is valid."
         ::= { adGenVdsl2VturIntervalEntry 6 }

         adGenVdsl2VturIntervalSES OBJECT-TYPE
             SYNTAX      Counter32
             UNITS       "seconds"
             MAX-ACCESS  read-only
             STATUS      current
             DESCRIPTION
                 "Count of Severely Errored Seconds in the interval."
         ::= { adGenVdsl2VturIntervalEntry 7 }

         adGenVdsl2VturIntervalUAS OBJECT-TYPE
             SYNTAX      Counter32
             UNITS       "seconds"
             MAX-ACCESS  read-only
             STATUS      current
             DESCRIPTION
                 "Count of Unavailable Seconds in the interval."
         ::= { adGenVdsl2VturIntervalEntry 8 }

         adGenVdsl2VturIntervalFECs OBJECT-TYPE
             SYNTAX      Counter32
             UNITS       "seconds"
             MAX-ACCESS  read-only
             STATUS      current
             DESCRIPTION
                 "Count of seconds in the interval during which at
                 least one forward error correction event took
                 place."
         ::= { adGenVdsl2VturIntervalEntry 9 }

         adGenVdsl2VturIntervalFEC OBJECT-TYPE
             SYNTAX      Counter32
             UNITS       "seconds"
             MAX-ACCESS  read-only
             STATUS      current
             DESCRIPTION
                 "Count of forward error correction events that
                 took place in the interval."
         ::= { adGenVdsl2VturIntervalEntry 10 }

         adGenVdsl2VturIntervalCRC OBJECT-TYPE
             SYNTAX      Counter32
             UNITS       "seconds"
             MAX-ACCESS  read-only
             STATUS      current
             DESCRIPTION
                 "Count of CRC anomolies that took place in
                  the interval."
         ::= { adGenVdsl2VturIntervalEntry 11 }

         adGenVdsl2VturIntervalSraDownshifts OBJECT-TYPE
             SYNTAX      Counter32
             UNITS       "downshifts"
             MAX-ACCESS  read-only
             STATUS      current
             DESCRIPTION
                 "Count of SRA payload rate downshifts since last
                 successful train in the specified 15-min interval"
         ::= { adGenVdsl2VturIntervalEntry 12 }

         adGenVdsl2VturIntervalSraUpshifts OBJECT-TYPE
             SYNTAX      Counter32
             UNITS       "upshifts"
             MAX-ACCESS  read-only
             STATUS      current
             DESCRIPTION
                 "Count of SRA payload rate upshifts since last
                 successful train in the specified 15-min interval"
         ::= { adGenVdsl2VturIntervalEntry 13 }

         adGenVdsl2VturIntervalSraRateMax OBJECT-TYPE
             SYNTAX      Gauge32
             UNITS       "bps"
             MAX-ACCESS  read-only
             STATUS      current
             DESCRIPTION
                 "Max payload rate in the specified 15-min interval
                 since last successful train."
         ::= { adGenVdsl2VturIntervalEntry 14 }

         adGenVdsl2VturIntervalSraRateMin OBJECT-TYPE
             SYNTAX      Gauge32
             UNITS       "bps"
             MAX-ACCESS  read-only
             STATUS      current
             DESCRIPTION
                 "Min payload rate in the specified 15-min interval
                 since last successful train."
         ::= { adGenVdsl2VturIntervalEntry 15 }

         adGenVdsl2VturIntervalRtxMinEftr OBJECT-TYPE
             SYNTAX      Gauge32
             UNITS       "bps"
             MAX-ACCESS  read-only
             STATUS      current
             DESCRIPTION
                 "Retransmission parameter defined as the minimum of
                  the error-free throughput rate observed in the specified
                  15-min interval."
             REFERENCE "Recommendation ITU-T G.998.4, Clause 11.4.3"
         ::= { adGenVdsl2VturIntervalEntry 16 }

         adGenVdsl2VturIntervalRtxLeftrs OBJECT-TYPE
             SYNTAX      Counter32
             UNITS       "seconds"
             MAX-ACCESS  read-only
             STATUS      current
             DESCRIPTION
                 "Count of low error-free throughput rate defect
                  seconds in the specified 15-min interval."
             REFERENCE "Recommendation ITU-T G.998.4, Clause 11.4.1"
         ::= { adGenVdsl2VturIntervalEntry 17 }


         -- ========= PM Group (adGenVdsl2VtucChanPerfDataTable) =============
         adGenVdsl2VtucChanPerfDataTable       OBJECT-TYPE
             SYNTAX          SEQUENCE OF AdGenVdsl2VtucChanPerfDataEntry
             MAX-ACCESS      not-accessible
             STATUS          current
             DESCRIPTION
                 "This table provides one row for each Vtuc channel.
                 VDSL2 channel interfaces can range from 1 -4"
         ::= { adGenVdsl2PM 5 }

         adGenVdsl2VtucChanPerfDataEntry       OBJECT-TYPE

             SYNTAX          AdGenVdsl2VtucChanPerfDataEntry
             MAX-ACCESS      not-accessible
             STATUS          current
             DESCRIPTION     "An entry in adGenVdsl2VtucChanPerfDataTable."
             INDEX           { ifIndex, adGenVdsl2VtucChanNumber }
         ::= { adGenVdsl2VtucChanPerfDataTable 1 }

         AdGenVdsl2VtucChanPerfDataEntry ::=
          SEQUENCE {
              adGenVdsl2VtucChanNumber                            Integer32,
              adGenVdsl2VtucChanReceivedBlks                      Counter32,
              adGenVdsl2VtucChanTransmittedBlks                   Counter32,
              adGenVdsl2VtucChanCorrectedBlks                     Counter32,
              adGenVdsl2VtucChanUncorrectBlks                     Counter32,
              adGenVdsl2VtucChanPerfValidIntervals                Integer32,
              adGenVdsl2VtucChanPerfInvalidIntervals              Integer32,
              adGenVdsl2VtucChanPerfCurr15MinTimeElapsed          Gauge32,
              adGenVdsl2VtucChanPerfCurr15MinReceivedBlks         Counter32,
              adGenVdsl2VtucChanPerfCurr15MinTransmittedBlks      Counter32,
              adGenVdsl2VtucChanPerfCurr15MinCorrectedBlks        Counter32,
              adGenVdsl2VtucChanPerfCurr15MinUncorrectBlks        Counter32,
              adGenVdsl2VtucChanPerfCurr1DayTimeElapsed           Gauge32,
              adGenVdsl2VtucChanPerfCurr1DayReceivedBlks          Counter32,
              adGenVdsl2VtucChanPerfCurr1DayTransmittedBlks       Counter32,
              adGenVdsl2VtucChanPerfCurr1DayCorrectedBlks         Counter32,
              adGenVdsl2VtucChanPerfCurr1DayUncorrectBlks         Counter32,
              adGenVdsl2VtucChanPerfTcTxUnits                     Counter32,
              adGenVdsl2VtucChanPerfTcTxDataUnits                 Counter32,
              adGenVdsl2VtucChanPerfTcTxDataOctets                Counter32,
              adGenVdsl2VtucChanPerfTcTxIdleUnits                 Counter32,
              adGenVdsl2VtucChanPerfTcRxUnits                     Counter32,
              adGenVdsl2VtucChanPerfTcRxDataUnits                 Counter32,
              adGenVdsl2VtucChanPerfTcRxDataOctets                Counter32,
              adGenVdsl2VtucChanPerfTcRxIdleUnits                 Counter32,
              adGenVdsl2VtucChanPerfTcRxErroredUnits              Counter32,
              adGenVdsl2VtucChanPerfRtxUncorrectedDtu             Counter32,
              adGenVdsl2VtucChanPerfRtxCorrectedDtu               Counter32,
              adGenVdsl2VtucChanPerfRtxRetransmittedDtu           Counter32,
              adGenVdsl2VtucChanPerfCurr15MinRtxUncorrectedDtu    Counter32,
              adGenVdsl2VtucChanPerfCurr15MinRtxCorrectedDtu      Counter32,
              adGenVdsl2VtucChanPerfCurr15MinRtxRetransmittedDtu  Counter32,
              adGenVdsl2VtucChanPerfCurr1DayRtxUncorrectedDtu     Counter32,
              adGenVdsl2VtucChanPerfCurr1DayRtxCorrectedDtu       Counter32,
              adGenVdsl2VtucChanPerfCurr1DayRtxRetransmittedDtu   Counter32
          }

         adGenVdsl2VtucChanNumber OBJECT-TYPE
             SYNTAX      Integer32(1..4)
             MAX-ACCESS  read-only
             STATUS      current
             DESCRIPTION
                 "VDSL2 logical channel. Channel values are 1 - 4."
         ::= { adGenVdsl2VtucChanPerfDataEntry 1 }


         adGenVdsl2VtucChanReceivedBlks OBJECT-TYPE
             SYNTAX      Counter32
             MAX-ACCESS  read-only
             STATUS      current
             DESCRIPTION
                 "Count of all encoded blocks received on this channel
                 since agent reset."
         ::= { adGenVdsl2VtucChanPerfDataEntry 2 }

         adGenVdsl2VtucChanTransmittedBlks  OBJECT-TYPE
             SYNTAX      Counter32
             MAX-ACCESS  read-only
             STATUS      current
             DESCRIPTION
                 "Count of all encoded blocks transmitted on this
                 channel since agent reset."
         ::= { adGenVdsl2VtucChanPerfDataEntry 3 }

         adGenVdsl2VtucChanCorrectedBlks  OBJECT-TYPE
             SYNTAX      Counter32
             MAX-ACCESS  read-only
             STATUS      current
             DESCRIPTION
                 "Count of all blocks received with errors that were
                 corrected since agent reset.  These blocks are passed
                 on as good data."
         ::= { adGenVdsl2VtucChanPerfDataEntry 4 }

         adGenVdsl2VtucChanUncorrectBlks  OBJECT-TYPE
             SYNTAX      Counter32
             MAX-ACCESS  read-only
             STATUS      current
             DESCRIPTION
                 "Count of all blocks received with uncorrectable
                 errors since agent reset."
         ::= { adGenVdsl2VtucChanPerfDataEntry 5 }

         adGenVdsl2VtucChanPerfValidIntervals OBJECT-TYPE
             SYNTAX      Integer32(0..96)
             MAX-ACCESS  read-only
             STATUS      current
             DESCRIPTION
                 "The number of previous 15-minute intervals in the
                 interval table for which data was collected.  Given
                 that <n> is the maximum # of intervals supported.
                 The value will be <n> unless the measurement was
                 (re-)started within the last (<n>*15) minutes, in which
                 case the value will be the number of complete 15
                 minute intervals for which the agent has at least
                 some data. In certain cases (e.g., in the case
                 where the agent is a proxy) it is possible that some
                 intervals are unavailable.  In this case, this
                 interval is the maximum interval number for
                 which data is available."
         ::= { adGenVdsl2VtucChanPerfDataEntry 6 }

         adGenVdsl2VtucChanPerfInvalidIntervals OBJECT-TYPE
             SYNTAX      Integer32(0..96)
             MAX-ACCESS  read-only
             STATUS      current
             DESCRIPTION
                 "The number of intervals in the range from
                 0 to the value of adGenVdsl2VtucChanPerfValidIntervals
                 for which no data is available. This object
                 will typically be zero except in cases where
                 the data for some intervals are not available
                 (e.g., in proxy situations)."
         ::= { adGenVdsl2VtucChanPerfDataEntry 7 }

         adGenVdsl2VtucChanPerfCurr15MinTimeElapsed OBJECT-TYPE
             SYNTAX      Gauge32(0..899)
             UNITS       "seconds"
             MAX-ACCESS  read-only
             STATUS      current
             DESCRIPTION
                 "Total elapsed seconds in this interval."
         ::= { adGenVdsl2VtucChanPerfDataEntry 8}

         adGenVdsl2VtucChanPerfCurr15MinReceivedBlks OBJECT-TYPE
             SYNTAX      Counter32
             MAX-ACCESS  read-only
             STATUS      current
             DESCRIPTION
                 "Count of all encoded blocks received on this channel
                 within the current 15 minute interval."
         ::= { adGenVdsl2VtucChanPerfDataEntry 9 }


         adGenVdsl2VtucChanPerfCurr15MinTransmittedBlks OBJECT-TYPE
             SYNTAX      Counter32
             MAX-ACCESS  read-only
             STATUS      current
             DESCRIPTION
                 "Count of all encoded blocks transmitted on this
                 channel within the current 15 minute interval."
         ::= { adGenVdsl2VtucChanPerfDataEntry 10 }

         adGenVdsl2VtucChanPerfCurr15MinCorrectedBlks  OBJECT-TYPE
             SYNTAX      Counter32
             MAX-ACCESS  read-only
             STATUS      current
             DESCRIPTION
                 "Count of all blocks received with errors that were
                 corrected on this channel within the current 15 minute
                 interval."
         ::= { adGenVdsl2VtucChanPerfDataEntry 11 }

         adGenVdsl2VtucChanPerfCurr15MinUncorrectBlks  OBJECT-TYPE
             SYNTAX      Counter32
             MAX-ACCESS  read-only
             STATUS      current
             DESCRIPTION
                 "Count of all blocks received with uncorrectable
                 errors on this channel within the current 15 minute
                 interval."
         ::= { adGenVdsl2VtucChanPerfDataEntry 12 }

         adGenVdsl2VtucChanPerfCurr1DayTimeElapsed OBJECT-TYPE
             SYNTAX      Gauge32(0..86399)
             UNITS       "seconds"
             MAX-ACCESS  read-only
             STATUS      current
             DESCRIPTION
                 "Number of seconds that have elapsed since the
                 beginning of the current 1-day interval."
         ::= { adGenVdsl2VtucChanPerfDataEntry 13 }

         adGenVdsl2VtucChanPerfCurr1DayReceivedBlks  OBJECT-TYPE
             SYNTAX      Counter32
             MAX-ACCESS  read-only
             STATUS      current
             DESCRIPTION
                 "Count of all encoded blocks received on this
                 channel during the current day as measured by


                 adGenVdsl2VtucChanPerfCurr1DayTimeElapsed."
         ::= { adGenVdsl2VtucChanPerfDataEntry 14 }

         adGenVdsl2VtucChanPerfCurr1DayTransmittedBlks  OBJECT-TYPE
             SYNTAX      Counter32
             MAX-ACCESS  read-only
             STATUS      current
             DESCRIPTION
                 "Count of all encoded blocks transmitted on this
                 channel during the current day as measured by
                 adGenVdsl2VtucChanPerfCurr1DayTimeElapsed."
         ::= { adGenVdsl2VtucChanPerfDataEntry 15 }

         adGenVdsl2VtucChanPerfCurr1DayCorrectedBlks  OBJECT-TYPE
             SYNTAX      Counter32
             MAX-ACCESS  read-only
             STATUS      current
             DESCRIPTION
                 "Count of all blocks received with errors that were
                 corrected on this channel during the current day as
                 measured by adGenVdsl2VtucChanPerfCurr1DayTimeElapsed."
         ::= { adGenVdsl2VtucChanPerfDataEntry 16 }

         adGenVdsl2VtucChanPerfCurr1DayUncorrectBlks  OBJECT-TYPE
             SYNTAX      Counter32
             MAX-ACCESS  read-only
             STATUS      current
             DESCRIPTION
                 "Count of all blocks received with uncorrectable
                 errors on this channel during the current day as
                 measured by adGenVdsl2VtucChanPerfCurr1DayTimeElapsed."
         ::= { adGenVdsl2VtucChanPerfDataEntry 17 }

         adGenVdsl2VtucChanPerfTcTxUnits OBJECT-TYPE
             SYNTAX      Counter32
             UNITS       "pkts/cells"
             MAX-ACCESS  read-only
             STATUS      current
             DESCRIPTION
                 "Count of total transmitted transmission convergence layer
                  (TC) cells (ATM framing mode) or packets (other framing
                  modes)."
         ::= { adGenVdsl2VtucChanPerfDataEntry 18 }

         adGenVdsl2VtucChanPerfTcTxDataUnits OBJECT-TYPE
             SYNTAX      Counter32
             UNITS       "pkts/cells"
             MAX-ACCESS  read-only
             STATUS      current
             DESCRIPTION
                 "Count of data carrying transmitted transmission convergence
                  layer (TC) cells (ATM framing mode) or packets (other
                  framing modes)."
         ::= { adGenVdsl2VtucChanPerfDataEntry 19 }

         adGenVdsl2VtucChanPerfTcTxDataOctets OBJECT-TYPE
             SYNTAX      Counter32
             UNITS       "octets"
             MAX-ACCESS  read-only
             STATUS      current
             DESCRIPTION
                 "Count of octets in data carrying transmitted transmission
                  convergence layer (TC) cells (ATM framing mode) or packets
                  (other framing modes)."
         ::= { adGenVdsl2VtucChanPerfDataEntry 20 }

         adGenVdsl2VtucChanPerfTcTxIdleUnits OBJECT-TYPE
             SYNTAX      Counter32
             UNITS       "pkts/cells"
             MAX-ACCESS  read-only
             STATUS      current
             DESCRIPTION
                 "Count of idle/pause transmitted transmission convergence
                  layer (TC) cells (ATM framing mode) or packets (other
                  framing modes)."
         ::= { adGenVdsl2VtucChanPerfDataEntry 21 }

         adGenVdsl2VtucChanPerfTcRxUnits OBJECT-TYPE
             SYNTAX      Counter32
             UNITS       "pkts/cells"
             MAX-ACCESS  read-only
             STATUS      current
             DESCRIPTION
                 "Count of total transmitted transmission convergence layer
                  (TC) cells (ATM framing mode) or packets (other framing
                  modes)."
         ::= { adGenVdsl2VtucChanPerfDataEntry 22 }

         adGenVdsl2VtucChanPerfTcRxDataUnits OBJECT-TYPE
             SYNTAX      Counter32
             UNITS       "pkts/cells"
             MAX-ACCESS  read-only
             STATUS      current
             DESCRIPTION
                 "Count of data carrying received transmission convergence
                  layer (TC) cells (ATM framing mode) or packets (other
                  framing modes)."
         ::= { adGenVdsl2VtucChanPerfDataEntry 23 }

         adGenVdsl2VtucChanPerfTcRxDataOctets OBJECT-TYPE
             SYNTAX      Counter32
             UNITS       "octets"
             MAX-ACCESS  read-only
             STATUS      current
             DESCRIPTION
                 "Count of octets in data carrying received transmission
                  convergence layer (TC) cells (ATM framing mode) or packets
                  (other framing modes)."
         ::= { adGenVdsl2VtucChanPerfDataEntry 24 }

         adGenVdsl2VtucChanPerfTcRxIdleUnits OBJECT-TYPE
             SYNTAX      Counter32
             UNITS       "pkts/cells"
             MAX-ACCESS  read-only
             STATUS      current
             DESCRIPTION
                 "Count of idle/pause received transmission convergence
                  layer (TC) cells (ATM framing mode) or packets (other
                  framing modes)."
         ::= { adGenVdsl2VtucChanPerfDataEntry 25 }

         adGenVdsl2VtucChanPerfTcRxErroredUnits OBJECT-TYPE
             SYNTAX      Counter32
             UNITS       "pkts/cells"
             MAX-ACCESS  read-only
             STATUS      current
             DESCRIPTION
                 "Count of errored received transmission convergence
                  layer (TC) cells (ATM framing mode) or packets (other
                  framing modes)."
         ::= { adGenVdsl2VtucChanPerfDataEntry 26 }

         adGenVdsl2VtucChanPerfRtxUncorrectedDtu OBJECT-TYPE
             SYNTAX      Counter32
             UNITS       "dtus"
             MAX-ACCESS  read-only
             STATUS      current
             DESCRIPTION
                 "Count of DTUs since reset that have been detected in error
                  and that have not been corrected by one or more retransmissions
                  within the maximum delay constraint."
             REFERENCE "Recommendation ITU-T G.998.4, Clause 12"
         ::= { adGenVdsl2VtucChanPerfDataEntry 27 }

         adGenVdsl2VtucChanPerfRtxCorrectedDtu OBJECT-TYPE
             SYNTAX      Counter32
             UNITS       "dtus"
             MAX-ACCESS  read-only
             STATUS      current
             DESCRIPTION
                 "Count of DTUs since reset that have been detected in error
                  and that have been successfully corrected by a retransmission
                  within the maximum delay constraint."
             REFERENCE "Recommendation ITU-T G.998.4, Clause 12"
         ::= { adGenVdsl2VtucChanPerfDataEntry 28 }

         adGenVdsl2VtucChanPerfRtxRetransmittedDtu OBJECT-TYPE
             SYNTAX      Counter32
             UNITS       "dtus"
             MAX-ACCESS  read-only
             STATUS      current
             DESCRIPTION
                 "Count of DTUs since reset that have been retransmitted."
             REFERENCE "Recommendation ITU-T G.998.4, Clause 12"
         ::= { adGenVdsl2VtucChanPerfDataEntry 29 }

         adGenVdsl2VtucChanPerfCurr15MinRtxUncorrectedDtu OBJECT-TYPE
             SYNTAX      Counter32
             UNITS       "dtus"
             MAX-ACCESS  read-only
             STATUS      current
             DESCRIPTION
                 "Count of DTUs in the current 15-min interval that have been
                  detected in error and that have not been corrected by one or
                  more retransmissions within the maximum delay constraint."
             REFERENCE "Recommendation ITU-T G.998.4, Clause 12"
         ::= { adGenVdsl2VtucChanPerfDataEntry 30 }

         adGenVdsl2VtucChanPerfCurr15MinRtxCorrectedDtu OBJECT-TYPE
             SYNTAX      Counter32
             UNITS       "dtus"
             MAX-ACCESS  read-only
             STATUS      current
             DESCRIPTION
                 "Count of DTUs in the current 15-min interval that have been
                  detected in error and that have been successfully corrected
                  by a retransmission within the maximum delay constraint."
             REFERENCE "Recommendation ITU-T G.998.4, Clause 12"
         ::= { adGenVdsl2VtucChanPerfDataEntry 31 }

         adGenVdsl2VtucChanPerfCurr15MinRtxRetransmittedDtu OBJECT-TYPE
             SYNTAX      Counter32
             UNITS       "dtus"
             MAX-ACCESS  read-only
             STATUS      current
             DESCRIPTION
                 "Count of DTUs in the current 15-min interval that have been
                  retransmitted."
             REFERENCE "Recommendation ITU-T G.998.4, Clause 12"
         ::= { adGenVdsl2VtucChanPerfDataEntry 32 }

         adGenVdsl2VtucChanPerfCurr1DayRtxUncorrectedDtu OBJECT-TYPE
             SYNTAX      Counter32
             UNITS       "dtus"
             MAX-ACCESS  read-only
             STATUS      current
             DESCRIPTION
                 "Count of DTUs in the current 24-hr interval that have been
                  detected in error and that have not been corrected by one or
                  more retransmissions within the maximum delay constraint."
             REFERENCE "Recommendation ITU-T G.998.4, Clause 12"
         ::= { adGenVdsl2VtucChanPerfDataEntry 33 }

         adGenVdsl2VtucChanPerfCurr1DayRtxCorrectedDtu OBJECT-TYPE
             SYNTAX      Counter32
             UNITS       "dtus"
             MAX-ACCESS  read-only
             STATUS      current
             DESCRIPTION
                 "Count of DTUs in the current 24-hr interval that have been
                  detected in error and that have been successfully corrected
                  by a retransmission within the maximum delay constraint."
             REFERENCE "Recommendation ITU-T G.998.4, Clause 12"
         ::= { adGenVdsl2VtucChanPerfDataEntry 34 }

         adGenVdsl2VtucChanPerfCurr1DayRtxRetransmittedDtu OBJECT-TYPE
             SYNTAX      Counter32
             UNITS       "dtus"
             MAX-ACCESS  read-only
             STATUS      current
             DESCRIPTION
                 "Count of DTUs in the current 24-hr interval that have been
                  retransmitted."
             REFERENCE "Recommendation ITU-T G.998.4, Clause 12"
         ::= { adGenVdsl2VtucChanPerfDataEntry 35 }


         -- ========= PM Group (adGenVdsl2VturChanPerfDataTable) =============
         adGenVdsl2VturChanPerfDataTable       OBJECT-TYPE
             SYNTAX          SEQUENCE OF AdGenVdsl2VturChanPerfDataEntry
             MAX-ACCESS      not-accessible
             STATUS          current
             DESCRIPTION
                 "This table provides one row for each Vtur channel.
                 VDSL2 channel interfaces are those ifEntries
                 where ifType is equal to Interleave(124)
                 or Fast(125)."
         ::= { adGenVdsl2PM 6 }

         adGenVdsl2VturChanPerfDataEntry       OBJECT-TYPE
             SYNTAX          AdGenVdsl2VturChanPerfDataEntry
             MAX-ACCESS      not-accessible
             STATUS          current
             DESCRIPTION     "An entry in adGenVdsl2VturChanPerfDataTable."
             INDEX           { ifIndex, adGenVdsl2VturChanNumber }
         ::= { adGenVdsl2VturChanPerfDataTable 1 }

         AdGenVdsl2VturChanPerfDataEntry ::=
          SEQUENCE {
              adGenVdsl2VturChanNumber                            Integer32,
              adGenVdsl2VturChanReceivedBlks                      Counter32,
              adGenVdsl2VturChanTransmittedBlks                   Counter32,
              adGenVdsl2VturChanCorrectedBlks                     Counter32,
              adGenVdsl2VturChanUncorrectBlks                     Counter32,
              adGenVdsl2VturChanPerfValidIntervals                Integer32,
              adGenVdsl2VturChanPerfInvalidIntervals              Integer32,
              adGenVdsl2VturChanPerfCurr15MinTimeElapsed          Gauge32,
              adGenVdsl2VturChanPerfCurr15MinReceivedBlks         Counter32,
              adGenVdsl2VturChanPerfCurr15MinTransmittedBlks      Counter32,
              adGenVdsl2VturChanPerfCurr15MinCorrectedBlks        Counter32,
              adGenVdsl2VturChanPerfCurr15MinUncorrectBlks        Counter32,
              adGenVdsl2VturChanPerfCurr1DayTimeElapsed           Gauge32,
              adGenVdsl2VturChanPerfCurr1DayReceivedBlks          Counter32,
              adGenVdsl2VturChanPerfCurr1DayTransmittedBlks       Counter32,
              adGenVdsl2VturChanPerfCurr1DayCorrectedBlks         Counter32,
              adGenVdsl2VturChanPerfCurr1DayUncorrectBlks         Counter32,
              adGenVdsl2VturChanPerfTcTxUnits                     Counter32,
              adGenVdsl2VturChanPerfTcTxDataUnits                 Counter32,
              adGenVdsl2VturChanPerfTcTxDataOctets                Counter32,
              adGenVdsl2VturChanPerfTcTxIdleUnits                 Counter32,
              adGenVdsl2VturChanPerfTcRxUnits                     Counter32,
              adGenVdsl2VturChanPerfTcRxDataUnits                 Counter32,
              adGenVdsl2VturChanPerfTcRxDataOctets                Counter32,
              adGenVdsl2VturChanPerfTcRxIdleUnits                 Counter32,
              adGenVdsl2VturChanPerfTcRxErroredUnits              Counter32,
              adGenVdsl2VturChanPerfRtxUncorrectedDtu             Counter32,
              adGenVdsl2VturChanPerfRtxCorrectedDtu               Counter32,
              adGenVdsl2VturChanPerfRtxRetransmittedDtu           Counter32,
              adGenVdsl2VturChanPerfCurr15MinRtxUncorrectedDtu    Counter32,
              adGenVdsl2VturChanPerfCurr15MinRtxCorrectedDtu      Counter32,
              adGenVdsl2VturChanPerfCurr15MinRtxRetransmittedDtu  Counter32,
              adGenVdsl2VturChanPerfCurr1DayRtxUncorrectedDtu     Counter32,
              adGenVdsl2VturChanPerfCurr1DayRtxCorrectedDtu       Counter32,
              adGenVdsl2VturChanPerfCurr1DayRtxRetransmittedDtu   Counter32
          }

         adGenVdsl2VturChanNumber OBJECT-TYPE
             SYNTAX      Integer32(1..4)
             MAX-ACCESS  read-only
             STATUS      current
             DESCRIPTION
                 "VDSL2 logical channel. Channel values are 1 - 4."
         ::= { adGenVdsl2VturChanPerfDataEntry 1 }

         adGenVdsl2VturChanReceivedBlks OBJECT-TYPE
             SYNTAX      Counter32
             MAX-ACCESS  read-only
             STATUS      current
             DESCRIPTION
                 "Count of all encoded blocks received on this channel
                 since agent reset."
         ::= { adGenVdsl2VturChanPerfDataEntry 2 }

         adGenVdsl2VturChanTransmittedBlks  OBJECT-TYPE
             SYNTAX      Counter32
             MAX-ACCESS  read-only
             STATUS      current
             DESCRIPTION
                 "Count of all encoded blocks transmitted on this
                 channel since agent reset."
         ::= { adGenVdsl2VturChanPerfDataEntry 3 }

         adGenVdsl2VturChanCorrectedBlks  OBJECT-TYPE
             SYNTAX      Counter32
             MAX-ACCESS  read-only
             STATUS      current
             DESCRIPTION
                 "Count of all blocks received with errors that were
                 corrected since agent reset.  These blocks are passed
                 on as good data."
         ::= { adGenVdsl2VturChanPerfDataEntry 4 }

         adGenVdsl2VturChanUncorrectBlks  OBJECT-TYPE
             SYNTAX      Counter32
             MAX-ACCESS  read-only
             STATUS      current
             DESCRIPTION
                 "Count of all blocks received with uncorrectable
                 errors since agent reset."
         ::= { adGenVdsl2VturChanPerfDataEntry 5 }

         adGenVdsl2VturChanPerfValidIntervals OBJECT-TYPE
             SYNTAX      Integer32(0..96)
             MAX-ACCESS  read-only
             STATUS      current
             DESCRIPTION
                 "The number of previous 15-minute intervals in the
                 interval table for which data was collected.  Given
                 that <n> is the maximum # of intervals supported.
                 The value will be <n> unless the measurement was
                 (re-)started within the last (<n>*15) minutes, in which
                 case the value will be the number of complete 15
                 minute intervals for which the agent has at least
                 some data. In certain cases (e.g., in the case
                 where the agent is a proxy) it is possible that some
                 intervals are unavailable.  In this case, this
                 interval is the maximum interval number for
                 which data is available."
         ::= { adGenVdsl2VturChanPerfDataEntry 6 }

         adGenVdsl2VturChanPerfInvalidIntervals OBJECT-TYPE
             SYNTAX      Integer32(0..96)
             MAX-ACCESS  read-only
             STATUS      current
             DESCRIPTION
                 "The number of intervals in the range from
                 0 to the value of adGenVdsl2VturChanPerfValidIntervals
                 for which no data is available. This object
                 will typically be zero except in cases where
                 the data for some intervals are not available
                 (e.g., in proxy situations)."
         ::= { adGenVdsl2VturChanPerfDataEntry 7 }

         adGenVdsl2VturChanPerfCurr15MinTimeElapsed OBJECT-TYPE
             SYNTAX      Gauge32(0..899)
             UNITS       "seconds"
             MAX-ACCESS  read-only
             STATUS      current
             DESCRIPTION
                 "Total elapsed seconds in this interval.
                 A full interval is 900 seconds."
         ::= { adGenVdsl2VturChanPerfDataEntry 8 }

         adGenVdsl2VturChanPerfCurr15MinReceivedBlks OBJECT-TYPE
             SYNTAX      Counter32
             MAX-ACCESS  read-only
             STATUS      current
             DESCRIPTION
                 "Count of all encoded blocks received on this
                 channel within the current 15 minute interval."
         ::= { adGenVdsl2VturChanPerfDataEntry 9 }

         adGenVdsl2VturChanPerfCurr15MinTransmittedBlks OBJECT-TYPE
             SYNTAX      Counter32
             MAX-ACCESS  read-only
             STATUS      current
             DESCRIPTION
                 "Count of all encoded blocks transmitted on this
                 channel within the current 15 minute interval."
         ::= { adGenVdsl2VturChanPerfDataEntry 10 }

         adGenVdsl2VturChanPerfCurr15MinCorrectedBlks  OBJECT-TYPE
             SYNTAX      Counter32
             MAX-ACCESS  read-only
             STATUS      current
             DESCRIPTION
                 "Count of all blocks received with errors that were
                 corrected on this channel within the current 15 minute
                 interval."
         ::= { adGenVdsl2VturChanPerfDataEntry 11 }

         adGenVdsl2VturChanPerfCurr15MinUncorrectBlks  OBJECT-TYPE
             SYNTAX      Counter32
             MAX-ACCESS  read-only
             STATUS      current
             DESCRIPTION
                 "Count of all blocks received with uncorrectable
                 errors on this channel within the current 15 minute
                 interval."
         ::= { adGenVdsl2VturChanPerfDataEntry 12 }

         adGenVdsl2VturChanPerfCurr1DayTimeElapsed OBJECT-TYPE
             SYNTAX      Gauge32(0..86399)
             UNITS       "seconds"
             MAX-ACCESS  read-only
             STATUS      current
             DESCRIPTION
                 "Number of seconds that have elapsed since the
                 beginning of the current 1-day interval."
         ::= { adGenVdsl2VturChanPerfDataEntry 13 }

         adGenVdsl2VturChanPerfCurr1DayReceivedBlks  OBJECT-TYPE
             SYNTAX      Counter32
             MAX-ACCESS  read-only
             STATUS      current
             DESCRIPTION
                 "Count of all encoded blocks received on this
                 channel during the current day as measured by
                 adGenVdsl2VturChanPerfCurr1DayTimeElapsed."
         ::= { adGenVdsl2VturChanPerfDataEntry 14 }

         adGenVdsl2VturChanPerfCurr1DayTransmittedBlks  OBJECT-TYPE
             SYNTAX      Counter32
             MAX-ACCESS  read-only
             STATUS      current
             DESCRIPTION
                 "Count of all encoded blocks transmitted on this
                 channel during the current day as measured by
                 adGenVdsl2VturChanPerfCurr1DayTimeElapsed."

         ::= { adGenVdsl2VturChanPerfDataEntry 15 }

         adGenVdsl2VturChanPerfCurr1DayCorrectedBlks  OBJECT-TYPE
             SYNTAX      Counter32
             MAX-ACCESS  read-only
             STATUS      current
             DESCRIPTION
                 "Count of all blocks received with errors that were
                 corrected on this channel during the current day as
                 measured by adGenVdsl2VturChanPerfCurr1DayTimeElapsed."
         ::= { adGenVdsl2VturChanPerfDataEntry 16}

         adGenVdsl2VturChanPerfCurr1DayUncorrectBlks  OBJECT-TYPE
             SYNTAX      Counter32
             MAX-ACCESS  read-only
             STATUS      current
             DESCRIPTION
                 "Count of all blocks received with uncorrectable
                 errors on this channel during the current day as
                 measured by adGenVdsl2VturChanPerfCurr1DayTimeElapsed."
         ::= { adGenVdsl2VturChanPerfDataEntry 17 }

         adGenVdsl2VturChanPerfTcTxUnits OBJECT-TYPE
             SYNTAX      Counter32
             UNITS       "pkts/cells"
             MAX-ACCESS  read-only
             STATUS      current
             DESCRIPTION
                 "Count of total transmitted transmission convergence layer
                  (TC) cells (ATM framing mode) or packets (other framing
                  modes)."
         ::= { adGenVdsl2VturChanPerfDataEntry 18 }

         adGenVdsl2VturChanPerfTcTxDataUnits OBJECT-TYPE
             SYNTAX      Counter32
             UNITS       "pkts/cells"
             MAX-ACCESS  read-only
             STATUS      current
             DESCRIPTION
                 "Count of data carrying transmitted transmission convergence
                  layer (TC) cells (ATM framing mode) or packets (other
                  framing modes)."
         ::= { adGenVdsl2VturChanPerfDataEntry 19 }

         adGenVdsl2VturChanPerfTcTxDataOctets OBJECT-TYPE
             SYNTAX      Counter32
             UNITS       "octets"
             MAX-ACCESS  read-only
             STATUS      current
             DESCRIPTION
                 "Count of octets in data carrying transmitted transmission
                  convergence layer (TC) cells (ATM framing mode) or packets
                  (other framing modes)."
         ::= { adGenVdsl2VturChanPerfDataEntry 20 }

         adGenVdsl2VturChanPerfTcTxIdleUnits OBJECT-TYPE
             SYNTAX      Counter32
             UNITS       "pkts/cells"
             MAX-ACCESS  read-only
             STATUS      current
             DESCRIPTION
                 "Count of idle/pause transmitted transmission convergence
                  layer (TC) cells (ATM framing mode) or packets (other
                  framing modes)."
         ::= { adGenVdsl2VturChanPerfDataEntry 21 }

         adGenVdsl2VturChanPerfTcRxUnits OBJECT-TYPE
             SYNTAX      Counter32
             UNITS       "pkts/cells"
             MAX-ACCESS  read-only
             STATUS      current
             DESCRIPTION
                 "Count of total transmitted transmission convergence layer
                  (TC) cells (ATM framing mode) or packets (other framing
                  modes)."
         ::= { adGenVdsl2VturChanPerfDataEntry 22 }

         adGenVdsl2VturChanPerfTcRxDataUnits OBJECT-TYPE
             SYNTAX      Counter32
             UNITS       "pkts/cells"
             MAX-ACCESS  read-only
             STATUS      current
             DESCRIPTION
                 "Count of data carrying received transmission convergence
                  layer (TC) cells (ATM framing mode) or packets (other
                  framing modes)."
         ::= { adGenVdsl2VturChanPerfDataEntry 23 }

         adGenVdsl2VturChanPerfTcRxDataOctets OBJECT-TYPE
             SYNTAX      Counter32
             UNITS       "octets"
             MAX-ACCESS  read-only
             STATUS      current
             DESCRIPTION
                 "Count of octets in data carrying received transmission
                  convergence layer (TC) cells (ATM framing mode) or packets
                  (other framing modes)."
         ::= { adGenVdsl2VturChanPerfDataEntry 24 }

         adGenVdsl2VturChanPerfTcRxIdleUnits OBJECT-TYPE
             SYNTAX      Counter32
             UNITS       "pkts/cells"
             MAX-ACCESS  read-only
             STATUS      current
             DESCRIPTION
                 "Count of idle/pause received transmission convergence
                  layer (TC) cells (ATM framing mode) or packets (other
                  framing modes)."
         ::= { adGenVdsl2VturChanPerfDataEntry 25 }

         adGenVdsl2VturChanPerfTcRxErroredUnits OBJECT-TYPE
             SYNTAX      Counter32
             UNITS       "pkts/cells"
             MAX-ACCESS  read-only
             STATUS      current
             DESCRIPTION
                 "Count of errored received transmission convergence
                  layer (TC) cells (ATM framing mode) or packets (other
                  framing modes)."
         ::= { adGenVdsl2VturChanPerfDataEntry 26 }

         adGenVdsl2VturChanPerfRtxUncorrectedDtu OBJECT-TYPE
             SYNTAX      Counter32
             UNITS       "dtus"
             MAX-ACCESS  read-only
             STATUS      current
             DESCRIPTION
                 "Count of DTUs since reset that have been detected in error
                  and that have not been corrected by one or more retransmissions
                  within the maximum delay constraint."
             REFERENCE "Recommendation ITU-T G.998.4, Clause 12"
         ::= { adGenVdsl2VturChanPerfDataEntry 27 }

         adGenVdsl2VturChanPerfRtxCorrectedDtu OBJECT-TYPE
             SYNTAX      Counter32
             UNITS       "dtus"
             MAX-ACCESS  read-only
             STATUS      current
             DESCRIPTION
                 "Count of DTUs since reset that have been detected in error
                  and that have been successfully corrected by a retransmission
                  within the maximum delay constraint."
             REFERENCE "Recommendation ITU-T G.998.4, Clause 12"
         ::= { adGenVdsl2VturChanPerfDataEntry 28 }

         adGenVdsl2VturChanPerfRtxRetransmittedDtu OBJECT-TYPE
             SYNTAX      Counter32
             UNITS       "dtus"
             MAX-ACCESS  read-only
             STATUS      current
             DESCRIPTION
                 "Count of DTUs since reset that have been retransmitted."
             REFERENCE "Recommendation ITU-T G.998.4, Clause 12"
         ::= { adGenVdsl2VturChanPerfDataEntry 29 }

         adGenVdsl2VturChanPerfCurr15MinRtxUncorrectedDtu OBJECT-TYPE
             SYNTAX      Counter32
             UNITS       "dtus"
             MAX-ACCESS  read-only
             STATUS      current
             DESCRIPTION
                 "Count of DTUs in the current 15-min interval that have been
                  detected in error and that have not been corrected by one or
                  more retransmissions within the maximum delay constraint."
             REFERENCE "Recommendation ITU-T G.998.4, Clause 12"
         ::= { adGenVdsl2VturChanPerfDataEntry 30 }

         adGenVdsl2VturChanPerfCurr15MinRtxCorrectedDtu OBJECT-TYPE
             SYNTAX      Counter32
             UNITS       "dtus"
             MAX-ACCESS  read-only
             STATUS      current
             DESCRIPTION
                 "Count of DTUs in the current 15-min interval that have been
                  detected in error and that have been successfully corrected
                  by a retransmission within the maximum delay constraint."
             REFERENCE "Recommendation ITU-T G.998.4, Clause 12"
         ::= { adGenVdsl2VturChanPerfDataEntry 31 }

         adGenVdsl2VturChanPerfCurr15MinRtxRetransmittedDtu OBJECT-TYPE
             SYNTAX      Counter32
             UNITS       "dtus"
             MAX-ACCESS  read-only
             STATUS      current
             DESCRIPTION
                 "Count of DTUs in the current 15-min interval that have been
                  retransmitted."
             REFERENCE "Recommendation ITU-T G.998.4, Clause 12"
         ::= { adGenVdsl2VturChanPerfDataEntry 32 }

         adGenVdsl2VturChanPerfCurr1DayRtxUncorrectedDtu OBJECT-TYPE
             SYNTAX      Counter32
             UNITS       "dtus"
             MAX-ACCESS  read-only
             STATUS      current
             DESCRIPTION
                 "Count of DTUs in the current 24-hr interval that have been
                  detected in error and that have not been corrected by one or
                  more retransmissions within the maximum delay constraint."
             REFERENCE "Recommendation ITU-T G.998.4, Clause 12"
         ::= { adGenVdsl2VturChanPerfDataEntry 33 }

         adGenVdsl2VturChanPerfCurr1DayRtxCorrectedDtu OBJECT-TYPE
             SYNTAX      Counter32
             UNITS       "dtus"
             MAX-ACCESS  read-only
             STATUS      current
             DESCRIPTION
                 "Count of DTUs in the current 24-hr interval that have been
                  detected in error and that have been successfully corrected
                  by a retransmission within the maximum delay constraint."
             REFERENCE "Recommendation ITU-T G.998.4, Clause 12"
         ::= { adGenVdsl2VturChanPerfDataEntry 34 }

         adGenVdsl2VturChanPerfCurr1DayRtxRetransmittedDtu OBJECT-TYPE
             SYNTAX      Counter32
             UNITS       "dtus"
             MAX-ACCESS  read-only
             STATUS      current
             DESCRIPTION
                 "Count of DTUs in the current 24-hr interval that have been
                  retransmitted."
             REFERENCE "Recommendation ITU-T G.998.4, Clause 12"
         ::= { adGenVdsl2VturChanPerfDataEntry 35 }


         -- ========= PM Group (adGenVdsl2VtucChanIntervalTable) =============
         adGenVdsl2VtucChanIntervalTable   OBJECT-TYPE
             SYNTAX          SEQUENCE OF AdGenVdsl2VtucChanIntervalEntry
             MAX-ACCESS      not-accessible
             STATUS          current
             DESCRIPTION
                 "This table provides one row for each Vtuc channel's
                 performance data collection interval.
                 VDSL2 channel interfaces are those ifEntries
                 where ifType is equal to Interleave(124)
                 or Fast(125)."
         ::= { adGenVdsl2PM 7 }

         adGenVdsl2VtucChanIntervalEntry   OBJECT-TYPE
             SYNTAX          AdGenVdsl2VtucChanIntervalEntry
             MAX-ACCESS      not-accessible
             STATUS          current
             DESCRIPTION     "An entry in the adGenVdsl2VtucIntervalTable."
             INDEX           { ifIndex, adGenVdsl2VtucChanNum ,adGenVdsl2VtucChanIntervalNumber }
         ::= { adGenVdsl2VtucChanIntervalTable 1 }

         AdGenVdsl2VtucChanIntervalEntry ::=
             SEQUENCE {
                 adGenVdsl2VtucChanNum                          Integer32,
                 adGenVdsl2VtucChanIntervalNumber               Integer32,
                 adGenVdsl2VtucChanIntervalReceivedBlks         Counter32,
                 adGenVdsl2VtucChanIntervalTransmittedBlks      Counter32,
                 adGenVdsl2VtucChanIntervalCorrectedBlks        Counter32,
                 adGenVdsl2VtucChanIntervalUncorrectBlks        Counter32,
                 adGenVdsl2VtucChanIntervalValidData            INTEGER,
                 adGenVdsl2VtucChanIntervalRtxUncorrectedDtu    Counter32,
                 adGenVdsl2VtucChanIntervalRtxCorrectedDtu      Counter32,
                 adGenVdsl2VtucChanIntervalRtxRetransmittedDtu  Counter32
             }


         adGenVdsl2VtucChanNum OBJECT-TYPE
             SYNTAX      Integer32(1..4)
             MAX-ACCESS  read-only
             STATUS      current
             DESCRIPTION
                 "VDSL2 logical channel. Channel values are 1 - 4."
         ::= { adGenVdsl2VtucChanIntervalEntry 1 }

         adGenVdsl2VtucChanIntervalNumber OBJECT-TYPE
             SYNTAX      Integer32(1..96)
             MAX-ACCESS  read-only
             STATUS      current
             DESCRIPTION
                 "Performance Data Interval number 1 is the
                 the most recent previous interval; interval
                 96 is 24 hours ago.  Intervals 2..96 are
                 optional."
         ::= { adGenVdsl2VtucChanIntervalEntry 2 }

         adGenVdsl2VtucChanIntervalReceivedBlks OBJECT-TYPE
             SYNTAX      Counter32
             MAX-ACCESS  read-only
             STATUS      current
             DESCRIPTION
                 "Count of all encoded blocks received on this channel
                 during this interval."
         ::= { adGenVdsl2VtucChanIntervalEntry 3 }

         adGenVdsl2VtucChanIntervalTransmittedBlks  OBJECT-TYPE
             SYNTAX      Counter32
             MAX-ACCESS  read-only
             STATUS      current
             DESCRIPTION
                 "Count of all encoded blocks transmitted on this
                 channel during this interval."
         ::= { adGenVdsl2VtucChanIntervalEntry 4 }

         adGenVdsl2VtucChanIntervalCorrectedBlks  OBJECT-TYPE
             SYNTAX      Counter32
             MAX-ACCESS  read-only
             STATUS      current
             DESCRIPTION
                 "Count of all blocks received with errors that were
                 corrected on this channel during this interval."
         ::= { adGenVdsl2VtucChanIntervalEntry 5 }

         adGenVdsl2VtucChanIntervalUncorrectBlks  OBJECT-TYPE
             SYNTAX      Counter32
             MAX-ACCESS  read-only
             STATUS      current
             DESCRIPTION
                 "Count of all blocks received with uncorrectable
                 errors on this channel during this interval."
         ::= { adGenVdsl2VtucChanIntervalEntry 6 }

         adGenVdsl2VtucChanIntervalValidData OBJECT-TYPE
             SYNTAX      INTEGER {
                 valid (1),
                 notValid (2)
             }
             MAX-ACCESS read-only
             STATUS current
             DESCRIPTION
                 "This variable indicates if the data for this
                 interval is valid."
         ::= { adGenVdsl2VtucChanIntervalEntry 7 }

         adGenVdsl2VtucChanIntervalRtxUncorrectedDtu OBJECT-TYPE
             SYNTAX      Counter32
             UNITS       "dtus"
             MAX-ACCESS  read-only
             STATUS      current
             DESCRIPTION
                 "Count of DTUs in the specified 15-min interval that have been
                  detected in error and that have not been corrected by one or
                  more retransmissions within the maximum delay constraint."
             REFERENCE "Recommendation ITU-T G.998.4, Clause 12"
         ::= { adGenVdsl2VtucChanIntervalEntry 8 }

         adGenVdsl2VtucChanIntervalRtxCorrectedDtu OBJECT-TYPE
             SYNTAX      Counter32
             UNITS       "dtus"
             MAX-ACCESS  read-only
             STATUS      current
             DESCRIPTION
                 "Count of DTUs in the specified 15-min interval that have been
                  detected in error and that have been successfully corrected
                  by a retransmission within the maximum delay constraint."
             REFERENCE "Recommendation ITU-T G.998.4, Clause 12"
         ::= { adGenVdsl2VtucChanIntervalEntry 9 }

         adGenVdsl2VtucChanIntervalRtxRetransmittedDtu OBJECT-TYPE
             SYNTAX      Counter32
             UNITS       "dtus"
             MAX-ACCESS  read-only
             STATUS      current
             DESCRIPTION
                 "Count of DTUs in the specified 15-min interval that have been
                  retransmitted."
             REFERENCE "Recommendation ITU-T G.998.4, Clause 12"
         ::= { adGenVdsl2VtucChanIntervalEntry 10 }


         -- ========= PM Group (adGenVdsl2VtucChanIntervalTable) =============
         adGenVdsl2VturChanIntervalTable   OBJECT-TYPE
             SYNTAX          SEQUENCE OF AdGenVdsl2VturChanIntervalEntry
             MAX-ACCESS      not-accessible
             STATUS          current
             DESCRIPTION
                 "This table provides one row for each Vtur channel's
                 performance data collection interval.
                 VDSL2 channel interfaces are those ifEntries
                 where ifType is equal to Interleave(124)
                 or Fast(125)."
         ::= { adGenVdsl2PM 8 }

         adGenVdsl2VturChanIntervalEntry   OBJECT-TYPE
             SYNTAX          AdGenVdsl2VturChanIntervalEntry
             MAX-ACCESS      not-accessible
             STATUS          current
             DESCRIPTION     "An entry in the adGenVdsl2VturIntervalTable."
             INDEX           { ifIndex, adGenVdsl2VturChanNum , adGenVdsl2VturChanIntervalNumber }
         ::= { adGenVdsl2VturChanIntervalTable 1 }

         AdGenVdsl2VturChanIntervalEntry ::=
             SEQUENCE {
                 adGenVdsl2VturChanNum                          Integer32,
                 adGenVdsl2VturChanIntervalNumber               Integer32,
                 adGenVdsl2VturChanIntervalReceivedBlks         Counter32,
                 adGenVdsl2VturChanIntervalTransmittedBlks      Counter32,
                 adGenVdsl2VturChanIntervalCorrectedBlks        Counter32,
                 adGenVdsl2VturChanIntervalUncorrectBlks        Counter32,
                 adGenVdsl2VturChanIntervalValidData            INTEGER,
                 adGenVdsl2VturChanIntervalRtxUncorrectedDtu    Counter32,
                 adGenVdsl2VturChanIntervalRtxCorrectedDtu      Counter32,
                 adGenVdsl2VturChanIntervalRtxRetransmittedDtu  Counter32
             }

         adGenVdsl2VturChanNum OBJECT-TYPE
             SYNTAX      Integer32(1..4)
             MAX-ACCESS  read-only
             STATUS      current
             DESCRIPTION
                 "VDSL2 logical channel. Channel values are 1 - 4."
         ::= { adGenVdsl2VturChanIntervalEntry 1 }

         adGenVdsl2VturChanIntervalNumber OBJECT-TYPE
             SYNTAX      Integer32(1..96)
             MAX-ACCESS  read-only
             STATUS      current
             DESCRIPTION
                 "Performance Data Interval number 1 is the
                 the most recent previous interval; interval
                 96 is 24 hours ago.  Intervals 2..96 are
                 optional."
         ::= { adGenVdsl2VturChanIntervalEntry 2 }

         adGenVdsl2VturChanIntervalReceivedBlks OBJECT-TYPE
             SYNTAX      Counter32
             MAX-ACCESS  read-only
             STATUS      current
             DESCRIPTION
                 "Count of all encoded blocks received on this channel
                 during this interval."
         ::= { adGenVdsl2VturChanIntervalEntry 3 }

         adGenVdsl2VturChanIntervalTransmittedBlks  OBJECT-TYPE
             SYNTAX      Counter32
             MAX-ACCESS  read-only
             STATUS      current
             DESCRIPTION
                 "Count of all encoded blocks transmitted on this
                 channel during this interval."
         ::= { adGenVdsl2VturChanIntervalEntry 4 }

         adGenVdsl2VturChanIntervalCorrectedBlks  OBJECT-TYPE
             SYNTAX      Counter32
             MAX-ACCESS  read-only
             STATUS      current
             DESCRIPTION
                 "Count of all blocks received with errors that were
                 corrected on this channel during this interval."
         ::= { adGenVdsl2VturChanIntervalEntry 5 }

         adGenVdsl2VturChanIntervalUncorrectBlks  OBJECT-TYPE
             SYNTAX      Counter32
             MAX-ACCESS  read-only
             STATUS      current
             DESCRIPTION
                 "Count of all blocks received with uncorrectable
                 errors on this channel during this interval."
         ::= { adGenVdsl2VturChanIntervalEntry 6 }

         adGenVdsl2VturChanIntervalValidData OBJECT-TYPE
             SYNTAX      INTEGER {
                 valid (1),
                 notValid (2)
             }
             MAX-ACCESS read-only
             STATUS current
             DESCRIPTION
                 "This variable indicates if the data for this
                 interval is valid."
         ::= { adGenVdsl2VturChanIntervalEntry 7 }

         adGenVdsl2VturChanIntervalRtxUncorrectedDtu OBJECT-TYPE
             SYNTAX      Counter32
             UNITS       "dtus"
             MAX-ACCESS  read-only
             STATUS      current
             DESCRIPTION
                 "Count of DTUs in the specified 15-min interval that have been
                  detected in error and that have not been corrected by one or
                  more retransmissions within the maximum delay constraint."
             REFERENCE "Recommendation ITU-T G.998.4, Clause 12"
         ::= { adGenVdsl2VturChanIntervalEntry 8 }

         adGenVdsl2VturChanIntervalRtxCorrectedDtu OBJECT-TYPE
             SYNTAX      Counter32
             UNITS       "dtus"
             MAX-ACCESS  read-only
             STATUS      current
             DESCRIPTION
                 "Count of DTUs in the specified 15-min interval that have been
                  detected in error and that have been successfully corrected
                  by a retransmission within the maximum delay constraint."
             REFERENCE "Recommendation ITU-T G.998.4, Clause 12"
         ::= { adGenVdsl2VturChanIntervalEntry 9 }

         adGenVdsl2VturChanIntervalRtxRetransmittedDtu OBJECT-TYPE
             SYNTAX      Counter32
             UNITS       "dtus"
             MAX-ACCESS  read-only
             STATUS      current
             DESCRIPTION
                 "Count of DTUs in the specified 15-min interval that have been
                  retransmitted."
             REFERENCE "Recommendation ITU-T G.998.4, Clause 12"
         ::= { adGenVdsl2VturChanIntervalEntry 10 }


         -- ========= PM Group (adGenVdsl2Vtuc1DayIntervalTable) =================
         adGenVdsl2Vtuc1DayIntervalTable   OBJECT-TYPE
             SYNTAX          SEQUENCE OF AdGenVdsl2Vtuc1DayIntervalEntry
             MAX-ACCESS      not-accessible
             STATUS          current
             DESCRIPTION
                 "This table provides one row for each Vtuc
                 performance data collection 1 day interval.
                 VDSL2 physical interfaces are
                 those ifEntries where ifType is equal to vdsl(97)."
         ::= { adGenVdsl2PM 9 }

         adGenVdsl2Vtuc1DayIntervalEntry   OBJECT-TYPE
             SYNTAX          AdGenVdsl2Vtuc1DayIntervalEntry
             MAX-ACCESS      not-accessible
             STATUS          current
             DESCRIPTION     "An entry in the adGenVdsl2Vtuc1DayIntervalTable."
             INDEX           { ifIndex, adGenVdsl2Vtuc1DayIntervalNumber }
         ::= { adGenVdsl2Vtuc1DayIntervalTable 1 }

         AdGenVdsl2Vtuc1DayIntervalEntry ::=
             SEQUENCE {
                 adGenVdsl2Vtuc1DayIntervalNumber         Integer32,
                 adGenVdsl2Vtuc1DayIntervalLofs           Counter32,
                 adGenVdsl2Vtuc1DayIntervalLoss           Counter32,
                 adGenVdsl2Vtuc1DayIntervalLols           Counter32,
                 adGenVdsl2Vtuc1DayIntervalLprs           Counter32,
                 adGenVdsl2Vtuc1DayIntervalES             Counter32,
                 adGenVdsl2Vtuc1DayIntervalInits          Counter32,
                 adGenVdsl2Vtuc1DayIntervalValidData        INTEGER,
                 adGenVdsl2Vtuc1DayIntervalSES            Counter32,
                 adGenVdsl2Vtuc1DayIntervalUAS            Counter32,
                 adGenVdsl2Vtuc1DayIntervalFECs           Counter32,
                 adGenVdsl2Vtuc1DayIntervalFEC            Counter32,
                 adGenVdsl2Vtuc1DayIntervalCRC            Counter32,
                 adGenVdsl2Vtuc1DayIntervalSraDownshifts  Counter32,
                 adGenVdsl2Vtuc1DayIntervalSraUpshifts    Counter32,
                 adGenVdsl2Vtuc1DayIntervalSraRateMax       Gauge32,
                 adGenVdsl2Vtuc1DayIntervalSraRateMin       Gauge32,
                 adGenVdsl2Vtuc1DayIntervalRtxMinEftr       Gauge32,
                 adGenVdsl2Vtuc1DayIntervalRtxLeftrs      Counter32
             }

         adGenVdsl2Vtuc1DayIntervalNumber OBJECT-TYPE
             SYNTAX      Integer32(1..7)
             MAX-ACCESS  read-only
             STATUS      current
             DESCRIPTION
                 "Performance Data Interval number 1 is the
                 the most recent previous 1 day interval;
                 interval 7 is 7 Days ago.  Intervals 1..7 are
                 optional."
         ::= { adGenVdsl2Vtuc1DayIntervalEntry 1 }

         adGenVdsl2Vtuc1DayIntervalLofs OBJECT-TYPE
             SYNTAX      Counter32
             UNITS       "seconds"
             MAX-ACCESS  read-only
             STATUS      current
             DESCRIPTION
                 "Count of seconds in the interval when there was Loss
                 of Framing."
         ::= { adGenVdsl2Vtuc1DayIntervalEntry 2 }

         adGenVdsl2Vtuc1DayIntervalLoss  OBJECT-TYPE
             SYNTAX      Counter32
             UNITS       "seconds"
             MAX-ACCESS  read-only
             STATUS      current
             DESCRIPTION
                 "Count of seconds in the 1 Day interval when there was Loss
                  of Signal."
         ::= { adGenVdsl2Vtuc1DayIntervalEntry 3 }

         adGenVdsl2Vtuc1DayIntervalLols  OBJECT-TYPE
             SYNTAX      Counter32
             UNITS       "seconds"
             MAX-ACCESS  read-only
             STATUS      current
             DESCRIPTION
                 "Count of seconds in the 1 Day interval when there was
                  Loss of Link."
         ::= { adGenVdsl2Vtuc1DayIntervalEntry 4 }

         adGenVdsl2Vtuc1DayIntervalLprs  OBJECT-TYPE
             SYNTAX      Counter32
             UNITS       "seconds"
             MAX-ACCESS  read-only
             STATUS      current
             DESCRIPTION
                 "Count of seconds in the 1 Day interval when there was Loss
                  of Power."
         ::= { adGenVdsl2Vtuc1DayIntervalEntry 5 }

         adGenVdsl2Vtuc1DayIntervalES OBJECT-TYPE
             SYNTAX      Counter32
             UNITS       "seconds"
             MAX-ACCESS  read-only
             STATUS      current
             DESCRIPTION
                 "Count of Errored Seconds in the interval."
         ::= { adGenVdsl2Vtuc1DayIntervalEntry 6 }

         adGenVdsl2Vtuc1DayIntervalInits  OBJECT-TYPE
             SYNTAX      Counter32
             MAX-ACCESS  read-only
             STATUS      current
             DESCRIPTION
                 "Count of the line initialization attempts
                 during the 1 Day interval. Includes both successful
                 and failed attempts."
         ::= { adGenVdsl2Vtuc1DayIntervalEntry 7 }


         adGenVdsl2Vtuc1DayIntervalValidData OBJECT-TYPE
             SYNTAX      INTEGER {
                 valid (1),            -- no channels exist
                 notValid (2)          -- fast channel exists only
             }
             MAX-ACCESS read-only
             STATUS current
             DESCRIPTION
                 "This variable indicates if the data for this 1 Day
                 interval is valid."
         ::= { adGenVdsl2Vtuc1DayIntervalEntry 8 }

         adGenVdsl2Vtuc1DayIntervalSES OBJECT-TYPE
             SYNTAX      Counter32
             UNITS       "seconds"
             MAX-ACCESS  read-only
             STATUS      current
             DESCRIPTION
                 "Count of Severely Errored Seconds in the 1 Day interval."
         ::= { adGenVdsl2Vtuc1DayIntervalEntry 9 }

         adGenVdsl2Vtuc1DayIntervalUAS OBJECT-TYPE
             SYNTAX      Counter32
             UNITS       "seconds"
             MAX-ACCESS  read-only
             STATUS      current
             DESCRIPTION
                 "Count of Unavailable Seconds in the 1 Day interval."
         ::= { adGenVdsl2Vtuc1DayIntervalEntry 10 }

         adGenVdsl2Vtuc1DayIntervalFECs OBJECT-TYPE
             SYNTAX      Counter32
             UNITS       "seconds"
             MAX-ACCESS  read-only
             STATUS      current
             DESCRIPTION
                 "Count of seconds in the interval during which at
                 least one forward error correction event took
                 place."
         ::= { adGenVdsl2Vtuc1DayIntervalEntry 11 }

         adGenVdsl2Vtuc1DayIntervalFEC OBJECT-TYPE
             SYNTAX      Counter32
             UNITS       "seconds"
             MAX-ACCESS  read-only
             STATUS      current
             DESCRIPTION
                 "Count of forward error correction events that
                 took place in the 1 Day interval."
         ::= { adGenVdsl2Vtuc1DayIntervalEntry 12 }

         adGenVdsl2Vtuc1DayIntervalCRC OBJECT-TYPE
             SYNTAX      Counter32
             UNITS       "seconds"
             MAX-ACCESS  read-only
             STATUS      current
             DESCRIPTION
                 "Count of CRC anomolies that took place in the 1 Day interval."
         ::= { adGenVdsl2Vtuc1DayIntervalEntry 13 }

         adGenVdsl2Vtuc1DayIntervalSraDownshifts OBJECT-TYPE
             SYNTAX      Counter32
             UNITS       "downshifts"
             MAX-ACCESS  read-only
             STATUS      current
             DESCRIPTION
                 "Count of SRA payload rate downshifts since last
                 successful train in the specified 24-hr interval"
         ::= { adGenVdsl2Vtuc1DayIntervalEntry 14 }

         adGenVdsl2Vtuc1DayIntervalSraUpshifts OBJECT-TYPE
             SYNTAX      Counter32
             UNITS       "upshifts"
             MAX-ACCESS  read-only
             STATUS      current
             DESCRIPTION
                 "Count of SRA payload rate upshifts since last
                 successful train in the specified 24-hr interval"
         ::= { adGenVdsl2Vtuc1DayIntervalEntry 15 }

         adGenVdsl2Vtuc1DayIntervalSraRateMax OBJECT-TYPE
             SYNTAX      Gauge32
             UNITS       "bps"
             MAX-ACCESS  read-only
             STATUS      current
             DESCRIPTION
                 "Max payload rate in the specified 24-hr interval
                 since last successful train."
         ::= { adGenVdsl2Vtuc1DayIntervalEntry 16 }

         adGenVdsl2Vtuc1DayIntervalSraRateMin OBJECT-TYPE
             SYNTAX      Gauge32
             UNITS       "bps"
             MAX-ACCESS  read-only
             STATUS      current
             DESCRIPTION
                 "Min payload rate in the specified 24-hr interval
                 since last successful train."
         ::= { adGenVdsl2Vtuc1DayIntervalEntry 17 }

         adGenVdsl2Vtuc1DayIntervalRtxMinEftr OBJECT-TYPE
             SYNTAX      Gauge32
             UNITS       "bps"
             MAX-ACCESS  read-only
             STATUS      current
             DESCRIPTION
                 "Retransmission parameter defined as the minimum of
                  the error-free throughput rate observed in the specified
                  24-hr interval."
             REFERENCE "Recommendation ITU-T G.998.4, Clause 11.4.3"
         ::= { adGenVdsl2Vtuc1DayIntervalEntry 18 }

         adGenVdsl2Vtuc1DayIntervalRtxLeftrs OBJECT-TYPE
             SYNTAX      Counter32
             UNITS       "seconds"
             MAX-ACCESS  read-only
             STATUS      current
             DESCRIPTION
                 "Count of low error-free throughput rate defect
                  seconds in the specified 24-hr interval."
             REFERENCE "Recommendation ITU-T G.998.4, Clause 11.4.1"
         ::= { adGenVdsl2Vtuc1DayIntervalEntry 19 }


         -- ========= PM Group (adGenVdsl2Vtur1DayIntervalTable) =================
         adGenVdsl2Vtur1DayIntervalTable   OBJECT-TYPE
             SYNTAX          SEQUENCE OF AdGenVdsl2Vtur1DayIntervalEntry
             MAX-ACCESS      not-accessible
             STATUS          current
             DESCRIPTION
                 "This table provides one row for each Vtur
                 performance data collection 1 Day interval.
                 VDSL2 physical interfaces are those
                 ifEntries where ifType is equal to vdsl(97)."
         ::= { adGenVdsl2PM 10 }

         adGenVdsl2Vtur1DayIntervalEntry   OBJECT-TYPE
             SYNTAX          AdGenVdsl2Vtur1DayIntervalEntry
             MAX-ACCESS      not-accessible
             STATUS          current
             DESCRIPTION     "An entry in the adGenVdsl2Vtur1DayIntervalTable."
             INDEX           { ifIndex, adGenVdsl2Vtur1DayIntervalNumber }
         ::= { adGenVdsl2Vtur1DayIntervalTable 1 }

         AdGenVdsl2Vtur1DayIntervalEntry ::=
             SEQUENCE {
                 adGenVdsl2Vtur1DayIntervalNumber         Integer32,
                 adGenVdsl2Vtur1DayIntervalLofs           Counter32,
                 adGenVdsl2Vtur1DayIntervalLoss           Counter32,
                 adGenVdsl2Vtur1DayIntervalLprs           Counter32,
                 adGenVdsl2Vtur1DayIntervalES             Counter32,
                 adGenVdsl2Vtur1DayIntervalValidData        INTEGER,
                 adGenVdsl2Vtur1DayIntervalSES            Counter32,
                 adGenVdsl2Vtur1DayIntervalUAS            Counter32,
                 adGenVdsl2Vtur1DayIntervalFECs           Counter32,
                 adGenVdsl2Vtur1DayIntervalFEC            Counter32,
                 adGenVdsl2Vtur1DayIntervalCRC            Counter32,
                 adGenVdsl2Vtur1DayIntervalSraDownshifts  Counter32,
                 adGenVdsl2Vtur1DayIntervalSraUpshifts    Counter32,
                 adGenVdsl2Vtur1DayIntervalSraRateMax       Gauge32,
                 adGenVdsl2Vtur1DayIntervalSraRateMin       Gauge32,
                 adGenVdsl2Vtur1DayIntervalRtxMinEftr       Gauge32,
                 adGenVdsl2Vtur1DayIntervalRtxLeftrs      Counter32
             }

         adGenVdsl2Vtur1DayIntervalNumber OBJECT-TYPE
             SYNTAX      Integer32(1..7)
             MAX-ACCESS  read-only
             STATUS      current
             DESCRIPTION
                 "Performance Data Interval number 1 is the
                 the most recent previous 1 day interval;
                 interval 7 is 7 Days ago.  Intervals 1..7 are
                 optional."
         ::= { adGenVdsl2Vtur1DayIntervalEntry 1 }

         adGenVdsl2Vtur1DayIntervalLofs OBJECT-TYPE
             SYNTAX      Counter32
             UNITS       "seconds"
             MAX-ACCESS  read-only
             STATUS      current
             DESCRIPTION
                 "Count of seconds in the 1 Day interval when there was
                 Loss of Framing."
         ::= { adGenVdsl2Vtur1DayIntervalEntry 2 }

         adGenVdsl2Vtur1DayIntervalLoss  OBJECT-TYPE
             SYNTAX      Counter32
             UNITS       "seconds"
             MAX-ACCESS  read-only
             STATUS      current
             DESCRIPTION
                 "Count of seconds in the 1 Day interval when there was
                 Loss of Signal."
         ::= { adGenVdsl2Vtur1DayIntervalEntry 3 }

         adGenVdsl2Vtur1DayIntervalLprs  OBJECT-TYPE
             SYNTAX      Counter32
             UNITS       "seconds"
             MAX-ACCESS  read-only
             STATUS      current
             DESCRIPTION
                 "Count of seconds in the 1 Day interval when there was
                 Loss of Power."
         ::= { adGenVdsl2Vtur1DayIntervalEntry 4 }

         adGenVdsl2Vtur1DayIntervalES OBJECT-TYPE
             SYNTAX      Counter32
             UNITS       "seconds"
             MAX-ACCESS  read-only
             STATUS      current
             DESCRIPTION
                 "Count of Errored Seconds in the 1 Day interval."
         ::= { adGenVdsl2Vtur1DayIntervalEntry 5 }

         adGenVdsl2Vtur1DayIntervalValidData OBJECT-TYPE
             SYNTAX      INTEGER {
                 valid (1),
                 notValid (2)
             }
             MAX-ACCESS read-only
             STATUS current
             DESCRIPTION
                 "This variable indicates if the data for this 1 Day
                  interval is valid."
         ::= { adGenVdsl2Vtur1DayIntervalEntry 6 }

         adGenVdsl2Vtur1DayIntervalSES OBJECT-TYPE
             SYNTAX      Counter32
             UNITS       "seconds"
             MAX-ACCESS  read-only
             STATUS      current
             DESCRIPTION
                 "Count of Severely Errored Seconds in the 1 Day interval."
         ::= { adGenVdsl2Vtur1DayIntervalEntry 7 }

         adGenVdsl2Vtur1DayIntervalUAS OBJECT-TYPE
             SYNTAX      Counter32
             UNITS       "seconds"
             MAX-ACCESS  read-only
             STATUS      current
             DESCRIPTION
                 "Count of Unavailable Seconds in the 1 Day interval."
         ::= { adGenVdsl2Vtur1DayIntervalEntry 8 }

         adGenVdsl2Vtur1DayIntervalFECs OBJECT-TYPE
             SYNTAX      Counter32
             UNITS       "seconds"
             MAX-ACCESS  read-only
             STATUS      current
             DESCRIPTION
                 "Count of seconds in the 1 Day interval during which at
                 least one forward error correction event took
                 place."
         ::= { adGenVdsl2Vtur1DayIntervalEntry 9 }

         adGenVdsl2Vtur1DayIntervalFEC OBJECT-TYPE
             SYNTAX      Counter32
             UNITS       "seconds"
             MAX-ACCESS  read-only
             STATUS      current
             DESCRIPTION
                 "Count of forward error correction events that
                 took place in the 1 Day interval."
         ::= { adGenVdsl2Vtur1DayIntervalEntry 10 }

         adGenVdsl2Vtur1DayIntervalCRC OBJECT-TYPE
             SYNTAX      Counter32
             UNITS       "seconds"
             MAX-ACCESS  read-only
             STATUS      current
             DESCRIPTION
                 "Count of CRC anomolies that took place in
                  the 1 Day interval."
         ::= { adGenVdsl2Vtur1DayIntervalEntry 11 }

         adGenVdsl2Vtur1DayIntervalSraDownshifts OBJECT-TYPE
             SYNTAX      Counter32
             UNITS       "downshifts"
             MAX-ACCESS  read-only
             STATUS      current
             DESCRIPTION
                 "Count of SRA payload rate downshifts since last
                 successful train in the specified 24-hr interval"
         ::= { adGenVdsl2Vtur1DayIntervalEntry 12 }

         adGenVdsl2Vtur1DayIntervalSraUpshifts OBJECT-TYPE
             SYNTAX      Counter32
             UNITS       "upshifts"
             MAX-ACCESS  read-only
             STATUS      current
             DESCRIPTION
                 "Count of SRA payload rate upshifts since last
                 successful train in the specified 24-hr interval"
         ::= { adGenVdsl2Vtur1DayIntervalEntry 13 }

         adGenVdsl2Vtur1DayIntervalSraRateMax OBJECT-TYPE
             SYNTAX      Gauge32
             UNITS       "bps"
             MAX-ACCESS  read-only
             STATUS      current
             DESCRIPTION
                 "Max payload rate in the specified 24-hr interval
                 since last successful train."
         ::= { adGenVdsl2Vtur1DayIntervalEntry 14 }

         adGenVdsl2Vtur1DayIntervalSraRateMin OBJECT-TYPE
             SYNTAX      Gauge32
             UNITS       "bps"
             MAX-ACCESS  read-only
             STATUS      current
             DESCRIPTION
                 "Min payload rate in the specified 24-hr interval
                 since last successful train."
         ::= { adGenVdsl2Vtur1DayIntervalEntry 15 }

         adGenVdsl2Vtur1DayIntervalRtxMinEftr OBJECT-TYPE
             SYNTAX      Gauge32
             UNITS       "bps"
             MAX-ACCESS  read-only
             STATUS      current
             DESCRIPTION
                 "Retransmission parameter defined as the minimum of
                  the error-free throughput rate observed in the specified
                  24-hr interval."
             REFERENCE "Recommendation ITU-T G.998.4, Clause 11.4.3"
         ::= { adGenVdsl2Vtur1DayIntervalEntry 16 }

         adGenVdsl2Vtur1DayIntervalRtxLeftrs OBJECT-TYPE
             SYNTAX      Counter32
             UNITS       "seconds"
             MAX-ACCESS  read-only
             STATUS      current
             DESCRIPTION
                 "Count of low error-free throughput rate defect
                  seconds in the specified 24-hr interval."
             REFERENCE "Recommendation ITU-T G.998.4, Clause 11.4.1"
         ::= { adGenVdsl2Vtur1DayIntervalEntry 17 }

         -- ========= PM Group (adGenVdsl2VtucChanIntervalTable) =============
         adGenVdsl2VtucChan1DayIntervalTable   OBJECT-TYPE
             SYNTAX          SEQUENCE OF AdGenVdsl2VtucChan1DayIntervalEntry
             MAX-ACCESS      not-accessible
             STATUS          current
             DESCRIPTION
                 "This table provides one row for each Vtuc channel's
                 performance data daily collection intervals.
                 VDSL2 channel interfaces are those ifEntries
                 where ifType is equal to Interleave(124)
                 or Fast(125)."
         ::= { adGenVdsl2PM 11 }

         adGenVdsl2VtucChan1DayIntervalEntry   OBJECT-TYPE
             SYNTAX          AdGenVdsl2VtucChan1DayIntervalEntry
             MAX-ACCESS      not-accessible
             STATUS          current
             DESCRIPTION     "An entry in the adGenVdsl2Vtuc1DayIntervalTable."
             INDEX           { ifIndex, adGenVdsl2Vtuc1DayChanNum ,adGenVdsl2VtucChan1DayIntervalNumber }
         ::= { adGenVdsl2VtucChan1DayIntervalTable 1 }

         AdGenVdsl2VtucChan1DayIntervalEntry ::=
             SEQUENCE {
                 adGenVdsl2Vtuc1DayChanNum                          Integer32,
                 adGenVdsl2VtucChan1DayIntervalNumber               Integer32,
                 adGenVdsl2VtucChan1DayIntervalReceivedBlks         Counter32,
                 adGenVdsl2VtucChan1DayIntervalTransmittedBlks      Counter32,
                 adGenVdsl2VtucChan1DayIntervalCorrectedBlks        Counter32,
                 adGenVdsl2VtucChan1DayIntervalUncorrectBlks        Counter32,
                 adGenVdsl2VtucChan1DayIntervalValidData            INTEGER,
                 adGenVdsl2VtucChan1DayIntervalRtxUncorrectedDtu    Counter32,
                 adGenVdsl2VtucChan1DayIntervalRtxCorrectedDtu      Counter32,
                 adGenVdsl2VtucChan1DayIntervalRtxRetransmittedDtu  Counter32
             }

         adGenVdsl2Vtuc1DayChanNum OBJECT-TYPE
             SYNTAX      Integer32(1..4)
             MAX-ACCESS  read-only
             STATUS      current
             DESCRIPTION
                 "VDSL2 logical channel. Channel values are 1 - 4."
         ::= { adGenVdsl2VtucChan1DayIntervalEntry 1 }

         adGenVdsl2VtucChan1DayIntervalNumber OBJECT-TYPE
             SYNTAX      Integer32(1..7)
             MAX-ACCESS  read-only
             STATUS      current
             DESCRIPTION
                 "Performance Data Interval number 1 is the
                 the most recent previous interval; interval
                 7 is 1 week ago.  Intervals 2..7 are
                 optional."
         ::= { adGenVdsl2VtucChan1DayIntervalEntry 2 }

         adGenVdsl2VtucChan1DayIntervalReceivedBlks OBJECT-TYPE
             SYNTAX      Counter32
             MAX-ACCESS  read-only
             STATUS      current
             DESCRIPTION
                 "Count of all encoded blocks received on this channel
                 during this interval."
         ::= { adGenVdsl2VtucChan1DayIntervalEntry 3 }

         adGenVdsl2VtucChan1DayIntervalTransmittedBlks  OBJECT-TYPE
             SYNTAX      Counter32
             MAX-ACCESS  read-only
             STATUS      current
             DESCRIPTION
                 "Count of all encoded blocks transmitted on this
                 channel during this interval."
         ::= { adGenVdsl2VtucChan1DayIntervalEntry 4 }

         adGenVdsl2VtucChan1DayIntervalCorrectedBlks  OBJECT-TYPE
             SYNTAX      Counter32
             MAX-ACCESS  read-only
             STATUS      current
             DESCRIPTION
                 "Count of all blocks received with errors that were
                 corrected on this channel during this interval."
         ::= { adGenVdsl2VtucChan1DayIntervalEntry 5 }

         adGenVdsl2VtucChan1DayIntervalUncorrectBlks  OBJECT-TYPE
             SYNTAX      Counter32
             MAX-ACCESS  read-only
             STATUS      current
             DESCRIPTION
                 "Count of all blocks received with uncorrectable
                 errors on this channel during this interval."
         ::= { adGenVdsl2VtucChan1DayIntervalEntry 6 }

         adGenVdsl2VtucChan1DayIntervalValidData OBJECT-TYPE
             SYNTAX      INTEGER {
                 valid (1),
                 notValid (2)
             }
             MAX-ACCESS read-only
             STATUS current
             DESCRIPTION
                 "This variable indicates if the data for this
                 interval is valid."
         ::= { adGenVdsl2VtucChan1DayIntervalEntry 7 }

         adGenVdsl2VtucChan1DayIntervalRtxUncorrectedDtu OBJECT-TYPE
             SYNTAX      Counter32
             UNITS       "dtus"
             MAX-ACCESS  read-only
             STATUS      current
             DESCRIPTION
                 "Count of DTUs in the specified 24-hr interval that have been
                  detected in error and that have not been corrected by one or
                  more retransmissions within the maximum delay constraint."
             REFERENCE "Recommendation ITU-T G.998.4, Clause 12"
         ::= { adGenVdsl2VtucChan1DayIntervalEntry 8 }

         adGenVdsl2VtucChan1DayIntervalRtxCorrectedDtu OBJECT-TYPE
             SYNTAX      Counter32
             UNITS       "dtus"
             MAX-ACCESS  read-only
             STATUS      current
             DESCRIPTION
                 "Count of DTUs in the specified 24-hr interval that have been
                  detected in error and that have been successfully corrected
                  by a retransmission within the maximum delay constraint."
             REFERENCE "Recommendation ITU-T G.998.4, Clause 12"
         ::= { adGenVdsl2VtucChan1DayIntervalEntry 9 }

         adGenVdsl2VtucChan1DayIntervalRtxRetransmittedDtu OBJECT-TYPE
             SYNTAX      Counter32
             UNITS       "dtus"
             MAX-ACCESS  read-only
             STATUS      current
             DESCRIPTION
                 "Count of DTUs in the specified 24-hr interval that have been
                  retransmitted."
             REFERENCE "Recommendation ITU-T G.998.4, Clause 12"
         ::= { adGenVdsl2VtucChan1DayIntervalEntry 10 }


         -- ========= PM Group (adGenVdsl2VtucChanIntervalTable) =============
         adGenVdsl2VturChan1DayIntervalTable   OBJECT-TYPE
             SYNTAX          SEQUENCE OF AdGenVdsl2VturChan1DayIntervalEntry
             MAX-ACCESS      not-accessible
             STATUS          current
             DESCRIPTION
                 "This table provides one row for each Vtur channel's
                 performance data daily collection interval.
                 VDSL2 channel interfaces are those ifEntries
                 where ifType is equal to Interleave(124)
                 or Fast(125)."
         ::= { adGenVdsl2PM 12 }

         adGenVdsl2VturChan1DayIntervalEntry   OBJECT-TYPE
             SYNTAX          AdGenVdsl2VturChan1DayIntervalEntry
             MAX-ACCESS      not-accessible
             STATUS          current
             DESCRIPTION     "An entry in the adGenVdsl2Vtur1DayIntervalTable."
             INDEX           { ifIndex, adGenVdsl2Vtur1DayChanNum , adGenVdsl2VturChan1DayIntervalNumber }
         ::= { adGenVdsl2VturChan1DayIntervalTable 1 }

         AdGenVdsl2VturChan1DayIntervalEntry ::=
             SEQUENCE {
                 adGenVdsl2Vtur1DayChanNum                          Integer32,
		         adGenVdsl2VturChan1DayIntervalNumber               Integer32,
                 adGenVdsl2VturChan1DayIntervalReceivedBlks         Counter32,
                 adGenVdsl2VturChan1DayIntervalTransmittedBlks      Counter32,
                 adGenVdsl2VturChan1DayIntervalCorrectedBlks        Counter32,
                 adGenVdsl2VturChan1DayIntervalUncorrectBlks        Counter32,
                 adGenVdsl2VturChan1DayIntervalValidData            INTEGER,
                 adGenVdsl2VturChan1DayIntervalRtxUncorrectedDtu    Counter32,
                 adGenVdsl2VturChan1DayIntervalRtxCorrectedDtu      Counter32,
                 adGenVdsl2VturChan1DayIntervalRtxRetransmittedDtu  Counter32
             }

         adGenVdsl2Vtur1DayChanNum OBJECT-TYPE
             SYNTAX      Integer32(1..4)
             MAX-ACCESS  read-only
             STATUS      current
             DESCRIPTION
                 "VDSL2 logical channel. Channel values are 1 - 4."
         ::= { adGenVdsl2VturChan1DayIntervalEntry 1 }

         adGenVdsl2VturChan1DayIntervalNumber OBJECT-TYPE
             SYNTAX      Integer32(1..7)
             MAX-ACCESS  read-only
             STATUS      current
             DESCRIPTION
                 "Performance Data Interval number 1 is the
                 the most recent previous interval; interval
                 7 is 1 week ago.  Intervals 2..7 are
                 optional."
         ::= { adGenVdsl2VturChan1DayIntervalEntry 2 }

         adGenVdsl2VturChan1DayIntervalReceivedBlks OBJECT-TYPE
             SYNTAX      Counter32
             MAX-ACCESS  read-only
             STATUS      current
             DESCRIPTION
                 "Count of all encoded blocks received on this channel
                 during this interval."
         ::= { adGenVdsl2VturChan1DayIntervalEntry 3 }

         adGenVdsl2VturChan1DayIntervalTransmittedBlks  OBJECT-TYPE
             SYNTAX      Counter32
             MAX-ACCESS  read-only
             STATUS      current
             DESCRIPTION
                 "Count of all encoded blocks transmitted on this
                 channel during this interval."
         ::= { adGenVdsl2VturChan1DayIntervalEntry 4 }

         adGenVdsl2VturChan1DayIntervalCorrectedBlks  OBJECT-TYPE
             SYNTAX      Counter32
             MAX-ACCESS  read-only
             STATUS      current
             DESCRIPTION
                 "Count of all blocks received with errors that were
                 corrected on this channel during this interval."
         ::= { adGenVdsl2VturChan1DayIntervalEntry 5 }

         adGenVdsl2VturChan1DayIntervalUncorrectBlks  OBJECT-TYPE
             SYNTAX      Counter32
             MAX-ACCESS  read-only
             STATUS      current
             DESCRIPTION
                 "Count of all blocks received with uncorrectable
                 errors on this channel during this interval."
         ::= { adGenVdsl2VturChan1DayIntervalEntry 6 }

         adGenVdsl2VturChan1DayIntervalValidData OBJECT-TYPE
             SYNTAX      INTEGER {
                 valid (1),
                 notValid (2)
             }
             MAX-ACCESS read-only
             STATUS current
             DESCRIPTION
                 "This variable indicates if the data for this
                 interval is valid."
         ::= { adGenVdsl2VturChan1DayIntervalEntry 7 }

         adGenVdsl2VturChan1DayIntervalRtxUncorrectedDtu OBJECT-TYPE
             SYNTAX      Counter32
             UNITS       "dtus"
             MAX-ACCESS  read-only
             STATUS      current
             DESCRIPTION
                 "Count of DTUs in the specified 24-hr interval that have been
                  detected in error and that have not been corrected by one or
                  more retransmissions within the maximum delay constraint."
             REFERENCE "Recommendation ITU-T G.998.4, Clause 12"
         ::= { adGenVdsl2VturChan1DayIntervalEntry 8 }

         adGenVdsl2VturChan1DayIntervalRtxCorrectedDtu OBJECT-TYPE
             SYNTAX      Counter32
             UNITS       "dtus"
             MAX-ACCESS  read-only
             STATUS      current
             DESCRIPTION
                 "Count of DTUs in the specified 24-hr interval that have been
                  detected in error and that have been successfully corrected
                  by a retransmission within the maximum delay constraint."
             REFERENCE "Recommendation ITU-T G.998.4, Clause 12"
         ::= { adGenVdsl2VturChan1DayIntervalEntry 9 }

         adGenVdsl2VturChan1DayIntervalRtxRetransmittedDtu OBJECT-TYPE
             SYNTAX      Counter32
             UNITS       "dtus"
             MAX-ACCESS  read-only
             STATUS      current
             DESCRIPTION
                 "Count of DTUs in the specified 24-hr interval that have been
                  retransmitted."
             REFERENCE "Recommendation ITU-T G.998.4, Clause 12"
         ::= { adGenVdsl2VturChan1DayIntervalEntry 10 }


         -- ******************************************************************
         -- Group: ExtConfig
         --   The ExtConfig Group consists of the tables of entries
         --   necessary to maintain the extended VDSL2 line configuration.
         --   These entries are items that must be tracked per ifIndex
         --   (ie port) and not based on the profiles that could possibly
         --   be dynamically assigned.
         -- ******************************************************************

         adGenVdsl2ConfProfileExtTable   OBJECT-TYPE
         SYNTAX          SEQUENCE OF AdGenVdsl2ConfProfileExtEntry
         MAX-ACCESS      not-accessible
         STATUS          current
         DESCRIPTION
            "This table contains VDSL management profile configuration
             information not defined in the adGenVdsl2LineConfProfileTable
             from the VDSL-LINE-MIB.
            "
         ::= { adGenVdsl2ExtConfig 1 }

         adGenVdsl2ConfProfileExtEntry   OBJECT-TYPE
         SYNTAX          AdGenVdsl2ConfProfileExtEntry
         MAX-ACCESS      not-accessible
         STATUS          current
         DESCRIPTION
             "An entry extends the adslLineConfProfileEntry
              defined in VDSL-LINE-MIB.  Each entry corresponds
              to an VDSL line profile."
         INDEX { ifIndex }
         ::= { adGenVdsl2ConfProfileExtTable 1 }

         AdGenVdsl2ConfProfileExtEntry ::=
         SEQUENCE {
             adGenVdsl2LineManagementProfileNameApplied  DisplayString,
             adGenVdsl2LineManagementProfileIndexApplied Unsigned32,
             adGenVdsl2LineCircuitID                     DisplayString,
             adGenVdsl2LineResetCounters                 INTEGER,
             adGenVdsl2LineRetrainRequest                INTEGER
         }

         adGenVdsl2LineManagementProfileNameApplied OBJECT-TYPE
             SYNTAX  DisplayString --(SIZE (1..32))
             MAX-ACCESS  read-write
             STATUS  current
             DESCRIPTION
                 "Management profile name applied to the VDSL Port profile."
         ::= { adGenVdsl2ConfProfileExtEntry 1 }

         adGenVdsl2LineManagementProfileIndexApplied OBJECT-TYPE
             SYNTAX             Unsigned32
             MAX-ACCESS  read-write
             STATUS  current
             DESCRIPTION
                 "Management profile name applied to the VDSL Port profile."
         ::= { adGenVdsl2ConfProfileExtEntry 2 }

         adGenVdsl2LineCircuitID OBJECT-TYPE
             SYNTAX  DisplayString --(SIZE (1..32))
             MAX-ACCESS  read-write
             STATUS  current
             DESCRIPTION
                 "Circuit ID assigned to VDSL Port."
         ::= { adGenVdsl2ConfProfileExtEntry 3 }

         adGenVdsl2LineResetCounters OBJECT-TYPE
            SYNTAX      INTEGER
            {
                 all(1),              -- Reset both PM history and current counters
                 pmhistory(2),        -- Reset PM history counters
                 current(3),          -- Reset current counters
                 retrainne(4),        -- Retrain near-end counters
                 retrainfe(5),        -- Retrain far-end counters
                 rolling(6)           -- Reset rolling counters
            }
            MAX-ACCESS  read-write
            STATUS      current
            DESCRIPTION
              "Selection of counter types to reset/clear for the indexed interface.
               The counter types are performance monitoring intervals (PM history)
               which typically consist of 15 minute/24 hour interval data,
               current counters, near-end retrain counters, far-end retrain
               counters, and rolling counters. A read will always return all(1)."
            ::= { adGenVdsl2ConfProfileExtEntry 4 }

         adGenVdsl2LineRetrainRequest OBJECT-TYPE
            SYNTAX      INTEGER
            {
                 full(1),             -- request a full retrain/init
                 fast(2)              -- request a fast retrain/init
            }
            MAX-ACCESS  read-write
            STATUS      current
            DESCRIPTION
              "Request the selected line to perform a full retrain/init or a
               fast retrain/init. A read will always return full(1)."
            ::= { adGenVdsl2ConfProfileExtEntry 5 }


   -- ============ Prov Group (Band Profile) ===========================
         adGenVdsl2BandConfProfileTable    OBJECT-TYPE
             SYNTAX          SEQUENCE OF AdGenVdsl2BandConfProfileEntry
             MAX-ACCESS      not-accessible
             STATUS          current
             DESCRIPTION
                "This table contains information on the VDSL2 Band
                 configuration.  One entry in this table reflects band
                 profile defined by a manager which can be used to
                 configure the VDSL2 bands for a given
                 adGenVdsl2LineConfProfileEntry."
         ::= { adGenVdsl2Prov 4 }

         adGenVdsl2BandConfProfileEntry    OBJECT-TYPE
             SYNTAX          AdGenVdsl2BandConfProfileEntry
             MAX-ACCESS      not-accessible
             STATUS          current
             DESCRIPTION
                "Each entry consists of a list of parameters that
                 represents the configuration of an VDSL2 modem
                 band parameters.  These entries extend that of the
                 adGenVdsl2LineConfProfileTable by band.
                "
             INDEX { adGenVdsl2LineConfProfileName, adGenVdsl2BandNumber }
         ::= { adGenVdsl2BandConfProfileTable 1}

         AdGenVdsl2BandConfProfileEntry ::=
             SEQUENCE {
                 adGenVdsl2BandNumber                        Integer32,
                 adGenVdsl2BandConfUsCustomPboCableA         Unsigned32,
                 adGenVdsl2BandConfUsCustomPboCableB         Unsigned32
             }

   adGenVdsl2BandNumber OBJECT-TYPE
       SYNTAX      Integer32 (1..4)
       MAX-ACCESS  read-only
       STATUS      current
       DESCRIPTION
           "VDSL2 band number. Band values are 1 - 5 corresponding
            to upstream bands U0..U4 and downstream bands D1..D5."
   ::= { adGenVdsl2BandConfProfileEntry 1 }

   adGenVdsl2BandConfUsCustomPboCableA OBJECT-TYPE
       SYNTAX             Unsigned32 (4000..8095)
       UNITS              "0.01 dBm/Hz"
       MAX-ACCESS         read-create
       STATUS             current
       DESCRIPTION
           "Upstream power back-off band cable A parameter.
            This parameter defines the UPBO reference PSD used
            to compute the upstream power backoff for each
            upstream band except US0. A UPBOPSD defined for each
            band shall consist of two parameters [A, B]. The UPBO
            reference PSD at the frequency f expressed in MHz shall
            be equal to -A - B*sqrt(f).  Parameter A ranges from
            40 dBm/Hz to 80.95 dBm/Hz in steps of 0.01 dBm/Hz. A special
            case of A=40.00 dBm/Hz and B=0.00 dBm/Hz disables UPBO in
            the respective band. The first entry U0 must be disabled
	    since it is not supported in the standard yet."
   ::= { adGenVdsl2BandConfProfileEntry 2 }

   adGenVdsl2BandConfUsCustomPboCableB OBJECT-TYPE
       SYNTAX             Unsigned32 (0..4095)
       UNITS              "0.01 dBm/Hz"
       MAX-ACCESS         read-create
       STATUS             current
       DESCRIPTION
           "Upstream power back-off band cable B parameter.
            This parameter defines the UPBO reference PSD used
            to compute the upstream power backoff for each
            upstream band except US0. A UPBOPSD defined for each
            band shall consist of two parameters [A, B]. The UPBO
            reference PSD at the frequency f expressed in MHz shall
            be equal to -A - B*sqrt(f).  Parameter B ranges from
            0 dBm/Hz to 40.95 dBm/Hz in steps of 0.01 dBm/Hz. A special
            case of A=40.00 dBm/Hz and B=0.00 dBm/Hz disables UPBO in
            the respective band. The first entry U0 must be disabled
	    since it is not supported in the standard yet."
   ::= { adGenVdsl2BandConfProfileEntry 3 }

   -- ============ Prov Group (Alarm Provisioning) ===========================
         adGenVdsl2AlarmSlotProvTable    OBJECT-TYPE
             SYNTAX          SEQUENCE OF AdGenVdsl2AlarmSlotProvEntry
             MAX-ACCESS      not-accessible
             STATUS          current
             DESCRIPTION
                "This table sets alarm severity for all VDSL2 interfaces."
         ::= { adGenVdsl2Prov 5 }

         adGenVdsl2AlarmSlotProvEntry    OBJECT-TYPE
             SYNTAX          AdGenVdsl2AlarmSlotProvEntry
             MAX-ACCESS      not-accessible
             STATUS          current
             DESCRIPTION
                ""
             INDEX { adGenSlotInfoIndex }
         ::= { adGenVdsl2AlarmSlotProvTable 1}

         AdGenVdsl2AlarmSlotProvEntry ::=
             SEQUENCE {
                 adGenVdsl2AlmSlotLinkdownSeverity               INTEGER
         }

         adGenVdsl2AlmSlotLinkdownSeverity OBJECT-TYPE
         SYNTAX INTEGER {
                                info(2),
                                alert(3),
                                minor(4),
                                major(5),
                                critical(6)
                        }
    	MAX-ACCESS read-write
    	STATUS current
    	DESCRIPTION
        	"Sets the Linkdown alarm severity (affects all VDSL2 Ports)"
    	DEFVAL    { major }
        ::= { adGenVdsl2AlarmSlotProvEntry 1 }

   -- ============ Status Group (Band Status) ===========================
         adGenVdsl2BandStatusTable    OBJECT-TYPE
             SYNTAX          SEQUENCE OF AdGenVdsl2BandStatusEntry
             MAX-ACCESS      not-accessible
             STATUS          current
             DESCRIPTION
                "This table contains per band status information for VDSL2
                 configuration.  One entry in this table reflects band
                 profile defined by a manager which can be used to
                 configure the VDSL2 bands for a given
                 adGenVdsl2LineConfProfileEntry."
         ::= { adGenVdsl2Status 6 }

         adGenVdsl2BandStatusEntry    OBJECT-TYPE
             SYNTAX          AdGenVdsl2BandStatusEntry
             MAX-ACCESS      not-accessible
             STATUS          current
             DESCRIPTION
                "Each entry consists of a list of band status items.
                "
             INDEX {  ifIndex, adGenVdsl2BandNumber }
         ::= { adGenVdsl2BandStatusTable 1}

         AdGenVdsl2BandStatusEntry ::=
             SEQUENCE {
                 adGenVdsl2BandStatusNumber                  Integer32,
                 adGenVdsl2BandStatusUsStartCarrier          Unsigned32,
                 adGenVdsl2BandStatusUsStopCarrier           Unsigned32,
                 adGenVdsl2BandStatusUsMargin                Integer32,
                 adGenVdsl2BandStatusUsLatn                  Integer32,
                 adGenVdsl2BandStatusUsSatn                  Integer32,

                 adGenVdsl2BandStatusDsStartCarrier          Unsigned32,
                 adGenVdsl2BandStatusDsStopCarrier           Unsigned32,
                 adGenVdsl2BandStatusDsMargin                Integer32,
                 adGenVdsl2BandStatusDsLatn                  Integer32,
                 adGenVdsl2BandStatusDsSatn                  Integer32
             }

   adGenVdsl2BandStatusNumber OBJECT-TYPE
       SYNTAX      Integer32 (1..4)
       MAX-ACCESS  read-only
       STATUS      current
       DESCRIPTION
           "VDSL2 band number. Band values are 1 - 5 corresponding
            to upstream bands U0..U4 and downstream bands D1..D5."
   ::= { adGenVdsl2BandStatusEntry 1 }


   adGenVdsl2BandStatusUsStartCarrier OBJECT-TYPE
       SYNTAX      Unsigned32 (0..8192)
       MAX-ACCESS  read-only
       STATUS      current
       DESCRIPTION
           "The starting carrier of the VDSL2 upstream band at 4.3125KHz
            spacing"
   ::= { adGenVdsl2BandStatusEntry 2 }

   adGenVdsl2BandStatusUsStopCarrier OBJECT-TYPE
       SYNTAX      Unsigned32 (0..8192)
       MAX-ACCESS  read-only
       STATUS      current
       DESCRIPTION
           "The ending carrier of the VDSL2 upstream band at 4.3125KHz
            spacing"
   ::= { adGenVdsl2BandStatusEntry 3 }

   adGenVdsl2BandStatusUsMargin OBJECT-TYPE
       SYNTAX      Integer32 (-641..630)
       UNITS       "0.1 dB"
       MAX-ACCESS  read-only
       STATUS      current
       DESCRIPTION
           "Upstream Signal-to-Noise Ratio Margin per Band. This parameter
            is defined by usable band. The upstream signal to noise ratio
            margin per band is the maximum increase in dB of the noise
            power received at the VTU-C such that the BER requirements are met
            for all bearer channels of the band. The upstream SNR margin per
            band ranges from -64.1 dB to +63.0 dB with 0.1 dB steps. A value of
            -64.1 indicates out of range.
           "
   ::= { adGenVdsl2BandStatusEntry 4 }


   adGenVdsl2BandStatusUsLatn OBJECT-TYPE
       SYNTAX      Integer32 (0..1270)
       UNITS       "0.1 dB"
       MAX-ACCESS  read-only
       STATUS      current
       DESCRIPTION
           "Upstream Line Attenuation per Band. This parameter is defined per
            usable bands. It is the measured difference in the total power
            transmitted in this band and the total power received over all
            subcarriers of this band during initialization. The upstream
            line attenuation ranges per band from 0 to +127 dB with 0.1 dB
            steps.
           "
   ::= { adGenVdsl2BandStatusEntry 5 }


   adGenVdsl2BandStatusUsSatn OBJECT-TYPE
       SYNTAX      Integer32 (0..1270)
       UNITS       "0.1 dB"
       MAX-ACCESS  read-only
       STATUS      current
       DESCRIPTION
           "Upstream Signal Attenuation per Band. This parameter is defined per
            usable bands. It is the measured difference in the total power
            transmitted in this band and the total power received over all
            subcarriers of this band during showtime. The upstream line
            attenuation ranges per band from 0 to +127 dB with 0.1 dB steps.
            During showtime, only a subset of the subcarriers may be transmitted
            as compared to initialization.  Therefore, the upstream Signal
            attenuation may be significantly lower than the downstream Line
            attenuation.
           "
   ::= { adGenVdsl2BandStatusEntry 6 }

   adGenVdsl2BandStatusDsStartCarrier OBJECT-TYPE
       SYNTAX      Unsigned32 (0..8192)
       MAX-ACCESS  read-only
       STATUS      current
       DESCRIPTION
           "The starting carrier of the VDSL2 downstream band at 4.3125KHz
            spacing"
   ::= { adGenVdsl2BandStatusEntry 7 }

   adGenVdsl2BandStatusDsStopCarrier OBJECT-TYPE
       SYNTAX      Unsigned32 (0..8192)
       MAX-ACCESS  read-only
       STATUS      current
       DESCRIPTION
           "The ending carrier of the VDSL2 downstream band at 4.3125KHz
            spacing"
   ::= { adGenVdsl2BandStatusEntry 8 }

   adGenVdsl2BandStatusDsMargin OBJECT-TYPE
       SYNTAX      Integer32 (-641..630)
       UNITS       "0.1 dB"
       MAX-ACCESS  read-only
       STATUS      current
       DESCRIPTION
           "Downstream Signal-to-Noise Ratio Margin per Band. This parameter
            is defined by usable band. The downstream signal to noise ratio
            margin per band is the maximum increase in dB of the noise
            power received at the VTU-R such that the BER requirements are met
            for all bearer channels of the band. The downstream SNR margin per
            band ranges from -64.1 dB to +63.0 dB with 0.1 dB steps. A value of
            -64.1 indicates out of range.
           "
   ::= { adGenVdsl2BandStatusEntry 9 }


   adGenVdsl2BandStatusDsLatn OBJECT-TYPE
       SYNTAX      Integer32 (0..1270)
       UNITS       "0.1 dB"
       MAX-ACCESS  read-only
       STATUS      current
       DESCRIPTION
           "Downstream Line Attenuation per Band. This parameter is defined per
            usable bands. It is the measured difference in the total power
            transmitted in this band and the total power received over all
            subcarriers of this band during initialization. The downstream
            line attenuation ranges per band from 0 to +127 dB with 0.1 dB
            steps.
           "
   ::= { adGenVdsl2BandStatusEntry 10 }


   adGenVdsl2BandStatusDsSatn OBJECT-TYPE
       SYNTAX      Integer32 (0..1270)
       UNITS       "0.1 dB"
       MAX-ACCESS  read-only
       STATUS      current
       DESCRIPTION
           "Downstream Signal Attenuation per Band. This parameter is defined per
            usable bands. It is the measured difference in the total power
            transmitted in this band and the total power received over all
            subcarriers of this band during showtime. The downstream line
            attenuation ranges per band from 0 to +127 dB with 0.1 dB steps.
            During showtime, only a subset of the subcarriers may be transmitted
            as compared to initialization.  Therefore, the downstream Signal
            attenuation may be significantly lower than the downstream Line
            attenuation.
           "
   ::= { adGenVdsl2BandStatusEntry 11 }


   -- ============ Status Group (Sub-Carrier Status) ========================
         adGenVdsl2ScStatusTable    OBJECT-TYPE
             SYNTAX          SEQUENCE OF AdGenVdsl2ScStatusEntry
             MAX-ACCESS      not-accessible
             STATUS          current
             DESCRIPTION
                "This table contains per band status information for VDSL2
                 configuration.  One entry in this table reflects band
                 profile defined by a manager which can be used to
                 configure the VDSL2 bands for a given
                 adGenVdsl2LineConfProfileEntry."
         ::= { adGenVdsl2Status 7 }

         adGenVdsl2ScStatusEntry    OBJECT-TYPE
             SYNTAX          AdGenVdsl2ScStatusEntry
             MAX-ACCESS      not-accessible
             STATUS          current
             DESCRIPTION
                "Each entry consists of a list of band status items.
                "
             INDEX {  ifIndex, adGenVdsl2ScStatusNumber }
         ::= { adGenVdsl2ScStatusTable 1}

         AdGenVdsl2ScStatusEntry ::=
             SEQUENCE {
                 adGenVdsl2ScStatusNumber                  Integer32,

                 adGenVdsl2ScStatusUsBits                  Integer32,
                 adGenVdsl2ScStatusUsGain                  Integer32,
                 adGenVdsl2ScStatusUsSnr                   Integer32,

                 adGenVdsl2ScStatusDsBits                  Integer32,
                 adGenVdsl2ScStatusDsGain                  Integer32,
                 adGenVdsl2ScStatusDsSnr                   Integer32,

                 adGenVdsl2ScStatusUsQln                   Integer32,
                 adGenVdsl2ScStatusDsQln                   Integer32,
                 adGenVdsl2ScStatusUsHlog                  Integer32,
                 adGenVdsl2ScStatusDsHlog                  Integer32
             }

   adGenVdsl2ScStatusNumber OBJECT-TYPE
       SYNTAX      Integer32 (1..8192)
       MAX-ACCESS  read-only
       STATUS      current
       DESCRIPTION
           "DMT subcarrier number. There are 4096 possible DMT sub-carriers
            spaced by 4.3125 KHz in the upstream and downstream directions.
            These carriers are typically broken up into non-overlapping
            groups called bands. For this reason, not all carriers will be
            used in each direction.
           "
   ::= { adGenVdsl2ScStatusEntry 1 }

   adGenVdsl2ScStatusUsBits OBJECT-TYPE
       SYNTAX      Integer32 (0..15)
       MAX-ACCESS  read-only
       STATUS      current
       DESCRIPTION
           "Bits allocated per subcarrier in the upstream direction.
            Value ranges from 0 to 15.  A zero value indicates
            that no bits are allocated the upstream subcarrier.
           "
   ::= { adGenVdsl2ScStatusEntry 2 }

   adGenVdsl2ScStatusUsGain OBJECT-TYPE
       SYNTAX      Integer32 (0..4095)
       MAX-ACCESS  read-only
       STATUS      current
       DESCRIPTION
           "Upstream gains allocation per subcarrier. It is an array of integer
            values in the range of 0 to 4095 for each subcarrier.
            The gain value is represented as a multiple of 1/512 on
            linear scale.  The value of zero indicates carrier is not used.
            Min. value: 20*log(1/512) = -54.2 dB
            Max. value: 20*log(4095/512) = 18.0 dB
           "
   ::= { adGenVdsl2ScStatusEntry 3 }

   adGenVdsl2ScStatusUsSnr OBJECT-TYPE
       SYNTAX      Integer32 (0..955)
       UNITS       "0.1 dB"
       MAX-ACCESS  read-only
       STATUS      current
       DESCRIPTION
           "Upstream signal to noise (SNR) per sub-carrier number. The SNR
            ranges from 0 to +95.0 dB with 0.1 dB steps. A special value of
            955 indicates that no measurement could be done for the
            subcarrier because it is out of the passband or that the noise
            PSD is out of range to be represented.
           "
   ::= { adGenVdsl2ScStatusEntry 4 }

   adGenVdsl2ScStatusDsBits OBJECT-TYPE
       SYNTAX      Integer32 (0..15)
       MAX-ACCESS  read-only
       STATUS      current
       DESCRIPTION
           "Bits allocated per subcarrier in the downstream direction.
            Value ranges from 0 to 15.  A zero value indicates
            that no bits are allocated the downstream subcarrier.
           "
   ::= { adGenVdsl2ScStatusEntry 5 }

   adGenVdsl2ScStatusDsGain OBJECT-TYPE
       SYNTAX      Integer32 (0..4095)
       MAX-ACCESS  read-only
       STATUS      current
       DESCRIPTION
           "Downstream gains allocation per subcarrier. It is an array of
            integer values in the range of 0 to 4095 for each subcarrier.
            The gain value is represented as a multiple of 1/512 on
            linear scale.  The value of zero indicates carrier is not used.
            Min. value: 20*log(1/512) = -54.2 dB
            Max. value: 20*log(4095/512) = 18.0 dB
           "
   ::= { adGenVdsl2ScStatusEntry 6 }

   adGenVdsl2ScStatusDsSnr OBJECT-TYPE
       SYNTAX      Integer32 (0..955)
       UNITS       "0.1 dB"
       MAX-ACCESS  read-only
       STATUS      current
       DESCRIPTION
           "Downstream signal to noise (SNR) per sub-carrier number. The SNR
            ranges from 0 to +95.0 dB with 0.1 dB steps. A special value of
            955 indicates that no measurement could be done for the
            subcarrier because it is out of the passband or that the noise
            PSD is out of range to be represented.
           "
   ::= { adGenVdsl2ScStatusEntry 7 }


   adGenVdsl2ScStatusUsQln OBJECT-TYPE
       SYNTAX      Integer32 (-1505..-230)
       UNITS       "0.1 dBm/Hz"
       MAX-ACCESS  read-only
       STATUS      current
       DESCRIPTION
           "Upstream quiet line noise (QLN) per sub-carrier number. The QLN
            ranges from -150.5 to -23.0 dBm/Hz with 0.1 dB steps. A special
            value of -1505 indicates that no measurement could be done for the
            subcarrier because it is out of the passband or that the noise
            PSD is out of range to be represented."
   ::= { adGenVdsl2ScStatusEntry 8 }

   adGenVdsl2ScStatusDsQln OBJECT-TYPE
       SYNTAX      Integer32 (-1505..-230)
       UNITS       "0.1 dBm/Hz"
       MAX-ACCESS  read-only
       STATUS      current
       DESCRIPTION
           "Upstream quiet line noise (QLN) per sub-carrier number. The QLN
            ranges from -150.5 to -23.0 dBm/Hz with 0.1 dB steps. A special
            value of -1505 indicates that no measurement could be done for the
            subcarrier because it is out of the passband or that the noise
            PSD is out of range to be represented."
   ::= { adGenVdsl2ScStatusEntry 9 }

   adGenVdsl2ScStatusUsHlog OBJECT-TYPE
       SYNTAX      Integer32 (-963..60)
       UNITS       "0.1 dB"
       MAX-ACCESS  read-only
       STATUS      current
       DESCRIPTION
           "Upstream channel transfer function (HLOG) per sub-carrier number. The HLOG
            ranges from -96.3 to +6.0 dB with 0.1 dB steps. A special value of
            -963 indicates that no measurement could be done for the
            subcarrier because it is out of the passband or that the noise
            PSD is out of range to be represented."
   ::= { adGenVdsl2ScStatusEntry 10 }

   adGenVdsl2ScStatusDsHlog OBJECT-TYPE
       SYNTAX      Integer32 (-963..60)
       UNITS       "0.1 dB"
       MAX-ACCESS  read-only
       STATUS      current
       DESCRIPTION
           "Downstream channel transfer function (HLOG) per sub-carrier number. The HLOG
            ranges from -96.3 to +6.0 dB with 0.1 dB steps. A special value of
            -963 indicates that no measurement could be done for the
            subcarrier because it is out of the passband or that the noise
            PSD is out of range to be represented."
   ::= { adGenVdsl2ScStatusEntry 11 }

--==================================================================================================================
-- Bulk VDSL Tlv reserve instance
--==================================================================================================================

    adGenVdsl2ReserveInstanceBulkVDSLTlvTable
     OBJECT-TYPE
       SYNTAX      SEQUENCE OF AdGenVdsl2ReserveInstanceBulkVDSLTlvEntry
       MAX-ACCESS  not-accessible
       STATUS      current
       DESCRIPTION
           "Table contains instances that are created when there is a request to reserve a Bulk VDSL instance"
       ::= { adGenVdsl2Status 8 }

    adGenVdsl2ReserveInstanceBulkVDSLTlvEntry OBJECT-TYPE
       SYNTAX      AdGenVdsl2ReserveInstanceBulkVDSLTlvEntry
       MAX-ACCESS  not-accessible
       STATUS      current
       DESCRIPTION
           "Index is the slot number."
       INDEX { adGenSlotInfoIndex }
       ::= { adGenVdsl2ReserveInstanceBulkVDSLTlvTable 1 }

    AdGenVdsl2ReserveInstanceBulkVDSLTlvEntry ::=
       SEQUENCE {
           adGenVdsl2ReserveInstanceBulkVDSLSlotInstance           Integer32
       }

    adGenVdsl2ReserveInstanceBulkVDSLSlotInstance      OBJECT-TYPE
       SYNTAX                    		Integer32
       MAX-ACCESS                		read-only
       STATUS                    		current
       DESCRIPTION
           "Used to index the Tlv table; each time this is called by slot it
            creates an instance for that viewer"
        ::= { adGenVdsl2ReserveInstanceBulkVDSLTlvEntry 1 }


--==================================================================================================================
-- The Bulk VDSL Tlv Table
--==================================================================================================================
    adGenVdsl2BulkVDSLTlvTable OBJECT-TYPE
       SYNTAX      SEQUENCE OF AdGenVdsl2BulkVDSLTlvEntry
       MAX-ACCESS  not-accessible
       STATUS      current
       DESCRIPTION
           "Table contains filters that can be applied on the requested instances"
       ::= { adGenVdsl2Status 9 }

    adGenVdsl2BulkVDSLTlvEntry OBJECT-TYPE
       SYNTAX      AdGenVdsl2BulkVDSLTlvEntry
       MAX-ACCESS  not-accessible
       STATUS      current
       DESCRIPTION
           "Indexes are the slot and instance number"
       INDEX { adGenSlotInfoIndex, adGenVdsl2BulkVDSLTlvInstance }
       ::= { adGenVdsl2BulkVDSLTlvTable 1 }

    AdGenVdsl2BulkVDSLTlvEntry ::=
       SEQUENCE {
       	   adGenVdsl2BulkVDSLTlvInstance       Integer32,
       	   adGenVdsl2BulkVDSLTlvType           INTEGER,
       	   adGenVdsl2BulkVDSLTlvPort           Unsigned32,
       	   adGenVdsl2BulkVDLSTlvCreate         INTEGER
       }

    adGenVdsl2BulkVDSLTlvInstance      	OBJECT-TYPE
       SYNTAX                    		Integer32
       MAX-ACCESS                		not-accessible
       STATUS                    		current
       DESCRIPTION
           "Used to index the table by TLV Instance number."
        ::= { adGenVdsl2BulkVDSLTlvEntry 1 }

    adGenVdsl2BulkVDSLTlvType      OBJECT-TYPE
       SYNTAX                      INTEGER {
                                                bat(1),
                                                snr(2),
                                                qln(3),
                                                hlog(4)
                                           }
       MAX-ACCESS                  read-write
       STATUS                      current
       DESCRIPTION
            "Used to set the type of VDSL info to return in the VDSL TLV instance:
            1 - Bit Allocation Table (BAT), 2 - Signal Noise Ratio (SNR),
            3 - Quiet Line Noise (QLN), 4 - Channel Transfer Function (HLOG)"
       DEFVAL { bat }
        ::= { adGenVdsl2BulkVDSLTlvEntry 2 }

    adGenVdsl2BulkVDSLTlvPort      OBJECT-TYPE
       SYNTAX                      Unsigned32
       MAX-ACCESS                  read-write
       STATUS                      current
       DESCRIPTION
           "Used to set the VDSL port to get the info for VDSL TLV instance"

       DEFVAL { 1 }
        ::= { adGenVdsl2BulkVDSLTlvEntry 3 }

    adGenVdsl2BulkVDLSTlvCreate    OBJECT-TYPE
       SYNTAX INTEGER              {
       								 updateinstance(1)
       							   }
       MAX-ACCESS                  read-write
       STATUS                      current
       DESCRIPTION
           "Set this OID to 1 to update the instance with Bulk VDSL info depending on type set.
            A get on this OID always returns a 1."

        ::= { adGenVdsl2BulkVDSLTlvEntry 4 }

-- ***************************************************************************
-- Trap definitions
-- ***************************************************************************

  -- ============ Traps (VTUC)  ===========================
  adGenVdsl2VtucTraps OBJECT IDENTIFIER ::= { adGenVdsl2VtucTrapPrefix 0 }

         adGenVdsl2VtucSnrMgnThreshTrap      NOTIFICATION-TYPE
             OBJECTS {
                       adTrapInformSeqNum,
                       sysName,
                       adGenSlotInfoIndex,
                       adGenPortTrapIdentifier,
                       adGenVdsl2CurrUSSnrMgn,
                       adGenVdsl2VtucThreshSnrMgn
                     }
             STATUS  current
             DESCRIPTION
                 "SNR Margin threshold reached."
         --#TYPE         "WARNING - VTUC SNR Margin Threshold crossed"
         --#SUMMARY      "VTUC SNR Margin Threshold Alarm"
         --#SUMMARY      "detected at shelf: %s, slot: %d, port: %d, margin: %d, threshold: %d"
         --#ARGUMENTS    {1,2,3,4,5}
         --#SEVERITY     WARNING
         --#GENERIC      6
         --#CATEGORY     "Threshold Events"
         --#SOURCE_ID    "A"
         --#TIMEINDEX    0
         ::= { adGenVdsl2VtucTraps 1 }

         adGenVdsl2VtucLofsThreshTrap      NOTIFICATION-TYPE
             OBJECTS {
                       adTrapInformSeqNum,
                       sysName,
                       adGenSlotInfoIndex,
                       adGenPortTrapIdentifier,
                       adGenVdsl2VtucPerfCurr15MinLofs,
                       adGenVdsl2VtucThresh15MinLofs
                     }
             STATUS  current
             DESCRIPTION
                 "Loss of Framing 15-minute interval threshold reached."
         --#TYPE         "WARNING - VTUC 15-Minute LOFS Threshold crossed"
         --#SUMMARY      "VTUC 15-Minute LOFS Threshold Alarm"
         --#SUMMARY      "detected at shelf: %s, slot: %d, port: %d, lofs: %d, threshold: %d"
         --#ARGUMENTS    {1,2,3,4,5}
         --#SEVERITY     WARNING
         --#GENERIC      6
         --#CATEGORY     "Threshold Events"
         --#SOURCE_ID    "A"
         --#TIMEINDEX    0
         ::= { adGenVdsl2VtucTraps 2 }

         adGenVdsl2VtucLossThreshTrap      NOTIFICATION-TYPE
             OBJECTS {
                       adTrapInformSeqNum,
                       sysName,
                       adGenSlotInfoIndex,
                       adGenPortTrapIdentifier,
                       adGenVdsl2VtucPerfCurr15MinLoss,
                       adGenVdsl2VtucThresh15MinLoss
                     }
             STATUS  current
             DESCRIPTION
                 "Loss of Signal 15-minute interval threshold reached."
         --#TYPE         "WARNING - VTUC 15-Minute LOSS Threshold crossed"
         --#SUMMARY      "VTUC 15-Minute LOSS Threshold Alarm"
         --#SUMMARY      "detected at shelf: %s, slot: %d, port: %d, loss: %d, threshold: %d"
         --#ARGUMENTS    {1,2,3,4,5}
         --#SEVERITY     WARNING
         --#GENERIC      6
         --#CATEGORY     "Threshold Events"
         --#SOURCE_ID    "A"
         --#TIMEINDEX    0
         ::= { adGenVdsl2VtucTraps 3 }

         adGenVdsl2VtucLolsThreshTrap      NOTIFICATION-TYPE
             OBJECTS {
                       adTrapInformSeqNum,
                       sysName,
                       adGenSlotInfoIndex,
                       adGenPortTrapIdentifier,
                       adGenVdsl2VtucPerfCurr15MinLols,
                       adGenVdsl2VtucThresh15MinLols
                     }
             STATUS  current
             DESCRIPTION
                 "Lols of Signal 15-minute interval threshold reached."
         --#TYPE         "WARNING - VTUC 15-Minute LOLS Threshold crossed"
         --#SUMMARY      "VTUC 15-Minute LOLS Threshold Alarm"
         --#SUMMARY      "detected at shelf: %s, slot: %d, port: %d, lols: %d, threshold: %d"
         --#ARGUMENTS    {1,2,3,4,5}
         --#SEVERITY     WARNING
         --#GENERIC      6
         --#CATEGORY     "Threshold Events"
         --#SOURCE_ID    "A"
         --#TIMEINDEX    0
         ::= { adGenVdsl2VtucTraps 4 }

         adGenVdsl2VtucLprsThreshTrap      NOTIFICATION-TYPE
             OBJECTS {
                       adTrapInformSeqNum,
                       sysName,
                       adGenSlotInfoIndex,
                       adGenPortTrapIdentifier,
                       adGenVdsl2VtucPerfCurr15MinLprs,
                       adGenVdsl2VtucThresh15MinLprs
                     }
             STATUS  current
             DESCRIPTION
                 "Loss of Power 15-minute interval threshold reached."
         --#TYPE         "WARNING - VTUC 15-Minute LPRS Threshold crossed"
         --#SUMMARY      "VTUC 15-Minute LPRS Threshold Alarm"
         --#SUMMARY      "detected at shelf: %s, slot: %d, port: %d, lprs: %d, threshold: %d"
         --#ARGUMENTS    {1,2,3,4,5}
         --#SEVERITY     WARNING
         --#GENERIC      6
         --#CATEGORY     "Threshold Events"
         --#SOURCE_ID    "A"
         --#TIMEINDEX    0
         ::= { adGenVdsl2VtucTraps 5 }

         adGenVdsl2VtucESThreshTrap       NOTIFICATION-TYPE
             OBJECTS {
                       adTrapInformSeqNum,
                       sysName,
                       adGenSlotInfoIndex,
                       adGenPortTrapIdentifier,
                       adGenVdsl2VtucPerfCurr15MinEs,
                       adGenVdsl2VtucThresh15MinEs
                     }
             STATUS  current
             DESCRIPTION
                 "Errored Second 15-minute interval threshold reached."
         --#TYPE         "WARNING - VTUC 15-Minute ES Threshold crossed"
         --#SUMMARY      "VTUC 15-Minute ES Threshold Alarm"
         --#SUMMARY      "detected at shelf: %s, slot: %d, port: %d, es: %d, threshold: %d"
         --#ARGUMENTS    {1,2,3,4,5}
         --#SEVERITY     WARNING
         --#GENERIC      6
         --#CATEGORY     "Threshold Events"
         --#SOURCE_ID    "A"
         --#TIMEINDEX    0
         ::= { adGenVdsl2VtucTraps 6 }

         adGenVdsl2VtucSESThreshTrap       NOTIFICATION-TYPE
             OBJECTS {
                       adTrapInformSeqNum,
                       sysName,
                       adGenSlotInfoIndex,
                       adGenPortTrapIdentifier,
                       adGenVdsl2VtucPerfCurr15MinSes,
                       adGenVdsl2VtucThresh15MinSes
                     }
             STATUS  current
             DESCRIPTION
                 "Severely Errored Second 15-minute interval threshold
                 reached."
         --#TYPE         "WARNING - VTUC 15-Minute SES Threshold crossed"
         --#SUMMARY      "VTUC 15-Minute SES Threshold Alarm"
         --#SUMMARY      "detected at shelf: %s, slot: %d, port: %d, ses: %d, threshold: %d"
         --#ARGUMENTS    {1,2,3,4,5}
         --#SEVERITY     WARNING
         --#GENERIC      6
         --#CATEGORY     "Threshold Events"
         --#SOURCE_ID    "A"
         --#TIMEINDEX    0
         ::= { adGenVdsl2VtucTraps 7 }

         adGenVdsl2VtucUASThreshTrap       NOTIFICATION-TYPE
             OBJECTS {
                       adTrapInformSeqNum,
                       sysName,
                       adGenSlotInfoIndex,
                       adGenPortTrapIdentifier,
                       adGenVdsl2VtucPerfCurr15MinUas,
                       adGenVdsl2VtucThresh15MinUas
                     }
             STATUS  current
             DESCRIPTION
                 "Unavailable Second 15-minute interval threshold reached."
         --#TYPE         "WARNING - VTUC 15-Minute UAS Threshold crossed"
         --#SUMMARY      "VTUC 15-Minute UAS Threshold Alarm"
         --#SUMMARY      "detected at shelf: %s, slot: %d, port: %d, uas: %d, threshold: %d"
         --#ARGUMENTS    {1,2,3,4,5}
         --#SEVERITY     WARNING
         --#GENERIC      6
         --#CATEGORY     "Threshold Events"
         --#SOURCE_ID    "A"
         --#TIMEINDEX    0
         ::= { adGenVdsl2VtucTraps 8 }

  -- ============ Traps (VTUR)  ===========================

  adGenVdsl2VturTraps OBJECT IDENTIFIER ::= { adGenVdsl2VturTrapPrefix 0 }

         adGenVdsl2VturSnrMgnThreshTrap      NOTIFICATION-TYPE
             OBJECTS {
                       adTrapInformSeqNum,
                       sysName,
                       adGenSlotInfoIndex,
                       adGenPortTrapIdentifier,
                       adGenVdsl2CurrDSSnrMgn,
                       adGenVdsl2VturThreshSnrMgn
                     }

             STATUS  current
             DESCRIPTION
                 "SNR threshold reached."
         --#TYPE         "WARNING - VTUR SNR Margin Threshold crossed"
         --#SUMMARY      "VTUR SNR Margin Threshold Alarm"
         --#SUMMARY      "detected at shelf: %s, slot: %d, port: %d, margin: %d, threshold: %d"
         --#ARGUMENTS    {1,2,3,4,5}
         --#SEVERITY     WARNING
         --#GENERIC      6
         --#CATEGORY     "Threshold Events"
         --#SOURCE_ID    "A"
         --#TIMEINDEX    0
         ::= { adGenVdsl2VturTraps 1 }

         adGenVdsl2VturLofsThreshTrap      NOTIFICATION-TYPE
             OBJECTS {
                       adTrapInformSeqNum,
                       sysName,
                       adGenSlotInfoIndex,
                       adGenPortTrapIdentifier,
                       adGenVdsl2VturPerfCurr15MinLofs,
                       adGenVdsl2VturThresh15MinLofs
                     }
             STATUS  current
             DESCRIPTION
                 "Loss of Framing 15-minute interval threshold reached."
         --#TYPE         "WARNING - VTUR 15-Minute LOFS Threshold crossed"
         --#SUMMARY      "VTUR 15-Minute LOFS Threshold Alarm"
         --#SUMMARY      "detected at shelf: %s, slot: %d, port: %d, lofs: %d, threshold: %d"
         --#ARGUMENTS    {1,2,3,4,5}
         --#SEVERITY     WARNING
         --#GENERIC      6
         --#CATEGORY     "Threshold Events"
         --#SOURCE_ID    "A"
         --#TIMEINDEX    0
         ::= { adGenVdsl2VturTraps 2 }

         adGenVdsl2VturLossThreshTrap      NOTIFICATION-TYPE
             OBJECTS {
                       adTrapInformSeqNum,
                       sysName,
                       adGenSlotInfoIndex,
                       adGenPortTrapIdentifier,
                       adGenVdsl2VturPerfCurr15MinLoss,
                       adGenVdsl2VturThresh15MinLoss
                     }
             STATUS  current
             DESCRIPTION
                 "Loss of Signal 15-minute interval threshold reached."
         --#TYPE         "WARNING - VTUR 15-Minute LOSS Threshold crossed"
         --#SUMMARY      "VTUR 15-Minute LOSS Threshold Alarm"
         --#SUMMARY      "detected at shelf: %s, slot: %d, port: %d, loss: %d, threshold: %d"
         --#ARGUMENTS    {1,2,3,4,5}
         --#SEVERITY     WARNING
         --#GENERIC      6
         --#CATEGORY     "Threshold Events"
         --#SOURCE_ID    "A"
         --#TIMEINDEX    0
         ::= { adGenVdsl2VturTraps 3 }

         adGenVdsl2VturLprsThreshTrap      NOTIFICATION-TYPE
             OBJECTS {
                       adTrapInformSeqNum,
                       sysName,
                       adGenSlotInfoIndex,
                       adGenPortTrapIdentifier,
                       adGenVdsl2VturPerfCurr15MinLprs,
                       adGenVdsl2VturThresh15MinLprs
                     }
             STATUS  current
             DESCRIPTION
                 "Loss of Power 15-minute interval threshold reached."
         --#TYPE         "WARNING - VTUR 15-Minute LPRS Threshold crossed"
         --#SUMMARY      "VTUR 15-Minute LPRS Threshold Alarm"
         --#SUMMARY      "detected at shelf: %s, slot: %d, port: %d, lprs: %d, threshold: %d"
         --#ARGUMENTS    {1,2,3,4,5}
         --#SEVERITY     WARNING
         --#GENERIC      6
         --#CATEGORY     "Threshold Events"
         --#SOURCE_ID    "A"
         --#TIMEINDEX    0
         ::= { adGenVdsl2VturTraps 4 }

         adGenVdsl2VturESThreshTrap       NOTIFICATION-TYPE
             OBJECTS {
                       adTrapInformSeqNum,
                       sysName,
                       adGenSlotInfoIndex,
                       adGenPortTrapIdentifier,
                       adGenVdsl2VturPerfCurr15MinEs,
                       adGenVdsl2VturThresh15MinEs
                     }
             STATUS  current
             DESCRIPTION
                 "Errored Second 15-minute interval threshold reached."
         --#TYPE         "WARNING - VTUR 15-Minute ES Threshold crossed"
         --#SUMMARY      "VTUR 15-Minute ES Threshold Alarm"
         --#SUMMARY      "detected at shelf: %s, slot: %d, port: %d, es: %d, threshold: %d"
         --#ARGUMENTS    {1,2,3,4,5}
         --#SEVERITY     WARNING
         --#GENERIC      6
         --#CATEGORY     "Threshold Events"
         --#SOURCE_ID    "A"
         --#TIMEINDEX    0
         ::= { adGenVdsl2VturTraps 5 }

         adGenVdsl2VturSESThreshTrap       NOTIFICATION-TYPE
             OBJECTS {
                       adTrapInformSeqNum,
                       sysName,
                       adGenSlotInfoIndex,
                       adGenPortTrapIdentifier,
                       adGenVdsl2VturPerfCurr15MinSes,
                       adGenVdsl2VturThresh15MinSes
                     }
             STATUS  current
             DESCRIPTION
                 "Severely Errored Second 15-minute interval threshold
                 reached."
         --#TYPE         "WARNING - VTUR 15-Minute SES Threshold crossed"
         --#SUMMARY      "VTUR 15-Minute SES Threshold Alarm"
         --#SUMMARY      "detected at shelf: %s, slot: %d, port: %d, ses: %d, threshold: %d"
         --#ARGUMENTS    {1,2,3,4,5}
         --#SEVERITY     WARNING
         --#GENERIC      6
         --#CATEGORY     "Threshold Events"
         --#SOURCE_ID    "A"
         --#TIMEINDEX    0
         ::= { adGenVdsl2VturTraps 6 }

         adGenVdsl2VturUASThreshTrap       NOTIFICATION-TYPE
             OBJECTS {
                       adTrapInformSeqNum,
                       sysName,
                       adGenSlotInfoIndex,
                       adGenPortTrapIdentifier,
                       adGenVdsl2VturPerfCurr15MinUas,
                       adGenVdsl2VturThresh15MinUas
                     }
             STATUS  current
             DESCRIPTION
                 "Unavailable Second 15-minute interval threshold
                 reached."
         --#TYPE         "WARNING - VTUR 15-Minute UAS Threshold crossed"
         --#SUMMARY      "VTUR 15-Minute UAS Threshold Alarm"
         --#SUMMARY      "detected at shelf: %s, slot: %d, port: %d, uas: %d, threshold: %d"
         --#ARGUMENTS    {1,2,3,4,5}
         --#SEVERITY     WARNING
         --#GENERIC      6
         --#CATEGORY     "Threshold Events"
         --#SOURCE_ID    "A"
         --#TIMEINDEX    0
         ::= { adGenVdsl2VturTraps 7 }

  -- ============ Remote Device Traps (VTUC)  ===========================
  adGenVdsl2VtucRemoteTraps OBJECT IDENTIFIER ::= { adGenVdsl2VtucTrapPrefixRemote 0 }

         adGenVdsl2VtucSnrMgnRemoteThreshTrap      NOTIFICATION-TYPE
             OBJECTS {
                       adTrapInformSeqNum,
                       sysName,
                       ifIndex,
                       adGenVdsl2CurrUSSnrMgn,
                       adGenVdsl2VtucThreshSnrMgn
                     }
             STATUS  current
             DESCRIPTION
                 "SNR Margin threshold reached."
         --#TYPE         "WARNING - VTUC SNR Margin Threshold crossed"
         --#SUMMARY      "VTUC SNR Margin Threshold Alarm"
         --#SUMMARY      "detected at shelf: %s, remote: %d, margin: %d, threshold: %d"
         --#ARGUMENTS    {1,2,3,4}
         --#SEVERITY     WARNING
         --#GENERIC      6
         --#CATEGORY     "Threshold Events"
         --#SOURCE_ID    "A"
         --#TIMEINDEX    0
         ::= { adGenVdsl2VtucRemoteTraps 1 }

         adGenVdsl2VtucLofsRemoteThreshTrap      NOTIFICATION-TYPE
             OBJECTS {
                       adTrapInformSeqNum,
                       sysName,
                       ifIndex,
                       adGenVdsl2VtucPerfCurr15MinLofs,
                       adGenVdsl2VtucThresh15MinLofs
                     }
             STATUS  current
             DESCRIPTION
                 "Loss of Framing 15-minute interval threshold reached."
         --#TYPE         "WARNING - VTUC 15-Minute LOFS Threshold crossed"
         --#SUMMARY      "VTUC 15-Minute LOFS Threshold Alarm"
         --#SUMMARY      "detected at shelf: %s, remote: %d, margin: %d, threshold: %d"
         --#ARGUMENTS    {1,2,3,4}
         --#SEVERITY     WARNING
         --#GENERIC      6
         --#CATEGORY     "Threshold Events"
         --#SOURCE_ID    "A"
         --#TIMEINDEX    0
         ::= { adGenVdsl2VtucRemoteTraps 2 }

         adGenVdsl2VtucLossRemoteThreshTrap      NOTIFICATION-TYPE
             OBJECTS {
                       adTrapInformSeqNum,
                       sysName,
                       ifIndex,
                       adGenVdsl2VtucPerfCurr15MinLoss,
                       adGenVdsl2VtucThresh15MinLoss
                     }
             STATUS  current
             DESCRIPTION
                 "Loss of Signal 15-minute interval threshold reached."
         --#TYPE         "WARNING - VTUC 15-Minute LOSS Threshold crossed"
         --#SUMMARY      "VTUC 15-Minute LOSS Threshold Alarm"
         --#SUMMARY      "detected at shelf: %s, remote: %d, margin: %d, threshold: %d"
         --#ARGUMENTS    {1,2,3,4}
         --#SEVERITY     WARNING
         --#GENERIC      6
         --#CATEGORY     "Threshold Events"
         --#SOURCE_ID    "A"
         --#TIMEINDEX    0
         ::= { adGenVdsl2VtucRemoteTraps 3 }

         adGenVdsl2VtucLolsRemoteThreshTrap      NOTIFICATION-TYPE
             OBJECTS {
                       adTrapInformSeqNum,
                       sysName,
                       ifIndex,
                       adGenVdsl2VtucPerfCurr15MinLols,
                       adGenVdsl2VtucThresh15MinLols
                     }
             STATUS  current
             DESCRIPTION
                 "Lols of Signal 15-minute interval threshold reached."
         --#TYPE         "WARNING - VTUC 15-Minute LOLS Threshold crossed"
         --#SUMMARY      "VTUC 15-Minute LOLS Threshold Alarm"
         --#SUMMARY      "detected at shelf: %s, remote: %d, margin: %d, threshold: %d"
         --#ARGUMENTS    {1,2,3,4}
         --#SEVERITY     WARNING
         --#GENERIC      6
         --#CATEGORY     "Threshold Events"
         --#SOURCE_ID    "A"
         --#TIMEINDEX    0
         ::= { adGenVdsl2VtucRemoteTraps 4 }

         adGenVdsl2VtucLprsRemoteThreshTrap      NOTIFICATION-TYPE
             OBJECTS {
                       adTrapInformSeqNum,
                       sysName,
                       ifIndex,
                       adGenVdsl2VtucPerfCurr15MinLprs,
                       adGenVdsl2VtucThresh15MinLprs
                     }
             STATUS  current
             DESCRIPTION
                 "Loss of Power 15-minute interval threshold reached."
         --#TYPE         "WARNING - VTUC 15-Minute LPRS Threshold crossed"
         --#SUMMARY      "VTUC 15-Minute LPRS Threshold Alarm"
         --#SUMMARY      "detected at shelf: %s, remote: %d, margin: %d, threshold: %d"
         --#ARGUMENTS    {1,2,3,4}
         --#SEVERITY     WARNING
         --#GENERIC      6
         --#CATEGORY     "Threshold Events"
         --#SOURCE_ID    "A"
         --#TIMEINDEX    0
         ::= { adGenVdsl2VtucRemoteTraps 5 }

         adGenVdsl2VtucESRemoteThreshTrap       NOTIFICATION-TYPE
             OBJECTS {
                       adTrapInformSeqNum,
                       sysName,
                       ifIndex,
                       adGenVdsl2VtucPerfCurr15MinEs,
                       adGenVdsl2VtucThresh15MinEs
                     }
             STATUS  current
             DESCRIPTION
                 "Errored Second 15-minute interval threshold reached."
         --#TYPE         "WARNING - VTUC 15-Minute ES Threshold crossed"
         --#SUMMARY      "VTUC 15-Minute ES Threshold Alarm"
         --#SUMMARY      "detected at shelf: %s, remote: %d, margin: %d, threshold: %d"
         --#ARGUMENTS    {1,2,3,4}
         --#SEVERITY     WARNING
         --#GENERIC      6
         --#CATEGORY     "Threshold Events"
         --#SOURCE_ID    "A"
         --#TIMEINDEX    0
         ::= { adGenVdsl2VtucRemoteTraps 6 }

         adGenVdsl2VtucSESRemoteThreshTrap       NOTIFICATION-TYPE
             OBJECTS {
                       adTrapInformSeqNum,
                       sysName,
                       ifIndex,
                       adGenVdsl2VtucPerfCurr15MinSes,
                       adGenVdsl2VtucThresh15MinSes
                     }
             STATUS  current
             DESCRIPTION
                 "Severely Errored Second 15-minute interval threshold
                 reached."
         --#TYPE         "WARNING - VTUC 15-Minute SES Threshold crossed"
         --#SUMMARY      "VTUC 15-Minute SES Threshold Alarm"
         --#SUMMARY      "detected at shelf: %s, remote: %d, margin: %d, threshold: %d"
         --#ARGUMENTS    {1,2,3,4}
         --#SEVERITY     WARNING
         --#GENERIC      6
         --#CATEGORY     "Threshold Events"
         --#SOURCE_ID    "A"
         --#TIMEINDEX    0
         ::= { adGenVdsl2VtucRemoteTraps 7 }

         adGenVdsl2VtucUASRemoteThreshTrap       NOTIFICATION-TYPE
             OBJECTS {
                       adTrapInformSeqNum,
                       sysName,
                       ifIndex,
                       adGenVdsl2VtucPerfCurr15MinUas,
                       adGenVdsl2VtucThresh15MinUas
                     }
             STATUS  current
             DESCRIPTION
                 "Unavailable Second 15-minute interval threshold reached."
         --#TYPE         "WARNING - VTUC 15-Minute UAS Threshold crossed"
         --#SUMMARY      "VTUC 15-Minute UAS Threshold Alarm"
         --#SUMMARY      "detected at shelf: %s, remote: %d, margin: %d, threshold: %d"
         --#ARGUMENTS    {1,2,3,4}
         --#SEVERITY     WARNING
         --#GENERIC      6
         --#CATEGORY     "Threshold Events"
         --#SOURCE_ID    "A"
         --#TIMEINDEX    0
         ::= { adGenVdsl2VtucRemoteTraps 8 }

  -- ============ Remote Device Traps (VTUR)  ===========================

  adGenVdsl2VturRemoteTraps OBJECT IDENTIFIER ::= { adGenVdsl2VturTrapPrefixRemote 0 }

         adGenVdsl2VturSnrMgnRemoteThreshTrap      NOTIFICATION-TYPE
             OBJECTS {
                       adTrapInformSeqNum,
                       sysName,
                       ifIndex,
                       adGenVdsl2CurrDSSnrMgn,
                       adGenVdsl2VturThreshSnrMgn
                     }

             STATUS  current
             DESCRIPTION
                 "SNR threshold reached."
         --#TYPE         "WARNING - VTUR SNR Margin Threshold crossed"
         --#SUMMARY      "VTUR SNR Margin Threshold Alarm"
         --#SUMMARY      "detected at shelf: %s, remote: %d, margin: %d, threshold: %d"
         --#ARGUMENTS    {1,2,3,4}
         --#SEVERITY     WARNING
         --#GENERIC      6
         --#CATEGORY     "Threshold Events"
         --#SOURCE_ID    "A"
         --#TIMEINDEX    0
         ::= { adGenVdsl2VturRemoteTraps 1 }

         adGenVdsl2VturLofsRemoteThreshTrap      NOTIFICATION-TYPE
             OBJECTS {
                       adTrapInformSeqNum,
                       sysName,
                       ifIndex,
                       adGenVdsl2VturPerfCurr15MinLofs,
                       adGenVdsl2VturThresh15MinLofs
                     }
             STATUS  current
             DESCRIPTION
                 "Loss of Framing 15-minute interval threshold reached."
         --#TYPE         "WARNING - VTUR 15-Minute LOFS Threshold crossed"
         --#SUMMARY      "VTUR 15-Minute LOFS Threshold Alarm"
         --#SUMMARY      "detected at shelf: %s, remote: %d, margin: %d, threshold: %d"
         --#ARGUMENTS    {1,2,3,4}
         --#SEVERITY     WARNING
         --#GENERIC      6
         --#CATEGORY     "Threshold Events"
         --#SOURCE_ID    "A"
         --#TIMEINDEX    0
         ::= { adGenVdsl2VturRemoteTraps 2 }

         adGenVdsl2VturLossRemoteThreshTrap      NOTIFICATION-TYPE
             OBJECTS {
                       adTrapInformSeqNum,
                       sysName,
                       ifIndex,
                       adGenVdsl2VturPerfCurr15MinLoss,
                       adGenVdsl2VturThresh15MinLoss
                     }
             STATUS  current
             DESCRIPTION
                 "Loss of Signal 15-minute interval threshold reached."
         --#TYPE         "WARNING - VTUR 15-Minute LOSS Threshold crossed"
         --#SUMMARY      "VTUR 15-Minute LOSS Threshold Alarm"
         --#SUMMARY      "detected at shelf: %s, remote: %d, margin: %d, threshold: %d"
         --#ARGUMENTS    {1,2,3,4}
         --#SEVERITY     WARNING
         --#GENERIC      6
         --#CATEGORY     "Threshold Events"
         --#SOURCE_ID    "A"
         --#TIMEINDEX    0
         ::= { adGenVdsl2VturRemoteTraps 3 }

         adGenVdsl2VturLprsRemoteThreshTrap      NOTIFICATION-TYPE
             OBJECTS {
                       adTrapInformSeqNum,
                       sysName,
                       ifIndex,
                       adGenVdsl2VturPerfCurr15MinLprs,
                       adGenVdsl2VturThresh15MinLprs
                     }
             STATUS  current
             DESCRIPTION
                 "Loss of Power 15-minute interval threshold reached."
         --#TYPE         "WARNING - VTUR 15-Minute LPRS Threshold crossed"
         --#SUMMARY      "VTUR 15-Minute LPRS Threshold Alarm"
         --#SUMMARY      "detected at shelf: %s, remote: %d, margin: %d, threshold: %d"
         --#ARGUMENTS    {1,2,3,4}
         --#SEVERITY     WARNING
         --#GENERIC      6
         --#CATEGORY     "Threshold Events"
         --#SOURCE_ID    "A"
         --#TIMEINDEX    0
         ::= { adGenVdsl2VturRemoteTraps 4 }

         adGenVdsl2VturESRemoteThreshTrap       NOTIFICATION-TYPE
             OBJECTS {
                       adTrapInformSeqNum,
                       sysName,
                       ifIndex,
                       adGenVdsl2VturPerfCurr15MinEs,
                       adGenVdsl2VturThresh15MinEs
                     }
             STATUS  current
             DESCRIPTION
                 "Errored Second 15-minute interval threshold reached."
         --#TYPE         "WARNING - VTUR 15-Minute ES Threshold crossed"
         --#SUMMARY      "VTUR 15-Minute ES Threshold Alarm"
         --#SUMMARY      "detected at shelf: %s, remote: %d, margin: %d, threshold: %d"
         --#ARGUMENTS    {1,2,3,4}
         --#SEVERITY     WARNING
         --#GENERIC      6
         --#CATEGORY     "Threshold Events"
         --#SOURCE_ID    "A"
         --#TIMEINDEX    0
         ::= { adGenVdsl2VturRemoteTraps 5 }

         adGenVdsl2VturSESRemoteThreshTrap       NOTIFICATION-TYPE
             OBJECTS {
                       adTrapInformSeqNum,
                       sysName,
                       ifIndex,
                       adGenVdsl2VturPerfCurr15MinSes,
                       adGenVdsl2VturThresh15MinSes
                     }
             STATUS  current
             DESCRIPTION
                 "Severely Errored Second 15-minute interval threshold
                 reached."
         --#TYPE         "WARNING - VTUR 15-Minute SES Threshold crossed"
         --#SUMMARY      "VTUR 15-Minute SES Threshold Alarm"
         --#SUMMARY      "detected at shelf: %s, remote: %d, margin: %d, threshold: %d"
         --#ARGUMENTS    {1,2,3,4}
         --#SEVERITY     WARNING
         --#GENERIC      6
         --#CATEGORY     "Threshold Events"
         --#SOURCE_ID    "A"
         --#TIMEINDEX    0
         ::= { adGenVdsl2VturRemoteTraps 6 }

         adGenVdsl2VturUASRemoteThreshTrap       NOTIFICATION-TYPE
             OBJECTS {
                       adTrapInformSeqNum,
                       sysName,
                       ifIndex,
                       adGenVdsl2VturPerfCurr15MinUas,
                       adGenVdsl2VturThresh15MinUas
                     }
             STATUS  current
             DESCRIPTION
                 "Unavailable Second 15-minute interval threshold
                 reached."
         --#TYPE         "WARNING - VTUR 15-Minute UAS Threshold crossed"
         --#SUMMARY      "VTUR 15-Minute UAS Threshold Alarm"
         --#SUMMARY      "detected at shelf: %s, remote: %d, margin: %d, threshold: %d"
         --#ARGUMENTS    {1,2,3,4}
         --#SEVERITY     WARNING
         --#GENERIC      6
         --#CATEGORY     "Threshold Events"
         --#SOURCE_ID    "A"
         --#TIMEINDEX    0
         ::= { adGenVdsl2VturRemoteTraps 7 }

   -- ************************************************************************
   -- MIB Groups
   -- ************************************************************************

   -- ============ Prov Group ================================================
   adGenVdsl2ProvGroup OBJECT-GROUP
   OBJECTS
   {
             adGenVdsl2ConfDsRateMode,
             adGenVdsl2ConfDsTargetSnrMgn,
             adGenVdsl2ConfDsMaxSnrMgn,
             adGenVdsl2ConfDsMinSnrMgn,
             adGenVdsl2ConfUsTargetSnrMgn,
             adGenVdsl2ConfUsMaxSnrMgn,
             adGenVdsl2ConfUsMinSnrMgn,
             adGenVdsl2LineConfProfileRowStatus,

             adGenVdsl2ConfServiceMode,
             adGenVdsl2ConfMultiModeDmtTse,
             adGenVdsl2ConfBandProfiles,
             adGenVdsl2ConfSpecificPsdSelect,
             adGenVdsl2ConfUsPsdMaskU0Select,
             adGenVdsl2ConfUsTrellis,
             adGenVdsl2ConfDsTrellis,
             adGenVdsl2ConfUsPboSetting,
             adGenVdsl2ConfDsPboSetting,
             adGenVdsl2ConfUsVnoiseSetting,
             adGenVdsl2ConfDsVnoiseSetting,
             adGenVdsl2ConfUsBitSwap,
             adGenVdsl2ConfDsBitSwap,
             adGenVdsl2ConfHamBandNotches,
             adGenVdsl2ConfUsNomAggTxPwr,
             adGenVdsl2ConfDsNomAggTxPwr,
             adGenVdsl2ConfUsMaxNomTxPsd,
             adGenVdsl2ConfDsMaxNomTxPsd,
             adGenVdsl2ConfUsMaxAggRxPwr,
             adGenVdsl2ConfFramingMode,

             adGenVdsl2ConfUsLp0MaxPayloadRate,
             adGenVdsl2ConfUsLp0MinPayloadRate,
             adGenVdsl2ConfUsLp0MaxDelay,
             adGenVdsl2ConfUsLp0MinProtection,
             adGenVdsl2ConfUsLp0RaRatio,
             adGenVdsl2ConfUsLp0InitPolicy,
             adGenVdsl2ConfDsLp0MaxPayloadRate,
             adGenVdsl2ConfDsLp0MinPayloadRate,
             adGenVdsl2ConfDsLp0MaxDelay,
             adGenVdsl2ConfDsLp0MinProtection,
             adGenVdsl2ConfDsLp0RaRatio,
             adGenVdsl2ConfDsLp0InitPolicy,

             adGenVdsl2ConfUsLp1MaxPayloadRate,
             adGenVdsl2ConfUsLp1MinPayloadRate,
             adGenVdsl2ConfUsLp1MaxDelay,
             adGenVdsl2ConfUsLp1MinProtection,
             adGenVdsl2ConfUsLp1RaRatio,
             adGenVdsl2ConfUsLp1InitPolicy,
             adGenVdsl2ConfDsLp1MaxPayloadRate,
             adGenVdsl2ConfDsLp1MinPayloadRate,
             adGenVdsl2ConfDsLp1MaxDelay,
             adGenVdsl2ConfDsLp1MinProtection,
             adGenVdsl2ConfDsLp1RaRatio,
             adGenVdsl2ConfDsLp1InitPolicy,

             adGenVdsl2VtucThreshSnrMgn,
             adGenVdsl2VtucThresh15MinLofs,
             adGenVdsl2VtucThresh15MinLoss,
             adGenVdsl2VtucThresh15MinLols,
             adGenVdsl2VtucThresh15MinLprs,
             adGenVdsl2VtucThresh15MinEs,
             adGenVdsl2VtucThresh15MinSes,
             adGenVdsl2VtucThresh15MinUas,
             adGenVdsl2VturThreshSnrMgn,
             adGenVdsl2VturThresh15MinLofs,
             adGenVdsl2VturThresh15MinLoss,
             adGenVdsl2VturThresh15MinLprs,
             adGenVdsl2VturThresh15MinEs,
             adGenVdsl2VturThresh15MinSes,
             adGenVdsl2VturThresh15MinUas,
             adGenVdsl2LineAlarmConfProfileRowStatus,
             adGenVdsl2ThreshUsLp0RateUp,
             adGenVdsl2ThreshUsLp0RateDown,
             adGenVdsl2ThreshDsLp0RateUp,
             adGenVdsl2ThreshDsLp0RateDown,
             adGenVdsl2ThreshUsLp1RateUp,
             adGenVdsl2ThreshUsLp1RateDown,
             adGenVdsl2ThreshDsLp1RateUp,
             adGenVdsl2ThreshDsLp1RateDown,
             adGenVdsl2ConfRestoreDefaults,

             adGenVdsl2BandNumber,
             adGenVdsl2BandConfUsCustomPboCableA,
             adGenVdsl2BandConfUsCustomPboCableB,

             adGenVdsl2AlmSlotLinkdownSeverity
   }
   STATUS current
   DESCRIPTION
     "These objects provide support for Vdsl2 configuration."
   ::= { adGenVdsl2MibGroups 1 }


   -- ============ Status Group ===============================================
   adGenVdsl2StatusGroup  OBJECT-GROUP
   OBJECTS
   {
             adGenVdsl2LineCoding,
             adGenVdsl2LinePortServiceState,
             adGenVdsl2LineStatus,
             adGenVdsl2LineUpTime,

             adGenVdsl2LineCurrTransSysMode,
             adGenVdsl2LineCurrBandProfile,
             adGenVdsl2LineCurrEstimatedLength,
             adGenVdsl2LineCurrTpsTcFramingMode,

             adGenVdsl2VtucInvSerialNumber,
             adGenVdsl2VtucInvVendorID,
             adGenVdsl2VtucInvVersionNumber,
             adGenVdsl2CurrUSSnrMgn,
             adGenVdsl2CurrUSAtn,
             adGenVdsl2VtucCurrStatus,
             adGenVdsl2VtucCurrOutputPwr,
             adGenVdsl2VtucCurrAttainableRate,
             adGenVdsl2VtucCurrTxRate,
             adGenVdsl2VtucPrevTxRate,
             adGenVdsl2VtucActTxPsd,
             adGenVdsl2VtucCurrTpsTcStatus,

             adGenVdsl2VturInvSerialNumber,
             adGenVdsl2VturInvVendorID,
             adGenVdsl2VturInvVersionNumber,
             adGenVdsl2CurrDSSnrMgn,
             adGenVdsl2CurrDSAtn,
             adGenVdsl2VturCurrStatus,
             adGenVdsl2VturCurrOutputPwr,
             adGenVdsl2VturCurrAttainableRate,
             adGenVdsl2VturCurrTxRate,
             adGenVdsl2VturPrevTxRate,
             adGenVdsl2VturActTxPsd,

             adGenVdsl2VtucChanInterleaveDelay,
             adGenVdsl2VtucChanCurrTxRate,
             adGenVdsl2VtucChanPrevTxRate,
             adGenVdsl2VtucChanCrcBlockLength ,
             adGenVdsl2VtucChanINP,

             adGenVdsl2VturChanInterleaveDelay,
             adGenVdsl2VturChanCurrTxRate,
             adGenVdsl2VturChanPrevTxRate,
             adGenVdsl2VturChanCrcBlockLength ,
             adGenVdsl2VturChanINP,

             adGenVdsl2BandStatusUsStartCarrier,
             adGenVdsl2BandStatusUsStopCarrier,
             adGenVdsl2BandStatusUsMargin,
             adGenVdsl2BandStatusUsLatn,
             adGenVdsl2BandStatusUsSatn,

             adGenVdsl2BandStatusDsStartCarrier,
             adGenVdsl2BandStatusDsStopCarrier,
             adGenVdsl2BandStatusDsMargin,
             adGenVdsl2BandStatusDsLatn,
             adGenVdsl2BandStatusDsSatn,

             adGenVdsl2ScStatusUsBits,
             adGenVdsl2ScStatusUsGain,
             adGenVdsl2ScStatusUsSnr,

             adGenVdsl2ScStatusDsBits,
             adGenVdsl2ScStatusDsGain,
             adGenVdsl2ScStatusDsSnr
   }
   STATUS current
   DESCRIPTION
     "These objects provide support for the reporting of status
      of Vdsl2 physical interfaces, channel, band, and subcarrier.
     "
   ::= { adGenVdsl2MibGroups 2}

   -- ============ PM Group ==================================================
   adGenVdsl2PMGroup  OBJECT-GROUP
   OBJECTS
   {
             adGenVdsl2VtucPerfLofs,
             adGenVdsl2VtucPerfLoss,
             adGenVdsl2VtucPerfLols,
             adGenVdsl2VtucPerfLprs,
             adGenVdsl2VtucPerfEs,
             adGenVdsl2VtucPerfInits,
             adGenVdsl2VtucPerfSes,
             adGenVdsl2VtucPerfUas,
             adGenVdsl2VtucPerfFecs,
             adGenVdsl2VtucPerfCrc,
             adGenVdsl2VtucPerfFec,
             adGenVdsl2VtucPerfValidIntervals,
             adGenVdsl2VtucPerfInvalidIntervals,
             adGenVdsl2VtucPerfCurr15MinTimeElapsed,
             adGenVdsl2VtucPerfCurr15MinLofs,
             adGenVdsl2VtucPerfCurr15MinLoss,
             adGenVdsl2VtucPerfCurr15MinLols,
             adGenVdsl2VtucPerfCurr15MinLprs,
             adGenVdsl2VtucPerfCurr15MinEs,
             adGenVdsl2VtucPerfCurr15MinInits,
             adGenVdsl2VtucPerfCurr15MinSes,
             adGenVdsl2VtucPerfCurr15MinUas,
             adGenVdsl2VtucPerfCurr15MinFecs,
             adGenVdsl2VtucPerfCurr15MinCrc,
             adGenVdsl2VtucPerfCurr15MinFec,
             adGenVdsl2VtucPerfCurr1DayTimeElapsed,
             adGenVdsl2VtucPerfCurr1DayLofs,
             adGenVdsl2VtucPerfCurr1DayLoss,
             adGenVdsl2VtucPerfCurr1DayLols,
             adGenVdsl2VtucPerfCurr1DayLprs,
             adGenVdsl2VtucPerfCurr1DayEs,
             adGenVdsl2VtucPerfCurr1DayInits,
             adGenVdsl2VtucPerfCurr1DaySes,
             adGenVdsl2VtucPerfCurr1DayUas,
             adGenVdsl2VtucPerfCurr1DayFecs,
             adGenVdsl2VtucPerfCurr1DayCrc,
             adGenVdsl2VtucPerfCurr1DayFec,
             adGenVdsl2VtucPerfTcTxUnits,
             adGenVdsl2VtucPerfTcTxDataUnits,
             adGenVdsl2VtucPerfTcTxDataOctets,
             adGenVdsl2VtucPerfTcTxIdleUnits,
             adGenVdsl2VtucPerfTcRxUnits,
             adGenVdsl2VtucPerfTcRxDataUnits,
             adGenVdsl2VtucPerfTcRxDataOctets,
             adGenVdsl2VtucPerfTcRxIdleUnits,
             adGenVdsl2VtucPerfTcRxErroredUnits,

             adGenVdsl2VturPerfLofs,
             adGenVdsl2VturPerfLoss,
             adGenVdsl2VturPerfLprs,
             adGenVdsl2VturPerfEs,
             adGenVdsl2VturPerfSes,
             adGenVdsl2VturPerfUas,
             adGenVdsl2VturPerfFecs,
             adGenVdsl2VturPerfCrc,
             adGenVdsl2VturPerfFec,
             adGenVdsl2VturPerfValidIntervals,
             adGenVdsl2VturPerfInvalidIntervals,
             adGenVdsl2VturPerfCurr15MinTimeElapsed,
             adGenVdsl2VturPerfCurr15MinLofs,
             adGenVdsl2VturPerfCurr15MinLoss,
             adGenVdsl2VturPerfCurr15MinLprs,
             adGenVdsl2VturPerfCurr15MinEs,
             adGenVdsl2VturPerfCurr15MinSes,
             adGenVdsl2VturPerfCurr15MinUas,
             adGenVdsl2VturPerfCurr15MinFecs,
             adGenVdsl2VturPerfCurr15MinCrc,
             adGenVdsl2VturPerfCurr15MinFec,
             adGenVdsl2VturPerfCurr1DayTimeElapsed,
             adGenVdsl2VturPerfCurr1DayLofs,
             adGenVdsl2VturPerfCurr1DayLoss,
             adGenVdsl2VturPerfCurr1DayLprs,
             adGenVdsl2VturPerfCurr1DayEs,
             adGenVdsl2VturPerfCurr1DaySes,
             adGenVdsl2VturPerfCurr1DayUas,
             adGenVdsl2VturPerfCurr1DayFecs,
             adGenVdsl2VturPerfCurr1DayCrc,
             adGenVdsl2VturPerfCurr1DayFec,
             adGenVdsl2VturPerfTcTxUnits,
             adGenVdsl2VturPerfTcTxDataUnits,
             adGenVdsl2VturPerfTcTxDataOctets,
             adGenVdsl2VturPerfTcTxIdleUnits,
             adGenVdsl2VturPerfTcRxUnits,
             adGenVdsl2VturPerfTcRxDataUnits,
             adGenVdsl2VturPerfTcRxDataOctets,
             adGenVdsl2VturPerfTcRxIdleUnits,
             adGenVdsl2VturPerfTcRxErroredUnits,

             adGenVdsl2VtucIntervalNumber,
             adGenVdsl2VtucIntervalLofs,
             adGenVdsl2VtucIntervalLoss,
             adGenVdsl2VtucIntervalLols,
             adGenVdsl2VtucIntervalLprs,
             adGenVdsl2VtucIntervalES,
             adGenVdsl2VtucIntervalInits,
             adGenVdsl2VtucIntervalValidData,
             adGenVdsl2VtucIntervalSES,
             adGenVdsl2VtucIntervalUAS,
             adGenVdsl2VtucIntervalFECs,
             adGenVdsl2VtucIntervalFEC,
             adGenVdsl2VtucIntervalCRC,

             adGenVdsl2VturIntervalNumber,
             adGenVdsl2VturIntervalLofs,
             adGenVdsl2VturIntervalLoss,
             adGenVdsl2VturIntervalLprs,
             adGenVdsl2VturIntervalES,
             adGenVdsl2VturIntervalValidData,
             adGenVdsl2VturIntervalSES,
             adGenVdsl2VturIntervalUAS,
             adGenVdsl2VturIntervalFECs,
             adGenVdsl2VturIntervalFEC,
             adGenVdsl2VturIntervalCRC,

             adGenVdsl2VtucChanReceivedBlks,
             adGenVdsl2VtucChanTransmittedBlks,
             adGenVdsl2VtucChanCorrectedBlks,
             adGenVdsl2VtucChanUncorrectBlks,
             adGenVdsl2VtucChanPerfValidIntervals,
             adGenVdsl2VtucChanPerfInvalidIntervals,
             adGenVdsl2VtucChanPerfCurr15MinTimeElapsed,
             adGenVdsl2VtucChanPerfCurr15MinReceivedBlks,
             adGenVdsl2VtucChanPerfCurr15MinTransmittedBlks,
             adGenVdsl2VtucChanPerfCurr15MinCorrectedBlks,
             adGenVdsl2VtucChanPerfCurr15MinUncorrectBlks,
             adGenVdsl2VtucChanPerfCurr1DayTimeElapsed,
             adGenVdsl2VtucChanPerfCurr1DayReceivedBlks,
             adGenVdsl2VtucChanPerfCurr1DayTransmittedBlks,
             adGenVdsl2VtucChanPerfCurr1DayCorrectedBlks,
             adGenVdsl2VtucChanPerfCurr1DayUncorrectBlks,
             adGenVdsl2VtucChanPerfTcTxUnits,
             adGenVdsl2VtucChanPerfTcTxDataUnits,
             adGenVdsl2VtucChanPerfTcTxDataOctets,
             adGenVdsl2VtucChanPerfTcTxIdleUnits,
             adGenVdsl2VtucChanPerfTcRxUnits,
             adGenVdsl2VtucChanPerfTcRxDataUnits,
             adGenVdsl2VtucChanPerfTcRxDataOctets,
             adGenVdsl2VtucChanPerfTcRxIdleUnits,
             adGenVdsl2VtucChanPerfTcRxErroredUnits,

             adGenVdsl2VturChanReceivedBlks,
             adGenVdsl2VturChanTransmittedBlks,
             adGenVdsl2VturChanCorrectedBlks,
             adGenVdsl2VturChanUncorrectBlks,
             adGenVdsl2VturChanPerfValidIntervals,
             adGenVdsl2VturChanPerfInvalidIntervals,
             adGenVdsl2VturChanPerfCurr15MinTimeElapsed,
             adGenVdsl2VturChanPerfCurr15MinReceivedBlks,
             adGenVdsl2VturChanPerfCurr15MinTransmittedBlks,
             adGenVdsl2VturChanPerfCurr15MinCorrectedBlks,
             adGenVdsl2VturChanPerfCurr15MinUncorrectBlks,
             adGenVdsl2VturChanPerfCurr1DayTimeElapsed,
             adGenVdsl2VturChanPerfCurr1DayReceivedBlks,
             adGenVdsl2VturChanPerfCurr1DayTransmittedBlks,
             adGenVdsl2VturChanPerfCurr1DayCorrectedBlks,
             adGenVdsl2VturChanPerfCurr1DayUncorrectBlks,
             adGenVdsl2VturChanPerfTcTxUnits,
             adGenVdsl2VturChanPerfTcTxDataUnits,
             adGenVdsl2VturChanPerfTcTxDataOctets,
             adGenVdsl2VturChanPerfTcTxIdleUnits,
             adGenVdsl2VturChanPerfTcRxUnits,
             adGenVdsl2VturChanPerfTcRxDataUnits,
             adGenVdsl2VturChanPerfTcRxDataOctets,
             adGenVdsl2VturChanPerfTcRxIdleUnits,
             adGenVdsl2VturChanPerfTcRxErroredUnits,

             adGenVdsl2VtucChanIntervalNumber,
             adGenVdsl2VtucChanIntervalReceivedBlks,
             adGenVdsl2VtucChanIntervalTransmittedBlks,
             adGenVdsl2VtucChanIntervalCorrectedBlks,
             adGenVdsl2VtucChanIntervalUncorrectBlks,
             adGenVdsl2VtucChanIntervalValidData,
             adGenVdsl2VturChanIntervalNumber,
             adGenVdsl2VturChanIntervalReceivedBlks,
             adGenVdsl2VturChanIntervalTransmittedBlks,
             adGenVdsl2VturChanIntervalCorrectedBlks,
             adGenVdsl2VturChanIntervalUncorrectBlks,
             adGenVdsl2VturChanIntervalValidData,

             adGenVdsl2Vtuc1DayIntervalNumber,
             adGenVdsl2Vtuc1DayIntervalLofs,
             adGenVdsl2Vtuc1DayIntervalLoss,
             adGenVdsl2Vtuc1DayIntervalLols,
             adGenVdsl2Vtuc1DayIntervalLprs,
             adGenVdsl2Vtuc1DayIntervalES,
             adGenVdsl2Vtuc1DayIntervalInits,
             adGenVdsl2Vtuc1DayIntervalValidData,
             adGenVdsl2Vtuc1DayIntervalSES,
             adGenVdsl2Vtuc1DayIntervalUAS,
             adGenVdsl2Vtuc1DayIntervalFECs,
             adGenVdsl2Vtuc1DayIntervalFEC,
             adGenVdsl2Vtuc1DayIntervalCRC,

             adGenVdsl2Vtur1DayIntervalNumber,
             adGenVdsl2Vtur1DayIntervalLofs,
             adGenVdsl2Vtur1DayIntervalLoss,
             adGenVdsl2Vtur1DayIntervalLprs,
             adGenVdsl2Vtur1DayIntervalES,
             adGenVdsl2Vtur1DayIntervalValidData,
             adGenVdsl2Vtur1DayIntervalSES,
             adGenVdsl2Vtur1DayIntervalUAS,
             adGenVdsl2Vtur1DayIntervalFECs,
             adGenVdsl2Vtur1DayIntervalFEC,
             adGenVdsl2Vtur1DayIntervalCRC
   }
   STATUS current
   DESCRIPTION
     "These objects provide support for the reporting of the
      Vdsl2 interface PM data."
   ::= { adGenVdsl2MibGroups 3}


   -- ============ Traps Group ================================================
   adGenVdsl2TrapsGroup  OBJECT-GROUP
   OBJECTS
   {
        adGenVdsl2CurrUSSnrMgn,
        adGenVdsl2VtucThreshSnrMgn,
        adGenVdsl2VtucPerfCurr15MinLofs,
        adGenVdsl2VtucThresh15MinLofs,
        adGenVdsl2VtucPerfCurr15MinLoss,
        adGenVdsl2VtucThresh15MinLoss,
        adGenVdsl2VtucPerfCurr15MinLols,
        adGenVdsl2VtucThresh15MinLols,
        adGenVdsl2VtucPerfCurr15MinLprs,
        adGenVdsl2VtucThresh15MinLprs,
        adGenVdsl2VtucPerfCurr15MinEs,
        adGenVdsl2VtucThresh15MinEs,
        adGenVdsl2VtucPerfCurr15MinSes,
        adGenVdsl2VtucThresh15MinSes,
        adGenVdsl2VtucPerfCurr15MinUas,
        adGenVdsl2VtucThresh15MinUas,

        adGenVdsl2CurrDSSnrMgn,
        adGenVdsl2VturThreshSnrMgn,
        adGenVdsl2VturPerfCurr15MinLofs,
        adGenVdsl2VturThresh15MinLofs,
        adGenVdsl2VturPerfCurr15MinLoss,
        adGenVdsl2VturThresh15MinLoss,
        adGenVdsl2VturPerfCurr15MinLprs,
        adGenVdsl2VturThresh15MinLprs,
        adGenVdsl2VturPerfCurr15MinEs,
        adGenVdsl2VturThresh15MinEs,
        adGenVdsl2VturPerfCurr15MinSes,
        adGenVdsl2VturThresh15MinSes,
        adGenVdsl2VturPerfCurr15MinUas,
        adGenVdsl2VturThresh15MinUas
   }
   STATUS current
   DESCRIPTION
     "These objects provide support for the reporting of the
      traps from the Vdsl2 interfaces."
   ::= { adGenVdsl2MibGroups 4}

   -- ============ ExtConfig Group ===========================================
   adGenVdsl2ExtConfigGroup  OBJECT-GROUP
   OBJECTS
   {
        adGenVdsl2LineManagementProfileNameApplied,
        adGenVdsl2LineManagementProfileIndexApplied,
        adGenVdsl2LineCircuitID
   }
   STATUS current
   DESCRIPTION
     "These objects provide support for Vdsl2 extended profile configuration."
   ::= { adGenVdsl2MibGroups 5}

   -- ============ Test Group ================================================
--adGenVdsl2TestGroup  OBJECT-GROUP
--   OBJECTS
--   {
--   }
--   STATUS current
--   DESCRIPTION
--     "These objects provide access for the testing of Vdsl2 interfaces."
--   ::= { adGenVdsl2MibGroups 6}



END
