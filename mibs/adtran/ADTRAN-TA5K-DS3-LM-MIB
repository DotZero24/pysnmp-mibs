ADTRAN-TA5K-DS3-LM-MIB

    DEFINITIONS ::= BEGIN

    -- TITLE:     The ADTRAN Total Access TA5000 DS3 ATM Line Module MIB
    -- PRODUCT:   1187201L1
    -- VERSION:   1.0
    -- DATE:      March 12, 2007

    -- This MIB Contains tables specific to the quad port DS3 card

    -- MIBs supported:

    -- HISTORY:


    IMPORTS
        MODULE-IDENTITY,
        OBJECT-TYPE,
        Integer32,
        Counter32,
        IpAddress
           FROM SNMPv2-SMI

        ifIndex
            FROM IF-MIB

        adIdentity,
        adProducts,
        adMgmt
            FROM ADTRAN-MIB

        adTrapInformSeqNum
            FROM ADTRAN-GENTRAPINFORM-MIB

        dsx3CurrentIndex,
        dsx3IntervalIndex,
        dsx3IntervalNumber,
        dsx3TotalIndex
            FROM DS3-MIB

        PerfCurrentCount,
        PerfIntervalCount,
        PerfTotalCount
            FROM PerfHist-TC-MIB;

-- *********************************************************************************************************

    adTa5kDs3ModuleIdentity MODULE-IDENTITY
        LAST-UPDATED "200703120000Z"
        ORGANIZATION
            "ADTRAN, Inc."
        CONTACT-INFO
            "CND Tech Support
                Postal: ADTRAN, Inc.
                        901 Explorer Blvd.
                        Huntsville, AL  35806
                        Tel: +1 800 726-8663
                        Fax: +1 256 963 6217
                        E-mail: support@adtran.com"
        DESCRIPTION
            "Total Access 5000 Quad Port DS3 1187201L1 MIB"
        ::= { adIdentity 979 }

-- OBJECT IDENTIFIERS
    adTa5kDs3                   OBJECT IDENTIFIER ::= { adMgmt 979 }
    adTa5kDs3Traps              OBJECT IDENTIFIER ::= { adProducts 979 }
    adTa5kDS3Provisioning       OBJECT IDENTIFIER ::= { adTa5kDs3 1}
    adTa5kDS3Test               OBJECT IDENTIFIER ::= { adTa5kDs3 2}
    adTa5kDS3Performance        OBJECT IDENTIFIER ::= { adTa5kDs3 3}

-- *********************************************************************************************************
-- *********************************************************************************************************
    adTa5kDS3TestPattenTable OBJECT-TYPE
        SYNTAX      SEQUENCE OF AdTa5kDS3TestPattenEntry
        MAX-ACCESS  not-accessible
        STATUS      current
        DESCRIPTION
                   "DS3 Test Patten"
        ::= { adTa5kDS3Test 1 }

    adTa5kDS3TestPattenEntry OBJECT-TYPE
        SYNTAX  AdTa5kDS3TestPattenEntry
        MAX-ACCESS  not-accessible
        STATUS      current
        DESCRIPTION
                   "Table Entry"
        INDEX   { ifIndex}
        ::= { adTa5kDS3TestPattenTable 1 }

    AdTa5kDS3TestPattenEntry ::=
        SEQUENCE {
                        adTa5kDS3TxTestPattern          Integer32,
                        adTa5kDS3RxTestPattern          Integer32,
                        adTa5kDS3TestPatternErrors      Integer32,
                        adTa5kDS3TestPatternResetStatus Integer32
                 }

    adTa5kDS3TxTestPattern OBJECT-TYPE
        SYNTAX          Integer32
        MAX-ACCESS      read-write
        STATUS          current
        DESCRIPTION
                ""
        ::= { adTa5kDS3TestPattenEntry 1 }

    adTa5kDS3RxTestPattern OBJECT-TYPE
        SYNTAX          Integer32
        MAX-ACCESS      read-only
        STATUS          current
        DESCRIPTION
                ""
        ::= { adTa5kDS3TestPattenEntry 2 }

    adTa5kDS3TestPatternErrors OBJECT-TYPE
        SYNTAX          Integer32
        MAX-ACCESS      read-only
        STATUS          current
        DESCRIPTION
                ""
        ::= { adTa5kDS3TestPattenEntry 3 }

    adTa5kDS3TestPatternResetStatus OBJECT-TYPE
        SYNTAX          Integer32
        MAX-ACCESS      read-write
        STATUS          current
        DESCRIPTION
                ""
        ::= { adTa5kDS3TestPattenEntry 4 }

-- *********************************************************************************************************
    adTa5kDS3LoopbackTable OBJECT-TYPE
        SYNTAX      SEQUENCE OF AdTa5kDS3LoopbackEntry
        MAX-ACCESS  not-accessible
        STATUS      current
        DESCRIPTION
                   "DS3 Loopback"
        ::= { adTa5kDS3Test 2 }

    adTa5kDS3LoopbackEntry OBJECT-TYPE
        SYNTAX  AdTa5kDS3LoopbackEntry
        MAX-ACCESS  not-accessible
        STATUS      current
        DESCRIPTION
                   "Table Entry"
        INDEX   { ifIndex}
        ::= { adTa5kDS3LoopbackTable 1 }

    AdTa5kDS3LoopbackEntry ::=
        SEQUENCE {
                        adTa5kDS3LoopbackFarEnd         Integer32,
                        adTa5kDS3LoopbackCancelFarEnd   Integer32
                 }

    adTa5kDS3LoopbackFarEnd OBJECT-TYPE
        SYNTAX          Integer32
        MAX-ACCESS      read-write
        STATUS          current
        DESCRIPTION
                ""
        ::= { adTa5kDS3LoopbackEntry 1 }

    adTa5kDS3LoopbackCancelFarEnd OBJECT-TYPE
        SYNTAX          Integer32
        MAX-ACCESS      read-write
        STATUS          current
        DESCRIPTION
                ""
        ::= { adTa5kDS3LoopbackEntry 2 }

-- *********************************************************************************************************
-- Enterprise DS3 PLCP stats
-- the DS3/E3 Current Table


     adTa5kDS3CurrentTable OBJECT-TYPE
          SYNTAX  SEQUENCE OF AdTa5kDS3CurrentEntry
          MAX-ACCESS  not-accessible
          STATUS  current
          DESCRIPTION
                 "The DS3/E3 current table contains various
                 statistics being collected for the current 15
                 minute interval."
          ::= { adTa5kDS3Performance 1 }

     adTa5kDS3CurrentEntry OBJECT-TYPE
          SYNTAX  AdTa5kDS3CurrentEntry
          MAX-ACCESS  not-accessible
          STATUS  current
          DESCRIPTION
                 "An entry in the DS3/E3 Current table."
          INDEX   { dsx3CurrentIndex }
          ::= { adTa5kDS3CurrentTable 1 }

     AdTa5kDS3CurrentEntry ::=
          SEQUENCE {
              adTa5kDS3CurrentBIP8            PerfCurrentCount,
              adTa5kDS3CurrentPLCPES          PerfCurrentCount
         }

     adTa5kDS3CurrentBIP8 OBJECT-TYPE
          SYNTAX  PerfCurrentCount
          MAX-ACCESS  read-only
          STATUS  current
          DESCRIPTION
                 "The counter associated with the number of BIP8"

          ::= { adTa5kDS3CurrentEntry 1 }

     adTa5kDS3CurrentPLCPES OBJECT-TYPE
          SYNTAX  PerfCurrentCount
          MAX-ACCESS  read-only
          STATUS  current
          DESCRIPTION
                 "The counter associated with the number of PLCP
                 Errored Seconds."
          ::= { adTa5kDS3CurrentEntry 2 }

     -- the DS3/E3 Interval Table

     adTa5kDS3IntervalTable OBJECT-TYPE
          SYNTAX  SEQUENCE OF AdTa5kDS3IntervalEntry
          MAX-ACCESS  not-accessible
          STATUS  current
          DESCRIPTION
                 "The DS3/E3 Interval Table contains various
                 statistics collected by each DS3/E3 Interface over
                 the previous 24 hours of operation.  The past 24
                 hours are broken into 96 completed 15 minute
                 intervals."

          ::= { adTa5kDS3Performance 2 }

     adTa5kDS3IntervalEntry OBJECT-TYPE
          SYNTAX  AdTa5kDS3IntervalEntry
          MAX-ACCESS  not-accessible
          STATUS  current
          DESCRIPTION
                 "An entry in the DS3/E3 Interval table."
          INDEX   { dsx3IntervalIndex, dsx3IntervalNumber }
          ::= { adTa5kDS3IntervalTable 1 }

     AdTa5kDS3IntervalEntry ::=
          SEQUENCE {
              adTa5kDS3IntervalBIP8            PerfIntervalCount,
              adTa5kDS3IntervalPLCPES          PerfIntervalCount
          }

     adTa5kDS3IntervalBIP8 OBJECT-TYPE
          SYNTAX  PerfIntervalCount
          MAX-ACCESS  read-only
          STATUS  current
          DESCRIPTION
                 "The counter associated with the number of BIP8"
          ::= { adTa5kDS3IntervalEntry 1 }

     adTa5kDS3IntervalPLCPES OBJECT-TYPE
          SYNTAX  PerfIntervalCount
          MAX-ACCESS  read-only
          STATUS  current
          DESCRIPTION
                 "The counter associated with the number of PLCP
                 Errored Seconds."
          ::= { adTa5kDS3IntervalEntry 2 }

     -- the DS3/E3 Total

     adTa5kDS3TotalTable OBJECT-TYPE
          SYNTAX  SEQUENCE OF AdTa5kDS3TotalEntry
          MAX-ACCESS  not-accessible
          STATUS  current
          DESCRIPTION
                 "The DS3/E3 Total Table contains the cumulative
                 sum of the various statistics for the 24 hour
                 period preceding the current interval."
          ::= {adTa5kDS3Performance 3}

     adTa5kDS3TotalEntry OBJECT-TYPE
          SYNTAX  AdTa5kDS3TotalEntry
          MAX-ACCESS  not-accessible
          STATUS  current


          DESCRIPTION
                 "An entry in the DS3/E3 Total table."
         INDEX   { dsx3TotalIndex }
          ::= { adTa5kDS3TotalTable 1 }

     AdTa5kDS3TotalEntry ::=
          SEQUENCE {
              adTa5kDS3TotalBIP8       PerfTotalCount,
              adTa5kDS3TotalPLCPES     PerfTotalCount
          }

     adTa5kDS3TotalBIP8 OBJECT-TYPE
          SYNTAX  PerfTotalCount
          MAX-ACCESS  read-only
          STATUS  current
          DESCRIPTION
                 "The counter associated with the number of BIP8
                 encountered by a DS3 interface in
                 the previous 24 hour interval. Invalid 15 minute
                 intervals count as 0."
          ::= { adTa5kDS3TotalEntry 1 }

     adTa5kDS3TotalPLCPES OBJECT-TYPE
          SYNTAX  PerfTotalCount
          MAX-ACCESS  read-only
          STATUS  current


          DESCRIPTION
                 "The counter associated with the number of PLCP
                 Errored Seconds, encountered by a DS3
                 interface in the previous 24 hour interval.
                 Invalid 15 minute intervals count as 0."
          ::= { adTa5kDS3TotalEntry 2 }

-- *********************************************************************************************************
-- *********************************************************************************************************
   END
