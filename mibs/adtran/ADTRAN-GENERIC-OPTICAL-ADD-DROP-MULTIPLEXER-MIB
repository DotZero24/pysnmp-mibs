ADTRAN-GENERIC-OPTICAL-ADD-DROP-MULTIPLEXER-MIB

-- TITLE:     Generic Optical Add Drop Multiplexer MIB
-- PRODUCT:   MARS-2, VOADM
-- VERSION:   1.0
-- DATE:      Oct. 10, 2011
-- AUTHOR:    Albert Sue
-- STATUS:    Created
--

DEFINITIONS ::= BEGIN

IMPORTS

   adGenOpticalADM,
   adGenOpticalADMID         FROM ADTRAN-SHARED-CND-SYSTEM-MIB

   InterfaceIndex,
   ifIndex                   FROM IF-MIB

   OBJECT-TYPE,
   MODULE-IDENTITY,
   NOTIFICATION-TYPE,
   Integer32,
   IpAddress                 FROM SNMPv2-SMI

   TruthValue,
   DisplayString,
   RowStatus                 FROM SNMPv2-TC

   adGenSlotInfoIndex        FROM ADTRAN-GENSLOT-MIB

   adTrapInformSeqNum        FROM ADTRAN-GENTRAPINFORM-MIB
   sysName                   FROM SNMPv2-MIB;

adGenOpticalADMMIB MODULE-IDENTITY
   LAST-UPDATED "201207260000Z"
   ORGANIZATION "Adtran, Inc."
   CONTACT-INFO
     "CND Tech Support
         Postal: ADTRAN, Inc.
                 901 Explorer Blvd.
                 Huntsville, AL  35806
                 Tel: +1 800 726-8663
                 Fax: +1 256 963 6217
                 E-mail: support@adtran.com"
   DESCRIPTION
      "This MIB defines the objects for the Generic Optical Add drop Multiplexer MIB."

   REVISION "201207260000Z"
   DESCRIPTION "Added adGenOpticalADMRemoveAllCrossConnect,
                adGenOpticalADMProvGain,
                adGenOpticalADMInterfaceStatActualGain,
                adGenOpticalADMInterfaceStatInputPower
                "
   REVISION "201206120000Z"
   DESCRIPTION "Added adGenOpticalADMProvChannelAdminStatus and
                adGenOpticalADMCrossConnectAdminStatus"

   REVISION "201205180000Z"
   DESCRIPTION "Added adGenOpticalADMAlmComOutAmpShutOffClear and
                adGenOpticalADMAlmComOutAmpShutOffActive"

   REVISION "201204110000Z"
   DESCRIPTION "Added adGenOpticalADMProvChannelWaveLengthMin and
                adGenOpticalADMProvChannelWaveLengthMax"

   REVISION "201203190000Z"
   DESCRIPTION "Added adGenOpticalADMProvInsertionLoss"

   REVISION "201201300000Z"
   DESCRIPTION "Created"

::= { adGenOpticalADMID 1 }

  -- ///////////////////////////////////////////////////////
  -- Operation Groups
  -- ///////////////////////////////////////////////////////
  adGenOpticalADMConfiguration   OBJECT IDENTIFIER ::= { adGenOpticalADM  1   }
  adGenOpticalADMProvInterface   OBJECT IDENTIFIER ::= { adGenOpticalADM  2   }
  adGenOpticalADMProvChannel     OBJECT IDENTIFIER ::= { adGenOpticalADM  3   }
  adGenOpticalADMCrossConnect    OBJECT IDENTIFIER ::= { adGenOpticalADM  4   }
  adGenOpticalADMProvError       OBJECT IDENTIFIER ::= { adGenOpticalADM  5   }
  adGenOpticalADMStatus          OBJECT IDENTIFIER ::= { adGenOpticalADM  6   }
  adGenOpticalADMAlarm           OBJECT IDENTIFIER ::= { adGenOpticalADM  100 }
  adGenOpticalADMEvents          OBJECT IDENTIFIER ::= { adGenOpticalADMAlarm 0}

-- //////////////////////////////////////////////////////////////////
--                 adGenOpticalADMConfigration
-- //////////////////////////////////////////////////////////////////
    adGenOpticalADMConfigurationTable OBJECT-TYPE
        SYNTAX  SEQUENCE OF AdGenOpticalADMConfigurationEntry
        MAX-ACCESS  not-accessible
        STATUS  current
        DESCRIPTION
                   "Configuration table."
        ::= { adGenOpticalADMConfiguration 1 }

    -- /////////////////////////////////////////////////////////
    adGenOpticalADMConfigurationEntry OBJECT-TYPE
        SYNTAX  AdGenOpticalADMConfigurationEntry
        MAX-ACCESS  not-accessible
        STATUS  current
        DESCRIPTION
                   "Table Entry."
        INDEX   { adGenSlotInfoIndex }
        ::= { adGenOpticalADMConfigurationTable 1 }

    -- /////////////////////////////////////////////////////////
    AdGenOpticalADMConfigurationEntry ::=
        SEQUENCE {
                        adGenOpticalADMGridSpacingSupported  BITS,
                        adGenOpticalADMRemoveAllCrossConnect INTEGER
                 }
    -- /////////////////////////////////////////////////////////
    adGenOpticalADMGridSpacingSupported OBJECT-TYPE
    SYNTAX  BITS
            {
              fiftyGHz(0),
              oneHundredGHz(1)
            }
    MAX-ACCESS         read-only
    STATUS             current
    DESCRIPTION
       "This shows the supported Grid Spacing.
        Bit positions:
        0 - 50 GHz Grid Spacing supported
        1 - 100 GHz Grid Spacing supported"
    ::= { adGenOpticalADMConfigurationEntry 1 }

    -- /////////////////////////////////////////////////////////
    adGenOpticalADMRemoveAllCrossConnect OBJECT-TYPE
    SYNTAX  INTEGER
            {
              removeAllCrossConnect(1)
            }
    MAX-ACCESS         read-write
    STATUS             current
    DESCRIPTION
       "This can be used to remove all Cross Connect at once."
    ::= { adGenOpticalADMConfigurationEntry 2 }

-- //////////////////////////////////////////////////////////////////
--                 adGenOpticalADMProvInterface
-- //////////////////////////////////////////////////////////////////
    adGenOpticalADMProvInterfaceTable OBJECT-TYPE
        SYNTAX  SEQUENCE OF AdGenOpticalADMProvInterfaceEntry
        MAX-ACCESS  not-accessible
        STATUS  current
        DESCRIPTION
                   "Provision Interface table."
        ::= { adGenOpticalADMProvInterface 1 }

    -- /////////////////////////////////////////////////////////
    adGenOpticalADMProvInterfaceEntry OBJECT-TYPE
        SYNTAX  AdGenOpticalADMProvInterfaceEntry
        MAX-ACCESS  not-accessible
        STATUS  current
        DESCRIPTION
                   "Table Entry."
        INDEX   { ifIndex }
        ::= { adGenOpticalADMProvInterfaceTable 1 }

    -- /////////////////////////////////////////////////////////
    AdGenOpticalADMProvInterfaceEntry ::=
        SEQUENCE {
                        adGenOpticalADMProvInterfaceDescription     OCTET STRING,
                        adGenOpticalADMProvChannelPowerLevel        Integer32,
                        adGenOpticalADMProvAutoPowerBalancing       INTEGER,
                        adGenOpticalADMProvOcmTotalPowerThresholdHigh  Integer32,
                        adGenOpticalADMProvOcmTotalPowerThresholdLow   Integer32,
                        adGenOpticalADMProvTotalPowerThresholdHigh  Integer32,
                        adGenOpticalADMProvTotalPowerThresholdLow   Integer32,
                        adGenOpticalADMProvInsertionLoss            Integer32,
                        adGenOpticalADMProvGain                     Integer32
                 }
    -- /////////////////////////////////////////////////////////
    adGenOpticalADMProvInterfaceDescription OBJECT-TYPE
    SYNTAX             OCTET STRING (SIZE (1..50))
    MAX-ACCESS         read-write
    STATUS             current
    DESCRIPTION
       "A short description for this optical interface."
    ::= { adGenOpticalADMProvInterfaceEntry 1 }

    -- /////////////////////////////////////////////////////////
    adGenOpticalADMProvChannelPowerLevel OBJECT-TYPE
        SYNTAX Integer32
        UNITS "Tenth of a dBm"
        MAX-ACCESS read-write
        STATUS current
        DESCRIPTION
                "This OID defines the channel power level reference
                 for all the channels coming in on ADD-IN or EXP-IN
                 interfaces to be auto power balanced. This value
                 will be used when auto power balance is enabled"
        ::= { adGenOpticalADMProvInterfaceEntry 2 }

    -- /////////////////////////////////////////////////////////
    adGenOpticalADMProvAutoPowerBalancing OBJECT-TYPE
        SYNTAX INTEGER {
                          disable(1),
                          enable(2)
                       }
        MAX-ACCESS read-write
        STATUS current
        DESCRIPTION
                "This OID can be used to set the auto
                 power balancing mode on this interface."
        ::= { adGenOpticalADMProvInterfaceEntry 3 }

    -- /////////////////////////////////////////////////////////
    adGenOpticalADMProvOcmTotalPowerThresholdHigh OBJECT-TYPE
        SYNTAX Integer32
        UNITS "Tenth of a dBm"
        MAX-ACCESS read-write
        STATUS current
        DESCRIPTION
                "This sets the upper limit of the OCM Power threshold.  Once reached,
                 an alarm will be issued"
        ::= { adGenOpticalADMProvInterfaceEntry 4 }

    -- /////////////////////////////////////////////////////////
    adGenOpticalADMProvOcmTotalPowerThresholdLow OBJECT-TYPE
        SYNTAX Integer32
        UNITS "Tenth of a dBm"
        MAX-ACCESS read-write
        STATUS current
        DESCRIPTION
                "This sets the lower limit of the OCM Power threshold.  Once reached,
                 an alarm will be issued"
        ::= { adGenOpticalADMProvInterfaceEntry 5 }

    -- /////////////////////////////////////////////////////////
    adGenOpticalADMProvTotalPowerThresholdHigh OBJECT-TYPE
        SYNTAX Integer32
        UNITS "Tenth of a dBm"
        MAX-ACCESS read-write
        STATUS current
        DESCRIPTION
                "This sets the upper limit of the Power threshold.  Once reached,
                 an alarm will be issued"
        ::= { adGenOpticalADMProvInterfaceEntry 6 }

    -- /////////////////////////////////////////////////////////
    adGenOpticalADMProvTotalPowerThresholdLow OBJECT-TYPE
        SYNTAX Integer32
        UNITS "Tenth of a dBm"
        MAX-ACCESS read-write
        STATUS current
        DESCRIPTION
                "This sets the lower limit of the Power threshold.  Once reached,
                 an alarm will be issued"
        ::= { adGenOpticalADMProvInterfaceEntry 7 }

    -- /////////////////////////////////////////////////////////
    adGenOpticalADMProvInsertionLoss OBJECT-TYPE
        SYNTAX Integer32
        UNITS "Tenth of a dBm"
        MAX-ACCESS read-write
        STATUS current
        DESCRIPTION
                "This sets the Insertion Loss of connected device."
        ::= { adGenOpticalADMProvInterfaceEntry 8 }

    -- /////////////////////////////////////////////////////////
    adGenOpticalADMProvGain OBJECT-TYPE
        SYNTAX Integer32
        UNITS "Tenth of a dBm"
        MAX-ACCESS read-write
        STATUS current
        DESCRIPTION
                "This OID sets the gain of the amplifier"
        ::= { adGenOpticalADMProvInterfaceEntry 9 }

-- //////////////////////////////////////////////////////////////////
--                 adGenOpticalADMProvInterfaceSupport
-- //////////////////////////////////////////////////////////////////
    adGenOpticalADMProvInterfaceSupportTable OBJECT-TYPE
        SYNTAX  SEQUENCE OF AdGenOpticalADMProvInterfaceSupportEntry
        MAX-ACCESS  not-accessible
        STATUS  current
        DESCRIPTION
                   "Provision Interface Support table."
        ::= { adGenOpticalADMProvInterface 2 }

    -- /////////////////////////////////////////////////////////
    adGenOpticalADMProvInterfaceSupportEntry OBJECT-TYPE
        SYNTAX  AdGenOpticalADMProvInterfaceSupportEntry
        MAX-ACCESS  not-accessible
        STATUS  current
        DESCRIPTION
                   "Table Entry."
        INDEX   { ifIndex }
        ::= { adGenOpticalADMProvInterfaceSupportTable 1 }

    -- /////////////////////////////////////////////////////////
    AdGenOpticalADMProvInterfaceSupportEntry ::=
        SEQUENCE {
                        adGenOpticalADMProvOcmTotalPowerThresholdHighMin  Integer32,
                        adGenOpticalADMProvOcmTotalPowerThresholdHighMax  Integer32,
                        adGenOpticalADMProvOcmTotalPowerThresholdLowMin   Integer32,
                        adGenOpticalADMProvOcmTotalPowerThresholdLowMax   Integer32,
                        adGenOpticalADMProvTotalPowerThresholdHighMin     Integer32,
                        adGenOpticalADMProvTotalPowerThresholdHighMax     Integer32,
                        adGenOpticalADMProvTotalPowerThresholdLowMin      Integer32,
                        adGenOpticalADMProvTotalPowerThresholdLowMax      Integer32
                 }
     -- /////////////////////////////////////////////////////////
    adGenOpticalADMProvOcmTotalPowerThresholdHighMin OBJECT-TYPE
        SYNTAX Integer32
        UNITS "Tenth of a dBm"
        MAX-ACCESS read-only
        STATUS current
        DESCRIPTION
                "This retrieves the minimum value of the OCM Total Power threshold high
                 that can be set"
        ::= { adGenOpticalADMProvInterfaceSupportEntry 1 }

     -- /////////////////////////////////////////////////////////
    adGenOpticalADMProvOcmTotalPowerThresholdHighMax OBJECT-TYPE
        SYNTAX Integer32
        UNITS "Tenth of a dBm"
        MAX-ACCESS read-only
        STATUS current
        DESCRIPTION
                "This retrieves the maximum value of the OCM Total Power threshold high
                 that can be set"
        ::= { adGenOpticalADMProvInterfaceSupportEntry 2 }

     -- /////////////////////////////////////////////////////////
    adGenOpticalADMProvOcmTotalPowerThresholdLowMin OBJECT-TYPE
        SYNTAX Integer32
        UNITS "Tenth of a dBm"
        MAX-ACCESS read-only
        STATUS current
        DESCRIPTION
                "This retrieves the minimum value of the OCM Total Power threshold low
                 that can be set"
        ::= { adGenOpticalADMProvInterfaceSupportEntry 3 }

     -- /////////////////////////////////////////////////////////
    adGenOpticalADMProvOcmTotalPowerThresholdLowMax OBJECT-TYPE
        SYNTAX Integer32
        UNITS "Tenth of a dBm"
        MAX-ACCESS read-only
        STATUS current
        DESCRIPTION
                "This retrieves the maximum value of the OCM Total Power threshold low
                 that can be set"
        ::= { adGenOpticalADMProvInterfaceSupportEntry 4 }

     -- /////////////////////////////////////////////////////////
    adGenOpticalADMProvTotalPowerThresholdHighMin OBJECT-TYPE
        SYNTAX Integer32
        UNITS "Tenth of a dBm"
        MAX-ACCESS read-only
        STATUS current
        DESCRIPTION
                "This retrieves the minimum value of the Total Power threshold high
                 that can be set"
        ::= { adGenOpticalADMProvInterfaceSupportEntry 5 }

     -- /////////////////////////////////////////////////////////
    adGenOpticalADMProvTotalPowerThresholdHighMax OBJECT-TYPE
        SYNTAX Integer32
        UNITS "Tenth of a dBm"
        MAX-ACCESS read-only
        STATUS current
        DESCRIPTION
                "This retrieves the maximum value of the Total Power threshold high
                 that can be set"
        ::= { adGenOpticalADMProvInterfaceSupportEntry 6 }

    -- /////////////////////////////////////////////////////////
    adGenOpticalADMProvTotalPowerThresholdLowMin OBJECT-TYPE
        SYNTAX Integer32
        UNITS "Tenth of a dBm"
        MAX-ACCESS read-only
        STATUS current
        DESCRIPTION
                "This retrieves the minimum value of the Total Power threshold low
                 that can be set"
        ::= { adGenOpticalADMProvInterfaceSupportEntry 7 }

     -- /////////////////////////////////////////////////////////
    adGenOpticalADMProvTotalPowerThresholdLowMax OBJECT-TYPE
        SYNTAX Integer32
        UNITS "Tenth of a dBm"
        MAX-ACCESS read-only
        STATUS current
        DESCRIPTION
                "This retrieves the maximum value of the Total Power threshold low
                 that can be set"
        ::= { adGenOpticalADMProvInterfaceSupportEntry 8 }


-- //////////////////////////////////////////////////////////////////
--                        adGenOpticalADMProvChannel
-- //////////////////////////////////////////////////////////////////
    adGenOpticalADMProvChannelTable OBJECT-TYPE
        SYNTAX  SEQUENCE OF AdGenOpticalADMProvChannelEntry
        MAX-ACCESS  not-accessible
        STATUS  current
        DESCRIPTION
                   "Provision Channel table."
        ::= { adGenOpticalADMProvChannel 1 }

    -- /////////////////////////////////////////////////////////
    adGenOpticalADMProvChannelEntry OBJECT-TYPE
        SYNTAX  AdGenOpticalADMProvChannelEntry
        MAX-ACCESS  not-accessible
        STATUS  current
        DESCRIPTION
                   "Table Entry."
        INDEX   { ifIndex, adGenOpticalADMProvChannelGridSpacing }
        ::= { adGenOpticalADMProvChannelTable 1 }

    -- /////////////////////////////////////////////////////////
    AdGenOpticalADMProvChannelEntry ::=
        SEQUENCE {
                        adGenOpticalADMProvChannelGridSpacing      INTEGER,
                        adGenOpticalADMProvChannelRowStatus        RowStatus,
                        adGenOpticalADMProvChannelDescription      OCTET STRING,
                        adGenOpticalADMProvChannelNumber           Integer32,
                        adGenOpticalADMProvChannelFrequency        Integer32,
                        adGenOpticalADMProvChannelWaveLength       Integer32,
                        adGenOpticalADMProvChannelPowerOverride    INTEGER,
                        adGenOpticalADMProvChannelPower            Integer32,
                        adGenOpticalADMProvChannelAttenuation      Integer32,
                        adGenOpticalADMProvChannelOcmThresholdHigh Integer32,
                        adGenOpticalADMProvChannelOcmThresholdLow  Integer32,
                        adGenOpticalADMProvChannelCrossConnect     OCTET STRING,
                        adGenOpticalADMProvChannelOperStatus       INTEGER,
                        adGenOpticalADMProvChannelAdminStatus      INTEGER
                 }
    -- /////////////////////////////////////////////////////////
    adGenOpticalADMProvChannelGridSpacing OBJECT-TYPE
    SYNTAX             INTEGER
                       {
                           fiftyGHz(50),
                           oneHundredGHz(100)
                       }
    MAX-ACCESS         not-accessible
    STATUS             current
    DESCRIPTION
       "This identifies the Channel Gridspacing associated with this ifIndex."
    ::= { adGenOpticalADMProvChannelEntry 1 }

    -- /////////////////////////////////////////////////////////
    adGenOpticalADMProvChannelRowStatus OBJECT-TYPE
    SYNTAX             RowStatus
    MAX-ACCESS         read-create
    STATUS             current
    DESCRIPTION
       "This object is used to create a new row or modify or delete an
        existing row in the Channel table."
    ::= { adGenOpticalADMProvChannelEntry 2 }

    -- /////////////////////////////////////////////////////////
    adGenOpticalADMProvChannelDescription OBJECT-TYPE
    SYNTAX             OCTET STRING (SIZE (1..50))
    MAX-ACCESS         read-create
    STATUS             current
    DESCRIPTION
       "A short description for this optical channel interface."
    ::= { adGenOpticalADMProvChannelEntry 3 }

    -- /////////////////////////////////////////////////////////
    adGenOpticalADMProvChannelNumber OBJECT-TYPE
    SYNTAX             Integer32
    MAX-ACCESS         read-only
    STATUS             current
    DESCRIPTION
       "This identifies the Channel Number associated with this ifIndex.
        Values are multiplied by 100.
        Example:
                Channel 17    will be 1700
                Channel 17.25 will be 1725
                Channel 60.5  will be 6050"
    ::= { adGenOpticalADMProvChannelEntry 4 }

    -- /////////////////////////////////////////////////////////
    adGenOpticalADMProvChannelFrequency OBJECT-TYPE
    SYNTAX             Integer32
    UNITS              "Tera Hz"
    MAX-ACCESS         read-only
    STATUS             current
    DESCRIPTION
       "This identifies the Channel Frequency associated with this ifIndex."
    ::= { adGenOpticalADMProvChannelEntry 5 }

    -- /////////////////////////////////////////////////////////
    adGenOpticalADMProvChannelWaveLength OBJECT-TYPE
    SYNTAX             Integer32
    UNITS              "Pico Meters"
    MAX-ACCESS         read-only
    STATUS             current
    DESCRIPTION
       "This identifies the Channel wavelength associated with this ifIndex."
    ::= { adGenOpticalADMProvChannelEntry 6 }

    -- /////////////////////////////////////////////////////////
    adGenOpticalADMProvChannelPowerOverride OBJECT-TYPE
    SYNTAX             INTEGER
                       {
                           disable(1),
                           power(2),
                           attenuation(3)
                       }
    MAX-ACCESS         read-create
    STATUS             current
    DESCRIPTION
       "This identifies the Channel Power control associated with this ifIndex.
        This value can be used to set override the power at the channel level."
    ::= { adGenOpticalADMProvChannelEntry 7 }

    -- /////////////////////////////////////////////////////////
    adGenOpticalADMProvChannelPower OBJECT-TYPE
    SYNTAX             Integer32
    UNITS              "Tenth of a dBm"
    MAX-ACCESS         read-create
    STATUS             current
    DESCRIPTION
       "This OID can be used to set the channel power level. This
        value will be used if auto power balancing is disabled. The
        channels coming in on ADD-IN or EXP-IN interfaces will be
        attenuated to this power level. This is only used when the
        power control override on the channel level is set to power mode."
    ::= { adGenOpticalADMProvChannelEntry 8 }

    -- /////////////////////////////////////////////////////////
    adGenOpticalADMProvChannelAttenuation OBJECT-TYPE
    SYNTAX             Integer32
    UNITS              "Tenth of a dB"
    MAX-ACCESS         read-create
    STATUS             current
    DESCRIPTION
       "This OID can be used to set the attenuation. This
        value will be used if auto power balancing is disabled and
        the module needs to operate in constant attenuation mode.
        This is only used when the power control override on
        the channel level is set to attenuation mode."
    ::= { adGenOpticalADMProvChannelEntry 9 }

    -- /////////////////////////////////////////////////////////
    adGenOpticalADMProvChannelOcmThresholdHigh OBJECT-TYPE
    SYNTAX             Integer32
    UNITS              "Tenth of a dBm"
    MAX-ACCESS         read-create
    STATUS             current
    DESCRIPTION
       "This sets the upper limit of the OCM Power threshold.  Once reached,
        an alarm will be issued"
    ::= { adGenOpticalADMProvChannelEntry 10 }

    -- /////////////////////////////////////////////////////////
    adGenOpticalADMProvChannelOcmThresholdLow OBJECT-TYPE
    SYNTAX             Integer32
    UNITS              "Tenth of a dBm"
    MAX-ACCESS         read-create
    STATUS             current
    DESCRIPTION
       "This sets the lower limit of the OCM Power threshold.  Once reached,
        an alarm will be issued"
    ::= { adGenOpticalADMProvChannelEntry 11 }

    -- /////////////////////////////////////////////////////////
    adGenOpticalADMProvChannelCrossConnect OBJECT-TYPE
    SYNTAX             OCTET STRING
    MAX-ACCESS         read-only
    STATUS             current
    DESCRIPTION
       "This string describes display the cross connect name that channel
        is part of. If the channel is not part of any cross connect then
        it will be set to None."
    ::= { adGenOpticalADMProvChannelEntry 12 }

    -- /////////////////////////////////////////////////////////
    adGenOpticalADMProvChannelOperStatus OBJECT-TYPE
    SYNTAX             INTEGER
                       {
                          up(1),
                          down(2)
                       }
    MAX-ACCESS         read-only
    STATUS             current
    DESCRIPTION
       "This shows the current oper status of the selected Channel."
    ::= { adGenOpticalADMProvChannelEntry 13 }

    -- /////////////////////////////////////////////////////////
    adGenOpticalADMProvChannelAdminStatus OBJECT-TYPE
    SYNTAX             INTEGER
                       {
                          up(1),
                          down(2),
                          testing(3)
                       }
    MAX-ACCESS         read-create
    STATUS             current
    DESCRIPTION
       "This sets the administration status of the selected Channel."
    ::= { adGenOpticalADMProvChannelEntry 14 }

-- //////////////////////////////////////////////////////////////////
--                        adGenOpticalADMProvChannelSupport
-- //////////////////////////////////////////////////////////////////
    adGenOpticalADMProvChannelSupportTable OBJECT-TYPE
        SYNTAX  SEQUENCE OF AdGenOpticalADMProvChannelSupportEntry
        MAX-ACCESS  not-accessible
        STATUS  current
        DESCRIPTION
                   "Provision Channel table."
        ::= { adGenOpticalADMProvChannel 2 }

    -- /////////////////////////////////////////////////////////
    adGenOpticalADMProvChannelSupportEntry OBJECT-TYPE
        SYNTAX  AdGenOpticalADMProvChannelSupportEntry
        MAX-ACCESS  not-accessible
        STATUS  current
        DESCRIPTION
                   "Table Entry."
        INDEX   { ifIndex, adGenOpticalADMProvChannelGridSpacing }
        ::= { adGenOpticalADMProvChannelSupportTable 1 }

    -- /////////////////////////////////////////////////////////
    AdGenOpticalADMProvChannelSupportEntry ::=
        SEQUENCE {
                        adGenOpticalADMProvChannelPowerMin            Integer32,
                        adGenOpticalADMProvChannelPowerMax            Integer32,
                        adGenOpticalADMProvChannelAttenuationMin      Integer32,
                        adGenOpticalADMProvChannelAttenuationMax      Integer32,
                        adGenOpticalADMProvChannelOcmThresholdHighMin Integer32,
                        adGenOpticalADMProvChannelOcmThresholdHighMax Integer32,
                        adGenOpticalADMProvChannelOcmThresholdLowMin  Integer32,
                        adGenOpticalADMProvChannelOcmThresholdLowMax  Integer32,
                        adGenOpticalADMProvChannelWaveLengthMin       Integer32,
                        adGenOpticalADMProvChannelWaveLengthMax       Integer32

                 }
    -- /////////////////////////////////////////////////////////
    adGenOpticalADMProvChannelPowerMin OBJECT-TYPE
    SYNTAX             Integer32
    UNITS              "Tenth of a dBm"
    MAX-ACCESS         read-only
    STATUS             current
    DESCRIPTION
       "This OID retrieves the minimum value of the power level which
       can be set"
    ::= { adGenOpticalADMProvChannelSupportEntry 1 }

     -- /////////////////////////////////////////////////////////
    adGenOpticalADMProvChannelPowerMax OBJECT-TYPE
    SYNTAX             Integer32
    UNITS              "Tenth of a dBm"
    MAX-ACCESS         read-only
    STATUS             current
    DESCRIPTION
       "This OID retrieves the maximum value of the power level which
       can be set"
    ::= { adGenOpticalADMProvChannelSupportEntry 2 }

    -- /////////////////////////////////////////////////////////
    adGenOpticalADMProvChannelAttenuationMin OBJECT-TYPE
    SYNTAX             Integer32
    UNITS              "Tenth of a dB"
    MAX-ACCESS         read-only
    STATUS             current
    DESCRIPTION
       "This OID retrieves the minimum value of the attenuation which
       can be set"
    ::= { adGenOpticalADMProvChannelSupportEntry 3 }

    -- /////////////////////////////////////////////////////////
    adGenOpticalADMProvChannelAttenuationMax OBJECT-TYPE
    SYNTAX             Integer32
    UNITS              "Tenth of a dB"
    MAX-ACCESS         read-only
    STATUS             current
    DESCRIPTION
       "This OID retrieves the maximum value of the attenuation which
       can be set"
    ::= { adGenOpticalADMProvChannelSupportEntry 4 }

    -- /////////////////////////////////////////////////////////
    adGenOpticalADMProvChannelOcmThresholdHighMin OBJECT-TYPE
    SYNTAX             Integer32
    UNITS              "Tenth of a dBm"
    MAX-ACCESS         read-only
    STATUS             current
    DESCRIPTION
       "This retreives the minimum value of the OCM Threshold high
        that can be set"
    ::= { adGenOpticalADMProvChannelSupportEntry 5 }

    -- /////////////////////////////////////////////////////////
    adGenOpticalADMProvChannelOcmThresholdHighMax OBJECT-TYPE
    SYNTAX             Integer32
    UNITS              "Tenth of a dBm"
    MAX-ACCESS         read-only
    STATUS             current
    DESCRIPTION
       "This retreives the maximum value of the OCM Threshold high
        that can be set"
    ::= { adGenOpticalADMProvChannelSupportEntry 6 }

    -- /////////////////////////////////////////////////////////
    adGenOpticalADMProvChannelOcmThresholdLowMin OBJECT-TYPE
    SYNTAX             Integer32
    UNITS              "Tenth of a dBm"
    MAX-ACCESS         read-only
    STATUS             current
    DESCRIPTION
       "This retreives the minimum value of the OCM Threshold low
        that can be set"
    ::= { adGenOpticalADMProvChannelSupportEntry 7 }

    -- /////////////////////////////////////////////////////////
    adGenOpticalADMProvChannelOcmThresholdLowMax OBJECT-TYPE
    SYNTAX             Integer32
    UNITS              "Tenth of a dBm"
    MAX-ACCESS         read-only
    STATUS             current
    DESCRIPTION
       "This retreives the maximum value of the OCM Threshold low
        that can be set"
    ::= { adGenOpticalADMProvChannelSupportEntry 8 }

    -- /////////////////////////////////////////////////////////
    adGenOpticalADMProvChannelWaveLengthMin OBJECT-TYPE
    SYNTAX             Integer32
    UNITS              "PicoMeter"
    MAX-ACCESS         read-only
    STATUS             current
    DESCRIPTION
       "This retreives the minimum supported wavelength value."
    ::= { adGenOpticalADMProvChannelSupportEntry 9 }

    -- /////////////////////////////////////////////////////////
    adGenOpticalADMProvChannelWaveLengthMax OBJECT-TYPE
    SYNTAX             Integer32
    UNITS              "PicoMeter"
    MAX-ACCESS         read-only
    STATUS             current
    DESCRIPTION
        "This retreives the maximum supported wavelength value."
    ::= { adGenOpticalADMProvChannelSupportEntry 10 }

-- //////////////////////////////////////////////////////////////////
--                        adGenOpticalADMProvError
-- //////////////////////////////////////////////////////////////////
    adGenOpticalADMProvErrorTable OBJECT-TYPE
        SYNTAX  SEQUENCE OF AdGenOpticalADMProvErrorEntry
        MAX-ACCESS  not-accessible
        STATUS  current
        DESCRIPTION
                   "Provision Channel Error table."
        ::= { adGenOpticalADMProvError 1 }

    -- /////////////////////////////////////////////////////////
    adGenOpticalADMProvErrorEntry OBJECT-TYPE
        SYNTAX  AdGenOpticalADMProvErrorEntry
        MAX-ACCESS  not-accessible
        STATUS  current
        DESCRIPTION
                   "Table Entry."
        INDEX   { adGenSlotInfoIndex }
        ::= { adGenOpticalADMProvErrorTable 1 }

    -- /////////////////////////////////////////////////////////
    AdGenOpticalADMProvErrorEntry ::=
        SEQUENCE {
                        adGenOpticalADMProvChannelError        DisplayString,
                        adGenOpticalADMProvCrossConnectError   DisplayString
                 }
    -- /////////////////////////////////////////////////////////
    adGenOpticalADMProvChannelError OBJECT-TYPE
    SYNTAX             DisplayString
    MAX-ACCESS         read-only
    STATUS             current
    DESCRIPTION
       "Returns information about the last error for the Channel
        creation.  This is SLOT indexed.  If row creation fails,
        this string will provide details about why the row could
        not be created."
    ::= { adGenOpticalADMProvErrorEntry 1 }

    -- /////////////////////////////////////////////////////////
    adGenOpticalADMProvCrossConnectError OBJECT-TYPE
    SYNTAX             DisplayString
    MAX-ACCESS         read-only
    STATUS             current
    DESCRIPTION
       "Returns information about the last error for the Cross connect
        creation.  This is SLOT indexed.  If row creation fails,
        this string will provide details about why the row could
        not be created."
    ::= { adGenOpticalADMProvErrorEntry 2 }

-- //////////////////////////////////////////////////////////////////
--                        adGenOpticalADMCrossConnect
-- //////////////////////////////////////////////////////////////////
    adGenOpticalADMCrossConnectTable OBJECT-TYPE
        SYNTAX  SEQUENCE OF AdGenOpticalADMCrossConnectEntry
        MAX-ACCESS  not-accessible
        STATUS  current
        DESCRIPTION
                   "Cross Connect table."
        ::= { adGenOpticalADMCrossConnect 1 }

    -- /////////////////////////////////////////////////////////
    adGenOpticalADMCrossConnectEntry OBJECT-TYPE
        SYNTAX  AdGenOpticalADMCrossConnectEntry
        MAX-ACCESS  not-accessible
        STATUS  current
        DESCRIPTION
                   "Table Entry."
        INDEX   { adGenSlotInfoIndex, IMPLIED adGenOpticalADMCrossConnectName }
        ::= { adGenOpticalADMCrossConnectTable 1 }

    -- /////////////////////////////////////////////////////////
    AdGenOpticalADMCrossConnectEntry ::=
        SEQUENCE {
                        adGenOpticalADMCrossConnectName                   DisplayString,
                        adGenOpticalADMCrossConnectRowStatus              RowStatus,
                        adGenOpticalADMCrossConnectSrcChannelIfIndex      InterfaceIndex,
                        adGenOpticalADMCrossConnectSrcChannelGridSpacing  INTEGER,
                        adGenOpticalADMCrossConnectDstInterfaceIfIndex    InterfaceIndex,
                        adGenOpticalADMCrossConnectOperationStatus        INTEGER,
                        adGenOpticalADMCrossConnectError                  DisplayString,
                        adGenOpticalADMCrossConnectAdminStatus            INTEGER
                 }
    -- /////////////////////////////////////////////////////////
    adGenOpticalADMCrossConnectName OBJECT-TYPE
    SYNTAX             DisplayString (SIZE (1..50))
    MAX-ACCESS         not-accessible
    STATUS             current
    DESCRIPTION
       "This OID specifies the cross connect name. This is a unique name that
        identifies the cross connect in that slot."
    ::= { adGenOpticalADMCrossConnectEntry 1 }

    -- /////////////////////////////////////////////////////////
    adGenOpticalADMCrossConnectRowStatus OBJECT-TYPE
    SYNTAX             RowStatus
    MAX-ACCESS         read-create
    STATUS             current
    DESCRIPTION
       "This object is used to create a new row or modify or delete an
        existing row in the Cross Connect table."
    ::= { adGenOpticalADMCrossConnectEntry 2 }

    -- /////////////////////////////////////////////////////////
    adGenOpticalADMCrossConnectSrcChannelIfIndex OBJECT-TYPE
    SYNTAX             InterfaceIndex
    MAX-ACCESS         read-create
    STATUS             current
    DESCRIPTION
       "This ifIndex OID specifies the source slot, optical interface and channel."
    ::= { adGenOpticalADMCrossConnectEntry 3 }

    -- /////////////////////////////////////////////////////////
    adGenOpticalADMCrossConnectSrcChannelGridSpacing OBJECT-TYPE
    SYNTAX             INTEGER
                       {
                           fiftyGHz(50),
                           oneHundredGHz(100)
                       }
    MAX-ACCESS         read-create
    STATUS             current
    DESCRIPTION
       "This OID specifies the source gridspacing."
    ::= { adGenOpticalADMCrossConnectEntry 4 }

    -- /////////////////////////////////////////////////////////
    adGenOpticalADMCrossConnectDstInterfaceIfIndex OBJECT-TYPE
    SYNTAX             InterfaceIndex
    MAX-ACCESS         read-create
    STATUS             current
    DESCRIPTION
       "This ifIndex OID specifies the destination slot and optical interface."
    ::= { adGenOpticalADMCrossConnectEntry 5 }

    -- /////////////////////////////////////////////////////////
    adGenOpticalADMCrossConnectOperationStatus OBJECT-TYPE
    SYNTAX             INTEGER
                       {
                           up(1),
                           down(2)
                       }
    MAX-ACCESS         read-only
    STATUS             current
    DESCRIPTION
       "This OID displays the current Operation Status of this Cross Connect."
    ::= { adGenOpticalADMCrossConnectEntry 6 }

    -- /////////////////////////////////////////////////////////
    adGenOpticalADMCrossConnectError OBJECT-TYPE
    SYNTAX             DisplayString
    MAX-ACCESS         read-only
    STATUS             current
    DESCRIPTION
       "This OID displays the error in creating the cross connect.  Also during
        operation, this will display any errors that caused operation status to
        go down."
    ::= { adGenOpticalADMCrossConnectEntry 7 }

    -- /////////////////////////////////////////////////////////
    adGenOpticalADMCrossConnectAdminStatus OBJECT-TYPE
    SYNTAX             INTEGER
                       {
                          up(1),
                          down(2),
                          testing(3)
                       }
    MAX-ACCESS         read-create
    STATUS             current
    DESCRIPTION
       "This sets the administration status of the selected Channel."
    ::= { adGenOpticalADMCrossConnectEntry 8 }

-- //////////////////////////////////////////////////////////////////
--                        adGenOpticalInterfaceADMStatus
-- //////////////////////////////////////////////////////////////////
    adGenOpticalADMInterfaceStatusTable OBJECT-TYPE
        SYNTAX  SEQUENCE OF AdGenOpticalADMInterfaceStatusEntry
        MAX-ACCESS  not-accessible
        STATUS  current
        DESCRIPTION
                   "Status table."
        ::= { adGenOpticalADMStatus 1 }

    -- /////////////////////////////////////////////////////////
    adGenOpticalADMInterfaceStatusEntry OBJECT-TYPE
        SYNTAX  AdGenOpticalADMInterfaceStatusEntry
        MAX-ACCESS  not-accessible
        STATUS  current
        DESCRIPTION
                   "Table Interface Entry."
        INDEX   { ifIndex }
        ::= { adGenOpticalADMInterfaceStatusTable 1 }

    -- /////////////////////////////////////////////////////////
    AdGenOpticalADMInterfaceStatusEntry ::=
        SEQUENCE  {
                        adGenOpticalADMInterfaceStatOcmTotalPower         Integer32,
                        adGenOpticalADMInterfaceStatTotalPower            Integer32,
                        adGenOpticalADMInterfaceStatActualGain            Integer32,
                        adGenOpticalADMInterfaceStatInputPower            Integer32
                  }
    -- /////////////////////////////////////////////////////////
    adGenOpticalADMInterfaceStatOcmTotalPower OBJECT-TYPE
    SYNTAX             Integer32
    UNITS              "Tenth of a dBm"
    MAX-ACCESS         read-only
    STATUS             current
    DESCRIPTION
       "This displays the Total OCM current power value of the selected index."
    ::= { adGenOpticalADMInterfaceStatusEntry 1 }
    -- /////////////////////////////////////////////////////////
    adGenOpticalADMInterfaceStatTotalPower OBJECT-TYPE
    SYNTAX             Integer32
    UNITS              "Tenth of a dBm"
    MAX-ACCESS         read-only
    STATUS             current
    DESCRIPTION
       "This displays the Total current power value of the selected index."
    ::= { adGenOpticalADMInterfaceStatusEntry 2 }

    -- /////////////////////////////////////////////////////////
    adGenOpticalADMInterfaceStatActualGain OBJECT-TYPE
    SYNTAX             Integer32
    UNITS              "Tenth of a dBm"
    MAX-ACCESS         read-only
    STATUS             current
    DESCRIPTION
       "This displays the power gain of the selected index."
    ::= { adGenOpticalADMInterfaceStatusEntry 3 }

    -- /////////////////////////////////////////////////////////
    adGenOpticalADMInterfaceStatInputPower OBJECT-TYPE
    SYNTAX             Integer32
    UNITS              "Tenth of a dBm"
    MAX-ACCESS         read-only
    STATUS             current
    DESCRIPTION
       "This displays the input power of the selected index."
    ::= { adGenOpticalADMInterfaceStatusEntry 4 }

-- //////////////////////////////////////////////////////////////////
--                        adGenOpticalADMChannelStatus
-- //////////////////////////////////////////////////////////////////
    adGenOpticalADMChannelStatusTable OBJECT-TYPE
        SYNTAX  SEQUENCE OF AdGenOpticalADMChannelStatusEntry
        MAX-ACCESS  not-accessible
        STATUS  current
        DESCRIPTION
                   "Channel Status table."
        ::= { adGenOpticalADMStatus 2 }

    -- /////////////////////////////////////////////////////////
    adGenOpticalADMChannelStatusEntry OBJECT-TYPE
        SYNTAX  AdGenOpticalADMChannelStatusEntry
        MAX-ACCESS  not-accessible
        STATUS  current
        DESCRIPTION
                   "Table Channel Entry."
        INDEX   { ifIndex, adGenOpticalADMProvChannelGridSpacing }
        ::= { adGenOpticalADMChannelStatusTable 1 }

    -- /////////////////////////////////////////////////////////
    AdGenOpticalADMChannelStatusEntry ::=
        SEQUENCE  {
                        adGenOpticalADMChannelStatOcmChannelPower       Integer32,
                        adGenOpticalADMChannelStatAttenuation           Integer32
                  }
     -- /////////////////////////////////////////////////////////
    adGenOpticalADMChannelStatOcmChannelPower OBJECT-TYPE
    SYNTAX             Integer32
    UNITS              "Tenth of a dBm"
    MAX-ACCESS         read-only
    STATUS             current
    DESCRIPTION
       "This displays the Channel current power value of the selected index."
    ::= { adGenOpticalADMChannelStatusEntry 1 }

    -- /////////////////////////////////////////////////////////
    adGenOpticalADMChannelStatAttenuation OBJECT-TYPE
    SYNTAX             Integer32
    UNITS              "Tenth of a dB"
    MAX-ACCESS         read-only
    STATUS             current
    DESCRIPTION
       "This displays the Channel current attenuation value of the selected index."
    ::= { adGenOpticalADMChannelStatusEntry 2 }

-- //////////////////////////////////////////////////////////////////

-- //////////////////////////////////////////////////////////////////
-- Alarm Traps
-- //////////////////////////////////////////////////////////////////
adGenOpticalADMAlmComInLOSActiveClear    NOTIFICATION-TYPE
   OBJECTS  {
                adTrapInformSeqNum,
                sysName,
                adGenSlotInfoIndex,
                ifIndex
            }
    STATUS          current
    DESCRIPTION     "Composite-IN Loss of Signal Cleared."

    --#TYPE         "Composite-IN Loss of Signal Cleared."
    --#SUMMARY      "Composite-IN Loss of Signal"
    --#SUMMARY      "Cleared at shelf: %s, slot: %d, interface %d"
    --#ARGUMENTS    {1,2,3}
    --#SEVERITY     CRITICAL
    --#GENERIC      6
    --#CATEGORY     "Alarm Events"
    --#SOURCE_ID    "A"
    --#TIMEINDEX    0
    ::= {adGenOpticalADMEvents 1}

adGenOpticalADMAlmComInLOSActive   NOTIFICATION-TYPE
   OBJECTS  {
                adTrapInformSeqNum,
                sysName,
                adGenSlotInfoIndex,
                ifIndex
            }
    STATUS          current
    DESCRIPTION     "Composite-IN Loss of Signal Active."

    --#TYPE         "Composite-IN Loss of Signal Active."
    --#SUMMARY      "Composite-IN Loss of Signal"
    --#SUMMARY      "Activated at shelf: %s, slot: %d, interface %d"
    --#ARGUMENTS    {1,2,3}
    --#SEVERITY     CRITICAL
    --#GENERIC      6
    --#CATEGORY     "Alarm Events"
    --#SOURCE_ID    "A"
    --#TIMEINDEX    0
    ::= {adGenOpticalADMEvents 2}

-- //////////////////////////////////////////////////////////////////
adGenOpticalADMAlmComInTotalPwrTHHiActiveClear    NOTIFICATION-TYPE
   OBJECTS  {
                adTrapInformSeqNum,
                sysName,
                adGenSlotInfoIndex,
                ifIndex
            }
    STATUS          current
    DESCRIPTION     "Composite-IN Total Power Threshold HI Cleared."

    --#TYPE         "Composite-IN Total Power Threshold HI Cleared."
    --#SUMMARY      "Composite-IN Total Power Threshold HI"
    --#SUMMARY      "Cleared at shelf: %s, slot: %d, interface %d"
    --#ARGUMENTS    {1,2,3}
    --#SEVERITY     MINOR
    --#GENERIC      6
    --#CATEGORY     "Alarm Events"
    --#SOURCE_ID    "A"
    --#TIMEINDEX    0
    ::= {adGenOpticalADMEvents 3}

adGenOpticalADMAlmComInTotalPwrTHHiActive   NOTIFICATION-TYPE
   OBJECTS  {
                adTrapInformSeqNum,
                sysName,
                adGenSlotInfoIndex,
                ifIndex
            }
    STATUS          current
    DESCRIPTION     "Composite-IN Total Power Threshold HI Active."

    --#TYPE         "Composite-IN Total Power Threshold HI Active."
    --#SUMMARY      "Composite-IN Total Power Threshold HI"
    --#SUMMARY      "Activated at shelf: %s, slot: %d, interface %d"
    --#ARGUMENTS    {1,2,3}
    --#SEVERITY     MINOR
    --#GENERIC      6
    --#CATEGORY     "Alarm Events"
    --#SOURCE_ID    "A"
    --#TIMEINDEX    0
    ::= {adGenOpticalADMEvents 4}


-- //////////////////////////////////////////////////////////////////
adGenOpticalADMAlmComInTotalPwrTHLowActiveClear    NOTIFICATION-TYPE
   OBJECTS  {
                adTrapInformSeqNum,
                sysName,
                adGenSlotInfoIndex,
                ifIndex
            }
    STATUS          current
    DESCRIPTION     "Composite-IN Total Power Threshold Low Cleared."

    --#TYPE         "Composite-IN Total Power Threshold Low Cleared."
    --#SUMMARY      "Composite-IN Total Power Threshold Low"
    --#SUMMARY      "Cleared at shelf: %s, slot: %d, interface %d"
    --#ARGUMENTS    {1,2,3}
    --#SEVERITY     MINOR
    --#GENERIC      6
    --#CATEGORY     "Alarm Events"
    --#SOURCE_ID    "A"
    --#TIMEINDEX    0
    ::= {adGenOpticalADMEvents 5}

adGenOpticalADMAlmComInTotalPwrTHLowActive   NOTIFICATION-TYPE
   OBJECTS  {
                adTrapInformSeqNum,
                sysName,
                adGenSlotInfoIndex,
                ifIndex
            }
    STATUS          current
    DESCRIPTION     "Composite-IN Total Power Threshold Low Active."

    --#TYPE         "Composite-IN Total Power Threshold Low Active."
    --#SUMMARY      "Composite-IN Total Power Threshold Low"
    --#SUMMARY      "Activated at shelf: %s, slot: %d, interface %d"
    --#ARGUMENTS    {1,2,3}
    --#SEVERITY     MINOR
    --#GENERIC      6
    --#CATEGORY     "Alarm Events"
    --#SOURCE_ID    "A"
    --#TIMEINDEX    0
    ::= {adGenOpticalADMEvents 6}

-- //////////////////////////////////////////////////////////////////
adGenOpticalADMAlmComInOcmTotalPwrTHHiActiveClear    NOTIFICATION-TYPE
   OBJECTS  {
                adTrapInformSeqNum,
                sysName,
                adGenSlotInfoIndex,
                ifIndex
            }
    STATUS          current
    DESCRIPTION     "Composite-IN OCM Total Power Threshold HI Cleared."

    --#TYPE         "Composite-IN OCM Total Power Threshold HI Cleared."
    --#SUMMARY      "Composite-IN OCM Total Power Threshold HI"
    --#SUMMARY      "Cleared at shelf: %s, slot: %d, interface %d"
    --#ARGUMENTS    {1,2,3}
    --#SEVERITY     MINOR
    --#GENERIC      6
    --#CATEGORY     "Alarm Events"
    --#SOURCE_ID    "A"
    --#TIMEINDEX    0
    ::= {adGenOpticalADMEvents 7}

adGenOpticalADMAlmComInOcmTotalPwrTHHiActive   NOTIFICATION-TYPE
   OBJECTS  {
                adTrapInformSeqNum,
                sysName,
                adGenSlotInfoIndex,
                ifIndex
            }
    STATUS          current
    DESCRIPTION     "Composite-IN OCM Total Power Threshold HI Active."

    --#TYPE         "Composite-IN OCM Total Power Threshold HI Active."
    --#SUMMARY      "Composite-IN OCM Total Power Threshold HI"
    --#SUMMARY      "Activated at shelf: %s, slot: %d, interface %d"
    --#ARGUMENTS    {1,2,3}
    --#SEVERITY     MINOR
    --#GENERIC      6
    --#CATEGORY     "Alarm Events"
    --#SOURCE_ID    "A"
    --#TIMEINDEX    0
    ::= {adGenOpticalADMEvents 8}

-- //////////////////////////////////////////////////////////////////
adGenOpticalADMAlmComInOcmTotalPwrTHLowActiveClear    NOTIFICATION-TYPE
   OBJECTS  {
                adTrapInformSeqNum,
                sysName,
                adGenSlotInfoIndex,
                ifIndex
            }
    STATUS          current
    DESCRIPTION     "Composite-IN Total OCM Power Threshold LOW Cleared."

    --#TYPE         "Composite-IN OCM Total Power Threshold LOW Cleared."
    --#SUMMARY      "Composite-IN OCM Total Power Threshold LOW"
    --#SUMMARY      "Cleared at shelf: %s, slot: %d, interface %d"
    --#ARGUMENTS    {1,2,3}
    --#SEVERITY     MINOR
    --#GENERIC      6
    --#CATEGORY     "Alarm Events"
    --#SOURCE_ID    "A"
    --#TIMEINDEX    0
    ::= {adGenOpticalADMEvents 9}

adGenOpticalADMAlmComInOcmTotalPwrTHLowActive   NOTIFICATION-TYPE
   OBJECTS  {
                adTrapInformSeqNum,
                sysName,
                adGenSlotInfoIndex,
                ifIndex
            }
    STATUS          current
    DESCRIPTION     "Composite-IN OCM Total Power Threshold LOW Active."

    --#TYPE         "Composite-IN OCM Total Power Threshold LOW Active."
    --#SUMMARY      "Composite-IN OCM Total Power Threshold LOW"
    --#SUMMARY      "Activated at shelf: %s, slot: %d, interface %d"
    --#ARGUMENTS    {1,2,3}
    --#SEVERITY     MINOR
    --#GENERIC      6
    --#CATEGORY     "Alarm Events"
    --#SOURCE_ID    "A"
    --#TIMEINDEX    0
    ::= {adGenOpticalADMEvents 10}

-- //////////////////////////////////////////////////////////////////
adGenOpticalADMAlmComOutOcmTotalPwrTHHiActiveClear    NOTIFICATION-TYPE
   OBJECTS  {
                adTrapInformSeqNum,
                sysName,
                adGenSlotInfoIndex,
                ifIndex
            }
    STATUS          current
    DESCRIPTION     "Composite-OUT OCM Total Power Threshold HI Cleared."

    --#TYPE         "Composite-OUT OCM Total Power Threshold HI Cleared."
    --#SUMMARY      "Composite-OUT OCM Total Power Threshold HI"
    --#SUMMARY      "Cleared at shelf: %s, slot: %d, interface %d"
    --#ARGUMENTS    {1,2,3}
    --#SEVERITY     MINOR
    --#GENERIC      6
    --#CATEGORY     "Alarm Events"
    --#SOURCE_ID    "A"
    --#TIMEINDEX    0
    ::= {adGenOpticalADMEvents 11}

adGenOpticalADMAlmComOutOcmTotalPwrTHHiActive   NOTIFICATION-TYPE
   OBJECTS  {
                adTrapInformSeqNum,
                sysName,
                adGenSlotInfoIndex,
                ifIndex
            }
    STATUS          current
    DESCRIPTION     "Composite-OUT OCM Total Power Threshold HI Active."

    --#TYPE         "Composite-OUT OCM Total Power Threshold HI Active."
    --#SUMMARY      "Composite-OUT OCM Total Power Threshold HI"
    --#SUMMARY      "Activated at shelf: %s, slot: %d, interface %d"
    --#ARGUMENTS    {1,2,3}
    --#SEVERITY     MINOR
    --#GENERIC      6
    --#CATEGORY     "Alarm Events"
    --#SOURCE_ID    "A"
    --#TIMEINDEX    0
    ::= {adGenOpticalADMEvents 12}
-- //////////////////////////////////////////////////////////////////
adGenOpticalADMAlmComOutOcmTotalPwrTHLowActiveClear    NOTIFICATION-TYPE
   OBJECTS  {
                adTrapInformSeqNum,
                sysName,
                adGenSlotInfoIndex,
                ifIndex
            }
    STATUS          current
    DESCRIPTION     "Composite-OUT OCM Total Power Threshold LOW Cleared."

    --#TYPE         "Composite-OUT OCM Total Power Threshold LOW Cleared."
    --#SUMMARY      "Composite-OUT OCM Total Power Threshold LOW"
    --#SUMMARY      "Cleared at shelf: %s, slot: %d, interface %d"
    --#ARGUMENTS    {1,2,3}
    --#SEVERITY     MINOR
    --#GENERIC      6
    --#CATEGORY     "Alarm Events"
    --#SOURCE_ID    "A"
    --#TIMEINDEX    0
    ::= {adGenOpticalADMEvents 13}

adGenOpticalADMAlmComOutOcmTotalPwrTHLowActive   NOTIFICATION-TYPE
   OBJECTS  {
                adTrapInformSeqNum,
                sysName,
                adGenSlotInfoIndex,
                ifIndex
            }
    STATUS          current
    DESCRIPTION     "Composite-OUT OCM Total Power Threshold LOW Active."

    --#TYPE         "Composite-OUT OCM Total Power Threshold LOW Active."
    --#SUMMARY      "Composite-OUT OCM Total Power Threshold LOW"
    --#SUMMARY      "Activated at shelf: %s, slot: %d, interface %d"
    --#ARGUMENTS    {1,2,3}
    --#SEVERITY     MINOR
    --#GENERIC      6
    --#CATEGORY     "Alarm Events"
    --#SOURCE_ID    "A"
    --#TIMEINDEX    0
    ::= {adGenOpticalADMEvents 14}
-- //////////////////////////////////////////////////////////////////
adGenOpticalADMAlmChannelComInOcmPwrTHHiActiveClear    NOTIFICATION-TYPE
   OBJECTS  {
                adTrapInformSeqNum,
                sysName,
                adGenSlotInfoIndex,
                ifIndex
            }
    STATUS          current
    DESCRIPTION     "Composite-IN Channel OCM Power Threshold HI Cleared."

    --#TYPE         "Composite-IN Channel OCM Power Threshold HI Cleared."
    --#SUMMARY      "Composite-IN Channel OCM Power Threshold HI"
    --#SUMMARY      "Cleared at shelf: %s, slot: %d, com-in channel %d"
    --#ARGUMENTS    {1,2,3}
    --#SEVERITY     MINOR
    --#GENERIC      6
    --#CATEGORY     "Alarm Events"
    --#SOURCE_ID    "A"
    --#TIMEINDEX    0
    ::= {adGenOpticalADMEvents 15}

adGenOpticalADMAlmChannelComInOcmPwrTHHiActive   NOTIFICATION-TYPE
   OBJECTS  {
                adTrapInformSeqNum,
                sysName,
                adGenSlotInfoIndex,
                ifIndex
            }
    STATUS          current
    DESCRIPTION     "Composite-IN Channel OCM Power Threshold HI Active."

    --#TYPE         "Composite-IN Channel OCM Power Threshold HI Active."
    --#SUMMARY      "Composite-IN Channel OCM Power Threshold HI"
    --#SUMMARY      "Activated at shelf: %s, slot: %d, com-in channel %d"
    --#ARGUMENTS    {1,2,3}
    --#SEVERITY     MINOR
    --#GENERIC      6
    --#CATEGORY     "Alarm Events"
    --#SOURCE_ID    "A"
    --#TIMEINDEX    0
    ::= {adGenOpticalADMEvents 16}

-- //////////////////////////////////////////////////////////////////
adGenOpticalADMAlmChannelComInOcmPwrTHLowActiveClear    NOTIFICATION-TYPE
   OBJECTS  {
                adTrapInformSeqNum,
                sysName,
                adGenSlotInfoIndex,
                ifIndex
            }
    STATUS          current
    DESCRIPTION     "Composite-IN Channel OCM Power Threshold LOW Cleared."

    --#TYPE         "Composite-IN Channel OCM Power Threshold LOW Cleared."
    --#SUMMARY      "Composite-IN Channel OCM Power Threshold LOW"
    --#SUMMARY      "Cleared at shelf: %s, slot: %d, com-in channel %d"
    --#ARGUMENTS    {1,2,3}
    --#SEVERITY     MINOR
    --#GENERIC      6
    --#CATEGORY     "Alarm Events"
    --#SOURCE_ID    "A"
    --#TIMEINDEX    0
    ::= {adGenOpticalADMEvents 17}

adGenOpticalADMAlmChannelComInOcmPwrTHLowActive   NOTIFICATION-TYPE
   OBJECTS  {
                adTrapInformSeqNum,
                sysName,
                adGenSlotInfoIndex,
                ifIndex
            }
    STATUS          current
    DESCRIPTION     "Composite-IN Channel OCM Power Threshold LOW Active."

    --#TYPE         "Composite-IN Channel OCM Power Threshold LOW Active."
    --#SUMMARY      "Composite-IN Channel OCM Power Threshold LOW"
    --#SUMMARY      "Activated at shelf: %s, slot: %d, com-in channel %d"
    --#ARGUMENTS    {1,2,3}
    --#SEVERITY     MINOR
    --#GENERIC      6
    --#CATEGORY     "Alarm Events"
    --#SOURCE_ID    "A"
    --#TIMEINDEX    0
    ::= {adGenOpticalADMEvents 18}

-- //////////////////////////////////////////////////////////////////
adGenOpticalADMAlmChannelComOutOcmPwrTHHiActiveClear    NOTIFICATION-TYPE
   OBJECTS  {
                adTrapInformSeqNum,
                sysName,
                adGenSlotInfoIndex,
                ifIndex
            }
    STATUS          current
    DESCRIPTION     "Composite-OUT Channel OCM Power Threshold HI Cleared."

    --#TYPE         "Composite-OUT Channel OCM Power Threshold HI Cleared."
    --#SUMMARY      "Composite-OUT Channel OCM Power Threshold HI"
    --#SUMMARY      "Cleared at shelf: %s, slot: %d, com-out channel %d"
    --#ARGUMENTS    {1,2,3}
    --#SEVERITY     MINOR
    --#GENERIC      6
    --#CATEGORY     "Alarm Events"
    --#SOURCE_ID    "A"
    --#TIMEINDEX    0
    ::= {adGenOpticalADMEvents 19}

adGenOpticalADMAlmChannelComOutOcmPwrTHHiActive   NOTIFICATION-TYPE
   OBJECTS  {
                adTrapInformSeqNum,
                sysName,
                adGenSlotInfoIndex,
                ifIndex
            }
    STATUS          current
    DESCRIPTION     "Composite-OUT Channel OCM Power Threshold HI Active."

    --#TYPE         "Composite-OUT Channel OCM Power Threshold HI Active."
    --#SUMMARY      "Composite-OUT Channel OCM Power Threshold HI"
    --#SUMMARY      "Activated at shelf: %s, slot: %d, com-out channel %d"
    --#ARGUMENTS    {1,2,3}
    --#SEVERITY     MINOR
    --#GENERIC      6
    --#CATEGORY     "Alarm Events"
    --#SOURCE_ID    "A"
    --#TIMEINDEX    0
    ::= {adGenOpticalADMEvents 20}

-- //////////////////////////////////////////////////////////////////
adGenOpticalADMAlmChannelComOutOcmPwrTHLowActiveClear    NOTIFICATION-TYPE
   OBJECTS  {
                adTrapInformSeqNum,
                sysName,
                adGenSlotInfoIndex,
                ifIndex
            }
    STATUS          current
    DESCRIPTION     "Composite-OUT Channel OCM Power Threshold LOW Cleared."

    --#TYPE         "Composite-OUT Channel OCM Power Threshold LOW Cleared."
    --#SUMMARY      "Composite-OUT Channel OCM Power Threshold LOW"
    --#SUMMARY      "Cleared at shelf: %s, slot: %d, com-out channel %d"
    --#ARGUMENTS    {1,2,3}
    --#SEVERITY     MINOR
    --#GENERIC      6
    --#CATEGORY     "Alarm Events"
    --#SOURCE_ID    "A"
    --#TIMEINDEX    0
    ::= {adGenOpticalADMEvents 21}

adGenOpticalADMAlmChannelComOutOcmPwrTHLowActive   NOTIFICATION-TYPE
   OBJECTS  {
                adTrapInformSeqNum,
                sysName,
                adGenSlotInfoIndex,
                ifIndex
            }
    STATUS          current
    DESCRIPTION     "Composite-OUT Channel OCM Power Threshold LOW Active."

    --#TYPE         "Composite-OUT Channel OCM Power Threshold LOW Active."
    --#SUMMARY      "Composite-OUT Channel OCM Power Threshold LOW"
    --#SUMMARY      "Activated at shelf: %s, slot: %d, com-out channel %d"
    --#ARGUMENTS    {1,2,3}
    --#SEVERITY     MINOR
    --#GENERIC      6
    --#CATEGORY     "Alarm Events"
    --#SOURCE_ID    "A"
    --#TIMEINDEX    0
    ::= {adGenOpticalADMEvents 22}

-- //////////////////////////////////////////////////////////////////
adGenOpticalADMAlmChannelComOutAutoOORHiActiveClear    NOTIFICATION-TYPE
   OBJECTS  {
                adTrapInformSeqNum,
                sysName,
                adGenSlotInfoIndex,
                ifIndex
            }
    STATUS          current
    DESCRIPTION     "Composite-OUT Channel Auto Power Out Of Range HI Cleared."

    --#TYPE         "Composite-OUT Channel Auto Power Out Of Range HI Cleared."
    --#SUMMARY      "Composite-OUT Channel Auto Power Out Of Range HI."
    --#SUMMARY      "Cleared at shelf: %s, slot: %d, com-out channel %d"
    --#ARGUMENTS    {1,2,3}
    --#SEVERITY     MINOR
    --#GENERIC      6
    --#CATEGORY     "Alarm Events"
    --#SOURCE_ID    "A"
    --#TIMEINDEX    0
    ::= {adGenOpticalADMEvents 23}

adGenOpticalADMAlmChannelComOutAutoOORHiActive   NOTIFICATION-TYPE
   OBJECTS  {
                adTrapInformSeqNum,
                sysName,
                adGenSlotInfoIndex,
                ifIndex
            }
    STATUS          current
    DESCRIPTION     "Composite-OUT Channel Auto Power Out Of Range HI Active."

    --#TYPE         "Composite-OUT Channel Auto Power Out Of Range HI Active."
    --#SUMMARY      "Composite-OUT Channel Auto Power Out Of Range HI."
    --#SUMMARY      "Activated at shelf: %s, slot: %d, com-out channel %d"
    --#ARGUMENTS    {1,2,3}
    --#SEVERITY     MINOR
    --#GENERIC      6
    --#CATEGORY     "Alarm Events"
    --#SOURCE_ID    "A"
    --#TIMEINDEX    0
    ::= {adGenOpticalADMEvents 24}

-- //////////////////////////////////////////////////////////////////
adGenOpticalADMAlmChannelComOutAutoOORLowActiveClear    NOTIFICATION-TYPE
   OBJECTS  {
                adTrapInformSeqNum,
                sysName,
                adGenSlotInfoIndex,
                ifIndex
            }
    STATUS          current
    DESCRIPTION     "Composite-OUT Channel Auto Power Out Of Range LOW Cleared."

    --#TYPE         "Composite-OUT Channel Auto Power Out Of Range LOW Cleared."
    --#SUMMARY      "Composite-OUT Channel Auto Power Out Of Range LOW."
    --#SUMMARY      "Cleared at shelf: %s, slot: %d, com-out channel %d"
    --#ARGUMENTS    {1,2,3}
    --#SEVERITY     MINOR
    --#GENERIC      6
    --#CATEGORY     "Alarm Events"
    --#SOURCE_ID    "A"
    --#TIMEINDEX    0
    ::= {adGenOpticalADMEvents 25}

adGenOpticalADMAlmChannelComOutAutoOORLowActive   NOTIFICATION-TYPE
   OBJECTS  {
                adTrapInformSeqNum,
                sysName,
                adGenSlotInfoIndex,
                ifIndex
            }
    STATUS          current
    DESCRIPTION     "Composite-OUT Channel Auto Power Out Of Range LOW Active."

    --#TYPE         "Composite-OUT Channel Auto Power Out Of Range LOW Active."
    --#SUMMARY      "Composite-OUT Channel Auto Power Out Of Range LOW."
    --#SUMMARY      "Activated at shelf: %s, slot: %d, com-out channel %d"
    --#ARGUMENTS    {1,2,3}
    --#SEVERITY     MINOR
    --#GENERIC      6
    --#CATEGORY     "Alarm Events"
    --#SOURCE_ID    "A"
    --#TIMEINDEX    0
    ::= {adGenOpticalADMEvents 26}

-- //////////////////////////////////////////////////////////////////
adGenOpticalADMAlmLossOfMidStageInActiveClear    NOTIFICATION-TYPE
   OBJECTS  {
                adTrapInformSeqNum,
                sysName,
                adGenSlotInfoIndex,
                ifIndex
            }
    STATUS          current
    DESCRIPTION     "Loss of Mid-Stage In Cleared."

    --#TYPE         "Loss of Mid-Stage In Cleared."
    --#SUMMARY      "Power of Mid-Stage In falls below a threshold value."
    --#SUMMARY      "Cleared at shelf: %s, slot: %d, Mid-Stage In %d"
    --#ARGUMENTS    {1,2,3}
    --#SEVERITY     CRITICAL
    --#GENERIC      6
    --#CATEGORY     "Alarm Events"
    --#SOURCE_ID    "A"
    --#TIMEINDEX    0
    ::= {adGenOpticalADMEvents 27}

adGenOpticalADMAlmLossOfMidStageInActive   NOTIFICATION-TYPE
   OBJECTS  {
                adTrapInformSeqNum,
                sysName,
                adGenSlotInfoIndex,
                ifIndex
            }
    STATUS          current
    DESCRIPTION     "Loss of Mid-Stage In Active."

    --#TYPE         "Loss of Mid-Stage In Active."
    --#SUMMARY      "Power of Mid-Stage In falls below a threshold value."
    --#SUMMARY      "Activated at shelf: %s, slot: %d, Mid-Stage In %d"
    --#ARGUMENTS    {1,2,3}
    --#SEVERITY     CRITICAL
    --#GENERIC      6
    --#CATEGORY     "Alarm Events"
    --#SOURCE_ID    "A"
    --#TIMEINDEX    0
    ::= {adGenOpticalADMEvents 28}

-- //////////////////////////////////////////////////////////////////
adGenOpticalADMAlmComOutAmpShutOffClear    NOTIFICATION-TYPE
   OBJECTS  {
                adTrapInformSeqNum,
                sysName,
                adGenSlotInfoIndex,
                ifIndex
            }
    STATUS          current
    DESCRIPTION     "Composite-OUT Amplifier Shut Off Cleared.
                     This alarm is cleared, when Booster Amplifier's input
                     power falls back into its operational limits."
    --#TYPE         "Composite-OUT Amplifier Shut Off Cleared."
    --#SUMMARY      "Composite-OUT Amplifier Shut Off Cleared."
    --#SUMMARY      "Cleared at shelf: %s, slot: %d, interface %d"
    --#ARGUMENTS    {1,2,3}
    --#SEVERITY     CRITICAL
    --#GENERIC      6
    --#CATEGORY     "Alarm Events"
    --#SOURCE_ID    "A"
    --#TIMEINDEX    0
    ::= {adGenOpticalADMEvents 29}

adGenOpticalADMAlmComOutAmpShutOffActive   NOTIFICATION-TYPE
   OBJECTS  {
                adTrapInformSeqNum,
                sysName,
                adGenSlotInfoIndex,
                ifIndex
            }
    STATUS          current
    DESCRIPTION     "Composite-OUT Amplifier Shut Off Active.
                     This alarm is issued, when Booster Amplifier's input
                     power is outside the operational limits, thus
                     causing Amplifier to shut down."
    --#TYPE         "Composite-OUT Amplifier Shut Off Active."
    --#SUMMARY      "Composite-OUT Amplifier Shut Off Active."
    --#SUMMARY      "Activated at shelf: %s, slot: %d, interface %d"
    --#ARGUMENTS    {1,2,3}
    --#SEVERITY     CRITICAL
    --#GENERIC      6
    --#CATEGORY     "Alarm Events"
    --#SOURCE_ID    "A"
    --#TIMEINDEX    0
    ::= {adGenOpticalADMEvents 30}


-- //////////////////////////////////////////////////////////////////
    END
