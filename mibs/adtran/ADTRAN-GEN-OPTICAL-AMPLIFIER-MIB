ADTRAN-GEN-OPTICAL-AMPLIFIER-MIB

-- TITLE:     The ADTRAN OPTICAL AMPLIFIER MIB
-- PRODUCT:   TBD
-- VERSION:   1.0
-- DATE:      04/11/11
-- AUTHOR:    Prasanna Kumar Kemisetty
-- STATUS:    Created

-- This MIB defines the object identifiers (OIDs) for the
-- ADTRAN GENERIC OPTICAL AMPLIFIER MIB objects
-- ******************************************************************************************

DEFINITIONS ::= BEGIN

IMPORTS

   adGenOpticalAmplifier,
   adGenOpticalAmplifierID     FROM ADTRAN-SHARED-CND-SYSTEM-MIB

   OBJECT-TYPE,
   MODULE-IDENTITY,
   NOTIFICATION-TYPE,
   Integer32                 FROM SNMPv2-SMI

   DisplayString             FROM SNMPv2-TC

   InterfaceIndex            FROM IF-MIB

   adGenSlotInfoIndex        FROM ADTRAN-GENSLOT-MIB

   adTrapInformSeqNum        FROM ADTRAN-GENTRAPINFORM-MIB
   sysName                   FROM SNMPv2-MIB;

adGenOpticalAmplifierMIB MODULE-IDENTITY
   LAST-UPDATED "201307230000Z"
   ORGANIZATION "Adtran, Inc."
   CONTACT-INFO
     "CND Tech Support
         Postal: ADTRAN, Inc.
                 901 Explorer Blvd.
                 Huntsville, AL  35806
                 Tel: +1 800 726-8663
                 Fax: +1 256 963 6217
                 E-mail: support@adtran.com"
   DESCRIPTION
      "This MIB defines the objects for the Generic Optical Amplifier MIB."

   REVISION "201307230000Z"
   DESCRIPTION "Added adGenOpticalAmplifierAdminState and adGenOpticalAmplifierOperState."

   REVISION "201208270000Z"
   DESCRIPTION "Added adGenOpticalAmplifierMode."

   REVISION "201204120000Z"
   DESCRIPTION "Added new a Variable Gain item and its range."

   REVISION "201201170000Z"
   DESCRIPTION "Added new threshold items and their alarms.  A new supplement table
                for max and min threshold values.  Deprecated adGenOpticalAmplifierInputPowerThreshold"

   REVISION "201110200000Z"
   DESCRIPTION "Added adGenOpticalAmplifierIfIndexReference.  Added a new ENUM entree to
                adGenOpticalAmplifierStatus"

   REVISION "201108080000Z"
   DESCRIPTION "Created"

::= { adGenOpticalAmplifierID 1 }

adGenOpticalAmplifierProduct                     OBJECT IDENTIFIER ::= {adGenOpticalAmplifier 1}
adGenOpticalAmplifierAlrms                       OBJECT IDENTIFIER ::= {adGenOpticalAmplifierProduct 100}
adGenOpticalAmplifierEvents                      OBJECT IDENTIFIER ::= {adGenOpticalAmplifierAlrms 0}
--==================================================================================================================

   adGenOpticalAmplifierTable OBJECT-TYPE
      SYNTAX  SEQUENCE OF AdGenOpticalAmplifierEntry
      MAX-ACCESS  not-accessible
      STATUS  current
      DESCRIPTION
         "The Optical Amplifier Information table."
      ::= { adGenOpticalAmplifierProduct 1 }

   adGenOpticalAmplifierEntry OBJECT-TYPE
      SYNTAX  AdGenOpticalAmplifierEntry
      MAX-ACCESS  not-accessible
      STATUS  current
      DESCRIPTION
         "An entry in the Optical Amplifier Information table."
      INDEX  { adGenSlotInfoIndex }
      ::= { adGenOpticalAmplifierTable 1 }

   AdGenOpticalAmplifierEntry ::=
      SEQUENCE {
                  adGenOpticalAmplifierProdType                    INTEGER,
                  adGenOpticalAmplifierStatus		               INTEGER,
                  adGenOpticalAmplifierInputPower      		       Integer32,
                  adGenOpticalAmplifierOutputPower    		       Integer32,
                  adGenOpticalAmplifierGain		       	           Integer32,
                  adGenOpticalAmplifierCaseTemperature             Integer32,
                  adGenOpticalAmplifierBoardTemperature            Integer32,
                  adGenOpticalAmplifierPumpTemperature             Integer32,
                  adGenOpticalAmplifierLaserPumpOperatingCurrent   Integer32,
                  adGenOpticalAmplifierLaserPumpEndOfLifeCurrent   Integer32,
                  adGenOpticalAmplifierLaserPumpReflectedPower     Integer32,
                  adGenOpticalAmplifierInputPowerThreshold         INTEGER,
                  adGenOpticalAmplifierIfIndexReference            InterfaceIndex,
		  adGenOpticalAmplifierInputPowerThresholdLow      Integer32,
		  adGenOpticalAmplifierInputPowerThresholdHigh     Integer32,
		  adGenOpticalAmplifierOutputPowerThresholdLow     Integer32,
		  adGenOpticalAmplifierOutputPowerThresholdHigh    Integer32,
		  adGenOpticalAmplifierMidStageAttenuation         Integer32,
		  adGenOpticalAmplifierVariableGain                Integer32,
		  adGenOpticalAmplifierMode                        INTEGER,
		  adGenOpticalAmplifierAdminState                  INTEGER,
		  adGenOpticalAmplifierOperState                   INTEGER
               }

      adGenOpticalAmplifierProdType OBJECT-TYPE
         SYNTAX INTEGER  {
                            preAmp(1),
                            boostAmp(2),
                            midStageAmp(3)
                         }
         MAX-ACCESS     read-only
         STATUS         current
         DESCRIPTION
            "Amplifier Product Type."
         ::= { adGenOpticalAmplifierEntry 1 }

      adGenOpticalAmplifierStatus OBJECT-TYPE
         SYNTAX INTEGER  {
                            moduleDisabled(1),
                            eyeSafeMode(2),
                            moduleOk(3),
                            powerOrGainLimited(4)
                         }
         MAX-ACCESS     read-only
         STATUS         current
         DESCRIPTION
            "Amplifier Running Status."
         ::= { adGenOpticalAmplifierEntry 2 }

      adGenOpticalAmplifierInputPower OBJECT-TYPE
         SYNTAX         Integer32
         MAX-ACCESS     read-only
         STATUS         current
         DESCRIPTION
            "Input Power of the Optical Signal to the Amplifier module in dBm."
         ::= { adGenOpticalAmplifierEntry 3 }

      adGenOpticalAmplifierOutputPower OBJECT-TYPE
         SYNTAX         Integer32
         MAX-ACCESS     read-only
         STATUS         current
         DESCRIPTION
            "Output Power of the Optical Signal from the Amplifier module in dBm."
         ::= { adGenOpticalAmplifierEntry 4 }

      adGenOpticalAmplifierGain OBJECT-TYPE
         SYNTAX         Integer32
         MAX-ACCESS     read-only
         STATUS         current
         DESCRIPTION
            "Total Gain of the Optical Signalin dBm."
         ::= { adGenOpticalAmplifierEntry 5 }

      adGenOpticalAmplifierCaseTemperature OBJECT-TYPE
         SYNTAX         Integer32
         MAX-ACCESS     read-only
         STATUS         current
         DESCRIPTION
             "Current in degrees C Temperature of the Amplifier module."
         ::= { adGenOpticalAmplifierEntry 6 }

 	  adGenOpticalAmplifierBoardTemperature OBJECT-TYPE
         SYNTAX         Integer32
         MAX-ACCESS     read-only
         STATUS         current
         DESCRIPTION
            "Current Temperature in degrees C of the Optical Amplifier Card."
         ::= { adGenOpticalAmplifierEntry 7 }

      adGenOpticalAmplifierPumpTemperature OBJECT-TYPE
         SYNTAX         Integer32
         MAX-ACCESS     read-only
         STATUS         current
         DESCRIPTION
            "Current Temperature in degrees C of the Laser Pump in the Amplifier Module."
         ::= { adGenOpticalAmplifierEntry 8 }

      adGenOpticalAmplifierLaserPumpOperatingCurrent OBJECT-TYPE
         SYNTAX         Integer32
         MAX-ACCESS     read-only
         STATUS         current
         DESCRIPTION
             "Displays the laser diode pump operating current in mA."
         ::= { adGenOpticalAmplifierEntry 9 }

 	  adGenOpticalAmplifierLaserPumpEndOfLifeCurrent OBJECT-TYPE
         SYNTAX         Integer32
         MAX-ACCESS     read-only
         STATUS         current
         DESCRIPTION
            "Displays the laser diode pump end-of-life current in mA."
         ::= { adGenOpticalAmplifierEntry 10 }

      adGenOpticalAmplifierLaserPumpReflectedPower OBJECT-TYPE
         SYNTAX         Integer32
         MAX-ACCESS     read-only
         STATUS         current
         DESCRIPTION
            "Displays the reflected power at the total output in mA."
         ::= { adGenOpticalAmplifierEntry 11 }

      adGenOpticalAmplifierInputPowerThreshold OBJECT-TYPE
         SYNTAX         INTEGER (-50..31|32767)
         MAX-ACCESS     read-write
         STATUS         deprecated
         DESCRIPTION
             "Used to specify the Input Power Threshold in dBm. Valid range is -50 to 30. 32767 disables the Alarm.
              This OID is deprecated.  Please use adGenOpticalAmplifierInputPowerThresholdLow instead. "
         ::= { adGenOpticalAmplifierEntry 12 }

      adGenOpticalAmplifierIfIndexReference  OBJECT-TYPE
         SYNTAX         InterfaceIndex
         MAX-ACCESS     read-only
         STATUS         current
         DESCRIPTION
            "This will return the ifIndex value for this particular amplifier module."
         ::= { adGenOpticalAmplifierEntry 13 }

      adGenOpticalAmplifierInputPowerThresholdLow OBJECT-TYPE
         SYNTAX         Integer32
         MAX-ACCESS     read-write
         STATUS         current
         DESCRIPTION
             "Used to specify the Input Power Threshold in dBm.
              Valid range can be found using adGenOpticalAmplifierSupplementTable."
         ::= { adGenOpticalAmplifierEntry 14 }

      adGenOpticalAmplifierInputPowerThresholdHigh OBJECT-TYPE
         SYNTAX         Integer32
         MAX-ACCESS     read-write
         STATUS         current
         DESCRIPTION
             "Used to specify the Input Power Threshold in dBm.
              Valid range can be found using adGenOpticalAmplifierSupplementTable."
         ::= { adGenOpticalAmplifierEntry 15 }

      adGenOpticalAmplifierOutputPowerThresholdLow OBJECT-TYPE
         SYNTAX         Integer32
         MAX-ACCESS     read-write
         STATUS         current
         DESCRIPTION
             "Used to specify the Input Power Threshold in dBm.
              Valid range can be found using adGenOpticalAmplifierSupplementTable."
         ::= { adGenOpticalAmplifierEntry 16 }

     adGenOpticalAmplifierOutputPowerThresholdHigh OBJECT-TYPE
         SYNTAX         Integer32
         MAX-ACCESS     read-write
         STATUS         current
         DESCRIPTION
             "Used to specify the Output Power Threshold in dBm.
              Valid range can be found using adGenOpticalAmplifierSupplementTable."
         ::= { adGenOpticalAmplifierEntry 17 }

     adGenOpticalAmplifierMidStageAttenuation OBJECT-TYPE
         SYNTAX         Integer32
         MAX-ACCESS     read-write
         STATUS         current
         DESCRIPTION
             "Used to specify the Loss in dbm.
              Valid range can be found using adGenOpticalAmplifierSupplementTable."
         ::= { adGenOpticalAmplifierEntry 18 }

      adGenOpticalAmplifierVariableGain OBJECT-TYPE
         SYNTAX         Integer32
         MAX-ACCESS     read-write
         STATUS         current
         DESCRIPTION
             "Used to specify the variable gain in dB.
			  Valid range can be found using adGenOpticalAmplifierSupplementTable."
         ::= { adGenOpticalAmplifierEntry 19 }

     adGenOpticalAmplifierMode OBJECT-TYPE
        SYNTAX INTEGER  {
                            preAmp(1),
                            boostAmp(2)
                        }

         MAX-ACCESS     read-write
         STATUS         current
         DESCRIPTION
            "To set the amplifier in either Pre or Boost mode."
         ::= { adGenOpticalAmplifierEntry 20 }

     adGenOpticalAmplifierAdminState OBJECT-TYPE
        SYNTAX INTEGER  {
                          up(1),
                          down(2),
                          testing(3)
			}

         MAX-ACCESS     read-write
         STATUS         current
         DESCRIPTION
            "This sets the admin service state of the amplifier."
         ::= { adGenOpticalAmplifierEntry 21 }

     adGenOpticalAmplifierOperState OBJECT-TYPE
        SYNTAX INTEGER  {
                          up(1),
                          down(2),
                          testing(3)
			}

         MAX-ACCESS     read-only
         STATUS         current
         DESCRIPTION
            "This displays the current operation state of the amplifier."
         ::= { adGenOpticalAmplifierEntry 22 }

--///////////////////////////////////////////////////////
--///////////////////////////////////////////////////////

   adGenOpticalAmplifierSupplementTable OBJECT-TYPE
      SYNTAX  SEQUENCE OF AdGenOpticalAmplifierSupplementEntry
      MAX-ACCESS  not-accessible
      STATUS  current
      DESCRIPTION
         "The Optical Amplifier Information Supplement table."
      ::= { adGenOpticalAmplifierProduct 2 }

   adGenOpticalAmplifierSupplementEntry OBJECT-TYPE
      SYNTAX  AdGenOpticalAmplifierSupplementEntry
      MAX-ACCESS  not-accessible
      STATUS  current
      DESCRIPTION
         "An entry in the Optical Amplifier Information Supplement table."
      INDEX  { adGenSlotInfoIndex }
      ::= { adGenOpticalAmplifierSupplementTable 1 }

   AdGenOpticalAmplifierSupplementEntry ::=
      SEQUENCE {
                  adGenOpticalAmplifierInputPowerThresholdLowMax   Integer32,
                  adGenOpticalAmplifierInputPowerThresholdLowMin   Integer32,
                  adGenOpticalAmplifierInputPowerThresholdHighMax  Integer32,
                  adGenOpticalAmplifierInputPowerThresholdHighMin  Integer32,
                  adGenOpticalAmplifierOutputPowerThresholdLowMax  Integer32,
                  adGenOpticalAmplifierOutputPowerThresholdLowMin  Integer32,
                  adGenOpticalAmplifierOutputPowerThresholdHighMax Integer32,
                  adGenOpticalAmplifierOutputPowerThresholdHighMin Integer32,
		          adGenOpticalAmplifierMidStageAttenuationMax	   Integer32,
                  adGenOpticalAmplifierMidStageAttenuationMin	   Integer32,
				  adGenOpticalAmplifierVariableGainMin      	   Integer32,
				  adGenOpticalAmplifierVariableGainMax      	   Integer32
               }

      adGenOpticalAmplifierInputPowerThresholdLowMax OBJECT-TYPE
         SYNTAX         Integer32
         UNITS          "dBm"
         MAX-ACCESS     read-only
         STATUS         current
         DESCRIPTION
             "Displays the maximum provisionable value for
              Amplifier Input Threshold Low."
         ::= { adGenOpticalAmplifierSupplementEntry 1 }

      adGenOpticalAmplifierInputPowerThresholdLowMin OBJECT-TYPE
         SYNTAX         Integer32
         UNITS          "dBm"
         MAX-ACCESS     read-only
         STATUS         current
         DESCRIPTION
             "Displays the minmum provisionable value for
              Amplifier Input Threshold Low."
         ::= { adGenOpticalAmplifierSupplementEntry 2 }

      adGenOpticalAmplifierInputPowerThresholdHighMax OBJECT-TYPE
         SYNTAX         Integer32
         UNITS          "dBm"
         MAX-ACCESS     read-only
         STATUS         current
         DESCRIPTION
             "Displays the maximum provisionable value for
              Amplifier Input Threshold High."
         ::= { adGenOpticalAmplifierSupplementEntry 3 }

      adGenOpticalAmplifierInputPowerThresholdHighMin OBJECT-TYPE
         SYNTAX         Integer32
         UNITS          "dBm"
         MAX-ACCESS     read-only
         STATUS         current
         DESCRIPTION
             "Displays the minmum provisionable value for
              Amplifier Input Threshold High."
         ::= { adGenOpticalAmplifierSupplementEntry 4 }

      adGenOpticalAmplifierOutputPowerThresholdLowMax OBJECT-TYPE
         SYNTAX         Integer32
         UNITS          "dBm"
         MAX-ACCESS     read-only
         STATUS         current
         DESCRIPTION
             "Displays the maximum provisionable value for
              Amplifier Output Threshold Low."
         ::= { adGenOpticalAmplifierSupplementEntry 5 }

      adGenOpticalAmplifierOutputPowerThresholdLowMin OBJECT-TYPE
         SYNTAX         Integer32
         UNITS          "dBm"
         MAX-ACCESS     read-only
         STATUS         current
         DESCRIPTION
             "Displays the minmum provisionable value for
              Amplifier Output Threshold Low."
         ::= { adGenOpticalAmplifierSupplementEntry 6 }

      adGenOpticalAmplifierOutputPowerThresholdHighMax OBJECT-TYPE
         SYNTAX         Integer32
         UNITS          "dBm"
         MAX-ACCESS     read-only
         STATUS         current
         DESCRIPTION
             "Displays the maximum provisionable value for
              Amplifier Output Threshold High."
         ::= { adGenOpticalAmplifierSupplementEntry 7 }

      adGenOpticalAmplifierOutputPowerThresholdHighMin OBJECT-TYPE
         SYNTAX         Integer32
         UNITS          "dBm"
         MAX-ACCESS     read-only
         STATUS         current
         DESCRIPTION
             "Displays the minmum provisionable value for
              Amplifier Output Threshold High."
         ::= { adGenOpticalAmplifierSupplementEntry 8 }

      adGenOpticalAmplifierMidStageAttenuationMax  OBJECT-TYPE
         SYNTAX         Integer32
         UNITS          "dBm"
         MAX-ACCESS     read-only
         STATUS         current
         DESCRIPTION
             "Displays the maximum provisionable value for
              Amplifier Mid-Stage Loss."
         ::= { adGenOpticalAmplifierSupplementEntry 9 }

      adGenOpticalAmplifierMidStageAttenuationMin  OBJECT-TYPE
         SYNTAX         Integer32
         UNITS          "dBm"
         MAX-ACCESS     read-only
         STATUS         current
         DESCRIPTION
             "Displays the minmum provisionable value for
              Amplifier Mid-Stage Loss."
         ::= { adGenOpticalAmplifierSupplementEntry 10 }

      adGenOpticalAmplifierVariableGainMin  OBJECT-TYPE
         SYNTAX         Integer32
         UNITS          "dB"
         MAX-ACCESS     read-only
         STATUS         current
         DESCRIPTION
             "Displays the minmum provisionable value for
              Amplifier Variable Gain."
         ::= { adGenOpticalAmplifierSupplementEntry 11 }

      adGenOpticalAmplifierVariableGainMax  OBJECT-TYPE
         SYNTAX         Integer32
         UNITS          "dB"
         MAX-ACCESS     read-only
         STATUS         current
         DESCRIPTION
             "Displays the maximum provisionable value for
              Amplifier Variable Gain."
         ::= { adGenOpticalAmplifierSupplementEntry 12 }


--///////////////////////////////////////////////////////
-- Optical Amplifier alarms
--//////////////////////////////////////////////////////

 adGenInputPowerThrAlarmClear    NOTIFICATION-TYPE
     OBJECTS       {
             adTrapInformSeqNum,
             sysName,
             adGenSlotInfoIndex
             }
     STATUS      current
     DESCRIPTION
             "Input Power Thr Alrm"
     --#TYPE      "Critical - InputPower Thresh"
     --#SUMMARY   "1: Input Power Threshold;"
     --#SUMMARY   "cleared at shelf: %s, slot: %d"
     --#ARGUMENTS { 1, 2 }
     --#SEVERITY  CRITICAL
     --#GENERIC   6
     --#CATEGORY  "Error Events"
     --#SOURCE_ID "A"
     --#TIMEINDEX 0
     ::= {adGenOpticalAmplifierEvents 1}

  adGenInputPowerThrAlrmSet    NOTIFICATION-TYPE
     OBJECTS       {
             adTrapInformSeqNum,
             sysName,
             adGenSlotInfoIndex
             }
     STATUS       current
     DESCRIPTION
             "Input Power Thr Alrm"
     --#TYPE      "Critical - InputPower Thresh"
     --#SUMMARY   "2: Input Power Threshold Alarm;"
     --#SUMMARY   "detected at shelf: %s, slot: %d"
     --#ARGUMENTS { 1, 2 }
     --#SEVERITY  CRITICAL
     --#GENERIC   6
     --#CATEGORY  "Error Events"
     --#SOURCE_ID "A"
     --#TIMEINDEX 0
     ::= {adGenOpticalAmplifierEvents 2}


  adGenOutputPowerLossClear    NOTIFICATION-TYPE
     OBJECTS       {
             adTrapInformSeqNum,
             sysName,
             adGenSlotInfoIndex
             }
     STATUS          current
     DESCRIPTION
             "Output Power Loss"
     --#TYPE      "Critical - Output Power Loss"
     --#SUMMARY   "3: Output Power Loss Alarm;"
     --#SUMMARY   "cleared at shelf: %s, slot: %d"
     --#ARGUMENTS { 1, 2 }
     --#SEVERITY  CRITICAL
     --#GENERIC   6
     --#CATEGORY  "Error Events"
     --#SOURCE_ID "A"
     --#TIMEINDEX 0
     ::= {adGenOpticalAmplifierEvents 3}

  adGenOutputPowerLossAlrmSet    NOTIFICATION-TYPE
     OBJECTS       {
             adTrapInformSeqNum,
             sysName,
             adGenSlotInfoIndex
             }
     STATUS            current
     DESCRIPTION
             "Output Power Loss"
     --#TYPE      "Critical - Output Power Loss"
     --#SUMMARY   "4: Output Power Loss Alarm;"
     --#SUMMARY   "detected at shelf: %s, slot: %d"
     --#ARGUMENTS { 1, 2 }
     --#SEVERITY  CRITICAL
     --#GENERIC   6
     --#CATEGORY  "Error Events"
     --#SOURCE_ID "A"
     --#TIMEINDEX 0
     ::= {adGenOpticalAmplifierEvents 4}

  adGenBoardTempClear    NOTIFICATION-TYPE
     OBJECTS       {
             adTrapInformSeqNum,
             sysName,
             adGenSlotInfoIndex
             }
     STATUS       current
     DESCRIPTION
             "Board Temperature High"
     --#TYPE      "Warning - Board Temperature High"
     --#SUMMARY   "5: Board Temperature High Alarm;"
     --#SUMMARY   "cleared at shelf: %s, slot: %d"
     --#ARGUMENTS { 1, 2 }
     --#SEVERITY  WARNING
     --#GENERIC   6
     --#CATEGORY  "Error Events"
     --#SOURCE_ID "A"
     --#TIMEINDEX 0
     ::= {adGenOpticalAmplifierEvents 5}

  adGenBoardTempAlrmSet    NOTIFICATION-TYPE
     OBJECTS       {
             adTrapInformSeqNum,
             sysName,
             adGenSlotInfoIndex
             }
     STATUS          current
     DESCRIPTION
             "Board Temperature High"
     --#TYPE      "Warning - Board Temperature High"
     --#SUMMARY   "6: Board Temperature High Alarm;"
     --#SUMMARY   "detected at shelf: %s, slot: %d"
     --#ARGUMENTS { 1, 2 }
     --#SEVERITY  WARNING
     --#GENERIC   6
     --#CATEGORY  "Error Events"
     --#SOURCE_ID "A"
     --#TIMEINDEX 0
     ::= {adGenOpticalAmplifierEvents 6}

 adGenModuleTempLowClear    NOTIFICATION-TYPE
     OBJECTS       {
             adTrapInformSeqNum,
             sysName,
             adGenSlotInfoIndex
             }
     STATUS     current
     DESCRIPTION
             "Module Temperature Low"
     --#TYPE      "Warning - Module Temperature Low"
     --#SUMMARY   "7: Module Temperature Low Alarm;"
     --#SUMMARY   "cleared at shelf: %s, slot: %d"
     --#ARGUMENTS { 1, 2 }
     --#SEVERITY  WARNING
     --#GENERIC   6
     --#CATEGORY  "Error Events"
     --#SOURCE_ID "A"
     --#TIMEINDEX 0
     ::= {adGenOpticalAmplifierEvents 7}

  adGenModuleTempLowAlrmSet    NOTIFICATION-TYPE
     OBJECTS       {
             adTrapInformSeqNum,
             sysName,
             adGenSlotInfoIndex
             }
     STATUS        current
     DESCRIPTION
             "Module Temperature Low"
     --#TYPE      "Warning - Module Temperature Low"
     --#SUMMARY   "8: Module Temperature Low Alarm;"
     --#SUMMARY   "detected at shelf: %s, slot: %d"
     --#ARGUMENTS { 1, 2 }
     --#SEVERITY  WARNING
     --#GENERIC   6
     --#CATEGORY  "Error Events"
     --#SOURCE_ID "A"
     --#TIMEINDEX 0
     ::= {adGenOpticalAmplifierEvents 8}

 adGenModuleTempHighClear    NOTIFICATION-TYPE
     OBJECTS       {
             adTrapInformSeqNum,
             sysName,
             adGenSlotInfoIndex
             }
     STATUS		  current
     DESCRIPTION
             "Module Temperature High"
     --#TYPE      "Warning - Module Temperature High"
     --#SUMMARY   "9: Module Temperature High Alarm;"
     --#SUMMARY   "cleared at shelf: %s, slot: %d"
     --#ARGUMENTS { 1, 2 }
     --#SEVERITY  WARNING
     --#GENERIC   6
     --#CATEGORY  "Error Events"
     --#SOURCE_ID "A"
     --#TIMEINDEX 0
     ::= {adGenOpticalAmplifierEvents 9}

  adGenModuleTempHighAlrmSet    NOTIFICATION-TYPE
     OBJECTS       {
             adTrapInformSeqNum,
             sysName,
             adGenSlotInfoIndex
             }
     STATUS        current
     DESCRIPTION
             "Module Temperature High"
     --#TYPE      "Warning - Module Temperature High"
     --#SUMMARY   "10: Module Temperature High Alarm;"
     --#SUMMARY   "detected at shelf: %s, slot: %d"
     --#ARGUMENTS { 1, 2 }
     --#SEVERITY  WARNING
     --#GENERIC   6
     --#CATEGORY  "Error Events"
     --#SOURCE_ID "A"
     --#TIMEINDEX 0
     ::= {adGenOpticalAmplifierEvents 10}

 adGenLaserPumpTempClear    NOTIFICATION-TYPE
     OBJECTS       {
             adTrapInformSeqNum,
             sysName,
             adGenSlotInfoIndex
             }
     STATUS       current
     DESCRIPTION
             "Laser Temperature High"
     --#TYPE      "Warning - Laser Temperature High"
     --#SUMMARY   "11: Laser Temperature High Alarm;"
     --#SUMMARY   "cleared at shelf: %s, slot: %d"
     --#ARGUMENTS { 1, 2 }
     --#SEVERITY  WARNING
     --#GENERIC   6
     --#CATEGORY  "Error Events"
     --#SOURCE_ID "A"
     --#TIMEINDEX 0
     ::= {adGenOpticalAmplifierEvents 11}

  adGenLaserPumpTempAlrmSet    NOTIFICATION-TYPE
     OBJECTS       {
             adTrapInformSeqNum,
             sysName,
             adGenSlotInfoIndex
             }
     STATUS        current
     DESCRIPTION
             "Laser Temperature High"
     --#TYPE      "Warning - Laser Temperature High"
     --#SUMMARY   "12: Laser Temperature High Alarm;"
     --#SUMMARY   "detected at shelf: %s, slot: %d"
     --#ARGUMENTS { 1, 2 }
     --#SEVERITY  WARNING
     --#GENERIC   6
     --#CATEGORY  "Error Events"
     --#SOURCE_ID "A"
     --#TIMEINDEX 0
     ::= {adGenOpticalAmplifierEvents 12}

 adGenLaserPumpEOLClear    NOTIFICATION-TYPE
     OBJECTS       {
             adTrapInformSeqNum,
             sysName,
             adGenSlotInfoIndex
             }
     STATUS	         current
     DESCRIPTION
             "Laser End Of Life"
     --#TYPE      "Minor - Laser End Of Life"
     --#SUMMARY   "13: Laser End Of Life Alarm;"
     --#SUMMARY   "cleared at shelf: %s, slot: %d"
     --#ARGUMENTS { 1, 2 }
     --#SEVERITY  MINOR
     --#GENERIC   6
     --#CATEGORY  "Error Events"
     --#SOURCE_ID "A"
     --#TIMEINDEX 0
     ::= {adGenOpticalAmplifierEvents 13}

  adGenLaserPumpEOLAlrmSet    NOTIFICATION-TYPE
     OBJECTS       {
             adTrapInformSeqNum,
             sysName,
             adGenSlotInfoIndex
             }
     STATUS      current
     DESCRIPTION
             "Laser End Of Life"
     --#TYPE      "Minor - Laser End Of Life"
     --#SUMMARY   "14: Laser End Of Life Alarm;"
     --#SUMMARY   "detected at shelf: %s, slot: %d"
     --#ARGUMENTS { 1, 2 }
     --#SEVERITY  MINOR
     --#GENERIC   6
     --#CATEGORY  "Error Events"
     --#SOURCE_ID "A"
     --#TIMEINDEX 0
     ::= {adGenOpticalAmplifierEvents 14}

  adGenInputPowerThLowAlarmClear    NOTIFICATION-TYPE
     OBJECTS       {
             adTrapInformSeqNum,
             sysName,
             adGenSlotInfoIndex
             }
     STATUS      current
     DESCRIPTION
             "Input Power Th Low Alarm"
     --#TYPE      "Minor - InputPower Thresh"
     --#SUMMARY   "15: Input Power Threshold Low;"
     --#SUMMARY   "cleared at shelf: %s, slot: %d"
     --#ARGUMENTS { 1, 2 }
     --#SEVERITY  MINOR
     --#GENERIC   6
     --#CATEGORY  "Error Events"
     --#SOURCE_ID "A"
     --#TIMEINDEX 0
     ::= {adGenOpticalAmplifierEvents 15}

  adGenInputPowerThLowAlarmSet    NOTIFICATION-TYPE
     OBJECTS       {
             adTrapInformSeqNum,
             sysName,
             adGenSlotInfoIndex
             }
     STATUS       current
     DESCRIPTION
             "Input Power Th Low Alarm"
     --#TYPE      "Minor - InputPower Thresh"
     --#SUMMARY   "16: Input Power Threshold High Alarm;"
     --#SUMMARY   "detected at shelf: %s, slot: %d"
     --#ARGUMENTS { 1, 2 }
     --#SEVERITY  MINOR
     --#GENERIC   6
     --#CATEGORY  "Error Events"
     --#SOURCE_ID "A"
     --#TIMEINDEX 0
     ::= {adGenOpticalAmplifierEvents 16}

adGenInputPowerThHighAlarmClear    NOTIFICATION-TYPE
     OBJECTS       {
             adTrapInformSeqNum,
             sysName,
             adGenSlotInfoIndex
             }
     STATUS      current
     DESCRIPTION
             "Input Power Th High Alarm"
     --#TYPE      "Minor - InputPower Thresh "
     --#SUMMARY   "17: Input Power Threshold High;"
     --#SUMMARY   "cleared at shelf: %s, slot: %d"
     --#ARGUMENTS { 1, 2 }
     --#SEVERITY  MINOR
     --#GENERIC   6
     --#CATEGORY  "Error Events"
     --#SOURCE_ID "A"
     --#TIMEINDEX 0
     ::= {adGenOpticalAmplifierEvents 17}

  adGenInputPowerThHighAlarmSet    NOTIFICATION-TYPE
     OBJECTS       {
             adTrapInformSeqNum,
             sysName,
             adGenSlotInfoIndex
             }
     STATUS       current
     DESCRIPTION
             "Input Power Th High Alarm"
     --#TYPE      "Minor - InputPower Thresh"
     --#SUMMARY   "18: Input Power Threshold High Alarm;"
     --#SUMMARY   "detected at shelf: %s, slot: %d"
     --#ARGUMENTS { 1, 2 }
     --#SEVERITY  MINOR
     --#GENERIC   6
     --#CATEGORY  "Error Events"
     --#SOURCE_ID "A"
     --#TIMEINDEX 0
     ::= {adGenOpticalAmplifierEvents 18}

  adGenOutputPowerThLowAlarmClear    NOTIFICATION-TYPE
     OBJECTS       {
             adTrapInformSeqNum,
             sysName,
             adGenSlotInfoIndex
             }
     STATUS      current
     DESCRIPTION
             "Output Power Th Low Alarm"
     --#TYPE      "Minor - OutputPower Thresh"
     --#SUMMARY   "19: Output Power Threshold Low;"
     --#SUMMARY   "cleared at shelf: %s, slot: %d"
     --#ARGUMENTS { 1, 2 }
     --#SEVERITY  MINOR
     --#GENERIC   6
     --#CATEGORY  "Error Events"
     --#SOURCE_ID "A"
     --#TIMEINDEX 0
     ::= {adGenOpticalAmplifierEvents 19}

  adGenOutputPowerThLowAlarmSet    NOTIFICATION-TYPE
     OBJECTS       {
             adTrapInformSeqNum,
             sysName,
             adGenSlotInfoIndex
             }
     STATUS       current
     DESCRIPTION
             "Output Power Th Low Alarm"
     --#TYPE      "Minor - OutputPower Thresh"
     --#SUMMARY   "20: Output Power Threshold Low Alarm;"
     --#SUMMARY   "detected at shelf: %s, slot: %d"
     --#ARGUMENTS { 1, 2 }
     --#SEVERITY  MINOR
     --#GENERIC   6
     --#CATEGORY  "Error Events"
     --#SOURCE_ID "A"
     --#TIMEINDEX 0
     ::= {adGenOpticalAmplifierEvents 20}

adGenOutputPowerThHighAlarmClear    NOTIFICATION-TYPE
     OBJECTS       {
             adTrapInformSeqNum,
             sysName,
             adGenSlotInfoIndex
             }
     STATUS      current
     DESCRIPTION
             "Output Power Th High Alarm"
     --#TYPE      "Minor - OutputPower Thresh"
     --#SUMMARY   "21: Output Power Threshold High;"
     --#SUMMARY   "cleared at shelf: %s, slot: %d"
     --#ARGUMENTS { 1, 2 }
     --#SEVERITY  MINOR
     --#GENERIC   6
     --#CATEGORY  "Error Events"
     --#SOURCE_ID "A"
     --#TIMEINDEX 0
     ::= {adGenOpticalAmplifierEvents 21}

  adGenOutputPowerThHighAlarmSet    NOTIFICATION-TYPE
     OBJECTS       {
             adTrapInformSeqNum,
             sysName,
             adGenSlotInfoIndex
             }
     STATUS       current
     DESCRIPTION
             "Output Power Th High Alarm"
     --#TYPE      "Minor - OutputPower Thresh"
     --#SUMMARY   "22: Output Power Threshold High Alarm;"
     --#SUMMARY   "detected at shelf: %s, slot: %d"
     --#ARGUMENTS { 1, 2 }
     --#SEVERITY  MINOR
     --#GENERIC   6
     --#CATEGORY  "Error Events"
     --#SOURCE_ID "A"
     --#TIMEINDEX 0
     ::= {adGenOpticalAmplifierEvents 22}

     adGenAmplifierLOSAlarmClear    NOTIFICATION-TYPE
     OBJECTS       {
             adTrapInformSeqNum,
             sysName,
             adGenSlotInfoIndex
             }
     STATUS      current
     DESCRIPTION
             "Amplifier LOS"
     --#TYPE      "Critical - LOS"
     --#SUMMARY   "23: Amplifier LOS;"
     --#SUMMARY   "cleared at shelf: %s, slot: %d"
     --#ARGUMENTS { 1, 2 }
     --#SEVERITY  CRITICAL
     --#GENERIC   6
     --#CATEGORY  "Error Events"
     --#SOURCE_ID "A"
     --#TIMEINDEX 0
     ::= {adGenOpticalAmplifierEvents 23}

   adGenAmplifierLOSAlarmSet    NOTIFICATION-TYPE
     OBJECTS       {
             adTrapInformSeqNum,
             sysName,
             adGenSlotInfoIndex
             }
     STATUS       current
     DESCRIPTION
             "Amplifier LOS"
     --#TYPE      "Critical - LOS"
     --#SUMMARY   "24: Amplifier LOS Alarm;"
     --#SUMMARY   "detected at shelf: %s, slot: %d"
     --#ARGUMENTS { 1, 2 }
     --#SEVERITY  CRITICAL
     --#GENERIC   6
     --#CATEGORY  "Error Events"
     --#SOURCE_ID "A"
     --#TIMEINDEX 0
     ::= {adGenOpticalAmplifierEvents 24}

     adGenOpticalAmplifierLossOfMidStageInActiveClear    NOTIFICATION-TYPE
     OBJECTS       {
             adTrapInformSeqNum,
             sysName,
             adGenSlotInfoIndex
             }
     STATUS      current
     DESCRIPTION
             "Mid-Stage LOS"
     --#TYPE      "Critical - Mid-Stage LOS"
     --#SUMMARY   "25: Mid-Stage LOS;"
     --#SUMMARY   "cleared at shelf: %s, slot: %d"
     --#ARGUMENTS { 1, 2 }
     --#SEVERITY  CRITICAL
     --#GENERIC   6
     --#CATEGORY  "Error Events"
     --#SOURCE_ID "A"
     --#TIMEINDEX 0
     ::= {adGenOpticalAmplifierEvents 25}

   adGenOpticalAmplifierLossOfMidStageInActive    NOTIFICATION-TYPE
     OBJECTS       {
             adTrapInformSeqNum,
             sysName,
             adGenSlotInfoIndex
             }
     STATUS       current
     DESCRIPTION
             "Mid-Stage LOS"
     --#TYPE      "Critical - LOS"
     --#SUMMARY   "26: Mid-Stage LOS Alarm;"
     --#SUMMARY   "detected at shelf: %s, slot: %d"
     --#ARGUMENTS { 1, 2 }
     --#SEVERITY  CRITICAL
     --#GENERIC   6
     --#CATEGORY  "Error Events"
     --#SOURCE_ID "A"
     --#TIMEINDEX 0
     ::= {adGenOpticalAmplifierEvents 26}
 END
