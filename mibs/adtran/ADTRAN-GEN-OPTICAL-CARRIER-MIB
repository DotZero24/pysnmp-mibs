ADTRAN-GEN-OPTICAL-CARRIER-MIB

-- TITLE:     The ADTRAN OPTICAL CARRIER MIB
-- PRODUCT:   TBD
-- VERSION:   1.0
-- DATE:      05/23/11
-- AUTHOR:    Albert Sue
-- STATUS:    PRELIMINARY

-- This MIB defines the object identifiers (OIDs) for the
-- ADTRAN GENERIC OPTICAL CARRIER MIB objects
-- ******************************************************************************************

DEFINITIONS ::= BEGIN

IMPORTS

   adGenOpticalCarrier,
   adGenOpticalCarrierID     FROM ADTRAN-SHARED-CND-SYSTEM-MIB

   OBJECT-TYPE,
   MODULE-IDENTITY,
   Integer32                 FROM SNMPv2-SMI

   DisplayString             FROM SNMPv2-TC

   InterfaceIndex            FROM IF-MIB

   adGenSlotInfoIndex        FROM ADTRAN-GENSLOT-MIB

   adGenSubSlotProdInfoIndex FROM ADTRAN-GENSLOT-SUB-MODULE-MIB;

adGenOpticalCarrierMIB MODULE-IDENTITY
   LAST-UPDATED "201201120000Z"
   ORGANIZATION "Adtran, Inc."
   CONTACT-INFO
     "CND Tech Support
         Postal: ADTRAN, Inc.
                 901 Explorer Blvd.
                 Huntsville, AL  35806
                 Tel: +1 800 726-8663
                 Fax: +1 256 963 6217
                 E-mail: support@adtran.com"
   DESCRIPTION
      "This MIB defines the objects for the Generic Optical Carrier MIB."

   REVISION "201201120000Z"
   DESCRIPTION "Added adGenOpticalCarrierProdPortIfIndexReference"

   REVISION "201105230000Z"
   DESCRIPTION "Created"

::= { adGenOpticalCarrierID 1 }

adGenOpticalCarrierProduct                     OBJECT IDENTIFIER ::= {adGenOpticalCarrier 1}

--==================================================================================================================

   adGenOpticalCarrierProductTable OBJECT-TYPE
      SYNTAX  SEQUENCE OF AdGenOpticalCarrierProductEntry
      MAX-ACCESS  not-accessible
      STATUS  current
      DESCRIPTION
         "The Optical Carrier Product table."
      ::= { adGenOpticalCarrierProduct 1 }

   adGenOpticalCarrierProductEntry OBJECT-TYPE
      SYNTAX  AdGenOpticalCarrierProductEntry
      MAX-ACCESS  not-accessible
      STATUS  current
      DESCRIPTION
         "An entry in the Optical Carrier Product table."
      INDEX  { adGenSlotInfoIndex, adGenSubSlotProdInfoIndex }
      ::= { adGenOpticalCarrierProductTable 1 }

   AdGenOpticalCarrierProductEntry ::=
      SEQUENCE {
                  adGenOpticalCarrierProdType          INTEGER,
                  adGenOpticalCarrierProdGridSpacing   INTEGER,
                  adGenOpticalCarrierProdNumOfPorts    Integer32
               }

      adGenOpticalCarrierProdType OBJECT-TYPE
         SYNTAX INTEGER  {
                            invalid(1),
                            cwdmMUX(2),
                            dwdmMUX(3),
                            cwdmDEMUX(4),
                            dwdmDEMUX(5),
                            cwdmOADM(6),
                            dwdmOADM(7),
                            oscFILTER(8)
                         }
         MAX-ACCESS     read-only
         STATUS         current
         DESCRIPTION
            "Product Type.
             invalid = not able to retrieve information from card."
         ::= { adGenOpticalCarrierProductEntry 1 }

      adGenOpticalCarrierProdGridSpacing OBJECT-TYPE
         SYNTAX INTEGER  {
                            invalid(1),
                            allRange(2),
                            twentyFiveGHz(3),
                            fiftyGHz(4),
                            oneHundredGHz(5)
                         }
         MAX-ACCESS     read-only
         STATUS         current
         DESCRIPTION
            "Grid Spacing.
             invalid = not able to retrieve information from card."
         ::= { adGenOpticalCarrierProductEntry 2 }

      adGenOpticalCarrierProdNumOfPorts OBJECT-TYPE
         SYNTAX         Integer32
         MAX-ACCESS     read-only
         STATUS         current
         DESCRIPTION
            "Total Ports that this module supports."
         ::= { adGenOpticalCarrierProductEntry 3 }

--==================================================================================================================
--==================================================================================================================

   adGenOpticalCarrierProductPortTable OBJECT-TYPE
      SYNTAX  SEQUENCE OF AdGenOpticalCarrierProductPortEntry
      MAX-ACCESS  not-accessible
      STATUS  current
      DESCRIPTION
         "The Optical Carrier Product Port table."
      ::= { adGenOpticalCarrierProduct 2 }

   adGenOpticalCarrierProductPortEntry OBJECT-TYPE
      SYNTAX  AdGenOpticalCarrierProductPortEntry
      MAX-ACCESS  not-accessible
      STATUS  current
      DESCRIPTION
         "An entry in the Optical Carrier Product Port table."
      INDEX  { adGenSlotInfoIndex,
               adGenSubSlotProdInfoIndex,
               adGenOpticalCarrierProdPortInfoIndex  }
      ::= { adGenOpticalCarrierProductPortTable 1 }

   AdGenOpticalCarrierProductPortEntry ::=
      SEQUENCE {
                  adGenOpticalCarrierProdPortInfoIndex           Integer32,
                  adGenOpticalCarrierProdPortType                INTEGER,
                  adGenOpticalCarrierProdPortDirection           INTEGER,
                  adGenOpticalCarrierProdPortMinWaveLengthPicoMeter Integer32,
                  adGenOpticalCarrierProdPortMaxWaveLengthPicoMeter Integer32,
                  adGenOpticalCarrierProdPortInsertionLossDB  Integer32,
                  adGenOpticalCarrierProdPortIfIndexReference  InterfaceIndex
               }

      adGenOpticalCarrierProdPortInfoIndex OBJECT-TYPE
         SYNTAX         Integer32
         MAX-ACCESS     not-accessible
         STATUS         current
         DESCRIPTION
            "Optical Carrier Product Port Index."
         ::= { adGenOpticalCarrierProductPortEntry 1 }

      adGenOpticalCarrierProdPortType OBJECT-TYPE
         SYNTAX INTEGER  {
                            invalid(1),
                            add(2),
                            drop(3),
                            commonMUX(4),
                            commonDEMUX(5),
                            expressMUX(6),
                            expressDEMUX(7),
                            commonRX(8),
                            commonTX(9),
                            osc(10)
                         }
         MAX-ACCESS     read-only
         STATUS         current
         DESCRIPTION
            "Product Port Type.
             invalid = not able to retrieve information from card."
         ::= { adGenOpticalCarrierProductPortEntry 2 }

      adGenOpticalCarrierProdPortDirection OBJECT-TYPE
         SYNTAX INTEGER  {
                            invalid(1),
                            in(2),
                            out(3),
                            biDirection(4)
                         }
         MAX-ACCESS     read-only
         STATUS         current
         DESCRIPTION
            "Product Port Direction.
             invalid = not able to retrieve information from card."
         ::= { adGenOpticalCarrierProductPortEntry 3 }

      adGenOpticalCarrierProdPortMinWaveLengthPicoMeter OBJECT-TYPE
         SYNTAX         Integer32
         MAX-ACCESS     read-only
         STATUS         current
         DESCRIPTION
            "Product Port Minimum supported Wavelength in picometers."
         ::= { adGenOpticalCarrierProductPortEntry 4 }

      adGenOpticalCarrierProdPortMaxWaveLengthPicoMeter OBJECT-TYPE
         SYNTAX         Integer32
         MAX-ACCESS     read-only
         STATUS         current
         DESCRIPTION
            "Product Port Maximum supported Wavelength in picometers."
         ::= { adGenOpticalCarrierProductPortEntry 5 }

      adGenOpticalCarrierProdPortInsertionLossDB  OBJECT-TYPE
         SYNTAX         Integer32
         MAX-ACCESS     read-only
         STATUS         current
         DESCRIPTION
            "Product Port Insertion Loss in hundredths of a dB."
         ::= { adGenOpticalCarrierProductPortEntry 6 }

      adGenOpticalCarrierProdPortIfIndexReference  OBJECT-TYPE
         SYNTAX         InterfaceIndex
         MAX-ACCESS     read-only
         STATUS         current
         DESCRIPTION
            "This will return the ifIndex value for this particular port."
         ::= { adGenOpticalCarrierProductPortEntry 7 }


--=============================================================================
--=============================================================================

END
