ADTRAN-GENERIC-PEER-ADJACENCY-MIB

-- TITLE:     Generic Peer Adjacency MIB
-- PRODUCT:   TBD
-- VERSION:   1.0
-- DATE:      Oct. 20, 2011
-- AUTHOR:    Albert Sue
-- STATUS:    Created
--

DEFINITIONS ::= BEGIN

IMPORTS

   adGenPeerAdjacency,
   adGenPeerAdjacencyID       FROM ADTRAN-SHARED-CND-SYSTEM-MIB

   InterfaceIndex,
   ifIndex                   FROM IF-MIB

   OBJECT-TYPE,
   MODULE-IDENTITY,
   Integer32,
   IpAddress                 FROM SNMPv2-SMI

   TruthValue,
   DisplayString             FROM SNMPv2-TC;

adGenPeerAdjacencyMIB MODULE-IDENTITY
   LAST-UPDATED "201110260000Z"
   ORGANIZATION "Adtran, Inc."
   CONTACT-INFO
     "CND Tech Support
         Postal: ADTRAN, Inc.
                 901 Explorer Blvd.
                 Huntsville, AL  35806
                 Tel: +1 800 726-8663
                 Fax: +1 256 963 6217
                 E-mail: support@adtran.com"
   DESCRIPTION
      "This MIB defines the objects for the Generic Peer Adjacency MIB."

   REVISION "201110260000Z"
   DESCRIPTION "Created"

::= { adGenPeerAdjacencyID 1 }

  -- ///////////////////////////////////////////////////////
  -- Operation Groups
  -- ///////////////////////////////////////////////////////
  adGenPeerAdjacencyLogical              OBJECT IDENTIFIER ::= { adGenPeerAdjacency  1   }
  adGenPeerAdjacencyPhysical             OBJECT IDENTIFIER ::= { adGenPeerAdjacency  2   }

-- //////////////////////////////////////////////////////////////////
--                 adGenPeerAdjacencyLogical
-- //////////////////////////////////////////////////////////////////
    adGenPeerAdjacencyLogicalTable OBJECT-TYPE
        SYNTAX  SEQUENCE OF AdGenPeerAdjacencyLogicalEntry
        MAX-ACCESS  not-accessible
        STATUS  current
        DESCRIPTION
                   "Provisioning table."
        ::= { adGenPeerAdjacencyLogical 1 }

    -- /////////////////////////////////////////////////////////
    adGenPeerAdjacencyLogicalEntry OBJECT-TYPE
        SYNTAX  AdGenPeerAdjacencyLogicalEntry
        MAX-ACCESS  not-accessible
        STATUS  current
        DESCRIPTION
                   "Table Entry."
        INDEX   { ifIndex }
        ::= { adGenPeerAdjacencyLogicalTable 1 }

    -- /////////////////////////////////////////////////////////
    AdGenPeerAdjacencyLogicalEntry ::=
        SEQUENCE {
                        adGenPeerAdjacencyLogicalIpAddress      IpAddress,
                        adGenPeerAdjacencyLogicalChassisId      OCTET STRING,
                        adGenPeerAdjacencyLogicalPortId         OCTET STRING
                 }

    -- /////////////////////////////////////////////////////////
    adGenPeerAdjacencyLogicalIpAddress OBJECT-TYPE
    SYNTAX             IpAddress
    MAX-ACCESS         read-write
    STATUS             current
    DESCRIPTION
       "This provisions the IP Address of the peer device connected
        to this interface."
    ::= { adGenPeerAdjacencyLogicalEntry 1 }

    -- /////////////////////////////////////////////////////////
    adGenPeerAdjacencyLogicalChassisId OBJECT-TYPE
    SYNTAX             OCTET STRING
    MAX-ACCESS         read-write
    STATUS             current
    DESCRIPTION
       "This provisions the Chassis ID of the peer device connected
        to the this interface."
    ::= { adGenPeerAdjacencyLogicalEntry 2 }

    -- /////////////////////////////////////////////////////////
    adGenPeerAdjacencyLogicalPortId OBJECT-TYPE
    SYNTAX             OCTET STRING
    MAX-ACCESS         read-write
    STATUS             current
    DESCRIPTION
       "This provisions the Port ID of the peer device connected
        to the this interface."
    ::= { adGenPeerAdjacencyLogicalEntry 3 }

-- //////////////////////////////////////////////////////////////////
--                 adGenPeerAdjacencyPhysical
-- //////////////////////////////////////////////////////////////////
    adGenPeerAdjacencyPhysicalTable OBJECT-TYPE
        SYNTAX  SEQUENCE OF AdGenPeerAdjacencyPhysicalEntry
        MAX-ACCESS  not-accessible
        STATUS  current
        DESCRIPTION
                   "Provisioning table."
        ::= { adGenPeerAdjacencyPhysical 1 }

    -- /////////////////////////////////////////////////////////
    adGenPeerAdjacencyPhysicalEntry OBJECT-TYPE
        SYNTAX  AdGenPeerAdjacencyPhysicalEntry
        MAX-ACCESS  not-accessible
        STATUS  current
        DESCRIPTION
                   "Table Entry."
        INDEX   { ifIndex }
        ::= { adGenPeerAdjacencyPhysicalTable 1 }

    -- /////////////////////////////////////////////////////////
    AdGenPeerAdjacencyPhysicalEntry ::=
        SEQUENCE {
                        adGenPeerAdjacencyPhysicalOneDescriptionTx    OCTET STRING,
                        adGenPeerAdjacencyPhysicalOneDescriptionRx    OCTET STRING,
                        adGenPeerAdjacencyPhysicalOneIpAddressTx      IpAddress,
                        adGenPeerAdjacencyPhysicalOneIpAddressRx      IpAddress,
                        adGenPeerAdjacencyPhysicalOneChassisIdTx      OCTET STRING,
                        adGenPeerAdjacencyPhysicalOneChassisIdRx      OCTET STRING,
                        adGenPeerAdjacencyPhysicalOnePortIdTx         OCTET STRING,
                        adGenPeerAdjacencyPhysicalOnePortIdRx         OCTET STRING,
                        adGenPeerAdjacencyPhysicalOneUnknownDeviceTx  TruthValue,
                        adGenPeerAdjacencyPhysicalOneUnknownDeviceRx  TruthValue,

                        adGenPeerAdjacencyPhysicalTwoDescriptionTx    OCTET STRING,
                        adGenPeerAdjacencyPhysicalTwoDescriptionRx    OCTET STRING,
                        adGenPeerAdjacencyPhysicalTwoIpAddressTx      IpAddress,
                        adGenPeerAdjacencyPhysicalTwoIpAddressRx      IpAddress,
                        adGenPeerAdjacencyPhysicalTwoChassisIdTx      OCTET STRING,
                        adGenPeerAdjacencyPhysicalTwoChassisIdRx      OCTET STRING,
                        adGenPeerAdjacencyPhysicalTwoPortIdTx         OCTET STRING,
                        adGenPeerAdjacencyPhysicalTwoPortIdRx         OCTET STRING,
                        adGenPeerAdjacencyPhysicalTwoUnknownDeviceTx  TruthValue,
                        adGenPeerAdjacencyPhysicalTwoUnknownDeviceRx  TruthValue,

                        adGenPeerAdjacencyPhysicalOneDescription      OCTET STRING,
                        adGenPeerAdjacencyPhysicalOneIpAddress        IpAddress,
                        adGenPeerAdjacencyPhysicalOneChassisId        OCTET STRING,
                        adGenPeerAdjacencyPhysicalOnePortId           OCTET STRING,
                        adGenPeerAdjacencyPhysicalOneUnknownDevice    TruthValue,

                        adGenPeerAdjacencyPhysicalTwoDescription      OCTET STRING,
                        adGenPeerAdjacencyPhysicalTwoIpAddress        IpAddress,
                        adGenPeerAdjacencyPhysicalTwoChassisId        OCTET STRING,
                        adGenPeerAdjacencyPhysicalTwoPortId           OCTET STRING,
                        adGenPeerAdjacencyPhysicalTwoUnknownDevice    TruthValue

                 }
    -- /////////////////////////////////////////////////////////
    adGenPeerAdjacencyPhysicalOneDescriptionTx OBJECT-TYPE
    SYNTAX             OCTET STRING
    MAX-ACCESS         read-write
    STATUS             current
    DESCRIPTION
       "This provisions the description of the physical peer device connected
        to the Transmit component of a bi-directional interface."
    ::= { adGenPeerAdjacencyPhysicalEntry 1 }

    -- /////////////////////////////////////////////////////////
    adGenPeerAdjacencyPhysicalOneDescriptionRx OBJECT-TYPE
    SYNTAX             OCTET STRING
    MAX-ACCESS         read-write
    STATUS             current
    DESCRIPTION
       "This provisions the description of the physical peer device connected
        to the Receive component of a bi-directional interface."
    ::= { adGenPeerAdjacencyPhysicalEntry 2 }

    -- /////////////////////////////////////////////////////////
    adGenPeerAdjacencyPhysicalOneIpAddressTx OBJECT-TYPE
    SYNTAX             IpAddress
    MAX-ACCESS         read-write
    STATUS             current
    DESCRIPTION
       "This provisions the IP Address of the physical peer device connected
        to the Transmit component of a bi-directional interface."
    ::= { adGenPeerAdjacencyPhysicalEntry 3 }

    -- /////////////////////////////////////////////////////////
    adGenPeerAdjacencyPhysicalOneIpAddressRx OBJECT-TYPE
    SYNTAX             IpAddress
    MAX-ACCESS         read-write
    STATUS             current
    DESCRIPTION
       "This provisions the IP Address of the physical peer device connected
        to the Receive component of a bi-directional interface."
    ::= { adGenPeerAdjacencyPhysicalEntry 4 }

    -- /////////////////////////////////////////////////////////
    adGenPeerAdjacencyPhysicalOneChassisIdTx OBJECT-TYPE
    SYNTAX             OCTET STRING
    MAX-ACCESS         read-write
    STATUS             current
    DESCRIPTION
       "This provisions the Chassis ID of the physical peer device connected
        to the Transmit component of a bi-directional interface."
    ::= { adGenPeerAdjacencyPhysicalEntry 5 }

    -- /////////////////////////////////////////////////////////
    adGenPeerAdjacencyPhysicalOneChassisIdRx OBJECT-TYPE
    SYNTAX             OCTET STRING
    MAX-ACCESS         read-write
    STATUS             current
    DESCRIPTION
       "This provisions the Chassis ID of the physical peer device connected
        to the Receive component of a bi-directional interface."
    ::= { adGenPeerAdjacencyPhysicalEntry 6 }

    -- /////////////////////////////////////////////////////////
    adGenPeerAdjacencyPhysicalOnePortIdTx OBJECT-TYPE
    SYNTAX             OCTET STRING
    MAX-ACCESS         read-write
    STATUS             current
    DESCRIPTION
       "This provisions the Port ID of the physical peer device connected
        to the Transmit component of a bi-directional interface."
    ::= { adGenPeerAdjacencyPhysicalEntry 7 }

    -- /////////////////////////////////////////////////////////
    adGenPeerAdjacencyPhysicalOnePortIdRx OBJECT-TYPE
    SYNTAX             OCTET STRING
    MAX-ACCESS         read-write
    STATUS             current
    DESCRIPTION
       "This provisions the Port ID of the physical peer device connected
        to the Receive component of a bi-directional interface."
    ::= { adGenPeerAdjacencyPhysicalEntry 8 }

    -- /////////////////////////////////////////////////////////
    adGenPeerAdjacencyPhysicalOneUnknownDeviceTx OBJECT-TYPE
    SYNTAX             TruthValue
    MAX-ACCESS         read-write
    STATUS             current
    DESCRIPTION
       "This provisions whether the physical peer device connected
        to the Transmit component of a bi-directional interface is
        unknown or not.

        This is set by user to true, when the peer device does not support
        the provisioning of physical peer information, or when the connected
        device is a non-Adtran product."
    ::= { adGenPeerAdjacencyPhysicalEntry 9 }

    -- /////////////////////////////////////////////////////////
    adGenPeerAdjacencyPhysicalOneUnknownDeviceRx OBJECT-TYPE
    SYNTAX             TruthValue
    MAX-ACCESS         read-write
    STATUS             current
    DESCRIPTION
       "This provisions whether the physical peer device connected
        to the Receive component of a bi-directional interface is
        unknown or not.

        This is set by user to true, when the peer device does not support
        the provisioning of physical peer information, or when the connected
        device is a non-Adtran product."
    ::= { adGenPeerAdjacencyPhysicalEntry 10 }

    -- /////////////////////////////////////////////////////////
    adGenPeerAdjacencyPhysicalTwoDescriptionTx OBJECT-TYPE
    SYNTAX             OCTET STRING
    MAX-ACCESS         read-write
    STATUS             current
    DESCRIPTION
       "This provisions the description of the physical peer device connected
        to the Transmit component of a bi-directional interface.

        This object is applicable only when two peer devices are connected
        to the interface using a Y-cable."
    ::= { adGenPeerAdjacencyPhysicalEntry 11 }

    -- /////////////////////////////////////////////////////////
    adGenPeerAdjacencyPhysicalTwoDescriptionRx OBJECT-TYPE
    SYNTAX             OCTET STRING
    MAX-ACCESS         read-write
    STATUS             current
    DESCRIPTION
       "This provisions the description of the physical peer device connected
        to the Receive component of a bi-directional interface.

        This object is applicable only when two peer devices are connected
        to the interface using a Y-cable."
    ::= { adGenPeerAdjacencyPhysicalEntry 12 }

    -- /////////////////////////////////////////////////////////
    adGenPeerAdjacencyPhysicalTwoIpAddressTx OBJECT-TYPE
    SYNTAX             IpAddress
    MAX-ACCESS         read-write
    STATUS             current
    DESCRIPTION
       "This provisions the IP Address of the physical peer device connected
        to the Transmit component of a bi-directional interface.

        This object is applicable only when two peer devices are connected
        to the interface using a Y-cable."
    ::= { adGenPeerAdjacencyPhysicalEntry 13 }

    -- /////////////////////////////////////////////////////////
    adGenPeerAdjacencyPhysicalTwoIpAddressRx OBJECT-TYPE
    SYNTAX             IpAddress
    MAX-ACCESS         read-write
    STATUS             current
    DESCRIPTION
       "This provisions the IP Address of the physical peer device connected
        to the Receive component of a bi-directional interface.

        This object is applicable only when two peer devices are connected
        to the interface using a Y-cable."
    ::= { adGenPeerAdjacencyPhysicalEntry 14 }

    -- /////////////////////////////////////////////////////////
    adGenPeerAdjacencyPhysicalTwoChassisIdTx OBJECT-TYPE
    SYNTAX             OCTET STRING
    MAX-ACCESS         read-write
    STATUS             current
    DESCRIPTION
       "This provisions the Chassis ID of the physical peer device connected
        to the Transmit component of a bi-directional interface.

        This object is applicable only when two peer devices are connected
        to the interface using a Y-cable."
    ::= { adGenPeerAdjacencyPhysicalEntry 15 }

    -- /////////////////////////////////////////////////////////
    adGenPeerAdjacencyPhysicalTwoChassisIdRx OBJECT-TYPE
    SYNTAX             OCTET STRING
    MAX-ACCESS         read-write
    STATUS             current
    DESCRIPTION
       "This provisions the Chassis ID of the physical peer device connected
        to the Receive component of a bi-directional interface.

        This object is applicable only when two peer devices are connected
        to the interface using a Y-cable."
    ::= { adGenPeerAdjacencyPhysicalEntry 16 }

    -- /////////////////////////////////////////////////////////
    adGenPeerAdjacencyPhysicalTwoPortIdTx OBJECT-TYPE
    SYNTAX             OCTET STRING
    MAX-ACCESS         read-write
    STATUS             current
    DESCRIPTION
       "This provisions the Port ID of the physical peer device connected
        to the Transmit component of a bi-directional interface.

        This object is applicable only when two peer devices are connected
        to the interface using a Y-cable."
    ::= { adGenPeerAdjacencyPhysicalEntry 17 }

    -- /////////////////////////////////////////////////////////
    adGenPeerAdjacencyPhysicalTwoPortIdRx OBJECT-TYPE
    SYNTAX             OCTET STRING
    MAX-ACCESS         read-write
    STATUS             current
    DESCRIPTION
       "This provisions the Port ID of the physical peer device connected
        to the Receive component of a bi-directional interface.

        This object is applicable only when two peer devices are connected
        to the interface using a Y-cable."
    ::= { adGenPeerAdjacencyPhysicalEntry 18 }

    -- /////////////////////////////////////////////////////////
    adGenPeerAdjacencyPhysicalTwoUnknownDeviceTx OBJECT-TYPE
    SYNTAX             TruthValue
    MAX-ACCESS         read-write
    STATUS             current
    DESCRIPTION
       "This provisions whether the physical peer device connected
        to the Transmit component of a bi-directional interface is
        unknown or not.

        This is set by user to true, when the peer device does not support
        the provisioning of physical peer information, or when the connected
        device is a non-Adtran product.

        This object is applicable only when two peer devices are connected
        to the interface using a Y-cable."
    ::= { adGenPeerAdjacencyPhysicalEntry 19 }

    -- /////////////////////////////////////////////////////////
    adGenPeerAdjacencyPhysicalTwoUnknownDeviceRx OBJECT-TYPE
    SYNTAX             TruthValue
    MAX-ACCESS         read-write
    STATUS             current
    DESCRIPTION
       "This provisions whether the physical peer device connected
        to the Receive component of a bi-directional interface is
        unknown or not.

        This is set by user to true, when the peer device does not support
        the provisioning of physical peer information, or when the connected
        device is a non-Adtran product.

        This object is applicable only when two peer devices are connected
        to the interface using a Y-cable."
    ::= { adGenPeerAdjacencyPhysicalEntry 20 }

    -- /////////////////////////////////////////////////////////
    adGenPeerAdjacencyPhysicalOneDescription OBJECT-TYPE
    SYNTAX             OCTET STRING
    MAX-ACCESS         read-write
    STATUS             current
    DESCRIPTION
       "This provisions the description of the physical peer device connected."
    ::= { adGenPeerAdjacencyPhysicalEntry 21 }

    -- /////////////////////////////////////////////////////////
    adGenPeerAdjacencyPhysicalOneIpAddress OBJECT-TYPE
    SYNTAX             IpAddress
    MAX-ACCESS         read-write
    STATUS             current
    DESCRIPTION
       "This provisions the IP Address of the physical peer device connected."
    ::= { adGenPeerAdjacencyPhysicalEntry 22 }

    -- /////////////////////////////////////////////////////////
    adGenPeerAdjacencyPhysicalOneChassisId OBJECT-TYPE
    SYNTAX             OCTET STRING
    MAX-ACCESS         read-write
    STATUS             current
    DESCRIPTION
       "This provisions the Chassis ID of the physical peer device connected."
    ::= { adGenPeerAdjacencyPhysicalEntry 23 }

    -- /////////////////////////////////////////////////////////
    adGenPeerAdjacencyPhysicalOnePortId OBJECT-TYPE
    SYNTAX             OCTET STRING
    MAX-ACCESS         read-write
    STATUS             current
    DESCRIPTION
       "This provisions the Port ID of the physical peer device connected."
    ::= { adGenPeerAdjacencyPhysicalEntry 24 }

    -- /////////////////////////////////////////////////////////
    adGenPeerAdjacencyPhysicalOneUnknownDevice OBJECT-TYPE
    SYNTAX             TruthValue
    MAX-ACCESS         read-write
    STATUS             current
    DESCRIPTION
       "This provisions whether the physical peer device connected is unknown or not.

        This is set by user to true, when the peer device does not support
        the provisioning of physical peer information, or when the connected
        device is a non-Adtran product."
    ::= { adGenPeerAdjacencyPhysicalEntry 25 }

    -- /////////////////////////////////////////////////////////
    adGenPeerAdjacencyPhysicalTwoDescription OBJECT-TYPE
    SYNTAX             OCTET STRING
    MAX-ACCESS         read-write
    STATUS             current
    DESCRIPTION
       "This provisions the description of the physical peer device connected.

        This object is applicable only when two peer devices are connected
        to the interface using a Y-cable."
    ::= { adGenPeerAdjacencyPhysicalEntry 26 }

    -- /////////////////////////////////////////////////////////
    adGenPeerAdjacencyPhysicalTwoIpAddress OBJECT-TYPE
    SYNTAX             IpAddress
    MAX-ACCESS         read-write
    STATUS             current
    DESCRIPTION
       "This provisions the IP Address of the physical peer device connected.

        This object is applicable only when two peer devices are connected
        to the interface using a Y-cable."
    ::= { adGenPeerAdjacencyPhysicalEntry 27 }

    -- /////////////////////////////////////////////////////////
    adGenPeerAdjacencyPhysicalTwoChassisId OBJECT-TYPE
    SYNTAX             OCTET STRING
    MAX-ACCESS         read-write
    STATUS             current
    DESCRIPTION
       "This provisions the Chassis ID of the physical peer device connected.

        This object is applicable only when two peer devices are connected
        to the interface using a Y-cable."
    ::= { adGenPeerAdjacencyPhysicalEntry 28 }

    -- /////////////////////////////////////////////////////////
    adGenPeerAdjacencyPhysicalTwoPortId OBJECT-TYPE
    SYNTAX             OCTET STRING
    MAX-ACCESS         read-write
    STATUS             current
    DESCRIPTION
       "This provisions the Port ID of the physical peer device connected.

        This object is applicable only when two peer devices are connected
        to the interface using a Y-cable."
    ::= { adGenPeerAdjacencyPhysicalEntry 29 }

    -- /////////////////////////////////////////////////////////
    adGenPeerAdjacencyPhysicalTwoUnknownDevice OBJECT-TYPE
    SYNTAX             TruthValue
    MAX-ACCESS         read-write
    STATUS             current
    DESCRIPTION
       "This provisions whether the physical peer device connected is unknown or not.

        This is set by user to true, when the peer device does not support
        the provisioning of physical peer information, or when the connected
        device is a non-Adtran product.

        This object is applicable only when two peer devices are connected
        to the interface using a Y-cable."
    ::= { adGenPeerAdjacencyPhysicalEntry 30 }

-- //////////////////////////////////////////////////////////////////

    END
