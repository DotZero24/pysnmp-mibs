ADTRAN-TA5K-DS3-EXTRAPERFS-MIB

    DEFINITIONS ::= BEGIN

    -- TITLE:     The ADTRAN Total Access TA5000 DS3  MIB
    -- PRODUCT:   1187200L1 and 1187201L1
    -- VERSION:   1.0
    -- DATE:      7/19/2007

    -- This MIB Contains tables specific to any DS3 interface
    -- This MIB should only contain information about the Daily Performance
    -- Values for a DS3 Interfaces

    -- MIBs supported:

    -- HISTORY:
--		07/19/2007	First Revision
--              09/20/2007      twc - Fixed SMIC compiler errors
--              03/31/2008      jlb - Added adTa5kDs3PMReset.


    IMPORTS
        MODULE-IDENTITY, OBJECT-TYPE, Counter32
            	FROM SNMPv2-SMI

	ifIndex
		FROM IF-MIB

        adTa5kSingleDs3,
	adTa5kSingleDs3ModuleIdentity
                FROM ADTRAN-TA5K-SingleDS3-MIB;

    adTa5kDs3PMModuleIdentity MODULE-IDENTITY
        LAST-UPDATED "201108300000Z"
        ORGANIZATION
            "ADTRAN, Inc."
        CONTACT-INFO
            "CND Tech Support
                Postal: ADTRAN, Inc.
                        901 Explorer Blvd.
                        Huntsville, AL  35806
                        Tel: +1 800 726-8663
                        Fax: +1 256 963 6217
                        E-mail: support@adtran.com"
        DESCRIPTION
            "Total Access 5000 DS3 PM MIB"
	    REVISION "201108300000Z"
			DESCRIPTION
			"Added the adTa5kDs3RollingCountTable Table to add rolling counters for the DS3 PM stats"
        ::= { adTa5kSingleDs3ModuleIdentity 1 }

    -- OBJECT IDENTIFIERS
        adTa5kDS3PM             OBJECT IDENTIFIER ::= { adTa5kSingleDs3 2 }

    -- ********************************************************************
       AdTADS3PerfCurrentCount  ::= Counter32
       AdTADS3PerfIntervalCount ::= Counter32
    -- ********************************************************************


    -- ********************************************************************
    -- ********************************************************************
    --                  adTa5kDS3PM (896.2)
    -- ********************************************************************
    -- ********************************************************************
    --                 DS3 PM Daily Section Current (896.2.1)
    -- ********************************************************************
    adTa5kDs3PMCurrentDayTable OBJECT-TYPE
        SYNTAX  SEQUENCE OF AdTa5kDs3PMCurrentDayEntry
        MAX-ACCESS  not-accessible
        STATUS      current
        DESCRIPTION
                   " Performance Monitoring Current Daily Table"
        ::= { adTa5kDS3PM 1 }

    adTa5kDs3PMCurrentDayEntry OBJECT-TYPE
        SYNTAX  AdTa5kDs3PMCurrentDayEntry
        MAX-ACCESS  not-accessible
        STATUS      current
        DESCRIPTION
                   "Table Entry"
        INDEX   { ifIndex }
        ::= { adTa5kDs3PMCurrentDayTable 1 }

    AdTa5kDs3PMCurrentDayEntry ::=
        SEQUENCE {
                    adTa5kDs3PMDayCurrentPESs    AdTADS3PerfCurrentCount,
                    adTa5kDs3PMDayCurrentPSESs   AdTADS3PerfCurrentCount,
                    adTa5kDs3PMDayCurrentSEFSs   AdTADS3PerfCurrentCount,
                    adTa5kDs3PMDayCurrentUASs    AdTADS3PerfCurrentCount,
                    adTa5kDs3PMDayCurrentLCVs    AdTADS3PerfCurrentCount,
                    adTa5kDs3PMDayCurrentPCVs    AdTADS3PerfCurrentCount,
                    adTa5kDs3PMDayCurrentLESs    AdTADS3PerfCurrentCount,
                    adTa5kDs3PMDayCurrentCCVs    AdTADS3PerfCurrentCount,
                    adTa5kDs3PMDayCurrentCESs    AdTADS3PerfCurrentCount,
                    adTa5kDs3PMDayCurrentCSESs   AdTADS3PerfCurrentCount
                 }

    adTa5kDs3PMDayCurrentPESs OBJECT-TYPE
           SYNTAX       AdTADS3PerfCurrentCount
           MAX-ACCESS   read-only
           STATUS       current
           DESCRIPTION
                        "PM - Section CV."
     ::= { adTa5kDs3PMCurrentDayEntry 1 }

    adTa5kDs3PMDayCurrentPSESs OBJECT-TYPE
           SYNTAX       AdTADS3PerfCurrentCount
           MAX-ACCESS   read-only
           STATUS       current
           DESCRIPTION
                        "PM - Section ES."
     ::= { adTa5kDs3PMCurrentDayEntry 2 }

    adTa5kDs3PMDayCurrentSEFSs OBJECT-TYPE
           SYNTAX       AdTADS3PerfCurrentCount
           MAX-ACCESS   read-only
           STATUS       current
           DESCRIPTION
                        "PM - Section SES."
     ::= { adTa5kDs3PMCurrentDayEntry 3 }

    adTa5kDs3PMDayCurrentUASs OBJECT-TYPE
           SYNTAX       AdTADS3PerfCurrentCount
           MAX-ACCESS   read-only
           STATUS       current
           DESCRIPTION
                        "PM - Section SEFS."
     ::= { adTa5kDs3PMCurrentDayEntry 4 }

    adTa5kDs3PMDayCurrentLCVs OBJECT-TYPE
           SYNTAX       AdTADS3PerfCurrentCount
           MAX-ACCESS   read-only
           STATUS       current
           DESCRIPTION
                        "PM - Section CV."
     ::= { adTa5kDs3PMCurrentDayEntry 5 }

    adTa5kDs3PMDayCurrentPCVs OBJECT-TYPE
           SYNTAX       AdTADS3PerfCurrentCount
           MAX-ACCESS   read-only
           STATUS       current
           DESCRIPTION
                        "PM - Section ES."
     ::= { adTa5kDs3PMCurrentDayEntry 6 }

    adTa5kDs3PMDayCurrentLESs OBJECT-TYPE
           SYNTAX       AdTADS3PerfCurrentCount
           MAX-ACCESS   read-only
           STATUS       current
           DESCRIPTION
                        "PM - Section SES."
     ::= { adTa5kDs3PMCurrentDayEntry 7 }

    adTa5kDs3PMDayCurrentCCVs OBJECT-TYPE
           SYNTAX       AdTADS3PerfCurrentCount
           MAX-ACCESS   read-only
           STATUS       current
           DESCRIPTION
                        "PM - Section SEFS."
     ::= { adTa5kDs3PMCurrentDayEntry 8 }

    adTa5kDs3PMDayCurrentCESs OBJECT-TYPE
           SYNTAX       AdTADS3PerfCurrentCount
           MAX-ACCESS   read-only
           STATUS       current
           DESCRIPTION
                        "PM - Section SES."
     ::= { adTa5kDs3PMCurrentDayEntry 9 }

    adTa5kDs3PMDayCurrentCSESs OBJECT-TYPE
           SYNTAX       AdTADS3PerfCurrentCount
           MAX-ACCESS   read-only
           STATUS       current
           DESCRIPTION
                        "PM - Section SEFS."
     ::= { adTa5kDs3PMCurrentDayEntry 10 }

    -- ********************************************************************
    --                 DS3 PM Daily Section Interval (896.2.2)
    -- ********************************************************************
    adTa5kDs3PMIntervalDayTable OBJECT-TYPE
        SYNTAX  SEQUENCE OF AdTa5kDs3PMIntervalDayEntry
        MAX-ACCESS  not-accessible
        STATUS      current
        DESCRIPTION
                   " Performance Monitoring Interval Daily Table"
        ::= { adTa5kDS3PM 2 }

    adTa5kDs3PMIntervalDayEntry OBJECT-TYPE
        SYNTAX  AdTa5kDs3PMIntervalDayEntry
        MAX-ACCESS  not-accessible
        STATUS      current
        DESCRIPTION
                   "Table Entry"
        INDEX   { ifIndex , adTa5kDs3PMDayIntervalNumber}
        ::= { adTa5kDs3PMIntervalDayTable 1 }

    AdTa5kDs3PMIntervalDayEntry ::=
        SEQUENCE {
                    adTa5kDs3PMDayIntervalPESs    AdTADS3PerfIntervalCount,
                    adTa5kDs3PMDayIntervalPSESs   AdTADS3PerfIntervalCount,
                    adTa5kDs3PMDayIntervalSEFSs   AdTADS3PerfIntervalCount,
                    adTa5kDs3PMDayIntervalUASs    AdTADS3PerfIntervalCount,
                    adTa5kDs3PMDayIntervalLCVs    AdTADS3PerfIntervalCount,
                    adTa5kDs3PMDayIntervalPCVs    AdTADS3PerfIntervalCount,
                    adTa5kDs3PMDayIntervalLESs    AdTADS3PerfIntervalCount,
                    adTa5kDs3PMDayIntervalCCVs    AdTADS3PerfIntervalCount,
                    adTa5kDs3PMDayIntervalCESs    AdTADS3PerfIntervalCount,
                    adTa5kDs3PMDayIntervalCSESs   AdTADS3PerfIntervalCount,
                    adTa5kDs3PMDayIntervalNumber  INTEGER
                 }

    adTa5kDs3PMDayIntervalPESs OBJECT-TYPE
           SYNTAX       AdTADS3PerfIntervalCount
           MAX-ACCESS   read-only
           STATUS       current
           DESCRIPTION
                        "PM - Section CV."
     ::= { adTa5kDs3PMIntervalDayEntry 1 }

    adTa5kDs3PMDayIntervalPSESs OBJECT-TYPE
           SYNTAX       AdTADS3PerfIntervalCount
           MAX-ACCESS   read-only
           STATUS       current
           DESCRIPTION
                        "PM - Section ES."
     ::= { adTa5kDs3PMIntervalDayEntry 2 }

    adTa5kDs3PMDayIntervalSEFSs OBJECT-TYPE
           SYNTAX       AdTADS3PerfIntervalCount
           MAX-ACCESS   read-only
           STATUS       current
           DESCRIPTION
                        "PM - Section SES."
     ::= { adTa5kDs3PMIntervalDayEntry 3 }

    adTa5kDs3PMDayIntervalUASs OBJECT-TYPE
           SYNTAX       AdTADS3PerfIntervalCount
           MAX-ACCESS   read-only
           STATUS       current
           DESCRIPTION
                        "PM - Section SEFS."
     ::= { adTa5kDs3PMIntervalDayEntry 4 }

    adTa5kDs3PMDayIntervalLCVs OBJECT-TYPE
           SYNTAX       AdTADS3PerfIntervalCount
           MAX-ACCESS   read-only
           STATUS       current
           DESCRIPTION
                        "PM - Section CV."
     ::= { adTa5kDs3PMIntervalDayEntry 5 }

    adTa5kDs3PMDayIntervalPCVs OBJECT-TYPE
           SYNTAX       AdTADS3PerfIntervalCount
           MAX-ACCESS   read-only
           STATUS       current
           DESCRIPTION
                        "PM - Section ES."
     ::= { adTa5kDs3PMIntervalDayEntry 6 }

    adTa5kDs3PMDayIntervalLESs OBJECT-TYPE
           SYNTAX       AdTADS3PerfIntervalCount
           MAX-ACCESS   read-only
           STATUS       current
           DESCRIPTION
                        "PM - Section SES."
     ::= { adTa5kDs3PMIntervalDayEntry 7 }

    adTa5kDs3PMDayIntervalCCVs OBJECT-TYPE
           SYNTAX       AdTADS3PerfIntervalCount
           MAX-ACCESS   read-only
           STATUS       current
           DESCRIPTION
                        "PM - Section SEFS."
     ::= { adTa5kDs3PMIntervalDayEntry 8 }

    adTa5kDs3PMDayIntervalCESs OBJECT-TYPE
           SYNTAX       AdTADS3PerfIntervalCount
           MAX-ACCESS   read-only
           STATUS       current
           DESCRIPTION
                        "PM - Section SES."
     ::= { adTa5kDs3PMIntervalDayEntry 9 }

    adTa5kDs3PMDayIntervalCSESs OBJECT-TYPE
           SYNTAX       AdTADS3PerfIntervalCount
           MAX-ACCESS   read-only
           STATUS       current
           DESCRIPTION
                        "PM - Section SEFS."
     ::= { adTa5kDs3PMIntervalDayEntry 10 }

    adTa5kDs3PMDayIntervalNumber OBJECT-TYPE
           SYNTAX       INTEGER(1..7)
           MAX-ACCESS   read-only
           STATUS       current
           DESCRIPTION
                "A number between 1 and 7, where 1 is the most
             	recently completed 24 hour interval and 7 is
             	the 24 hour interval completed 6 days prior to
                interval 1."
     ::= { adTa5kDs3PMIntervalDayEntry 11 }

    -- ********************************************************************
    --                 DS3 PM Reset Section
    -- ********************************************************************
    adTa5kDs3PMResetTable OBJECT-TYPE
        SYNTAX  SEQUENCE OF AdTa5kDs3PMResetEntry
        MAX-ACCESS  not-accessible
        STATUS      current
        DESCRIPTION
                   " Performance Monitoring Reset Table"
        ::= { adTa5kDS3PM 3 }

    adTa5kDs3PMResetEntry OBJECT-TYPE
        SYNTAX  AdTa5kDs3PMResetEntry
        MAX-ACCESS  not-accessible
        STATUS      current
        DESCRIPTION
                   "Table Entry"
        INDEX   { ifIndex }
        ::= { adTa5kDs3PMResetTable 1 }

    AdTa5kDs3PMResetEntry ::=
        SEQUENCE {
                    adTa5kDs3PMReset    INTEGER
                 }

    adTa5kDs3PMReset OBJECT-TYPE
           SYNTAX       INTEGER
                        {
                        reset(1)
                        }
           MAX-ACCESS   read-write
           STATUS       current
           DESCRIPTION
                        "This entry resets the PM on the selected DS3 interface."
     ::= { adTa5kDs3PMResetEntry 1 }

    -- ********************************************************************
    --                 DS3 Rolling Counter Section
    -- ********************************************************************
    adTa5kDs3RollingCountTable OBJECT-TYPE
        SYNTAX  SEQUENCE OF AdTa5kDs3RollingCountEntry
        MAX-ACCESS  not-accessible
        STATUS      current
        DESCRIPTION
                   " DS3 Rolling Counter Table"
        ::= { adTa5kDS3PM 4 }

    adTa5kDs3RollingCountEntry OBJECT-TYPE
        SYNTAX  AdTa5kDs3RollingCountEntry
        MAX-ACCESS  not-accessible
        STATUS      current
        DESCRIPTION
                   "Table Entry"
        INDEX   { ifIndex }
        ::= { adTa5kDs3RollingCountTable 1 }

    AdTa5kDs3RollingCountEntry ::=
        SEQUENCE {
                    adTa5kDs3RollingCountPESs    Counter32,
                    adTa5kDs3RollingCountPSESs   Counter32,
                    adTa5kDs3RollingCountSEFSs   Counter32,
                    adTa5kDs3RollingCountUASs    Counter32,
                    adTa5kDs3RollingCountLCVs    Counter32,
                    adTa5kDs3RollingCountPCVs    Counter32,
                    adTa5kDs3RollingCountLESs    Counter32,
                    adTa5kDs3RollingCountCCVs    Counter32,
                    adTa5kDs3RollingCountCESs    Counter32,
                    adTa5kDs3RollingCountCSESs   Counter32,
                    adTa5kDs3RollingCountReset   INTEGER
                 }

    adTa5kDs3RollingCountPESs OBJECT-TYPE
           SYNTAX       Counter32
           MAX-ACCESS   read-only
           STATUS       current
           DESCRIPTION
                        "DS3 Rolling Counter- Section CV."
     ::= { adTa5kDs3RollingCountEntry 1 }

    adTa5kDs3RollingCountPSESs OBJECT-TYPE
           SYNTAX       Counter32
           MAX-ACCESS   read-only
           STATUS       current
           DESCRIPTION
                        "DS3 Rolling Counter- Section ES."
     ::= { adTa5kDs3RollingCountEntry 2 }

    adTa5kDs3RollingCountSEFSs OBJECT-TYPE
           SYNTAX       Counter32
           MAX-ACCESS   read-only
           STATUS       current
           DESCRIPTION
                        "DS3 Rolling Counter- Section SES."
     ::= { adTa5kDs3RollingCountEntry 3 }

    adTa5kDs3RollingCountUASs OBJECT-TYPE
           SYNTAX       Counter32
           MAX-ACCESS   read-only
           STATUS       current
           DESCRIPTION
                        "DS3 Rolling Counter- Section SEFS."
     ::= { adTa5kDs3RollingCountEntry 4 }

    adTa5kDs3RollingCountLCVs OBJECT-TYPE
           SYNTAX       Counter32
           MAX-ACCESS   read-only
           STATUS       current
           DESCRIPTION
                        "DS3 Rolling Counter- Section CV."
     ::= { adTa5kDs3RollingCountEntry 5 }

    adTa5kDs3RollingCountPCVs OBJECT-TYPE
           SYNTAX       Counter32
           MAX-ACCESS   read-only
           STATUS       current
           DESCRIPTION
                        "DS3 Rolling Counter- Section ES."
     ::= { adTa5kDs3RollingCountEntry 6 }

    adTa5kDs3RollingCountLESs OBJECT-TYPE
           SYNTAX       Counter32
           MAX-ACCESS   read-only
           STATUS       current
           DESCRIPTION
                        "DS3 Rolling Counter- Section SES."
     ::= { adTa5kDs3RollingCountEntry 7 }

    adTa5kDs3RollingCountCCVs OBJECT-TYPE
           SYNTAX       Counter32
           MAX-ACCESS   read-only
           STATUS       current
           DESCRIPTION
                        "DS3 Rolling Counter- Section SEFS."
     ::= { adTa5kDs3RollingCountEntry 8 }

    adTa5kDs3RollingCountCESs OBJECT-TYPE
           SYNTAX       Counter32
           MAX-ACCESS   read-only
           STATUS       current
           DESCRIPTION
                        "DS3 Rolling Counter- Section SES."
     ::= { adTa5kDs3RollingCountEntry 9 }

    adTa5kDs3RollingCountCSESs OBJECT-TYPE
           SYNTAX       Counter32
           MAX-ACCESS   read-only
           STATUS       current
           DESCRIPTION
                        "DS3 Rolling Counter- Section SEFS."
     ::= { adTa5kDs3RollingCountEntry 10 }

    adTa5kDs3RollingCountReset OBJECT-TYPE
           SYNTAX       INTEGER { reset(1) }
           MAX-ACCESS   read-write
           STATUS       current
           DESCRIPTION
                        "Setting 1 resets the DS3 Rolling Counters."
     ::= { adTa5kDs3RollingCountEntry 11 }
    END
