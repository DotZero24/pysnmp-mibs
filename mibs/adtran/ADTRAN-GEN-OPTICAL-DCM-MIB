ADTRAN-GEN-OPTICAL-DCM-MIB

-- TITLE:     The ADTRAN OPTICAL DCM MIB
-- PRODUCT:   TBD
-- VERSION:   1.0
-- DATE:      05/23/11
-- AUTHOR:    Albert Sue
-- STATUS:    PRELIMINARY

-- This MIB defines the object identifiers (OIDs) for the
-- ADTRAN GENERIC OPTICAL DCM MIB objects
-- ******************************************************************************************

DEFINITIONS ::= BEGIN

IMPORTS

   adGenOpticalDCM,
   adGenOpticalDCMID     FROM ADTRAN-SHARED-CND-SYSTEM-MIB

   OBJECT-TYPE,
   MODULE-IDENTITY,
   Integer32                 FROM SNMPv2-SMI

   DisplayString             FROM SNMPv2-TC

   InterfaceIndex            FROM IF-MIB

   adGenSlotInfoIndex        FROM ADTRAN-GENSLOT-MIB;

adGenOpticalDCMMIB MODULE-IDENTITY
   LAST-UPDATED "201201120000Z"
   ORGANIZATION "Adtran, Inc."
   CONTACT-INFO
     "CND Tech Support
         Postal: ADTRAN, Inc.
                 901 Explorer Blvd.
                 Huntsville, AL  35806
                 Tel: +1 800 726-8663
                 Fax: +1 256 963 6217
                 E-mail: support@adtran.com"
   DESCRIPTION
      "This MIB defines the objects for the Generic Optical DCM MIB."

   REVISION "201201120000Z"
   DESCRIPTION "Added adGenOpticalDCMPortIfIndexReference"

   REVISION "201105230000Z"
   DESCRIPTION "Created"

::= { adGenOpticalDCMID 1 }

adGenOpticalDCMProduct                     OBJECT IDENTIFIER ::= {adGenOpticalDCM 1}

--==================================================================================================================

   adGenOpticalDCMTable OBJECT-TYPE
      SYNTAX  SEQUENCE OF AdGenOpticalDCMEntry
      MAX-ACCESS  not-accessible
      STATUS  current
      DESCRIPTION
         "The Optical DCM table."
      ::= { adGenOpticalDCMProduct 1 }

   adGenOpticalDCMEntry OBJECT-TYPE
      SYNTAX  AdGenOpticalDCMEntry
      MAX-ACCESS  not-accessible
      STATUS  current
      DESCRIPTION
         "An entry in the Optical DCM table."
      INDEX  { adGenSlotInfoIndex }
      ::= { adGenOpticalDCMTable 1 }

   AdGenOpticalDCMEntry ::=
      SEQUENCE {
                  adGenOpticalDCMType          INTEGER,
                  adGenOpticalDCMGridSpacing   INTEGER,
                  adGenOpticalDCMNumOfPorts    Integer32
               }

      adGenOpticalDCMType OBJECT-TYPE
         SYNTAX INTEGER  {
                            dcmFTwentyKM(1),
                            dcmFFortyKM(2),
                            dcmFSixtyKM(3),
                            dcmFEightyKM(4),
                            dcmBTwentyKM(5),
                            dcmBFortyKM(6),
                            dcmBSixtyKM(7),
                            dcmBEightyKM(8)
                         }
         MAX-ACCESS     read-only
         STATUS         current
         DESCRIPTION
            "Product Type."
         ::= { adGenOpticalDCMEntry 1 }

      adGenOpticalDCMGridSpacing OBJECT-TYPE
         SYNTAX INTEGER  {
                            allRange(1),
                            twentyFiveGHz(2),
                            fiftyGHz(3),
                            oneHundredGHz(4)
                         }
         MAX-ACCESS     read-only
         STATUS         current
         DESCRIPTION
            "Grid Spacing."
         ::= { adGenOpticalDCMEntry 2 }

      adGenOpticalDCMNumOfPorts OBJECT-TYPE
         SYNTAX         Integer32
         MAX-ACCESS     read-only
         STATUS         current
         DESCRIPTION
            "Total Ports that this module supports."
         ::= { adGenOpticalDCMEntry 3 }

--=============================================================================
--=============================================================================

   adGenOpticalDCMPortTable OBJECT-TYPE
      SYNTAX  SEQUENCE OF AdGenOpticalDCMPortEntry
      MAX-ACCESS  not-accessible
      STATUS  current
      DESCRIPTION
         "The Optical DCM Port table."
      ::= { adGenOpticalDCMProduct 2 }

   adGenOpticalDCMPortEntry OBJECT-TYPE
      SYNTAX  AdGenOpticalDCMPortEntry
      MAX-ACCESS  not-accessible
      STATUS  current
      DESCRIPTION
         "An entry in the Optical DCM Port table."
      INDEX  { adGenSlotInfoIndex, adGenOpticalDCMPortInfoIndex }
      ::= { adGenOpticalDCMPortTable 1 }

   AdGenOpticalDCMPortEntry ::=
      SEQUENCE {
                  adGenOpticalDCMPortInfoIndex           Integer32,
                  adGenOpticalDCMPortType                INTEGER,
                  adGenOpticalDCMPortDirection           INTEGER,
                  adGenOpticalDCMPortMinWaveLengthPicoMeter Integer32,
                  adGenOpticalDCMPortMaxWaveLengthPicoMeter Integer32,
                  adGenOpticalDCMPortInsertionLossDB  Integer32,
                  adGenOpticalDCMPortIfIndexReference  InterfaceIndex

               }

      adGenOpticalDCMPortInfoIndex OBJECT-TYPE
         SYNTAX         Integer32
         MAX-ACCESS     not-accessible
         STATUS         current
         DESCRIPTION
            "Optical DCM Port Index."
         ::= { adGenOpticalDCMPortEntry 1 }

      adGenOpticalDCMPortType OBJECT-TYPE
         SYNTAX INTEGER  {
                            in(1),
                            out(2)
                         }
         MAX-ACCESS     read-only
         STATUS         current
         DESCRIPTION
            "DCM Port Type."
         ::= { adGenOpticalDCMPortEntry 2 }

      adGenOpticalDCMPortDirection OBJECT-TYPE
         SYNTAX INTEGER  {
                            in(1),
                            out(2)
                         }
         MAX-ACCESS     read-only
         STATUS         current
         DESCRIPTION
            "DCM Port Direction"
         ::= { adGenOpticalDCMPortEntry 3 }

      adGenOpticalDCMPortMinWaveLengthPicoMeter OBJECT-TYPE
         SYNTAX         Integer32
         MAX-ACCESS     read-only
         STATUS         current
         DESCRIPTION
            "DCM Port Minimum supported Wavelength in picometers."
         ::= { adGenOpticalDCMPortEntry 4 }

      adGenOpticalDCMPortMaxWaveLengthPicoMeter OBJECT-TYPE
         SYNTAX         Integer32
         MAX-ACCESS     read-only
         STATUS         current
         DESCRIPTION
            "DCM Port Maximum supported Wavelength in picometers."
         ::= { adGenOpticalDCMPortEntry 5 }

      adGenOpticalDCMPortInsertionLossDB  OBJECT-TYPE
         SYNTAX         Integer32
         MAX-ACCESS     read-only
         STATUS         current
         DESCRIPTION
            "DCM Port Insertion Loss in hundredths of a dB."
         ::= { adGenOpticalDCMPortEntry 6 }

      adGenOpticalDCMPortIfIndexReference  OBJECT-TYPE
         SYNTAX         InterfaceIndex
         MAX-ACCESS     read-only
         STATUS         current
         DESCRIPTION
            "This will return the ifIndex value for this particular port."
         ::= { adGenOpticalDCMPortEntry 7 }

--=============================================================================
--=============================================================================

END
