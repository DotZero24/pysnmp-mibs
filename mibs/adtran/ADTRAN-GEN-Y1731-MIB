ADTRAN-GEN-Y1731-MIB

--******************************************************************************
-- TITLE:     The ADTRAN GEN Y1731 MIB
-- PRODUCT:   EoCu and EoTDM network termination equipment
-- DATE:      06/27/11
-- AUTHOR:    Janet Baldazo
-- STATUS:    PRELIMINARY
--
-- This MIB defines the object identifier (OID) for the
-- ADTRAN Y.1731 MIB objects
--******************************************************************************
DEFINITIONS ::= BEGIN

    IMPORTS
        Unsigned32,
        Integer32,
        Counter32,
        OBJECT-TYPE,
        MODULE-IDENTITY,
        NOTIFICATION-TYPE
              FROM SNMPv2-SMI
        DisplayString,
        TimeStamp, RowStatus,
        TruthValue, MacAddress,
        TDomain, TAddress
            FROM SNMPv2-TC
    	adTrapInformSeqNum
            FROM ADTRAN-GENTRAPINFORM-MIB
        sysName
            FROM SNMPv2-MIB
        OBJECT-GROUP
            FROM SNMPv2-CONF
        adGenY1731,
        adGenY1731ID
            FROM ADTRAN-GEN-ETHERNET-OAM-MIB
        InterfaceIndexOrZero
            FROM IF-MIB        -- [RFC2863]
        LldpChassisId,
        LldpPortId,
        LldpPortIdSubtype
            FROM LLDP-MIB      -- [IEEExxx]
	adGenSlotInfoIndex
            FROM ADTRAN-GENSLOT-MIB
        ;

adGenY1731MIB MODULE-IDENTITY
   LAST-UPDATED "201407210000Z"
   ORGANIZATION "Adtran, Inc."
   CONTACT-INFO
     "CND Tech Support
         Postal: ADTRAN, Inc.
                 901 Explorer Blvd.
                 Huntsville, AL  35806
                 Tel: +1 800 726-8663
                 Fax: +1 256 963 6217
                 E-mail: support@adtran.com"
   DESCRIPTION
      "This MIB defines the objects for the Y.1731 MIB."
   REVISION "201407210000Z"
   DESCRIPTION "Added cfm to adGenY1731MegNameFormat and comments to adGenY1731MegNameLengthAndName."
   REVISION "201211080000Z"
   DESCRIPTION "Added varbind adGenSlotInfoIndex to the adGenY1731PMFlashFiles set and clear traps."
   REVISION "201206280000Z"
   DESCRIPTION "Added two traps for Y1731 PM Flash Files transfer."
   REVISION "201109260000Z"
   DESCRIPTION "Created"

::= { adGenY1731ID 1 }

--==============================================================================

adGenY1731MIBObjects        OBJECT IDENTIFIER  ::= { adGenY1731 1 }

--==============================================================================
adGenY1731Config           OBJECT IDENTIFIER ::= {adGenY1731MIBObjects 1}
adGenY1731Meg              OBJECT IDENTIFIER ::= {adGenY1731MIBObjects 2}
adGenY1731LocalMep         OBJECT IDENTIFIER ::= {adGenY1731MIBObjects 3}
adGenY1731Events           OBJECT IDENTIFIER ::= {adGenY1731MIBObjects 4}


adGenY1731MegMepList       OBJECT IDENTIFIER ::= {adGenY1731Meg 5}
adGenY1731MegMepListScalars OBJECT IDENTIFIER ::= {adGenY1731MegMepList 1}

adGenY1731LocalMepConfig        OBJECT IDENTIFIER ::= {adGenY1731LocalMep 1}
adGenY1731LocalMepConfigScalars OBJECT IDENTIFIER ::= {adGenY1731LocalMepConfig 1}

adGenY1731LocalMepRmepDb        OBJECT IDENTIFIER ::= {adGenY1731LocalMep 2}
adGenY1731LocalMepRmepDbScalars OBJECT IDENTIFIER ::= {adGenY1731LocalMepRmepDb 1}

adGenY1731LocalMepLbm           OBJECT IDENTIFIER ::= {adGenY1731LocalMep 3}

adGenY1731LocalMepDmm           OBJECT IDENTIFIER ::= {adGenY1731LocalMep 4}
adGenY1731DmmScalars            OBJECT IDENTIFIER ::= {adGenY1731LocalMepDmm 1}

adGenY1731LocalMepLmm           OBJECT IDENTIFIER ::= {adGenY1731LocalMep 5}
adGenY1731LmmScalars            OBJECT IDENTIFIER ::= {adGenY1731LocalMepLmm 1}

adGenY1731LocalMepLtm           OBJECT IDENTIFIER ::= {adGenY1731LocalMep 6}

adGenY1731LocalMepOneDm         OBJECT IDENTIFIER ::= {adGenY1731LocalMep 7}
adGenY1731OneDmScalars          OBJECT IDENTIFIER ::= {adGenY1731LocalMepOneDm 1}

adGenY1731LocalMepSlm           OBJECT IDENTIFIER ::= {adGenY1731LocalMep 8}
adGenY1731SlmScalars            OBJECT IDENTIFIER ::= {adGenY1731LocalMepSlm 1}

adGenY1731LocalMepClm           OBJECT IDENTIFIER ::= {adGenY1731LocalMep 9}

adGenY1731Traps            	 	OBJECT IDENTIFIER ::= { adGenY1731Events 0 }
--==============================================================================
--Y.1731 Configuration
--==============================================================================
adGenY1731Enable
OBJECT-TYPE
    SYNTAX      INTEGER {
                            enable(1),
                            disable(2)
                        }
    MAX-ACCESS  read-write
    STATUS      current
    DESCRIPTION
       "This OID is used to enable/disable Y.1731."
    ::= { adGenY1731Config 1 }

adGenY1731BulkDataExportInterval
OBJECT-TYPE
    SYNTAX      Integer32(30..300)
    MAX-ACCESS  read-write
    STATUS      current
    DESCRIPTION
       "The interval, in seconds, between Y.1731 PM file transfers to the
        management server.  The interval must be between 30 and 300 seconds.
        The default interval value is 300 seconds.
       "
    ::= { adGenY1731Config 2 }

adGenY1731LinktraceCacheHoldTime
OBJECT-TYPE
    SYNTAX      Integer32(1..65535)
    MAX-ACCESS  read-write
    STATUS      current
    DESCRIPTION
       "The Linktrace cache hold time specified in minutes. Linktrace replies in the Linktrace Reply Table
        (adGenY1731LocalMepLtrTable) will age out after the configured Linktrace cache hold time.
        The default Linktrace cache hold time value is 1 minute.
       "
    ::= { adGenY1731Config 3 }

adGenY1731LinktraceCacheSize
OBJECT-TYPE
    SYNTAX      Integer32(1..4095)
    MAX-ACCESS  read-write
    STATUS      current
    DESCRIPTION
       "The Linktrace cache size is the maximum entries that can be added stored in the Linktrace
        Reply Table (adGenY1731LocalMepLtrTable). Once the maximum size is reached, the oldest entry
        will be removed when a new one is inserted.
        The default cache size value is 10.
       "
    ::= { adGenY1731Config 4 }

--==============================================================================
--Y.1731 Meg Scalars
--==============================================================================

  adGenY1731MegMaxNumber OBJECT-TYPE
    SYNTAX      Unsigned32
    MAX-ACCESS  read-only
    STATUS      current
    DESCRIPTION
       "Maximum number of allowed Maintenenance Entity Groups."
     ::= { adGenY1731Meg 1 }

  adGenY1731MegCurrentNumber OBJECT-TYPE
    SYNTAX      Unsigned32
    MAX-ACCESS  read-only
    STATUS      current
    DESCRIPTION
       "Current number of MEGs."
     ::= { adGenY1731Meg 2 }

  adGenY1731MegLastCreateError OBJECT-TYPE
    SYNTAX      DisplayString
    MAX-ACCESS  read-only
    STATUS      current
    DESCRIPTION
       "The reason for the last error that occured while attempting to create
        an entry in the Maintenance Entity Group Table (adGenY1731MegTable)."
     ::= { adGenY1731Meg 3 }

--==============================================================================
--Y.1731 Meg Table
--==============================================================================
adGenY1731MegTable
OBJECT-TYPE
    SYNTAX  SEQUENCE OF AdGenY1731MegEntry
    MAX-ACCESS  not-accessible
    STATUS      current
    DESCRIPTION
       "The Y.1731 MEG table."
    ::= { adGenY1731Meg 4 }

adGenY1731MegEntry
OBJECT-TYPE
    SYNTAX      AdGenY1731MegEntry
    MAX-ACCESS  not-accessible
    STATUS      current
    DESCRIPTION
       "An entry in the Y.1731 MEG table."
    INDEX {
            adGenY1731MegLevel,
            adGenY1731MegNameFormat,
            adGenY1731MegNameLengthAndName
          }
    ::= { adGenY1731MegTable 1 }

AdGenY1731MegEntry ::= SEQUENCE {
      adGenY1731MegLevel                Integer32,
      adGenY1731MegNameFormat           INTEGER,
      adGenY1731MegNameLengthAndName    OCTET STRING,
      adGenY1731MegRowStatus            RowStatus,
      adGenY1731MegServiceTypeValueList OCTET STRING,
      adGenY1731MegCcmInterval          INTEGER,
      adGenY1731MegLocalMepConfigTableLastCreateError DisplayString,
      adGenY1731MegDisplayName          DisplayString
    }

adGenY1731MegLevel
OBJECT-TYPE
    SYNTAX      Integer32 (0..7)
    MAX-ACCESS  not-accessible
    STATUS      current
    DESCRIPTION
       "MEG level for the MEG."
    ::= { adGenY1731MegEntry 1 }

adGenY1731MegNameFormat
OBJECT-TYPE
    SYNTAX      INTEGER {
                    charString(2),
                    iccUmc(32),
                    cfm(256)
                }
    MAX-ACCESS  not-accessible
    STATUS      current
    DESCRIPTION
       "char-string - This is an IETF RFC 2579 DisplayString, with the
        exception that the character codes 0-31 (decimal) are not used.

        icc-umc - this consists of two subfields:
        (1) The ITU Carrier Code (ICC) followed by a unique MEG ID code (UMC).
            The ITU Carrier code consists of 1-6 left-justified characters,
            alphabetic, or leading alphabetic with trailing numeric.

        (2) The UMC code immediately follows the ICC and shall consist of 7-12
            characters.  The UMC shall be a matter for the organization to
            which the ICC has been assigned, provided that uniqueness is
            guaranteed.
        cfm - indicates the MEG name will follow the formatting rules defined by
        IEEE 802.1ag Connectivity Fault Management.  It will comprise of two names: a Maintenance
        Domain Name and a Maintenance Association Name.  Each name will have an associated name
        format.
       "
    ::= { adGenY1731MegEntry 2 }

adGenY1731MegNameLengthAndName
OBJECT-TYPE
    SYNTAX      OCTET STRING (SIZE (2..46))
    MAX-ACCESS  not-accessible
    STATUS      current
    DESCRIPTION
       "If adGenY1731MegNameFormat is char-string or icc-umc -
        The First octet represents the total length in octets of the MEG Name.
        Octets 2-46 represent the MEG Name associated with the MEG.

        If adGenY1731MegNameFormat is CFM - the adGenY1731MegNameLengthAndName field will be
        overridden to contain the IEEE 802.1ag MAID -> MD Name Format + MD Name Length + MD Name
        + MA Name Format + MA Name Length + MA Name.
       "
    ::= { adGenY1731MegEntry 3 }

adGenY1731MegRowStatus
OBJECT-TYPE
    SYNTAX      RowStatus
    MAX-ACCESS  read-create
    STATUS      current
    DESCRIPTION
       "This OID is used to create and delete the MEG.  The only supported
        settings are createAndGo, createAndWait, and destroy.
       "
    ::= { adGenY1731MegEntry 4 }

adGenY1731MegServiceTypeValueList
OBJECT-TYPE
    SYNTAX      OCTET STRING
    MAX-ACCESS  read-create
    STATUS      current
    DESCRIPTION
       "Octet string which defines the service type and value that maintenance
        points in the MEG reside and operate on.

        Expected format: First octet represents the overall format and order of
        service types. Subsequent octets represent list of service values.

        The order of the service values in the list must match the order
        specified by the first octet. The number of octets for an entry in the
        list depends on the type of service.  For VLAN tagged services the
        number of required octets is 2 for each tag.

        Options for the first octet are:
        untagged (1)
        single-tagged s-tag (2)
        single-tagged c-tag (3)
        single-tagged ce-tag (4)
        double-tagged s-tag c-tag (5)
        double-tagged s-tag ce-tag (6)
        triple-tagged s-tag c-tag ce-tag (7)

        Example of a MP residing on a untagged service:
        octet string = 0x01

        Example of a MP residing on a double-tagged s-tag ce-tag service with
        an s-tag value of 1000 and ce-tag value of 200
        octet string = 0x06, 0x03, 0xE8, 0x00, 0xC8

        Example of a MP residing on a single-tagged s-tag service having an
        s-tag value of 1000:
        octet string = 0x02, 0x03, 0xE8
       "
    ::= { adGenY1731MegEntry 5 }

adGenY1731MegCcmInterval
OBJECT-TYPE
    SYNTAX      INTEGER {
                    interval300Hz(1),
                    interval10ms(2),
                    interval100ms(3),
                    interval1s(4),
                    interval10s(5),
                    interval1min(6),
                    interval10min(7)
                }
    MAX-ACCESS  read-create
    STATUS      current
    DESCRIPTION
       "Interval between CCM transmissions to be used by all MEPs in the MEG.
        Default value is 1-second.
       "
    ::= { adGenY1731MegEntry 6 }

adGenY1731MegLocalMepConfigTableLastCreateError OBJECT-TYPE
         SYNTAX      DisplayString
         MAX-ACCESS  read-only
         STATUS      current
         DESCRIPTION
            "The reason for the last error that occured while attempting to create
             an entry in the MEG's local MEP Config Table
             (adGenY1731LocalMepConfigTable).
            "
         ::= { adGenY1731MegEntry 7 }

adGenY1731MegDisplayName
OBJECT-TYPE
    SYNTAX      DisplayString
    MAX-ACCESS  read-only
    STATUS      current
    DESCRIPTION
       "Represents the MEG Name associated with the MEG."
    ::= { adGenY1731MegEntry 8 }


--=============================================================================
--Y.1731 MEG MEP List Scalars
--=============================================================================

adGenY1731MegMepListMaxNumber
OBJECT-TYPE
    SYNTAX      Unsigned32
    MAX-ACCESS  read-only
    STATUS      current
    DESCRIPTION
       "Maximum number of allowed Maintenenance End Points that the device
        supports.  The number is the sum of all entries present in the local
        MEP table and the local MEP RMEP database table.
       "
    ::= { adGenY1731MegMepListScalars 1 }

adGenY1731MegMepListCurrentNumber
OBJECT-TYPE
    SYNTAX      Unsigned32
    MAX-ACCESS  read-only
    STATUS      current
    DESCRIPTION
       "Current number of MEPs in the MEG's list of MEPs."
    ::= { adGenY1731MegMepListScalars 2 }

adGenY1731MegMepListTableLastCreateError
OBJECT-TYPE
    SYNTAX      DisplayString
    MAX-ACCESS  read-only
    STATUS      current
    DESCRIPTION
       "The reason for the last error that occured while attempting to create
        an entry in the MEG MEP List (adGenY1731MegMepListTable).
       "
      ::= { adGenY1731MegMepListScalars 3 }

--=============================================================================
--Y.1731 MEG MEP List Table
--=============================================================================
adGenY1731MegMepListTable
OBJECT-TYPE
    SYNTAX      SEQUENCE OF AdGenY1731MegMepListEntry
    MAX-ACCESS  not-accessible
    STATUS      current
    DESCRIPTION
       "The list of all MEPs in the MEG.  For a device to create a local MEP it
        will need to create an entry in the adGenY1731LocalMepConfigTable.

        Once a local MEP is created, all other entries in the
        adGenY1731MegMepListTable are automatically considered remote MEPs of
        the local MEP and their information is used to populate
        the adGenY1731LocalMepRmepDbTable.

        The MEG MEP List should be the same across all devices in the MEG
        and contain the exact same list of adGenY1731MegMepListIdentifiers.

        On a given device, a MEPID in the MEG MEP list can transition from
        having no association to a local or remote MEP to any of the following
        (1) becoming a local MEP, (2) becoming a remote MEP of a local MEP, or
        (3) becoming both a local MEP and a remote MEP of a local MEP.  The
        third case is possible if two local MEPs in the same MEG are created
        on the same device.
       "
    ::= { adGenY1731MegMepList 2 }

adGenY1731MegMepListEntry
OBJECT-TYPE
    SYNTAX        AdGenY1731MegMepListEntry
    MAX-ACCESS    not-accessible
    STATUS        current
    DESCRIPTION
       "An entry in the Y.1731 MEG MEP list table."
    INDEX {adGenY1731MegLevel,
           adGenY1731MegNameFormat,
           adGenY1731MegNameLengthAndName,
           adGenY1731MegMepListIdentifier}
      ::= { adGenY1731MegMepListTable 1 }

AdGenY1731MegMepListEntry ::= SEQUENCE {
      adGenY1731MegMepListIdentifier   Integer32,
      adGenY1731MegMepListRowStatus    RowStatus
    }

adGenY1731MegMepListIdentifier
OBJECT-TYPE
    SYNTAX      Integer32 (1..8191)
    MAX-ACCESS  not-accessible
    STATUS      current
    DESCRIPTION
       "Integer that is unique among all the MEPs in the same MEG. Other
        definition is: a small integer, unique over a given Maintenance Entity
        Group, identifying a specific MEG End Point.

        MEP Identifier is also known as the MEPID.
       "
    ::= { adGenY1731MegMepListEntry 1 }

adGenY1731MegMepListRowStatus
OBJECT-TYPE
    SYNTAX      RowStatus
    MAX-ACCESS  read-create
    STATUS      current
    DESCRIPTION
       "This OID is used to create/delete the MEG MEP list entry.  The only
        supported settings are createAndGo, createAndWait, and destroy.
       "
    ::= { adGenY1731MegMepListEntry 2 }


--=============================================================================
--Y.1731 Local MEP Scalars
--=============================================================================

adGenY1731LocalMepMaxNumber
OBJECT-TYPE
      SYNTAX      Unsigned32
      MAX-ACCESS  read-only
      STATUS      current
      DESCRIPTION
         "Maximum number of allowed local Maintenenance End Points."
      ::= { adGenY1731LocalMepConfigScalars 1 }

adGenY1731LocalMepCurrentNumber
OBJECT-TYPE
      SYNTAX      Unsigned32
      MAX-ACCESS  read-only
      STATUS      current
      DESCRIPTION
       "Current number of local MEPs."
      ::= { adGenY1731LocalMepConfigScalars 2 }

adGenY1731LocalMepConfigTableLastCreateError OBJECT-TYPE
      SYNTAX      DisplayString
      MAX-ACCESS  read-only
      STATUS      current
      DESCRIPTION
       "The reason for the last error that occured while attempting to create
        an entry in the local MEP Table (adGenY1731LocalMepConfigTable).
       "
      ::= { adGenY1731LocalMepConfigScalars 3 }

--=============================================================================
--Y.1731 Local MEP Config Table
--=============================================================================

adGenY1731LocalMepConfigTable
OBJECT-TYPE
    SYNTAX      SEQUENCE OF AdGenY1731LocalMepConfigEntry
    MAX-ACCESS  not-accessible
    STATUS      current
    DESCRIPTION
       "The Y.1731 local MEP table.  A local MEP is one that resides on an
        interface of the system.
       "
    ::= { adGenY1731LocalMepConfig 2 }

adGenY1731LocalMepConfigEntry OBJECT-TYPE
    SYNTAX        AdGenY1731LocalMepConfigEntry
    MAX-ACCESS    not-accessible
    STATUS        current
    DESCRIPTION
       "An entry in the Y.1731 local MEP table."
    INDEX { adGenY1731MegLevel,
              adGenY1731MegNameFormat,
              adGenY1731MegNameLengthAndName,
              adGenY1731LocalMepIdentifier }
      ::= { adGenY1731LocalMepConfigTable 1 }

AdGenY1731LocalMepConfigEntry ::= SEQUENCE {
      adGenY1731LocalMepIdentifier   Integer32,
      adGenY1731LocalMepRowStatus    RowStatus,
      adGenY1731LocalMepStatus       INTEGER,
      adGenY1731LocalMepStatusString OCTET STRING,
      adGenY1731LocalMepIfIndex      InterfaceIndexOrZero,
      adGenY1731LocalMepDirection    INTEGER,
      adGenY1731LocalMepAdminState   INTEGER,
      adGenY1731LocalMepVlanPriority Integer32,
      adGenY1731LocalMepCcmEnabled   INTEGER
    }

adGenY1731LocalMepIdentifier
OBJECT-TYPE
    SYNTAX      Integer32 (1..8191)
    MAX-ACCESS  not-accessible
    STATUS      current
    DESCRIPTION
       "Integer that is unique among all the MEPs in the same MEG. Other
        definition is: a small integer, unique over a given Maintenance Entity
        Group, identifying a specific MEG End Point.

        MEP Identifier is also known as the MEPID.
       "
    ::= { adGenY1731LocalMepConfigEntry 1 }

adGenY1731LocalMepRowStatus
OBJECT-TYPE
    SYNTAX      RowStatus
    MAX-ACCESS  read-create
    STATUS      current
    DESCRIPTION
       "This OID is used to create/delete the MEP.  The only supported settings
        are createAndGo, createAndWait, and destroy.
       "
    ::= { adGenY1731LocalMepConfigEntry 2 }

adGenY1731LocalMepStatus
OBJECT-TYPE
    SYNTAX      INTEGER {
                    running(1),
                    notRunning(2)
                }
    MAX-ACCESS  read-only
    STATUS      current
    DESCRIPTION
       "Operational status of the MEP.  The minimum attributes that need to be
        set before a MEP can transition to running are: ifIndex, direction,
        and admin state.
       "
    ::= { adGenY1731LocalMepConfigEntry 3 }

adGenY1731LocalMepStatusString
OBJECT-TYPE
    SYNTAX       OCTET STRING
    MAX-ACCESS   read-only
    STATUS       current
    DESCRIPTION
       "Operational status string of the MEP.  If the MEP is expected to be
        active but is not able to be due to a provisioning issue or conflict,
        this string will explain the reason.
       "
    ::= { adGenY1731LocalMepConfigEntry 4 }

adGenY1731LocalMepIfIndex
OBJECT-TYPE
    SYNTAX      InterfaceIndexOrZero
    MAX-ACCESS  read-create
    STATUS      current
    DESCRIPTION
       "This object is the interface index of the interface either a bridge
        port, or an aggregated IEEE 802.1 link within a bridge port, to which
        the MEP is attached.  A value of 0 indicates no IfIndex
        has been assigned.
       "
    ::= { adGenY1731LocalMepConfigEntry 5 }

adGenY1731LocalMepDirection
OBJECT-TYPE
    SYNTAX      INTEGER {
                    notSet(0),
                    down(1),
                    up(2)
                }
    MAX-ACCESS  read-create
    STATUS      current
    DESCRIPTION
       "The direction in which the MEP faces on the Bridge port."
    ::= { adGenY1731LocalMepConfigEntry 6 }

adGenY1731LocalMepAdminState
OBJECT-TYPE
    SYNTAX      INTEGER {
                    enable(1),
                    disable(2)
                }
    MAX-ACCESS  read-create
    STATUS      current
    DESCRIPTION
       "The administrative state of the MEP.

        Enable indicates that the MEP is to function normally, and disable that
        it is to cease functioning.
       "
    ::= { adGenY1731LocalMepConfigEntry 7 }

adGenY1731LocalMepVlanPriority
OBJECT-TYPE
    SYNTAX      Integer32 (0..7)
    MAX-ACCESS  read-create
    STATUS      current
    DESCRIPTION
       "The priority value for messages transmitted by the MEP. Default value
        is the highest priority value for the service which is assumed to be 7.
        The management entity can obtain the default value for this variable
        from the priority regeneration table by extracting the highest priority
        value in this table on this MEPs bridge port.
       "
    ::= { adGenY1731LocalMepConfigEntry 8 }

adGenY1731LocalMepCcmEnabled
OBJECT-TYPE
    SYNTAX      INTEGER {
                    enable(1),
                    disable(2)
                }
    MAX-ACCESS  read-create
    STATUS      current
    DESCRIPTION
       "If set to true, the MEP will generate CCM messages."
    ::= { adGenY1731LocalMepConfigEntry 9 }

--=============================================================================
--Y.1731 Local MEP RMEP Database Scalars
--=============================================================================

adGenY1731LocalMepRmepDbMaxNumber
OBJECT-TYPE
      SYNTAX      Unsigned32
      MAX-ACCESS  read-only
      STATUS      current
      DESCRIPTION
         "A systemwide value representing the maximum number of remote
          Maintenance End Points that can be created across all Local
          MEPs on the device.
         "
      ::= { adGenY1731LocalMepRmepDbScalars 1 }

adGenY1731LocalMepRmepDbCurrentNumber
OBJECT-TYPE
      SYNTAX      Unsigned32
      MAX-ACCESS  read-only
      STATUS      current
      DESCRIPTION
       "Current number of remote MEPs."
      ::= { adGenY1731LocalMepRmepDbScalars 2 }


--=============================================================================
--Y.1731 Local MEP RMEP Database Table
--=============================================================================

adGenY1731LocalMepRmepDbTable
OBJECT-TYPE
    SYNTAX      SEQUENCE OF AdGenY1731LocalMepRmepDbEntry
    MAX-ACCESS  not-accessible
    STATUS      current
    DESCRIPTION
       "The RMEP database table for a given local MEP.  Maintains information
        and status for each RMEP of a local MEP.
       "
    ::= { adGenY1731LocalMepRmepDb 2 }

adGenY1731LocalMepRmepDbEntry OBJECT-TYPE
    SYNTAX        AdGenY1731LocalMepRmepDbEntry
    MAX-ACCESS    not-accessible
    STATUS        current
    DESCRIPTION
       "An entry in the a local MEP's RMEP database table.  An RMEP
        associated with a specific local MEP
       "
    INDEX { adGenY1731MegLevel,
            adGenY1731MegNameFormat,
            adGenY1731MegNameLengthAndName,
            adGenY1731LocalMepIdentifier,
            adGenY1731RemoteMepIdentifier
          }
      ::= { adGenY1731LocalMepRmepDbTable 1 }

AdGenY1731LocalMepRmepDbEntry ::= SEQUENCE {
      adGenY1731RemoteMepIdentifier         Integer32,
      adGenY1731RemoteMepStatus             INTEGER,
      adGenY1731RemoteMepFailedOkTime       TimeStamp,
      adGenY1731RemoteMepMacAddress         MacAddress,
      adGenY1731RemoteMepLastCcmSequenceNumber Unsigned32,
      adGenY1731RemoteMepRdi                TruthValue,
      adGenY1731RemoteMepPortStatus         INTEGER,
      adGenY1731RemoteMepInterfaceStatus    INTEGER,
      adGenY1731RemoteMepChassisIdSubtype   INTEGER,
      adGenY1731RemoteMepChassisId          LldpChassisId,
      adGenY1731RemoteMepManAddressDomain   TDomain,
      adGenY1731RemoteMepManAddress         TAddress
    }

adGenY1731RemoteMepIdentifier
OBJECT-TYPE
    SYNTAX      Integer32 (1..8191)
    MAX-ACCESS  not-accessible
    STATUS      current
    DESCRIPTION
       "Integer that is unique among all the MEPs in the same MEG. Other
        definition is: a small integer, unique over a given Maintenance Entity
        Group, identifying a specific MEG End Point.

        MEP Identifier is also known as the MEPID.
       "
    ::= { adGenY1731LocalMepRmepDbEntry 1 }

adGenY1731RemoteMepStatus
OBJECT-TYPE
    SYNTAX      INTEGER {
                    idle(0),
                    okay(1),
                    failed(2)
                }
    MAX-ACCESS  read-only
    STATUS      current
    DESCRIPTION
       "Status of the RMEP.
        Status of idle indicates the local MEP associated with this RMEP entry
        is not in the active state.

        Status of okay indicates the local MEP  is actively receiving CCMs from
        the RMEP at the expected CCI.

        Status of failed indicates the local MEP has not received a CCM from
        the RMEP within 3.5 times the CCI.
       "
    ::= { adGenY1731LocalMepRmepDbEntry 2 }

adGenY1731RemoteMepFailedOkTime
OBJECT-TYPE
    SYNTAX       TimeStamp
    MAX-ACCESS   read-only
    STATUS       current
    DESCRIPTION
       "The time (SysUpTime) at which the RMEP state machine last entered
        either the idle, okay, or failed state.  The value is the time since
        the device started up and is represented using TimeStamp syntax.
       "
    ::= { adGenY1731LocalMepRmepDbEntry 3 }

adGenY1731RemoteMepMacAddress
OBJECT-TYPE
    SYNTAX       MacAddress
    MAX-ACCESS   read-only
    STATUS       current
    DESCRIPTION
       "The MAC address of the remote MEP."
    ::= { adGenY1731LocalMepRmepDbEntry 4 }

adGenY1731RemoteMepLastCcmSequenceNumber
OBJECT-TYPE
    SYNTAX       Unsigned32
    MAX-ACCESS   read-only
    STATUS       current
    DESCRIPTION
       "Sequence number in last CCM received from the remote MEP."
    ::= { adGenY1731LocalMepRmepDbEntry 5 }

adGenY1731RemoteMepRdi
OBJECT-TYPE
    SYNTAX      TruthValue
    MAX-ACCESS  read-only
    STATUS      current
    DESCRIPTION
       "State of the RDI bit in the last received CCM (true for RDI=1), or
        false if none has been received.
       "
    ::= { adGenY1731LocalMepRmepDbEntry 6 }

adGenY1731RemoteMepPortStatus
OBJECT-TYPE
    SYNTAX      INTEGER {
                    psNoPortStatusTlv(0),
                    psBlocked(1),
                    psUp(2)
                }
    MAX-ACCESS  read-only
    STATUS      current
    DESCRIPTION
       "An enumerated value of the Port Status TLV received in the last CCM
        from the remote MEP.

        The default value psNoPortStatusTlv is returned if no CCM has been
        received or if no Port Status TLV was received in the last CCM.

        psBlocked - Ordinary data cannot pass freely through the port on
        which the remote MEP resides.

        psUp - Ordinary data can pass freely through the port on which the
        remote MEP resides.
       "
    ::= { adGenY1731LocalMepRmepDbEntry 7 }

adGenY1731RemoteMepInterfaceStatus
OBJECT-TYPE
    SYNTAX      INTEGER {
                    isNoInterfaceStatusTLV(0),
                    isUp(1),
                    isDown(2),
                    isTesting(3),
                    isUnknown(4),
                    isDormant(5),
                    isNotPresent(6),
                    isLowerLayerDown(7)
                }
    MAX-ACCESS  read-only
    STATUS      current
    DESCRIPTION
       "An enumerated value of the Interface status TLV received in the last
        CCM from the remote MEP.

        The the default value isNoInterfaceStatus TLV is returned if either no
        CCM has been received or if no interface status TLV was received in the
        last CCM.
       "
    ::= { adGenY1731LocalMepRmepDbEntry 8 }

adGenY1731RemoteMepChassisIdSubtype
OBJECT-TYPE
    SYNTAX      INTEGER {
                    nonePresent(0),
                    chassisComponent(1),
                    interfaceAlias(2),
                    portComponent(3),
                    macAddress(4),
                    networkAddress(5),
                    interfaceName(6),
                    local(7)
                }
    MAX-ACCESS   read-only
    STATUS       current
    DESCRIPTION
       "Specifies the format of the Chassis ID received in the last CCM.
        If the Chassis ID field was not included in the Sender ID TLV
        received, the value nonePresent(0) will be returned.
       "
    ::= { adGenY1731LocalMepRmepDbEntry 9 }

adGenY1731RemoteMepChassisId
OBJECT-TYPE
    SYNTAX       LldpChassisId
    MAX-ACCESS   read-only
    STATUS       current
    DESCRIPTION
       "Chassis ID received in the last CCM format of which is determined by
        the value of adGenY1731RemoteMepChassisIdSubtype.
       "
    ::= { adGenY1731LocalMepRmepDbEntry 10 }

adGenY1731RemoteMepManAddressDomain
OBJECT-TYPE
    SYNTAX       TDomain
    MAX-ACCESS   read-only
    STATUS       current
    DESCRIPTION
       "The TDomain that identifies the type and format of
        the related adGenY1731RemoteMepManAddress object, used to access
        the SNMP agent of the system transmitting the CCM.  The value is
        derived from the Sender ID TLV in the last CCM received.

        Typical values will be one of (not all inclusive) list:


           snmpUDPDomain          (from SNMPv2-TM, RFC3417)
           snmpIeee802Domain      (from SNMP-IEEE802-TM-MIB, RFC4789)

        The value 'zeroDotZero' (from RFC2578) indicates 'no management
        address was present in the LTR', in which case the related
        object adGenY1731RemoteMepManAddress must have a zero-length OCTET
        STRING as a value.
       "
    ::= { adGenY1731LocalMepRmepDbEntry 11 }

adGenY1731RemoteMepManAddress
OBJECT-TYPE
    SYNTAX       TAddress
    MAX-ACCESS   read-only
    STATUS       current
    DESCRIPTION
       "The TAddress that can be used to access the SNMP agent of the system
        transmitting the CCM.  This is received in the CCM Sender ID TLV from
        that system.

        If the related object adGenY1731RemoteMepManAddressDomain contains
        the value 'zeroDotZero', this object adGenY1731RemoteMepManAddress
        must have a zero-length OCTET STRING as a value.
       "
    ::= { adGenY1731LocalMepRmepDbEntry 12 }

--=============================================================================
--Y.1731 Local MEP Loopback Message(LBM)
--=============================================================================

--=============================================================================
--Y.1731 Local MEP LBM Transmit Table
--=============================================================================

adGenY1731LocalMepLbmTransmitTable  OBJECT-TYPE
    SYNTAX      SEQUENCE OF AdGenY1731LocalMepLbmTransmitEntry
    MAX-ACCESS  not-accessible
    STATUS      current
    DESCRIPTION
       "The Y.1731 Local MEP Loopback Transmit table.  A Local MEP is one that
        resides on an interface of the system. This table will enable the user
        to configure a Local MEP in preparation for starting a Loopback
        session.
       "
    ::= { adGenY1731LocalMepLbm 1 }

adGenY1731LocalMepLbmTransmitEntry OBJECT-TYPE
    SYNTAX        AdGenY1731LocalMepLbmTransmitEntry
    MAX-ACCESS    not-accessible
    STATUS        current
    DESCRIPTION
       "An entry in the Y.1731 Local MEP Loopback Transmit table."
    INDEX { adGenY1731MegLevel,
            adGenY1731MegNameFormat,
            adGenY1731MegNameLengthAndName,
            adGenY1731LocalMepIdentifier }
      ::= { adGenY1731LocalMepLbmTransmitTable 1 }

AdGenY1731LocalMepLbmTransmitEntry ::= SEQUENCE {
      adGenY1731LocalMepLbmStatus           TruthValue,
      adGenY1731LocalMepLbmConfigStatus     TruthValue,
      adGenY1731LocalMepLbmDestMacAddress   MacAddress,
      adGenY1731LocalMepLbmDestMepId        Integer32,
      adGenY1731LocalMepLbmDestIsMepId      TruthValue,
      adGenY1731LocalMepLbmMessageCount     Integer32,
      adGenY1731LocalMepLbmActive           TruthValue,
      adGenY1731LocalMepLbmDataTlv          OCTET STRING,
      adGenY1731LocalMepLbmVlanPriority     Integer32,
      adGenY1731LocalMepLbmVlanDropEnable   TruthValue,
      adGenY1731LocalMepLbmErrorStatus      DisplayString,
      adGenY1731LocalMepLbmTimeout          Unsigned32,
      adGenY1731LocalMepLbmInterframeDelay  Unsigned32,
      adGenY1731LocalMepLbmNextTransId      Unsigned32,
      adGenY1731LocalMepLbmSize             Integer32,
      adGenY1731LocalMepValidateData        TruthValue
    }

adGenY1731LocalMepLbmStatus OBJECT-TYPE
   SYNTAX      TruthValue
   MAX-ACCESS  read-only
   STATUS      current
   DESCRIPTION
      "A Boolean flag where true means the MEP is actively sending LBM messages
       and false means that no LBMs are being transmitted.
      "
   DEFVAL { false }
   ::= { adGenY1731LocalMepLbmTransmitEntry 1 }

adGenY1731LocalMepLbmConfigStatus OBJECT-TYPE
   SYNTAX      TruthValue
   MAX-ACCESS  read-write
   STATUS      current
   DESCRIPTION
      "True means the MEP is ready for configuring LBM and a false means the MEP
       is under LBM configuration. This flag is used to prevent simultaneous
       configuration by more than  one user. If one minute has passed since the
       last LocalMepLbm attribute was set, then it is assume the user has abandoned
       configuring the session and the adGenY1731LocalMepLbmConfigStatus will be
       reset to true.
       "
   DEFVAL { true }
   ::= { adGenY1731LocalMepLbmTransmitEntry 2 }

adGenY1731LocalMepLbmDestMacAddress OBJECT-TYPE
    SYNTAX      MacAddress
    MAX-ACCESS  read-write
    STATUS      current
    DESCRIPTION
       "The Target MAC Address Field to be transmitted.  This is a unicast
        destination MAC address.

        This address will be used if the value of the column
        adGenY1731LocalMepTransmitLbmDestMepId is 'false'.
       "
    ::= { adGenY1731LocalMepLbmTransmitEntry 3 }

adGenY1731LocalMepLbmDestMepId OBJECT-TYPE
    SYNTAX      Integer32 (1..8191)
    MAX-ACCESS  read-write
    STATUS      current
    DESCRIPTION
       "The MEG End Point Identifier of another MEP in the same MEG to which
        the LBM is to be sent. This address will be used if the value of the
        column adGenY1731LocalMepTransmitLbmDestIsMepId is 'true'.
       "
    ::= { adGenY1731LocalMepLbmTransmitEntry 4 }

adGenY1731LocalMepLbmDestIsMepId OBJECT-TYPE
    SYNTAX      TruthValue
    MAX-ACCESS  read-write
    STATUS      current
    DESCRIPTION
       "True indicates that MEPID of the target MEP is used for Loopback
        transmission.  False indicates that unicast destination MAC address of
        the target MEP is used for Loopback transmission.
       "
    ::= {adGenY1731LocalMepLbmTransmitEntry 5 }

adGenY1731LocalMepLbmMessageCount OBJECT-TYPE
    SYNTAX      Integer32(1..1024)
    MAX-ACCESS  read-write
    STATUS      current
    DESCRIPTION
       "The number of Loopback messages to be transmitted."
    DEFVAL { 1 }
    ::= {adGenY1731LocalMepLbmTransmitEntry 6 }

adGenY1731LocalMepLbmActive OBJECT-TYPE
    SYNTAX      TruthValue
    MAX-ACCESS  read-write
    STATUS      current
    DESCRIPTION
       "Start or stop LBM transmission. By writing true, start LBM transmisson.
       By writing false, stop LBM transmission
       "
    DEFVAL { false }
    ::= {adGenY1731LocalMepLbmTransmitEntry 7 }

adGenY1731LocalMepLbmDataTlv OBJECT-TYPE
    SYNTAX      OCTET STRING (SIZE(0..1500))
    MAX-ACCESS  read-write
    STATUS      current
    DESCRIPTION
       "An arbitrary amount of data to be included in the Data TLV, if the Data
        TLV is selected to be sent.
       "
    ::= { adGenY1731LocalMepLbmTransmitEntry 8 }

adGenY1731LocalMepLbmVlanPriority OBJECT-TYPE
    SYNTAX      Integer32(0..7)
    MAX-ACCESS  read-write
    STATUS      current
    DESCRIPTION
       "The 3 bit priority value to be used in the VLAN tag, if present, in the
        transmitted frame.

        The default value is CCM priority.
       "
    ::= { adGenY1731LocalMepLbmTransmitEntry 9 }

adGenY1731LocalMepLbmVlanDropEnable OBJECT-TYPE
    SYNTAX      TruthValue
    MAX-ACCESS  read-write
    STATUS      current
    DESCRIPTION
       "Drop Enable bit value to be used in the VLAN tag, if present
        in the transmitted frame.

        For more information about VLAN Drop Enable, please check
        IEEE 802.1ad.
       "
    DEFVAL { true }
    ::= { adGenY1731LocalMepLbmTransmitEntry 10 }

adGenY1731LocalMepLbmErrorStatus OBJECT-TYPE
    SYNTAX      DisplayString
    MAX-ACCESS  read-only
    STATUS      current
    DESCRIPTION
       "MEP Loopback error status.
       "
     ::= { adGenY1731LocalMepLbmTransmitEntry 11 }

adGenY1731LocalMepLbmTimeout OBJECT-TYPE
    SYNTAX      Unsigned32 (100..5000)
    MAX-ACCESS  read-write
    STATUS      current
    DESCRIPTION
       "MEP Loopback Timeout in milliseconds.
       "
     ::= { adGenY1731LocalMepLbmTransmitEntry 12 }

adGenY1731LocalMepLbmInterframeDelay OBJECT-TYPE
    SYNTAX      Unsigned32 (100..10000)
    MAX-ACCESS  read-write
    STATUS      current
    DESCRIPTION
       "MEP Loopback Interframe Delay in milliseconds.
       "
     ::= { adGenY1731LocalMepLbmTransmitEntry 13 }

adGenY1731LocalMepLbmNextTransId OBJECT-TYPE
    SYNTAX      Unsigned32
    MAX-ACCESS  read-only
    STATUS      current
    DESCRIPTION
       "Next transaction identifier to be sent in a Loopback message. This
        transaction identifier can be zero because it wraps around.
       "
    ::= { adGenY1731LocalMepLbmTransmitEntry 14 }

adGenY1731LocalMepLbmSize OBJECT-TYPE
    SYNTAX      Integer32
    MAX-ACCESS  read-write
    STATUS      current
    DESCRIPTION
       "Size of the LBM in bytes.  The size encompasses the entire Ethernet
        frame from the header through the FCS.

        The supported values are:
        0 to indicate Data TLV should not be included in LBM sent.
        64 to 2000 bytes to indicate the Data TLV should be included to increase
        the frame length to the specified size.

        If the Data TLV is not included, the LBM will be sent with the minimum
        Ethernet frame size of 64-bytes but it will not contain the Data TLV.  A
        zero-pad will be used to fulfill  the minimum length requirement.

        The default value is 0.
       "
    ::= { adGenY1731LocalMepLbmTransmitEntry 15 }

adGenY1731LocalMepValidateData OBJECT-TYPE
   SYNTAX      TruthValue
   MAX-ACCESS  read-write
   STATUS      current
   DESCRIPTION
      "A Boolean flag where true means the data sent in LBM message has to be
       validated with the LBR. False indicates no validation is required.
      "
   DEFVAL { false }
   ::= { adGenY1731LocalMepLbmTransmitEntry 16 }


--=============================================================================
--Y.1731 Local MEP LBM Result Table
--=============================================================================
adGenY1731LocalMepLbmResultTable OBJECT-TYPE
    SYNTAX      SEQUENCE OF AdGenY1731LocalMepLbmResultEntry
    MAX-ACCESS  not-accessible
    STATUS      current
    DESCRIPTION
       "The Y.1731 Local MEP Loopback Result table.  A Local MEP is one that resides on an
        interface of the system. This table can be used to query the results and counters
        related to LBM
       "
    ::= { adGenY1731LocalMepLbm 2 }

adGenY1731LocalMepLbmResultEntry OBJECT-TYPE
    SYNTAX        AdGenY1731LocalMepLbmResultEntry
    MAX-ACCESS    not-accessible
    STATUS        current
    DESCRIPTION
       "An entry in the Y.1731 Local MEP Loopback Result table."
    INDEX { adGenY1731MegLevel,
            adGenY1731MegNameFormat,
            adGenY1731MegNameLengthAndName,
            adGenY1731LocalMepIdentifier }
      ::= { adGenY1731LocalMepLbmResultTable 1 }

AdGenY1731LocalMepLbmResultEntry ::= SEQUENCE {
      adGenY1731LocalMepLbrResultOk        TruthValue,
      adGenY1731LocalMepLbrResponseTimeMin Unsigned32,
      adGenY1731LocalMepLbrResponseTimeMax Unsigned32,
      adGenY1731LocalMepLbrResponseTimeAvg Unsigned32,
      adGenY1731LocalMepLbrIn              Counter32,
      adGenY1731LocalMepLbrInOutOfOrder    Counter32,
      adGenY1731LocalMepLbrBadMsdu         Counter32,
      adGenY1731LocalMepLbmOut             Counter32
    }

adGenY1731LocalMepLbrResultOk OBJECT-TYPE
    SYNTAX      TruthValue
    MAX-ACCESS  read-only
    STATUS      current
    DESCRIPTION
       "Indicates the result of the operation:

        - true       The Loopback Message(s) will be
                     (or has been) sent.
        - false      The Loopback Message(s) will not
                     be sent.
       "
    DEFVAL { true }
    ::= { adGenY1731LocalMepLbmResultEntry 1 }

adGenY1731LocalMepLbrResponseTimeMin OBJECT-TYPE
    SYNTAX      Unsigned32
    MAX-ACCESS  read-only
    STATUS      current
    DESCRIPTION
       "Minimum LBR round-trip time (in milliseconds).
       "
     ::= { adGenY1731LocalMepLbmResultEntry 2 }

adGenY1731LocalMepLbrResponseTimeMax OBJECT-TYPE
    SYNTAX      Unsigned32
    MAX-ACCESS  read-only
    STATUS      current
    DESCRIPTION
       "Maximum LBR round-trip time (in milliseconds).
       "
     ::= { adGenY1731LocalMepLbmResultEntry 3 }

adGenY1731LocalMepLbrResponseTimeAvg OBJECT-TYPE
    SYNTAX      Unsigned32
    MAX-ACCESS  read-only
    STATUS      current
    DESCRIPTION
       "Average LBR round-trip time (in milliseconds).
       "
     ::= { adGenY1731LocalMepLbmResultEntry 4 }

adGenY1731LocalMepLbrIn OBJECT-TYPE
    SYNTAX      Counter32
    MAX-ACCESS  read-only
    STATUS      current
    DESCRIPTION
       "Total number of valid, Loopback Replies received."
    ::= { adGenY1731LocalMepLbmResultEntry 5 }

adGenY1731LocalMepLbrInOutOfOrder OBJECT-TYPE
    SYNTAX      Counter32
    MAX-ACCESS  read-only
    STATUS      current
    DESCRIPTION
       "The total number of valid, out-of-order Loopback Replies
        received.
       "
    ::= { adGenY1731LocalMepLbmResultEntry 6 }

adGenY1731LocalMepLbrBadMsdu OBJECT-TYPE
    SYNTAX      Counter32
    MAX-ACCESS  read-only
    STATUS      current
    DESCRIPTION
       "The total number of LBRs received whose
        mac_service_data_unit did not match (except for the OpCode)
        that of the corresponding LBM.
       "
    ::= { adGenY1731LocalMepLbmResultEntry 7}

adGenY1731LocalMepLbmOut OBJECT-TYPE
    SYNTAX      Counter32
    MAX-ACCESS  read-only
    STATUS      current
    DESCRIPTION
       "The total number of LBMs transmitted.
       "
    ::= { adGenY1731LocalMepLbmResultEntry 8}


--=============================================================================
--Y.1731 Local MEP LBM Responder Table
--=============================================================================
adGenY1731LocalMepLbmResponderTable  OBJECT-TYPE
    SYNTAX      SEQUENCE OF AdGenY1731LocalMepLbmResponderEntry
    MAX-ACCESS  not-accessible
    STATUS      current
    DESCRIPTION
       "The Y.1731 Local MEP Loopback Responder table.  A Local MEP is one that resides on an
        interface of the system. This table can be used to query the counters
        related to LBR
       "
    ::= { adGenY1731LocalMepLbm 3 }

adGenY1731LocalMepLbmResponderEntry OBJECT-TYPE
    SYNTAX        AdGenY1731LocalMepLbmResponderEntry
    MAX-ACCESS    not-accessible
    STATUS        current
    DESCRIPTION
       "An entry in the Y.1731 Local MEP Loopback Responder table."
    INDEX { adGenY1731MegLevel,
            adGenY1731MegNameFormat,
            adGenY1731MegNameLengthAndName,
            adGenY1731LocalMepIdentifier }
      ::= { adGenY1731LocalMepLbmResponderTable 1 }

AdGenY1731LocalMepLbmResponderEntry ::= SEQUENCE {
      adgenY1731LocalMepLbrOut Counter32,
      adGenY1731LocalMepLbmIn  Counter32
    }

adgenY1731LocalMepLbrOut OBJECT-TYPE
    SYNTAX      Counter32
    MAX-ACCESS  read-only
    STATUS      current
    DESCRIPTION
       "Total number of Loopback Replies transmitted."
    ::= { adGenY1731LocalMepLbmResponderEntry 1 }

adGenY1731LocalMepLbmIn OBJECT-TYPE
    SYNTAX      Counter32
    MAX-ACCESS  read-only
    STATUS      current
    DESCRIPTION
       "Total number of valid, Loopback Messages received."
    ::= { adGenY1731LocalMepLbmResponderEntry 2 }


--=============================================================================
--Y.1731 Local MEP ETH-DMM Scalars
--=============================================================================

adGenY1731DmmSessionMaxNumber OBJECT-TYPE
    SYNTAX      Unsigned32
    MAX-ACCESS  read-only
    STATUS      current
    DESCRIPTION
       "A systemwide value representing the maximum number of DMM sessions
        that can be created across all local MEPs on the device.
       "
    ::= { adGenY1731DmmScalars 1 }

adGenY1731DmmSessionCurrentNumber OBJECT-TYPE
    SYNTAX      Unsigned32
    MAX-ACCESS  read-only
    STATUS      current
    DESCRIPTION
       "Current number of DMM sessions created."
    ::= { adGenY1731DmmScalars 2 }

adGenY1731DmmSessionLastCreateError OBJECT-TYPE
    SYNTAX      DisplayString
    MAX-ACCESS  read-only
    STATUS      current
    DESCRIPTION
       "The reason for the last error that occurred while attempting to create
        an DMM Session Transmit entry (adGenY1731DmmSessionTransmitEntry).
       "
    ::= { adGenY1731DmmScalars 3 }

--=============================================================================
--Y.1731 Local MEP ETH-DMM Transmit Table
--=============================================================================
adGenY1731DmmSessionTransmitTable
OBJECT-TYPE
    SYNTAX      SEQUENCE OF AdGenY1731DmmSessionTransmitEntry
    MAX-ACCESS  not-accessible
    STATUS      current
    DESCRIPTION
       "The two-way frame-delay (DMM) session table for a given local MEP.
        A local MEP's DMM sessions can be created, edited, and deleted using
        this table.  A local MEP can target a remote MEP to run two-way frame
        delay measurements between the two MEPs in the MEG.

        The target can be specified by either using a MAC address of the target
        MEP or the MEPID of the target MEP.  For the DMM session to go active,
        the local MEP must be successfully receiving CCMs from the remote MEP
        in order to specify the RMEPID as the target.
       "
    ::= { adGenY1731LocalMepDmm 2 }

adGenY1731DmmSessionTransmitEntry OBJECT-TYPE
    SYNTAX        AdGenY1731DmmSessionTransmitEntry
    MAX-ACCESS    not-accessible
    STATUS        current
    DESCRIPTION
       "A two-way frame-delay (DMM) performance monitoring session of a
        local MEP.  A DMM PM session is unique based on target identifier
        and VLAN priority.  The target identifier is either a MAC address
        or RMEPID.  Inclusion of VLAN priority in the index allows a local MEP
        to simultaneously run several DMM PM sessions between it and the target
        at various CoS levels.
       "
    INDEX { adGenY1731MegLevel,
            adGenY1731MegNameFormat,
            adGenY1731MegNameLengthAndName,
            adGenY1731LocalMepIdentifier,
            adGenY1731DmmSessionTargetRmepIdOrMacAddress,
            adGenY1731DmmSessionTarget,
            adGenY1731DmmSessionVlanPriority
          }
    ::= { adGenY1731DmmSessionTransmitTable 1 }

AdGenY1731DmmSessionTransmitEntry ::= SEQUENCE {
      adGenY1731DmmSessionTargetRmepIdOrMacAddress   INTEGER,
      adGenY1731DmmSessionTarget                     OCTET STRING,
      adGenY1731DmmSessionVlanPriority               Integer32,
      adGenY1731DmmSessionTargetRemoteMepIdentifier  Integer32,
      adGenY1731DmmSessionTargetMacAddress           MacAddress,
      adGenY1731DmmSessionRowStatus                  RowStatus,
      adGenY1731DmmSessionAdminState                 TruthValue,
      adGenY1731DmmSessionStatus                     INTEGER,
      adGenY1731DmmSessionStatusString               DisplayString,
      adGenY1731DmmSessionInterframeDelay            Integer32,
      adGenY1731DmmSessionMeasurementInterval        Integer32,
      adGenY1731DmmSessionSize                       Integer32,
      adGenY1731DmmSessionData                       OCTET STRING,
      adGenY1731DmmSessionBulkDataExportFileTypes    INTEGER
    }

adGenY1731DmmSessionTargetRmepIdOrMacAddress
OBJECT-TYPE
    SYNTAX      INTEGER {
                    rmepId(1),
                    macAddress(2)
                }
    MAX-ACCESS  not-accessible
    STATUS      current
    DESCRIPTION
       "Indicates whether the target specified is a MEPID or a unicast MAC
        Address.  If the target specified is a MEPID, the local MEP will not be
        able to initiate the DMM session until a CCM has been received from the
        RMEP
       "
    ::= { adGenY1731DmmSessionTransmitEntry 1 }

adGenY1731DmmSessionTarget
OBJECT-TYPE
    SYNTAX      OCTET STRING (SIZE (1..6))
    MAX-ACCESS  not-accessible
    STATUS      current
    DESCRIPTION
       "Octet string defining the target for the DMM session.
        If adGenY1731DmmSessionTargetRmepIdOrMacAddress indicates the target is
        a MEPID then the octet string should represent a MEPID between the
        range 1-8191.  Otherwise, it should be the target's unicast MAC address
       "
    ::= { adGenY1731DmmSessionTransmitEntry 2 }

adGenY1731DmmSessionVlanPriority
OBJECT-TYPE
    SYNTAX      Integer32 (0..7)
    MAX-ACCESS  not-accessible
    STATUS      current
    DESCRIPTION
       "VLAN Priority that will be used in all DMM frames sent by this
        DMM transmit session.
       "
    ::= { adGenY1731DmmSessionTransmitEntry 3 }

adGenY1731DmmSessionTargetRemoteMepIdentifier
OBJECT-TYPE
    SYNTAX      Integer32 (1..8191)
    MAX-ACCESS  read-only
    STATUS      current
    DESCRIPTION
       "Target MEPID for this DMM session"
    ::= { adGenY1731DmmSessionTransmitEntry 4 }

adGenY1731DmmSessionTargetMacAddress
OBJECT-TYPE
    SYNTAX      MacAddress
    MAX-ACCESS  read-only
    STATUS      current
    DESCRIPTION
       "Target MAC address for this DMM session"
    ::= { adGenY1731DmmSessionTransmitEntry 5 }

adGenY1731DmmSessionRowStatus
OBJECT-TYPE
    SYNTAX      RowStatus
    MAX-ACCESS  read-create
    STATUS      current
    DESCRIPTION
       "This OID is used to create/delete a transmit DMM session of a Local
        MEP.  The only supported settings are createAndGo, createAndWait, and
        destroy.
       "
    ::= { adGenY1731DmmSessionTransmitEntry 6 }

adGenY1731DmmSessionAdminState
OBJECT-TYPE
    SYNTAX      TruthValue
    MAX-ACCESS  read-create
    STATUS      current
    DESCRIPTION
       "The administrative state of the DMM transmit session.

        True indicates that the DMM session is to function normally and
        actively transmit DMMs towards the specified target, and false that
        it is to cease functioning.
       "
    ::= { adGenY1731DmmSessionTransmitEntry 7 }

adGenY1731DmmSessionStatus
OBJECT-TYPE
    SYNTAX      INTEGER {
                    running(1),
                    notRunning(2)
                }
    MAX-ACCESS  read-only
    STATUS      current
    DESCRIPTION
       "Operational status of the DMM transmit session.  The minimum
        attributes that need to be set before a MEP can transmit DMMs towards
        the target are: Target MEPID or MAC Address and admin state.  If a
        MEPID is used to specify the target then the local MEP must have
        received a CCM from the remote MEP in-order to learn its MAC address.
       "
    ::= { adGenY1731DmmSessionTransmitEntry 8 }

adGenY1731DmmSessionStatusString
OBJECT-TYPE
    SYNTAX      DisplayString
    MAX-ACCESS  read-only
    STATUS      current
    DESCRIPTION
       "Operational status string of the DMM transmit session.  If the session
        is expected to be active but is not able to be due to a provisioning
        issue or conflict, this string will explain the reason.
       "
    ::= { adGenY1731DmmSessionTransmitEntry 9 }

adGenY1731DmmSessionInterframeDelay
OBJECT-TYPE
    SYNTAX      Integer32 (100..10000)
    MAX-ACCESS  read-create
    STATUS      current
    DESCRIPTION
       "Amount of time in milliseconds between DMM transmissions.  The
        supported range is 100 - 10,000 ms and the default value is 1000 ms.
       "
    ::= { adGenY1731DmmSessionTransmitEntry 10 }

adGenY1731DmmSessionMeasurementInterval
OBJECT-TYPE
    SYNTAX      Integer32 (60..900)
    MAX-ACCESS  read-create
    STATUS      current
    DESCRIPTION
       "Interval in seconds over which statistics are generated.  The supported
        range is 60 - 900 seconds and the default value is 60.  The statistics
        calculated for a measurement interval are stored in the averaged data
        file.  The data for the current and previous intervals is available via
        the adGenY1731DmmSessionResultTable.
       "
    ::= { adGenY1731DmmSessionTransmitEntry 11 }

adGenY1731DmmSessionSize
OBJECT-TYPE
    SYNTAX      Integer32
    MAX-ACCESS  read-create
    STATUS      current
    DESCRIPTION
       "Size of the DMM in bytes.  The size encompasses the entire Ethernet
        frame from the header through the FCS.

        The supported values are:
        0 to indicate Data TLV should not be included in DMM sent.
        64 to 2000 bytes to indicate the DataTLV should be included to increase
        the frame length to the specified size.

        If the Data TLV is not included, the DMM will be sent with the minimum
        Ethernet frame size of 64-bytes but it will not contain the DataTLV.  A
        zero-pad will be used to fulfill  the minimum length requirement.

        The default value is 0.
       "
    ::= { adGenY1731DmmSessionTransmitEntry 12 }

adGenY1731DmmSessionData
OBJECT-TYPE
    SYNTAX      OCTET STRING (SIZE (2))
    MAX-ACCESS  read-create
    STATUS      current
    DESCRIPTION
       "Data pattern to be used when padding is required to meet the size
        setting.  The default value is 0x00 0x00.
       "
    ::= { adGenY1731DmmSessionTransmitEntry 13 }

adGenY1731DmmSessionBulkDataExportFileTypes
OBJECT-TYPE
    SYNTAX      INTEGER {
                    none(1),
                    average(2),
                    raw(3),
                    averageAndRaw(4)
                }
    MAX-ACCESS  read-create
    STATUS      current
    DESCRIPTION
       "Determines which, if any, files are generated by this DMM transmit
        session.  The files are used to store two-way frame-delay statistics.
        The average setting will enable storage of statistics generated by
        each measurement interval.  The raw setting will enable storage
        for each two-way frame-delay sample.  The averageAndRaw setting
        will result in both files being generated.
       "
    ::= { adGenY1731DmmSessionTransmitEntry 14 }

--=============================================================================
--Y.1731 Local MEP ETH-LMM Scalars
--=============================================================================

adGenY1731LmmSessionMaxNumber OBJECT-TYPE
    SYNTAX      Unsigned32
    MAX-ACCESS  read-only
    STATUS      current
    DESCRIPTION
       "A systemwide value representing the maximum number of LMM sessions
        that can be created across all local MEPs on the device.
       "
    ::= { adGenY1731LmmScalars 1 }

adGenY1731LmmSessionCurrentNumber OBJECT-TYPE
    SYNTAX      Unsigned32
    MAX-ACCESS  read-only
    STATUS      current
    DESCRIPTION
       "Current number of LMM sessions created."
    ::= { adGenY1731LmmScalars 2 }

adGenY1731LmmSessionLastCreateError OBJECT-TYPE
    SYNTAX      DisplayString
    MAX-ACCESS  read-only
    STATUS      current
    DESCRIPTION
       "The reason for the last error that occurred while attempting to create
        an LMM Session Transmit entry (adGenY1731LmmSessionTransmitEntry).
       "
    ::= { adGenY1731LmmScalars 3 }

--=============================================================================
--Y.1731 Local MEP ETH-LMM Transmit Table
--=============================================================================
adGenY1731LmmSessionTransmitTable
OBJECT-TYPE
    SYNTAX      SEQUENCE OF AdGenY1731LmmSessionTransmitEntry
    MAX-ACCESS  not-accessible
    STATUS      current
    DESCRIPTION
       "The single-ended frame-loss (LMM) session table for a given local MEP.
        A local MEP's LMM sessions can be created, edited, and deleted using
        this table.  A local MEP can target a remote MEP to run single-ended
        frame-loss measurements between the two MEPs in the MEG.

        The target can be specified by either using a MAC address of the target
        MEP or the MEPID of the target MEP.  For the LMM session to go active,
        the local MEP must be successfully receiving CCMs from the remote MEP
        in order to specify the RMEPID as the target.
       "
    ::= { adGenY1731LocalMepLmm 2 }

adGenY1731LmmSessionTransmitEntry OBJECT-TYPE
    SYNTAX        AdGenY1731LmmSessionTransmitEntry
    MAX-ACCESS    not-accessible
    STATUS        current
    DESCRIPTION
       "A single-ended frame-loss (LMM) performance monitoring session of a
        local MEP.  A LMM PM session is unique based on target identifier
        and VLAN priority.  The target identifier is either a MAC address
        or RMEPID.  Inclusion of VLAN priority in the index allows a local MEP
        to simultaneously run several LMM PM sessions between it and the target
        at various CoS levels.
       "
    INDEX { adGenY1731MegLevel,
            adGenY1731MegNameFormat,
            adGenY1731MegNameLengthAndName,
            adGenY1731LocalMepIdentifier,
            adGenY1731LmmSessionTargetRmepIdOrMacAddress,
            adGenY1731LmmSessionTarget,
            adGenY1731LmmSessionVlanPriority
          }
      ::= { adGenY1731LmmSessionTransmitTable 1 }

AdGenY1731LmmSessionTransmitEntry ::= SEQUENCE {
      adGenY1731LmmSessionTargetRmepIdOrMacAddress   INTEGER,
      adGenY1731LmmSessionTarget                     OCTET STRING,
      adGenY1731LmmSessionVlanPriority               Integer32,
      adGenY1731LmmSessionTargetRemoteMepIdentifier  Integer32,
      adGenY1731LmmSessionTargetMacAddress           MacAddress,
      adGenY1731LmmSessionRowStatus                  RowStatus,
      adGenY1731LmmSessionAdminState                 TruthValue,
      adGenY1731LmmSessionStatus                     INTEGER,
      adGenY1731LmmSessionStatusString               DisplayString,
      adGenY1731LmmSessionInterframeDelay            Integer32,
      adGenY1731LmmSessionMeasurementInterval        Integer32,
      adGenY1731LmmSessionSize                       Integer32,
      adGenY1731LmmSessionData                       OCTET STRING,
      adGenY1731LmmSessionBulkDataExportFileTypes    INTEGER
    }

adGenY1731LmmSessionTargetRmepIdOrMacAddress
OBJECT-TYPE
    SYNTAX      INTEGER {
                    rmepId(1),
                    macAddress(2)
                }
    MAX-ACCESS  not-accessible
    STATUS      current
    DESCRIPTION
       "Indicates whether the target specified is a MEPID or a unicast MAC
        Address.  If the target specified is a MEPID the local MEP will not be
        able to initiate the LMM session until a CCM has been received from the
        RMEP
       "
    ::= { adGenY1731LmmSessionTransmitEntry 1 }

adGenY1731LmmSessionTarget
OBJECT-TYPE
    SYNTAX      OCTET STRING (SIZE (1..6))
    MAX-ACCESS  not-accessible
    STATUS      current
    DESCRIPTION
       "Octet string defining the target for the LMM session.
        If adGenY1731LmmSessionTargetRmepIdOrMacAddress indicates the target is
        a MEPID then the octet string should represent a MEPID between the
        range 1-8191.  Otherwise, it should be the target's unicast MAC address
       "
    ::= { adGenY1731LmmSessionTransmitEntry 2 }

adGenY1731LmmSessionVlanPriority
OBJECT-TYPE
    SYNTAX      Integer32 (0..7)
    MAX-ACCESS  not-accessible
    STATUS      current
    DESCRIPTION
       "VLAN Priority that will be used in all LMM frames sent by this
        LMM transmit session.
       "
    ::= { adGenY1731LmmSessionTransmitEntry 3 }

adGenY1731LmmSessionTargetRemoteMepIdentifier
OBJECT-TYPE
    SYNTAX       Integer32 (1..8191)
    MAX-ACCESS   read-only
    STATUS       current
    DESCRIPTION
       "Target MEPID for this LMM session"
    ::= { adGenY1731LmmSessionTransmitEntry 4 }

adGenY1731LmmSessionTargetMacAddress
OBJECT-TYPE
    SYNTAX      MacAddress
    MAX-ACCESS  read-only
    STATUS      current
    DESCRIPTION
       "Target MAC address for this LMM session"
    ::= { adGenY1731LmmSessionTransmitEntry 5 }

adGenY1731LmmSessionRowStatus
OBJECT-TYPE
    SYNTAX      RowStatus
    MAX-ACCESS  read-create
    STATUS      current
    DESCRIPTION
       "This OID is used to create/delete a transmit LMM session of a Local
        MEP.  The only supported settings are createAndGo, createAndWait, and
        destroy.
       "
    ::= { adGenY1731LmmSessionTransmitEntry 6 }

adGenY1731LmmSessionAdminState
OBJECT-TYPE
    SYNTAX      TruthValue
    MAX-ACCESS  read-create
    STATUS      current
    DESCRIPTION
       "The administrative state of the LMM transmit session.

        True indicates that the LMM session is to function normally and
        actively transmit LMMs towards the specified target, and false that
        it is to cease functioning.
       "
    ::= { adGenY1731LmmSessionTransmitEntry 7 }

adGenY1731LmmSessionStatus
OBJECT-TYPE
    SYNTAX      INTEGER {
                    running(1),
                    notRunning(2)
                }
    MAX-ACCESS  read-only
    STATUS      current
    DESCRIPTION
       "Operational status of the LMM transmit session.  The minimum
        attributes that need to be set before a MEP can transmit LMMs towards
        the target are: Target MEPID or MAC Address and admin state.  If a
        MEPID is used to specify the target then the local MEP must have
        received a CCM from the remote MEP in-order to learn its MAC address.
       "
    ::= { adGenY1731LmmSessionTransmitEntry 8 }

adGenY1731LmmSessionStatusString
OBJECT-TYPE
    SYNTAX      DisplayString
    MAX-ACCESS  read-only
    STATUS      current
    DESCRIPTION
       "Operational status string of the LMM transmit session.  If the session
        is expected to be active but is not able to be due to a provisioning
        issue or conflict, this string will explain the reason.
       "
    ::= { adGenY1731LmmSessionTransmitEntry 9 }

adGenY1731LmmSessionInterframeDelay
OBJECT-TYPE
    SYNTAX      Integer32 (100..10000)
    MAX-ACCESS  read-create
    STATUS      current
    DESCRIPTION
       "Amount of time in milliseconds between LMM transmissions.  The
        supported range is 100 - 10,000 ms and the default value is 1000 ms.
       "
    ::= { adGenY1731LmmSessionTransmitEntry 10 }

adGenY1731LmmSessionMeasurementInterval
OBJECT-TYPE
    SYNTAX      Integer32 (60..900)
    MAX-ACCESS  read-create
    STATUS      current
    DESCRIPTION
       "Interval in seconds over which statistics are generated.  The supported
        range is 60 - 900 seconds and the default value is 60.  The statistics
        calculated for a measurement interval are stored in the averaged data
        file.  The data for the current and previous intervals is available via
        the adGenY1731LmmSessionResultTable.
       "
    ::= { adGenY1731LmmSessionTransmitEntry 11 }

adGenY1731LmmSessionSize
OBJECT-TYPE
    SYNTAX      Integer32
    MAX-ACCESS  read-create
    STATUS      current
    DESCRIPTION
       "Size of the LMM in bytes.  The size encompasses the entire Ethernet
        frame from the header through the FCS.

        The supported values are:
        0 to indicate Data TLV should not be included in LMM sent.
        64 to 2000 bytes to indicate the DataTLV should be included to increase
        the frame length to the specified size.

        If the Data TLV is not included, the LMM will be sent with the minimum
        Ethernet frame size of 64-bytes but it will not contain the DataTLV.  A
        zero-pad will be used to fulfill  the minimum length requirement.

        The default value is 0.
       "
    ::= { adGenY1731LmmSessionTransmitEntry 12 }

adGenY1731LmmSessionData
OBJECT-TYPE
    SYNTAX      OCTET STRING (SIZE (2))
    MAX-ACCESS  read-create
    STATUS      current
    DESCRIPTION
       "Data pattern to be used when padding is required to meet the size
        setting.  The default value is 0x00 0x00.
       "
    ::= { adGenY1731LmmSessionTransmitEntry 13 }

adGenY1731LmmSessionBulkDataExportFileTypes
OBJECT-TYPE
    SYNTAX      INTEGER {
                    none(1),
                    average(2),
                    raw(3),
                    averageAndRaw(4)
                }
    MAX-ACCESS  read-create
    STATUS      current
    DESCRIPTION
       "Determines which, if any, files are generated by this LMM transmit
        session.  The files are used to store single-ended frame-loss
        statistics.  The average setting will enable storage of statistics
        generated by each measurement interval.  The raw setting will enable
        storage for each single-ended frame-loss sample.  The averageAndRaw
        setting will result in both files being generated.
       "
    ::= { adGenY1731LmmSessionTransmitEntry 14 }

--=============================================================================
--Y.1731 Local MEP Linktrace Message(LTM)
--=============================================================================
adGenY1731LocalMepLtmTable  OBJECT-TYPE
    SYNTAX      SEQUENCE OF AdGenY1731LocalMepLtmEntry
    MAX-ACCESS  not-accessible
    STATUS      current
    DESCRIPTION
       "The Y.1731 Local MEP Linktrace table.  A Local MEP is one that resides
        on an interface of the system. This table will enable the user to
        configure in preparation for starting a Linktrace session.
       "
    ::= { adGenY1731LocalMepLtm 1 }

adGenY1731LocalMepLtmEntry OBJECT-TYPE
    SYNTAX        AdGenY1731LocalMepLtmEntry
    MAX-ACCESS    not-accessible
    STATUS        current
    DESCRIPTION
       "An entry in the Y.1731 Local MEP Linktrace table."
    INDEX { adGenY1731MegLevel,
            adGenY1731MegNameFormat,
            adGenY1731MegNameLengthAndName,
            adGenY1731LocalMepIdentifier }
      ::= { adGenY1731LocalMepLtmTable 1 }

AdGenY1731LocalMepLtmEntry ::= SEQUENCE {

      adGenY1731LocalMepLtmNextTransactionId         Unsigned32,
      adGenY1731LocalMepUnexpLtrIn                   Counter32,
      adGenY1731LocalMepTransmitLtmStatus            TruthValue,
      adGenY1731LocalMepTransmitLtmFlags             BITS,
      adGenY1731LocalMepTransmitLtmTargetMacAddress  MacAddress,
      adGenY1731LocalMepTransmitLtmTargetMepId       Integer32,
      adGenY1731LocalMepTransmitLtmTargetIsMepId     TruthValue,
      adGenY1731LocalMepTransmitLtmTtl               Unsigned32,
      adGenY1731LocalMepTransmitLtmResult            TruthValue,
      adGenY1731LocalMepTransmitLtmTransactionId     Unsigned32,
      adGenY1731LocalMepTransmitLtmEgressIdentifier  OCTET STRING,
      adGenY1731LocalMepTransmitLtmStatusString      DisplayString,
      adGenY1731LocalMepTransmitLtmConfigStatus      TruthValue,
      adGenY1731LocalMepLtmActive                    TruthValue,
      adGenY1731LocalMepLtmTotalOut                  Counter32,
      adGenY1731LocalMepLtrTotalIn                   Counter32,
      adGenY1731LocalMepLtrTotalInvalidIn            Counter32,
      adGenY1731LocalMepLtrTotalValidIn              Counter32
    }

adGenY1731LocalMepLtmNextTransactionId
OBJECT-TYPE
    SYNTAX      Unsigned32
    MAX-ACCESS  read-only
    STATUS      current
    DESCRIPTION
       "Next transaction identifier to be sent in a Linktrace message. This
        transaction identifier value can be zero because it wraps around.
       "
    ::= { adGenY1731LocalMepLtmEntry 1 }

adGenY1731LocalMepUnexpLtrIn
OBJECT-TYPE
    SYNTAX      Counter32
    MAX-ACCESS  read-only
    STATUS      current
    DESCRIPTION
       "The total number of unexpected LTRs received."
    ::= { adGenY1731LocalMepLtmEntry 2 }

adGenY1731LocalMepTransmitLtmStatus OBJECT-TYPE
   SYNTAX      TruthValue
   MAX-ACCESS  read-only
   STATUS      current
   DESCRIPTION
      "A Boolean flag set to true by the bridge port to indicate that another
       LTM may be transmitted. Reset to false by the MEP Linktrace Initiator
       State Machine."
   DEFVAL { true }
   ::= { adGenY1731LocalMepLtmEntry 3 }

adGenY1731LocalMepTransmitLtmFlags
OBJECT-TYPE
    SYNTAX      BITS {
                  useFDBonly   (0)
                }
    MAX-ACCESS  read-write
    STATUS      current
    DESCRIPTION
       "The flags field for LTMs transmitted by the MEP."
    DEFVAL { {useFDBonly } }
    ::= { adGenY1731LocalMepLtmEntry 4 }

adGenY1731LocalMepTransmitLtmTargetMacAddress
OBJECT-TYPE
    SYNTAX      MacAddress
    MAX-ACCESS  read-write
    STATUS      current
    DESCRIPTION
       "The Target MAC Address Field to be transmitted: A unicast destination
        MAC address. This address will be used if the value of the column
        adGenY1731LocalMepTransmitLtmTargetIsMepId is 'false'.
       "
    ::= { adGenY1731LocalMepLtmEntry 5 }

adGenY1731LocalMepTransmitLtmTargetMepId
OBJECT-TYPE
    SYNTAX      Integer32 (1..8191)
    MAX-ACCESS  read-write
    STATUS      current
    DESCRIPTION
       "An indication of the Target MAC Address Field to be transmitted.  The
        MAC address to be used will be retrieved from the Local MEP's Remote
        MEP database by using the MEPID specified to perform the look-up.  This
        address will be used if the value of the column
        adGenY1731LocalMepTransmitLtmTargetIsMepId is 'true'.
       "
    ::= { adGenY1731LocalMepLtmEntry 6 }

adGenY1731LocalMepTransmitLtmTargetIsMepId
OBJECT-TYPE
    SYNTAX      TruthValue
    MAX-ACCESS  read-write
    STATUS      current
    DESCRIPTION
       "True indicates that MEPID of the target MEP is used for Linktrace
        transmission. False indicates that unicast destination MAC address of
        the target MEP is used for Linktrace transmission.
       "
    ::= { adGenY1731LocalMepLtmEntry 7 }

adGenY1731LocalMepTransmitLtmTtl
OBJECT-TYPE
    SYNTAX      Unsigned32 (0..255)
    MAX-ACCESS  read-write
    STATUS      current
    DESCRIPTION
       "The LTM TTL field. Default value, if not specified, is 64.  The TTL
        field indicates the number of hops remaining to the LTM.
        Decremented by 1 by each Linktrace Responder that handles the LTM.
        The value returned in the LTR is one less than that received in the
        LTM.  If the LTM TTL is 0 or 1, the LTM is not forwarded to the next
        hop, and if 0, no LTR is generated.
       "
    DEFVAL {64}
    ::= { adGenY1731LocalMepLtmEntry 8 }

adGenY1731LocalMepTransmitLtmResult
OBJECT-TYPE
    SYNTAX      TruthValue
    MAX-ACCESS  read-only
    STATUS      current
    DESCRIPTION
       "Indicates the result of the operation:

        true    The Linktrace Message will be (or has been) sent.
        false   The Linktrace Message will not be sent.
       "
    DEFVAL { true }
    ::= { adGenY1731LocalMepLtmEntry 9 }

adGenY1731LocalMepTransmitLtmTransactionId
OBJECT-TYPE
    SYNTAX      Unsigned32
    MAX-ACCESS  read-only
    STATUS      current
    DESCRIPTION
       "The LTM Transaction Identifier (adGenY1731LocalMepLtmNextTransactionId)
        of the LTM sent. The value returned is undefined if
        adGenY1731LocalMepTransmitLtmResult is false.
       "
    ::= { adGenY1731LocalMepLtmEntry 10 }

adGenY1731LocalMepTransmitLtmEgressIdentifier
OBJECT-TYPE
    SYNTAX      OCTET STRING (SIZE(8))
    MAX-ACCESS  read-only
    STATUS      current
    DESCRIPTION
       "Identifies the MEP Linktrace Initiator that is originating, or the
        Linktrace Responder that is forwarding, this LTM.  The low-order six
        octets contain a 48-bit IEEE MAC address unique to the system in which
        the MEP Linktrace Initiator or Linktrace Responder resides.  The
        high-order two octets contain a value sufficient to uniquely identify
        the MEP Linktrace Initiator or Linktrace Responder within that system.

        For most Bridges, the address of any MAC attached to the Bridge will
        suffice for the low-order six octets, and 0 for the high-order octets.
        In some situations, e.g., if multiple virtual Bridges utilizing
        emulated LANs are implemented in a single physical system, the
        high-order two octets can be used to differentiate among the
        transmitting entities.

        The value returned is undefined if adGenY1731LocalMepTransmitLtmResult
        is false.
       "
    ::= { adGenY1731LocalMepLtmEntry 11 }

adGenY1731LocalMepTransmitLtmStatusString OBJECT-TYPE
    SYNTAX      DisplayString
    MAX-ACCESS  read-only
    STATUS      current
    DESCRIPTION
       "Linktrace error status contains a string indicating the reason they
        the Lintkrace transmission attempt failed.
       "
     ::= { adGenY1731LocalMepLtmEntry 12 }

adGenY1731LocalMepTransmitLtmConfigStatus OBJECT-TYPE
    SYNTAX      TruthValue
    MAX-ACCESS  read-write
    STATUS      current
    DESCRIPTION
       "True means the MEP is ready for configuring LTM and a false means the MEP
        is under LTM configuration. This flag is used to prevent simultaneous
        configuration by more than  one user. If one minute has passed since the
        last LocalMepLtm attribute was set, then it is assume the user has abandoned
        configuring the session and the adGenY1731LocalMepTransmitLtmConfigStatus will be
        reset to true.
       "
     ::= { adGenY1731LocalMepLtmEntry 13 }

adGenY1731LocalMepLtmActive OBJECT-TYPE
    SYNTAX      TruthValue
    MAX-ACCESS  read-write
    STATUS      current
    DESCRIPTION
       "Start or stop LTM transmission. By writing true, start LTM transmisson.
       By writing false, stop LTM transmission
       "
    DEFVAL { false }
    ::= {adGenY1731LocalMepLtmEntry 14 }

adGenY1731LocalMepLtmTotalOut
OBJECT-TYPE
    SYNTAX      Counter32
    MAX-ACCESS  read-only
    STATUS      current
    DESCRIPTION
       "The total number of LTMs transmitted by the Local MEP."
    ::= { adGenY1731LocalMepLtmEntry 15 }

adGenY1731LocalMepLtrTotalIn
OBJECT-TYPE
    SYNTAX      Counter32
    MAX-ACCESS  read-only
    STATUS      current
    DESCRIPTION
       "The total number of LTRs received by the Local MEP."
    ::= { adGenY1731LocalMepLtmEntry 16 }

adGenY1731LocalMepLtrTotalInvalidIn
OBJECT-TYPE
    SYNTAX      Counter32
    MAX-ACCESS  read-only
    STATUS      current
    DESCRIPTION
       "The total number of invalid LTRs received by the Local MEP."
    ::= { adGenY1731LocalMepLtmEntry 17 }

adGenY1731LocalMepLtrTotalValidIn
OBJECT-TYPE
    SYNTAX      Counter32
    MAX-ACCESS  read-only
    STATUS      current
    DESCRIPTION
       "The total number of valid LTRs received by the Local MEP."
    ::= { adGenY1731LocalMepLtmEntry 18 }

--=============================================================================
--Y.1731 Local MEP Linktrace Session Table
--=============================================================================
adGenY1731LocalMepLtSessionTable  OBJECT-TYPE
    SYNTAX      SEQUENCE OF AdGenY1731LocalMepLtSessionEntry
    MAX-ACCESS  not-accessible
    STATUS      current
    DESCRIPTION
       "The Y.1731 Local MEP Linktrace session table.  This table contains a list
        of Linktrace sessions and the counters associated with each session.
       "
    ::= { adGenY1731LocalMepLtm 2 }

adGenY1731LocalMepLtSessionEntry OBJECT-TYPE
    SYNTAX        AdGenY1731LocalMepLtSessionEntry
    MAX-ACCESS    not-accessible
    STATUS        current
    DESCRIPTION
       "An entry in the Y.1731 Local MEP Linktrace session table."
    INDEX { adGenY1731MegLevel,
            adGenY1731MegNameFormat,
            adGenY1731MegNameLengthAndName,
            adGenY1731LocalMepIdentifier,
            adGenY1731LocalMepLtmTransactionId}
      ::= { adGenY1731LocalMepLtSessionTable 1 }

AdGenY1731LocalMepLtSessionEntry ::= SEQUENCE {
      adGenY1731LocalMepLtmTransactionId    Unsigned32,
      adGenY1731LocalMepLtmOut              Counter32,
      adGenY1731LocalMepLtrIn               Counter32,
      adGenY1731LocalMepLtrInvalidIn        Counter32,
      adGenY1731LocalMepLtrValidIn          Counter32,
      adGenY1731LocalMepLtTimeRemaining     Unsigned32
    }

adGenY1731LocalMepLtmTransactionId
OBJECT-TYPE
    SYNTAX      Unsigned32 (0..4294967295)
    MAX-ACCESS  not-accessible
    STATUS      current
    DESCRIPTION
       "Transaction identifier value in LTM transmitted for this Linktrace
        session.
       "
    ::= { adGenY1731LocalMepLtSessionEntry 1}

adGenY1731LocalMepLtmOut
OBJECT-TYPE
    SYNTAX      Counter32
    MAX-ACCESS  read-only
    STATUS      current
    DESCRIPTION
       "The number of LTM transmitted for this Linktrace session."
    ::= { adGenY1731LocalMepLtSessionEntry 2 }

adGenY1731LocalMepLtrIn
OBJECT-TYPE
    SYNTAX      Counter32
    MAX-ACCESS  read-only
    STATUS      current
    DESCRIPTION
       "The number of LTRs received for this Linktrace session."
    ::= { adGenY1731LocalMepLtSessionEntry 3 }

adGenY1731LocalMepLtrInvalidIn
OBJECT-TYPE
    SYNTAX      Counter32
    MAX-ACCESS  read-only
    STATUS      current
    DESCRIPTION
       "The number of LTRs received and discarded for this Linktrace session
        due to invalid formatting.
       "
    ::= { adGenY1731LocalMepLtSessionEntry 4 }

adGenY1731LocalMepLtrValidIn
OBJECT-TYPE
    SYNTAX      Counter32
    MAX-ACCESS  read-only
    STATUS      current
    DESCRIPTION
       "The number of LTRs received and processed as valid for this Linktrace
        session.
       "
    ::= { adGenY1731LocalMepLtSessionEntry 5 }

adGenY1731LocalMepLtTimeRemaining OBJECT-TYPE
    SYNTAX      Unsigned32
    MAX-ACCESS  read-only
    STATUS      current
    DESCRIPTION
       "Each Linktrace sequence will run for a fixed period of time.  This
        counter indicates how much time is remaining.  When the counter is 0,
        there are results in the Linktrace cache. If this object does not exist
        for a given index, then there are no results in the cache for that
        MEP/Transaction ID combination.
       "
     ::= { adGenY1731LocalMepLtSessionEntry 6 }

--=============================================================================
--Y.1731 Local MEP Linktrace Reply Table
--=============================================================================
adGenY1731LocalMepLtrTable  OBJECT-TYPE
    SYNTAX      SEQUENCE OF AdGenY1731LocalMepLtrEntry
    MAX-ACCESS  not-accessible
    STATUS      current
    DESCRIPTION
       "The Y.1731 Local MEP Linktrace reply table.  This table contains a list
       of Linktrace replies received by a specific MEP in response to a
       Linktrace message.
       "
    ::= { adGenY1731LocalMepLtm 3 }

adGenY1731LocalMepLtrEntry OBJECT-TYPE
    SYNTAX        AdGenY1731LocalMepLtrEntry
    MAX-ACCESS    not-accessible
    STATUS        current
    DESCRIPTION
       "An entry in the Y.1731 Local MEP Linktrace reply table."
    INDEX { adGenY1731MegLevel,
            adGenY1731MegNameFormat,
            adGenY1731MegNameLengthAndName,
            adGenY1731LocalMepIdentifier,
            adGenY1731LocalMepLtrTransactionId,
            adGenY1731LocalMepLtrReceiveOrder }
      ::= { adGenY1731LocalMepLtrTable 1 }

AdGenY1731LocalMepLtrEntry ::= SEQUENCE {
      adGenY1731LocalMepLtrTransactionId            Unsigned32,
      adGenY1731LocalMepLtrReceiveOrder             Unsigned32,
      adGenY1731LocalMepLtrTtl                      Unsigned32,
      adGenY1731LocalMepLtrForwarded                TruthValue,
      adGenY1731LocalMepLtrTerminalMep              TruthValue,
      adGenY1731LocalMepLtrLastEgressIdentifier     OCTET STRING,
      adGenY1731LocalMepLtrNextEgressIdentifier     OCTET STRING,
      adGenY1731LocalMepLtrRelay                    INTEGER,
      adGenY1731LocalMepLtrChassisIdSubtype         INTEGER,
      adGenY1731LocalMepLtrChassisId                LldpChassisId,
      adGenY1731LocalMepLtrManAddressDomain         TDomain,
      adGenY1731LocalMepLtrManAddress               TAddress,
      adGenY1731LocalMepLtrIngress                  INTEGER,
      adGenY1731LocalMepLtrIngressMac               MacAddress,
      adGenY1731LocalMepLtrIngressPortIdSubtype     LldpPortIdSubtype,
      adGenY1731LocalMepLtrIngressPortId            LldpPortId,
      adGenY1731LocalMepLtrEgress                   INTEGER,
      adGenY1731LocalMepLtrEgressMac                MacAddress,
      adGenY1731LocalMepLtrEgressPortIdSubtype      LldpPortIdSubtype,
      adGenY1731LocalMepLtrEgressPortId             LldpPortId,
      adGenY1731LocalMepLtrOrganizationSpecificTlv  OCTET STRING
    }

adGenY1731LocalMepLtrTransactionId
OBJECT-TYPE
    SYNTAX      Unsigned32 (0..4294967295)
    MAX-ACCESS  not-accessible
    STATUS      current
    DESCRIPTION
       "Transaction identifier returned by a previous transmit Linktrace
        message command, indicating which LTM's response is going to be
        returned.
       "
    ::= { adGenY1731LocalMepLtrEntry 1}

adGenY1731LocalMepLtrReceiveOrder
OBJECT-TYPE
    SYNTAX      Unsigned32(1..4294967295)
    MAX-ACCESS  not-accessible
    STATUS      current
    DESCRIPTION
       "An index to distinguish among multiple LTRs with the same LTR
        Transaction Identifier field value.  adGenY1731LocalMepLtrReceiveOrder
        are assigned sequentially from 1, in the order that the Linktrace
        Initiator received the LTRs.
       "
    ::= { adGenY1731LocalMepLtrEntry 2 }

adGenY1731LocalMepLtrTtl
OBJECT-TYPE
    SYNTAX      Unsigned32 (0..255)
    MAX-ACCESS  read-only
    STATUS      current
    DESCRIPTION
       "TTL field value for a returned LTR."
    ::= { adGenY1731LocalMepLtrEntry 3 }

adGenY1731LocalMepLtrForwarded
OBJECT-TYPE
    SYNTAX      TruthValue
    MAX-ACCESS  read-only
    STATUS      current
    DESCRIPTION
       "Indicates if a LTM was forwarded by the responding MP, as returned in
        the 'FwdYes' flag of the flags field.
       "
    ::= { adGenY1731LocalMepLtrEntry 4 }

adGenY1731LocalMepLtrTerminalMep
OBJECT-TYPE
    SYNTAX      TruthValue
    MAX-ACCESS  read-only
    STATUS      current
    DESCRIPTION
       "A boolean value stating whether the forwarded LTM reached a MEP within
        the MEG, as returned in the Terminal MEP flag of the Flags field.
       "
    ::= { adGenY1731LocalMepLtrEntry 5 }

adGenY1731LocalMepLtrLastEgressIdentifier
OBJECT-TYPE
    SYNTAX      OCTET STRING (SIZE(8))
    MAX-ACCESS  read-only
    STATUS      current
    DESCRIPTION
       "An octet field holding the Last Egress Identifier returned in the LTR
        Egress Identifier TLV of the LTR. The Last Egress Identifier identifies
        the MEP Linktrace Initiator that originated, or the Linktrace Responder
        that forwarded, the LTM to which this LTR is the response.  This is the
        same value as the Egress Identifier TLV of that LTM.
       "
    ::= { adGenY1731LocalMepLtrEntry 6 }

adGenY1731LocalMepLtrNextEgressIdentifier
OBJECT-TYPE
    SYNTAX      OCTET STRING (SIZE(8))
    MAX-ACCESS  read-only
    STATUS      current
    DESCRIPTION
       "An octet field holding the Next Egress Identifier returned in the LTR
        Egress Identifier TLV of the LTR.  The Next Egress Identifier
        Identifies the Linktrace Responder that transmitted this LTR, and can
        forward the LTM to the next hop.  This is the same value as the Egress
        Identifier TLV of the forwarded LTM, if any. If the FwdYes bit of the
        Flags field is false, the contents of this field are undefined, i.e.,
        any value can be transmitted, and the field is ignored by the receiver.
       "
    ::= { adGenY1731LocalMepLtrEntry 7 }

adGenY1731LocalMepLtrRelay
OBJECT-TYPE
    SYNTAX      INTEGER {
                  rlyHit     (1),
                  rlyFdb     (2),
                  rlyMpdb    (3)
                }
    MAX-ACCESS  read-only
    STATUS      current
    DESCRIPTION
       "Value returned in the Relay Action field."
    ::= { adGenY1731LocalMepLtrEntry 8 }

adGenY1731LocalMepLtrChassisIdSubtype
OBJECT-TYPE
    SYNTAX      INTEGER {
                    nonePresent(0),
                    chassisComponent(1),
                    interfaceAlias(2),
                    portComponent(3),
                    macAddress(4),
                    networkAddress(5),
                    interfaceName(6),
                    local(7)
                }
    MAX-ACCESS  read-only
    STATUS      current
    DESCRIPTION
       "This object specifies the format of the Chassis ID returned in the
        Sender ID TLV of the LTR, if any.
       "
    ::= { adGenY1731LocalMepLtrEntry 9 }

adGenY1731LocalMepLtrChassisId
OBJECT-TYPE
    SYNTAX      LldpChassisId
    MAX-ACCESS  read-only
    STATUS      current
    DESCRIPTION
       "The Chassis ID returned in the Sender ID TLV of the LTR, if any. The
        format of this object is determined by the value of the
        adGenY1731LocalMepLtrChassisIdSubtype object.
       "
    ::= { adGenY1731LocalMepLtrEntry 10 }

adGenY1731LocalMepLtrManAddressDomain
OBJECT-TYPE
    SYNTAX      TDomain
    MAX-ACCESS  read-only
    STATUS      current
    DESCRIPTION
       "The TDomain that identifies the type and format of the related
        adGenY1731LocalMepLtrManAddress object, used to access the SNMP agent
        of the system transmitting the LTR.  Received in the LTR Sender ID TLV
        from that system.

        Typical values will be one of (not all inclusive) list:


           snmpUDPDomain          (from SNMPv2-TM, RFC3417)
           snmpIeee802Domain      (from SNMP-IEEE802-TM-MIB, RFC4789)

        The value 'zeroDotZero' (from RFC2578) indicates 'no management address
        was present in the LTR', in which case the related object
        adGenY1731LocalMepLtrManAddress must have a zero-length OCTET STRING as
        a value.
       "
    ::= { adGenY1731LocalMepLtrEntry 11 }

adGenY1731LocalMepLtrManAddress
OBJECT-TYPE
    SYNTAX      TAddress
    MAX-ACCESS  read-only
    STATUS      current
    DESCRIPTION
       "The TAddress that can be used to access the SNMP agent of the system
        transmitting the CCM, received in the CCM Sender ID TLV from that
        system.

        If the related object adGenY1731LocalMepLtrManAddressDomain contains
        the value 'zeroDotZero', this object dot1agCfmLtrManAddress must have
        a zero-length OCTET STRING as a value.
      "
    ::= { adGenY1731LocalMepLtrEntry 12 }

adGenY1731LocalMepLtrIngress
OBJECT-TYPE
    SYNTAX      INTEGER {
                  ingNoTlv    (0),
                  ingOk       (1),
                  ingDown     (2),
                  ingBlocked  (3),
                  ingVid      (4)
                }
    MAX-ACCESS  read-only
    STATUS      current
    DESCRIPTION
       "The value returned in the Ingress Action Field of the LTM. The value
        ingNoTlv(0) indicates that no Reply Ingress TLV was returned in the LTM.
       "
    ::= { adGenY1731LocalMepLtrEntry 13 }

adGenY1731LocalMepLtrIngressMac
OBJECT-TYPE
    SYNTAX      MacAddress
    MAX-ACCESS  read-only
    STATUS      current
    DESCRIPTION
       "MAC address returned in the ingress MAC address field.  If the
        adGenY1731LocalMepLtrIngress object contains the value ingNoTlv(0),
        then the contents of this object are meaningless.
       "
    ::= { adGenY1731LocalMepLtrEntry 14 }

adGenY1731LocalMepLtrIngressPortIdSubtype
OBJECT-TYPE
    SYNTAX      LldpPortIdSubtype
    MAX-ACCESS  read-only
    STATUS      current
    DESCRIPTION
       "Format of the Ingress Port ID.

        If the adGenY1731LocalMepLtrIngress object contains the value
        ingNoTlv(0), then the contents of this object are meaningless.
       "
   ::= { adGenY1731LocalMepLtrEntry 15 }

adGenY1731LocalMepLtrIngressPortId
OBJECT-TYPE
    SYNTAX      LldpPortId
    MAX-ACCESS  read-only
    STATUS      current
    DESCRIPTION
       "Ingress Port ID.

        The format of this object is determined by the value of the
        adGenY1731LocalMepLtrIngressPortIdSubtype object.  If the
        adGenY1731LocalMepLtrIngress object contains the value ingNoTlv(0),
        then the contents of this object are meaningless.
       "
    ::= { adGenY1731LocalMepLtrEntry 16 }

adGenY1731LocalMepLtrEgress
OBJECT-TYPE
    SYNTAX      INTEGER {
                  egrNoTlv    (0),
                  egrOK       (1),
                  egrDown     (2),
                  egrBlocked  (3),
                  egrVid      (4)
                }
    MAX-ACCESS  read-only
    STATUS      current
    DESCRIPTION
       "The value returned in the Egress Action Field of the LTR.  The value
        egrNoTlv(0) indicates that no Reply Egress TLV was returned in the LTR.
       "
    ::= { adGenY1731LocalMepLtrEntry 17 }

adGenY1731LocalMepLtrEgressMac
OBJECT-TYPE
    SYNTAX      MacAddress
    MAX-ACCESS  read-only
    STATUS      current
    DESCRIPTION
       "MAC address returned in the egress MAC address field.

        If the adGenY1731LocalMepLtrIngress object contains the value
        egrNoTlv(0), then the contents of this object are meaningless.
       "
    ::= { adGenY1731LocalMepLtrEntry 18 }

adGenY1731LocalMepLtrEgressPortIdSubtype
OBJECT-TYPE
    SYNTAX      LldpPortIdSubtype
    MAX-ACCESS  read-only
    STATUS      current
    DESCRIPTION
       "Format of the egress Port ID.

        If the adGenY1731LocalMepLtrEgress object contains the value
        egrNoTlv(0), then the contents of this object are meaningless.
       "
    ::= { adGenY1731LocalMepLtrEntry 19 }

adGenY1731LocalMepLtrEgressPortId
OBJECT-TYPE
    SYNTAX      LldpPortId
    MAX-ACCESS  read-only
    STATUS      current
    DESCRIPTION
       "Egress Port ID.

        The format of this object is determined by the value of the
        adGenY1731LocalMepLtrEgressPortIdSubtype object.  If the
        adGenY1731LocalMepLtrEgress object contains the value egrNoTlv(0),
        then the contents of this object are meaningless.
       "
    ::= { adGenY1731LocalMepLtrEntry 20 }

adGenY1731LocalMepLtrOrganizationSpecificTlv
OBJECT-TYPE
    SYNTAX      OCTET STRING (SIZE(0|4..1500))
    MAX-ACCESS  read-only
    STATUS      current
    DESCRIPTION
       "All Organization specific TLVs returned in the LTR, if any.  Includes
        all octets including and following the TLV Length field of each TLV,
        concatenated together.
       "
    ::= { adGenY1731LocalMepLtrEntry 21 }

--=============================================================================
--Y.1731 Local MEP Linktrace Responder Table
--=============================================================================
adGenY1731LocalMepLtmResponderTable  OBJECT-TYPE
    SYNTAX      SEQUENCE OF AdGenY1731LocalMepLtmResponderEntry
    MAX-ACCESS  not-accessible
    STATUS      current
    DESCRIPTION
       "The Y.1731 Local MEP Linktrace Responder table.  This table contains
        the counters associated with each Local MEP's Linktrace Responder.
       "
    ::= { adGenY1731LocalMepLtm 4 }

adGenY1731LocalMepLtmResponderEntry OBJECT-TYPE
    SYNTAX        AdGenY1731LocalMepLtmResponderEntry
    MAX-ACCESS    not-accessible
    STATUS        current
    DESCRIPTION
       "An entry in the Y.1731 Local MEP Linktrace Responder table."
    INDEX { adGenY1731MegLevel,
            adGenY1731MegNameFormat,
            adGenY1731MegNameLengthAndName,
            adGenY1731LocalMepIdentifier}
      ::= { adGenY1731LocalMepLtmResponderTable 1 }

AdGenY1731LocalMepLtmResponderEntry ::= SEQUENCE {
      adGenY1731LocalMepLtmIn                       Counter32,
      adGenY1731LocalMepLtmDiscardedInvalidFormat   Counter32,
      adGenY1731LocalMepLtmDiscardedTtl             Counter32,
      adGenY1731LocalMepLtmDiscardedTargetMac       Counter32,
      adGenY1731LocalMepLtrOut                      Counter32
    }


adGenY1731LocalMepLtmIn
OBJECT-TYPE
    SYNTAX      Counter32
    MAX-ACCESS  read-only
    STATUS      current
    DESCRIPTION
       "The total number of valid LTMs received."
    ::= { adGenY1731LocalMepLtmResponderEntry 1 }

adGenY1731LocalMepLtmDiscardedInvalidFormat
OBJECT-TYPE
    SYNTAX      Counter32
    MAX-ACCESS  read-only
    STATUS      current
    DESCRIPTION
       "The total number LTMs discarded due to invalid format."
    ::= { adGenY1731LocalMepLtmResponderEntry 2 }

adGenY1731LocalMepLtmDiscardedTtl
OBJECT-TYPE
    SYNTAX      Counter32
    MAX-ACCESS  read-only
    STATUS      current
    DESCRIPTION
       "The total number of LTMs discarded due to invalid Ttl."
    ::= { adGenY1731LocalMepLtmResponderEntry 3 }

adGenY1731LocalMepLtmDiscardedTargetMac
OBJECT-TYPE
    SYNTAX      Counter32
    MAX-ACCESS  read-only
    STATUS      current
    DESCRIPTION
       "The total number of LTMs discarded due to invalid target MAC address."
    ::= { adGenY1731LocalMepLtmResponderEntry 4 }

adGenY1731LocalMepLtrOut
OBJECT-TYPE
    SYNTAX      Counter32
    MAX-ACCESS  read-only
    STATUS      current
    DESCRIPTION
       "The total number of LTRs transmitted."
    ::= { adGenY1731LocalMepLtmResponderEntry 5 }

--=============================================================================
--Y.1731 Local MEP ETH-1DM Scalars
--=============================================================================

adGenY1731OneDmSessionMaxNumber OBJECT-TYPE
    SYNTAX      Unsigned32
    MAX-ACCESS  read-only
    STATUS      current
    DESCRIPTION
       "A systemwide value representing the maximum number of one-way frame
        delay (ETH-1DM) sessions that can be created across all local MEPs on
        the device.
       "
    ::= { adGenY1731OneDmScalars 1 }

adGenY1731OneDmSessionCurrentNumber OBJECT-TYPE
    SYNTAX      Unsigned32
    MAX-ACCESS  read-only
    STATUS      current
    DESCRIPTION
       "Current number of 1DM sessions created."
    ::= { adGenY1731OneDmScalars 2 }

adGenY1731OneDmSessionLastCreateError OBJECT-TYPE
    SYNTAX      DisplayString
    MAX-ACCESS  read-only
    STATUS      current
    DESCRIPTION
       "The reason for the last error that occurred while attempting to create
        an 1DM Session Transmit entry (adGenY1731OneDmSessionTransmitEntry).
       "
    ::= { adGenY1731OneDmScalars 3 }

--=============================================================================
--Y.1731 Local MEP ETH-1DM Transmit Table
--=============================================================================
adGenY1731OneDmSessionTransmitTable
OBJECT-TYPE
    SYNTAX      SEQUENCE OF AdGenY1731OneDmSessionTransmitEntry
    MAX-ACCESS  not-accessible
    STATUS      current
    DESCRIPTION
       "The one-way frame-delay (ETH-1DM) session table for a given local MEP.
        A local MEP's 1DM sessions can be created, edited, and deleted using
        this table.  A local MEP can target a remote MEP to run one-way frame
        delay measurements between the local MEP and another remote MEP in the
        MEG.

        The target can be specified by either using a MAC address of the target
        MEP or the MEPID of the target MEP.  For the 1DM session to go active,
        the local MEP must be successfully receiving CCMs from the remote MEP
        in order to specify the RMEPID as the target.
       "
    ::= { adGenY1731LocalMepOneDm 2 }

adGenY1731OneDmSessionTransmitEntry OBJECT-TYPE
    SYNTAX        AdGenY1731OneDmSessionTransmitEntry
    MAX-ACCESS    not-accessible
    STATUS        current
    DESCRIPTION
       "A one-way frame-delay (1DM) performance monitoring session of a
        local MEP.  A 1DM PM session is unique based on target identifier
        and VLAN priority.  The target identifier is either a MAC address
        or RMEPID.  Inclusion of VLAN priority in the index allows a local MEP
        to simultaneously run several 1DM PM sessions between it and the target
        at various CoS levels.
       "
    INDEX { adGenY1731MegLevel,
            adGenY1731MegNameFormat,
            adGenY1731MegNameLengthAndName,
            adGenY1731LocalMepIdentifier,
            adGenY1731OneDmSessionTargetRmepIdOrMacAddress,
            adGenY1731OneDmSessionTarget,
            adGenY1731OneDmSessionVlanPriority
          }
    ::= { adGenY1731OneDmSessionTransmitTable 1 }

AdGenY1731OneDmSessionTransmitEntry ::= SEQUENCE {
      adGenY1731OneDmSessionTargetRmepIdOrMacAddress   INTEGER,
      adGenY1731OneDmSessionTarget                     OCTET STRING,
      adGenY1731OneDmSessionVlanPriority               Integer32,
      adGenY1731OneDmSessionTargetRemoteMepIdentifier  Integer32,
      adGenY1731OneDmSessionTargetMacAddress           MacAddress,
      adGenY1731OneDmSessionRowStatus                  RowStatus,
      adGenY1731OneDmSessionAdminState                 TruthValue,
      adGenY1731OneDmSessionStatus                     INTEGER,
      adGenY1731OneDmSessionStatusString               DisplayString,
      adGenY1731OneDmSessionInterframeDelay            Integer32,
      adGenY1731OneDmSessionSize                       Integer32,
      adGenY1731OneDmSessionData                       OCTET STRING
    }

adGenY1731OneDmSessionTargetRmepIdOrMacAddress
OBJECT-TYPE
    SYNTAX      INTEGER {
                    rmepId(1),
                    macAddress(2)
                }
    MAX-ACCESS  not-accessible
    STATUS      current
    DESCRIPTION
       "Indicates whether the target specified is a MEPID or a unicast MAC
        Address.  If the target specified is a MEPID, the local MEP will not be
        able to initiate the 1DM session until a CCM has been received from the
        RMEP
       "
    ::= { adGenY1731OneDmSessionTransmitEntry 1 }

adGenY1731OneDmSessionTarget
OBJECT-TYPE
    SYNTAX      OCTET STRING (SIZE (1..6))
    MAX-ACCESS  not-accessible
    STATUS      current
    DESCRIPTION
       "Octet string defining the target for the 1DM session.
        If adGenY1731OneDmSessionTargetRmepIdOrMacAddress indicates the target
        is a MEPID then the octet string should represent a MEPID between the
        range 1-8191.  Otherwise, it should be the target's unicast MAC address
       "
    ::= { adGenY1731OneDmSessionTransmitEntry 2 }

adGenY1731OneDmSessionVlanPriority
OBJECT-TYPE
    SYNTAX      Integer32 (0..7)
    MAX-ACCESS  not-accessible
    STATUS      current
    DESCRIPTION
       "VLAN Priority that will be used in all 1DM frames sent by this
        1DM transmit session.
       "
    ::= { adGenY1731OneDmSessionTransmitEntry 3 }

adGenY1731OneDmSessionTargetRemoteMepIdentifier
OBJECT-TYPE
    SYNTAX      Integer32 (1..8191)
    MAX-ACCESS  read-only
    STATUS      current
    DESCRIPTION
       "Target MEPID for this 1DM session"
    ::= { adGenY1731OneDmSessionTransmitEntry 4 }

adGenY1731OneDmSessionTargetMacAddress
OBJECT-TYPE
    SYNTAX      MacAddress
    MAX-ACCESS  read-only
    STATUS      current
    DESCRIPTION
       "Target MAC address for this 1DM session"
    ::= { adGenY1731OneDmSessionTransmitEntry 5 }

adGenY1731OneDmSessionRowStatus
OBJECT-TYPE
    SYNTAX      RowStatus
    MAX-ACCESS  read-create
    STATUS      current
    DESCRIPTION
       "This OID is used to create/delete a transmit 1DM session of a Local
        MEP.  The only supported settings are createAndGo, createAndWait, and
        destroy.
       "
    ::= { adGenY1731OneDmSessionTransmitEntry 6 }

adGenY1731OneDmSessionAdminState
OBJECT-TYPE
    SYNTAX      TruthValue
    MAX-ACCESS  read-create
    STATUS      current
    DESCRIPTION
       "The administrative state of the 1DM transmit session.

        True indicates that the 1DM session is to function normally and
        actively transmit 1DMs towards the specified target, and false that
        it is to cease functioning.
       "
    ::= { adGenY1731OneDmSessionTransmitEntry 7 }

adGenY1731OneDmSessionStatus
OBJECT-TYPE
    SYNTAX      INTEGER {
                    running(1),
                    notRunning(2)
                }
    MAX-ACCESS  read-only
    STATUS      current
    DESCRIPTION
       "Operational status of the 1DM transmit session.  The minimum
        attributes that need to be set before a MEP can transmit 1DMs towards
        the target are: Target MEPID or MAC Address and admin state.  If a
        MEPID is used to specify the target then the local MEP must have
        received a CCM from the remote MEP in-order to learn its MAC address.
       "
    ::= { adGenY1731OneDmSessionTransmitEntry 8 }

adGenY1731OneDmSessionStatusString
OBJECT-TYPE
    SYNTAX      DisplayString
    MAX-ACCESS  read-only
    STATUS      current
    DESCRIPTION
       "Operational status string of the 1DM transmit session.  If the session
        is expected to be active but is not able to be due to a provisioning
        issue or conflict, this string will explain the reason.
       "
    ::= { adGenY1731OneDmSessionTransmitEntry 9 }

adGenY1731OneDmSessionInterframeDelay
OBJECT-TYPE
    SYNTAX      Integer32 (100..10000)
    MAX-ACCESS  read-create
    STATUS      current
    DESCRIPTION
       "Amount of time in milliseconds between 1DM transmissions.  The
        supported range is 100 - 10,000 ms and the default value is 1000 ms.
       "
    ::= { adGenY1731OneDmSessionTransmitEntry 10 }

adGenY1731OneDmSessionSize
OBJECT-TYPE
    SYNTAX      Integer32
    MAX-ACCESS  read-create
    STATUS      current
    DESCRIPTION
       "Size of the 1DM in bytes.  The size encompasses the entire Ethernet
        frame from the header through the FCS.

        The supported values are:
        0 to indicate Data TLV should not be included in 1DM sent.
        64 to 2000 bytes to indicate the DataTLV should be included to increase
        the frame length to the specified size.

        If the Data TLV is not included, the 1DM will be sent with the minimum
        Ethernet frame size of 64-bytes but it will not contain the DataTLV.  A
        zero-pad will be used to fulfill  the minimum length requirement.

        The default value is 0.
       "
    ::= { adGenY1731OneDmSessionTransmitEntry 11 }

adGenY1731OneDmSessionData
OBJECT-TYPE
    SYNTAX      OCTET STRING (SIZE (2))
    MAX-ACCESS  read-create
    STATUS      current
    DESCRIPTION
       "Data pattern to be used when padding is required to meet the size
        setting.  The default value is 0x00 0x00.
       "
    ::= { adGenY1731OneDmSessionTransmitEntry 12 }

--=============================================================================
--Y.1731 Local MEP ETH-1DM Receive Table
--=============================================================================
adGenY1731OneDmSessionReceiveTable
OBJECT-TYPE
    SYNTAX      SEQUENCE OF AdGenY1731OneDmSessionReceiveEntry
    MAX-ACCESS  not-accessible
    STATUS      current
    DESCRIPTION
       "The one-way frame-delay (ETH-1DM) receive table for a given local MEP.

        The local MEP's 1DM receive attributes can be edited using this table.
        These settings are common across all 1DM sessions the local MEP is
        receiving.

        As the receiver of 1DM frames, the Local MEP does not have any
        information about the 1DM transmit configuration on the far-end RMEP
        that is originating the 1DM frames and thus the receiving MEP cannot
        pair the received 1DM frames with a 1DM transmit table entry.  The
        1DM receive attributes must be configured at the Local MEP scope.
       "
    ::= { adGenY1731LocalMepOneDm 3 }

adGenY1731OneDmSessionReceiveEntry OBJECT-TYPE
    SYNTAX        AdGenY1731OneDmSessionReceiveEntry
    MAX-ACCESS    not-accessible
    STATUS        current
    DESCRIPTION
       "The one-way frame-delay (1DM) performance monitoring session receive
        attributes of a local MEP.
       "
    INDEX { adGenY1731MegLevel,
            adGenY1731MegNameFormat,
            adGenY1731MegNameLengthAndName,
            adGenY1731LocalMepIdentifier
          }
    ::= { adGenY1731OneDmSessionReceiveTable 1 }

AdGenY1731OneDmSessionReceiveEntry ::= SEQUENCE {
        adGenY1731OneDmSessionMeasurementInterval Integer32,
        adGenY1731OneDmSessionBulkDataExportFileTypes INTEGER
    }

adGenY1731OneDmSessionMeasurementInterval
OBJECT-TYPE
    SYNTAX      Integer32 (60..900)
    MAX-ACCESS  read-create
    STATUS      current
    DESCRIPTION
       "Interval in seconds over which statistics are generated for received
        one-way frame delay sessions.  The supported range is 60 - 900 seconds
        and the default value is 60.  The statistics calculated for a
        measurement interval are stored in the averaged data file.  The data
        for the current and previous intervals is available via the
        adGenY1731OneDmSessionResultTable.
       "
    ::= { adGenY1731OneDmSessionReceiveEntry 1 }

adGenY1731OneDmSessionBulkDataExportFileTypes
OBJECT-TYPE
    SYNTAX      INTEGER {
                    none(1),
                    average(2),
                    raw(3),
                    averageAndRaw(4)
                }
    MAX-ACCESS  read-create
    STATUS      current
    DESCRIPTION
       "Determines which, if any, files are generated by one-way frame delays
        calculated from received 1DM frames.

        The files are used to store one-way frame-delay statistics.
        The average setting will enable storage of statistics generated by
        each measurement interval.  The raw setting will enable storage
        for each one-way frame-delay sample.  The averageAndRaw setting
        will result in both files being generated.
       "
    ::= { adGenY1731OneDmSessionReceiveEntry 2 }

--=============================================================================
--Y.1731 Local MEP ETH-SLM Scalars
--=============================================================================

adGenY1731SlmSessionMaxNumber OBJECT-TYPE
    SYNTAX      Unsigned32
    MAX-ACCESS  read-only
    STATUS      current
    DESCRIPTION
       "A systemwide value representing the maximum number of SLM sessions
        that can be created across all local MEPs on the device.
       "
    ::= { adGenY1731SlmScalars 1 }

adGenY1731SlmSessionCurrentNumber OBJECT-TYPE
    SYNTAX      Unsigned32
    MAX-ACCESS  read-only
    STATUS      current
    DESCRIPTION
       "Current number of SLM sessions created."
    ::= { adGenY1731SlmScalars 2 }

adGenY1731SlmSessionLastCreateError OBJECT-TYPE
    SYNTAX      DisplayString
    MAX-ACCESS  read-only
    STATUS      current
    DESCRIPTION
       "The reason for the last error that occurred while attempting to create
        an SLM Session Transmit entry (adGenY1731SlmSessionTransmitEntry).
       "
    ::= { adGenY1731SlmScalars 3 }

--=============================================================================
--Y.1731 Local MEP ETH-SLM Transmit Table
--=============================================================================
adGenY1731SlmSessionTransmitTable
OBJECT-TYPE
    SYNTAX      SEQUENCE OF AdGenY1731SlmSessionTransmitEntry
    MAX-ACCESS  not-accessible
    STATUS      current
    DESCRIPTION
       "The synthetic single-ended frame-loss (SLM) session table for a given
        local MEP.  The main difference between synthetic frame-loss (ETH-SLM)
        and normal frame-loss (ETH-LMM) is that ETH-SLM only counts the
        synthetic it generates where as ETH-LMM counts all data frames.

        A local MEP's SLM sessions can be created, edited, and deleted using
        this table.  A local MEP can target a remote MEP to run single-ended
        frame-loss measurements using synthetic traffic between the two MEPs in
        the MEG.

        The target can be specified by either using a MAC address of the target
        MEP or the MEPID of the target MEP.  For the SLM session to go active,
        the local MEP must be successfully receiving CCMs from the remote MEP
        in order to specify the RMEPID as the target.
       "
    ::= { adGenY1731LocalMepSlm 2 }

adGenY1731SlmSessionTransmitEntry OBJECT-TYPE
    SYNTAX        AdGenY1731SlmSessionTransmitEntry
    MAX-ACCESS    not-accessible
    STATUS        current
    DESCRIPTION
       "A synthetic single-ended frame-loss (SLM) performance monitoring
        session of a local MEP.  A SLM PM session is unique based on target
        identifier and VLAN priority.  The target identifier is either a MAC
        address or RMEPID.  Inclusion of VLAN priority in the index allows a
        local MEP to simultaneously run several SLM PM sessions between it and
        the target at various CoS levels.
       "
    INDEX { adGenY1731MegLevel,
            adGenY1731MegNameFormat,
            adGenY1731MegNameLengthAndName,
            adGenY1731LocalMepIdentifier,
            adGenY1731SlmSessionTargetRmepIdOrMacAddress,
            adGenY1731SlmSessionTarget,
            adGenY1731SlmSessionVlanPriority
          }
      ::= { adGenY1731SlmSessionTransmitTable 1 }

AdGenY1731SlmSessionTransmitEntry ::= SEQUENCE {
      adGenY1731SlmSessionTargetRmepIdOrMacAddress   INTEGER,
      adGenY1731SlmSessionTarget                     OCTET STRING,
      adGenY1731SlmSessionVlanPriority               Integer32,
      adGenY1731SlmSessionTargetRemoteMepIdentifier  Integer32,
      adGenY1731SlmSessionTargetMacAddress           MacAddress,
      adGenY1731SlmSessionRowStatus                  RowStatus,
      adGenY1731SlmSessionAdminState                 TruthValue,
      adGenY1731SlmSessionStatus                     INTEGER,
      adGenY1731SlmSessionStatusString               DisplayString,
      adGenY1731SlmSessionInterframeDelay            Integer32,
      adGenY1731SlmSessionMeasurementInterval        Integer32,
      adGenY1731SlmSessionSize                       Integer32,
      adGenY1731SlmSessionData                       OCTET STRING,
      adGenY1731SlmSessionBulkDataExportFileTypes    INTEGER
    }

adGenY1731SlmSessionTargetRmepIdOrMacAddress
OBJECT-TYPE
    SYNTAX      INTEGER {
                    rmepId(1),
                    macAddress(2)
                }
    MAX-ACCESS  not-accessible
    STATUS      current
    DESCRIPTION
       "Indicates whether the target specified is a MEPID or a unicast MAC
        Address.  If the target specified is a MEPID the local MEP will not be
        able to initiate the SLM session until a CCM has been received from the
        RMEP
       "
    ::= { adGenY1731SlmSessionTransmitEntry 1 }

adGenY1731SlmSessionTarget
OBJECT-TYPE
    SYNTAX      OCTET STRING (SIZE (1..6))
    MAX-ACCESS  not-accessible
    STATUS      current
    DESCRIPTION
       "Octet string defining the target for the SLM session.
        If adGenY1731SlmSessionTargetRmepIdOrMacAddress indicates the target is
        a MEPID then the octet string should represent a MEPID between the
        range 1-8191.  Otherwise, it should be the target's unicast MAC address
       "
    ::= { adGenY1731SlmSessionTransmitEntry 2 }

adGenY1731SlmSessionVlanPriority
OBJECT-TYPE
    SYNTAX      Integer32 (0..7)
    MAX-ACCESS  not-accessible
    STATUS      current
    DESCRIPTION
       "VLAN Priority that will be used in all SLM frames sent by this
        SLM transmit session.
       "
    ::= { adGenY1731SlmSessionTransmitEntry 3 }

adGenY1731SlmSessionTargetRemoteMepIdentifier
OBJECT-TYPE
    SYNTAX       Integer32 (1..8191)
    MAX-ACCESS   read-only
    STATUS       current
    DESCRIPTION
       "Target MEPID for this SLM session"
    ::= { adGenY1731SlmSessionTransmitEntry 4 }

adGenY1731SlmSessionTargetMacAddress
OBJECT-TYPE
    SYNTAX      MacAddress
    MAX-ACCESS  read-only
    STATUS      current
    DESCRIPTION
       "Target MAC address for this SLM session"
    ::= { adGenY1731SlmSessionTransmitEntry 5 }

adGenY1731SlmSessionRowStatus
OBJECT-TYPE
    SYNTAX      RowStatus
    MAX-ACCESS  read-create
    STATUS      current
    DESCRIPTION
       "This OID is used to create/delete a transmit SLM session of a Local
        MEP.  The only supported settings are createAndGo, createAndWait, and
        destroy.
       "
    ::= { adGenY1731SlmSessionTransmitEntry 6 }

adGenY1731SlmSessionAdminState
OBJECT-TYPE
    SYNTAX      TruthValue
    MAX-ACCESS  read-create
    STATUS      current
    DESCRIPTION
       "The administrative state of the SLM transmit session.

        True indicates that the SLM session is to function normally and
        actively transmit SLMs towards the specified target, and false that
        it is to cease functioning.
       "
    ::= { adGenY1731SlmSessionTransmitEntry 7 }

adGenY1731SlmSessionStatus
OBJECT-TYPE
    SYNTAX      INTEGER {
                    running(1),
                    notRunning(2)
                }
    MAX-ACCESS  read-only
    STATUS      current
    DESCRIPTION
       "Operational status of the SLM transmit session.  The minimum
        attributes that need to be set before a MEP can transmit SLMs towards
        the target are: Target MEPID or MAC Address and admin state.  If a
        MEPID is used to specify the target then the local MEP must have
        received a CCM from the remote MEP in-order to learn its MAC address.
       "
    ::= { adGenY1731SlmSessionTransmitEntry 8 }

adGenY1731SlmSessionStatusString
OBJECT-TYPE
    SYNTAX      DisplayString
    MAX-ACCESS  read-only
    STATUS      current
    DESCRIPTION
       "Operational status string of the SLM transmit session.  If the session
        is expected to be active but is not able to be due to a provisioning
        issue or conflict, this string will explain the reason.
       "
    ::= { adGenY1731SlmSessionTransmitEntry 9 }

adGenY1731SlmSessionInterframeDelay
OBJECT-TYPE
    SYNTAX      Integer32 (100..10000)
    MAX-ACCESS  read-create
    STATUS      current
    DESCRIPTION
       "Amount of time in milliseconds between SLM transmissions.  The
        supported range is 100 - 10,000 ms and the default value is 1000 ms.
       "
    ::= { adGenY1731SlmSessionTransmitEntry 10 }

adGenY1731SlmSessionMeasurementInterval
OBJECT-TYPE
    SYNTAX      Integer32 (60..900)
    MAX-ACCESS  read-create
    STATUS      current
    DESCRIPTION
       "Interval in seconds over which statistics are generated.  The supported
        range is 60 - 900 seconds and the default value is 60.  The statistics
        calculated for a measurement interval are stored in the averaged data
        file.  The data for the current and previous intervals is available via
        the adGenY1731SlmSessionResultTable.
       "
    ::= { adGenY1731SlmSessionTransmitEntry 11 }

adGenY1731SlmSessionSize
OBJECT-TYPE
    SYNTAX      Integer32
    MAX-ACCESS  read-create
    STATUS      current
    DESCRIPTION
       "Size of the SLM in bytes.  The size encompasses the entire Ethernet
        frame from the header through the FCS.

        The supported values are:
        0 to indicate Data TLV should not be included in SLM sent.
        64 to 2000 bytes to indicate the DataTLV should be included to increase
        the frame length to the specified size.

        If the Data TLV is not included, the SLM will be sent with the minimum
        Ethernet frame size of 64-bytes but it will not contain the DataTLV.  A
        zero-pad will be used to fulfill  the minimum length requirement.

        The default value is 0.
       "
    ::= { adGenY1731SlmSessionTransmitEntry 12 }

adGenY1731SlmSessionData
OBJECT-TYPE
    SYNTAX      OCTET STRING (SIZE (2))
    MAX-ACCESS  read-create
    STATUS      current
    DESCRIPTION
       "Data pattern to be used when padding is required to meet the size
        setting.  The default value is 0x00 0x00.
       "
    ::= { adGenY1731SlmSessionTransmitEntry 13 }

adGenY1731SlmSessionBulkDataExportFileTypes
OBJECT-TYPE
    SYNTAX      INTEGER {
                    none(1),
                    average(2),
                    raw(3),
                    averageAndRaw(4)
                }
    MAX-ACCESS  read-create
    STATUS      current
    DESCRIPTION
       "Determines which, if any, files are generated by this SLM transmit
        session.  The files are used to store synthetic single-ended frame-loss
        statistics.  The average setting will enable storage of statistics
        generated by each measurement interval.  The raw setting will enable
        storage for each synthetic single-ended frame-loss sample.  The
        averageAndRaw setting will result in both files being generated.
       "
    ::= { adGenY1731SlmSessionTransmitEntry 14 }

--=============================================================================
--Y.1731 Local MEP ETH-CLM Receiver Properties Table
--=============================================================================
adGenY1731ClmReceiverTable
OBJECT-TYPE
    SYNTAX      SEQUENCE OF AdGenY1731ClmReceiverEntry
    MAX-ACCESS  not-accessible
    STATUS      current
    DESCRIPTION
       "A local MEP can be provisioned to calculate near-end frame-loss between
        it and a known RMEP by monitoring sequence numbers in received CCMs.
        This method is referred to as CLM and if the local MEP is enabled for
        CLM it will perform the calculation for each RMEP in its MEP-database.
       "
    ::= { adGenY1731LocalMepClm 1 }

adGenY1731ClmReceiverEntry OBJECT-TYPE
    SYNTAX        AdGenY1731ClmReceiverEntry
    MAX-ACCESS    not-accessible
    STATUS        current
    DESCRIPTION
       "The receive properties for a local MEP's CLM function.  The properties
        are unique to a local MEP.
       "
    INDEX { adGenY1731MegLevel,
            adGenY1731MegNameFormat,
            adGenY1731MegNameLengthAndName,
            adGenY1731LocalMepIdentifier
          }
      ::= { adGenY1731ClmReceiverTable 1 }

AdGenY1731ClmReceiverEntry ::= SEQUENCE {
      adGenY1731ClmReceiverEnabled                  TruthValue,
      adGenY1731ClmReceiverMeasurementInterval      Integer32,
      adGenY1731ClmReceiverBulkDataExportFileTypes  INTEGER
    }

adGenY1731ClmReceiverEnabled
OBJECT-TYPE
    SYNTAX      TruthValue
    MAX-ACCESS  read-write
    STATUS      current
    DESCRIPTION
       "Configures the administrative state of the local MEP's ETH-CLM
        function.  If the ETH-CLM function is enabled, the MEP will monitor the
        sequence-numbers in CCMs received from known RMEPs for frame-loss.
       "
    ::= { adGenY1731ClmReceiverEntry 1 }

adGenY1731ClmReceiverMeasurementInterval
OBJECT-TYPE
    SYNTAX      Integer32 (60..900)
    MAX-ACCESS  read-write
    STATUS      current
    DESCRIPTION
       "Interval in seconds over which statistics are generated.  The supported
        range is 60 - 900 seconds and the default value is 60.  The statistics
        calculated for a measurement interval are stored in the averaged data
        file.
       "
    ::= { adGenY1731ClmReceiverEntry 2 }

adGenY1731ClmReceiverBulkDataExportFileTypes
OBJECT-TYPE
    SYNTAX      INTEGER {
                    none(1),
                    average(2)
                }
    MAX-ACCESS  read-write
    STATUS      current
    DESCRIPTION
       "Determines which, if any, files are generated by this local MEP's CLM
        function.  The files are used to store near-end frame-loss statistics
        calculated by the local MEP's CLM function.  The average setting will
        enable storage of statistics generated by each measurement interval.
       "
    ::= { adGenY1731ClmReceiverEntry 3 }


--==============================================================================
--==============================================================================
--==============================================================================



   adGenY1731PMFlashFilesClear NOTIFICATION-TYPE
      OBJECTS  {
         adTrapInformSeqNum,
         sysName,
	 adGenSlotInfoIndex
      }
      STATUS  current
      DESCRIPTION
         "This trap indicates all current and stored bulk PM files have been
          successfully exported to the server."

         --#TYPE         "Status - Alarm"
         --#SUMMARY      "Y1731 1: Y1731 PM Flash File Clear"
         --#SEVERITY     MINOR
         --#GENERIC      6
         --#CATEGORY     "Error Events"
         --#SOURCE_ID    "A"
         --#TIMEINDEX    0
      ::= { adGenY1731Traps 1 }

   adGenY1731PMFlashFilesSet NOTIFICATION-TYPE
      OBJECTS  {
         adTrapInformSeqNum,
         sysName,
	 adGenSlotInfoIndex
      }
      STATUS  current
      DESCRIPTION
         "This trap indicates that the Y1731 PM File transferred to flash
          because bulk data export transfer failed."
         --#TYPE         "Status - Alarm"
         --#SUMMARY      "Y1731 2: Y1731 PM Flash File Set"
         --#SEVERITY     MINOR
         --#GENERIC      6
         --#CATEGORY     "Error Events"
         --#SOURCE_ID    "A"
         --#TIMEINDEX    0
      ::= { adGenY1731Traps 2 }

END
