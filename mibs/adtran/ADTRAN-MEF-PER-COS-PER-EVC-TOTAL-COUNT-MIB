ADTRAN-MEF-PER-COS-PER-EVC-TOTAL-COUNT-MIB DEFINITIONS ::= BEGIN

IMPORTS
   MODULE-IDENTITY,
   OBJECT-TYPE,
   Integer32, Unsigned32
      FROM SNMPv2-SMI
   DisplayString
       FROM SNMPv2-TC
   HCPerfTimeElapsed,
   HCPerfValidIntervals,
   HCPerfInvalidIntervals,
   HCPerfCurrentCount,
   HCPerfIntervalCount,
   HCPerfTotalCount
      FROM HC-PerfHist-TC-MIB
   MODULE-COMPLIANCE,
   OBJECT-GROUP
      FROM SNMPv2-CONF
   adIdentity
      FROM ADTRAN-MIB
   adGenAOSMef,
   adGenAOSConformance
      FROM ADTRAN-AOS;

adGenAosMefPerCosPerEvcTotalCountMib MODULE-IDENTITY
   LAST-UPDATED "201710140000Z" -- October 14, 2017
   ORGANIZATION "ADTRAN Inc."
   CONTACT-INFO
     "Info:   www.adtran.com
      Postal: ADTRAN, Inc.
              901 Explorer Blvd.
              Huntsville, AL 35806
      Tel:    +1 888 423-8726
      E-mail: support@adtran.com"

   DESCRIPTION
     "This MIB module defines high capacity performance statistics
      per COS per EVC within an AOS product.

      Copyright (C) ADTRAN, Inc. (2017)."

   REVISION    "201710140000Z" -- October 14, 2017
   DESCRIPTION
     "Initial version"
    ::= { adIdentity 10000 53 9 8 }

adGenAosMefPerCosPerEvcTotalCount OBJECT IDENTIFIER ::= { adGenAOSMef 8 }

------------------------------------------------------------
-- Current Table for Total count of Green, yellow and red counters for Per Cos Per Evc.
--
adMefPerCosPerEvcTcTable OBJECT-TYPE
   SYNTAX      SEQUENCE OF AdMefPerCosPerEvcTcEntry
   MAX-ACCESS  not-accessible
   STATUS      current
   DESCRIPTION
     "This table contains totla number of count for green, yeloow and red
      counters with Per Cos Per Evc. This table is indexed by
      adMefPerCosPerEvcTcEvcNameFixedLen and the queue number."
   ::= { adGenAosMefPerCosPerEvcTotalCount 1 }

adMefPerCosPerEvcTcEntry OBJECT-TYPE
   SYNTAX      AdMefPerCosPerEvcTcEntry
   MAX-ACCESS  not-accessible
   STATUS      current
   DESCRIPTION
     "This specifies the information contained in one entry of the
      adMefPerCosPerEvcTcTable.  It is indexed by an EVC's
      adMefPerCosPerEvcTcEvcNameFixedLen and the queue number."
   INDEX { adMefPerCosPerEvcTcEvcNameFixedLen, adMefPerCosPerEvcTcQueueNumber }
   ::= { adMefPerCosPerEvcTcTable 1 }

AdMefPerCosPerEvcTcEntry ::=
   SEQUENCE
   {
      adMefPerCosPerEvcTcEvcNameFixedLen                     OCTET STRING,
      adMefPerCosPerEvcTcQueueNumber                         Unsigned32,
      adMefPerCosPerEvcTotalIngressGreenOctets               HCPerfCurrentCount,
      adMefPerCosPerEvcTotalIngressGreenFrames               HCPerfCurrentCount,
      adMefPerCosPerEvcTotalIngressYellowOctets              HCPerfCurrentCount,
      adMefPerCosPerEvcTotalIngressYellowFrames              HCPerfCurrentCount,
      adMefPerCosPerEvcTotalIngressRedFrames                 HCPerfCurrentCount
   }

adMefPerCosPerEvcTcEvcNameFixedLen OBJECT-TYPE
   SYNTAX      OCTET STRING (SIZE (50))
   MAX-ACCESS  not-accessible
   STATUS      current
   DESCRIPTION
     "The name of the EVC.  This string is padded at the end with 0x00 so that
      this table index has a fixed length of characters of the specified SIZE."
   ::= { adMefPerCosPerEvcTcEntry 1}

adMefPerCosPerEvcTcQueueNumber OBJECT-TYPE
   SYNTAX      Unsigned32 (0..7)
   MAX-ACCESS  not-accessible
   STATUS      current
   DESCRIPTION
     "NNI queue number."
   ::= { adMefPerCosPerEvcTcEntry 2 }


adMefPerCosPerEvcTotalIngressGreenOctets OBJECT-TYPE
   SYNTAX      HCPerfCurrentCount
   MAX-ACCESS  read-only
   STATUS      current
   DESCRIPTION
     "Total number of Green Octets"
   ::= { adMefPerCosPerEvcTcEntry 3 }

adMefPerCosPerEvcTotalIngressGreenFrames OBJECT-TYPE
   SYNTAX      HCPerfCurrentCount
   MAX-ACCESS  read-only
   STATUS      current
   DESCRIPTION
     "Total number of Green frames."
   ::= { adMefPerCosPerEvcTcEntry 4 }

adMefPerCosPerEvcTotalIngressYellowOctets OBJECT-TYPE
   SYNTAX      HCPerfCurrentCount
   MAX-ACCESS  read-only
   STATUS      current
   DESCRIPTION
     "Total number of yellow octets."
   ::= { adMefPerCosPerEvcTcEntry 5 }

adMefPerCosPerEvcTotalIngressYellowFrames OBJECT-TYPE
   SYNTAX      HCPerfCurrentCount
   MAX-ACCESS  read-only
   STATUS      current
   DESCRIPTION
     "The total number of yellow frames."
   ::= { adMefPerCosPerEvcTcEntry 6 }

adMefPerCosPerEvcTotalIngressRedFrames OBJECT-TYPE
   SYNTAX      HCPerfCurrentCount
   MAX-ACCESS  read-only
   STATUS      current
   DESCRIPTION
     "Total number of red frames."
   ::= { adMefPerCosPerEvcTcEntry 7 }

------------------------------------------------------------
-- Conformance information
--
adGenAosMefPerCosPerEvcTotalCountConformance OBJECT IDENTIFIER
   ::= { adGenAOSConformance 30 }

adMefPerCosPerEvcTotalCountGroups OBJECT IDENTIFIER
   ::= { adGenAosMefPerCosPerEvcTotalCountConformance 1 }

adGenAosMefPerCosPerEvcTotalCountCompliances OBJECT IDENTIFIER
   ::= { adGenAosMefPerCosPerEvcTotalCountConformance 2 }

-- Compliance statements
--

adGenAosMefPerUniTotalCountCompliance MODULE-COMPLIANCE
   STATUS  current
   DESCRIPTION
     "The compliance statement for SNMPv2 entities which
      implement UNI interface for total number of count."
   MODULE
   MANDATORY-GROUPS {
      adMefPerCosPerEvcTotalCountGroup
   }
   ::= { adGenAosMefPerCosPerEvcTotalCountCompliances 1 }

-- Units of conformance
--
adMefPerCosPerEvcTotalCountGroup OBJECT-GROUP
   OBJECTS
   {
      adMefPerCosPerEvcTotalIngressGreenOctets,
      adMefPerCosPerEvcTotalIngressGreenFrames,
      adMefPerCosPerEvcTotalIngressYellowOctets,
      adMefPerCosPerEvcTotalIngressYellowFrames,
      adMefPerCosPerEvcTotalIngressRedFrames
   }
   STATUS  current
   DESCRIPTION
     "The 1 day interval group."
   ::= { adMefPerCosPerEvcTotalCountGroups 1 }

END
