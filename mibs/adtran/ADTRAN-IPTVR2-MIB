ADTRAN-IPTVR2-MIB

-- TITLE:     The ADTRAN IPTV Rev2 MIB
-- PRODUCT:   ADTRAN Ethernet Dslam Products
-- VERSION:   0.1
-- DATE:      2010/05/20
-- AUTHOR:    Ron Zuckerman
-- STATUS:    PRELIMINARY

-- This MIB defines the object identifier (OID) for the
-- ADTRAN IPTV Rev2 MIB objects

-- HISTORY:
-- 2010/05/20 rmz STATUS: PRELIMINARY.
--                Initial version
-- 2010/06/07 rmz STATUS: PRELIMINARY.
--                Added adGenIPTVR2Scalars, adGenIPTVR2ChannelLineupLastCreateError,
--                and adGenIPTVR2MulticastACLLastCreateError
-- ******************************************************************************************

DEFINITIONS ::= BEGIN

    IMPORTS
         OBJECT-TYPE,
         MODULE-IDENTITY,
         NOTIFICATION-TYPE,
         IpAddress,
         Integer32
            FROM SNMPv2-SMI
         NOTIFICATION-GROUP
            FROM SNMPv2-CONF
         adGenIPTVR2,
         adGenIPTVR2ID
            FROM ADTRAN-SHARED-CND-SYSTEM-MIB
         DisplayString,
         RowStatus
         	FROM SNMPv2-TC
        ;

adGenIPTVR2MIB MODULE-IDENTITY
   LAST-UPDATED "201006070000Z"
   ORGANIZATION "Adtran, Inc."
   CONTACT-INFO "http://www.adtran.com"
   DESCRIPTION
      "This MIB defines the objects for the IPTV MIB."
   REVISION "201006070000Z"
   DESCRIPTION "Created"
::= { adGenIPTVR2ID 26 }

-- ******************************************************************************************
-- Index
-- ******************************************************************************************

-- ******************************************************************************************
-- Configuration
-- ******************************************************************************************


-- ******************************************************************************************
-- Provisioning
-- ******************************************************************************************

-- *************************
-- IPTV Channel Lineup Table
-- *************************
adGenIPTVR2ChannelLineupTable OBJECT-TYPE
   SYNTAX      SEQUENCE OF AdGenIPTVR2ChannelLineupEntry
   MAX-ACCESS  not-accessible
   STATUS      current
   DESCRIPTION
     "Each row in this table specifies a range of multicast Video IP Addresses,
     the BW of a video stream in the range, and whether or not
     the range is guaranteed or not guaranteed BW on a subscriber port."
   ::= { adGenIPTVR2 1  }

adGenIPTVR2ChannelLineupEntry OBJECT-TYPE
   SYNTAX      AdGenIPTVR2ChannelLineupEntry
   MAX-ACCESS  not-accessible
   STATUS      current
   DESCRIPTION
     "An entry in the adGenIPTVR2ChannelLineupTable."
   INDEX { adGenIPTVR2ChannelLineupIndex }
   ::= { adGenIPTVR2ChannelLineupTable 1 }


AdGenIPTVR2ChannelLineupEntry ::=
  SEQUENCE
  {
      adGenIPTVR2ChannelLineupIndex						INTEGER,
      adGenIPTVR2ChannelLineupDescription	  			DisplayString,
      adGenIPTVR2ChannelLineupStartMulticastIP          IpAddress,
      adGenIPTVR2ChannelLineupStopMulticastIP           IpAddress,
      adGenIPTVR2ChannelLineupBandwidth            		Integer32,
      adGenIPTVR2ChannelLineupGuaranteed            	INTEGER,
      adGenIPTVR2ChannelLineupLastErrorString           DisplayString,
      adGenIPTVR2ChannelLineupLayer3MTU					INTEGER,
      adGenIPTVR2ChannelLineupRowStatus            		RowStatus
  }

  adGenIPTVR2ChannelLineupIndex OBJECT-TYPE
     SYNTAX  		INTEGER(1..256)
     MAX-ACCESS  	not-accessible
     STATUS  		current
     DESCRIPTION
       "Contains the unique index number of this channel range."
     ::= { adGenIPTVR2ChannelLineupEntry 1 }

  adGenIPTVR2ChannelLineupDescription OBJECT-TYPE
     SYNTAX          DisplayString (SIZE (1..32))
     MAX-ACCESS      read-create
     STATUS          current
     DESCRIPTION
       "Contains a description of this channel range."
     ::= { adGenIPTVR2ChannelLineupEntry 2 }

  adGenIPTVR2ChannelLineupStartMulticastIP OBJECT-TYPE
     SYNTAX  		IpAddress
     MAX-ACCESS  	read-create
     STATUS  		current
     DESCRIPTION
       "Indicate the starting IP Address to be included in the range of
        this channel range."
     ::= { adGenIPTVR2ChannelLineupEntry 3 }

  adGenIPTVR2ChannelLineupStopMulticastIP OBJECT-TYPE
     SYNTAX  		IpAddress
     MAX-ACCESS  	read-create
     STATUS  		current
     DESCRIPTION
       "Indicate the last IP Address to be included in the range of
      	this channel range."
     ::= { adGenIPTVR2ChannelLineupEntry 4 }

  adGenIPTVR2ChannelLineupBandwidth OBJECT-TYPE
     SYNTAX  		Integer32
     MAX-ACCESS  	read-create
     STATUS  		current
     DESCRIPTION
       "Specify the bandwidth (kbps) of a channel in this channel range.
        The bandwidth is the encoded rate plus Layer 3 overhead. Every channel
        in this range will have this bandwidth."
     ::= { adGenIPTVR2ChannelLineupEntry 5 }

  adGenIPTVR2ChannelLineupGuaranteed OBJECT-TYPE
     SYNTAX  		INTEGER{
						 	guaranteed (1),
			       	 		nonguaranteed (2)
		               	   }
     MAX-ACCESS  	read-create
     STATUS  		current
     DESCRIPTION
       "Each row in this table specifies a range of multicast Video IP Addresses,
        whether or not the range is guaranteed or not guaranteed, and a
        bandwidth value (BW).  If guaranteed, the BW value represents the
        bandwidth allocation for the entire range of multicast IP addresses.
        If not guaranteed, the BW value represents the bandwidth of an individual
        multicast address within that range."
     ::= { adGenIPTVR2ChannelLineupEntry 6 }

  adGenIPTVR2ChannelLineupLastErrorString OBJECT-TYPE
     SYNTAX  		DisplayString
     MAX-ACCESS  	read-create
     STATUS  		current
     DESCRIPTION
       "Indicates the last provisioning error for this channel range."
     ::= { adGenIPTVR2ChannelLineupEntry 7 }

  adGenIPTVR2ChannelLineupLayer3MTU OBJECT-TYPE
     SYNTAX  		INTEGER(0..65536)
     MAX-ACCESS  	read-create
     STATUS  		current
     DESCRIPTION
       "Specify the maximum Layer 3 packet size in bytes. Use 65536 to set the default
        value (1344)."
     ::= { adGenIPTVR2ChannelLineupEntry 8 }

  adGenIPTVR2ChannelLineupRowStatus OBJECT-TYPE
      SYNTAX  		RowStatus
      MAX-ACCESS  	read-create
      STATUS  		current
      DESCRIPTION
        "This object is used to create a new row or modify or delete an
         existing channel range in this table."
      ::= { adGenIPTVR2ChannelLineupEntry 9 }

-- ******************************************************************************************
-- IPTV Multicast Access Control List
-- ******************************************************************************************

adGenIPTVR2MulticastACLTable OBJECT-TYPE
   SYNTAX      SEQUENCE OF AdGenIPTVR2MulticastACLEntry
   MAX-ACCESS  not-accessible
   STATUS      current
   DESCRIPTION
     "Each row in this table specifies a set of channel range indices that make up
      the multicast access control list (ACL)."
   ::= { adGenIPTVR2 2  }

adGenIPTVR2MulticastACLEntry OBJECT-TYPE
   SYNTAX      AdGenIPTVR2MulticastACLEntry
   MAX-ACCESS  not-accessible
   STATUS      current
   DESCRIPTION
     "An entry in the adGenIPTVR2MulticastACLTable."
   INDEX { IMPLIED adGenIPTVR2MulticastACLName }
   ::= { adGenIPTVR2MulticastACLTable 1 }


AdGenIPTVR2MulticastACLEntry ::=
  SEQUENCE
  {
      adGenIPTVR2MulticastACLName						DisplayString,
      adGenIPTVR2MulticastACLLastErrorString            DisplayString,
      adGenIPTVR2MulticastACLList						OCTET STRING,
      adGenIPTVR2MulticastACLRowStatus           		RowStatus
   }

  adGenIPTVR2MulticastACLName OBJECT-TYPE
     SYNTAX  		DisplayString (SIZE(1..32))
     MAX-ACCESS  	not-accessible
     STATUS  		current
     DESCRIPTION
       "Contains the unique name of this multicast ACL."
     ::= { adGenIPTVR2MulticastACLEntry 1 }

  adGenIPTVR2MulticastACLLastErrorString OBJECT-TYPE
     SYNTAX  		DisplayString
     MAX-ACCESS  	read-create
     STATUS  		current
     DESCRIPTION
       "Indicates the last provisioning error for this multicast ACL."
     ::= { adGenIPTVR2MulticastACLEntry 2 }

  adGenIPTVR2MulticastACLList OBJECT-TYPE
     SYNTAX  		OCTET STRING (SIZE(0..32))
     MAX-ACCESS  	read-create
     STATUS  		current
     DESCRIPTION
       "This object contains a bitmap that indicates which channel range index values
        are in the multicast ACL. If the bit is 1, it means that the channel range
        index is in the multicast ACL; otherwise, is it not. The 1st byte specifies
        channel range indices from 1 through 8 (where bit 0 [index 1] is the LSB),
        the 2nd byte specifies channel range indices from 9 through 16, etc. For
        example:

            0x01 0x02 0xFF 0xFE 0x00 ... 0x00

        means channel range indices 1, 10, 17 through 24, and 26 through 32 are in
        the multicast ACL."
      ::= { adGenIPTVR2MulticastACLEntry 3 }

  adGenIPTVR2MulticastACLRowStatus OBJECT-TYPE
     SYNTAX  		RowStatus
     MAX-ACCESS  	read-create
     STATUS  		current
     DESCRIPTION
       "This object is used to create a new row or modify or delete an
        existing multicast ACL in this table."
     ::= { adGenIPTVR2MulticastACLEntry 4 }

-- ******************************************************************************************
-- IPTV Scalars
-- ******************************************************************************************
adGenIPTVR2Scalars  OBJECT IDENTIFIER ::= {adGenIPTVR2 3}

  adGenIPTVR2ChannelLineupLastCreateError OBJECT-TYPE
     SYNTAX  		DisplayString
     MAX-ACCESS  	read-only
     STATUS  		current
     DESCRIPTION
       "Indicates the last error when creating a channel range."
     ::= { adGenIPTVR2Scalars 1 }

  adGenIPTVR2MulticastACLLastCreateError OBJECT-TYPE
     SYNTAX  		DisplayString
     MAX-ACCESS  	read-only
     STATUS  		current
     DESCRIPTION
       "Indicates the last error when creating a multicast ACL."
     ::= { adGenIPTVR2Scalars 2 }

-- ******************************************************************************************
-- PM History (TBD)
-- ******************************************************************************************

END
