ADTRAN-GENMUXPONDERQOS-MIB

-- TITLE:     The ADTRAN Muxponder QoS MIB
-- PRODUCT:   Metro Ethernet Products
-- VERSION:   1.0
-- DATE:      09/16/10
-- AUTHOR:    Bhushan Parikh
-- STATUS:    PRELIMINARY

-- This MIB defines the object identifiers (OIDs) for the
-- ADTRAN MUXPONDER QOS MIB objects

-- HISTORY:
-- 2010/09/16 bcp   STATUS: PRELIMINARY.
-- ******************************************************************************************
DEFINITIONS ::= BEGIN

IMPORTS

   adGenMuxponderQoS,
   adGenMuxponderQoSID           FROM ADTRAN-SHARED-CND-SYSTEM-MIB

   OBJECT-TYPE,
   MODULE-IDENTITY,
   Integer32                    FROM SNMPv2-SMI

   adGenSlotInfoIndex           FROM ADTRAN-GENSLOT-MIB

   ;

adGenMuxponderQoSMIB MODULE-IDENTITY
   LAST-UPDATED "201009160000Z"
   ORGANIZATION "Adtran, Inc."
   CONTACT-INFO
     "CND Tech Support
         Postal: ADTRAN, Inc.
                 901 Explorer Blvd.
                 Huntsville, AL  35806
                 Tel: +1 800 726-8663
                 Fax: +1 256 963 6217
                 E-mail: support@adtran.com"
   DESCRIPTION
      "This MIB defines the objects for the Muxponder QoS MIB."
   REVISION "201009160000Z"
   DESCRIPTION "Created"
::= { adGenMuxponderQoSID 1 }

adGenMuxponderQoSEvents                      OBJECT IDENTIFIER ::= {adGenMuxponderQoS 0}
adGenMuxponderQoSProvisioning                OBJECT IDENTIFIER ::= {adGenMuxponderQoS 1}

--==================================================================================================================

   adGenMuxponderQueueCoSMapTable OBJECT-TYPE
      SYNTAX  SEQUENCE OF AdGenMuxponderQueueCoSMapEntry
      MAX-ACCESS  not-accessible
      STATUS  current
      DESCRIPTION
         "The queue class of service map provisioning table."
      ::= { adGenMuxponderQoSProvisioning 1 }

   adGenMuxponderQueueCoSMapEntry OBJECT-TYPE
      SYNTAX  AdGenMuxponderQueueCoSMapEntry
      MAX-ACCESS  not-accessible
      STATUS  current
      DESCRIPTION
         "An entry in the queue class of service provisioning table.
          Each entry in the table is uniquely identified by Slot."
      INDEX  { adGenSlotInfoIndex }
      ::= { adGenMuxponderQueueCoSMapTable 1 }

   AdGenMuxponderQueueCoSMapEntry ::=
      SEQUENCE {
         adGenMuxponderQueueCoSMapForPri0    Integer32,
         adGenMuxponderQueueCoSMapForPri1    Integer32,
         adGenMuxponderQueueCoSMapForPri2    Integer32,
         adGenMuxponderQueueCoSMapForPri3    Integer32,
         adGenMuxponderQueueCoSMapForPri4    Integer32,
         adGenMuxponderQueueCoSMapForPri5    Integer32,
         adGenMuxponderQueueCoSMapForPri6    Integer32,
         adGenMuxponderQueueCoSMapForPri7    Integer32,
         adGenMuxponderQueueCoSMapUntagged   Integer32
      }

      adGenMuxponderQueueCoSMapForPri0 OBJECT-TYPE
         SYNTAX  Integer32
         MAX-ACCESS  read-write
         STATUS  current
         DESCRIPTION
            "This variable is used to provision the CoS queue that all
             traffic with a p-bit value of 0 gets mapped into.
             The valid range is 0 - 7 where 7 gets treated with the
             highest priority.  The default value is 1 per IEEE 802.1Q-2005"
         ::= { adGenMuxponderQueueCoSMapEntry 1 }

      adGenMuxponderQueueCoSMapForPri1 OBJECT-TYPE
         SYNTAX  Integer32
         MAX-ACCESS  read-write
         STATUS  current
         DESCRIPTION
            "This variable is used to provision the CoS queue that all
             traffic with a p-bit value of 1 gets mapped into.
             The valid range is 0 - 7 where 7 gets treated with the
             highest priority.  The default value is 0 per IEEE 802.1Q-2005"
         ::= { adGenMuxponderQueueCoSMapEntry 2 }

      adGenMuxponderQueueCoSMapForPri2 OBJECT-TYPE
         SYNTAX  Integer32
         MAX-ACCESS  read-write
         STATUS  current
         DESCRIPTION
            "This variable is used to provision the CoS queue that all
             traffic with a p-bit value of 2 gets mapped into.
             The valid range is 0 - 7 where 7 gets treated with the
             highest priority.  The default value is 2 per IEEE 802.1Q-2005"
         ::= { adGenMuxponderQueueCoSMapEntry 3 }

      adGenMuxponderQueueCoSMapForPri3 OBJECT-TYPE
         SYNTAX  Integer32
         MAX-ACCESS  read-write
         STATUS  current
         DESCRIPTION
            "This variable is used to provision the CoS queue that all
             traffic with a p-bit value of 3 gets mapped into.
             The valid range is 0 - 7 where 7 gets treated with the
             highest priority.  The default value is 3 per IEEE 802.1Q-2005"
         ::= { adGenMuxponderQueueCoSMapEntry 4 }

      adGenMuxponderQueueCoSMapForPri4 OBJECT-TYPE
         SYNTAX  Integer32
         MAX-ACCESS  read-write
         STATUS  current
         DESCRIPTION
            "This variable is used to provision the CoS queue that all
             traffic with a p-bit value of 4 gets mapped into.
             The valid range is 0 - 7 where 7 gets treated with the
             highest priority.  The default value is 4 per IEEE 802.1Q-2005"
         ::= { adGenMuxponderQueueCoSMapEntry 5 }

      adGenMuxponderQueueCoSMapForPri5 OBJECT-TYPE
         SYNTAX  Integer32
         MAX-ACCESS  read-write
         STATUS  current
         DESCRIPTION
            "This variable is used to provision the CoS queue that all
             traffic with a p-bit value of 5 gets mapped into.
             The valid range is 0 - 7 where 7 gets treated with the
             highest priority.  The default value is 5 per IEEE 802.1Q-2005"
         ::= { adGenMuxponderQueueCoSMapEntry 6 }

      adGenMuxponderQueueCoSMapForPri6 OBJECT-TYPE
         SYNTAX  Integer32
         MAX-ACCESS  read-write
         STATUS  current
         DESCRIPTION
            "This variable is used to provision the CoS queue that all
             traffic with a p-bit value of 6 gets mapped into.
             The valid range is 0 - 7 where 7 gets treated with the
             highest priority.  The default value is 6 per IEEE 802.1Q-2005"
         ::= { adGenMuxponderQueueCoSMapEntry 7 }

      adGenMuxponderQueueCoSMapForPri7 OBJECT-TYPE
         SYNTAX  Integer32
         MAX-ACCESS  read-write
         STATUS  current
         DESCRIPTION
            "This variable is used to provision the CoS queue that all
             traffic with a p-bit value of 7 gets mapped into.
             The valid range is 0 - 7 where 7 gets treated with the
             highest priority.  The default value is 7 per IEEE 802.1Q-2005"
         ::= { adGenMuxponderQueueCoSMapEntry 8 }

      adGenMuxponderQueueCoSMapUntagged OBJECT-TYPE
         SYNTAX  Integer32
         MAX-ACCESS  read-write
         STATUS  current
         DESCRIPTION
            "This variable is used to provision the Class of Service (CoS) value for
            untagged traffic. The valid range is 0 - 7 where 7 gets treated with the
            highest priority.  The default value is 0 per IEEE 802.1Q-2005"
         ::= { adGenMuxponderQueueCoSMapEntry 9 }

END
