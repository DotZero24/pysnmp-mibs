ADTRAN-EFM-NTU-MIB

-- TITLE:     The ADTRAN EFM NTU MIB
-- PRODUCT:   ADTRAN EFM NTU
-- VERSION:   1.0
-- DATE:      2/22/06
-- AUTHOR:    Joey Boyd
-- STATUS:    PRELIMINARY

-- This MIB defines the object identifier (OID) for the
-- ADTRAN EFM NTU MIB objects

-- HISTORY:
-- 02/22/06 jlb STATUS: PRELIMINARY.
-- 03/03/06 jlb Updated to latest requirements.
-- 03/06/06 jlb Changed adGenEfmNtuProvCfmMaLevel to adGenEfmNtuProvCfmMdLevel in compliance
--				of Draft 6.0 of IEEE 802.1ag.
-- 09/15/06 jlb Added adGenEfmNtuProvMgmtIpTable
-- 02/07/07 jlb Added adGenEfmNtuProvMgmtTftpServer
-- 02/28/07 jlb Added adGenEfmNtuProvMgmtSnmpWriteCommunity and adGenEfmNtuProvMgmtSnmpReadCommunity
-- 05/14/07 jlb Added adGenEfmNtuProvMgmtSysName, adGenEfmNtuProvMgmtFarEndIfIndex
--              adGenEfmNtuProvMgmtFarEndIpAddress, and adGenEfmNtuProvMgmtFarEndSysName
-- 08/31/07 jlb Converted to SNMPv2.
-- 11/27/07 jlb Uncommented out the Read and Write Community strings.
-- 04/02/08 jlb Added adGenEfmNtuProvMgmtPriority.
-- 05/05/10 bly Added the following, SMIC verified: adGenEfmNtuProvMgmtSnmpSysLocation,
--              adGenEfmNtuProvMgmtEzProvHostOneIpAddress, adGenEfmNtuProvMgmtEzProvHostOneTrapVersion,
--              adGenEfmNtuProvMgmtEzProvHostTwoIpAddress, adGenEfmNtuProvMgmtEzProvHostTwoTrapVersion,
--              adGenEfmNtuProvMgmtEzProvEnabled


-- ******************************************************************************************

DEFINITIONS ::= BEGIN

    IMPORTS
        Gauge32,
        TimeTicks,
        Unsigned32,
	Integer32,
        IpAddress,
        OBJECT-TYPE,
        MODULE-IDENTITY,
        NOTIFICATION-TYPE
            FROM SNMPv2-SMI
	OBJECT-GROUP,
        NOTIFICATION-GROUP
            FROM SNMPv2-CONF
        sysName
            FROM SNMPv2-MIB
        DisplayString,
        TruthValue
            FROM SNMPv2-TC
        InetAddressIPv4,
        InetAddressIPv6,
        InetAddressPrefixLength
            FROM INET-ADDRESS-MIB
        AdGenTrapVersion
            FROM ADTRAN-SHARED-CND-SYSTEM-TC-MIB
        InterfaceIndex,
        ifDescr,
        ifIndex
            FROM IF-MIB
        adGenPortTrapIdentifier
            FROM ADTRAN-GENPORT-MIB
        adTrapInformSeqNum
            FROM ADTRAN-GENTRAPINFORM-MIB
        adGenSlotInfoIndex
            FROM ADTRAN-GENSLOT-MIB
        EntryStatus
            FROM ADTRAN-TC
        adGenEfmNtu,
        adGenEfmNtuID
            FROM ADTRAN-SHARED-EFM-MIB
        ;

adGenEfmNtuMIB MODULE-IDENTITY
   LAST-UPDATED "201409220000Z"
   ORGANIZATION "Adtran, Inc."
   CONTACT-INFO "http://www.adtran.com"
   DESCRIPTION
      "This MIB defines the objects for the EFM NTU MIB."

   REVISION "201409220000Z"
   DESCRIPTION
     "Added new items for Auto-Discovery and Auto-Config:
      adGenEfmNtuAutoDiscoverMode,
      adGenEfmNtuAutoDiscoverAck,
      adGenEfmNtuAutoDiscover,
      adGenEfmNtuProvMgmtAutoConfigMode,
      adGenEfmNtuProvMgmtAutoConfigFilename,
      adGenEfmNtuProvMgmtAutoConfigGroupName,
      adGenEfmNtuProvMgmtAutoConfigHostIpv4,
      adGenEfmNtuProvMgmtAutoConfigHostIpv6"

   REVISION "201405160000Z"
   DESCRIPTION "Added the following OIDs for IPv6 address management:
       adGenEfmNtuProvMgmtIpv6AddressLinkLocal,
       adGenEfmNtuProvMgmtIpv6Address,
       adGenEfmNtuProvMgmtIpv6AddressPrefixLength,
       adGenEfmNtuProvMgmtIpv6AddressEui64"

   REVISION "200708310000Z"
   DESCRIPTION "Created"

::= { adGenEfmNtuID 1 }



-- OBJECT IDENTIFIERS

adGenEfmNtuConfiguration   	OBJECT IDENTIFIER ::= {adGenEfmNtu 1}
adGenEfmNtuProvisioning    	OBJECT IDENTIFIER ::= {adGenEfmNtu 2}
adGenEfmNtuStatus          	OBJECT IDENTIFIER ::= {adGenEfmNtu 3}
adGenEfmNtuTest            	OBJECT IDENTIFIER ::= {adGenEfmNtu 4}
adGenEfmNtuPerformance     	OBJECT IDENTIFIER ::= {adGenEfmNtu 5}
adGenEfmNtuMibConformance       OBJECT IDENTIFIER ::= {adGenEfmNtu 7 }
adGenEfmNtuMibGroups            OBJECT IDENTIFIER ::= {adGenEfmNtuMibConformance 1 }

adGenEfmNtuAlarmsPrefix         OBJECT IDENTIFIER ::= {adGenEfmNtu 10}
adGenEfmNtuAlarms               OBJECT IDENTIFIER ::= {adGenEfmNtuAlarmsPrefix 0}

-- ******************************************************************************************
-- Configuration
-- ******************************************************************************************


-- ******************************************************************************************
-- Provisioning
-- ******************************************************************************************

-- ************************************
-- Unit Provisioning
-- ************************************
adGenEfmNtuProvTable OBJECT-TYPE
   SYNTAX      SEQUENCE OF AdGenEfmNtuProvEntry
   MAX-ACCESS  not-accessible
   STATUS      current
   DESCRIPTION
     "This table supports unit level provisioning variables."
   ::= { adGenEfmNtuProvisioning 1 }

adGenEfmNtuProvEntry OBJECT-TYPE
   SYNTAX      AdGenEfmNtuProvEntry
   MAX-ACCESS  not-accessible
   STATUS      current
   DESCRIPTION
     "An entry in the adGenEfmNtuProvTable."
   INDEX { ifIndex }
   ::= { adGenEfmNtuProvTable 1 }

AdGenEfmNtuProvEntry ::=
   SEQUENCE
   {
   adGenEfmNtuProvRestoreDefaults			INTEGER,
   adGenEfmNtuProvReset                                 INTEGER,
   adGenEfmNtuProvSwDownloadStart			INTEGER,
   adGenEfmNtuProvSwDownloadFilename                    OCTET STRING,
   adGenEfmNtuProvSwDownloadStatus                      OCTET STRING,
   adGenEfmNtuProvCustId                                OCTET STRING,
   adGenEfmNtuProvCustIfAutoNeg				INTEGER,
   adGenEfmNtuProvCustIfSpeed				INTEGER,
   adGenEfmNtuProvCustIfDuplex				INTEGER,
   adGenEfmNtuProvCustIfFlowControl			INTEGER,
   adGenEfmNtuProvEnablePassword			OCTET STRING,
   adGenEfmNtuProvMacTableSize				Integer32,
   adGenEfmNtuProvMacAging                              Integer32,
   adGenEfmNtuProvLinkStateAware			INTEGER,
   adGenEfmNtuAutoDiscoverMode                          TruthValue,
   adGenEfmNtuAutoDiscoverAck                           TruthValue
   }

adGenEfmNtuProvRestoreDefaults OBJECT-TYPE
   SYNTAX      	INTEGER
               	{
               	restoreDefaults(1)
               	}
   MAX-ACCESS   read-write
   STATUS       current
   DESCRIPTION
     "This object restores the factory default options for the
      entire unit.  A GET returns a 1."
   ::= { adGenEfmNtuProvEntry 1 }

adGenEfmNtuProvReset OBJECT-TYPE
   SYNTAX      	INTEGER
               	{
               	reset(1)
               	}
   MAX-ACCESS   read-write
   STATUS       current
   DESCRIPTION
     "This object performs a soft reset of the unit. A GET returns a 1."
   ::= { adGenEfmNtuProvEntry 2 }

adGenEfmNtuProvSwDownloadStart OBJECT-TYPE
   SYNTAX      INTEGER
               {
               start(1)
               }
   MAX-ACCESS     read-write
   STATUS      current
   DESCRIPTION
     "A set command will initiate a software download.
      Get has no meaning and will always return 1."
   ::= { adGenEfmNtuProvEntry 3 }

adGenEfmNtuProvSwDownloadFilename OBJECT-TYPE
   SYNTAX      OCTET STRING
   MAX-ACCESS  read-write
   STATUS      current
   DESCRIPTION
     "Filename for used for the software download."
   ::= { adGenEfmNtuProvEntry 4 }

adGenEfmNtuProvSwDownloadStatus OBJECT-TYPE
   SYNTAX      OCTET STRING
   MAX-ACCESS  read-only
   STATUS      current
   DESCRIPTION
     "A GET command returns the status of the software download."
   ::= { adGenEfmNtuProvEntry 5 }

adGenEfmNtuProvCustId OBJECT-TYPE
   SYNTAX      OCTET STRING
   MAX-ACCESS  read-write
   STATUS      current
   DESCRIPTION
     "Unique text identifier for this customer."
   ::= { adGenEfmNtuProvEntry 6 }

adGenEfmNtuProvCustIfAutoNeg OBJECT-TYPE
   SYNTAX      INTEGER
               {
               enable(1),
               disable(2)
               }
   MAX-ACCESS  read-write
   STATUS      current
   DESCRIPTION
     "This object is used to enable/disable auto-negotiation
	  on the customer interface."
   ::= { adGenEfmNtuProvEntry 7 }

adGenEfmNtuProvCustIfSpeed OBJECT-TYPE
   SYNTAX      INTEGER
               {
               tenBaseT(1),
               hundredBaseT(2)
               }
   MAX-ACCESS  read-write
   STATUS      current
   DESCRIPTION
     "This object configures the speed of the customer interface.
	  If auto-negotiation is enabled, then this setting is ignored."
   ::= { adGenEfmNtuProvEntry 8 }

adGenEfmNtuProvCustIfDuplex OBJECT-TYPE
   SYNTAX      INTEGER
               {
               halfDuplex(1),
               fullDuplex(2)
               }
   MAX-ACCESS  read-write
   STATUS      current
   DESCRIPTION
     "This object configures the duplex of the customer interface.
	  If auto-negotiation is enabled, then this setting is ignored."
   ::= { adGenEfmNtuProvEntry 9 }

adGenEfmNtuProvCustIfFlowControl OBJECT-TYPE
   SYNTAX      INTEGER
               {
               enable(1),
               disable(2)
               }
   MAX-ACCESS     read-write
   STATUS      current
   DESCRIPTION
     "This object configures the flow control of the
	  customer interface."
   ::= { adGenEfmNtuProvEntry 10 }

adGenEfmNtuProvEnablePassword OBJECT-TYPE
   SYNTAX      OCTET STRING
   MAX-ACCESS  read-write
   STATUS      current
   DESCRIPTION
     "This object configures the enable login password."
   ::= { adGenEfmNtuProvEntry 11 }

adGenEfmNtuProvMacTableSize OBJECT-TYPE
   SYNTAX      Integer32
   MAX-ACCESS  read-write
   STATUS      current
   DESCRIPTION
     "This object configures the MAC forwarding table size."
   ::= { adGenEfmNtuProvEntry 12 }

adGenEfmNtuProvMacAging OBJECT-TYPE
   SYNTAX      Integer32
   MAX-ACCESS  read-write
   STATUS      current
   DESCRIPTION
     "This object configures the MAC aging interval (in seconds).
	  A value of 0 means there will be no aging of MAC addresses."
   ::= { adGenEfmNtuProvEntry 13 }

adGenEfmNtuProvLinkStateAware OBJECT-TYPE
   SYNTAX      INTEGER
               {
               enable(1),
               disable(2)
               }
   MAX-ACCESS  read-write
   STATUS      current
   DESCRIPTION
     "This object is used to enable/disable link state awareness."
   ::= { adGenEfmNtuProvEntry 14 }

adGenEfmNtuAutoDiscoverMode OBJECT-TYPE
   SYNTAX       TruthValue
   MAX-ACCESS   read-write
   STATUS       current
   DESCRIPTION
     "Auto-Discover mode. When set to true, the system will send a notification
     (adGenEfmNtuAutoDiscover) to prompt the EMS to automatically discover the NTU.
     The system will retransmit the trap periodically until the EMS acknowledges the
     notification by setting adGenEfmNtuAutoDiscoverAck to true."
   DEFVAL { false }
    ::= { adGenEfmNtuProvEntry 15 }

adGenEfmNtuAutoDiscoverAck OBJECT-TYPE
   SYNTAX       TruthValue
   MAX-ACCESS   read-write
   STATUS       current
   DESCRIPTION
     "Auto-Discover acknowledgement. The NE sets this value to false when it activates
     the Auto-Discovery alarm (adGenEfmNtuAutoDiscover). The EMS should set this value
     to true to acknowledge the notification."
   DEFVAL { false }
    ::= { adGenEfmNtuProvEntry 16 }

-- ************************************
-- IEEE 802.1 CFM Provisioning
-- ************************************
adGenEfmNtuProvCfmTable OBJECT-TYPE
   SYNTAX      SEQUENCE OF AdGenEfmNtuProvCfmEntry
   MAX-ACCESS  not-accessible
   STATUS      current
   DESCRIPTION
     "This table supports provisioning of IEEE 802.1ag
	  CFM (Connectivity Fault Management)."
   ::= { adGenEfmNtuProvisioning 2 }

adGenEfmNtuProvCfmEntry OBJECT-TYPE
   SYNTAX      AdGenEfmNtuProvCfmEntry
   MAX-ACCESS  not-accessible
   STATUS      current
   DESCRIPTION
     "An entry in the adGenEfmNtuProvCfmTable."
   INDEX { ifIndex }
   ::= { adGenEfmNtuProvCfmTable 1 }

AdGenEfmNtuProvCfmEntry ::=
   SEQUENCE
   {
        adGenEfmNtuProvCfmMdName                OCTET STRING,
        adGenEfmNtuProvCfmMaName                OCTET STRING,
	adGenEfmNtuProvCfmLocalMepId  		Integer32,
        adGenEfmNtuProvCfmMdLevel               Integer32,
        adGenEfmNtuProvCfmVlanId                Integer32,
	adGenEfmNtuProvCfmCcmInterval		Integer32,
	adGenEfmNtuProvCfmMepTableNextIndex	Integer32
   }

adGenEfmNtuProvCfmMdName OBJECT-TYPE
   SYNTAX      	OCTET STRING
   MAX-ACCESS   read-write
   STATUS       current
   DESCRIPTION
     "A text string used to identify the maintenance domain
	  that this end-point belongs to."
	 ::= { adGenEfmNtuProvCfmEntry 1 }

adGenEfmNtuProvCfmMaName OBJECT-TYPE
   SYNTAX      	OCTET STRING
   MAX-ACCESS   read-write
   STATUS       current
   DESCRIPTION
     "A text string used to identify the maintenance association
	  that this end-point belongs to."
	 ::= { adGenEfmNtuProvCfmEntry 2 }

adGenEfmNtuProvCfmLocalMepId OBJECT-TYPE
   SYNTAX      	Integer32
   MAX-ACCESS   read-write
   STATUS       current
   DESCRIPTION
     "A unique numeric value used to represent this end-point
	  within a maintenance domain. Range is 1 to 8191"
	 ::= { adGenEfmNtuProvCfmEntry 3 }

adGenEfmNtuProvCfmMdLevel OBJECT-TYPE
   SYNTAX      	Integer32
   MAX-ACCESS   read-write
   STATUS       current
   DESCRIPTION
     "The maintenance domain level to which this end-point
	  belongs (range is 0 to 7; typically 7, 6, or 5 for the
	  customer device)."
	 ::= { adGenEfmNtuProvCfmEntry 4 }

adGenEfmNtuProvCfmVlanId OBJECT-TYPE
   SYNTAX      	Integer32
   MAX-ACCESS   read-write
   STATUS       current
   DESCRIPTION
     "The VLAN ID used by this end-point.  0 means the data is
	  untagged.  Range is 0 to 4094."
	 ::= { adGenEfmNtuProvCfmEntry 5 }

adGenEfmNtuProvCfmCcmInterval OBJECT-TYPE
   SYNTAX      	Integer32
   MAX-ACCESS   read-write
   STATUS       current
   DESCRIPTION
     "The time (in milliseconds) between the transmission of
	  continuity check messages.  A value of 0 stops the
	  transmission of CC messages.  The maximum interval
	  supported is 60 seconds (60000 milliseconds)."
	 ::= { adGenEfmNtuProvCfmEntry 6 }

adGenEfmNtuProvCfmMepTableNextIndex OBJECT-TYPE
   SYNTAX      	Integer32
   MAX-ACCESS   read-only
   STATUS       current
   DESCRIPTION
     "The next available index in the MEP table.  This will
	  be used to create another entry in the MEP table."
	 ::= { adGenEfmNtuProvCfmEntry 7 }

-- ************************************
-- IEEE 802.1 MEP Table
-- ************************************
adGenEfmNtuProvCfmMepTable OBJECT-TYPE
   SYNTAX      SEQUENCE OF AdGenEfmNtuProvCfmMepEntry
   MAX-ACCESS  not-accessible
   STATUS      current
   DESCRIPTION
     "This table supports provisioning of the maintenance
	  end-point (MEP) table.  This table is used to store
	  information about all of the peers within the
	  maintenance domain."
   ::= { adGenEfmNtuProvisioning 3 }

adGenEfmNtuProvCfmMepEntry OBJECT-TYPE
   SYNTAX      AdGenEfmNtuProvCfmMepEntry
   MAX-ACCESS  not-accessible
   STATUS      current
   DESCRIPTION
     "An entry in the adGenEfmNtuProvCfmMepTable."
   INDEX { ifIndex, adGenEfmNtuProvCfmMepIndex }
   ::= { adGenEfmNtuProvCfmMepTable 1 }

AdGenEfmNtuProvCfmMepEntry ::=
   SEQUENCE
   {
   	adGenEfmNtuProvCfmMepIndex  		Integer32,
	adGenEfmNtuProvCfmMepId         	Integer32,
	adGenEfmNtuProvCfmMepEntryStatus	EntryStatus
   }

adGenEfmNtuProvCfmMepIndex OBJECT-TYPE
   SYNTAX      	Integer32
   MAX-ACCESS   read-only
   STATUS       current
   DESCRIPTION
     "An index into the MEP table.  When creating a new
	  entry, use adGenEfmNtuProvCfmMepNextIndex to determine
	  the next available index."
	 ::= { adGenEfmNtuProvCfmMepEntry 1 }

adGenEfmNtuProvCfmMepId OBJECT-TYPE
   SYNTAX      	Integer32
   MAX-ACCESS   read-write
   STATUS       current
   DESCRIPTION
     "A unique numeric value used to represent this end-point
	  within a maintenance domain. Range is 1 to 8191"
	 ::= { adGenEfmNtuProvCfmMepEntry 2 }

adGenEfmNtuProvCfmMepEntryStatus OBJECT-TYPE
   SYNTAX      	EntryStatus
   MAX-ACCESS   read-write
   STATUS       current
   DESCRIPTION
	 "Used to create and delete entries in the MEP table."
	 ::= { adGenEfmNtuProvCfmMepEntry 3 }

-- ************************************
-- Management IP Table
-- ************************************
adGenEfmNtuProvMgmtIpTable OBJECT-TYPE
   SYNTAX      SEQUENCE OF AdGenEfmNtuProvMgmtIpEntry
   MAX-ACCESS  not-accessible
   STATUS      current
   DESCRIPTION
     "This table supports provisioning of the managment
	  IP table.  These entries will be proxied for by the
	  connected LTU.  Once provisioned, the NTU can be
	  managed directly."
   ::= { adGenEfmNtuProvisioning 4 }

adGenEfmNtuProvMgmtIpEntry OBJECT-TYPE
   SYNTAX      AdGenEfmNtuProvMgmtIpEntry
   MAX-ACCESS  not-accessible
   STATUS      current
   DESCRIPTION
     "An entry in the adGenEfmNtuProvMgmtIpTable."
   INDEX { ifIndex }
   ::= { adGenEfmNtuProvMgmtIpTable 1 }

AdGenEfmNtuProvMgmtIpEntry ::=
   SEQUENCE
   {
      adGenEfmNtuProvMgmtIpAddress           IpAddress,
      adGenEfmNtuProvMgmtIpSubnetMask        IpAddress,
      adGenEfmNtuProvMgmtIpGateway           IpAddress,
      adGenEfmNtuProvMgmtIpVlan              Integer32,
      adGenEfmNtuProvMgmtTftpServer          IpAddress,
      adGenEfmNtuProvMgmtSnmpWriteCommunity  DisplayString,
      adGenEfmNtuProvMgmtSnmpReadCommunity   DisplayString,
      adGenEfmNtuProvMgmtSysName             DisplayString,
      adGenEfmNtuProvMgmtFarEndIfIndex       InterfaceIndex,
      adGenEfmNtuProvMgmtFarEndIpAddress     IpAddress,
      adGenEfmNtuProvMgmtFarEndSysName       DisplayString,
      adGenEfmNtuProvMgmtPriority            Integer32,
      adGenEfmNtuProvMgmtSnmpSysLocation     DisplayString,
      adGenEfmNtuProvMgmtEzProvHostOneIpAddress     IpAddress,
      adGenEfmNtuProvMgmtEzProvHostOneTrapVersion   AdGenTrapVersion,
      adGenEfmNtuProvMgmtEzProvHostTwoIpAddress     IpAddress,
      adGenEfmNtuProvMgmtEzProvHostTwoTrapVersion   AdGenTrapVersion,
      adGenEfmNtuProvMgmtEzProvEnabled              TruthValue,
      adGenEfmNtuProvMgmtIpv6AddressPrefixLength    InetAddressPrefixLength,
      adGenEfmNtuProvMgmtIpv6AddressEui64           TruthValue,
      adGenEfmNtuProvMgmtIpv6Address                InetAddressIPv6,
      adGenEfmNtuProvMgmtIpv6AddressLinkLocal       InetAddressIPv6,
      adGenEfmNtuProvMgmtAutoConfigMode             TruthValue,
      adGenEfmNtuProvMgmtAutoConfigFilename         DisplayString,
      adGenEfmNtuProvMgmtAutoConfigGroupName        DisplayString,
      adGenEfmNtuProvMgmtAutoConfigHostIpv4         InetAddressIPv4,
      adGenEfmNtuProvMgmtAutoConfigHostIpv6         InetAddressIPv6
   }

adGenEfmNtuProvMgmtIpAddress OBJECT-TYPE
   SYNTAX      	IpAddress
   MAX-ACCESS   read-write
   STATUS       current
   DESCRIPTION
     "The management IP address of the NTU."
	 ::= { adGenEfmNtuProvMgmtIpEntry 1 }

adGenEfmNtuProvMgmtIpSubnetMask OBJECT-TYPE
   SYNTAX      	IpAddress
   MAX-ACCESS   read-write
   STATUS       current
   DESCRIPTION
     "The management subnet mask of the NTU."
	 ::= { adGenEfmNtuProvMgmtIpEntry 2 }

adGenEfmNtuProvMgmtIpGateway OBJECT-TYPE
   SYNTAX      	IpAddress
   MAX-ACCESS   read-write
   STATUS       current
   DESCRIPTION
     "The management default gateway of the NTU."
	 ::= { adGenEfmNtuProvMgmtIpEntry 3 }

adGenEfmNtuProvMgmtIpVlan OBJECT-TYPE
   SYNTAX      	Integer32
   MAX-ACCESS   read-write
   STATUS       current
   DESCRIPTION
     "The management VLAN of the NTU."
	 ::= { adGenEfmNtuProvMgmtIpEntry 4 }

adGenEfmNtuProvMgmtTftpServer OBJECT-TYPE
   SYNTAX      	IpAddress
   MAX-ACCESS   read-write
   STATUS       current
   DESCRIPTION
     "The TFTP server address used by the NTU."
	 ::= { adGenEfmNtuProvMgmtIpEntry 5 }

adGenEfmNtuProvMgmtSnmpWriteCommunity OBJECT-TYPE
   SYNTAX         DisplayString
   MAX-ACCESS    read-write
   STATUS         current
   DESCRIPTION
     "The read-write SNMP community string used
      by the NTU."
         ::= { adGenEfmNtuProvMgmtIpEntry 6 }

adGenEfmNtuProvMgmtSnmpReadCommunity OBJECT-TYPE
   SYNTAX         DisplayString
   MAX-ACCESS    read-write
   STATUS         current
   DESCRIPTION
     "The read-only SNMP community string used
      by the NTU."
         ::= { adGenEfmNtuProvMgmtIpEntry 7 }

adGenEfmNtuProvMgmtSysName OBJECT-TYPE
   SYNTAX       DisplayString
   MAX-ACCESS   read-write
   STATUS       current
   DESCRIPTION
     "The System Name (TID) used by the NTU."
    ::= { adGenEfmNtuProvMgmtIpEntry 8 }

adGenEfmNtuProvMgmtFarEndIfIndex OBJECT-TYPE
   SYNTAX       InterfaceIndex
   MAX-ACCESS   read-only
   STATUS       current
   DESCRIPTION
     "The ifIndex associated with the bonded group connected to this NTU."
    ::= { adGenEfmNtuProvMgmtIpEntry 9 }

adGenEfmNtuProvMgmtFarEndIpAddress OBJECT-TYPE
   SYNTAX       IpAddress
   MAX-ACCESS   read-only
   STATUS       current
   DESCRIPTION
     "The IP address associated with the system connected to this NTU."
    ::= { adGenEfmNtuProvMgmtIpEntry 10 }

adGenEfmNtuProvMgmtFarEndSysName OBJECT-TYPE
   SYNTAX       DisplayString
   MAX-ACCESS   read-only
   STATUS       current
   DESCRIPTION
     "The System Name (TID) associated with the system connected to this NTU."
    ::= { adGenEfmNtuProvMgmtIpEntry 11 }

adGenEfmNtuProvMgmtPriority OBJECT-TYPE
   SYNTAX      	Integer32
   MAX-ACCESS   read-write
   STATUS       current
   DESCRIPTION
     "The priority of the management VLAN of the NTU."
    ::= { adGenEfmNtuProvMgmtIpEntry 12 }

adGenEfmNtuProvMgmtSnmpSysLocation OBJECT-TYPE
   SYNTAX        DisplayString
   MAX-ACCESS    read-write
   STATUS        current
   DESCRIPTION
     "The SNMP SysLocation string used by the NTU."
    ::= { adGenEfmNtuProvMgmtIpEntry 13 }

adGenEfmNtuProvMgmtEzProvHostOneIpAddress OBJECT-TYPE
   SYNTAX      	IpAddress
   MAX-ACCESS   read-write
   STATUS       current
   DESCRIPTION
     "The EZ-Provisioning trap host IP address of the NTU."
    ::= { adGenEfmNtuProvMgmtIpEntry 14 }

adGenEfmNtuProvMgmtEzProvHostOneTrapVersion OBJECT-TYPE
   SYNTAX       AdGenTrapVersion
   MAX-ACCESS   read-write
   STATUS       current
   DESCRIPTION
     "The EZ-Provisioning trap version of the NTU."
    ::= { adGenEfmNtuProvMgmtIpEntry 15 }

adGenEfmNtuProvMgmtEzProvHostTwoIpAddress OBJECT-TYPE
   SYNTAX      	IpAddress
   MAX-ACCESS   read-write
   STATUS       current
   DESCRIPTION
     "The EZ-Provisioning trap host IP address of the NTU."
    ::= { adGenEfmNtuProvMgmtIpEntry 16 }

adGenEfmNtuProvMgmtEzProvHostTwoTrapVersion OBJECT-TYPE
   SYNTAX       AdGenTrapVersion
   MAX-ACCESS   read-write
   STATUS       current
   DESCRIPTION
     "The EZ-Provisioning trap version of the NTU."
    ::= { adGenEfmNtuProvMgmtIpEntry 17 }

adGenEfmNtuProvMgmtEzProvEnabled OBJECT-TYPE
   SYNTAX       TruthValue
   MAX-ACCESS   read-write
   STATUS       current
   DESCRIPTION
     "The EZ-Provisioning administrative state of the NTU."
    ::= { adGenEfmNtuProvMgmtIpEntry 18 }

adGenEfmNtuProvMgmtIpv6AddressPrefixLength OBJECT-TYPE
   SYNTAX        InetAddressPrefixLength
   MAX-ACCESS    read-write
   STATUS        current
   DESCRIPTION
     "The provisioned IPv6 unicast address prefix length."
    ::= { adGenEfmNtuProvMgmtIpEntry 19 }

adGenEfmNtuProvMgmtIpv6AddressEui64 OBJECT-TYPE
   SYNTAX       TruthValue
   MAX-ACCESS   read-write
   STATUS       current
   DESCRIPTION
     "When true, then the operational IPv6 unicast address is a combination
      of the provisioned prefix and an EUI-64 formatted Interface ID."
    ::= { adGenEfmNtuProvMgmtIpEntry 20 }

adGenEfmNtuProvMgmtIpv6Address OBJECT-TYPE
   SYNTAX        InetAddressIPv6
   MAX-ACCESS    read-write
   STATUS        current
   DESCRIPTION
     "The provisioned IPv6 unicast address or address prefix.
      If EUI-64 is false, then the operational unicast address equals
      this value. If EUI-64 is true, then the operational unicast address
      is derived from this value (high-order bits) and the Interface ID
      (low-order bits) in combination with the prefix length."
    ::= { adGenEfmNtuProvMgmtIpEntry 21 }

adGenEfmNtuProvMgmtIpv6AddressLinkLocal OBJECT-TYPE
   SYNTAX        InetAddressIPv6
   MAX-ACCESS    read-write
   STATUS        current
   DESCRIPTION
     "The provisioned IPv6 link-local address prefix.
      The prefix length is implicitly 10 bits."
    ::= { adGenEfmNtuProvMgmtIpEntry 22 }

adGenEfmNtuProvMgmtAutoConfigMode OBJECT-TYPE
   SYNTAX       TruthValue
   MAX-ACCESS   read-write
   STATUS       current
   DESCRIPTION
     "Auto-Config mode.  When set to True, the Auto-Config feature is
      enabled on the NTU.  When set to False, the Auto-Config feature
      is disabled on the NTU."
   DEFVAL { false }
    ::= { adGenEfmNtuProvMgmtIpEntry 23 }

adGenEfmNtuProvMgmtAutoConfigFilename OBJECT-TYPE
   SYNTAX        DisplayString (SIZE (0..64))
   MAX-ACCESS    read-write
   STATUS        current
   DESCRIPTION
     "Auto-Config filename.  This filename is used by the NTU during the
      Auto-Config sequence to retrieve configuration and firmware."
   DEFVAL { "" }
    ::= { adGenEfmNtuProvMgmtIpEntry 24 }

adGenEfmNtuProvMgmtAutoConfigGroupName OBJECT-TYPE
   SYNTAX        DisplayString (SIZE (0..64))
   MAX-ACCESS    read-write
   STATUS        current
   DESCRIPTION
     "Auto-Config group name.  This group name may be used by the NTU to
      configure filenames to retrieve from the file server."
   DEFVAL { "" }
    ::= { adGenEfmNtuProvMgmtIpEntry 25 }

adGenEfmNtuProvMgmtAutoConfigHostIpv4 OBJECT-TYPE
   SYNTAX        InetAddressIPv4
   MAX-ACCESS    read-write
   STATUS        current
   DESCRIPTION
     "Auto-Config file server IPv4 address"
    ::= { adGenEfmNtuProvMgmtIpEntry 26 }

adGenEfmNtuProvMgmtAutoConfigHostIpv6 OBJECT-TYPE
   SYNTAX        InetAddressIPv6
   MAX-ACCESS    read-write
   STATUS        current
   DESCRIPTION
     "Auto-Config file server IPv6 address"
    ::= { adGenEfmNtuProvMgmtIpEntry 27 }

-- ******************************************************************************************
-- Status
-- ******************************************************************************************

adGenEfmNtuStatTable OBJECT-TYPE
   SYNTAX      SEQUENCE OF AdGenEfmNtuStatEntry
   MAX-ACCESS  not-accessible
   STATUS      current
   DESCRIPTION
     "This table supports unit level status."
   ::= { adGenEfmNtuStatus 1 }

adGenEfmNtuStatEntry OBJECT-TYPE
   SYNTAX      AdGenEfmNtuStatEntry
   MAX-ACCESS  not-accessible
   STATUS      current
   DESCRIPTION
     "An entry in the adGenEfmNtuStatTable."
   INDEX { ifIndex }
   ::= { adGenEfmNtuStatTable 1 }

AdGenEfmNtuStatEntry ::=
   SEQUENCE
   {
        adGenEfmNtuStatUpTime                        TimeTicks,
        adGenEfmNtuStatLinkStateAware                INTEGER,
        adGenEfmNtuStatCustIf                        INTEGER
   }

adGenEfmNtuStatUpTime OBJECT-TYPE
   SYNTAX      TimeTicks
   MAX-ACCESS  read-only
   STATUS      current
   DESCRIPTION
     "The time (in hundredths of a second) since the
      unit was powered up."
   ::= { adGenEfmNtuStatEntry 1 }

adGenEfmNtuStatLinkStateAware OBJECT-TYPE
   SYNTAX      INTEGER
               {
               down(1),
               up(2)
               }
   MAX-ACCESS  read-only
   STATUS      current
   DESCRIPTION
     "The current status of the link state awareness."
   ::= { adGenEfmNtuStatEntry 2 }

adGenEfmNtuStatCustIf OBJECT-TYPE
   SYNTAX      INTEGER
               {
               down(1),
               up(2)
               }
   MAX-ACCESS  read-only
   STATUS      current
   DESCRIPTION
     "The current status of the customer interface."
   ::= { adGenEfmNtuStatEntry 3 }



-- ******************************************************************************************
-- Test
-- ******************************************************************************************


-- ******************************************************************************************
-- Performance
-- ******************************************************************************************

adGenEfmNtuPerfTable OBJECT-TYPE
   SYNTAX      SEQUENCE OF AdGenEfmNtuPerfEntry
   MAX-ACCESS   not-accessible
   STATUS      current
   DESCRIPTION
     "This table supports unit level performance."
   ::= { adGenEfmNtuPerformance 1 }

adGenEfmNtuPerfEntry OBJECT-TYPE
   SYNTAX      AdGenEfmNtuPerfEntry
   MAX-ACCESS  not-accessible
   STATUS      current
   DESCRIPTION
     "An entry in the adGenEfmNtuPerfTable."
   INDEX { ifIndex }
   ::= { adGenEfmNtuPerfTable 1 }

AdGenEfmNtuPerfEntry ::=
   SEQUENCE
   {
        adGenEfmNtuPerfCustIfTxOctets                        Gauge32,
        adGenEfmNtuPerfCustIfTxFrames                        Gauge32,
        adGenEfmNtuPerfCustIfRxOctets                        Gauge32,
        adGenEfmNtuPerfCustIfRxFrames                        Gauge32,
        adGenEfmNtuPerfCustIfRxErroredFrames                 Gauge32,
        adGenEfmNtuPerfCustIfRxDiscardedFrames               Gauge32
   }

adGenEfmNtuPerfCustIfTxOctets OBJECT-TYPE
   SYNTAX      Gauge32
   MAX-ACCESS  read-only
   STATUS      current
   DESCRIPTION
     "The number of octets transmitted to the customer interface."
   ::= { adGenEfmNtuPerfEntry 1 }

adGenEfmNtuPerfCustIfTxFrames OBJECT-TYPE
   SYNTAX      Gauge32
   MAX-ACCESS  read-only
   STATUS      current
   DESCRIPTION
     "The number of ethernet frames transmitted to the customer interface."
   ::= { adGenEfmNtuPerfEntry 2 }

adGenEfmNtuPerfCustIfRxOctets OBJECT-TYPE
   SYNTAX      Gauge32
   MAX-ACCESS  read-only
   STATUS      current
   DESCRIPTION
     "The number of octets received from the customer interface."
   ::= { adGenEfmNtuPerfEntry 3 }

adGenEfmNtuPerfCustIfRxFrames OBJECT-TYPE
   SYNTAX      Gauge32
   MAX-ACCESS  read-only
   STATUS      current
   DESCRIPTION
     "The number of ethernet frames received from the customer interface."
   ::= { adGenEfmNtuPerfEntry 4 }

adGenEfmNtuPerfCustIfRxErroredFrames OBJECT-TYPE
   SYNTAX      Gauge32
   MAX-ACCESS  read-only
   STATUS      current
   DESCRIPTION
     "The number of ethernet frames received from the customer interface
	  that contain errors."
   ::= { adGenEfmNtuPerfEntry 5 }

adGenEfmNtuPerfCustIfRxDiscardedFrames OBJECT-TYPE
   SYNTAX      Gauge32
   MAX-ACCESS  read-only
   STATUS      current
   DESCRIPTION
     "The number of ethernet frames received from the customer interface
	  that have been discarded due to congestion."
   ::= { adGenEfmNtuPerfEntry 6 }

-- ******************************************************************************************
-- MIB Groups
-- ******************************************************************************************
adGenEfmNtuProvGroup OBJECT-GROUP
   OBJECTS
   {
        adGenEfmNtuProvRestoreDefaults,
        adGenEfmNtuProvReset,
        adGenEfmNtuProvSwDownloadStart,
        adGenEfmNtuProvSwDownloadFilename,
        adGenEfmNtuProvSwDownloadStatus,
        adGenEfmNtuProvCustId,
        adGenEfmNtuProvCustIfAutoNeg,
        adGenEfmNtuProvCustIfSpeed,
        adGenEfmNtuProvCustIfDuplex,
        adGenEfmNtuProvCustIfFlowControl,
        adGenEfmNtuProvEnablePassword,
        adGenEfmNtuProvMacTableSize,
        adGenEfmNtuProvMacAging,
        adGenEfmNtuProvLinkStateAware,
        adGenEfmNtuAutoDiscoverMode,
        adGenEfmNtuAutoDiscoverAck
   }
   STATUS current
   DESCRIPTION
     "These objects provide support for EFM NTU provisioning."
   ::= { adGenEfmNtuMibGroups 1 }

adGenEfmNtuProvCfmGroup OBJECT-GROUP
   OBJECTS
   {
        adGenEfmNtuProvCfmMdName,
        adGenEfmNtuProvCfmMaName,
        adGenEfmNtuProvCfmLocalMepId,
        adGenEfmNtuProvCfmMdLevel,
        adGenEfmNtuProvCfmVlanId,
        adGenEfmNtuProvCfmCcmInterval,
        adGenEfmNtuProvCfmMepTableNextIndex
   }
   STATUS current
   DESCRIPTION
     "These objects provide support for EFM NTU CFM provisioning."
   ::= { adGenEfmNtuMibGroups 2 }

adGenEfmNtuProvCfmMepGroup OBJECT-GROUP
   OBJECTS
   {
        adGenEfmNtuProvCfmMepIndex,
        adGenEfmNtuProvCfmMepId,
        adGenEfmNtuProvCfmMepEntryStatus
   }
   STATUS current
   DESCRIPTION
     "These objects provide support for EFM NTU CFM MEP provisioning."
   ::= { adGenEfmNtuMibGroups 3 }

adGenEfmNtuProvMgmtGroup OBJECT-GROUP
   OBJECTS
   {
        adGenEfmNtuProvMgmtIpAddress,
        adGenEfmNtuProvMgmtIpSubnetMask,
        adGenEfmNtuProvMgmtIpGateway,
        adGenEfmNtuProvMgmtIpVlan,
        adGenEfmNtuProvMgmtTftpServer,
        adGenEfmNtuProvMgmtSysName,
        adGenEfmNtuProvMgmtFarEndIfIndex,
        adGenEfmNtuProvMgmtFarEndIpAddress,
        adGenEfmNtuProvMgmtFarEndSysName,
        adGenEfmNtuProvMgmtSnmpWriteCommunity,
        adGenEfmNtuProvMgmtSnmpReadCommunity,
        adGenEfmNtuProvMgmtPriority,
        adGenEfmNtuProvMgmtSnmpSysLocation,
        adGenEfmNtuProvMgmtEzProvHostOneIpAddress,
        adGenEfmNtuProvMgmtEzProvHostOneTrapVersion,
        adGenEfmNtuProvMgmtEzProvHostTwoIpAddress,
        adGenEfmNtuProvMgmtEzProvHostTwoTrapVersion,
        adGenEfmNtuProvMgmtEzProvEnabled,
        adGenEfmNtuProvMgmtIpv6AddressPrefixLength,
        adGenEfmNtuProvMgmtIpv6AddressEui64,
        adGenEfmNtuProvMgmtIpv6Address,
        adGenEfmNtuProvMgmtIpv6AddressLinkLocal,
        adGenEfmNtuProvMgmtAutoConfigMode,
        adGenEfmNtuProvMgmtAutoConfigFilename,
        adGenEfmNtuProvMgmtAutoConfigGroupName,
        adGenEfmNtuProvMgmtAutoConfigHostIpv4,
        adGenEfmNtuProvMgmtAutoConfigHostIpv6
   }
   STATUS current
   DESCRIPTION
     "These objects provide support for EFM NTU management provisioning."
   ::= { adGenEfmNtuMibGroups 4 }

adGenEfmNtuStatGroup OBJECT-GROUP
   OBJECTS
   {
        adGenEfmNtuStatUpTime,
        adGenEfmNtuStatLinkStateAware,
        adGenEfmNtuStatCustIf
   }
   STATUS current
   DESCRIPTION
     "These objects provide support for EFM NTU status."
   ::= { adGenEfmNtuMibGroups 5 }

adGenEfmNtuPerfGroup OBJECT-GROUP
   OBJECTS
   {
        adGenEfmNtuPerfCustIfTxOctets,
        adGenEfmNtuPerfCustIfTxFrames,
        adGenEfmNtuPerfCustIfRxOctets,
        adGenEfmNtuPerfCustIfRxFrames,
        adGenEfmNtuPerfCustIfRxErroredFrames,
        adGenEfmNtuPerfCustIfRxDiscardedFrames
   }
   STATUS current
   DESCRIPTION
     "These objects provide support for EFM NTU performance."
   ::= { adGenEfmNtuMibGroups 6 }

adGenEfmNtuEventGroup NOTIFICATION-GROUP
   NOTIFICATIONS
   {
        adGenEfmNtuCraftLoginSuccess,
        adGenEfmNtuCraftLoginFail,
        adGenEfmNtuSwDownloadFail,
        adGenEfmNtuCorruptConfiguration,
        adGenEfmNtuMACTableExhaust,
        adGenEfmNtuCustIfDownClr,
        adGenEfmNtuCustIfDownAct,
        adGenEfmNtuAutoDiscover
   }
   STATUS current
   DESCRIPTION
     "These objects provide support for EFM NTU performance."
   ::= { adGenEfmNtuMibGroups 7 }


-- ******************************************************************************************
-- Alarms
-- ******************************************************************************************
adGenEfmNtuCraftLoginSuccess   NOTIFICATION-TYPE
    OBJECTS         {
                    adTrapInformSeqNum,
                    sysName,
                    adGenSlotInfoIndex,
                    adGenEfmNtuProvCustId
                    }
    STATUS          current
    DESCRIPTION
                    "NTU Craft Login Successful"
    --#TYPE         "Info - NTU Craft Login Successful"
    --#SUMMARY      "NTU Craft Login Successful "
    --#SUMMARY      "detected at shelf: %s, slot: %d and customer: %s"
    --#ARGUMENTS    {1,2,3}
    --#SEVERITY     "ALERT"
    --#GENERIC      6
    --#CATEGORY     "Info Events"
    --#SOURCE_ID    "A"
    --#TIMEINDEX    0
    ::= {adGenEfmNtuAlarms 1}

adGenEfmNtuCraftLoginFail   NOTIFICATION-TYPE
    OBJECTS         {
                    adTrapInformSeqNum,
                    sysName,
                    adGenSlotInfoIndex,
                    adGenEfmNtuProvCustId
                    }
    STATUS          current
    DESCRIPTION
                    "NTU Craft Login Failed"
    --#TYPE         "Info - NTU Craft Login Failed"
    --#SUMMARY      "NTU Craft Login Failed "
    --#SUMMARY      "detected at shelf: %s, slot: %d and customer: %s"
    --#ARGUMENTS    {1,2,3}
    --#SEVERITY     "ALERT"
    --#GENERIC      6
    --#CATEGORY     "Info Events"
    --#SOURCE_ID    "A"
    --#TIMEINDEX    0
    ::= {adGenEfmNtuAlarms 2}

adGenEfmNtuSwDownloadFail   NOTIFICATION-TYPE
    OBJECTS         {
                    adTrapInformSeqNum,
                    sysName,
                    adGenSlotInfoIndex,
                    adGenEfmNtuProvCustId,
                    adGenEfmNtuProvSwDownloadStatus
                    }
    STATUS          current
    DESCRIPTION
                    "NTU Software Download Failed"
    --#TYPE         "Info - NTU Software Download Failed"
    --#SUMMARY      "NTU Software Download Failed "
    --#SUMMARY      "detected at shelf: %s, slot: %d and customer: %s"
    --#ARGUMENTS    {1,2,3}
    --#SEVERITY     "ALERT"
    --#GENERIC      6
    --#CATEGORY     "Info Events"
    --#SOURCE_ID    "A"
    --#TIMEINDEX    0
    ::= {adGenEfmNtuAlarms 3}

adGenEfmNtuCorruptConfiguration   NOTIFICATION-TYPE
    OBJECTS         {
                    adTrapInformSeqNum,
                    sysName,
                    adGenSlotInfoIndex,
                    adGenEfmNtuProvCustId
                    }
    STATUS          current
    DESCRIPTION
                    "NTU Corrupt Configuration"
    --#TYPE         "Info - NTU Corrupt Configuration"
    --#SUMMARY      "NTU Corrupt Configuration "
    --#SUMMARY      "detected at shelf: %s, slot: %d and customer: %s"
    --#ARGUMENTS    {1,2,3}
    --#SEVERITY     "ALERT"
    --#GENERIC      6
    --#CATEGORY     "Info Events"
    --#SOURCE_ID    "A"
    --#TIMEINDEX    0
    ::= {adGenEfmNtuAlarms 4}

adGenEfmNtuMACTableExhaust   NOTIFICATION-TYPE
    OBJECTS         {
                    adTrapInformSeqNum,
                    sysName,
                    adGenSlotInfoIndex,
                    adGenEfmNtuProvCustId
                    }
    STATUS          current
    DESCRIPTION
                    "NTU MAC Table Exhausted"
    --#TYPE         "Info - NTU MAC Table Exhausted"
    --#SUMMARY      "NTU MAC Table Exhausted "
    --#SUMMARY      "detected at shelf: %s, slot: %d and customer: %s"
    --#ARGUMENTS    {1,2,3}
    --#SEVERITY     "ALERT"
    --#GENERIC      6
    --#CATEGORY     "Info Events"
    --#SOURCE_ID    "A"
    --#TIMEINDEX    0
    ::= {adGenEfmNtuAlarms 5}



adGenEfmNtuCustIfDownClr   NOTIFICATION-TYPE
    OBJECTS         {
                    adTrapInformSeqNum,
                    sysName,
                    adGenSlotInfoIndex,
                    adGenEfmNtuProvCustId
                    }
    STATUS          current
    DESCRIPTION
                    "Customer Interface Down - Cleared"
    --#TYPE         "Major - Customer Interface Down - Cleared"
    --#SUMMARY      "Customer Interface Down - Cleared "
    --#SUMMARY      "cleared at shelf: %s, slot: %d and customer: %s"
    --#ARGUMENTS    {1,2,3}
    --#SEVERITY     "MAJOR"
    --#GENERIC      6
    --#CATEGORY     "Alarm Events"
    --#SOURCE_ID    "A"
    --#TIMEINDEX    0
    ::= {adGenEfmNtuAlarms 10}

adGenEfmNtuCustIfDownAct   NOTIFICATION-TYPE
    OBJECTS         {
                    adTrapInformSeqNum,
                    sysName,
                    adGenSlotInfoIndex,
                    adGenEfmNtuProvCustId
                    }
    STATUS          current
    DESCRIPTION
                    "Customer Interface Down - Active"
    --#TYPE         "Major - Customer Interface Down - Active"
    --#SUMMARY      "Customer Interface Down - Active "
    --#SUMMARY      "detected at shelf: %s, slot: %d and customer: %s"
    --#ARGUMENTS    {1,2,3}
    --#SEVERITY     "MAJOR"
    --#GENERIC      6
    --#CATEGORY     "Alarm Events"
    --#SOURCE_ID    "A"
    --#TIMEINDEX    0
    ::= {adGenEfmNtuAlarms 11}

adGenEfmNtuAutoDiscover   NOTIFICATION-TYPE
    OBJECTS         {
                    adTrapInformSeqNum,
                    sysName,
                    adGenSlotInfoIndex,
                    ifDescr,
                    ifIndex
                    }
    STATUS          current
    DESCRIPTION
                    "NTU Discovery"
    --#TYPE         "Info - NTU Discovery
    --#SUMMARY      "NTU Discovery "
    --#SUMMARY      "detected at shelf: %s, slot: %d and customer: %s"
    --#ARGUMENTS    {1,2,3}
    --#SEVERITY     "INFORMATIONAL"
    --#GENERIC      6
    --#CATEGORY     "Info Events"
    --#SOURCE_ID    "A"
    --#TIMEINDEX    0
    ::= {adGenEfmNtuAlarms 12}

-- ******************************************************************************************

END
