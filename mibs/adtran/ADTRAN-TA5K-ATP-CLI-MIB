ADTRAN-TA5K-ATP-CLI-MIB

    DEFINITIONS ::= BEGIN

    -- TITLE:     The ADTRAN Total Access TA5000 ATP CLI MIB
    -- PRODUCT:   All complex modules and SM
    -- VERSION:   1.0
    -- DATE:      Cinco de Mayo, 2006

    -- This MIB Contains tables specific to the TA5000 to allow ATP to access the CLI via SNMP
    --

    -- MIBs supported:

    -- HISTORY:
    --     04/18/06 tpm First edition


    IMPORTS
        MODULE-IDENTITY,
        OBJECT-TYPE,
        Integer32
            FROM SNMPv2-SMI

        DisplayString,
        TEXTUAL-CONVENTION
            FROM SNMPv2-TC

        adIdentity,
        adIdentityShared,
        adProducts,
        adMgmt
            FROM ADTRAN-MIB

        adGenTa5kAtpCli,
        adGenTa5kAtpCliID
            FROM ADTRAN-GENTA5K-MIB

        adGenSlotInfoIndex
            FROM ADTRAN-GENSLOT-MIB;

-- *********************************************************************************************************

    adTa5kAtpCliModuleIdentity MODULE-IDENTITY
        LAST-UPDATED "200605050832Z"
        ORGANIZATION
            "ADTRAN, Inc."
        CONTACT-INFO
            "CND Tech Support
                Postal: ADTRAN, Inc.
                        901 Explorer Blvd.
                        Huntsville, AL  35806
                        Tel: +1 800 726-8663
                        Fax: +1 256 963 6217
                        E-mail: support@adtran.com"
        DESCRIPTION
            "Total Access 5000 AtpCli MIB"
        ::= { adGenTa5kAtpCliID 1 }

-- OBJECT IDENTIFIERS

    adTa5kAtpCliTable OBJECT-TYPE
       SYNTAX      SEQUENCE OF AdTa5kAtpCliEntry
       MAX-ACCESS  not-accessible
       STATUS      current
       DESCRIPTION
           "..."
       ::= { adGenTa5kAtpCli 1 }

    adTa5kAtpCliEntry OBJECT-TYPE
       SYNTAX      AdTa5kAtpCliEntry
       MAX-ACCESS  not-accessible
       STATUS      current
       DESCRIPTION
           "..."
       INDEX { adGenSlotInfoIndex }
       ::= { adTa5kAtpCliTable 1 }

   AdTa5kAtpCliEntry ::=
       SEQUENCE {
           adTa5kAtpCliCommand                                     DisplayString
       }

   adTa5kAtpCliCommand          OBJECT-TYPE
       SYNTAX                    DisplayString
       MAX-ACCESS                read-write
       STATUS                    current
       DESCRIPTION
           ""
       ::= { adTa5kAtpCliEntry 1 }

   END
