ADTRAN-ERPS-CONTAINER-MIB

  DEFINITIONS ::= BEGIN

  -- TITLE:     Adtran ERPS Container MIB.
  -- DATE:      September 30,2008
  -- AUTHOR:    Siddharth Madiwale
  --
  -- REVISION HISTORY: Date           Comments
  -- 		       09/30/2008     First created

  -- This MIB defines the container MIB for the ERPS MIB

    IMPORTS
        MODULE-IDENTITY
            FROM SNMPv2-SMI
      adShared,
      adIdentityShared,
      adComplianceShared
          FROM ADTRAN-MIB;

     adGenErpsModuleIdentity MODULE-IDENTITY
        LAST-UPDATED "200809301344Z"
        ORGANIZATION
            "ADTRAN, Inc."
        CONTACT-INFO
            "CND Tech Support
                Postal: ADTRAN, Inc.
                        901 Explorer Blvd.
                        Huntsville, AL  35806
                        Tel: +1 800 726-8663
                        Fax: +1 256 963 6217
                        E-mail: support@adtran.com"
        DESCRIPTION
            "Ethernet Ring Protection Switching, Container MIB
	     This MIB is the interface between the main ADTRAN OID tree
             and the ERPS MIB tree."
        ::= { adIdentityShared 79 }


-- OBJECT IDENTIFIERS

  adGenErpsModule                  OBJECT IDENTIFIER ::= { adShared 79  }
  adGenErpsCompliance        OBJECT IDENTIFIER ::= { adComplianceShared 79 }
--  The compliance part of this MIB is optional but available.
--  As of 09/30/2008 the identity part is been defined as above in MODULE-IDENTITY.
--  The compliance part is  defined as in the above line but never used.


-- ERPS OID top level definitions
  adGenErps            OBJECT IDENTIFIER ::= { adGenErpsModule 1  }
  adGenErpsID          OBJECT IDENTIFIER ::= { adGenErpsModuleIdentity   1  }
  --  adGenErps...Compliance  OBJECT IDENTIFIER ::= { adGenErpsCompliance   1  }

-- Follow this scheme for additional MIBs with 2, 3, 4...

-- Next

  END
