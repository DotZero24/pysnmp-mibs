-- SOCOMEC SICON MIB
-- MIB for Intelligent Power Management
--
-- { iso org(3) dod(6) internet(1) private(4) enterprises(1) socomecSicon(4555)
-- product(1) pduAgent(1) iPDU(20)
-- ==============================================================================================
---
---     Revision History
---
---     v0.80a1   02-Apr-2012     Brian Chen/socomecSicon
---                             Created
---
---     v0.80a2   07-Jan-2013     Brian Chen/Ingrasys
---                               Modified trap group
---                               Modified EMD trap issue.
---
SOCOMECIPDU-MIB DEFINITIONS ::= BEGIN

IMPORTS
  enterprises
    FROM RFC1155-SMI
  OBJECT-TYPE
    FROM RFC-1212
  DisplayString
    FROM RFC1213-MIB
  TRAP-TYPE
    FROM RFC-1215;

socomecSicon            OBJECT IDENTIFIER ::= { enterprises 4555 }
product                 OBJECT IDENTIFIER ::= { socomecSicon 1 }
pduAgent                OBJECT IDENTIFIER ::= { product 1 }
iPDU                    OBJECT IDENTIFIER ::= { pduAgent  20 }
ipduObjects          OBJECT IDENTIFIER ::= { iPDU 1 }
ipduTraps            OBJECT IDENTIFIER ::= { iPDU 2 }

ipduIdent            OBJECT IDENTIFIER ::= { ipduObjects 1 }
ipduAgent            OBJECT IDENTIFIER ::= { ipduObjects 2 }
ipduDevice           OBJECT IDENTIFIER ::= { ipduObjects 3 }
ipduSlave            OBJECT IDENTIFIER ::= { ipduObjects 4 }
ipduEnv              OBJECT IDENTIFIER ::= { ipduObjects 5 }

-- ===========================================================================
--
-- ipduIdent
--
--  iPDU Identification Group
--
-- ===========================================================================
ipduIdentManufacturer OBJECT-TYPE
       SYNTAX DisplayString (SIZE (0..31))
       ACCESS read-write
       STATUS mandatory
       DESCRIPTION
               "The name of manufacturer."
       ::= { ipduIdent 1 }

ipduIdentModel OBJECT-TYPE
      SYNTAX DisplayString (SIZE (0..31))
      ACCESS read-write
      STATUS mandatory
      DESCRIPTION
          "The Model designation of device."
      ::= { ipduIdent 2 }

ipduIdentAgentSoftwareVersion OBJECT-TYPE
       SYNTAX DisplayString (SIZE (0..63))
       ACCESS read-only
       STATUS mandatory
       DESCRIPTION
               "The firmware version of the device."
      ::= { ipduIdent 3 }

ipduIdentName OBJECT-TYPE
      SYNTAX DisplayString (SIZE(0..31))
      ACCESS read-write
      STATUS mandatory
      DESCRIPTION
               "A description of this device."
      ::= { ipduIdent 4 }

ipduAgentConfig    OBJECT IDENTIFIER ::= { ipduAgent 1 }
-- ===========================================================================
--
-- ipduConfig
--
--  iPDU Configuration Group, configure the secific features of iPDU
--
-- ===========================================================================
ipduAgentMibVersion OBJECT-TYPE
        SYNTAX INTEGER (1..65500) --
        ACCESS read-only
        STATUS mandatory
        DESCRIPTION
                "The Mib Version implemented on this device."
        ::= { ipduAgentConfig 1 }

ipduAgentTime    OBJECT IDENTIFIER ::= { ipduAgent 2 }
-- ===========================================================================
--
-- ipduConfigTime
--
--  Date/Time Configuration Group of the device.
--
-- ===========================================================================
ipduAgentTimeDate OBJECT-TYPE
        SYNTAX DisplayString (SIZE (10..10))
        ACCESS read-write
        STATUS mandatory
        DESCRIPTION
                "The date in agent, format is (dd/mm/yyyy)"
        ::= { ipduAgentTime 1 }

ipduAgentTimeTime OBJECT-TYPE
        SYNTAX DisplayString (SIZE (8..8))
        ACCESS read-write
        STATUS mandatory
        DESCRIPTION
                "The time in agent, format is (hh:mm:ss)"
        ::= { ipduAgentTime 2 }

ipduAgentTimerFromNtp OBJECT-TYPE
        SYNTAX  INTEGER {
                enabled(1),
                disabled(2)
                }
        ACCESS read-write
        STATUS mandatory
        DESCRIPTION
                "Enable or disable the agent to synchronize date/time with NTP server."
        ::= { ipduAgentTime 3 }

ipduAgentNtpIpAddress OBJECT-TYPE
       SYNTAX IpAddress
       ACCESS read-write
       STATUS mandatory
       DESCRIPTION
               "The ip address of NTP server."
       ::= { ipduAgentTime 4 }

ipduAgentNtpTimeZone OBJECT-TYPE
        SYNTAX  INTEGER {
                    gMT-1200(1),
                    gMT-1100(2),
                    gMT-1000(3),
                    gMT-0900(4),
                    gMT-0800(5),
                    gMT-0700(6),
                    gMT-0600(7),
                    gMT-0500(8),
                    gMT-0400(9),
                    gMT-0330(10),
                    gMT-0300(11),
                    gMT-0200(12),
                    gMT-0100(13),
                    gMT-0000(14),
                    gMT0100(15),
                    gMT0200(16),
                    gMT0300(17),
                    gMT0330(18),
                    gMT0400(19),
                    gMT0500(20),
                    gMT0530(21),
                    gMT0600(22),
                    gMT0700(23),
                    gMT0800(24),
                    gMT0900(25),
                    gMT1000(26),
                    gMT1100(27),
                    gMT1200(28)
                }
        ACCESS read-write
        STATUS mandatory
        DESCRIPTION
                "Time Zone to use when synchronize with NTP server."
        ::= { ipduAgentTime 5 }

ipduAgentDayLightSaving OBJECT-TYPE
        SYNTAX  INTEGER {
                enabled(1),
                disabled(2)
                }
        ACCESS read-write
        STATUS mandatory
        DESCRIPTION
                "Enable/disable the Day Light Saving when synchronize with NTP server."
        ::= { ipduAgentTime 6 }

ipduAgentNetwork    OBJECT IDENTIFIER ::= { ipduAgent 3 }
-- ===========================================================================
--
-- ipduConfigNetwork
--
--  Network Configuration Group of the device.
--
-- ===========================================================================

ipduAgentNetworkIp    OBJECT IDENTIFIER ::= { ipduAgentNetwork 1 }
-- ===========================================================================
--
-- ipduAgentNetworkIp
--
--  Ip address Configuration Group of the device.
--
-- ===========================================================================
ipduAgentNetworkIpAdress OBJECT-TYPE
        SYNTAX IpAddress
        ACCESS read-write
        STATUS mandatory
        DESCRIPTION
                "The ip address that NMS can identify the managed device."
        ::= { ipduAgentNetworkIp 1}

ipduAgentNetworkIpGateway OBJECT-TYPE
        SYNTAX IpAddress
        ACCESS read-write
        STATUS mandatory
        DESCRIPTION
                "The default gateway that allow device managed through routers."
        ::= { ipduAgentNetworkIp 2}

ipduAgentNetworkIpSubnet OBJECT-TYPE
        SYNTAX IpAddress
        ACCESS read-write
        STATUS mandatory
        DESCRIPTION
                "Internet address subnet mask"
        ::= { ipduAgentNetworkIp 3}

ipduAgentNetworkDhcpControl OBJECT-TYPE
        SYNTAX  INTEGER {
                enabled(1),
                disabled(2)
                }
        ACCESS read-write
        STATUS mandatory
        DESCRIPTION
                "Enable/disable DHCP protocol"
        ::= { ipduAgentNetwork 2 }

ipduAgentNetworkPingControl OBJECT-TYPE
        SYNTAX  INTEGER {
                enabled(1),
                disabled(2)
                }
        ACCESS read-write
        STATUS mandatory
        DESCRIPTION
                "Enable/disable to response to PING request."
        ::= { ipduAgentNetwork 3 }

ipduAgentNetworkTftpControl OBJECT-TYPE
        SYNTAX  INTEGER {
                enabled(1),
                disabled(2)
                }
        ACCESS read-write
        STATUS mandatory
        DESCRIPTION
                "Enable/disable TFTP protocol"
        ::= { ipduAgentNetwork 4 }

ipduAgentNetworkTelnet    OBJECT IDENTIFIER ::= { ipduAgentNetwork 5 }
-- ===========================================================================
--
-- ipduConfigNetworkTelnet
--
--  Telnet Configuration Group of the device.
--
-- ===========================================================================
ipduAgentTelnetControl OBJECT-TYPE
        SYNTAX  INTEGER {
                enabled(1),
                disabled(2)
                }
        ACCESS read-write
        STATUS mandatory
        DESCRIPTION
                "Enable/disable Telnet protocol."
        ::= { ipduAgentNetworkTelnet 1 }

ipduAgentTelnetPort OBJECT-TYPE
        SYNTAX INTEGER
        ACCESS read-write
        STATUS mandatory
        DESCRIPTION
                "The TCP port for telnet"
        ::= { ipduAgentNetworkTelnet 2}

ipduAgentNetworkHttp    OBJECT IDENTIFIER ::= { ipduAgentNetwork 6 }
-- ===========================================================================
--
-- ipduConfigNetworkHttp
--
--  HTTP Configuration Group of the device.
--
-- ===========================================================================
ipduAgentHttpControl OBJECT-TYPE
        SYNTAX  INTEGER {
                enabled(1),
                disabled(2)
                }
        ACCESS read-write
        STATUS mandatory
        DESCRIPTION
                "Enable/disable HTTP protocol."
        ::= { ipduAgentNetworkHttp 1 }

ipduAgentHttpPort OBJECT-TYPE
        SYNTAX INTEGER
        ACCESS read-write
        STATUS mandatory
        DESCRIPTION
                "The TCP port for HTTP."
        ::= { ipduAgentNetworkHttp 2}

ipduAgentNetworkSnmp    OBJECT IDENTIFIER ::= { ipduAgentNetwork 7 }
-- ===========================================================================
--
-- ipduAgentNetworkSnmp
--
--  SNMP Configuration Group of the device.
--
-- ===========================================================================
ipduAgentSnmpControl OBJECT-TYPE
        SYNTAX  INTEGER {
                enabled(1),
                disabled(2)
                }
        ACCESS read-write
        STATUS mandatory
        DESCRIPTION
                "Enable/disable SNMP protocol."
        ::= { ipduAgentNetworkSnmp 1 }

ipduAgentSnmpPort OBJECT-TYPE
        SYNTAX INTEGER
        ACCESS read-write
        STATUS mandatory
        DESCRIPTION
                "The UDP port for SNMP."
        ::= { ipduAgentNetworkSnmp 2}

ipduAgentLog    OBJECT IDENTIFIER ::= { ipduAgentConfig 4 }
-- ===========================================================================
--
-- ipduConfigLog
--
--  Log Configuration Group of the device.
--
-- ===========================================================================
pduAgentDataLogInterval OBJECT-TYPE
        SYNTAX INTEGER (60..28800) -- in seconds
        ACCESS read-write
        STATUS mandatory
        DESCRIPTION
                "The interval of the updation of the data log. The value
                 is in seconds"
        ::= { ipduAgentLog 1 }

ipduAgentControl    OBJECT IDENTIFIER ::= { ipduAgentConfig 5 }
-- ===========================================================================
--
-- ipduAgentAgentControl
--
--  Agent Control Configuration Group of the device.
--
-- ===========================================================================
ipduAgentControlDefault OBJECT-TYPE
        SYNTAX  INTEGER {
                reset(1),
                nothing(2)
                }
        ACCESS read-write
        STATUS mandatory
        DESCRIPTION
                "Reset all parameters of the agent to default value."
        ::= { ipduAgentControl 1}

ipduAgentControlRestart OBJECT-TYPE
        SYNTAX  INTEGER {
                restart(1),
                nothing(2)
                }
        ACCESS read-write
        STATUS mandatory
        DESCRIPTION
                "Restart the agent."
        ::= { ipduAgentControl 2}

ipduAgentTrap    OBJECT IDENTIFIER ::= { ipduAgentConfig 6 }
-- ===========================================================================
--
-- ipduAgentTrap
--
--  Trap Configuration Group of the agent.
--
-- ===========================================================================
ipduAgentTrapRetryCount OBJECT-TYPE
        SYNTAX  INTEGER
        ACCESS read-write
        STATUS mandatory
        DESCRIPTION
                "The count of repeat traps send to NMS before trap
                 acknowledgement received."
        ::= { ipduAgentTrap 1}

ipduAgentTrapRetryTime OBJECT-TYPE
        SYNTAX  INTEGER
        ACCESS read-write
        STATUS mandatory
        DESCRIPTION
                "The time interval in seconds between retry traps sned to NMS."
        ::= { ipduAgentTrap 2}

ipduAgentTrapAckSignature OBJECT-TYPE
        SYNTAX  INTEGER
        ACCESS read-write
        STATUS mandatory
        DESCRIPTION
                "The signature of trap acknowledgement."
        ::= { ipduAgentTrap 3}


-- ===========================================================================
--
-- ipduAgentTrapsReceiversTable
--
-- ===========================================================================

ipduAgentTrapsReceiversTable OBJECT-TYPE
        SYNTAX SEQUENCE OF IpduAgentTrapsReceiversEntry
        ACCESS not-accessible
        STATUS mandatory
        DESCRIPTION
                "A list of managers to send traps to.  The number of
                 entries is given by the value of agentConfigNumTrapReceivers"
        ::= { ipduAgentConfig 7}

ipduAgentTrapsReceiversEntry OBJECT-TYPE
        SYNTAX IpduAgentTrapsReceiversEntry
        ACCESS not-accessible
        STATUS mandatory
        DESCRIPTION
                "The managers to send traps to."
        INDEX  { trapsIndex }
        ::= { ipduAgentTrapsReceiversTable 1 }

IpduAgentTrapsReceiversEntry ::=
        SEQUENCE {
                trapsIndex              INTEGER,
                trapsReceiverAddr       IpAddress,
                receiverCommunityString DisplayString,
                receiverNmsType         INTEGER,
                receiverSeverityLevel   INTEGER,
                receiverDescription     DisplayString
        }

trapsIndex OBJECT-TYPE
        SYNTAX INTEGER (0..65535)
        ACCESS read-only
        STATUS mandatory
        DESCRIPTION
                "The index to a trap receiver entry."
        ::= { ipduAgentTrapsReceiversEntry 1 }

trapsReceiverAddr OBJECT-TYPE
        SYNTAX IpAddress
        ACCESS read-write
        STATUS mandatory
        DESCRIPTION
                "The IP address of the manager to send a trap to."
        ::= { ipduAgentTrapsReceiversEntry 2 }

receiverCommunityString OBJECT-TYPE
        SYNTAX DisplayString (SIZE(0..15))
        ACCESS read-write
        STATUS mandatory
        DESCRIPTION
                "The community name to use in the trap when
                 sent to the manager."
        ::= { ipduAgentTrapsReceiversEntry 3 }

receiverNmsType OBJECT-TYPE
        SYNTAX  INTEGER {
                none(1),
                iPDU-trap(2)
                }
        ACCESS read-write
        STATUS mandatory
        DESCRIPTION
                "The trap group that NMS desired."
        ::= { ipduAgentTrapsReceiversEntry 4 }

receiverSeverityLevel OBJECT-TYPE
        SYNTAX  INTEGER {
                informational(1),
                warning(2),
                severe(3)
                }
        ACCESS read-write
        STATUS mandatory
        DESCRIPTION
                "The severity level of traps to be received by this manager."
        ::= { ipduAgentTrapsReceiversEntry 5 }

receiverDescription OBJECT-TYPE
        SYNTAX DisplayString (SIZE(0..31))
        ACCESS read-write
        STATUS mandatory
        DESCRIPTION
                "Description of trap receivers"
        ::= { ipduAgentTrapsReceiversEntry 6 }


-- ===========================================================================
--
-- ipduAgentAccessControlTable
--
-- ===========================================================================
ipduAgentAccessControlTable OBJECT-TYPE
        SYNTAX SEQUENCE OF IpduAgentAccessControlEntry
        ACCESS not-accessible
        STATUS mandatory
        DESCRIPTION
                "A list of managers which can access the device with private
                community string."
        ::= { ipduAgentConfig 8}

ipduAgentAccessControlEntry OBJECT-TYPE
        SYNTAX IpduAgentAccessControlEntry
        ACCESS not-accessible
        STATUS mandatory
        DESCRIPTION
                "The managers."
        INDEX  { accessIndex}
        ::= { ipduAgentAccessControlTable 1 }

IpduAgentAccessControlEntry ::=
        SEQUENCE {
                accessIndex
                        INTEGER,
                accessControlAddr
                        IpAddress,
                accessControlMode
                        INTEGER
        }

accessIndex OBJECT-TYPE
        SYNTAX INTEGER (0..65535)
        ACCESS read-only
        STATUS mandatory
        DESCRIPTION
                "The index to a access control entry."
        ::= { ipduAgentAccessControlEntry 1 }

accessControlAddr OBJECT-TYPE
        SYNTAX IpAddress
        ACCESS read-write
        STATUS mandatory
        DESCRIPTION
                "The IP address of the manager to access the device."
        ::= { ipduAgentAccessControlEntry 2 }

accessControlMode OBJECT-TYPE
        SYNTAX  INTEGER {
                permitted (1),
                denied (2)
                }
        ACCESS read-write
        STATUS mandatory
        DESCRIPTION
                "Access type, only read/Write access type can change parameter
                 of the device."
        ::= { ipduAgentAccessControlEntry 3 }

ipduDeviceInlet      OBJECT IDENTIFIER ::= { ipduDevice 1 }
-- ===========================================================================
--
-- ipduDeviceInlet
--
--  Inlet  Group
--
-- ===========================================================================
ipduDeviceInletNumber OBJECT-TYPE
        SYNTAX  INTEGER
        ACCESS read-only
        STATUS mandatory
        DESCRIPTION
                "The inlet number on this device."
        ::= { ipduDeviceInlet 1}

ipduDeviceInletConfigTable OBJECT-TYPE
        SYNTAX SEQUENCE OF IpduDeviceInletConfigEntry
        ACCESS not-accessible
        STATUS mandatory
        DESCRIPTION
                "A list of inlet on this device."
        ::= { ipduDeviceInlet 2}

ipduDeviceInletConfigEntry OBJECT-TYPE
        SYNTAX IpduDeviceInletConfigEntry
        ACCESS not-accessible
        STATUS mandatory
        DESCRIPTION
                "The inlet number of device."
        INDEX  { inletConfigIndex}
        ::= { ipduDeviceInletConfigTable 1 }

IpduDeviceInletConfigEntry ::=
        SEQUENCE {
                inletConfigIndex
                        INTEGER,
                inletConfigDesc
                        DisplayString,
                inletConfigVoltageHigh
                        INTEGER,
                inletConfigVoltageHighAction
                        INTEGER,
                inletConfigVoltageLow
                        INTEGER,
                inletConfigVoltageLowAction
                        INTEGER,
                inletConfigCurrentHigh
                        INTEGER,
                inletConfigCurrentHighAction
                        INTEGER,
                inletConfigFrequencyHigh
                        INTEGER,
                inletConfigfrequencyHighAction
                        INTEGER,
                inletConfigFrequencyLow
                        INTEGER,
                inletConfigfrequencyLowAction
                        INTEGER
        }

inletConfigIndex OBJECT-TYPE
        SYNTAX INTEGER (0..65535)
        ACCESS read-only
        STATUS mandatory
        DESCRIPTION
                "The index to a access inlet configuration table."
        ::= { ipduDeviceInletConfigEntry 1 }

inletConfigDesc OBJECT-TYPE
        SYNTAX DisplayString (SIZE(0..31))
        ACCESS read-write
        STATUS mandatory
        DESCRIPTION
                "A Description of inlet of device."
        ::= { ipduDeviceInletConfigEntry 2 }

inletConfigVoltageHigh OBJECT-TYPE
        SYNTAX INTEGER (1..65500) --
        ACCESS read-write
        STATUS mandatory
        DESCRIPTION
                "The Inlet high voltage threshold, in volts."
        ::= { ipduDeviceInletConfigEntry 3 }

inletConfigVoltageHighAction OBJECT-TYPE
        SYNTAX  INTEGER {
                outletsOff (1),
                nothing (2)
                }
        ACCESS read-write
        STATUS mandatory
        DESCRIPTION
                "Reaction of the device when inlet voltage higher than set point."
        ::= { ipduDeviceInletConfigEntry 4 }

inletConfigVoltageLow OBJECT-TYPE
        SYNTAX INTEGER (1..65500) --
        ACCESS read-write
        STATUS mandatory
        DESCRIPTION
                "The Inlet low voltage threshold, in volts."
        ::= { ipduDeviceInletConfigEntry 5 }

inletConfigVoltageLowAction OBJECT-TYPE
        SYNTAX  INTEGER {
                outletsOff (1),
                nothing (2)
                }
        ACCESS read-write
        STATUS mandatory
        DESCRIPTION
                "Reaction of the device when inlet voltage lower than set point."
        ::= { ipduDeviceInletConfigEntry 6 }

inletConfigCurrentHigh OBJECT-TYPE
        SYNTAX INTEGER (1..160) --
        ACCESS read-write
        STATUS mandatory
        DESCRIPTION
                "The Inlet low voltage threshold, in 0.1 amps."
        ::= { ipduDeviceInletConfigEntry 7 }

inletConfigCurrentHighAction OBJECT-TYPE
        SYNTAX  INTEGER {
                outletsOff (1),
                nothing (2)
                }
        ACCESS read-write
        STATUS mandatory
        DESCRIPTION
                "Reaction of the device when inlet current higher than set point."
        ::= { ipduDeviceInletConfigEntry 8 }

inletConfigFrequencyHigh OBJECT-TYPE
        SYNTAX INTEGER (1..65500) --
        ACCESS read-write
        STATUS mandatory
        DESCRIPTION
                "The Inlet high frequency threshold, in hz."
        ::= { ipduDeviceInletConfigEntry 9 }

inletConfigfrequencyHighAction OBJECT-TYPE
        SYNTAX  INTEGER {
                outletsOff (1),
                nothing (2)
                }
        ACCESS read-write
        STATUS mandatory
        DESCRIPTION
                "Reaction of the device when inlet frequency higher than set point."
        ::= { ipduDeviceInletConfigEntry 10 }

inletConfigFrequencyLow OBJECT-TYPE
        SYNTAX INTEGER (1..65500) --
        ACCESS read-write
        STATUS mandatory
        DESCRIPTION
                "The Inlet low frequency threshold, in hz."
        ::= { ipduDeviceInletConfigEntry 11 }

inletConfigfrequencyLowAction OBJECT-TYPE
        SYNTAX  INTEGER {
                outletsOff (1),
                nothing (2)
                }
        ACCESS read-write
        STATUS mandatory
        DESCRIPTION
                "Reaction of the device when inlet frequency lower than set point."
        ::= { ipduDeviceInletConfigEntry 12 }

ipduDeviceInletStatusTable OBJECT-TYPE
        SYNTAX SEQUENCE OF IpduDeviceInletStatusEntry
        ACCESS not-accessible
        STATUS mandatory
        DESCRIPTION
                "A list of inlet on this device."
        ::= { ipduDeviceInlet 3}

ipduDeviceInletStatusEntry OBJECT-TYPE
        SYNTAX IpduDeviceInletStatusEntry
        ACCESS not-accessible
        STATUS mandatory
        DESCRIPTION
                "The inlet number of device."
        INDEX  { inletStatusIndex}
        ::= { ipduDeviceInletStatusTable 1 }

IpduDeviceInletStatusEntry ::=
        SEQUENCE {
                inletStatusIndex
                        INTEGER,
                inletStatusVoltage
                        INTEGER,
                inletStatusCurrent
                        INTEGER,
                inletStatusFrequency
                        INTEGER,
                inletStatusKwatt
                        INTEGER,
                inletStatusWH
                        INTEGER
        }

inletStatusIndex OBJECT-TYPE
        SYNTAX INTEGER (0..65535)
        ACCESS read-only
        STATUS mandatory
        DESCRIPTION
                "The index to a access inlet configuration table."
        ::= { ipduDeviceInletStatusEntry 1 }

inletStatusVoltage OBJECT-TYPE
        SYNTAX INTEGER (1..65500) --
        ACCESS read-only
        STATUS mandatory
        DESCRIPTION
                "The Inlet Voltage in 0.1 volts"
        ::= { ipduDeviceInletStatusEntry 2 }

inletStatusCurrent OBJECT-TYPE
        SYNTAX INTEGER (0..65500) --
        ACCESS read-only
        STATUS mandatory
        DESCRIPTION
                "The Inlet Current in 0.001 Amp."
        ::= { ipduDeviceInletStatusEntry 3 }

inletStatusFrequency OBJECT-TYPE
        SYNTAX INTEGER (1..65500) --
        ACCESS read-only
        STATUS mandatory
        DESCRIPTION
                "The Inlet Frequency in 0.1 Hz"
        ::= { ipduDeviceInletStatusEntry 4 }

inletStatusKwatt OBJECT-TYPE
        SYNTAX INTEGER (0..65500) --
        ACCESS read-only
        STATUS mandatory
        DESCRIPTION
                "The Inlet Kwatt in 0.1 KW/H"
        ::= { ipduDeviceInletStatusEntry 5 }

inletStatusWH OBJECT-TYPE
        SYNTAX INTEGER (1..65500) --
        ACCESS read-only
        STATUS mandatory
        DESCRIPTION
                "The Inlet Kwatt in 0.1 W/H"
        ::= { ipduDeviceInletStatusEntry 6 }


inletWattReset OBJECT-TYPE
        SYNTAX INTEGER {
                none(1),
                inlet1(2),
                inlet2(3)
    }
        ACCESS read-write
        STATUS mandatory
        DESCRIPTION
                "Reset inlet kw."
        ::= { ipduDeviceInlet 4}


ipduDeviceOutlet     OBJECT IDENTIFIER ::= { ipduDevice 2 }
-- ===========================================================================
--
-- ipduDeviceOutlet
--
--  Inlet  Group
--
-- ===========================================================================
ipduDeviceOutletNumber OBJECT-TYPE
        SYNTAX  INTEGER
        ACCESS read-only
        STATUS mandatory
        DESCRIPTION
                "The outlet number on this device."
        ::= { ipduDeviceOutlet 1}

ipduDeviceOutletConfigTable OBJECT-TYPE
        SYNTAX SEQUENCE OF IpduDeviceOutletConfigEntry
        ACCESS not-accessible
        STATUS mandatory
        DESCRIPTION
                "A list of outlet on this device."
        ::= { ipduDeviceOutlet 2}

ipduDeviceOutletConfigEntry OBJECT-TYPE
        SYNTAX IpduDeviceOutletConfigEntry
        ACCESS not-accessible
        STATUS mandatory
        DESCRIPTION
                "The inlet number of device."
        INDEX  { inletConfigIndex}
        ::= { ipduDeviceOutletConfigTable 1 }

IpduDeviceOutletConfigEntry ::=
        SEQUENCE {
                outletConfigIndex
                        INTEGER,
                outletConfigDesc
                        DisplayString,
                outletConfigLocation
                        DisplayString,
                outletConfigOnDelay
                        INTEGER,
                outletConfigOffDelay
                        INTEGER,
                outletConfigCurrentHigh
                        INTEGER,
                outletConfigCurrentHighAction
                        INTEGER
         }

outletConfigIndex OBJECT-TYPE
        SYNTAX INTEGER
        ACCESS read-only
        STATUS mandatory
        DESCRIPTION
                "The index to a access inlet configuration table."
        ::= { ipduDeviceOutletConfigEntry 1 }

outletConfigDesc OBJECT-TYPE
        SYNTAX DisplayString (SIZE(0..31))
        ACCESS read-write
        STATUS mandatory
        DESCRIPTION
                "A Description of outlet of device."
        ::= { ipduDeviceOutletConfigEntry 2 }

outletConfigLocation OBJECT-TYPE
        SYNTAX DisplayString (SIZE(0..31))
        ACCESS read-write
        STATUS mandatory
        DESCRIPTION
                "Location of device connectted to this outlet."
        ::= { ipduDeviceOutletConfigEntry 3 }

outletConfigOnDelay OBJECT-TYPE
        SYNTAX INTEGER
        ACCESS read-write
        STATUS mandatory
        DESCRIPTION
                "The delay time before turn on tis outlet, in seconds."
        ::= { ipduDeviceOutletConfigEntry 4 }

outletConfigOffDelay OBJECT-TYPE
        SYNTAX INTEGER
        ACCESS read-write
        STATUS mandatory
        DESCRIPTION
                "The delay time before turn off tis outlet, in seconds."
        ::= { ipduDeviceOutletConfigEntry 5 }

outletConfigCurrentHigh OBJECT-TYPE
        SYNTAX INTEGER (1..65500) --
        ACCESS read-write
        STATUS mandatory
        DESCRIPTION
                "The outlet high current threshold, in amp."
        ::= { ipduDeviceOutletConfigEntry 6 }

outletConfigCurrentHighAction OBJECT-TYPE
        SYNTAX  INTEGER {
                outletOff (1),
                nothing (2)
                }
        ACCESS read-write
        STATUS mandatory
        DESCRIPTION
                "Reaction of the device when outlet current higher than set point."
        ::= { ipduDeviceOutletConfigEntry 7 }



ipduDeviceOutletStatusTable OBJECT-TYPE
        SYNTAX SEQUENCE OF IpduDeviceOutletStatusEntry
        ACCESS not-accessible
        STATUS mandatory
        DESCRIPTION
                "A list of outlet on this device."
        ::= { ipduDeviceOutlet 3}

ipduDeviceOutletStatusEntry OBJECT-TYPE
        SYNTAX IpduDeviceOutletStatusEntry
        ACCESS not-accessible
        STATUS mandatory
        DESCRIPTION
                "The outlet number of device."
        INDEX  { outletStatusIndex}
        ::= { ipduDeviceOutletStatusTable 1 }

IpduDeviceOutletStatusEntry ::=
        SEQUENCE {
                outletStatusIndex
                        INTEGER,
                outletStatusStatus
                        INTEGER,
                outletStatusCurrent
                        INTEGER,
                outletStatusKwatt
                        INTEGER,
                outletStatusWH
                        INTEGER,
                outletStatusStateTime
                        INTEGER,
                outletStatusTimeToGo
                        INTEGER
        }

outletStatusIndex OBJECT-TYPE
        SYNTAX INTEGER (0..65535)
        ACCESS read-only
        STATUS mandatory
        DESCRIPTION
                "The index to a access outlet configuration table."
        ::= { ipduDeviceOutletStatusEntry 1 }

outletStatusStatus OBJECT-TYPE
        SYNTAX  INTEGER {
                unknow (1),
                outletOff (2),
                outletOn (3),
                outletOffToOn (4),
                outletOnToOff (5),
        outletCycling (6)
                }
        ACCESS read-only
        STATUS mandatory
        DESCRIPTION
                "Outlet state"
        ::= { ipduDeviceOutletStatusEntry 2 }

outletStatusCurrent OBJECT-TYPE
        SYNTAX INTEGER (0..65500) --
        ACCESS read-only
        STATUS mandatory
        DESCRIPTION
                "The outlet Current in 0.001 Amp."
        ::= { ipduDeviceOutletStatusEntry 3 }

outletStatusKwatt OBJECT-TYPE
        SYNTAX INTEGER (0..65500) --
        ACCESS read-only
        STATUS mandatory
        DESCRIPTION
                "The outlet Kwatt in 0.001 KW/H."
        ::= { ipduDeviceOutletStatusEntry 4 }

outletStatusWH OBJECT-TYPE
        SYNTAX INTEGER (0..65500) --
        ACCESS read-only
        STATUS mandatory
        DESCRIPTION
                "The outlet Watt in 0.1 W/H."
        ::= { ipduDeviceOutletStatusEntry 5 }

outletStatusStateTime OBJECT-TYPE
        SYNTAX  INTEGER
        ACCESS read-only
        STATUS mandatory
        DESCRIPTION
                "Time in seconds since the outlet changed to current state."
        ::= { ipduDeviceOutletStatusEntry 6 }

outletStatusTimeToGo OBJECT-TYPE
        SYNTAX  INTEGER
        ACCESS read-only
        STATUS mandatory
        DESCRIPTION
                "Remain time the outlet state will be changed by agent, in seconds"
        ::= { ipduDeviceOutletStatusEntry 7 }

ipduDeviceOutletControlTable OBJECT-TYPE
        SYNTAX SEQUENCE OF IpduDeviceOutletControlEntry
        ACCESS not-accessible
        STATUS mandatory
        DESCRIPTION
                "A list of outlet on this device."
        ::= { ipduDeviceOutlet 4}

ipduDeviceOutletControlEntry OBJECT-TYPE
        SYNTAX IpduDeviceOutletControlEntry
        ACCESS not-accessible
        STATUS mandatory
        DESCRIPTION
                "The outlet number of device."
        INDEX  { outletControlIndex}
        ::= { ipduDeviceOutletControlTable 1 }

IpduDeviceOutletControlEntry ::=
        SEQUENCE {
                outletControlIndex
                        INTEGER,
                outletControlControl
                        INTEGER
        }

outletControlIndex OBJECT-TYPE
        SYNTAX INTEGER (0..65535)
        ACCESS read-only
        STATUS mandatory
        DESCRIPTION
                "The index to a access outlet configuration table."
        ::= { ipduDeviceOutletControlEntry 1 }

outletControlControl OBJECT-TYPE
        SYNTAX INTEGER {
        none(1),
                cancelAction(2),
                onImmediately(3),
                offImmediately(4),
                cycleImmediately(5),
                onByActionTimer(6),
                offByActionTimer(7),
                cycleByActionTimer(8),
                onThenOffByActionTimers(9),
                offThenOnByActionTimers(10)
    }
        ACCESS read-write
        STATUS mandatory
        DESCRIPTION
                "Set to control the outlet perform action as requested."
        ::= { ipduDeviceOutletControlEntry 2 }

ipduDeviceOutletControlAll OBJECT-TYPE
        SYNTAX INTEGER {
        none(1),
                cancelAction(2),
                onImmediately(3),
                offImmediately(4),
                cycleImmediately(5),
                onByActionTimers(6),
                offByActionTimers(7),
                cycleByActionTimers(8),
                onThenOffByActionTimers(9),
                offThenOnByActionTimers(10)
    }
        ACCESS read-write
        STATUS mandatory
        DESCRIPTION
                "Set to control all outlets perform action as requested."
        ::= { ipduDeviceOutlet 5}

ipduDeviceOutletWattReset OBJECT-TYPE
        SYNTAX INTEGER {
                none(1),
                outleta(2),
                outletb(3),
                outletc(4),
                outletd(5),
                outlete(6),
                outletf(7),

                outletg(8),
                outleth(9),
                outleti(10),
                outletj(11),
                outletk(12),
                outletl(13)
    }
        ACCESS read-write
        STATUS mandatory
        DESCRIPTION
                "Reset outlet kw."
        ::= { ipduDeviceOutlet 6}


ipduDeviceCcOut      OBJECT IDENTIFIER ::= { ipduDevice 3 }
-- ===========================================================================
--
-- ipduDeviceCCOut
--
--  Contact Closure Output Group
--
-- ===========================================================================
ipduDeviceCcOutNumber OBJECT-TYPE
        SYNTAX  INTEGER
        ACCESS read-only
        STATUS mandatory
        DESCRIPTION
                "The contact closure output number on this device."
        ::= { ipduDeviceCcOut 1}

ipduDeviceCcOutConfigTable OBJECT-TYPE
        SYNTAX SEQUENCE OF IpduDeviceCcOutConfigEntry
        ACCESS not-accessible
        STATUS mandatory
        DESCRIPTION
                "A list of contact closure output on this device."
        ::= { ipduDeviceCcOut 2}

ipduDeviceCcOutConfigEntry OBJECT-TYPE
        SYNTAX IpduDeviceCcOutConfigEntry
        ACCESS not-accessible
        STATUS mandatory
        DESCRIPTION
                "The CC number of device."
        INDEX  { ccOutConfigIndex}
        ::= { ipduDeviceCcOutConfigTable 1 }

IpduDeviceCcOutConfigEntry ::=
        SEQUENCE {
                ccOutConfigIndex
                        INTEGER,
                ccOutConfigDesc
                        DisplayString,
                ccOutConfigEventAction
                        INTEGER,
                ccOutConfigCloseDelay
                        INTEGER,
                ccOutConfigOpenDelay
                        INTEGER
         }

ccOutConfigIndex OBJECT-TYPE
        SYNTAX INTEGER (0..65535)
        ACCESS read-only
        STATUS mandatory
        DESCRIPTION
                "The index to access contact closure output configuration table."
        ::= { ipduDeviceCcOutConfigEntry 1 }

ccOutConfigDesc OBJECT-TYPE
        SYNTAX DisplayString (SIZE(0..31))
        ACCESS read-write
        STATUS mandatory
        DESCRIPTION
                "A Description of a contact closure output of device."
        ::= { ipduDeviceCcOutConfigEntry 2 }

ccOutConfigEventAction OBJECT-TYPE
        SYNTAX INTEGER {
        yes (1),
        no (2)
    }
        ACCESS read-write
        STATUS mandatory
        DESCRIPTION
                "Enable/disble the contact closure output to react to events."
        ::= { ipduDeviceCcOutConfigEntry 3 }

ccOutConfigCloseDelay OBJECT-TYPE
        SYNTAX INTEGER
        ACCESS read-write
        STATUS mandatory
        DESCRIPTION
                "The delay time in seconds when the contact closure output set to close."
        ::= { ipduDeviceCcOutConfigEntry 4 }

ccOutConfigOpenDelay OBJECT-TYPE
        SYNTAX INTEGER
        ACCESS read-write
        STATUS mandatory
        DESCRIPTION
                "The delay time in seconds when the contact closure output set to open."
        ::= { ipduDeviceCcOutConfigEntry 5 }

ipduDeviceCcOutStatusTable OBJECT-TYPE
        SYNTAX SEQUENCE OF IpduDeviceCcOutStatusEntry
        ACCESS not-accessible
        STATUS mandatory
        DESCRIPTION
                "A list of contact closure output on this device."
        ::= { ipduDeviceCcOut 3}

ipduDeviceCcOutStatusEntry OBJECT-TYPE
        SYNTAX IpduDeviceCcOutStatusEntry
        ACCESS not-accessible
        STATUS mandatory
        DESCRIPTION
                "The CC number of device."
        INDEX  { ccOutStatusIndex}
        ::= { ipduDeviceCcOutStatusTable 1 }

IpduDeviceCcOutStatusEntry ::=
        SEQUENCE {
                ccOutStatusIndex
                        INTEGER,
                ccOutStatusStatus
                        INTEGER,
                ccOutStatusTimeOnState
                        INTEGER
         }

ccOutStatusIndex OBJECT-TYPE
        SYNTAX INTEGER (0..65535)
        ACCESS read-only
        STATUS mandatory
        DESCRIPTION
                "The index to access contact closure output configuration table."
        ::= { ipduDeviceCcOutStatusEntry 1 }

ccOutStatusStatus OBJECT-TYPE
        SYNTAX INTEGER {
        closed (1),
        open (2)
    }
        ACCESS read-only
        STATUS mandatory
        DESCRIPTION
                "State of a contact closure output of device."
        ::= { ipduDeviceCcOutStatusEntry 2 }

ccOutStatusTimeOnState OBJECT-TYPE
        SYNTAX INTEGER
        ACCESS read-only
        STATUS mandatory
        DESCRIPTION
                "Time in seconds since the contact closure output changed to current state."
        ::= { ipduDeviceCcOutStatusEntry 3 }

ipduDeviceCcOutControlTable OBJECT-TYPE
        SYNTAX SEQUENCE OF IpduDeviceCcOutControlEntry
        ACCESS not-accessible
        STATUS mandatory
        DESCRIPTION
                "A list of contact closure output on this device."
        ::= { ipduDeviceCcOut 4}

ipduDeviceCcOutControlEntry OBJECT-TYPE
        SYNTAX IpduDeviceCcOutControlEntry
        ACCESS not-accessible
        STATUS mandatory
        DESCRIPTION
                "The outlet number of device."
        INDEX  { ccOutControlIndex}
        ::= { ipduDeviceCcOutControlTable 1 }

IpduDeviceCcOutControlEntry ::=
        SEQUENCE {
                ccOutControlIndex
                        INTEGER,
        ccOutControlControl
            INTEGER
        }

ccOutControlIndex OBJECT-TYPE
        SYNTAX INTEGER (0..65535)
        ACCESS read-only
        STATUS mandatory
        DESCRIPTION
                "The index to a access contact closure output configuration table."
        ::= { ipduDeviceCcOutControlEntry 1 }

ccOutControlControl OBJECT-TYPE
        SYNTAX INTEGER {
        none(1),
                cancelAction(2),
                closeImmediately(3),
                openImmediately(4),
                cycleImmediately(5),
                closeByCloseTimer(6),
                openByOpenTimer(7),
                cycleByActionTimer(8),
                closeThenOpenByActionTimers(9),
                openThenCloseByActionTimers(10)
    }
        ACCESS read-write
        STATUS mandatory
        DESCRIPTION
                "Set to control the contact closure output perform action as requested."
        ::= { ipduDeviceCcOutControlEntry 2 }

ipduSlaveState       OBJECT IDENTIFIER ::= { ipduSlave 1 }
-- ===========================================================================
--
-- ipduSlaveState
--
--     Daisy Chain Device Group
--
-- ===========================================================================
--

ipduSlaveStateTable OBJECT-TYPE
        SYNTAX SEQUENCE OF IpduSlaveStateEntry
        ACCESS not-accessible
        STATUS mandatory
        DESCRIPTION
                "A list of outlet on this device."
        ::= { ipduSlaveState 1}

ipduSlaveStateEntry OBJECT-TYPE
        SYNTAX IpduSlaveStateEntry
        ACCESS not-accessible
        STATUS mandatory
        DESCRIPTION
                "The outlet number of device."
        INDEX  { slaveStateIndex}
        ::= { ipduSlaveStateTable 1 }

IpduSlaveStateEntry ::=
        SEQUENCE {
                slaveStateIndex
                        INTEGER,
                slaveStateControl01
                        INTEGER
        }

slaveStateIndex OBJECT-TYPE
        SYNTAX INTEGER (0..65535)
        ACCESS read-only
        STATUS mandatory
        DESCRIPTION
                "The index to a access outlet configuration table."
        ::= { ipduSlaveStateEntry 1 }

slaveStateControl01 OBJECT-TYPE
        SYNTAX INTEGER {
                disconnected(1),
                connected(2)
    }
        ACCESS read-only
        STATUS mandatory
        DESCRIPTION
                "Set to control the outlet perform action as requested to slave outlet A"
        ::= { ipduSlaveStateEntry 2 }

ipduSlaveInlet       OBJECT IDENTIFIER ::= { ipduSlave 2 }
-- ===========================================================================
--
-- ipduSlaveAllDevice
--
--     Daisy Chain Device Group
--
-- ===========================================================================

ipduSlaveInletStatus     OBJECT IDENTIFIER ::= { ipduSlaveInlet 1 }
-- ===========================================================================
--
-- ipduSlaveAllDevice
--
--     Daisy Chain Device Group
--
-- ===========================================================================


ipduDeviceSlaveInletStatusTable OBJECT-TYPE
        SYNTAX SEQUENCE OF IpduDeviceSlaveInletStatusEntry
        ACCESS not-accessible
        STATUS mandatory
        DESCRIPTION
                "A list of inlet on this device."
        ::= { ipduSlaveInletStatus 1}

ipduDeviceSlaveInletStatusEntry OBJECT-TYPE
        SYNTAX IpduDeviceSlaveInletStatusEntry
        ACCESS not-accessible
        STATUS mandatory
        DESCRIPTION
                "The inlet number of device."
        INDEX  { inletStatusIndex}
        ::= { ipduDeviceSlaveInletStatusTable 1 }

IpduDeviceSlaveInletStatusEntry ::=
        SEQUENCE {
                inletSlaveStatusIndex
                        INTEGER,
                inletSlaveStatusVoltage
                        INTEGER,
                inletSlaveStatusCurrent
                        INTEGER,
                inletSlaveStatusFrequency
                        INTEGER,
                inletSlaveStatusKwatt
                        INTEGER,
                inletSlaveStatusWH
                        INTEGER,
                inletSlaveStatusVoltage2
                        INTEGER,
                inletSlaveStatusCurrent2
                        INTEGER,
                inletSlaveStatusFrequency2
                        INTEGER,
                inletSlaveStatusKwatt2
                        INTEGER,
                inletSlaveStatusWH2
                        INTEGER
        }

inletSlaveStatusIndex OBJECT-TYPE
        SYNTAX INTEGER (0..65535)
        ACCESS read-only
        STATUS mandatory
        DESCRIPTION
                "The index to a access inlet configuration table."
        ::= { ipduDeviceSlaveInletStatusEntry 1 }

inletSlaveStatusVoltage OBJECT-TYPE
        SYNTAX INTEGER (1..65500) --
        ACCESS read-only
        STATUS mandatory
        DESCRIPTION
                "The Inlet Voltage in 0.1 volts"
        ::= { ipduDeviceSlaveInletStatusEntry 2 }

inletSlaveStatusCurrent OBJECT-TYPE
        SYNTAX INTEGER (0..65500) --
        ACCESS read-only
        STATUS mandatory
        DESCRIPTION
                "The Inlet Current in 0.001 Amp."
        ::= { ipduDeviceSlaveInletStatusEntry 3 }

inletSlaveStatusFrequency OBJECT-TYPE
        SYNTAX INTEGER (1..65500) --
        ACCESS read-only
        STATUS mandatory
        DESCRIPTION
                "The Inlet Frequency in 0.1 Hz"
        ::= { ipduDeviceSlaveInletStatusEntry 4 }

inletSlaveStatusKwatt OBJECT-TYPE
        SYNTAX INTEGER (0..65500) --
        ACCESS read-only
        STATUS mandatory
        DESCRIPTION
                "The Inlet Kwatt in 0.001 KW/H"
        ::= { ipduDeviceSlaveInletStatusEntry 5 }

inletSlaveStatusWH OBJECT-TYPE
        SYNTAX INTEGER (1..65500) --
        ACCESS read-only
        STATUS mandatory
        DESCRIPTION
                "The Inlet Kwatt in 0.001 KW/H"
        ::= { ipduDeviceSlaveInletStatusEntry 6 }

inletSlaveStatusVoltage2 OBJECT-TYPE
        SYNTAX INTEGER (1..65500) --
        ACCESS read-only
        STATUS mandatory
        DESCRIPTION
                "The Inlet Voltage in 0.1 volts"
        ::= { ipduDeviceSlaveInletStatusEntry 7 }

inletSlaveStatusCurrent2 OBJECT-TYPE
        SYNTAX INTEGER (0..65500) --
        ACCESS read-only
        STATUS mandatory
        DESCRIPTION
                "The Inlet Current in 0.001 Amp."
        ::= { ipduDeviceSlaveInletStatusEntry 8 }

inletSlaveStatusFrequency2 OBJECT-TYPE
        SYNTAX INTEGER (1..65500) --
        ACCESS read-only
        STATUS mandatory
        DESCRIPTION
                "The Inlet Frequency in 0.1 Hz"
        ::= { ipduDeviceSlaveInletStatusEntry 9 }

inletSlaveStatusKwatt2 OBJECT-TYPE
        SYNTAX INTEGER (0..65500) --
        ACCESS read-only
        STATUS mandatory
        DESCRIPTION
                "The Inlet Kwatt in 0.001 KW/H"
        ::= { ipduDeviceSlaveInletStatusEntry 10 }

inletSlaveStatusWH2 OBJECT-TYPE
        SYNTAX INTEGER (1..65500) --
        ACCESS read-only
        STATUS mandatory
        DESCRIPTION
                "The Inlet Kwatt in 0.001 KW/H"
        ::= { ipduDeviceSlaveInletStatusEntry 11 }

ipduSlaveInletConfig     OBJECT IDENTIFIER ::= { ipduSlaveInlet 2 }
-- ===========================================================================
--
-- ipduSlaveAllDevice
--
--     Daisy Chain Device Group
--
-- ===========================================================================


ipduDeviceslaveInletConfigTable OBJECT-TYPE
        SYNTAX SEQUENCE OF IpduDeviceslaveInletConfigEntry
        ACCESS not-accessible
        STATUS mandatory
        DESCRIPTION
                "A list of inlet on this device."
        ::= { ipduSlaveInletConfig 1}

ipduDeviceslaveInletConfigEntry OBJECT-TYPE
        SYNTAX IpduDeviceslaveInletConfigEntry
        ACCESS not-accessible
        STATUS mandatory
        DESCRIPTION
                "The inlet number of device."
        INDEX  { slaveInletConfigIndex}
        ::= { ipduDeviceslaveInletConfigTable 1 }

IpduDeviceslaveInletConfigEntry ::=
        SEQUENCE {
                slaveInletConfigIndex
                        INTEGER,
                slaveInletConfigVoltageHigh
                        INTEGER,
                slaveInletConfigVoltageLow
                        INTEGER,
                slaveInlet2ConfigVoltageHigh
                        INTEGER,
                slaveInlet2ConfigVoltageLow
                        INTEGER
        }

slaveInletConfigIndex OBJECT-TYPE
        SYNTAX INTEGER (0..65535)
        ACCESS read-only
        STATUS mandatory
        DESCRIPTION
                "The index to a access inlet configuration table."
        ::= { ipduDeviceslaveInletConfigEntry 1 }


slaveInletConfigVoltageHigh OBJECT-TYPE
        SYNTAX INTEGER (1..65500) --
        ACCESS read-write
        STATUS mandatory
        DESCRIPTION
                "The Inlet high voltage threshold, in volts."
        ::= { ipduDeviceslaveInletConfigEntry 2 }


slaveInletConfigVoltageLow OBJECT-TYPE
        SYNTAX INTEGER (1..65500) --
        ACCESS read-write
        STATUS mandatory
        DESCRIPTION
                "The Inlet low voltage threshold, in volts."
        ::= { ipduDeviceslaveInletConfigEntry 3 }


slaveInlet2ConfigVoltageHigh OBJECT-TYPE
        SYNTAX INTEGER (1..65500) --
        ACCESS read-write
        STATUS mandatory
        DESCRIPTION
                "The Inlet 2 high voltage threshold, in volts."
        ::= { ipduDeviceslaveInletConfigEntry 4 }

slaveInlet2ConfigVoltageLow OBJECT-TYPE
        SYNTAX INTEGER (1..65500) --
        ACCESS read-write
        STATUS mandatory
        DESCRIPTION
                "The Inlet low voltage threshold, in volts."
        ::= { ipduDeviceslaveInletConfigEntry 5 }


ipduSlaveOutlet      OBJECT IDENTIFIER ::= { ipduSlave 3 }
-- ===========================================================================
--
-- ipduSlaveAllDevice
--
--     Daisy Chain Device Group
--
-- ===========================================================================

ipduSlaveOutletConfig        OBJECT IDENTIFIER ::= { ipduSlaveOutlet 1 }
-- ===========================================================================
--
-- ipduOutletConfig
--
--     Outlet Config Group
--
-- ===========================================================================

--
-- Outlet Name Description
--

ipduSlaveDeviceOutletNameTable OBJECT-TYPE
        SYNTAX SEQUENCE OF IpduSlaveDeviceOutletNameEntry
        ACCESS not-accessible
        STATUS mandatory
        DESCRIPTION
                "A list of outlet on this device."
        ::= { ipduSlaveOutletConfig 1}

ipduSlaveDeviceOutletNameEntry OBJECT-TYPE
        SYNTAX IpduSlaveDeviceOutletNameEntry
        ACCESS not-accessible
        STATUS mandatory
        DESCRIPTION
                "The outlet number of device."
        INDEX  { slaveOutletNameIndex}
        ::= { ipduSlaveDeviceOutletNameTable 1 }

IpduSlaveDeviceOutletNameEntry ::=
        SEQUENCE {
                slaveOutletNameIndex
                        INTEGER,
                slaveOutletName01
                        DisplayString,
                slaveOutletName02
                        DisplayString,
                slaveOutletName03
                        DisplayString,
                slaveOutletName04
                        DisplayString,
                slaveOutletName05
                        DisplayString,
                slaveOutletName06
                        DisplayString,
                slaveOutletName07
                        DisplayString,
                slaveOutletName08
                        DisplayString,
                slaveOutletName09
                        DisplayString,
                slaveOutletName10
                        DisplayString,
                slaveOutletName11
                        DisplayString,
                slaveOutletName12
                        DisplayString
        }

slaveOutletNameIndex OBJECT-TYPE
        SYNTAX INTEGER (0..65535)
        ACCESS read-only
        STATUS mandatory
        DESCRIPTION
                "The index to a access outlet configuration table."
        ::= { ipduSlaveDeviceOutletNameEntry 1 }

slaveOutletName01 OBJECT-TYPE
        SYNTAX DisplayString (SIZE(0..31))
        ACCESS read-write
        STATUS mandatory
        DESCRIPTION
                "A Description of a outlet name of device."
        ::= { ipduSlaveDeviceOutletNameEntry 2 }

slaveOutletName02 OBJECT-TYPE
        SYNTAX DisplayString (SIZE(0..31))
        ACCESS read-write
        STATUS mandatory
        DESCRIPTION
                "A Description of a outlet name of device."
        ::= { ipduSlaveDeviceOutletNameEntry 3 }

slaveOutletName03 OBJECT-TYPE
        SYNTAX DisplayString (SIZE(0..31))
        ACCESS read-write
        STATUS mandatory
        DESCRIPTION
                "A Description of a outlet name of device."
        ::= { ipduSlaveDeviceOutletNameEntry 4 }

slaveOutletName04 OBJECT-TYPE
        SYNTAX DisplayString (SIZE(0..31))
        ACCESS read-write
        STATUS mandatory
        DESCRIPTION
                "A Description of a outlet name of device."
        ::= { ipduSlaveDeviceOutletNameEntry 5 }

slaveOutletName05 OBJECT-TYPE
        SYNTAX DisplayString (SIZE(0..31))
        ACCESS read-write
        STATUS mandatory
        DESCRIPTION
                "A Description of a outlet name of device."
        ::= { ipduSlaveDeviceOutletNameEntry 6 }

slaveOutletName06 OBJECT-TYPE
        SYNTAX DisplayString (SIZE(0..31))
        ACCESS read-write
        STATUS mandatory
        DESCRIPTION
                "A Description of a outlet name of device."
        ::= { ipduSlaveDeviceOutletNameEntry 7 }

slaveOutletName07 OBJECT-TYPE
        SYNTAX DisplayString (SIZE(0..31))
        ACCESS read-write
        STATUS mandatory
        DESCRIPTION
                "A Description of a outlet name of device."
        ::= { ipduSlaveDeviceOutletNameEntry 8 }

slaveOutletName08 OBJECT-TYPE
        SYNTAX DisplayString (SIZE(0..31))
        ACCESS read-write
        STATUS mandatory
        DESCRIPTION
                "A Description of a outlet name of device."
        ::= { ipduSlaveDeviceOutletNameEntry 9 }

slaveOutletName09 OBJECT-TYPE
        SYNTAX DisplayString (SIZE(0..31))
        ACCESS read-write
        STATUS mandatory
        DESCRIPTION
                "A Description of a outlet name of device."
        ::= { ipduSlaveDeviceOutletNameEntry 10 }

slaveOutletName10 OBJECT-TYPE
        SYNTAX DisplayString (SIZE(0..31))
        ACCESS read-write
        STATUS mandatory
        DESCRIPTION
                "A Description of a outlet name of device."
        ::= { ipduSlaveDeviceOutletNameEntry 11 }

slaveOutletName11 OBJECT-TYPE
        SYNTAX DisplayString (SIZE(0..31))
        ACCESS read-write
        STATUS mandatory
        DESCRIPTION
                "A Description of a outlet name of device."
        ::= { ipduSlaveDeviceOutletNameEntry 12 }

slaveOutletName12 OBJECT-TYPE
        SYNTAX DisplayString (SIZE(0..31))
        ACCESS read-write
        STATUS mandatory
        DESCRIPTION
                "A Description of a outlet name of device."
        ::= { ipduSlaveDeviceOutletNameEntry 13 }

-- ===============================
-- Outlet Location Description
-- ===============================


ipduSlaveDeviceOutletLocationTable OBJECT-TYPE
        SYNTAX SEQUENCE OF IpduSlaveDeviceOutletLocationEntry
        ACCESS not-accessible
        STATUS mandatory
        DESCRIPTION
                "A list of outlet on this device."
        ::= { ipduSlaveOutletConfig 2}

ipduSlaveDeviceOutletLocationEntry OBJECT-TYPE
        SYNTAX IpduSlaveDeviceOutletLocationEntry
        ACCESS not-accessible
        STATUS mandatory
        DESCRIPTION
                "The outlet number of device."
        INDEX  { slaveOutletLocationIndex}
        ::= { ipduSlaveDeviceOutletLocationTable 1 }

IpduSlaveDeviceOutletLocationEntry ::=
        SEQUENCE {
                slaveOutletLocationIndex
                        INTEGER,
                slaveOutletLocation01
                        DisplayString,
                slaveOutletLocation02
                        DisplayString,
                slaveOutletLocation03
                        DisplayString,
                slaveOutletLocation04
                        DisplayString,
                slaveOutletLocation05
                        DisplayString,
                slaveOutletLocation06
                        DisplayString,
                slaveOutletLocation07
                        DisplayString,
                slaveOutletLocation08
                        DisplayString,
                slaveOutletLocation09
                        DisplayString,
                slaveOutletLocation10
                        DisplayString,
                slaveOutletLocation11
                        DisplayString,
                slaveOutletLocation12
                        DisplayString
        }

slaveOutletLocationIndex OBJECT-TYPE
        SYNTAX INTEGER (0..65535)
        ACCESS read-only
        STATUS mandatory
        DESCRIPTION
                "The index to a access outlet configuration table."
        ::= { ipduSlaveDeviceOutletLocationEntry 1 }

slaveOutletLocation01 OBJECT-TYPE
        SYNTAX DisplayString (SIZE(0..31))
        ACCESS read-write
        STATUS mandatory
        DESCRIPTION
                "A Description of a outlet name of device."
        ::= { ipduSlaveDeviceOutletLocationEntry 2 }

slaveOutletLocation02 OBJECT-TYPE
        SYNTAX DisplayString (SIZE(0..31))
        ACCESS read-write
        STATUS mandatory
        DESCRIPTION
                "A Description of a outlet name of device."
        ::= { ipduSlaveDeviceOutletLocationEntry 3 }

slaveOutletLocation03 OBJECT-TYPE
        SYNTAX DisplayString (SIZE(0..31))
        ACCESS read-write
        STATUS mandatory
        DESCRIPTION
                "A Description of a outlet name of device."
        ::= { ipduSlaveDeviceOutletLocationEntry 4 }

slaveOutletLocation04 OBJECT-TYPE
        SYNTAX DisplayString (SIZE(0..31))
        ACCESS read-write
        STATUS mandatory
        DESCRIPTION
                "A Description of a outlet name of device."
        ::= { ipduSlaveDeviceOutletLocationEntry 5 }

slaveOutletLocation05 OBJECT-TYPE
        SYNTAX DisplayString (SIZE(0..31))
        ACCESS read-write
        STATUS mandatory
        DESCRIPTION
                "A Description of a outlet name of device."
        ::= { ipduSlaveDeviceOutletLocationEntry 6 }

slaveOutletLocation06 OBJECT-TYPE
        SYNTAX DisplayString (SIZE(0..31))
        ACCESS read-write
        STATUS mandatory
        DESCRIPTION
                "A Description of a outlet name of device."
        ::= { ipduSlaveDeviceOutletLocationEntry 7 }

slaveOutletLocation07 OBJECT-TYPE
        SYNTAX DisplayString (SIZE(0..31))
        ACCESS read-write
        STATUS mandatory
        DESCRIPTION
                "A Description of a outlet name of device."
        ::= { ipduSlaveDeviceOutletLocationEntry 8 }

slaveOutletLocation08 OBJECT-TYPE
        SYNTAX DisplayString (SIZE(0..31))
        ACCESS read-write
        STATUS mandatory
        DESCRIPTION
                "A Description of a outlet name of device."
        ::= { ipduSlaveDeviceOutletLocationEntry 9 }

slaveOutletLocation09 OBJECT-TYPE
        SYNTAX DisplayString (SIZE(0..31))
        ACCESS read-write
        STATUS mandatory
        DESCRIPTION
                "A Description of a outlet name of device."
        ::= { ipduSlaveDeviceOutletLocationEntry 10 }

slaveOutletLocation10 OBJECT-TYPE
        SYNTAX DisplayString (SIZE(0..31))
        ACCESS read-write
        STATUS mandatory
        DESCRIPTION
                "A Description of a outlet name of device."
        ::= { ipduSlaveDeviceOutletLocationEntry 11 }

slaveOutletLocation11 OBJECT-TYPE
        SYNTAX DisplayString (SIZE(0..31))
        ACCESS read-write
        STATUS mandatory
        DESCRIPTION
                "A Description of a outlet name of device."
        ::= { ipduSlaveDeviceOutletLocationEntry 12 }

slaveOutletLocation12 OBJECT-TYPE
        SYNTAX DisplayString (SIZE(0..31))
        ACCESS read-write
        STATUS mandatory
        DESCRIPTION
                "A Description of a outlet name of device."
        ::= { ipduSlaveDeviceOutletLocationEntry 13 }

-- ==========================================
-- Outlet On Delay Time
-- ==========================================

ipduSlaveDeviceOutletOnTimeTable OBJECT-TYPE
        SYNTAX SEQUENCE OF IpduSlaveDeviceOutletOnTimeEntry
        ACCESS not-accessible
        STATUS mandatory
        DESCRIPTION
                "A list of outlet on this device."
        ::= { ipduSlaveOutletConfig 3}

ipduSlaveDeviceOutletOnTimeEntry OBJECT-TYPE
        SYNTAX IpduSlaveDeviceOutletOnTimeEntry
        ACCESS not-accessible
        STATUS mandatory
        DESCRIPTION
                "The outlet number of device."
        INDEX  { slaveOutletOnTimeIndex}
        ::= { ipduSlaveDeviceOutletOnTimeTable 1 }

IpduSlaveDeviceOutletOnTimeEntry ::=
        SEQUENCE {
                slaveOutletOnTimeIndex
                        INTEGER,
                slaveOutletOnTime01
                        INTEGER,
                slaveOutletOnTime02
                        INTEGER,
                slaveOutletOnTime03
                        INTEGER,
                slaveOutletOnTime04
                        INTEGER,
                slaveOutletOnTime05
                        INTEGER,
                slaveOutletOnTime06
                        INTEGER,
                slaveOutletOnTime07
                        INTEGER,
                slaveOutletOnTime08
                        INTEGER,
                slaveOutletOnTime09
                        INTEGER,
                slaveOutletOnTime10
                        INTEGER,
                slaveOutletOnTime11
                        INTEGER,
                slaveOutletOnTime12
                        INTEGER
        }

slaveOutletOnTimeIndex OBJECT-TYPE
        SYNTAX INTEGER (0..65535)
        ACCESS read-only
        STATUS mandatory
        DESCRIPTION
                "The index to a access outlet configuration table."
        ::= { ipduSlaveDeviceOutletOnTimeEntry 1 }

slaveOutletOnTime01 OBJECT-TYPE
        SYNTAX INTEGER
        ACCESS read-write
        STATUS mandatory
        DESCRIPTION
                "The delay time before turn on tis outlet, in seconds."
        ::= { ipduSlaveDeviceOutletOnTimeEntry 2 }

slaveOutletOnTime02 OBJECT-TYPE
        SYNTAX INTEGER
        ACCESS read-write
        STATUS mandatory
        DESCRIPTION
                "The delay time before turn on tis outlet, in seconds."
        ::= { ipduSlaveDeviceOutletOnTimeEntry 3 }

slaveOutletOnTime03 OBJECT-TYPE
        SYNTAX INTEGER
        ACCESS read-write
        STATUS mandatory
        DESCRIPTION
                "The delay time before turn on tis outlet, in seconds."
        ::= { ipduSlaveDeviceOutletOnTimeEntry 4 }

slaveOutletOnTime04 OBJECT-TYPE
        SYNTAX INTEGER
        ACCESS read-write
        STATUS mandatory
        DESCRIPTION
                "The delay time before turn on tis outlet, in seconds."
        ::= { ipduSlaveDeviceOutletOnTimeEntry 5 }

slaveOutletOnTime05 OBJECT-TYPE
        SYNTAX INTEGER
        ACCESS read-write
        STATUS mandatory
        DESCRIPTION
                "The delay time before turn on tis outlet, in seconds."
        ::= { ipduSlaveDeviceOutletOnTimeEntry 6 }

slaveOutletOnTime06 OBJECT-TYPE
        SYNTAX INTEGER
        ACCESS read-write
        STATUS mandatory
        DESCRIPTION
                "The delay time before turn on tis outlet, in seconds."
        ::= { ipduSlaveDeviceOutletOnTimeEntry 7 }

slaveOutletOnTime07 OBJECT-TYPE
        SYNTAX INTEGER
        ACCESS read-write
        STATUS mandatory
        DESCRIPTION
                "The delay time before turn on tis outlet, in seconds."
        ::= { ipduSlaveDeviceOutletOnTimeEntry 8 }

slaveOutletOnTime08 OBJECT-TYPE
        SYNTAX INTEGER
        ACCESS read-write
        STATUS mandatory
        DESCRIPTION
                "The delay time before turn on tis outlet, in seconds."
        ::= { ipduSlaveDeviceOutletOnTimeEntry 9 }

slaveOutletOnTime09 OBJECT-TYPE
        SYNTAX INTEGER
        ACCESS read-write
        STATUS mandatory
        DESCRIPTION
                "The delay time before turn on tis outlet, in seconds."
        ::= { ipduSlaveDeviceOutletOnTimeEntry 10 }

slaveOutletOnTime10 OBJECT-TYPE
        SYNTAX INTEGER
        ACCESS read-write
        STATUS mandatory
        DESCRIPTION
                "The delay time before turn on tis outlet, in seconds."
        ::= { ipduSlaveDeviceOutletOnTimeEntry 11 }


slaveOutletOnTime11 OBJECT-TYPE
        SYNTAX INTEGER
        ACCESS read-write
        STATUS mandatory
        DESCRIPTION
                "The delay time before turn on tis outlet, in seconds."
        ::= { ipduSlaveDeviceOutletOnTimeEntry 12 }

slaveOutletOnTime12 OBJECT-TYPE
        SYNTAX INTEGER
        ACCESS read-write
        STATUS mandatory
        DESCRIPTION
                "The delay time before turn on tis outlet, in seconds."
        ::= { ipduSlaveDeviceOutletOnTimeEntry 13 }

-- ==========================================
-- Outlet Off Delay Time
-- ==========================================

ipduSlaveDeviceOutletOffTimeTable OBJECT-TYPE
        SYNTAX SEQUENCE OF IpduSlaveDeviceOutletOffTimeEntry
        ACCESS not-accessible
        STATUS mandatory
        DESCRIPTION
                "A list of outlet on this device."
        ::= { ipduSlaveOutletConfig 4}

ipduSlaveDeviceOutletOffTimeEntry OBJECT-TYPE
        SYNTAX IpduSlaveDeviceOutletOffTimeEntry
        ACCESS not-accessible
        STATUS mandatory
        DESCRIPTION
                "The outlet number of device."
        INDEX  { slaveOutletOffTimeIndex}
        ::= { ipduSlaveDeviceOutletOffTimeTable 1 }

IpduSlaveDeviceOutletOffTimeEntry ::=
        SEQUENCE {
                slaveOutletOffTimeIndex
                        INTEGER,
                slaveOutletOffTime01
                        INTEGER,
                slaveOutletOffTime02
                        INTEGER,
                slaveOutletOffTime03
                        INTEGER,
                slaveOutletOffTime04
                        INTEGER,
                slaveOutletOffTime05
                        INTEGER,
                slaveOutletOffTime06
                        INTEGER,
                slaveOutletOffTime07
                        INTEGER,
                slaveOutletOffTime08
                        INTEGER,
                slaveOutletOffTime09
                        INTEGER,
                slaveOutletOffTime10
                        INTEGER,
                slaveOutletOffTime11
                        INTEGER,
                slaveOutletOffTime12
                        INTEGER
        }

slaveOutletOffTimeIndex OBJECT-TYPE
        SYNTAX INTEGER (0..65535)
        ACCESS read-only
        STATUS mandatory
        DESCRIPTION
                "The index to a access outlet configuration table."
        ::= { ipduSlaveDeviceOutletOffTimeEntry 1 }

slaveOutletOffTime01 OBJECT-TYPE
        SYNTAX INTEGER
        ACCESS read-write
        STATUS mandatory
        DESCRIPTION
                "The delay time before turn on tis outlet, in seconds."
        ::= { ipduSlaveDeviceOutletOffTimeEntry 2 }

slaveOutletOffTime02 OBJECT-TYPE
        SYNTAX INTEGER
        ACCESS read-write
        STATUS mandatory
        DESCRIPTION
                "The delay time before turn on tis outlet, in seconds."
        ::= { ipduSlaveDeviceOutletOffTimeEntry 3 }

slaveOutletOffTime03 OBJECT-TYPE
        SYNTAX INTEGER
        ACCESS read-write
        STATUS mandatory
        DESCRIPTION
                "The delay time before turn on tis outlet, in seconds."
        ::= { ipduSlaveDeviceOutletOffTimeEntry 4 }

slaveOutletOffTime04 OBJECT-TYPE
        SYNTAX INTEGER
        ACCESS read-write
        STATUS mandatory
        DESCRIPTION
                "The delay time before turn on tis outlet, in seconds."
        ::= { ipduSlaveDeviceOutletOffTimeEntry 5 }

slaveOutletOffTime05 OBJECT-TYPE
        SYNTAX INTEGER
        ACCESS read-write
        STATUS mandatory
        DESCRIPTION
                "The delay time before turn on tis outlet, in seconds."
        ::= { ipduSlaveDeviceOutletOffTimeEntry 6 }

slaveOutletOffTime06 OBJECT-TYPE
        SYNTAX INTEGER
        ACCESS read-write
        STATUS mandatory
        DESCRIPTION
                "The delay time before turn on tis outlet, in seconds."
        ::= { ipduSlaveDeviceOutletOffTimeEntry 7 }

slaveOutletOffTime07 OBJECT-TYPE
        SYNTAX INTEGER
        ACCESS read-write
        STATUS mandatory
        DESCRIPTION
                "The delay time before turn on tis outlet, in seconds."
        ::= { ipduSlaveDeviceOutletOffTimeEntry 8 }

slaveOutletOffTime08 OBJECT-TYPE
        SYNTAX INTEGER
        ACCESS read-write
        STATUS mandatory
        DESCRIPTION
                "The delay time before turn on tis outlet, in seconds."
        ::= { ipduSlaveDeviceOutletOffTimeEntry 9 }

slaveOutletOffTime09 OBJECT-TYPE
        SYNTAX INTEGER
        ACCESS read-write
        STATUS mandatory
        DESCRIPTION
                "The delay time before turn on tis outlet, in seconds."
        ::= { ipduSlaveDeviceOutletOffTimeEntry 10 }

slaveOutletOffTime10 OBJECT-TYPE
        SYNTAX INTEGER
        ACCESS read-write
        STATUS mandatory
        DESCRIPTION
                "The delay time before turn on tis outlet, in seconds."
        ::= { ipduSlaveDeviceOutletOffTimeEntry 11 }


slaveOutletOffTime11 OBJECT-TYPE
        SYNTAX INTEGER
        ACCESS read-write
        STATUS mandatory
        DESCRIPTION
                "The delay time before turn on tis outlet, in seconds."
        ::= { ipduSlaveDeviceOutletOffTimeEntry 12 }

slaveOutletOffTime12 OBJECT-TYPE
        SYNTAX INTEGER
        ACCESS read-write
        STATUS mandatory
        DESCRIPTION
                "The delay time before turn on tis outlet, in seconds."
        ::= { ipduSlaveDeviceOutletOffTimeEntry 13 }


-- ==========================================
-- Outlet Current TH
-- ==========================================

ipduSlaveDeviceOutletCurrThTable OBJECT-TYPE
        SYNTAX SEQUENCE OF IpduSlaveDeviceOutletCurrThEntry
        ACCESS not-accessible
        STATUS mandatory
        DESCRIPTION
                "A list of outlet on this device."
        ::= { ipduSlaveOutletConfig 5}

ipduSlaveDeviceOutletCurrThEntry OBJECT-TYPE
        SYNTAX IpduSlaveDeviceOutletCurrThEntry
        ACCESS not-accessible
        STATUS mandatory
        DESCRIPTION
                "The outlet number of device."
        INDEX  { slaveOutletCurrThIndex}
        ::= { ipduSlaveDeviceOutletCurrThTable 1 }

IpduSlaveDeviceOutletCurrThEntry ::=
        SEQUENCE {
                slaveOutletCurrThIndex
                        INTEGER,
                slaveOutletCurrTh01
                        INTEGER,
                slaveOutletCurrTh02
                        INTEGER,
                slaveOutletCurrTh03
                        INTEGER,
                slaveOutletCurrTh04
                        INTEGER,
                slaveOutletCurrTh05
                        INTEGER,
                slaveOutletCurrTh06
                        INTEGER,
                slaveOutletCurrTh07
                        INTEGER,
                slaveOutletCurrTh08
                        INTEGER,
                slaveOutletCurrTh09
                        INTEGER,
                slaveOutletCurrTh10
                        INTEGER,
                slaveOutletCurrTh11
                        INTEGER,
                slaveOutletCurrTh12
                        INTEGER
        }

slaveOutletCurrThIndex OBJECT-TYPE
        SYNTAX INTEGER (0..65535)
        ACCESS read-only
        STATUS mandatory
        DESCRIPTION
                "The index to a access outlet configuration table."
        ::= { ipduSlaveDeviceOutletCurrThEntry 1 }

slaveOutletCurrTh01 OBJECT-TYPE
        SYNTAX INTEGER
        ACCESS read-write
        STATUS mandatory
        DESCRIPTION
                "The Outlet Current Threshold ,in 0.1 Amp."
        ::= { ipduSlaveDeviceOutletCurrThEntry 2 }

slaveOutletCurrTh02 OBJECT-TYPE
        SYNTAX INTEGER
        ACCESS read-write
        STATUS mandatory
        DESCRIPTION
                "The Outlet Current Threshold ,in 0.1 Amp."
        ::= { ipduSlaveDeviceOutletCurrThEntry 3 }

slaveOutletCurrTh03 OBJECT-TYPE
        SYNTAX INTEGER
        ACCESS read-write
        STATUS mandatory
        DESCRIPTION
                "The Outlet Current Threshold ,in 0.1 Amp."
        ::= { ipduSlaveDeviceOutletCurrThEntry 4 }

slaveOutletCurrTh04 OBJECT-TYPE
        SYNTAX INTEGER
        ACCESS read-write
        STATUS mandatory
        DESCRIPTION
                "The Outlet Current Threshold ,in 0.1 Amp."
        ::= { ipduSlaveDeviceOutletCurrThEntry 5 }

slaveOutletCurrTh05 OBJECT-TYPE
        SYNTAX INTEGER
        ACCESS read-write
        STATUS mandatory
        DESCRIPTION
                "The Outlet Current Threshold ,in 0.1 Amp."
        ::= { ipduSlaveDeviceOutletCurrThEntry 6 }

slaveOutletCurrTh06 OBJECT-TYPE
        SYNTAX INTEGER
        ACCESS read-write
        STATUS mandatory
        DESCRIPTION
                "The Outlet Current Threshold ,in 0.1 Amp."
        ::= { ipduSlaveDeviceOutletCurrThEntry 7 }

slaveOutletCurrTh07 OBJECT-TYPE
        SYNTAX INTEGER
        ACCESS read-write
        STATUS mandatory
        DESCRIPTION
                "The Outlet Current Threshold ,in 0.1 Amp."
        ::= { ipduSlaveDeviceOutletCurrThEntry 8 }

slaveOutletCurrTh08 OBJECT-TYPE
        SYNTAX INTEGER
        ACCESS read-write
        STATUS mandatory
        DESCRIPTION
                "The Outlet Current Threshold ,in 0.1 Amp."
        ::= { ipduSlaveDeviceOutletCurrThEntry 9 }

slaveOutletCurrTh09 OBJECT-TYPE
        SYNTAX INTEGER
        ACCESS read-write
        STATUS mandatory
        DESCRIPTION
                "The Outlet Current Threshold ,in 0.1 Amp."
        ::= { ipduSlaveDeviceOutletCurrThEntry 10 }

slaveOutletCurrTh10 OBJECT-TYPE
        SYNTAX INTEGER
        ACCESS read-write
        STATUS mandatory
        DESCRIPTION
                "The Outlet Current Threshold ,in 0.1 Amp."
        ::= { ipduSlaveDeviceOutletCurrThEntry 11 }


slaveOutletCurrTh11 OBJECT-TYPE
        SYNTAX INTEGER
        ACCESS read-write
        STATUS mandatory
        DESCRIPTION
                "The Outlet Current Threshold ,in 0.1 Amp."
        ::= { ipduSlaveDeviceOutletCurrThEntry 12 }

slaveOutletCurrTh12 OBJECT-TYPE
        SYNTAX INTEGER
        ACCESS read-write
        STATUS mandatory
        DESCRIPTION
                "The Outlet Current Threshold ,in 0.1 Amp."
        ::= { ipduSlaveDeviceOutletCurrThEntry 13 }

ipduSlaveOutletStatus        OBJECT IDENTIFIER ::= { ipduSlaveOutlet 2 }
-- ===========================================================================
--
-- ipduOutletStatus
--
--     Outlet Status Group
--
-- ===========================================================================
-- ==========================================
-- Outlet Current
-- ==========================================

ipduSlaveDeviceOutletCurrentTable OBJECT-TYPE
        SYNTAX SEQUENCE OF IpduSlaveDeviceOutletCurrentEntry
        ACCESS not-accessible
        STATUS mandatory
        DESCRIPTION
                "A list of outlet on this device."
        ::= { ipduSlaveOutletStatus 1}

ipduSlaveDeviceOutletCurrentEntry OBJECT-TYPE
        SYNTAX IpduSlaveDeviceOutletCurrentEntry
        ACCESS not-accessible
        STATUS mandatory
        DESCRIPTION
                "The outlet number of device."
        INDEX  { slaveOutletCurrentIndex}
        ::= { ipduSlaveDeviceOutletCurrentTable 1 }

IpduSlaveDeviceOutletCurrentEntry ::=
        SEQUENCE {
                slaveOutletCurrentIndex
                        INTEGER,
                slaveOutletCurrent01
                        INTEGER,
                slaveOutletCurrent02
                        INTEGER,
                slaveOutletCurrent03
                        INTEGER,
                slaveOutletCurrent04
                        INTEGER,
                slaveOutletCurrent05
                        INTEGER,
                slaveOutletCurrent06
                        INTEGER,
                slaveOutletCurrent07
                        INTEGER,
                slaveOutletCurrent08
                        INTEGER,
                slaveOutletCurrent09
                        INTEGER,
                slaveOutletCurrent10
                        INTEGER,
                slaveOutletCurrent11
                        INTEGER,
                slaveOutletCurrent12
                        INTEGER
        }

slaveOutletCurrentIndex OBJECT-TYPE
        SYNTAX INTEGER (0..65535)
        ACCESS read-only
        STATUS mandatory
        DESCRIPTION
                "The index to a access outlet configuration table."
        ::= { ipduSlaveDeviceOutletCurrentEntry 1 }

slaveOutletCurrent01 OBJECT-TYPE
        SYNTAX INTEGER
        ACCESS read-only
        STATUS mandatory
        DESCRIPTION
                "The outlet A Current in 0.001 Amp."
        ::= { ipduSlaveDeviceOutletCurrentEntry 2 }

slaveOutletCurrent02 OBJECT-TYPE
        SYNTAX INTEGER
        ACCESS read-only
        STATUS mandatory
        DESCRIPTION
                "The outlet B Current in 0.001 Amp."
        ::= { ipduSlaveDeviceOutletCurrentEntry 3 }

slaveOutletCurrent03 OBJECT-TYPE
        SYNTAX INTEGER
        ACCESS read-only
        STATUS mandatory
        DESCRIPTION
                "The outlet C Current in 0.001 Amp."
        ::= { ipduSlaveDeviceOutletCurrentEntry 4 }

slaveOutletCurrent04 OBJECT-TYPE
        SYNTAX INTEGER
        ACCESS read-only
        STATUS mandatory
        DESCRIPTION
                "The outlet D Current in 0.001 Amp."
        ::= { ipduSlaveDeviceOutletCurrentEntry 5 }

slaveOutletCurrent05 OBJECT-TYPE
        SYNTAX INTEGER
        ACCESS read-only
        STATUS mandatory
        DESCRIPTION
                "The outlet E Current in 0.001 Amp."
        ::= { ipduSlaveDeviceOutletCurrentEntry 6 }

slaveOutletCurrent06 OBJECT-TYPE
        SYNTAX INTEGER
        ACCESS read-only
        STATUS mandatory
        DESCRIPTION
                "The outlet F Current in 0.001 Amp."
        ::= { ipduSlaveDeviceOutletCurrentEntry 7 }

slaveOutletCurrent07 OBJECT-TYPE
        SYNTAX INTEGER
        ACCESS read-only
        STATUS mandatory
        DESCRIPTION
                "The outlet G Current in 0.001 Amp."
        ::= { ipduSlaveDeviceOutletCurrentEntry 8 }

slaveOutletCurrent08 OBJECT-TYPE
        SYNTAX INTEGER
        ACCESS read-only
        STATUS mandatory
        DESCRIPTION
                "The outlet H Current in 0.001 Amp."
        ::= { ipduSlaveDeviceOutletCurrentEntry 9 }

slaveOutletCurrent09 OBJECT-TYPE
        SYNTAX INTEGER
        ACCESS read-only
        STATUS mandatory
        DESCRIPTION
                "The outlet I Current in 0.001 Amp."
        ::= { ipduSlaveDeviceOutletCurrentEntry 10 }

slaveOutletCurrent10 OBJECT-TYPE
        SYNTAX INTEGER
        ACCESS read-only
        STATUS mandatory
        DESCRIPTION
                "The outlet J Current in 0.001 Amp."
        ::= { ipduSlaveDeviceOutletCurrentEntry 11 }


slaveOutletCurrent11 OBJECT-TYPE
        SYNTAX INTEGER
        ACCESS read-only
        STATUS mandatory
        DESCRIPTION
                "The outlet K Current in 0.001 Amp."
        ::= { ipduSlaveDeviceOutletCurrentEntry 12 }

slaveOutletCurrent12 OBJECT-TYPE
        SYNTAX INTEGER
        ACCESS read-only
        STATUS mandatory
        DESCRIPTION
                "The outlet L Current in 0.001 Amp."
        ::= { ipduSlaveDeviceOutletCurrentEntry 13 }

-- ==========================================
-- Outlet W/H
-- ==========================================

ipduSlaveDeviceOutletWattTable OBJECT-TYPE
        SYNTAX SEQUENCE OF IpduSlaveDeviceOutletWattEntry
        ACCESS not-accessible
        STATUS mandatory
        DESCRIPTION
                "A list of outlet on this device."
        ::= { ipduSlaveOutletStatus 2}

ipduSlaveDeviceOutletWattEntry OBJECT-TYPE
        SYNTAX IpduSlaveDeviceOutletWattEntry
        ACCESS not-accessible
        STATUS mandatory
        DESCRIPTION
                "The outlet number of device."
        INDEX  { slaveOutletWattIndex}
        ::= { ipduSlaveDeviceOutletWattTable 1 }

IpduSlaveDeviceOutletWattEntry ::=
        SEQUENCE {
                slaveOutletWattIndex
                        INTEGER,
                slaveOutletWatt01
                        INTEGER,
                slaveOutletWatt02
                        INTEGER,
                slaveOutletWatt03
                        INTEGER,
                slaveOutletWatt04
                        INTEGER,
                slaveOutletWatt05
                        INTEGER,
                slaveOutletWatt06
                        INTEGER,
                slaveOutletWatt07
                        INTEGER,
                slaveOutletWatt08
                        INTEGER,
                slaveOutletWatt09
                        INTEGER,
                slaveOutletWatt10
                        INTEGER,
                slaveOutletWatt11
                        INTEGER,
                slaveOutletWatt12
                        INTEGER
        }

slaveOutletWattIndex OBJECT-TYPE
        SYNTAX INTEGER (0..65535)
        ACCESS read-only
        STATUS mandatory
        DESCRIPTION
                "The index to a access outlet configuration table."
        ::= { ipduSlaveDeviceOutletWattEntry 1 }

slaveOutletWatt01 OBJECT-TYPE
        SYNTAX INTEGER
        ACCESS read-only
        STATUS mandatory
        DESCRIPTION
                "The outlet A Watt in 0.1 W/H."
        ::= { ipduSlaveDeviceOutletWattEntry 2 }

slaveOutletWatt02 OBJECT-TYPE
        SYNTAX INTEGER
        ACCESS read-only
        STATUS mandatory
        DESCRIPTION
                "The outlet B Watt in 0.1 W/H."
        ::= { ipduSlaveDeviceOutletWattEntry 3 }

slaveOutletWatt03 OBJECT-TYPE
        SYNTAX INTEGER
        ACCESS read-only
        STATUS mandatory
        DESCRIPTION
                "The outlet C Watt in 0.1 W/H."
        ::= { ipduSlaveDeviceOutletWattEntry 4 }

slaveOutletWatt04 OBJECT-TYPE
        SYNTAX INTEGER
        ACCESS read-only
        STATUS mandatory
        DESCRIPTION
                "The outlet D Watt in 0.1 W/H."
        ::= { ipduSlaveDeviceOutletWattEntry 5 }

slaveOutletWatt05 OBJECT-TYPE
        SYNTAX INTEGER
        ACCESS read-only
        STATUS mandatory
        DESCRIPTION
                "The outlet E Watt in 0.1 W/H."
        ::= { ipduSlaveDeviceOutletWattEntry 6 }

slaveOutletWatt06 OBJECT-TYPE
        SYNTAX INTEGER
        ACCESS read-only
        STATUS mandatory
        DESCRIPTION
                "The outlet F Watt in 0.1 W/H."
        ::= { ipduSlaveDeviceOutletWattEntry 7 }

slaveOutletWatt07 OBJECT-TYPE
        SYNTAX INTEGER
        ACCESS read-only
        STATUS mandatory
        DESCRIPTION
                "The outlet G Watt in 0.1 W/H."
        ::= { ipduSlaveDeviceOutletWattEntry 8 }

slaveOutletWatt08 OBJECT-TYPE
        SYNTAX INTEGER
        ACCESS read-only
        STATUS mandatory
        DESCRIPTION
                "The outlet H Watt in 0.1 W/H."
        ::= { ipduSlaveDeviceOutletWattEntry 9 }

slaveOutletWatt09 OBJECT-TYPE
        SYNTAX INTEGER
        ACCESS read-only
        STATUS mandatory
        DESCRIPTION
                "The outlet I Watt in 0.1 W/H."
        ::= { ipduSlaveDeviceOutletWattEntry 10 }

slaveOutletWatt10 OBJECT-TYPE
        SYNTAX INTEGER
        ACCESS read-only
        STATUS mandatory
        DESCRIPTION
                "The outlet J Watt in 0.1 W/H."
        ::= { ipduSlaveDeviceOutletWattEntry 11 }


slaveOutletWatt11 OBJECT-TYPE
        SYNTAX INTEGER
        ACCESS read-only
        STATUS mandatory
        DESCRIPTION
                "The outlet K Watt in 0.1 W/H."
        ::= { ipduSlaveDeviceOutletWattEntry 12 }

slaveOutletWatt12 OBJECT-TYPE
        SYNTAX INTEGER
        ACCESS read-only
        STATUS mandatory
        DESCRIPTION
                "The outlet L Watt in 0.1 W/H."
        ::= { ipduSlaveDeviceOutletWattEntry 13 }

-- ==========================================
-- Outlet W/H
-- ==========================================

ipduSlaveDeviceOutletKwattTable OBJECT-TYPE
        SYNTAX SEQUENCE OF IpduSlaveDeviceOutletKwattEntry
        ACCESS not-accessible
        STATUS mandatory
        DESCRIPTION
                "A list of outlet on this device."
        ::= { ipduSlaveOutletStatus 3}

ipduSlaveDeviceOutletKwattEntry OBJECT-TYPE
        SYNTAX IpduSlaveDeviceOutletKwattEntry
        ACCESS not-accessible
        STATUS mandatory
        DESCRIPTION
                "The outlet number of device."
        INDEX  { slaveOutletKwattIndex}
        ::= { ipduSlaveDeviceOutletKwattTable 1 }

IpduSlaveDeviceOutletKwattEntry ::=
        SEQUENCE {
                slaveOutletKwattIndex
                        INTEGER,
                slaveOutletKwatt01
                        INTEGER,
                slaveOutletKwatt02
                        INTEGER,
                slaveOutletKwatt03
                        INTEGER,
                slaveOutletKwatt04
                        INTEGER,
                slaveOutletKwatt05
                        INTEGER,
                slaveOutletKwatt06
                        INTEGER,
                slaveOutletKwatt07
                        INTEGER,
                slaveOutletKwatt08
                        INTEGER,
                slaveOutletKwatt09
                        INTEGER,
                slaveOutletKwatt10
                        INTEGER,
                slaveOutletKwatt11
                        INTEGER,
                slaveOutletKwatt12
                        INTEGER
        }

slaveOutletKwattIndex OBJECT-TYPE
        SYNTAX INTEGER (0..65535)
        ACCESS read-only
        STATUS mandatory
        DESCRIPTION
                "The index to a access outlet configuration table."
        ::= { ipduSlaveDeviceOutletKwattEntry 1 }

slaveOutletKwatt01 OBJECT-TYPE
        SYNTAX INTEGER
        ACCESS read-only
        STATUS mandatory
        DESCRIPTION
                "The outlet A Kwatt in 0.001 KW/H."
        ::= { ipduSlaveDeviceOutletKwattEntry 2 }

slaveOutletKwatt02 OBJECT-TYPE
        SYNTAX INTEGER
        ACCESS read-only
        STATUS mandatory
        DESCRIPTION
                "The outlet B Kwatt in 0.001 KW/H."
        ::= { ipduSlaveDeviceOutletKwattEntry 3 }

slaveOutletKwatt03 OBJECT-TYPE
        SYNTAX INTEGER
        ACCESS read-only
        STATUS mandatory
        DESCRIPTION
                "The outlet C Kwatt in 0.001 KW/H."
        ::= { ipduSlaveDeviceOutletKwattEntry 4 }

slaveOutletKwatt04 OBJECT-TYPE
        SYNTAX INTEGER
        ACCESS read-only
        STATUS mandatory
        DESCRIPTION
                "The outlet D Kwatt in 0.001 KW/H."
        ::= { ipduSlaveDeviceOutletKwattEntry 5 }

slaveOutletKwatt05 OBJECT-TYPE
        SYNTAX INTEGER
        ACCESS read-only
        STATUS mandatory
        DESCRIPTION
                "The outlet E Kwatt in 0.001 KW/H."
        ::= { ipduSlaveDeviceOutletKwattEntry 6 }

slaveOutletKwatt06 OBJECT-TYPE
        SYNTAX INTEGER
        ACCESS read-only
        STATUS mandatory
        DESCRIPTION
                "The outlet F Kwatt in 0.001 KW/H."
        ::= { ipduSlaveDeviceOutletKwattEntry 7 }

slaveOutletKwatt07 OBJECT-TYPE
        SYNTAX INTEGER
        ACCESS read-only
        STATUS mandatory
        DESCRIPTION
                "The outlet G Kwatt in 0.001 KW/H."
        ::= { ipduSlaveDeviceOutletKwattEntry 8 }

slaveOutletKwatt08 OBJECT-TYPE
        SYNTAX INTEGER
        ACCESS read-only
        STATUS mandatory
        DESCRIPTION
                "The outlet H Kwatt in 0.001 KW/H."
        ::= { ipduSlaveDeviceOutletKwattEntry 9 }

slaveOutletKwatt09 OBJECT-TYPE
        SYNTAX INTEGER
        ACCESS read-only
        STATUS mandatory
        DESCRIPTION
                "The outlet I Kwatt in 0.001 KW/H."
        ::= { ipduSlaveDeviceOutletKwattEntry 10 }

slaveOutletKwatt10 OBJECT-TYPE
        SYNTAX INTEGER
        ACCESS read-only
        STATUS mandatory
        DESCRIPTION
                "The outlet J Kwatt in 0.001 KW/H."
        ::= { ipduSlaveDeviceOutletKwattEntry 11 }


slaveOutletKwatt11 OBJECT-TYPE
        SYNTAX INTEGER
        ACCESS read-only
        STATUS mandatory
        DESCRIPTION
                "The outlet K Kwatt in 0.001 KW/H."
        ::= { ipduSlaveDeviceOutletKwattEntry 12 }

slaveOutletKwatt12 OBJECT-TYPE
        SYNTAX INTEGER
        ACCESS read-only
        STATUS mandatory
        DESCRIPTION
                "The outlet L Kwatt in 0.001 KW/H."
        ::= { ipduSlaveDeviceOutletKwattEntry 13 }


ipduSlaveOutletAction        OBJECT IDENTIFIER ::= { ipduSlaveOutlet 3 }
-- ===========================================================================
--
-- ipduOutletStatus
--
--     Outlet Action Group
--
-- ===========================================================================

ipduSlaveDeviceOutletActionTable OBJECT-TYPE
        SYNTAX SEQUENCE OF IpduSlaveDeviceOutletActionEntry
        ACCESS not-accessible
        STATUS mandatory
        DESCRIPTION
                "A list of outlet on this device."
        ::= { ipduSlaveOutletAction 1}

ipduSlaveDeviceOutletActionEntry OBJECT-TYPE
        SYNTAX IpduSlaveDeviceOutletActionEntry
        ACCESS not-accessible
        STATUS mandatory
        DESCRIPTION
                "The outlet number of device."
        INDEX  { slaveOutletActionIndex}
        ::= { ipduSlaveDeviceOutletActionTable 1 }

IpduSlaveDeviceOutletActionEntry ::=
        SEQUENCE {
                slaveOutletActionIndex
                        INTEGER,
                slaveOutletAction01
                        INTEGER,
                slaveOutletAction02
                        INTEGER,
                slaveOutletAction03
                        INTEGER,
                slaveOutletAction04
                        INTEGER,
                slaveOutletAction05
                        INTEGER,
                slaveOutletAction06
                        INTEGER,
                slaveOutletAction07
                        INTEGER,
                slaveOutletAction08
                        INTEGER,
                slaveOutletAction09
                        INTEGER,
                slaveOutletAction10
                        INTEGER,
                slaveOutletAction11
                        INTEGER,
                slaveOutletAction12
                        INTEGER
        }

slaveOutletActionIndex OBJECT-TYPE
        SYNTAX INTEGER (0..65535)
        ACCESS read-only
        STATUS mandatory
        DESCRIPTION
                "The index to a access outlet configuration table."
        ::= { ipduSlaveDeviceOutletActionEntry 1 }

slaveOutletAction01 OBJECT-TYPE
        SYNTAX INTEGER {
        none(1),
        cancelAction(2),
        onImmediately(3),
        offImmediately(4),
        cycleImmediately(5),
        onByActionTimer(6),
        offByActionTimer(7),
        cycleByActionTimer(8),
        onThenOffByActionTimers(9),
        offThenOnByActionTimers(10)
    }
        ACCESS read-write
        STATUS mandatory
        DESCRIPTION
                "Set to control the outlet perform action as requested."
        ::= { ipduSlaveDeviceOutletActionEntry 2 }

slaveOutletAction02 OBJECT-TYPE
        SYNTAX INTEGER {
        none(1),
        cancelAction(2),
        onImmediately(3),
        offImmediately(4),
        cycleImmediately(5),
        onByActionTimer(6),
        offByActionTimer(7),
        cycleByActionTimer(8),
        onThenOffByActionTimers(9),
        offThenOnByActionTimers(10)
    }
        ACCESS read-write
        STATUS mandatory
        DESCRIPTION
                "Set to control the outlet perform action as requested."
        ::= { ipduSlaveDeviceOutletActionEntry 3 }

slaveOutletAction03 OBJECT-TYPE
        SYNTAX INTEGER {
        none(1),
        cancelAction(2),
        onImmediately(3),
        offImmediately(4),
        cycleImmediately(5),
        onByActionTimer(6),
        offByActionTimer(7),
        cycleByActionTimer(8),
        onThenOffByActionTimers(9),
        offThenOnByActionTimers(10)
    }
        ACCESS read-write
        STATUS mandatory
        DESCRIPTION
                "Set to control the outlet perform action as requested."
        ::= { ipduSlaveDeviceOutletActionEntry 4 }

slaveOutletAction04 OBJECT-TYPE
        SYNTAX INTEGER {
        none(1),
        cancelAction(2),
        onImmediately(3),
        offImmediately(4),
        cycleImmediately(5),
        onByActionTimer(6),
        offByActionTimer(7),
        cycleByActionTimer(8),
        onThenOffByActionTimers(9),
        offThenOnByActionTimers(10)
    }
        ACCESS read-write
        STATUS mandatory
        DESCRIPTION
                "Set to control the outlet perform action as requested."
        ::= { ipduSlaveDeviceOutletActionEntry 5 }

slaveOutletAction05 OBJECT-TYPE
        SYNTAX INTEGER {
        none(1),
        cancelAction(2),
        onImmediately(3),
        offImmediately(4),
        cycleImmediately(5),
        onByActionTimer(6),
        offByActionTimer(7),
        cycleByActionTimer(8),
        onThenOffByActionTimers(9),
        offThenOnByActionTimers(10)
    }
        ACCESS read-write
        STATUS mandatory
        DESCRIPTION
                "Set to control the outlet perform action as requested."
        ::= { ipduSlaveDeviceOutletActionEntry 6 }

slaveOutletAction06 OBJECT-TYPE
        SYNTAX INTEGER {
        none(1),
        cancelAction(2),
        onImmediately(3),
        offImmediately(4),
        cycleImmediately(5),
        onByActionTimer(6),
        offByActionTimer(7),
        cycleByActionTimer(8),
        onThenOffByActionTimers(9),
        offThenOnByActionTimers(10)
    }
        ACCESS read-write
        STATUS mandatory
        DESCRIPTION
                "Set to control the outlet perform action as requested."
        ::= { ipduSlaveDeviceOutletActionEntry 7 }

slaveOutletAction07 OBJECT-TYPE
        SYNTAX INTEGER {
        none(1),
        cancelAction(2),
        onImmediately(3),
        offImmediately(4),
        cycleImmediately(5),
        onByActionTimer(6),
        offByActionTimer(7),
        cycleByActionTimer(8),
        onThenOffByActionTimers(9),
        offThenOnByActionTimers(10)
    }
        ACCESS read-write
        STATUS mandatory
        DESCRIPTION
                "Set to control the outlet perform action as requested."
        ::= { ipduSlaveDeviceOutletActionEntry 8 }

slaveOutletAction08 OBJECT-TYPE
        SYNTAX INTEGER {
        none(1),
        cancelAction(2),
        onImmediately(3),
        offImmediately(4),
        cycleImmediately(5),
        onByActionTimer(6),
        offByActionTimer(7),
        cycleByActionTimer(8),
        onThenOffByActionTimers(9),
        offThenOnByActionTimers(10)
    }
        ACCESS read-write
        STATUS mandatory
        DESCRIPTION
                "Set to control the outlet perform action as requested."
        ::= { ipduSlaveDeviceOutletActionEntry 9 }

slaveOutletAction09 OBJECT-TYPE
        SYNTAX INTEGER {
        none(1),
        cancelAction(2),
        onImmediately(3),
        offImmediately(4),
        cycleImmediately(5),
        onByActionTimer(6),
        offByActionTimer(7),
        cycleByActionTimer(8),
        onThenOffByActionTimers(9),
        offThenOnByActionTimers(10)
    }
        ACCESS read-write
        STATUS mandatory
        DESCRIPTION
                "Set to control the outlet perform action as requested."
        ::= { ipduSlaveDeviceOutletActionEntry 10 }

slaveOutletAction10 OBJECT-TYPE
        SYNTAX INTEGER {
        none(1),
        cancelAction(2),
        onImmediately(3),
        offImmediately(4),
        cycleImmediately(5),
        onByActionTimer(6),
        offByActionTimer(7),
        cycleByActionTimer(8),
        onThenOffByActionTimers(9),
        offThenOnByActionTimers(10)
    }
        ACCESS read-write
        STATUS mandatory
        DESCRIPTION
                "Set to control the outlet perform action as requested."
        ::= { ipduSlaveDeviceOutletActionEntry 11 }

slaveOutletAction11 OBJECT-TYPE
        SYNTAX INTEGER {
        none(1),
        cancelAction(2),
        onImmediately(3),
        offImmediately(4),
        cycleImmediately(5),
        onByActionTimer(6),
        offByActionTimer(7),
        cycleByActionTimer(8),
        onThenOffByActionTimers(9),
        offThenOnByActionTimers(10)
    }
        ACCESS read-write
        STATUS mandatory
        DESCRIPTION
                "Set to control the outlet perform action as requested."
        ::= { ipduSlaveDeviceOutletActionEntry 12 }

slaveOutletAction12 OBJECT-TYPE
        SYNTAX INTEGER {
        none(1),
        cancelAction(2),
        onImmediately(3),
        offImmediately(4),
        cycleImmediately(5),
        onByActionTimer(6),
        offByActionTimer(7),
        cycleByActionTimer(8),
        onThenOffByActionTimers(9),
        offThenOnByActionTimers(10)
    }
        ACCESS read-write
        STATUS mandatory
        DESCRIPTION
                "Set to control the outlet perform action as requested."
        ::= { ipduSlaveDeviceOutletActionEntry 13 }

ipduEnvEmd       OBJECT IDENTIFIER ::= { ipduEnv 1 }
-- ===========================================================================
--
-- ipduEnvEmd
--
--  Environmental Monitor Device Group
--
-- ===========================================================================

ipduEnvEmdStatus     OBJECT IDENTIFIER ::= { ipduEnvEmd 1 }
-- ===========================================================================
--
-- ipduEnvEmd
--
--  Environmental Monitor Device Status Group
--
-- ===========================================================================

ipduEnvEmdStatusEmdType OBJECT-TYPE
        SYNTAX  INTEGER {
                unknown(1),
                disabled(2),
                eMD-HT(3),
                eMD-T(4)
                }
        ACCESS read-only
        STATUS mandatory
        DESCRIPTION
                "EMD Type."
        ::= { ipduEnvEmdStatus 1 }

ipduEnvEmdStatusTemperature OBJECT-TYPE
        SYNTAX INTEGER (1..10000) --
        ACCESS read-only
        STATUS mandatory
        DESCRIPTION
                "EMD Temperature in 0.1 degree C."
        ::= { ipduEnvEmdStatus  2 }

ipduEnvEmdStatusHumidity OBJECT-TYPE
        SYNTAX INTEGER (1..10000) --
        ACCESS read-only
        STATUS mandatory
        DESCRIPTION
                "EMD Humidity in 0.1%."
        ::= { ipduEnvEmdStatus  3 }

ipduEnvEmdStatusAlarm1 OBJECT-TYPE
        SYNTAX  INTEGER {
                unknown(1),
                disabled(2),
                alarm(3),
                normal(4)
                }
        ACCESS read-only
        STATUS mandatory
        DESCRIPTION
                "EMD Alarm-1 state."
        ::= { ipduEnvEmdStatus 4 }

ipduEnvEmdStatusAlarm2 OBJECT-TYPE
        SYNTAX  INTEGER {
                unknown(1),
                disabled(2),
                alarm(3),
                normal(4)
                }
        ACCESS read-only
        STATUS mandatory
        DESCRIPTION
                "EMD Alarm-2 state."
        ::= { ipduEnvEmdStatus 5 }

ipduEnvEmdConfig     OBJECT IDENTIFIER ::= { ipduEnvEmd 2 }
-- ===========================================================================
--
-- ipduEnvEmd
--
--  Environmental Monitor Device Configuration Group
--
-- ===========================================================================
ipduEnvEmdConfigEmdPresence OBJECT-TYPE
        SYNTAX  INTEGER {
                disabled(1),
                autoDetect(2)
                }
        ACCESS read-write
        STATUS mandatory
        DESCRIPTION
                "Configure the EMD presence by auto-detect or not exist (disabled)."
        ::= { ipduEnvEmdConfig 1 }

ipduEnvEmdConfigEmdName OBJECT-TYPE
       SYNTAX DisplayString (SIZE (0..31))
       ACCESS read-write
       STATUS mandatory
       DESCRIPTION
               "The name of Emd."
       ::= { ipduEnvEmdConfig 2 }

ipduEnvEmdConfigTemp     OBJECT IDENTIFIER ::= { ipduEnvEmdConfig 3 }
-- ===========================================================================
--
-- ipduEnvEmdConfigTemp
--
--  Environmental Monitor Device Temperature Configuration Group
--
-- ===========================================================================
ipduEnvEmdConfigTempName OBJECT-TYPE
       SYNTAX DisplayString (SIZE (0..31))
       ACCESS read-write
       STATUS mandatory
       DESCRIPTION
               "The name of EMD Temperature sensor."
       ::= { ipduEnvEmdConfigTemp 1 }

ipduEnvEmdConfigTempHighSetPoint OBJECT-TYPE
        SYNTAX INTEGER (5..65) --
        ACCESS read-write
        STATUS mandatory
        DESCRIPTION
                "EMD Temperature set point high, alarm will active when temperature
         over this value, in degree C."
        ::= { ipduEnvEmdConfigTemp  2 }

ipduEnvEmdConfigTempHighStatus OBJECT-TYPE
        SYNTAX  INTEGER {
                enabled(1),
                disabled(2)
                }
        ACCESS read-write
        STATUS mandatory
        DESCRIPTION
                "Enabled/disabled the high setpoint be applied or not"
        ::= { ipduEnvEmdConfigTemp 3 }

ipduEnvEmdConfigTempLowSetPoint OBJECT-TYPE
        SYNTAX INTEGER (5..65) --
        ACCESS read-write
        STATUS mandatory
        DESCRIPTION
                "EMD Temperature set point high, alarm will active when temperature
         under this value, in degree C."
        ::= { ipduEnvEmdConfigTemp  4 }

ipduEnvEmdConfigTempLowStatus OBJECT-TYPE
        SYNTAX  INTEGER {
                enabled(1),
                disabled(2)
                }
        ACCESS read-write
        STATUS mandatory
        DESCRIPTION
                "Enabled/disabled the low setpoint be applied or not"
        ::= { ipduEnvEmdConfigTemp 5 }

ipduEnvEmdConfigTempOffset OBJECT-TYPE
        SYNTAX  INTEGER {
                t0p0(1),
                t0p5(2),
                t1p0(3),
                t1p5(4),
                t2p0(5),
                t2p5(6),
                t3p0(7),
                t-0p5(8),
                t-1p0(9),
                t-1p5(10),
                t-2p0(11),
                t-2p5(12),
                t-3p0(13)
                }
        ACCESS read-write
        STATUS mandatory
        DESCRIPTION
                "Offset of temperature in degree C to adjust EMD temperature measurement."
        ::= { ipduEnvEmdConfigTemp 6 }

ipduEnvEmdConfigHumi     OBJECT IDENTIFIER ::= { ipduEnvEmdConfig 4 }
-- ===========================================================================
--
-- ipduEnvEmdConfigHumi
--
--  Environmental Monitor Device Humidity Configuration Group
--
-- ===========================================================================
ipduEnvEmdConfigHumiName OBJECT-TYPE
       SYNTAX DisplayString (SIZE (0..31))
       ACCESS read-write
       STATUS mandatory
       DESCRIPTION
               "The name of EMD Humidity."
       ::= { ipduEnvEmdConfigHumi 1 }

ipduEnvEmdConfigHumiHighSetPoint OBJECT-TYPE
        SYNTAX INTEGER (5..95) --
        ACCESS read-write
        STATUS mandatory
        DESCRIPTION
                "EMD humidity set point high, alarm will active when humidity
         over this value, in %."
        ::= { ipduEnvEmdConfigHumi  2 }

ipduEnvEmdConfigHumiHighStatus OBJECT-TYPE
        SYNTAX  INTEGER {
                enabled(1),
                disabled(2)
                }
        ACCESS read-write
        STATUS mandatory
        DESCRIPTION
                "Enabled/disabled the high setpoint be applied or not"
        ::= { ipduEnvEmdConfigHumi 3 }

ipduEnvEmdConfigHumiLowSetPoint OBJECT-TYPE
        SYNTAX INTEGER (5..95) --
        ACCESS read-write
        STATUS mandatory
        DESCRIPTION
                "EMD humidity set point low, alarm will active when humidity
         under this value, in %."
        ::= { ipduEnvEmdConfigHumi  4 }

ipduEnvEmdConfigHumiLowStatus OBJECT-TYPE
        SYNTAX  INTEGER {
                enabled(1),
                disabled(2)
                }
        ACCESS read-write
        STATUS mandatory
        DESCRIPTION
                "Enabled/disabled the high setpoint be applied or not"
        ::= { ipduEnvEmdConfigHumi 5 }

ipduEnvEmdConfigHumiOffset OBJECT-TYPE
        SYNTAX  INTEGER {
                h0p0(1),
                h1p0(2),
                h2p0(3),
                h3p0(4),
                h4p0(5),
                h5p0(6),
                h6p0(7),
                h-1p0(8),
                h-2p0(9),
                h-3p0(10),
                h-4p0(11),
                h-5p0(12),
                h-6p0(13)
                }
        ACCESS read-write
        STATUS mandatory
        DESCRIPTION
                "Emd Hum Offset;"
        ::= { ipduEnvEmdConfigHumi 6 }

ipduEnvEmdConfigAlarm1       OBJECT IDENTIFIER ::= { ipduEnvEmdConfig 5 }
-- ===========================================================================
--
-- ipduEnvEmdConfigAlarm1
--
--  Environmental Monitor Device Alarm-1 Configuration Group
--
-- ===========================================================================
ipduEnvEmdConfigAlarm1Name OBJECT-TYPE
       SYNTAX DisplayString (SIZE (0..31))
       ACCESS read-write
       STATUS mandatory
       DESCRIPTION
               "The name of EMD Alarm-1."
       ::= { ipduEnvEmdConfigAlarm1 1 }

ipduEnvEmdConfigAlarm1Type OBJECT-TYPE
        SYNTAX  INTEGER {
                disabled(1),
                normalOpen(2),
                normalClose(3)
                }
        ACCESS read-write
        STATUS mandatory
        DESCRIPTION
                "EMD Alarm-1 type"
        ::= { ipduEnvEmdConfigAlarm1 2 }

ipduEnvEmdConfigAlarm2       OBJECT IDENTIFIER ::= { ipduEnvEmdConfig 6 }
-- ===========================================================================
--
-- ipduEnvEmdConfigAlarm2
--
--  Environmental Monitor Device Alarm-2 Configuration Group
--
-- ===========================================================================
ipduEnvEmdConfigAlarm2Name OBJECT-TYPE
       SYNTAX DisplayString (SIZE (0..31))
       ACCESS read-write
       STATUS mandatory
       DESCRIPTION
               "The name of EMD Alarm-2."
       ::= { ipduEnvEmdConfigAlarm2 1 }

ipduEnvEmdConfigAlarm2Type OBJECT-TYPE
        SYNTAX  INTEGER {
                disabled(1),
                normalOpen(2),
                normalClose(3)
                }
        ACCESS read-write
        STATUS mandatory
        DESCRIPTION
                "EMD Alarm-2 type"
        ::= { ipduEnvEmdConfigAlarm2 2 }


-- ===========================================================================
-- ipduTraps
--
-- iPDU Trap group
-- ===========================================================================

   -- This section defines the well-known notifications sent by
   -- iPDU agents.

ipduInletVoltageTooHigh TRAP-TYPE
        ENTERPRISE ipduTraps
        VARIABLES {
    inletConfigIndex,
        inletStatusVoltage,
        inletConfigVoltageHigh,
        inletConfigDesc
        }
        DESCRIPTION
                "CRITICAL: The input voltage over high threshold."
        ::= 1

ipduInletVoltageNotTooHigh TRAP-TYPE
        ENTERPRISE ipduTraps
        VARIABLES {
    inletConfigIndex,
        inletStatusVoltage,
        inletConfigVoltageHigh,
        inletConfigDesc
        }
        DESCRIPTION
                "WARNING: The input voltage return from over high threshold."
        ::= 2

ipduInletVoltageTooLow TRAP-TYPE
        ENTERPRISE ipduTraps
        VARIABLES {
    inletConfigIndex,
        inletStatusVoltage,
        inletConfigVoltageLow,
        inletConfigDesc
        }
        DESCRIPTION
                "CRITICAL: The input voltage under low threshold."
        ::= 3

ipduInletVoltageNotTooLow TRAP-TYPE
        ENTERPRISE ipduTraps
        VARIABLES {
    inletConfigIndex,
        inletStatusVoltage,
        inletConfigVoltageLow,
        inletConfigDesc
        }
        DESCRIPTION
                "WARNING: The input voltage return from under low threshold."
        ::= 4

ipduInletCurrentTooHigh TRAP-TYPE
        ENTERPRISE ipduTraps
        VARIABLES {
    inletConfigIndex,
        inletStatusCurrent,
        inletConfigCurrentHigh,
        inletConfigDesc
        }
        DESCRIPTION
                "CRITICAL: The input current over high threshold."
        ::= 5

ipduInletCurrentNotTooHigh TRAP-TYPE
        ENTERPRISE ipduTraps
        VARIABLES {
    inletConfigIndex,
        inletStatusCurrent,
        inletConfigCurrentHigh,
        inletConfigDesc
        }
        DESCRIPTION
                "WARNING: The input current return from over high threshold."
        ::= 6

ipduInletFrequencyTooHigh TRAP-TYPE
        ENTERPRISE ipduTraps
        VARIABLES {
    inletConfigIndex,
        inletStatusFrequency,
        inletConfigFrequencyHigh,
        inletConfigDesc
        }
        DESCRIPTION
                "CRITICAL: The input frequency over high threshold."
        ::= 7

ipduInletFrequencyNotTooHigh TRAP-TYPE
        ENTERPRISE ipduTraps
        VARIABLES {
    inletConfigIndex,
        inletStatusFrequency,
        inletConfigFrequencyHigh,
        inletConfigDesc
        }
        DESCRIPTION
                "WARNING: The input frequency return from over high threshold."
        ::= 8

ipduInletFrequencyTooLow TRAP-TYPE
        ENTERPRISE ipduTraps
        VARIABLES {
    inletConfigIndex,
        inletStatusFrequency,
        inletConfigFrequencyLow,
        inletConfigDesc
        }
        DESCRIPTION
                "CRITICAL: The input frequency under low threshold."
        ::= 9

ipduInletFrequencyNotTooLow TRAP-TYPE
        ENTERPRISE ipduTraps
        VARIABLES {
    inletConfigIndex,
        inletStatusFrequency,
        inletConfigFrequencyLow,
        inletConfigDesc
        }
        DESCRIPTION
                "WARNING: The input frequency return from under low threshold."
        ::= 10

ipduInlet2VoltageTooHigh TRAP-TYPE
        ENTERPRISE ipduTraps
        VARIABLES {
    inletConfigIndex,
        inletStatusVoltage,
        inletConfigVoltageHigh,
        inletConfigDesc
        }
        DESCRIPTION
                "CRITICAL: The input2 voltage over high threshold."
        ::= 11

ipduInlet2VoltageNotTooHigh TRAP-TYPE
        ENTERPRISE ipduTraps
        VARIABLES {
    inletConfigIndex,
        inletStatusVoltage,
        inletConfigVoltageHigh,
        inletConfigDesc
        }
        DESCRIPTION
                "WARNING: The input2 voltage return from over high threshold."
        ::= 12

ipduInlet2VoltageTooLow TRAP-TYPE
        ENTERPRISE ipduTraps
        VARIABLES {
    inletConfigIndex,
        inletStatusVoltage,
        inletConfigVoltageLow,
        inletConfigDesc
        }
        DESCRIPTION
                "CRITICAL: The input2 voltage under low threshold."
        ::= 13

ipduInlet2VoltageNotTooLow TRAP-TYPE
        ENTERPRISE ipduTraps
        VARIABLES {
    inletConfigIndex,
        inletStatusVoltage,
        inletConfigVoltageLow,
        inletConfigDesc
        }
        DESCRIPTION
                "WARNING: The input2 voltage return from under low threshold."
        ::= 14

ipduInlet2CurrentTooHigh TRAP-TYPE
        ENTERPRISE ipduTraps
        VARIABLES {
    inletConfigIndex,
        inletStatusCurrent,
        inletConfigCurrentHigh,
        inletConfigDesc
        }
        DESCRIPTION
                "CRITICAL: The input2 current over high threshold."
        ::= 15

ipduInlet2CurrentNotTooHigh TRAP-TYPE
        ENTERPRISE ipduTraps
        VARIABLES {
    inletConfigIndex,
        inletStatusCurrent,
        inletConfigCurrentHigh,
        inletConfigDesc
        }
        DESCRIPTION
                "WARNING: The input2 current return from over high threshold."
        ::= 16

ipduInlet2FrequencyTooHigh TRAP-TYPE
        ENTERPRISE ipduTraps
        VARIABLES {
    inletConfigIndex,
        inletStatusFrequency,
        inletConfigFrequencyHigh,
        inletConfigDesc
        }
        DESCRIPTION
                "CRITICAL: The input2 frequency over high threshold."
        ::= 17

ipduInlet2FrequencyNotTooHigh TRAP-TYPE
        ENTERPRISE ipduTraps
        VARIABLES {
    inletConfigIndex,
        inletStatusFrequency,
        inletConfigFrequencyHigh,
        inletConfigDesc
        }
        DESCRIPTION
                "WARNING: The input2 frequency return from over high threshold."
        ::= 18

ipduInlet2FrequencyTooLow TRAP-TYPE
        ENTERPRISE ipduTraps
        VARIABLES {
    inletConfigIndex,
        inletStatusFrequency,
        inletConfigFrequencyLow,
        inletConfigDesc
        }
        DESCRIPTION
                "CRITICAL: The input2 frequency under low threshold."
        ::= 19

ipduInlet2FrequencyNotTooLow TRAP-TYPE
        ENTERPRISE ipduTraps
        VARIABLES {
    inletConfigIndex,
        inletStatusFrequency,
        inletConfigFrequencyLow,
        inletConfigDesc
        }
        DESCRIPTION
                "WARNING: The input2 frequency return from under low threshold."
        ::= 20


ipduOutletCurrentTooHigh TRAP-TYPE
        ENTERPRISE ipduTraps
        VARIABLES {
    outletConfigIndex,
        outletStatusCurrent,
        outletConfigCurrentHigh,
        outletConfigDesc
        }
        DESCRIPTION
                "CRITICAL: The output current of outlet over high threshold."
        ::= 21

ipduOutletCurrentNotTooHigh TRAP-TYPE
        ENTERPRISE ipduTraps
        VARIABLES {
    outletConfigIndex,
        outletStatusCurrent,
        outletConfigCurrentHigh,
        outletConfigDesc
        }
        DESCRIPTION
                "WARNING: The output current of outlet return from over high threshold."
        ::= 22

ipduOutletStateChanged TRAP-TYPE
        ENTERPRISE ipduTraps
        VARIABLES {
    outletConfigIndex,
    outletStatusStatus,
        outletConfigDesc
        }
        DESCRIPTION
                "INFORMATION: The outlet state had changed from on to off, or from off to on."
        ::= 23

ipduEmdTemperatureNotHigh TRAP-TYPE
        ENTERPRISE      ipduTraps
        VARIABLES {
        ipduEnvEmdStatusTemperature,
        ipduEnvEmdConfigTempHighSetPoint,
        ipduEnvEmdConfigTempName
        }
        DESCRIPTION
                "INFORMATION: emd Temperature Not High."
        ::= 24

ipduEmdTemperatureTooHigh TRAP-TYPE
        ENTERPRISE      ipduTraps
        VARIABLES {
        ipduEnvEmdStatusTemperature,
        ipduEnvEmdConfigTempHighSetPoint,
        ipduEnvEmdConfigTempName
        }
        DESCRIPTION
                "WARNING:  emd Temperature Too High."
        ::= 25

ipduEmdTemperatureNotLow TRAP-TYPE
        ENTERPRISE      ipduTraps
        VARIABLES {
        ipduEnvEmdStatusTemperature,
        ipduEnvEmdConfigTempLowSetPoint,
        ipduEnvEmdConfigTempName
        }
        DESCRIPTION
                "INFORMATION: emd Temperature Not Low."
        ::= 26

ipduEmdTemperatureTooLow TRAP-TYPE
        ENTERPRISE      ipduTraps
        VARIABLES {
        ipduEnvEmdStatusTemperature,
        ipduEnvEmdConfigTempLowSetPoint,
        ipduEnvEmdConfigTempName
        }
        DESCRIPTION
                "WARNING: emd Temperature Too Low."
        ::= 27

ipduEmdHumidityNotHigh TRAP-TYPE
        ENTERPRISE      ipduTraps
        VARIABLES {
        ipduEnvEmdStatusHumidity,
        ipduEnvEmdConfigHumiHighSetPoint,
        ipduEnvEmdConfigHumiName
        }
        DESCRIPTION
                "INFORMATION: emd Humidity Not High."
        ::= 28

ipduEmdHumidityTooHigh TRAP-TYPE
        ENTERPRISE      ipduTraps
        VARIABLES {
        ipduEnvEmdStatusHumidity,
        ipduEnvEmdConfigHumiHighSetPoint,
        ipduEnvEmdConfigHumiName
        }
        DESCRIPTION
                "WARNING: emd Humidity Too High."
        ::= 29

ipduEmdHumidityNotLow TRAP-TYPE
        ENTERPRISE      ipduTraps
        VARIABLES {
        ipduEnvEmdStatusHumidity,
        ipduEnvEmdConfigHumiLowSetPoint,
        ipduEnvEmdConfigHumiName
        }
        DESCRIPTION
                "INFORMATION: emd Humidity Not Low."
        ::= 30

ipduEmdHumidityTooLow TRAP-TYPE
        ENTERPRISE      ipduTraps
        VARIABLES {
        ipduEnvEmdStatusHumidity,
        ipduEnvEmdConfigHumiLowSetPoint,
        ipduEnvEmdConfigHumiName
        }
        DESCRIPTION
                "WARNING: emd Humidity Too Low."
        ::= 31

ipduEmdAlarm1Normal TRAP-TYPE
        ENTERPRISE      ipduTraps
        VARIABLES {
        ipduEnvEmdConfigAlarm1Type,
        ipduEnvEmdConfigAlarm1Name
        }
        DESCRIPTION
                "INFORMATION: emd Alarm1 Normal."
        ::= 32

ipduEmdAlarm1Active TRAP-TYPE
        ENTERPRISE      ipduTraps
        VARIABLES {
        ipduEnvEmdConfigAlarm1Type,
        ipduEnvEmdConfigAlarm1Name
        }
        DESCRIPTION
                "WARNING: emd Alarm1 Active."
        ::= 33

ipduEmdAlarm2Normal TRAP-TYPE
        ENTERPRISE      ipduTraps
        VARIABLES {
        ipduEnvEmdConfigAlarm2Type,
        ipduEnvEmdConfigAlarm2Name
        }
        DESCRIPTION
                "INFORMATION: emd Alarm2 Normal."
        ::= 34

ipduEmdAlarm2Active TRAP-TYPE
        ENTERPRISE      ipduTraps
        VARIABLES {
        ipduEnvEmdConfigAlarm2Type,
        ipduEnvEmdConfigAlarm2Name
        }
        DESCRIPTION
                "WARNING: emd Alarm2 Active."
        ::= 35

--==========================================================================
-- Slave01 trap
--==========================================================================
ipduSlave01Inlet01OverHigh TRAP-TYPE
        ENTERPRISE      ipduTraps
        DESCRIPTION
                "CRITICAL: The Slave01 input01 voltage over high threshold."
        ::= 36

ipduSlave01Inlet01NotOverHigh TRAP-TYPE
        ENTERPRISE      ipduTraps
        DESCRIPTION
                "WARNING: The Slave01 input01 voltage Not over high threshold."
        ::= 37

ipduSlave01Inlet02OverHigh TRAP-TYPE
        ENTERPRISE      ipduTraps
        DESCRIPTION
                "CRITICAL: The Slave01 input02 voltage over high threshold."
        ::= 38

ipduSlave01Inlet02NotOverHigh TRAP-TYPE
        ENTERPRISE      ipduTraps
        DESCRIPTION
                "WARNING: The Slave01 input02 voltage Not over high threshold."
        ::= 39

ipduSlave01Inlet01UnderLow TRAP-TYPE
        ENTERPRISE      ipduTraps
        DESCRIPTION
                "CRITICAL: The Slave01 input01 voltage under low threshold."
        ::= 40

ipduSlave01Inlet01NotUnderLow TRAP-TYPE
        ENTERPRISE      ipduTraps
        DESCRIPTION
                "WARNING: The Slave01 input01 voltage Not under low threshold."
        ::= 41

ipduSlave01Inlet02UnderLow TRAP-TYPE
        ENTERPRISE      ipduTraps
        DESCRIPTION
                "CRITICAL: The Slave01 input02 voltage under low threshold."
        ::= 42

ipduSlave01Inlet02NotUnderLow TRAP-TYPE
        ENTERPRISE      ipduTraps
        DESCRIPTION
                "WARNING: The Slave01 input02 voltage Not under low threshold."
        ::= 43

ipduSlave01Inlet01CurrentOverTh TRAP-TYPE
        ENTERPRISE      ipduTraps
        DESCRIPTION
                "CRITICAL: The Slave01 input01 current over high threshold."
        ::= 44

ipduSlave01Inlet01NotCurrentOverTh TRAP-TYPE
        ENTERPRISE      ipduTraps
        DESCRIPTION
                "WARNING: The Slave01 input01 current not over high threshold."
        ::= 45

ipduSlave01Inlet02CurrentOverTh TRAP-TYPE
        ENTERPRISE      ipduTraps
        DESCRIPTION
                "CRITICAL: The Slave01 input02 current over high threshold."
        ::= 46

ipduSlave01Inlet02NotCurrentOverTh TRAP-TYPE
        ENTERPRISE      ipduTraps
        DESCRIPTION
                "WARNING: The Slave01 input02 current not over high threshold."
        ::= 47

ipduSlave01EmdTemperatureTooHigh TRAP-TYPE
        ENTERPRISE      ipduTraps
        DESCRIPTION
                "WARNING: The Slave01 emd Temperature Too High."
        ::= 48

ipduSlave01EmdTemperatureNotHigh TRAP-TYPE
        ENTERPRISE      ipduTraps
        DESCRIPTION
                "INFORMATION: The Slave01 emd Temperature Not High."
        ::= 49

ipduSlave01EmdTemperatureTooLow TRAP-TYPE
        ENTERPRISE      ipduTraps
        DESCRIPTION
                "WARNING: The Slave01 emd Temperature Too Low."
        ::= 50

ipduSlave01EmdTemperatureNotLow TRAP-TYPE
        ENTERPRISE      ipduTraps
        DESCRIPTION
                "INFORMATION: The Slave01 emd Temperature Not Low."
        ::= 51

ipduSlave01EmdHumidityTooHigh TRAP-TYPE
        ENTERPRISE      ipduTraps
        DESCRIPTION
                "WARNING: The Slave01 emd Humidity Too High."
        ::= 52

ipduSlave01EmdHumidityNotHigh TRAP-TYPE
        ENTERPRISE      ipduTraps
        DESCRIPTION
                "INFORMATION: The Slave01 emd Humidity Not High."
        ::= 53

ipduSlave01EmdHumidityTooLow TRAP-TYPE
        ENTERPRISE      ipduTraps
        DESCRIPTION
                "WARNING: The Slave01 emd Humidity Too Low."
        ::= 54

ipduSlave01EmdHumidityNotLow TRAP-TYPE
        ENTERPRISE      ipduTraps
        DESCRIPTION
                "INFORMATION: The Slave01 emd Humidity Not Low."
        ::= 55

ipduSlave01EmdAlarm1Active TRAP-TYPE
        ENTERPRISE      ipduTraps
        DESCRIPTION
                "WARNING: The Slave01 emd Alarm1 Active."
        ::= 56

ipduSlave01EmdAlarm1Normal TRAP-TYPE
        ENTERPRISE      ipduTraps
        DESCRIPTION
                "INFORMATION: The Slave01 emd Alarm1 Normal."
        ::= 57

ipduSlave01EmdAlarm2Active TRAP-TYPE
        ENTERPRISE      ipduTraps
        DESCRIPTION
                "WARNING: The Slave01 emd Alarm2 Active."
        ::= 58

ipduSlave01EmdAlarm2Normal TRAP-TYPE
        ENTERPRISE      ipduTraps
        DESCRIPTION
                "INFORMATION: The Slave01 emd Alarm2 Normal."
        ::= 59

ipduSlave01Outlet01CurrentOverTh TRAP-TYPE
        ENTERPRISE      ipduTraps
        DESCRIPTION
                "CRITICAL: The Slave01 Outlet01 Current over threshold."
        ::= 60

ipduSlave01Outlet01CurrentNotOverTh TRAP-TYPE
        ENTERPRISE      ipduTraps
        DESCRIPTION
                "WARNING: The Slave01 Outlet01 Current not over threshold."
        ::= 61

ipduSlave01Outlet02CurrentOverTh TRAP-TYPE
        ENTERPRISE      ipduTraps
        DESCRIPTION
                "CRITICAL: The Slave01 Outlet02 Current over threshold."
        ::= 62

ipduSlave01Outlet02CurrentNotOverTh TRAP-TYPE
        ENTERPRISE      ipduTraps
        DESCRIPTION
                "WARNING: The Slave01 Outlet02 Current not over threshold."
        ::= 63

ipduSlave01Outlet03CurrentOverTh TRAP-TYPE
        ENTERPRISE      ipduTraps
        DESCRIPTION
                "CRITICAL: The Slave01 Outlet03 Current over threshold."
        ::= 64

ipduSlave01Outlet03CurrentNotOverTh TRAP-TYPE
        ENTERPRISE      ipduTraps
        DESCRIPTION
                "WARNING: The Slave01 Outlet03 Current not over threshold."
        ::= 65

ipduSlave01Outlet04CurrentOverTh TRAP-TYPE
        ENTERPRISE      ipduTraps
        DESCRIPTION
                "CRITICAL: The Slave01 Outlet04 Current over threshold."
        ::= 66

ipduSlave01Outlet04CurrentNotOverTh TRAP-TYPE
        ENTERPRISE      ipduTraps
        DESCRIPTION
                "WARNING: The Slave01 Outlet04 Current not over threshold."
        ::= 67

ipduSlave01Outlet05CurrentOverTh TRAP-TYPE
        ENTERPRISE      ipduTraps
        DESCRIPTION
                "CRITICAL: The Slave01 Outlet05 Current over threshold."
        ::= 68

ipduSlave01Outlet05CurrentNotOverTh TRAP-TYPE
        ENTERPRISE      ipduTraps
        DESCRIPTION
                "WARNING: The Slave01 Outlet05 Current not over threshold."
        ::= 69

ipduSlave01Outlet06CurrentOverTh TRAP-TYPE
        ENTERPRISE      ipduTraps
        DESCRIPTION
                "CRITICAL: The Slave01 Outlet06 Current over threshold."
        ::= 70

ipduSlave01Outlet06CurrentNotOverTh TRAP-TYPE
        ENTERPRISE      ipduTraps
        DESCRIPTION
                "WARNING: The Slave01 Outlet06 Current not over threshold."
        ::= 71

ipduSlave01Outlet07CurrentOverTh TRAP-TYPE
        ENTERPRISE      ipduTraps
        DESCRIPTION
                "CRITICAL: The Slave01 Outlet07 Current over threshold."
        ::= 72

ipduSlave01Outlet07CurrentNotOverTh TRAP-TYPE
        ENTERPRISE      ipduTraps
        DESCRIPTION
                "WARNING: The Slave01 Outlet07 Current not over threshold."
        ::= 73

ipduSlave01Outlet08CurrentOverTh TRAP-TYPE
        ENTERPRISE      ipduTraps
        DESCRIPTION
                "CRITICAL: The Slave01 Outlet08 Current over threshold."
        ::= 74

ipduSlave01Outlet08CurrentNotOverTh TRAP-TYPE
        ENTERPRISE      ipduTraps
        DESCRIPTION
                "WARNING: The Slave01 Outlet08 Current not over threshold."
        ::= 75

ipduSlave01Outlet09CurrentOverTh TRAP-TYPE
        ENTERPRISE      ipduTraps
        DESCRIPTION
                "CRITICAL: The Slave01 Outlet09 Current over threshold."
        ::= 76

ipduSlave01Outlet09CurrentNotOverTh TRAP-TYPE
        ENTERPRISE      ipduTraps
        DESCRIPTION
                "WARNING: The Slave01 Outlet09 Current not over threshold."
        ::= 77

ipduSlave01Outlet10CurrentOverTh TRAP-TYPE
        ENTERPRISE      ipduTraps
        DESCRIPTION
                "CRITICAL: The Slave01 Outlet10 Current over threshold."
        ::= 78

ipduSlave01Outlet10CurrentNotOverTh TRAP-TYPE
        ENTERPRISE      ipduTraps
        DESCRIPTION
                "WARNING: The Slave01 Outlet10 Current not over threshold."
        ::= 79

ipduSlave01Outlet11CurrentOverTh TRAP-TYPE
        ENTERPRISE      ipduTraps
        DESCRIPTION
                "CRITICAL: The Slave01 Outlet11 Current over threshold."
        ::= 80

ipduSlave01Outlet11CurrentNotOverTh TRAP-TYPE
        ENTERPRISE      ipduTraps
        DESCRIPTION
                "WARNING: The Slave01 Outlet11 Current not over threshold."
        ::= 81

ipduSlave01Outlet12CurrentOverTh TRAP-TYPE
        ENTERPRISE      ipduTraps
        DESCRIPTION
                "CRITICAL: The Slave01 Outlet12 Current over threshold."
        ::= 82

ipduSlave01Outlet12CurrentNotOverTh TRAP-TYPE
        ENTERPRISE      ipduTraps
        DESCRIPTION
                "WARNING: The Slave01 Outlet12 Current not over threshold."
        ::= 83

--==========================================================================
-- Slave02 trap
--==========================================================================
ipduSlave02Inlet01OverHigh TRAP-TYPE
        ENTERPRISE      ipduTraps
        DESCRIPTION
                "CRITICAL: The Slave02 input01 voltage over high threshold."
        ::= 84

ipduSlave02Inlet01NotOverHigh TRAP-TYPE
        ENTERPRISE      ipduTraps
        DESCRIPTION
                "WARNING: The Slave02 input01 voltage Not over high threshold."
        ::= 85

ipduSlave02Inlet02OverHigh TRAP-TYPE
        ENTERPRISE      ipduTraps
        DESCRIPTION
                "CRITICAL: The Slave02 input02 voltage over high threshold."
        ::= 86

ipduSlave02Inlet02NotOverHigh TRAP-TYPE
        ENTERPRISE      ipduTraps
        DESCRIPTION
                "WARNING: The Slave02 input02 voltage Not over high threshold."
        ::= 87

ipduSlave02Inlet01UnderLow TRAP-TYPE
        ENTERPRISE      ipduTraps
        DESCRIPTION
                "CRITICAL: The Slave02 input01 voltage under low threshold."
        ::= 88

ipduSlave02Inlet01NotUnderLow TRAP-TYPE
        ENTERPRISE      ipduTraps
        DESCRIPTION
                "WARNING: The Slave02 input01 voltage Not under low threshold."
        ::= 89

ipduSlave02Inlet02UnderLow TRAP-TYPE
        ENTERPRISE      ipduTraps
        DESCRIPTION
                "CRITICAL: The Slave02 input02 voltage under low threshold."
        ::= 90

ipduSlave02Inlet02NotUnderLow TRAP-TYPE
        ENTERPRISE      ipduTraps
        DESCRIPTION
                "WARNING: The Slave02 input02 voltage Not under low threshold."
        ::= 91

ipduSlave02Inlet01CurrentOverTh TRAP-TYPE
        ENTERPRISE      ipduTraps
        DESCRIPTION
                "CRITICAL: The Slave02 input01 current over high threshold."
        ::= 92

ipduSlave02Inlet01NotCurrentOverTh TRAP-TYPE
        ENTERPRISE      ipduTraps
        DESCRIPTION
                "WARNING: The Slave02 input01 current not over high threshold."
        ::= 93

ipduSlave02Inlet02CurrentOverTh TRAP-TYPE
        ENTERPRISE      ipduTraps
        DESCRIPTION
                "CRITICAL: The Slave02 input02 current over high threshold."
        ::= 94

ipduSlave02Inlet02NotCurrentOverTh TRAP-TYPE
        ENTERPRISE      ipduTraps
        DESCRIPTION
                "WARNING: The Slave02 input02 current not over high threshold."
        ::= 95

ipduSlave02EmdTemperatureTooHigh TRAP-TYPE
        ENTERPRISE      ipduTraps
        DESCRIPTION
                "WARNING: The Slave02 emd Temperature Too High."
        ::= 96

ipduSlave02EmdTemperatureNotHigh TRAP-TYPE
        ENTERPRISE      ipduTraps
        DESCRIPTION
                "INFORMATION: The Slave02 emd Temperature Not High."
        ::= 97

ipduSlave02EmdTemperatureTooLow TRAP-TYPE
        ENTERPRISE      ipduTraps
        DESCRIPTION
                "WARNING: The Slave02 emd Temperature Too Low."
        ::= 98

ipduSlave02EmdTemperatureNotLow TRAP-TYPE
        ENTERPRISE      ipduTraps
        DESCRIPTION
                "INFORMATION: The Slave02 emd Temperature Not Low."
        ::= 99

ipduSlave02EmdHumidityTooHigh TRAP-TYPE
        ENTERPRISE      ipduTraps
        DESCRIPTION
                "WARNING: The Slave02 emd Humidity Too High."
        ::= 100

ipduSlave02EmdHumidityNotHigh TRAP-TYPE
        ENTERPRISE      ipduTraps
        DESCRIPTION
                "INFORMATION: The Slave02 emd Humidity Not High."
        ::= 101

ipduSlave02EmdHumidityTooLow TRAP-TYPE
        ENTERPRISE      ipduTraps
        DESCRIPTION
                "WARNING: The Slave02 emd Humidity Too Low."
        ::= 102

ipduSlave02EmdHumidityNotLow TRAP-TYPE
        ENTERPRISE      ipduTraps
        DESCRIPTION
                "INFORMATION: The Slave02 emd Humidity Not Low."
        ::= 103

ipduSlave02EmdAlarm1Active TRAP-TYPE
        ENTERPRISE      ipduTraps
        DESCRIPTION
                "WARNING: The Slave02 emd Alarm1 Active."
        ::= 104

ipduSlave02EmdAlarm1Normal TRAP-TYPE
        ENTERPRISE      ipduTraps
        DESCRIPTION
                "INFORMATION: The Slave02 emd Alarm1 Normal."
        ::= 105

ipduSlave02EmdAlarm2Active TRAP-TYPE
        ENTERPRISE      ipduTraps
        DESCRIPTION
                "WARNING: The Slave02 emd Alarm2 Active."
        ::= 106

ipduSlave02EmdAlarm2Normal TRAP-TYPE
        ENTERPRISE      ipduTraps
        DESCRIPTION
                "INFORMATION: The Slave02 emd Alarm2 Normal."
        ::= 107

ipduSlave02Outlet01CurrentOverTh TRAP-TYPE
        ENTERPRISE      ipduTraps
        DESCRIPTION
                "CRITICAL: The Slave02 Outlet01 Current over threshold."
        ::= 108

ipduSlave02Outlet01CurrentNotOverTh TRAP-TYPE
        ENTERPRISE      ipduTraps
        DESCRIPTION
                "WARNING: The Slave02 Outlet01 Current not over threshold."
        ::= 109

ipduSlave02Outlet02CurrentOverTh TRAP-TYPE
        ENTERPRISE      ipduTraps
        DESCRIPTION
                "CRITICAL: The Slave02 Outlet02 Current over threshold."
        ::= 110

ipduSlave02Outlet02CurrentNotOverTh TRAP-TYPE
        ENTERPRISE      ipduTraps
        DESCRIPTION
                "WARNING: The Slave02 Outlet02 Current not over threshold."
        ::= 111

ipduSlave02Outlet03CurrentOverTh TRAP-TYPE
        ENTERPRISE      ipduTraps
        DESCRIPTION
                "CRITICAL: The Slave02 Outlet03 Current over threshold."
        ::= 112

ipduSlave02Outlet03CurrentNotOverTh TRAP-TYPE
        ENTERPRISE      ipduTraps
        DESCRIPTION
                "WARNING: The Slave02 Outlet03 Current not over threshold."
        ::= 113

ipduSlave02Outlet04CurrentOverTh TRAP-TYPE
        ENTERPRISE      ipduTraps
        DESCRIPTION
                "CRITICAL: The Slave02 Outlet04 Current over threshold."
        ::= 114

ipduSlave02Outlet04CurrentNotOverTh TRAP-TYPE
        ENTERPRISE      ipduTraps
        DESCRIPTION
                "WARNING: The Slave02 Outlet04 Current not over threshold."
        ::= 115

ipduSlave02Outlet05CurrentOverTh TRAP-TYPE
        ENTERPRISE      ipduTraps
        DESCRIPTION
                "CRITICAL: The Slave02 Outlet05 Current over threshold."
        ::= 116

ipduSlave02Outlet05CurrentNotOverTh TRAP-TYPE
        ENTERPRISE      ipduTraps
        DESCRIPTION
                "WARNING: The Slave02 Outlet05 Current not over threshold."
        ::= 117

ipduSlave02Outlet06CurrentOverTh TRAP-TYPE
        ENTERPRISE      ipduTraps
        DESCRIPTION
                "CRITICAL: The Slave02 Outlet06 Current over threshold."
        ::= 118

ipduSlave02Outlet06CurrentNotOverTh TRAP-TYPE
        ENTERPRISE      ipduTraps
        DESCRIPTION
                "WARNING: The Slave02 Outlet06 Current not over threshold."
        ::= 119

ipduSlave02Outlet07CurrentOverTh TRAP-TYPE
        ENTERPRISE      ipduTraps
        DESCRIPTION
                "CRITICAL: The Slave02 Outlet07 Current over threshold."
        ::= 120

ipduSlave02Outlet07CurrentNotOverTh TRAP-TYPE
        ENTERPRISE      ipduTraps
        DESCRIPTION
                "WARNING: The Slave02 Outlet07 Current not over threshold."
        ::= 121

ipduSlave02Outlet08CurrentOverTh TRAP-TYPE
        ENTERPRISE      ipduTraps
        DESCRIPTION
                "CRITICAL: The Slave02 Outlet08 Current over threshold."
        ::= 122

ipduSlave02Outlet08CurrentNotOverTh TRAP-TYPE
        ENTERPRISE      ipduTraps
        DESCRIPTION
                "WARNING: The Slave02 Outlet08 Current not over threshold."
        ::= 123

ipduSlave02Outlet09CurrentOverTh TRAP-TYPE
        ENTERPRISE      ipduTraps
        DESCRIPTION
                "CRITICAL: The Slave02 Outlet09 Current over threshold."
        ::= 124

ipduSlave02Outlet09CurrentNotOverTh TRAP-TYPE
        ENTERPRISE      ipduTraps
        DESCRIPTION
                "WARNING: The Slave02 Outlet09 Current not over threshold."
        ::= 125

ipduSlave02Outlet10CurrentOverTh TRAP-TYPE
        ENTERPRISE      ipduTraps
        DESCRIPTION
                "CRITICAL: The Slave02 Outlet10 Current over threshold."
        ::= 126

ipduSlave02Outlet10CurrentNotOverTh TRAP-TYPE
        ENTERPRISE      ipduTraps
        DESCRIPTION
                "WARNING: The Slave02 Outlet10 Current not over threshold."
        ::= 127

ipduSlave02Outlet11CurrentOverTh TRAP-TYPE
        ENTERPRISE      ipduTraps
        DESCRIPTION
                "CRITICAL: The Slave02 Outlet11 Current over threshold."
        ::= 128

ipduSlave02Outlet11CurrentNotOverTh TRAP-TYPE
        ENTERPRISE      ipduTraps
        DESCRIPTION
                "WARNING: The Slave02 Outlet11 Current not over threshold."
        ::= 129

ipduSlave02Outlet12CurrentOverTh TRAP-TYPE
        ENTERPRISE      ipduTraps
        DESCRIPTION
                "CRITICAL: The Slave02 Outlet12 Current over threshold."
        ::= 130

ipduSlave02Outlet12CurrentNotOverTh TRAP-TYPE
        ENTERPRISE      ipduTraps
        DESCRIPTION
                "WARNING: The Slave02 Outlet12 Current not over threshold."
        ::= 131
--==========================================================================
-- Slave03 trap
--==========================================================================
ipduSlave03Inlet01OverHigh TRAP-TYPE
        ENTERPRISE      ipduTraps
        DESCRIPTION
                "CRITICAL: The Slave03 input01 voltage over high threshold."
        ::= 132

ipduSlave03Inlet01NotOverHigh TRAP-TYPE
        ENTERPRISE      ipduTraps
        DESCRIPTION
                "WARNING: The Slave03 input01 voltage Not over high threshold."
        ::= 133

ipduSlave03Inlet02OverHigh TRAP-TYPE
        ENTERPRISE      ipduTraps
        DESCRIPTION
                "CRITICAL: The Slave03 input02 voltage over high threshold."
        ::= 134

ipduSlave03Inlet02NotOverHigh TRAP-TYPE
        ENTERPRISE      ipduTraps
        DESCRIPTION
                "WARNING: The Slave03 input02 voltage Not over high threshold."
        ::= 135

ipduSlave03Inlet01UnderLow TRAP-TYPE
        ENTERPRISE      ipduTraps
        DESCRIPTION
                "CRITICAL: The Slave03 input01 voltage under low threshold."
        ::= 136

ipduSlave03Inlet01NotUnderLow TRAP-TYPE
        ENTERPRISE      ipduTraps
        DESCRIPTION
                "WARNING: The Slave03 input01 voltage Not under low threshold."
        ::= 137

ipduSlave03Inlet02UnderLow TRAP-TYPE
        ENTERPRISE      ipduTraps
        DESCRIPTION
                "CRITICAL: The Slave03 input02 voltage under low threshold."
        ::= 138

ipduSlave03Inlet02NotUnderLow TRAP-TYPE
        ENTERPRISE      ipduTraps
        DESCRIPTION
                "WARNING: The Slave03 input02 voltage Not under low threshold."
        ::= 139

ipduSlave03Inlet01CurrentOverTh TRAP-TYPE
        ENTERPRISE      ipduTraps
        DESCRIPTION
                "CRITICAL: The Slave03 input01 current over high threshold."
        ::= 140

ipduSlave03Inlet01NotCurrentOverTh TRAP-TYPE
        ENTERPRISE      ipduTraps
        DESCRIPTION
                "WARNING: The Slave03 input01 current not over high threshold."
        ::= 141

ipduSlave03Inlet02CurrentOverTh TRAP-TYPE
        ENTERPRISE      ipduTraps
        DESCRIPTION
                "CRITICAL: The Slave03 input02 current over high threshold."
        ::= 142

ipduSlave03Inlet02NotCurrentOverTh TRAP-TYPE
        ENTERPRISE      ipduTraps
        DESCRIPTION
                "WARNING: The Slave03 input02 current not over high threshold."
        ::= 143

ipduSlave03EmdTemperatureTooHigh TRAP-TYPE
        ENTERPRISE      ipduTraps
        DESCRIPTION
                "WARNING: The Slave03 emd Temperature Too High."
        ::= 144

ipduSlave03EmdTemperatureNotHigh TRAP-TYPE
        ENTERPRISE      ipduTraps
        DESCRIPTION
                "INFORMATION: The Slave03 emd Temperature Not High."
        ::= 145

ipduSlave03EmdTemperatureTooLow TRAP-TYPE
        ENTERPRISE      ipduTraps
        DESCRIPTION
                "WARNING: The Slave03 emd Temperature Too Low."
        ::= 146

ipduSlave03EmdTemperatureNotLow TRAP-TYPE
        ENTERPRISE      ipduTraps
        DESCRIPTION
                "INFORMATION: The Slave03 emd Temperature Not Low."
        ::= 147

ipduSlave03EmdHumidityTooHigh TRAP-TYPE
        ENTERPRISE      ipduTraps
        DESCRIPTION
                "WARNING: The Slave03 emd Humidity Too High."
        ::= 148

ipduSlave03EmdHumidityNotHigh TRAP-TYPE
        ENTERPRISE      ipduTraps
        DESCRIPTION
                "INFORMATION: The Slave03 emd Humidity Not High."
        ::= 149

ipduSlave03EmdHumidityTooLow TRAP-TYPE
        ENTERPRISE      ipduTraps
        DESCRIPTION
                "WARNING: The Slave03 emd Humidity Too Low."
        ::= 150

ipduSlave03EmdHumidityNotLow TRAP-TYPE
        ENTERPRISE      ipduTraps
        DESCRIPTION
                "INFORMATION: The Slave03 emd Humidity Not Low."
        ::= 151

ipduSlave03EmdAlarm1Active TRAP-TYPE
        ENTERPRISE      ipduTraps
        DESCRIPTION
                "WARNING: The Slave03 emd Alarm1 Active."
        ::= 152

ipduSlave03EmdAlarm1Normal TRAP-TYPE
        ENTERPRISE      ipduTraps
        DESCRIPTION
                "INFORMATION: The Slave03 emd Alarm1 Normal."
        ::= 153

ipduSlave03EmdAlarm2Active TRAP-TYPE
        ENTERPRISE      ipduTraps
        DESCRIPTION
                "WARNING: The Slave03 emd Alarm2 Active."
        ::= 154

ipduSlave03EmdAlarm2Normal TRAP-TYPE
        ENTERPRISE      ipduTraps
        DESCRIPTION
                "INFORMATION: The Slave03 emd Alarm2 Normal."
        ::= 155

ipduSlave03Outlet01CurrentOverTh TRAP-TYPE
        ENTERPRISE      ipduTraps
        DESCRIPTION
                "CRITICAL: The Slave03 Outlet01 Current over threshold."
        ::= 156

ipduSlave03Outlet01CurrentNotOverTh TRAP-TYPE
        ENTERPRISE      ipduTraps
        DESCRIPTION
                "WARNING: The Slave03 Outlet01 Current not over threshold."
        ::= 157

ipduSlave03Outlet02CurrentOverTh TRAP-TYPE
        ENTERPRISE      ipduTraps
        DESCRIPTION
                "CRITICAL: The Slave03 Outlet02 Current over threshold."
        ::= 158

ipduSlave03Outlet02CurrentNotOverTh TRAP-TYPE
        ENTERPRISE      ipduTraps
        DESCRIPTION
                "WARNING: The Slave03 Outlet02 Current not over threshold."
        ::= 159

ipduSlave03Outlet03CurrentOverTh TRAP-TYPE
        ENTERPRISE      ipduTraps
        DESCRIPTION
                "CRITICAL: The Slave03 Outlet03 Current over threshold."
        ::= 160

ipduSlave03Outlet03CurrentNotOverTh TRAP-TYPE
        ENTERPRISE      ipduTraps
        DESCRIPTION
                "WARNING: The Slave03 Outlet03 Current not over threshold."
        ::= 161

ipduSlave03Outlet04CurrentOverTh TRAP-TYPE
        ENTERPRISE      ipduTraps
        DESCRIPTION
                "CRITICAL: The Slave03 Outlet04 Current over threshold."
        ::= 162

ipduSlave03Outlet04CurrentNotOverTh TRAP-TYPE
        ENTERPRISE      ipduTraps
        DESCRIPTION
                "WARNING: The Slave03 Outlet04 Current not over threshold."
        ::= 163

ipduSlave03Outlet05CurrentOverTh TRAP-TYPE
        ENTERPRISE      ipduTraps
        DESCRIPTION
                "CRITICAL: The Slave03 Outlet05 Current over threshold."
        ::= 164

ipduSlave03Outlet05CurrentNotOverTh TRAP-TYPE
        ENTERPRISE      ipduTraps
        DESCRIPTION
                "WARNING: The Slave03 Outlet05 Current not over threshold."
        ::= 165

ipduSlave03Outlet06CurrentOverTh TRAP-TYPE
        ENTERPRISE      ipduTraps
        DESCRIPTION
                "CRITICAL: The Slave03 Outlet06 Current over threshold."
        ::= 166

ipduSlave03Outlet06CurrentNotOverTh TRAP-TYPE
        ENTERPRISE      ipduTraps
        DESCRIPTION
                "WARNING: The Slave03 Outlet06 Current not over threshold."
        ::= 167

ipduSlave03Outlet07CurrentOverTh TRAP-TYPE
        ENTERPRISE      ipduTraps
        DESCRIPTION
                "CRITICAL: The Slave03 Outlet07 Current over threshold."
        ::= 168

ipduSlave03Outlet07CurrentNotOverTh TRAP-TYPE
        ENTERPRISE      ipduTraps
        DESCRIPTION
                "WARNING: The Slave03 Outlet07 Current not over threshold."
        ::= 169

ipduSlave03Outlet08CurrentOverTh TRAP-TYPE
        ENTERPRISE      ipduTraps
        DESCRIPTION
                "CRITICAL: The Slave03 Outlet08 Current over threshold."
        ::= 170

ipduSlave03Outlet08CurrentNotOverTh TRAP-TYPE
        ENTERPRISE      ipduTraps
        DESCRIPTION
                "WARNING: The Slave03 Outlet08 Current not over threshold."
        ::= 171

ipduSlave03Outlet09CurrentOverTh TRAP-TYPE
        ENTERPRISE      ipduTraps
        DESCRIPTION
                "CRITICAL: The Slave03 Outlet09 Current over threshold."
        ::= 172

ipduSlave03Outlet09CurrentNotOverTh TRAP-TYPE
        ENTERPRISE      ipduTraps
        DESCRIPTION
                "WARNING: The Slave03 Outlet09 Current not over threshold."
        ::= 173

ipduSlave03Outlet10CurrentOverTh TRAP-TYPE
        ENTERPRISE      ipduTraps
        DESCRIPTION
                "CRITICAL: The Slave03 Outlet10 Current over threshold."
        ::= 174

ipduSlave03Outlet10CurrentNotOverTh TRAP-TYPE
        ENTERPRISE      ipduTraps
        DESCRIPTION
                "WARNING: The Slave03 Outlet10 Current not over threshold."
        ::= 175

ipduSlave03Outlet11CurrentOverTh TRAP-TYPE
        ENTERPRISE      ipduTraps
        DESCRIPTION
                "CRITICAL: The Slave03 Outlet11 Current over threshold."
        ::= 176

ipduSlave03Outlet11CurrentNotOverTh TRAP-TYPE
        ENTERPRISE      ipduTraps
        DESCRIPTION
                "WARNING: The Slave03 Outlet11 Current not over threshold."
        ::= 177

ipduSlave03Outlet12CurrentOverTh TRAP-TYPE
        ENTERPRISE      ipduTraps
        DESCRIPTION
                "CRITICAL: The Slave03 Outlet12 Current over threshold."
        ::= 178

ipduSlave03Outlet12CurrentNotOverTh TRAP-TYPE
        ENTERPRISE      ipduTraps
        DESCRIPTION
                "WARNING: The Slave03 Outlet12 Current not over threshold."
        ::= 179

--==========================================================================
-- Slave04 trap
--==========================================================================
ipduSlave04Inlet01OverHigh TRAP-TYPE
        ENTERPRISE      ipduTraps
        DESCRIPTION
                "CRITICAL: The Slave04 input01 voltage over high threshold."
        ::= 180

ipduSlave04Inlet01NotOverHigh TRAP-TYPE
        ENTERPRISE      ipduTraps
        DESCRIPTION
                "WARNING: The Slave04 input01 voltage Not over high threshold."
        ::= 181

ipduSlave04Inlet02OverHigh TRAP-TYPE
        ENTERPRISE      ipduTraps
        DESCRIPTION
                "CRITICAL: The Slave04 input02 voltage over high threshold."
        ::= 182

ipduSlave04Inlet02NotOverHigh TRAP-TYPE
        ENTERPRISE      ipduTraps
        DESCRIPTION
                "WARNING: The Slave04 input02 voltage Not over high threshold."
        ::= 183

ipduSlave04Inlet01UnderLow TRAP-TYPE
        ENTERPRISE      ipduTraps
        DESCRIPTION
                "CRITICAL: The Slave04 input01 voltage under low threshold."
        ::= 184

ipduSlave04Inlet01NotUnderLow TRAP-TYPE
        ENTERPRISE      ipduTraps
        DESCRIPTION
                "WARNING: The Slave04 input01 voltage Not under low threshold."
        ::= 185

ipduSlave04Inlet02UnderLow TRAP-TYPE
        ENTERPRISE      ipduTraps
        DESCRIPTION
                "CRITICAL: The Slave04 input02 voltage under low threshold."
        ::= 186

ipduSlave04Inlet02NotUnderLow TRAP-TYPE
        ENTERPRISE      ipduTraps
        DESCRIPTION
                "WARNING: The Slave04 input02 voltage Not under low threshold."
        ::= 187

ipduSlave04Inlet01CurrentOverTh TRAP-TYPE
        ENTERPRISE      ipduTraps
        DESCRIPTION
                "CRITICAL: The Slave04 input01 current over high threshold."
        ::= 188

ipduSlave04Inlet01NotCurrentOverTh TRAP-TYPE
        ENTERPRISE      ipduTraps
        DESCRIPTION
                "WARNING: The Slave04 input01 current not over high threshold."
        ::= 189

ipduSlave04Inlet02CurrentOverTh TRAP-TYPE
        ENTERPRISE      ipduTraps
        DESCRIPTION
                "CRITICAL: The Slave04 input02 current over high threshold."
        ::= 190

ipduSlave04Inlet02NotCurrentOverTh TRAP-TYPE
        ENTERPRISE      ipduTraps
        DESCRIPTION
                "WARNING: The Slave04 input02 current not over high threshold."
        ::= 191

ipduSlave04EmdTemperatureTooHigh TRAP-TYPE
        ENTERPRISE      ipduTraps
        DESCRIPTION
                "WARNING: The Slave04 emd Temperature Too High."
        ::= 192

ipduSlave04EmdTemperatureNotHigh TRAP-TYPE
        ENTERPRISE      ipduTraps
        DESCRIPTION
                "INFORMATION: The Slave04 emd Temperature Not High."
        ::= 193

ipduSlave04EmdTemperatureTooLow TRAP-TYPE
        ENTERPRISE      ipduTraps
        DESCRIPTION
                "WARNING: The Slave04 emd Temperature Too Low."
        ::= 194

ipduSlave04EmdTemperatureNotLow TRAP-TYPE
        ENTERPRISE      ipduTraps
        DESCRIPTION
                "INFORMATION: The Slave04 emd Temperature Not Low."
        ::= 195

ipduSlave04EmdHumidityTooHigh TRAP-TYPE
        ENTERPRISE      ipduTraps
        DESCRIPTION
                "WARNING: The Slave04 emd Humidity Too High."
        ::= 196

ipduSlave04EmdHumidityNotHigh TRAP-TYPE
        ENTERPRISE      ipduTraps
        DESCRIPTION
                "INFORMATION: The Slave04 emd Humidity Not High."
        ::= 197

ipduSlave04EmdHumidityTooLow TRAP-TYPE
        ENTERPRISE      ipduTraps
        DESCRIPTION
                "WARNING: The Slave04 emd Humidity Too Low."
        ::= 198

ipduSlave04EmdHumidityNotLow TRAP-TYPE
        ENTERPRISE      ipduTraps
        DESCRIPTION
                "INFORMATION: The Slave04 emd Humidity Not Low."
        ::= 199

ipduSlave04EmdAlarm1Active TRAP-TYPE
        ENTERPRISE      ipduTraps
        DESCRIPTION
                "WARNING: The Slave04 emd Alarm1 Active."
        ::= 200

ipduSlave04EmdAlarm1Normal TRAP-TYPE
        ENTERPRISE      ipduTraps
        DESCRIPTION
                "INFORMATION: The Slave04 emd Alarm1 Normal."
        ::= 201

ipduSlave04EmdAlarm2Active TRAP-TYPE
        ENTERPRISE      ipduTraps
        DESCRIPTION
                "WARNING: The Slave04 emd Alarm2 Active."
        ::= 202

ipduSlave04EmdAlarm2Normal TRAP-TYPE
        ENTERPRISE      ipduTraps
        DESCRIPTION
                "INFORMATION: The Slave04 emd Alarm2 Normal."
        ::= 203

ipduSlave04Outlet01CurrentOverTh TRAP-TYPE
        ENTERPRISE      ipduTraps
        DESCRIPTION
                "CRITICAL: The Slave04 Outlet01 Current over threshold."
        ::= 204

ipduSlave04Outlet01CurrentNotOverTh TRAP-TYPE
        ENTERPRISE      ipduTraps
        DESCRIPTION
                "WARNING: The Slave04 Outlet01 Current not over threshold."
        ::= 205

ipduSlave04Outlet02CurrentOverTh TRAP-TYPE
        ENTERPRISE      ipduTraps
        DESCRIPTION
                "CRITICAL: The Slave04 Outlet02 Current over threshold."
        ::= 206

ipduSlave04Outlet02CurrentNotOverTh TRAP-TYPE
        ENTERPRISE      ipduTraps
        DESCRIPTION
                "WARNING: The Slave04 Outlet02 Current not over threshold."
        ::= 207

ipduSlave04Outlet03CurrentOverTh TRAP-TYPE
        ENTERPRISE      ipduTraps
        DESCRIPTION
                "CRITICAL: The Slave04 Outlet03 Current over threshold."
        ::= 208

ipduSlave04Outlet03CurrentNotOverTh TRAP-TYPE
        ENTERPRISE      ipduTraps
        DESCRIPTION
                "WARNING: The Slave04 Outlet03 Current not over threshold."
        ::= 209

ipduSlave04Outlet04CurrentOverTh TRAP-TYPE
        ENTERPRISE      ipduTraps
        DESCRIPTION
                "CRITICAL: The Slave04 Outlet04 Current over threshold."
        ::= 210

ipduSlave04Outlet04CurrentNotOverTh TRAP-TYPE
        ENTERPRISE      ipduTraps
        DESCRIPTION
                "WARNING: The Slave04 Outlet04 Current not over threshold."
        ::= 211

ipduSlave04Outlet05CurrentOverTh TRAP-TYPE
        ENTERPRISE      ipduTraps
        DESCRIPTION
                "CRITICAL: The Slave04 Outlet05 Current over threshold."
        ::= 212

ipduSlave04Outlet05CurrentNotOverTh TRAP-TYPE
        ENTERPRISE      ipduTraps
        DESCRIPTION
                "WARNING: The Slave04 Outlet05 Current not over threshold."
        ::= 213

ipduSlave04Outlet06CurrentOverTh TRAP-TYPE
        ENTERPRISE      ipduTraps
        DESCRIPTION
                "CRITICAL: The Slave04 Outlet06 Current over threshold."
        ::= 214

ipduSlave04Outlet06CurrentNotOverTh TRAP-TYPE
        ENTERPRISE      ipduTraps
        DESCRIPTION
                "WARNING: The Slave04 Outlet06 Current not over threshold."
        ::= 215

ipduSlave04Outlet07CurrentOverTh TRAP-TYPE
        ENTERPRISE      ipduTraps
        DESCRIPTION
                "CRITICAL: The Slave04 Outlet07 Current over threshold."
        ::= 216

ipduSlave04Outlet07CurrentNotOverTh TRAP-TYPE
        ENTERPRISE      ipduTraps
        DESCRIPTION
                "WARNING: The Slave04 Outlet07 Current not over threshold."
        ::= 217

ipduSlave04Outlet08CurrentOverTh TRAP-TYPE
        ENTERPRISE      ipduTraps
        DESCRIPTION
                "CRITICAL: The Slave04 Outlet08 Current over threshold."
        ::= 218

ipduSlave04Outlet08CurrentNotOverTh TRAP-TYPE
        ENTERPRISE      ipduTraps
        DESCRIPTION
                "WARNING: The Slave04 Outlet08 Current not over threshold."
        ::= 219

ipduSlave04Outlet09CurrentOverTh TRAP-TYPE
        ENTERPRISE      ipduTraps
        DESCRIPTION
                "CRITICAL: The Slave04 Outlet09 Current over threshold."
        ::= 220

ipduSlave04Outlet09CurrentNotOverTh TRAP-TYPE
        ENTERPRISE      ipduTraps
        DESCRIPTION
                "WARNING: The Slave04 Outlet09 Current not over threshold."
        ::= 221

ipduSlave04Outlet10CurrentOverTh TRAP-TYPE
        ENTERPRISE      ipduTraps
        DESCRIPTION
                "CRITICAL: The Slave04 Outlet10 Current over threshold."
        ::= 222

ipduSlave04Outlet10CurrentNotOverTh TRAP-TYPE
        ENTERPRISE      ipduTraps
        DESCRIPTION
                "WARNING: The Slave04 Outlet10 Current not over threshold."
        ::= 223

ipduSlave04Outlet11CurrentOverTh TRAP-TYPE
        ENTERPRISE      ipduTraps
        DESCRIPTION
                "CRITICAL: The Slave04 Outlet11 Current over threshold."
        ::= 224

ipduSlave04Outlet11CurrentNotOverTh TRAP-TYPE
        ENTERPRISE      ipduTraps
        DESCRIPTION
                "WARNING: The Slave04 Outlet11 Current not over threshold."
        ::= 225

ipduSlave04Outlet12CurrentOverTh TRAP-TYPE
        ENTERPRISE      ipduTraps
        DESCRIPTION
                "CRITICAL: The Slave04 Outlet12 Current over threshold."
        ::= 226

ipduSlave04Outlet12CurrentNotOverTh TRAP-TYPE
        ENTERPRISE      ipduTraps
        DESCRIPTION
                "WARNING: The Slave04 Outlet12 Current not over threshold."
        ::= 227

--==========================================================================
-- Slave05 trap
--==========================================================================
ipduSlave05Inlet01OverHigh TRAP-TYPE
        ENTERPRISE      ipduTraps
        DESCRIPTION
                "CRITICAL: The Slave05 input01 voltage over high threshold."
        ::= 228

ipduSlave05Inlet01NotOverHigh TRAP-TYPE
        ENTERPRISE      ipduTraps
        DESCRIPTION
                "WARNING: The Slave05 input01 voltage Not over high threshold."
        ::= 229

ipduSlave05Inlet02OverHigh TRAP-TYPE
        ENTERPRISE      ipduTraps
        DESCRIPTION
                "CRITICAL: The Slave05 input02 voltage over high threshold."
        ::= 230

ipduSlave05Inlet02NotOverHigh TRAP-TYPE
        ENTERPRISE      ipduTraps
        DESCRIPTION
                "WARNING: The Slave05 input02 voltage Not over high threshold."
        ::= 231

ipduSlave05Inlet01UnderLow TRAP-TYPE
        ENTERPRISE      ipduTraps
        DESCRIPTION
                "CRITICAL: The Slave05 input01 voltage under low threshold."
        ::= 232

ipduSlave05Inlet01NotUnderLow TRAP-TYPE
        ENTERPRISE      ipduTraps
        DESCRIPTION
                "WARNING: The Slave05 input01 voltage Not under low threshold."
        ::= 233

ipduSlave05Inlet02UnderLow TRAP-TYPE
        ENTERPRISE      ipduTraps
        DESCRIPTION
                "CRITICAL: The Slave05 input02 voltage under low threshold."
        ::= 234

ipduSlave05Inlet02NotUnderLow TRAP-TYPE
        ENTERPRISE      ipduTraps
        DESCRIPTION
                "WARNING: The Slave05 input02 voltage Not under low threshold."
        ::= 235

ipduSlave05Inlet01CurrentOverTh TRAP-TYPE
        ENTERPRISE      ipduTraps
        DESCRIPTION
                "CRITICAL: The Slave05 input01 current over high threshold."
        ::= 236

ipduSlave05Inlet01NotCurrentOverTh TRAP-TYPE
        ENTERPRISE      ipduTraps
        DESCRIPTION
                "WARNING: The Slave05 input01 current not over high threshold."
        ::= 237

ipduSlave05Inlet02CurrentOverTh TRAP-TYPE
        ENTERPRISE      ipduTraps
        DESCRIPTION
                "CRITICAL: The Slave05 input02 current over high threshold."
        ::= 238

ipduSlave05Inlet02NotCurrentOverTh TRAP-TYPE
        ENTERPRISE      ipduTraps
        DESCRIPTION
                "WARNING: The Slave05 input02 current not over high threshold."
        ::= 239

ipduSlave05EmdTemperatureTooHigh TRAP-TYPE
        ENTERPRISE      ipduTraps
        DESCRIPTION
                "WARNING: The Slave05 emd Temperature Too High."
        ::= 240

ipduSlave05EmdTemperatureNotHigh TRAP-TYPE
        ENTERPRISE      ipduTraps
        DESCRIPTION
                "INFORMATION: The Slave05 emd Temperature Not High."
        ::= 241

ipduSlave05EmdTemperatureTooLow TRAP-TYPE
        ENTERPRISE      ipduTraps
        DESCRIPTION
                "WARNING: The Slave05 emd Temperature Too Low."
        ::= 242

ipduSlave05EmdTemperatureNotLow TRAP-TYPE
        ENTERPRISE      ipduTraps
        DESCRIPTION
                "INFORMATION: The Slave05 emd Temperature Not Low."
        ::= 243

ipduSlave05EmdHumidityTooHigh TRAP-TYPE
        ENTERPRISE      ipduTraps
        DESCRIPTION
                "WARNING: The Slave05 emd Humidity Too High."
        ::= 244

ipduSlave05EmdHumidityNotHigh TRAP-TYPE
        ENTERPRISE      ipduTraps
        DESCRIPTION
                "INFORMATION: The Slave05 emd Humidity Not High."
        ::= 245

ipduSlave05EmdHumidityTooLow TRAP-TYPE
        ENTERPRISE      ipduTraps
        DESCRIPTION
                "WARNING: The Slave05 emd Humidity Too Low."
        ::= 246

ipduSlave05EmdHumidityNotLow TRAP-TYPE
        ENTERPRISE      ipduTraps
        DESCRIPTION
                "INFORMATION: The Slave05 emd Humidity Not Low."
        ::= 247

ipduSlave05EmdAlarm1Active TRAP-TYPE
        ENTERPRISE      ipduTraps
        DESCRIPTION
                "WARNING: The Slave05 emd Alarm1 Active."
        ::= 248

ipduSlave05EmdAlarm1Normal TRAP-TYPE
        ENTERPRISE      ipduTraps
        DESCRIPTION
                "INFORMATION: The Slave05 emd Alarm1 Normal."
        ::= 249

ipduSlave05EmdAlarm2Active TRAP-TYPE
        ENTERPRISE      ipduTraps
        DESCRIPTION
                "WARNING: The Slave05 emd Alarm2 Active."
        ::= 250

ipduSlave05EmdAlarm2Normal TRAP-TYPE
        ENTERPRISE      ipduTraps
        DESCRIPTION
                "INFORMATION: The Slave05 emd Alarm2 Normal."
        ::= 251

ipduSlave05Outlet01CurrentOverTh TRAP-TYPE
        ENTERPRISE      ipduTraps
        DESCRIPTION
                "CRITICAL: The Slave05 Outlet01 Current over threshold."
        ::= 252

ipduSlave05Outlet01CurrentNotOverTh TRAP-TYPE
        ENTERPRISE      ipduTraps
        DESCRIPTION
                "WARNING: The Slave05 Outlet01 Current not over threshold."
        ::= 253

ipduSlave05Outlet02CurrentOverTh TRAP-TYPE
        ENTERPRISE      ipduTraps
        DESCRIPTION
                "CRITICAL: The Slave05 Outlet02 Current over threshold."
        ::= 254

ipduSlave05Outlet02CurrentNotOverTh TRAP-TYPE
        ENTERPRISE      ipduTraps
        DESCRIPTION
                "WARNING: The Slave05 Outlet02 Current not over threshold."
        ::= 255

ipduSlave05Outlet03CurrentOverTh TRAP-TYPE
        ENTERPRISE      ipduTraps
        DESCRIPTION
                "CRITICAL: The Slave05 Outlet03 Current over threshold."
        ::= 256

ipduSlave05Outlet03CurrentNotOverTh TRAP-TYPE
        ENTERPRISE      ipduTraps
        DESCRIPTION
                "WARNING: The Slave05 Outlet03 Current not over threshold."
        ::= 257

ipduSlave05Outlet04CurrentOverTh TRAP-TYPE
        ENTERPRISE      ipduTraps
        DESCRIPTION
                "CRITICAL: The Slave05 Outlet04 Current over threshold."
        ::= 258

ipduSlave05Outlet04CurrentNotOverTh TRAP-TYPE
        ENTERPRISE      ipduTraps
        DESCRIPTION
                "WARNING: The Slave05 Outlet04 Current not over threshold."
        ::= 259

ipduSlave05Outlet05CurrentOverTh TRAP-TYPE
        ENTERPRISE      ipduTraps
        DESCRIPTION
                "CRITICAL: The Slave05 Outlet05 Current over threshold."
        ::= 260

ipduSlave05Outlet05CurrentNotOverTh TRAP-TYPE
        ENTERPRISE      ipduTraps
        DESCRIPTION
                "WARNING: The Slave05 Outlet05 Current not over threshold."
        ::= 261

ipduSlave05Outlet06CurrentOverTh TRAP-TYPE
        ENTERPRISE      ipduTraps
        DESCRIPTION
                "CRITICAL: The Slave05 Outlet06 Current over threshold."
        ::= 262

ipduSlave05Outlet06CurrentNotOverTh TRAP-TYPE
        ENTERPRISE      ipduTraps
        DESCRIPTION
                "WARNING: The Slave05 Outlet06 Current not over threshold."
        ::= 263

ipduSlave05Outlet07CurrentOverTh TRAP-TYPE
        ENTERPRISE      ipduTraps
        DESCRIPTION
                "CRITICAL: The Slave05 Outlet07 Current over threshold."
        ::= 264

ipduSlave05Outlet07CurrentNotOverTh TRAP-TYPE
        ENTERPRISE      ipduTraps
        DESCRIPTION
                "WARNING: The Slave05 Outlet07 Current not over threshold."
        ::= 265

ipduSlave05Outlet08CurrentOverTh TRAP-TYPE
        ENTERPRISE      ipduTraps
        DESCRIPTION
                "CRITICAL: The Slave05 Outlet08 Current over threshold."
        ::= 266

ipduSlave05Outlet08CurrentNotOverTh TRAP-TYPE
        ENTERPRISE      ipduTraps
        DESCRIPTION
                "WARNING: The Slave05 Outlet08 Current not over threshold."
        ::= 267

ipduSlave05Outlet09CurrentOverTh TRAP-TYPE
        ENTERPRISE      ipduTraps
        DESCRIPTION
                "CRITICAL: The Slave05 Outlet09 Current over threshold."
        ::= 268

ipduSlave05Outlet09CurrentNotOverTh TRAP-TYPE
        ENTERPRISE      ipduTraps
        DESCRIPTION
                "WARNING: The Slave05 Outlet09 Current not over threshold."
        ::= 269

ipduSlave05Outlet10CurrentOverTh TRAP-TYPE
        ENTERPRISE      ipduTraps
        DESCRIPTION
                "CRITICAL: The Slave05 Outlet10 Current over threshold."
        ::= 270

ipduSlave05Outlet10CurrentNotOverTh TRAP-TYPE
        ENTERPRISE      ipduTraps
        DESCRIPTION
                "WARNING: The Slave05 Outlet10 Current not over threshold."
        ::= 271

ipduSlave05Outlet11CurrentOverTh TRAP-TYPE
        ENTERPRISE      ipduTraps
        DESCRIPTION
                "CRITICAL: The Slave05 Outlet11 Current over threshold."
        ::= 272

ipduSlave05Outlet11CurrentNotOverTh TRAP-TYPE
        ENTERPRISE      ipduTraps
        DESCRIPTION
                "WARNING: The Slave05 Outlet11 Current not over threshold."
        ::= 273

ipduSlave05Outlet12CurrentOverTh TRAP-TYPE
        ENTERPRISE      ipduTraps
        DESCRIPTION
                "CRITICAL: The Slave05 Outlet12 Current over threshold."
        ::= 274

ipduSlave05Outlet12CurrentNotOverTh TRAP-TYPE
        ENTERPRISE      ipduTraps
        DESCRIPTION
                "WARNING: The Slave05 Outlet12 Current not over threshold."
        ::= 275

   END
