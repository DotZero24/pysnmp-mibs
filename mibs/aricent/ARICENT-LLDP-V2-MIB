-- Copyright (C) 2015 Aricent. All Rights Reserved.

-- $Id: fslldpv2.mib,v 1.6 2016/01/28 11:10:37 siva Exp $

-- This MIB defines the objects that are imported in Standard DCBX MIB
-- (LLDP-EXT-DOT1-DCBX-MIB). The objects in this MIB can not be
-- provisioned or populated. This MIB will only be used for successful
-- loading of the Standard DCBX MIB (LLDP-EXT-DOT1-DCBX-MIB).

ARICENT-LLDP-V2-MIB DEFINITIONS ::= BEGIN

IMPORTS
    MODULE-IDENTITY, OBJECT-TYPE, Integer32
        FROM SNMPv2-SMI
    lldpExtensions, LldpPortNumber
        FROM LLDP-MIB
    TimeFilter
        FROM RMON2-MIB;

-- ***********************************************************
--
-- Textual Conventions
--
-- ***********************************************************
fslldpV2MIB MODULE-IDENTITY
    LAST-UPDATED "201209050000Z"
    ORGANIZATION "ARICENT COMMUNICATIONS SOFTWARE"
    CONTACT-INFO "support@aricent.com"
    DESCRIPTION
         "The proprietary extension of LLDP MIB module to compile stdcdb mib. "
    REVISION "201209050000Z"
    DESCRIPTION
         "The proprietary extension of LLDP MIB module to compile stdcdb mib. "
   ::= { lldpExtensions 40001 }

lldpV2Objects		      OBJECT IDENTIFIER ::= { fslldpV2MIB 1 }
lldpV2Configuration       OBJECT IDENTIFIER ::= { lldpV2Objects 1 }

lldpV2RemTimeMark  OBJECT-TYPE
    SYNTAX      TimeFilter
    MAX-ACCESS  read-only
    STATUS      current
    DESCRIPTION
            "A TimeFilter for this entry. See the TimeFilter textual
            convention in IETF RFC 2021 and
            http://www.ietf.org/IESG/Implementations/RFC2021-Implementation.txt
            to see how TimeFilter works."
    ::= { lldpV2Configuration 1 }

lldpV2RemLocalIfIndex  OBJECT-TYPE
    SYNTAX      LldpPortNumber
    MAX-ACCESS  read-only
    STATUS      current
    DESCRIPTION
            "The index value used to identify the port component
            (contained in the local chassis with the LLDP agent)
            associated with this entry. The lldpRemLocalPortNum
            identifies the port on which the remote system information
            is received.

            The value of this object is used as a port index to the
            lldpRemTable."
    ::= { lldpV2Configuration 2 }

lldpV2LocPortIfIndex  OBJECT-TYPE
    SYNTAX      LldpPortNumber
    MAX-ACCESS  read-only
    STATUS      current
    DESCRIPTION
            "The index value used to identify the port component
            (contained in the local chassis with the LLDP agent)
            associated with this entry. The lldpRemLocalPortNum
            identifies the port on which the remote system information
            is received.

            The value of this object is used as a port index to the
            lldpRemTable."
    ::= { lldpV2Configuration 3 }

lldpV2RemIndex  OBJECT-TYPE
    SYNTAX      Integer32(1..2147483647)
    MAX-ACCESS  read-only
    STATUS      current
    DESCRIPTION
            "This object represents an arbitrary local integer value used
            by this agent to identify a particular connection instance,
            unique only for the indicated remote system.

            An agent is encouraged to assign monotonically increasing
            index values to new entries, starting with one, after each
            reboot. It is considered unlikely that the lldpRemIndex
            will wrap between reboots."
    ::= { lldpV2Configuration 4 }

lldpV2RemLocalDestMACAddress  OBJECT-TYPE
    SYNTAX      OCTET STRING (SIZE(6))
    MAX-ACCESS  read-only
    STATUS      current
    DESCRIPTION
            "This object represents an arbitrary local integer value used
            by this agent to identify a particular connection instance,
            unique only for the indicated remote system.

            An agent is encouraged to assign monotonically increasing
            index values to new entries, starting with one, after each
            reboot. It is considered unlikely that the lldpRemIndex
            will wrap between reboots."
    ::= { lldpV2Configuration 5 }



lldpV2PortConfigTable   OBJECT-TYPE
    SYNTAX      SEQUENCE OF LldpV2PortConfigEntry
    MAX-ACCESS  not-accessible
    STATUS      current
    DESCRIPTION
            "The table that controls LLDP frame transmission on individual
            ports."
    ::= { lldpV2Configuration 6 }

lldpV2PortConfigEntry   OBJECT-TYPE
    SYNTAX      LldpV2PortConfigEntry
    MAX-ACCESS  not-accessible
    STATUS      current
    DESCRIPTION
            "LLDP configuration information for a particular port.
            This configuration parameter controls the transmission and
            the reception of LLDP frames on those ports whose rows are
            created in this table."
     INDEX  { lldpV2PortConfigPortNum }
    ::= { lldpV2PortConfigTable 1 }

LldpV2PortConfigEntry ::= SEQUENCE {
      lldpV2PortConfigPortNum            LldpPortNumber
				 }

lldpV2PortConfigPortNum   OBJECT-TYPE
    SYNTAX      LldpPortNumber
    MAX-ACCESS  read-only
    STATUS      current
    DESCRIPTION
            "The index value used to identify the port component
            (contained in the local chassis with the LLDP agent)
            associated with this entry.

            The value of this object is used as a port index to the
            lldpPortConfigTable."
    ::= { lldpV2PortConfigEntry 1 }

END
