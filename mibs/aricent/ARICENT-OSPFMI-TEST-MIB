-- Copyright (C) 2007-2012 Aricent Group . All Rights Reserved

-- $Id: fsosmitest.mib,v 1.4 2016/07/29 09:49:19 siva Exp $

ARICENT-OSPFMI-TEST-MIB DEFINITIONS ::= BEGIN

-- Enterprises MIB for testing OSPF.
   IMPORTS
      MODULE-IDENTITY, OBJECT-TYPE,
      Unsigned32, Integer32 , IpAddress , enterprises
                                                 FROM SNMPv2-SMI
      RowStatus
                                                 FROM SNMPv2-TC
      fsMIStdOspfContextId, BigMetric, TOSType
                                                 FROM ARICENT-MISTDOSPF-MIB;


fsMIOspfTestGroup  MODULE-IDENTITY
      LAST-UPDATED "201209050000Z"
      ORGANIZATION "ARICENT COMMUNICATIONS SOFTWARE"
      CONTACT-INFO "support@aricent.com"
      DESCRIPTION
      "The Proprietary OSPFMI TEST MIB"
      REVISION "201209050000Z"
      DESCRIPTION
      "The Proprietary OSPFMI TEST MIB"

         ::= { enterprises futuresoftware (2076) 147 }

fsMIOspfGrTestGroup    OBJECT IDENTIFIER ::= { fsMIOspfTestGroup 100 }

-- ABR/ASBR Routes Table
   fsMIOspfBRRouteTable OBJECT-TYPE
       SYNTAX      SEQUENCE OF FsMIOspfBRRouteEntry
       MAX-ACCESS  not-accessible
       STATUS      current
       DESCRIPTION
           "A table of routing information."
       ::=  { fsMIOspfTestGroup 1 }

   fsMIOspfBRRouteEntry OBJECT-TYPE
       SYNTAX      FsMIOspfBRRouteEntry
       MAX-ACCESS  not-accessible
       STATUS      current
       DESCRIPTION
           "The information regarding a single route."
       INDEX {fsMIStdOspfContextId,fsMIOspfBRRouteIpAddr,fsMIOspfBRRouteIpAddrMask,
              fsMIOspfBRRouteIpTos,fsMIOspfBRRouteIpNextHop,
	      fsMIOspfBRRouteDestType}
       ::=  { fsMIOspfBRRouteTable 1 }

   FsMIOspfBRRouteEntry ::= SEQUENCE {
       fsMIOspfBRRouteIpAddr          IpAddress,
       fsMIOspfBRRouteIpAddrMask      IpAddress,
       fsMIOspfBRRouteIpTos           Unsigned32,
       fsMIOspfBRRouteIpNextHop       IpAddress,
       fsMIOspfBRRouteDestType        INTEGER,
       fsMIOspfBRRouteType            INTEGER,
       fsMIOspfBRRouteAreaId          IpAddress,
       fsMIOspfBRRouteCost            BigMetric,
       fsMIOspfBRRouteInterfaceIndex  Integer32
       }

   fsMIOspfBRRouteIpAddr OBJECT-TYPE
       SYNTAX      IpAddress
       MAX-ACCESS  not-accessible
       STATUS      current
       DESCRIPTION
           " Router Id of the destination router.
	     ABR/ASBR entries will have Router Id as
	     the destination network Id "
       ::=  { fsMIOspfBRRouteEntry 1 }

   fsMIOspfBRRouteIpAddrMask OBJECT-TYPE
       SYNTAX      IpAddress
       MAX-ACCESS  not-accessible
       STATUS      current
       DESCRIPTION
           " IP Address Mask of the route. This will be
	     0.0.0.0 for all routes, because for ABR/ASBR
	     route entries netmask is 0.0.0.0 "
       ::=  { fsMIOspfBRRouteEntry 2 }

   fsMIOspfBRRouteIpTos OBJECT-TYPE
       SYNTAX      Unsigned32
       MAX-ACCESS  not-accessible
       STATUS      current
       DESCRIPTION
           " IP TOS of the route "
       ::=  { fsMIOspfBRRouteEntry 3 }

   fsMIOspfBRRouteIpNextHop OBJECT-TYPE
       SYNTAX      IpAddress
       MAX-ACCESS  not-accessible
       STATUS      current
       DESCRIPTION
           " IP Next Hop of the route "
       ::=  { fsMIOspfBRRouteEntry 4 }

   fsMIOspfBRRouteDestType OBJECT-TYPE
       SYNTAX      INTEGER {
                             areaBorder (2),
		             asBoundary (3)
		           }
       MAX-ACCESS  not-accessible
       STATUS      current
       DESCRIPTION
           " Type of the route. The route can be ABR route
	     entry or ASBR route entry "
       ::=  { fsMIOspfBRRouteEntry 5 }

   fsMIOspfBRRouteType OBJECT-TYPE
       SYNTAX      INTEGER {
                             intraArea (1),
		             interArea (2)
		           }
       MAX-ACCESS  read-only
       STATUS      current
       DESCRIPTION
           " Type of the route "
       ::=  { fsMIOspfBRRouteEntry 6 }

   fsMIOspfBRRouteAreaId OBJECT-TYPE
       SYNTAX      IpAddress
       MAX-ACCESS  read-only
       STATUS      current
       DESCRIPTION
           " Area ID associated with the route "
       ::=  { fsMIOspfBRRouteEntry 7 }

   fsMIOspfBRRouteCost OBJECT-TYPE
       SYNTAX BigMetric
       MAX-ACCESS  read-only
       STATUS      current
       DESCRIPTION
          " The cost associated with the route "
       ::=  { fsMIOspfBRRouteEntry 8 }

   fsMIOspfBRRouteInterfaceIndex OBJECT-TYPE
       SYNTAX Integer32 (0..65535)
       MAX-ACCESS  read-only
       STATUS      current
       DESCRIPTION
           " Interface Index associated with the route "
       ::=  { fsMIOspfBRRouteEntry 9 }


   fsMIOspfExtRouteTable OBJECT-TYPE
       SYNTAX SEQUENCE OF FsMIOspfExtRouteEntry
       MAX-ACCESS not-accessible
       STATUS      current
       DESCRIPTION
           "A table of exterior route information."
       ::=  { fsMIOspfTestGroup 2 }

   fsMIOspfExtRouteEntry OBJECT-TYPE
       SYNTAX FsMIOspfExtRouteEntry
       MAX-ACCESS not-accessible
       STATUS      current
       DESCRIPTION
           "The information regarding a single exterior route."
       INDEX {fsMIStdOspfContextId,fsMIOspfExtRouteDest,fsMIOspfExtRouteMask,fsMIOspfExtRouteTOS}
       ::=  { fsMIOspfExtRouteTable 1 }

   FsMIOspfExtRouteEntry ::= SEQUENCE {
       fsMIOspfExtRouteDest       IpAddress,
       fsMIOspfExtRouteMask       IpAddress,
       fsMIOspfExtRouteTOS        TOSType,
       fsMIOspfExtRouteMetric     BigMetric,
       fsMIOspfExtRouteMetricType INTEGER,
       fsMIOspfExtRouteTag        Integer32,
       fsMIOspfExtRouteFwdAdr     IpAddress,
       fsMIOspfExtRouteIfIndex    Integer32,
       fsMIOspfExtRouteNextHop    IpAddress,
       fsMIOspfExtRouteStatus     RowStatus
       }

   fsMIOspfExtRouteDest OBJECT-TYPE
       SYNTAX      IpAddress
       MAX-ACCESS  not-accessible
       STATUS      current
       DESCRIPTION
           " Net Id of the External route to Destination."
       ::=  { fsMIOspfExtRouteEntry 1 }

   fsMIOspfExtRouteMask OBJECT-TYPE
       SYNTAX      IpAddress
       MAX-ACCESS  not-accessible
       STATUS      current
       DESCRIPTION
           " Mask of the Exterior Route to Destination."
       ::=  { fsMIOspfExtRouteEntry 2 }

   fsMIOspfExtRouteTOS OBJECT-TYPE
       SYNTAX TOSType
       MAX-ACCESS  not-accessible
       STATUS      current
       DESCRIPTION
           " The  Type  of  Service  associated with the External Route."
       ::=  { fsMIOspfExtRouteEntry 3 }

   fsMIOspfExtRouteMetric OBJECT-TYPE
       SYNTAX BigMetric
       MAX-ACCESS  read-create
       STATUS      current
       DESCRIPTION
           " The metric value applied at the indicated type
             of  service.  By default, this equals the least
             metric at the type of service among the  inter-faces
             to other areas."
       ::=  { fsMIOspfExtRouteEntry 4 }

   fsMIOspfExtRouteMetricType OBJECT-TYPE
       SYNTAX      INTEGER {
                            asexttype1 (1),
                            asexttype2 (2)
		           }
       MAX-ACCESS  read-create
       STATUS      current
       DESCRIPTION
           " The metric Type applied at the indicated type of service."
       DEFVAL { asexttype2 }
       ::=  { fsMIOspfExtRouteEntry 5 }

   fsMIOspfExtRouteTag OBJECT-TYPE
       SYNTAX      Integer32
       MAX-ACCESS  read-create
       STATUS      current
       DESCRIPTION
           " The Route tag applied at the indicated type of service."
       DEFVAL { 0 }
       ::=  { fsMIOspfExtRouteEntry 6 }

   fsMIOspfExtRouteFwdAdr OBJECT-TYPE
       SYNTAX      IpAddress
       MAX-ACCESS  read-create
       STATUS      current
       DESCRIPTION
           " This Indicates the IP Address to which Packets
             for the destinations should be forwarded."
       DEFVAL { '0000'h }
       ::=  { fsMIOspfExtRouteEntry 7 }

   fsMIOspfExtRouteIfIndex OBJECT-TYPE
       SYNTAX      Integer32 (0..65535)
       MAX-ACCESS  read-create
       STATUS      current
       DESCRIPTION
           " The Interface to reach the destination.
             This will have a valid value for ospfExtRouteFwdAdr
             value being 0.0.0.0. Otherwise this has the
             value of 0."
       DEFVAL { 0 }
       ::=  { fsMIOspfExtRouteEntry 8 }

   fsMIOspfExtRouteNextHop OBJECT-TYPE
       SYNTAX      IpAddress
       MAX-ACCESS  read-create
       STATUS      current
       DESCRIPTION
           " IP address of the next hop to reach the destination.
             This will have a valid value for ospfExtRouteFwdAdr
             value being 0.0.0.0. Otherwise this has the
             value of 0.0.0.0."
       DEFVAL { '0000'h }
       ::=  { fsMIOspfExtRouteEntry 9 }

   fsMIOspfExtRouteStatus OBJECT-TYPE
       SYNTAX      RowStatus
       MAX-ACCESS  read-create
       STATUS      current
       DESCRIPTION
           " This variable displays the status of  the  en-
             try.  Setting it to 'invalid' has the effect of
             rendering it inoperative.  The internal  effect
             (row removal) is implementation dependent."
       ::=  { fsMIOspfExtRouteEntry 10 }

-- fsMIOspfGrTestGroup BEGINS

   fsMIOspfGrTable OBJECT-TYPE
       SYNTAX SEQUENCE OF FsMIOspfGrEntry
       MAX-ACCESS not-accessible
       STATUS      current
       DESCRIPTION
           "A table of exterior route information."
       ::=  { fsMIOspfGrTestGroup 2 }

   fsMIOspfGrEntry OBJECT-TYPE
       SYNTAX FsMIOspfGrEntry
       MAX-ACCESS not-accessible
       STATUS      current
       DESCRIPTION
           "The information regarding a single exterior route."
       INDEX { fsMIStdOspfContextId }
       ::=  { fsMIOspfGrTable 1 }

   FsMIOspfGrEntry ::= SEQUENCE {
       fsMIOspfGrShutdown INTEGER
       }

   fsMIOspfGrShutdown OBJECT-TYPE
      SYNTAX      INTEGER {
                            none (1),
                            unplanned (2)
                          }
      MAX-ACCESS  read-write
      STATUS      current
      DESCRIPTION
          "This object is used to trigger unplanned graceful restart
           for testing purpose. The object shuts the OSPF
           process gracefully.

           This MIB object is used to trigger the unplanned software
           restart. The object restricts the user to disable the restart process.
           'none' cannot be written."
      DEFVAL { none }
      ::= { fsMIOspfGrEntry 1 }

-- fsMIOspfGrTestGroup ENDS

END
