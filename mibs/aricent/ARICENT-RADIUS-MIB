-- Copyright (C) 2008-2012 Aricent Group . All Rights Reserved

-- $Id: fsradius.mib,v 1.5 2015/04/28 12:25:01 siva Exp $

-- ****************************************************************************
-- *                         Document Version Info                            *
-- ****************************************************************************
-- *Version |    Date        |   Author             |        Changes          *
-- * ------------------------------------------------------------------------ *
-- * 1.1    |  31st MAY 2000 | Private              |Removed duplicate objects*
-- *        |                |                      |available in Std Table   *
-- *        |                |                      |			      *
-- *        |                |                      |	 		      *
-- ****************************************************************************

-- RADIUS-CLIENT-MIB DEFINITIONS ::= BEGIN


ARICENT-RADIUS-MIB DEFINITIONS ::= BEGIN

 IMPORTS
     MODULE-IDENTITY, OBJECT-TYPE,
     Integer32, enterprises,
     IpAddress                        FROM SNMPv2-SMI
     DisplayString, RowStatus         FROM SNMPv2-TC
     InterfaceIndex                   FROM IF-MIB;


 futureRADIUSMIB MODULE-IDENTITY
    LAST-UPDATED "201209050000Z"
    ORGANIZATION "ARICENT COMMUNICATIONS SOFTWARE"
    CONTACT-INFO "support@aricent.com"
	DESCRIPTION " The RADIUS ext. MIB is placed under futuresoftware MIB branch."
	REVISION "201209050000Z"
	DESCRIPTION " The RADIUS ext. MIB is placed under futuresoftware MIB branch."
	::= { enterprises futuresoftware (2076) 25 }



 radiusExtClient           OBJECT IDENTIFIER ::= { futureRADIUSMIB 1 }


radiusExtDebugMask OBJECT-TYPE
      SYNTAX Integer32
      MAX-ACCESS read-write
      STATUS current
      DESCRIPTION
        "This object is used to enable Trace Statements in
        Radius Module.

        A FOUR BYTE integer is used for enabling the level of tracing.
        Each BIT in the four byte integer, represents a particular
        level of Trace.

        The maping between the bit positions & the level of trace is
        as follows:
        0 - Error Traces
        1 - Event Traces
        2 - Packet Traces
        3 - Response Traces
        4 - Timer Traces

        The remaining bits are unused. Combination of levels are
        also allowed.

        For example if the bits 0 and 1 are set, then the Trace
        statements related to Error and Event
        will be printed.

        The user has to enter the corresponding INTEGER VALUE for the
        bits set. For example if bits 0 and 1 are set then user has to
        give the value 3."
      ::= { radiusExtClient 1 }

radiusMaxNoOfUserEntries OBJECT-TYPE
      SYNTAX Integer32 (1 ..100)
      MAX-ACCESS read-write
      STATUS current
      DESCRIPTION
            "  Max of No of User entries stored.For value of this
	 object will be stored for the MemPool Initialization."
      ::= { radiusExtClient 2 }

radiusExtServerTable OBJECT-TYPE
    SYNTAX SEQUENCE OF RadiusExtServerEntry
    MAX-ACCESS not-accessible
    STATUS current
    DESCRIPTION
        "The (conceptual) table listing the RADIUS servers with
                 which the client shares a secret."
    ::=  { radiusExtClient 3 }

radiusExtServerEntry OBJECT-TYPE
    SYNTAX RadiusExtServerEntry
    MAX-ACCESS not-accessible
    STATUS current
    DESCRIPTION
        "An entry (conceptual row) representing a RADIUS server
                 with which the client shares a secret."
    INDEX {radiusExtServerIndex}
    ::=  { radiusExtServerTable 1 }

RadiusExtServerEntry ::= SEQUENCE {
    radiusExtServerIndex    InterfaceIndex,
    radiusExtServerAddress    IpAddress,
    radiusExtServerType    INTEGER,
    radiusExtServerSharedSecret    DisplayString,
    radiusExtServerEnabled    INTEGER,
    radiusExtServerResponseTime INTEGER,
    radiusExtServerMaximumRetransmission  INTEGER,
    radiusExtServerEntryStatus		RowStatus
   }


radiusExtServerIndex OBJECT-TYPE
    SYNTAX InterfaceIndex
    MAX-ACCESS read-only
    STATUS current
    DESCRIPTION
        "The RADIUS server with whom the client interacts."
    ::=  { radiusExtServerEntry 1 }

radiusExtServerAddress OBJECT-TYPE
    SYNTAX IpAddress
    MAX-ACCESS read-write
    STATUS current
    DESCRIPTION
        "The IP address of the RADIUS server
                 referred to in this table entry."
    ::=  { radiusExtServerEntry 2 }

radiusExtServerType OBJECT-TYPE
    SYNTAX INTEGER { auth (1),
                     acct (2),
                     both (3)
                   }
    MAX-ACCESS read-write
    STATUS current
    DESCRIPTION
        "The RADIUS server type (Authentication or Accounting or Both).
         For creating a server entry Server Type should be set"
    ::=  { radiusExtServerEntry 3 }

radiusExtServerSharedSecret OBJECT-TYPE
    SYNTAX DisplayString
    MAX-ACCESS read-write
    STATUS current
    DESCRIPTION
        "The secret string which is shared between Server and Client"
    ::=  { radiusExtServerEntry 4 }

radiusExtServerEnabled OBJECT-TYPE
    SYNTAX INTEGER { enabled (1),
                     disabled (2),
                     destroy (3)
                   }
    MAX-ACCESS read-write
    STATUS current
    DESCRIPTION
        "Flag to tell whether the server is active or Inactive"
    DEFVAL { enabled }
    ::=  { radiusExtServerEntry 5 }

radiusExtServerResponseTime OBJECT-TYPE
    SYNTAX INTEGER (1 ..120)
    MAX-ACCESS read-write
    STATUS current
    DESCRIPTION
        "The maximum time within which the server has to respond for a
         request from the client"
    ::=  { radiusExtServerEntry 6 }

radiusExtServerMaximumRetransmission OBJECT-TYPE
    SYNTAX INTEGER (1 ..254)
    MAX-ACCESS read-write
    STATUS current
    DESCRIPTION
        "The allowed maximum no. of trials to be tried by a client to get
         response from the server for a request"
    ::=  { radiusExtServerEntry 7 }

 radiusExtServerEntryStatus	OBJECT-TYPE
   SYNTAX    			RowStatus
   MAX-ACCESS 			read-write
   STATUS 			current
   DESCRIPTION
      "The status of the entry can be used as specified in the SNMP V2
      standard. "
  ::=  {   radiusExtServerEntry 8  }

END
