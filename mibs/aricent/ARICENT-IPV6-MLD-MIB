-- Copyright (C) 2015 Aricent. All Rights Reserved

-- $Id: fsmld.mib,v 1.9 2015/06/19 06:19:33 siva Exp $

ARICENT-IPV6-MLD-MIB DEFINITIONS ::= BEGIN

   IMPORTS
       MODULE-IDENTITY, OBJECT-TYPE,enterprises,
       Unsigned32 FROM SNMPv2-SMI;

   futuremld MODULE-IDENTITY
       LAST-UPDATED "201209050000Z"
       ORGANIZATION "ARICENT COMMUNICATIONS SOFTWARE"
       CONTACT-INFO "support@aricent.com"
       DESCRIPTION
               "The MIB module for MLD Management."
       REVISION "201209050000Z"
       DESCRIPTION
               "The MIB module for MLD Management."
       ::={ enterprises futuresoftware(2076) 70 }

fsmldScalars OBJECT IDENTIFIER ::= { futuremld 1 }

        fsmldNoOfCacheEntries OBJECT-TYPE
             SYNTAX  Unsigned32
             MAX-ACCESS  read-write
             STATUS  deprecated
             DESCRIPTION
                "Maximum number of multicast address per interface."
             ::= { fsmldScalars 1 }

        fsmldNoOfRoutingProtocols OBJECT-TYPE
             SYNTAX  Unsigned32
             MAX-ACCESS  read-write
             STATUS  deprecated
             DESCRIPTION
                "Maximum number of Routing Protocols that can register
                 with MLD."
             ::= { fsmldScalars 2 }


        fsmldTraceDebug OBJECT-TYPE
             SYNTAX  Unsigned32
             MAX-ACCESS  read-write
             STATUS  current
             DESCRIPTION
                "This is used to enable Trace Statements in MLD Module."
             ::= { fsmldScalars 3 }

	fsmldDebugLevel OBJECT-TYPE
             SYNTAX  Unsigned32
             MAX-ACCESS  read-write
             STATUS  current
             DESCRIPTION
                "This is used to enable debug statements in MLD Module."
             ::= { fsmldScalars 4 }


        fsmldMode OBJECT-TYPE
             SYNTAX  INTEGER{
                    mldrouter(1),
                    mldhost(2),
                    mldrouterhost (3)
                    }
             MAX-ACCESS  read-write
             STATUS  current
             DESCRIPTION
                "This is used to enable router or host mode for MLD."
             DEFVAL { mldrouter }
             ::= { fsmldScalars 5 }

        fsmldProtocolUpDown OBJECT-TYPE
             SYNTAX  INTEGER{
                    mldinit(1),
                    mldshutdown(2)
                    }
             MAX-ACCESS  read-write
             STATUS  current
             DESCRIPTION
                "This is used to bring the MLD Protocol up/down during
                 runtime."
             ::= { fsmldScalars 6 }

   END
