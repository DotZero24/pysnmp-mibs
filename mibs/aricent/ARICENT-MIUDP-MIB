-- Copyright (C) 2009-2012 Aricent Group . All Rights Reserved

-- $Id: fsmsudpipvx.mib,v 1.3 2012/09/07 09:52:05 siva Exp $

   ARICENT-MIUDP-MIB DEFINITIONS ::= BEGIN

   IMPORTS
       MODULE-IDENTITY, OBJECT-TYPE, Integer32, Counter32, Counter64,
       Unsigned32, enterprises            FROM SNMPv2-SMI
       InetAddress, InetAddressType,
       InetPortNumber                     FROM INET-ADDRESS-MIB;

   fsMIUdpMIB MODULE-IDENTITY
       LAST-UPDATED "201209050000Z"
       ORGANIZATION "ARICENT COMMUNICATIONS SOFTWARE"
       CONTACT-INFO "support@aricent.com"

       DESCRIPTION
              "The MIB module for managing UDP implementations.
               This version of this MIB module is part of RFC 4113;
               see the RFC itself for full legal notices."
       REVISION      "201209050000Z"
       DESCRIPTION
              "IP version neutral revision, incorporating the
               following revisions:

               - Added udpHCInDatagrams and udpHCOutDatagrams in order
                 to provide high-capacity counters for fast networks.
               - Added text to the descriptions of all counter objects
                 to indicate how discontinuities are detected.
               - Deprecated the IPv4-specific udpTable and replaced it
                 with the version neutral udpEndpointTable.  This
                 table includes support for connected UDP endpoints
                 and support for identification of the operating
                 system process associated with a UDP endpoint.
               - Deprecated the udpGroup and replaced it with object
                 groups representing the current set of objects.
               - Deprecated udpMIBCompliance and replaced it with
                 udpMIBCompliance2, which includes the compliance
                 information for the new object groups.

               This version published as RFC 4113."
       REVISION      "199411010000Z"    -- November 1, 1994
       DESCRIPTION
              "Initial SMIv2 version, published as RFC 2013."
       REVISION      "199103310000Z"    -- March 31, 1991
       DESCRIPTION
              "The initial revision of this MIB module was part of
               MIB-II, published as RFC 1213."
       ::= {  enterprises  aricent-communication-holding-ltd(29601) iss(2) 28 }

   fsMIUdp    OBJECT IDENTIFIER ::= { fsMIUdpMIB  1}

   fsMiUdpInDatagrams OBJECT-TYPE
       SYNTAX     Counter32
       MAX-ACCESS read-only
       STATUS     current
       DESCRIPTION
              "The total number of UDP datagrams delivered to UDP
               users.
               Discontinuities in the value of this counter can occur
               at re-initialization of the management system, and at
               other times as indicated by discontinuities in the
               value of sysUpTime."
       ::= { fsMIUdp 1 }

   fsMiUdpNoPorts OBJECT-TYPE
       SYNTAX     Counter32
       MAX-ACCESS read-only
       STATUS     current
       DESCRIPTION
              "The total number of received UDP datagrams for which
               there was no application at the destination port.

               Discontinuities in the value of this counter can occur
               at re-initialization of the management system, and at
               other times as indicated by discontinuities in the
               value of sysUpTime."
       ::= { fsMIUdp 2 }

   fsMiUdpInErrors OBJECT-TYPE
       SYNTAX     Counter32
       MAX-ACCESS read-only
       STATUS     current
       DESCRIPTION
              "The number of received UDP datagrams that could not be
               delivered for reasons other than the lack of an
               application at the destination port.

               Discontinuities in the value of this counter can occur
               at re-initialization of the management system, and at
               other times as indicated by discontinuities in the
               value of sysUpTime."
       ::= { fsMIUdp 3 }

   fsMiUdpOutDatagrams OBJECT-TYPE
       SYNTAX     Counter32
       MAX-ACCESS read-only
       STATUS     current
       DESCRIPTION
              "The total number of UDP datagrams sent from this
               entity.

               Discontinuities in the value of this counter can occur
               at re-initialization of the management system, and at
               other times as indicated by discontinuities in the
               value of sysUpTime."
       ::= { fsMIUdp 4 }

      fsMiUdpInNoCksum    OBJECT-TYPE
        SYNTAX        Counter32
        MAX-ACCESS        read-only
        STATUS        current
        DESCRIPTION " Number of UDP datagrams received without
                checksum "
        ::= { fsMIUdp 5 }

      fsMiUdpInIcmpErr OBJECT-TYPE
        SYNTAX        Counter32
        MAX-ACCESS        read-only
        STATUS        current
        DESCRIPTION " Number of ICMP error packets received "
        ::= { fsMIUdp 6 }

      fsMiUdpInErrCksum    OBJECT-TYPE
        SYNTAX        Counter32
        MAX-ACCESS        read-only
        STATUS        current
        DESCRIPTION " Number of UDP packets received with wrong
                 checksum "
        ::= { fsMIUdp 7 }

      fsMiUdpInBcast OBJECT-TYPE
        SYNTAX        Counter32
        MAX-ACCESS        read-only
        STATUS        current
        DESCRIPTION " Number of UDP packets received in broadcast mode "
        ::= { fsMIUdp 8 }

   fsMiUdpHCInDatagrams OBJECT-TYPE
       SYNTAX     Counter64
       MAX-ACCESS read-only
       STATUS     current
       DESCRIPTION
              "The total number of UDP datagrams delivered to UDP
               users, for devices that can receive more than 1
               million UDP datagrams per second.

               Discontinuities in the value of this counter can occur
               at re-initialization of the management system, and at
               other times as indicated by discontinuities in the
               value of sysUpTime."
       ::= { fsMIUdp 9 }

   fsMiUdpHCOutDatagrams OBJECT-TYPE
       SYNTAX     Counter64
       MAX-ACCESS read-only
       STATUS     current
       DESCRIPTION
              "The total number of UDP datagrams sent from this
               entity, for devices that can transmit more than 1
               million UDP datagrams per second.

               Discontinuities in the value of this counter can occur
               at re-initialization of the management system, and at
               other times as indicated by discontinuities in the
               value of sysUpTime."
       ::= { fsMIUdp 10 }


    fsMIUdpStatTable OBJECT-TYPE
    SYNTAX SEQUENCE OF FsMIUdpStatEntry
    MAX-ACCESS not-accessible
    STATUS     current
    DESCRIPTION
        "Table to store the virtual router specific udp datagram information."
    ::= {fsMIUdp 11}

    fsMIUdpStatEntry OBJECT-TYPE
    SYNTAX     FsMIUdpStatEntry
    MAX-ACCESS not-accessible
    STATUS     current
    DESCRIPTION
        "Each entry has udp datagram information for the Virtual router"
    INDEX {fsMiUdpIpvxContextId}
    ::= {fsMIUdpStatTable 1}

    FsMIUdpStatEntry ::= SEQUENCE {
        fsMiUdpIpvxContextId         Integer32,
        fsMiUdpIpvxInDatagrams       Counter32,
        fsMiUdpIpvxNoPorts           Counter32,
        fsMiUdpIpvxInErrors          Counter32,
        fsMiUdpIpvxOutDatagrams      Counter32,
        fsMiUdpIpvxInNoCksum         Counter32,
        fsMiUdpIpvxInIcmpErr         Counter32,
        fsMiUdpIpvxInErrCksum        Counter32,
        fsMiUdpIpvxInBcast           Counter32,
        fsMiUdpIpvxHCInDatagrams     Counter64,
        fsMiUdpIpvxHCOutDatagrams    Counter64
    }

    fsMiUdpIpvxContextId OBJECT-TYPE
    SYNTAX     Integer32 (0..255)
    MAX-ACCESS not-accessible
    STATUS     current
    DESCRIPTION
        "A unique VR Id representing the Virtual Router for each entry"
    ::= {fsMIUdpStatEntry 1}

    fsMiUdpIpvxInDatagrams OBJECT-TYPE
    SYNTAX     Counter32
    MAX-ACCESS read-only
    STATUS     current
    DESCRIPTION
              "The total number of UDP datagrams delivered to UDP
               users.
               Discontinuities in the value of this counter can occur
               at re-initialization of the management system, and at
               other times as indicated by discontinuities in the
               value of sysUpTime."
       ::= { fsMIUdpStatEntry 2 }


   fsMiUdpIpvxNoPorts OBJECT-TYPE
       SYNTAX     Counter32
       MAX-ACCESS read-only
       STATUS     current
       DESCRIPTION
              "The total number of received UDP datagrams for which
               there was no application at the destination port.

               Discontinuities in the value of this counter can occur
               at re-initialization of the management system, and at
               other times as indicated by discontinuities in the
               value of sysUpTime."
       ::= { fsMIUdpStatEntry 3 }

   fsMiUdpIpvxInErrors OBJECT-TYPE
       SYNTAX     Counter32
       MAX-ACCESS read-only
       STATUS     current
       DESCRIPTION
              "The number of received UDP datagrams that could not be
               delivered for reasons other than the lack of an
               application at the destination port.

               Discontinuities in the value of this counter can occur
               at re-initialization of the management system, and at
               other times as indicated by discontinuities in the
               value of sysUpTime."
       ::= { fsMIUdpStatEntry 4 }

   fsMiUdpIpvxOutDatagrams OBJECT-TYPE
       SYNTAX     Counter32
       MAX-ACCESS read-only
       STATUS     current
       DESCRIPTION
              "The total number of UDP datagrams sent from this
               entity.

               Discontinuities in the value of this counter can occur
               at re-initialization of the management system, and at
               other times as indicated by discontinuities in the
               value of sysUpTime."
       ::= { fsMIUdpStatEntry 5 }

     fsMiUdpIpvxInNoCksum    OBJECT-TYPE
        SYNTAX        Counter32
        MAX-ACCESS        read-only
        STATUS        current
        DESCRIPTION " Number of UDP datagrams received without
                checksum "
        ::= { fsMIUdpStatEntry 6 }

      fsMiUdpIpvxInIcmpErr OBJECT-TYPE
        SYNTAX        Counter32
        MAX-ACCESS        read-only
        STATUS        current
        DESCRIPTION " Number of ICMP error packets received "
        ::= { fsMIUdpStatEntry 7 }

      fsMiUdpIpvxInErrCksum    OBJECT-TYPE
        SYNTAX        Counter32
        MAX-ACCESS        read-only
        STATUS        current
        DESCRIPTION " Number of UDP packets received with wrong
                 checksum "
        ::= { fsMIUdpStatEntry 8 }

      fsMiUdpIpvxInBcast OBJECT-TYPE
        SYNTAX        Counter32
        MAX-ACCESS        read-only
        STATUS        current
        DESCRIPTION " Number of UDP packets received in broadcast mode "
        ::= { fsMIUdpStatEntry 9 }

   fsMiUdpIpvxHCInDatagrams OBJECT-TYPE
       SYNTAX     Counter64
       MAX-ACCESS read-only
       STATUS     current
       DESCRIPTION
              "The total number of UDP datagrams delivered to UDP
               users, for devices that can receive more than 1
               million UDP datagrams per second.

               Discontinuities in the value of this counter can occur
               at re-initialization of the management system, and at
               other times as indicated by discontinuities in the
               value of sysUpTime."
       ::= { fsMIUdpStatEntry 10 }

   fsMiUdpIpvxHCOutDatagrams OBJECT-TYPE
       SYNTAX     Counter64
       MAX-ACCESS read-only
       STATUS     current
       DESCRIPTION
              "The total number of UDP datagrams sent from this
               entity, for devices that can transmit more than 1
               million UDP datagrams per second.

               Discontinuities in the value of this counter can occur
               at re-initialization of the management system, and at
               other times as indicated by discontinuities in the
               value of sysUpTime."
       ::= { fsMIUdpStatEntry 11 }

   -- The Global UDP "Endpoint" table.
    fsMiUdpEndpointTable OBJECT-TYPE
       SYNTAX     SEQUENCE OF FsMiUdpEndpointEntry
       MAX-ACCESS not-accessible
       STATUS     current
       DESCRIPTION
              "This Endpoint table will contain the entities which are
               common for all contexts.
               A table containing information about this entity's UDP
               endpoints on which a local application is currently
               accepting or sending datagrams.
               The address type in this table represents the address
               type used for the communication, irrespective of the
               higher-layer abstraction.  For example, an application
               using IPv6 'sockets' to communicate via IPv4 between
               ::ffff:10.0.0.1 and ::ffff:10.0.0.2 would use
               InetAddressType ipv4(1).

               Unlike the udpTable in RFC 2013, this table also allows
               the representation of an application that completely
               specifies both local and remote addresses and ports.  A
               listening application is represented in three possible
               ways:

               1) An application that is willing to accept both IPv4
                  and IPv6 datagrams is represented by a
                  udpEndpointLocalAddressType of unknown(0) and a
                  udpEndpointLocalAddress of ''h (a zero-length
                  octet-string).

               2) An application that is willing to accept only IPv4
                  or only IPv6 datagrams is represented by a
                  udpEndpointLocalAddressType of the appropriate
                  address type and a udpEndpointLocalAddress of
                  '0.0.0.0' or '::' respectively.

               3) An application that is listening for datagrams only
                  for a specific IP address but from any remote
                  system is represented by a
                  udpEndpointLocalAddressType of the appropriate
                  address type, with udpEndpointLocalAddress
                  specifying the local address.

               In all cases where the remote is a wildcard, the
               udpEndpointRemoteAddressType is unknown(0), the
               udpEndpointRemoteAddress is ''h (a zero-length
               octet-string), and the udpEndpointRemotePort is 0.

               If the operating system is demultiplexing UDP packets
               by remote address and port, or if the application has
               'connected' the socket specifying a default remote
               address and port, the udpEndpointRemote* values should
               be used to reflect this."
       ::= { fsMIUdp 12 }

   fsMiUdpEndpointEntry OBJECT-TYPE
       SYNTAX     FsMiUdpEndpointEntry
       MAX-ACCESS not-accessible
       STATUS     current
       DESCRIPTION
              "Information about a particular current UDP endpoint.

               Implementers need to be aware that if the total number
               of elements (octets or sub-identifiers) in
               udpEndpointLocalAddress and udpEndpointRemoteAddress
               exceeds 111, then OIDs of column instances in this table
               will have more than 128 sub-identifiers and cannot be
               accessed using SNMPv1, SNMPv2c, or SNMPv3."
       INDEX   { fsMiUdpEndpointLocalAddressType,
                 fsMiUdpEndpointLocalAddress,
                 fsMiUdpEndpointLocalPort,
                 fsMiUdpEndpointRemoteAddressType,
                 fsMiUdpEndpointRemoteAddress,
                 fsMiUdpEndpointRemotePort,
                 fsMiUdpEndpointInstance }
       ::= { fsMiUdpEndpointTable 1 }

   FsMiUdpEndpointEntry ::= SEQUENCE {
           fsMiUdpEndpointLocalAddressType   InetAddressType,
           fsMiUdpEndpointLocalAddress       InetAddress,
           fsMiUdpEndpointLocalPort          InetPortNumber,
           fsMiUdpEndpointRemoteAddressType  InetAddressType,
           fsMiUdpEndpointRemoteAddress      InetAddress,
           fsMiUdpEndpointRemotePort         InetPortNumber,
           fsMiUdpEndpointInstance           Unsigned32,
           fsMiUdpEndpointProcess            Unsigned32
       }

   fsMiUdpEndpointLocalAddressType OBJECT-TYPE
       SYNTAX     InetAddressType
       MAX-ACCESS not-accessible
       STATUS     current
       DESCRIPTION
              "The address type of udpEndpointLocalAddress.  Only
               IPv4, IPv4z, IPv6, and IPv6z addresses are expected, or
               unknown(0) if datagrams for all local IP addresses are
               accepted."
       ::= { fsMiUdpEndpointEntry 1 }

   fsMiUdpEndpointLocalAddress OBJECT-TYPE
       SYNTAX     InetAddress (SIZE(16))
       MAX-ACCESS not-accessible
       STATUS     current
       DESCRIPTION
              "The local IP address for this UDP endpoint.

               The value of this object can be represented in three
               possible ways, depending on the characteristics of the
               listening application:

               1. For an application that is willing to accept both
                  IPv4 and IPv6 datagrams, the value of this object
                  must be ''h (a zero-length octet-string), with
                  the value of the corresponding instance of the
                  udpEndpointLocalAddressType object being unknown(0).

               2. For an application that is willing to accept only IPv4
                  or only IPv6 datagrams, the value of this object
                  must be '0.0.0.0' or '::', respectively, while the
                  corresponding instance of the
                  udpEndpointLocalAddressType object represents the
                  appropriate address type.

               3. For an application that is listening for data
                  destined only to a specific IP address, the value
                  of this object is the specific IP address for which
                  this node is receiving packets, with the
                  corresponding instance of the
                  udpEndpointLocalAddressType object representing the
                  appropriate address type.

               As this object is used in the index for the
               udpEndpointTable, implementors of this table should be
               careful not to create entries that would result in OIDs
               with more than 128 subidentifiers; else the information
               cannot be accessed using SNMPv1, SNMPv2c, or SNMPv3."
       ::= { fsMiUdpEndpointEntry 2 }

   fsMiUdpEndpointLocalPort OBJECT-TYPE
       SYNTAX     InetPortNumber
       MAX-ACCESS not-accessible
       STATUS     current
       DESCRIPTION
              "The local port number for this UDP endpoint."
       ::= { fsMiUdpEndpointEntry 3 }

   fsMiUdpEndpointRemoteAddressType OBJECT-TYPE
       SYNTAX     InetAddressType
       MAX-ACCESS not-accessible
       STATUS     current
       DESCRIPTION
              "The address type of udpEndpointRemoteAddress.  Only
               IPv4, IPv4z, IPv6, and IPv6z addresses are expected, or
               unknown(0) if datagrams for all remote IP addresses are
               accepted.  Also, note that some combinations of
               udpEndpointLocalAdressType and
               udpEndpointRemoteAddressType are not supported.  In
               particular, if the value of this object is not
               unknown(0), it is expected to always refer to the
               same IP version as udpEndpointLocalAddressType."
       ::= { fsMiUdpEndpointEntry 4 }

   fsMiUdpEndpointRemoteAddress OBJECT-TYPE
       SYNTAX     InetAddress (SIZE(16))
       MAX-ACCESS not-accessible
       STATUS     current
       DESCRIPTION
              "The remote IP address for this UDP endpoint.  If
               datagrams from any remote system are to be accepted,
               this value is ''h (a zero-length octet-string).
               Otherwise, it has the type described by
               udpEndpointRemoteAddressType and is the address of the
               remote system from which datagrams are to be accepted
               (or to which all datagrams will be sent).

               As this object is used in the index for the
               udpEndpointTable, implementors of this table should be
               careful not to create entries that would result in OIDs
               with more than 128 subidentifiers; else the information
               cannot be accessed using SNMPv1, SNMPv2c, or SNMPv3."
       ::= { fsMiUdpEndpointEntry 5 }

   fsMiUdpEndpointRemotePort OBJECT-TYPE
       SYNTAX     InetPortNumber
       MAX-ACCESS not-accessible
       STATUS     current
       DESCRIPTION
              "The remote port number for this UDP endpoint.  If
               datagrams from any remote system are to be accepted,
               this value is zero."
       ::= { fsMiUdpEndpointEntry 6 }

   fsMiUdpEndpointInstance OBJECT-TYPE
       SYNTAX     Unsigned32 (1..'ffffffff'h)
       MAX-ACCESS not-accessible
       STATUS     current
       DESCRIPTION
              "The instance of this tuple.  This object is used to
               distinguish among multiple processes 'connected' to
               the same UDP endpoint.  For example, on a system
               implementing the BSD sockets interface, this would be
               used to support the SO_REUSEADDR and SO_REUSEPORT
               socket options."
       ::= { fsMiUdpEndpointEntry 7 }

   fsMiUdpEndpointProcess OBJECT-TYPE
       SYNTAX     Unsigned32
       MAX-ACCESS read-only
       STATUS     current
       DESCRIPTION
              "The system's process ID for the process associated with
               this endpoint, or zero if there is no such process.
               This value is expected to be the same as
               HOST-RESOURCES-MIB::hrSWRunIndex or SYSAPPL-MIB::
               sysApplElmtRunIndex for some row in the appropriate
               tables."
       ::= { fsMiUdpEndpointEntry 8 }

 -- The UDP "Endpoint" table for Multiple virtual routers
   fsMiUdpIpvxEndpointTable OBJECT-TYPE
       SYNTAX     SEQUENCE OF FsMiUdpIpvxEndpointEntry
       MAX-ACCESS not-accessible
       STATUS     current
       DESCRIPTION
              "This table contains context specific endpoint entries.
               A table containing information about this entity's UDP
               endpoints on which a local application is currently
               accepting or sending datagrams.
               The address type in this table represents the address
               type used for the communication, irrespective of the
               higher-layer abstraction.  For example, an application
               using IPv6 'sockets' to communicate via IPv4 between
               ::ffff:10.0.0.1 and ::ffff:10.0.0.2 would use
               InetAddressType ipv4(1).

               Unlike the udpTable in RFC 2013, this table also allows
               the representation of an application that completely
               specifies both local and remote addresses and ports.  A
               listening application is represented in three possible
               ways:

               1) An application that is willing to accept both IPv4
                  and IPv6 datagrams is represented by a
                  udpEndpointLocalAddressType of unknown(0) and a
                  udpEndpointLocalAddress of ''h (a zero-length
                  octet-string).

               2) An application that is willing to accept only IPv4
                  or only IPv6 datagrams is represented by a
                  udpEndpointLocalAddressType of the appropriate
                  address type and a udpEndpointLocalAddress of
                  '0.0.0.0' or '::' respectively.

               3) An application that is listening for datagrams only
                  for a specific IP address but from any remote
                  system is represented by a
                  udpEndpointLocalAddressType of the appropriate
                  address type, with udpEndpointLocalAddress
                  specifying the local address.

               In all cases where the remote is a wildcard, the
               udpEndpointRemoteAddressType is unknown(0), the
               udpEndpointRemoteAddress is ''h (a zero-length
               octet-string), and the udpEndpointRemotePort is 0.

               If the operating system is demultiplexing UDP packets
               by remote address and port, or if the application has
               'connected' the socket specifying a default remote
               address and port, the udpEndpointRemote* values should
               be used to reflect this."
       ::= { fsMIUdp 13 }


   fsMiUdpIpvxEndpointEntry OBJECT-TYPE
       SYNTAX     FsMiUdpIpvxEndpointEntry
       MAX-ACCESS not-accessible
       STATUS     current
       DESCRIPTION
              "Information about a particular current UDP endpoint.

               Implementers need to be aware that if the total number
               of elements (octets or sub-identifiers) in
               udpEndpointLocalAddress and udpEndpointRemoteAddress
               exceeds 111, then OIDs of column instances in this table
               will have more than 128 sub-identifiers and cannot be
               accessed using SNMPv1, SNMPv2c, or SNMPv3."
       INDEX   { fsMiUdpIpvxContextId,
                 fsMiUdpIpvxEndpointLocalAddressType,
                 fsMiUdpIpvxEndpointLocalAddress,
                 fsMiUdpIpvxEndpointLocalPort,
                 fsMiUdpIpvxEndpointRemoteAddressType,
                 fsMiUdpIpvxEndpointRemoteAddress,
                 fsMiUdpIpvxEndpointRemotePort,
                 fsMiUdpIpvxEndpointInstance }
       ::= { fsMiUdpIpvxEndpointTable 1 }

   FsMiUdpIpvxEndpointEntry ::= SEQUENCE {
           fsMiUdpIpvxEndpointLocalAddressType   InetAddressType,
           fsMiUdpIpvxEndpointLocalAddress       InetAddress,
           fsMiUdpIpvxEndpointLocalPort          InetPortNumber,
           fsMiUdpIpvxEndpointRemoteAddressType  InetAddressType,
           fsMiUdpIpvxEndpointRemoteAddress      InetAddress,
           fsMiUdpIpvxEndpointRemotePort         InetPortNumber,
           fsMiUdpIpvxEndpointInstance           Unsigned32,
           fsMiUdpIpvxEndpointProcess            Unsigned32
       }

   fsMiUdpIpvxEndpointLocalAddressType OBJECT-TYPE
       SYNTAX     InetAddressType
       MAX-ACCESS not-accessible
       STATUS     current
       DESCRIPTION
              "The address type of udpEndpointLocalAddress.  Only
               IPv4, IPv4z, IPv6, and IPv6z addresses are expected, or
               unknown(0) if datagrams for all local IP addresses are
               accepted."
       ::= { fsMiUdpIpvxEndpointEntry 1 }

   fsMiUdpIpvxEndpointLocalAddress OBJECT-TYPE
       SYNTAX     InetAddress (SIZE(16))
       MAX-ACCESS not-accessible
       STATUS     current
       DESCRIPTION
              "The local IP address for this UDP endpoint.

               The value of this object can be represented in three
               possible ways, depending on the characteristics of the
               listening application:

               1. For an application that is willing to accept both
                  IPv4 and IPv6 datagrams, the value of this object
                  must be ''h (a zero-length octet-string), with
                  the value of the corresponding instance of the
                  udpEndpointLocalAddressType object being unknown(0).

               2. For an application that is willing to accept only IPv4
                  or only IPv6 datagrams, the value of this object
                  must be '0.0.0.0' or '::', respectively, while the
                  corresponding instance of the
                  udpEndpointLocalAddressType object represents the
                  appropriate address type.

               3. For an application that is listening for data
                  destined only to a specific IP address, the value
                  of this object is the specific IP address for which
                  this node is receiving packets, with the
                  corresponding instance of the
                  udpEndpointLocalAddressType object representing the
                  appropriate address type.

               As this object is used in the index for the
               udpEndpointTable, implementors of this table should be
               careful not to create entries that would result in OIDs
               with more than 128 subidentifiers; else the information
               cannot be accessed using SNMPv1, SNMPv2c, or SNMPv3."
       ::= { fsMiUdpIpvxEndpointEntry 2 }

   fsMiUdpIpvxEndpointLocalPort OBJECT-TYPE
       SYNTAX     InetPortNumber
       MAX-ACCESS not-accessible
       STATUS     current
       DESCRIPTION
              "The local port number for this UDP endpoint."
       ::= { fsMiUdpIpvxEndpointEntry 3 }

   fsMiUdpIpvxEndpointRemoteAddressType OBJECT-TYPE
       SYNTAX     InetAddressType
       MAX-ACCESS not-accessible
       STATUS     current
       DESCRIPTION
              "The address type of udpEndpointRemoteAddress.  Only
               IPv4, IPv4z, IPv6, and IPv6z addresses are expected, or
               unknown(0) if datagrams for all remote IP addresses are
               accepted.  Also, note that some combinations of
               udpEndpointLocalAdressType and
               udpEndpointRemoteAddressType are not supported.  In
               particular, if the value of this object is not
               unknown(0), it is expected to always refer to the
               same IP version as udpEndpointLocalAddressType."
       ::= { fsMiUdpIpvxEndpointEntry 4 }

   fsMiUdpIpvxEndpointRemoteAddress OBJECT-TYPE
       SYNTAX     InetAddress (SIZE(16))
       MAX-ACCESS not-accessible
       STATUS     current
       DESCRIPTION
              "The remote IP address for this UDP endpoint.  If
               datagrams from any remote system are to be accepted,
               this value is ''h (a zero-length octet-string).
               Otherwise, it has the type described by
               udpEndpointRemoteAddressType and is the address of the
               remote system from which datagrams are to be accepted
               (or to which all datagrams will be sent).

               As this object is used in the index for the
               udpEndpointTable, implementors of this table should be
               careful not to create entries that would result in OIDs
               with more than 128 subidentifiers; else the information
               cannot be accessed using SNMPv1, SNMPv2c, or SNMPv3."
       ::= { fsMiUdpIpvxEndpointEntry 5 }

   fsMiUdpIpvxEndpointRemotePort OBJECT-TYPE
       SYNTAX     InetPortNumber
       MAX-ACCESS not-accessible
       STATUS     current
       DESCRIPTION
              "The remote port number for this UDP endpoint.  If
               datagrams from any remote system are to be accepted,
               this value is zero."
       ::= { fsMiUdpIpvxEndpointEntry 6 }

   fsMiUdpIpvxEndpointInstance OBJECT-TYPE
       SYNTAX     Unsigned32 (1..'ffffffff'h)
       MAX-ACCESS not-accessible
       STATUS     current
       DESCRIPTION
              "The instance of this tuple.  This object is used to
               distinguish among multiple processes 'connected' to
               the same UDP endpoint.  For example, on a system
               implementing the BSD sockets interface, this would be
               used to support the SO_REUSEADDR and SO_REUSEPORT
               socket options."
       ::= { fsMiUdpIpvxEndpointEntry 7 }

   fsMiUdpIpvxEndpointProcess OBJECT-TYPE
       SYNTAX     Unsigned32
       MAX-ACCESS read-only
       STATUS     current
       DESCRIPTION
              "The system's process ID for the process associated with
               this endpoint, or zero if there is no such process.
               This value is expected to be the same as
               HOST-RESOURCES-MIB::hrSWRunIndex or SYSAPPL-MIB::
               sysApplElmtRunIndex for some row in the appropriate
               tables."
       ::= { fsMiUdpIpvxEndpointEntry 8 }

   END
