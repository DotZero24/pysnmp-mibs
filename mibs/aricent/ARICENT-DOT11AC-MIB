--******************************************************************************
--Copyright (C) 2012 Aricent Inc . All Rights Reserved
--
--$Id: fs11ac.mib,v 1.5 2016/05/23 12:40:14 siva Exp $
--
--Description : This file contains MIB definitions for ISS module.
--
--******************************************************************************/

-- AricentISS MIB Definition

-- MIB for 'Wireless Switch Solution'

-- The 'Wireless Switch Solution' MIB definition is as follows:



ARICENT-DOT11AC-MIB DEFINITIONS ::= BEGIN

IMPORTS
   MODULE-IDENTITY, OBJECT-TYPE,
   enterprises, Unsigned32, Integer32 FROM SNMPv2-SMI
   ifIndex FROM IF-MIB
   TruthValue FROM SNMPv2-TC;

fs11AC MODULE-IDENTITY
      LAST-UPDATED "201503050000Z"
      ORGANIZATION "ARICENT COMMUNICATIONS SOFTWARE"
      CONTACT-INFO

        "ARICENT COMMUNICATIONS SOFTWARE
         3460 Hillview Avenue,
         Palo Alto, CA 94304-1388, USA,
         Phone : +1-650-391-1088
         E-mail:support@aricent.com"

      DESCRIPTION
       "The enterprise ID 29601 is assigned to Aricent Communication
       Holdings Limitied."
      REVISION "201503050000Z"

      DESCRIPTION
         "The MIB for 802.11AC in WSS module."
   ::=  { enterprises aricent-communication-holding-ltd(29601) iss(2) 100 }


-- ----------------------------------------------------------------- --
-- groups in the MIB
-- ----------------------------------------------------------------- --

fsDot11ACConfig          OBJECT IDENTIFIER ::= { fs11AC 1 }
fsDot11VHTStationConfig  OBJECT IDENTIFIER ::= { fs11AC 2 }
fsDot11PhyVHT            OBJECT IDENTIFIER ::= { fs11AC 3 }

-- *********************** 11ac Configuration ***************************

-- ********************11ac Congiguration Table *************************

fsDot11ACConfigTable OBJECT-TYPE
	SYNTAX SEQUENCE OF FsDot11ACConfigEntry
	MAX-ACCESS not-accessible
	STATUS current
	DESCRIPTION
	"This table contains Station Configuration attributes in tabular form to allow for multiple
	instances on an agent."
	::= { fsDot11ACConfig 1 }

fsDot11ACConfigEntry OBJECT-TYPE
	SYNTAX FsDot11ACConfigEntry
	MAX-ACCESS not-accessible
	STATUS current
	DESCRIPTION
	"This object specifies an entry (conceptual row) in the dot11HTStationConfig Table.
	ifIndex - Each IEEE 802.11 interface is represented by an ifEntry. Interface
	tables in this MIB module are indexed by ifIndex."
	INDEX { ifIndex }
	::= { fsDot11ACConfigTable 1 }

FsDot11ACConfigEntry ::= SEQUENCE {
				fsDot11ACMaxMPDULength INTEGER,
				fsDot11ACMaxMPDULengthConfig INTEGER,
				fsDot11ACVHTMaxRxAMPDUFactor Unsigned32,
				fsDot11ACVHTMaxRxAMPDUFactorConfig Unsigned32,
				fsDot11ACVHTControlFieldSupported TruthValue,
				fsDot11ACVHTTXOPPowerSaveOptionImplemented TruthValue,
				fsDot11ACVHTRxMCSMap OCTET STRING,
				fsDot11ACVHTRxHighestDataRateSupported Unsigned32,
				fsDot11ACVHTTxMCSMap OCTET STRING,
				fsDot11ACVHTTxHighestDataRateSupported Unsigned32,
				fsDot11ACVHTOBSSScanCount Unsigned32,
				fsDot11ACCurrentChannelBandwidth INTEGER,
				fsDot11ACCurrentChannelBandwidthConfig INTEGER,
	                        fsDot11ACCurrentChannelCenterFrequencyIndex0 Unsigned32,
				fsDot11ACCurrentChannelCenterFrequencyIndex0Config Unsigned32,
        	                fsDot11ACCurrentChannelCenterFrequencyIndex1 Unsigned32,
                	        fsDot11ACVHTShortGIOptionIn80Implemented TruthValue,
                        	fsDot11ACVHTShortGIOptionIn80Activated TruthValue,
	                        fsDot11ACVHTShortGIOptionIn160and80p80Implemented TruthValue,
	                        fsDot11ACVHTShortGIOptionIn160and80p80Activated TruthValue,
	                        fsDot11ACVHTLDPCCodingOptionImplemented TruthValue,
	                        fsDot11ACVHTLDPCCodingOptionActivated TruthValue,
	                        fsDot11ACVHTTxSTBCOptionImplemented TruthValue,
	                        fsDot11ACVHTTxSTBCOptionActivated TruthValue,
	                        fsDot11ACVHTRxSTBCOptionImplemented TruthValue,
	                        fsDot11ACVHTRxSTBCOptionActivated TruthValue,
	                        fsDot11ACVHTMUMaxUsersImplemented Unsigned32,
	                        fsDot11ACVHTMUMaxNSTSPerUserImplemented Unsigned32,
	                        fsDot11ACVHTMUMaxNSTSTotalImplemented Unsigned32,
				fsDot11ACSuBeamFormer INTEGER,
				fsDot11ACSuBeamFormee INTEGER,
				fsDot11ACMuBeamFormer INTEGER,
				fsDot11ACMuBeamFormee INTEGER,
				fsDot11ACVHTLinkAdaption INTEGER,
				fsDot11ACRxAntennaPattern INTEGER,
				fsDot11ACTxAntennaPattern INTEGER,
				fsDot11ACBasicMCSMap OCTET STRING,
				fsDot11ACVHTRxMCSMapConfig OCTET STRING,
				fsDot11ACVHTTxMCSMapConfig OCTET STRING,
				fsDot11ACCurrentChannelCenterFrequencyIndex1Config Unsigned32,
                fsDot11VHTOptionImplemented TruthValue,
                fsDot11OperatingModeNotificationImplemented TruthValue,
                fsDot11ExtendedChannelSwitchActivated TruthValue,
                fsDot11FragmentationThreshold Unsigned32
				}


fsDot11ACMaxMPDULength OBJECT-TYPE
	SYNTAX INTEGER { short(3895), medium(7991), long(11454) }
	MAX-ACCESS read-write
	STATUS current
	DESCRIPTION
		"This object specifies the supported maximum MPDU size, and
		is determined by device capabilities."
	DEFVAL { short }
	::= { fsDot11ACConfigEntry 1 }

fsDot11ACMaxMPDULengthConfig OBJECT-TYPE
        SYNTAX INTEGER { short(3895), medium(7991), long(11454) }
        MAX-ACCESS read-write
        STATUS current
        DESCRIPTION
        "This object specifies the supported maximum MPDU size
		and its maximum value can only be less than or equal to
		device capability(fsDot11ACMaxMPDULength)."
        DEFVAL { short }
        ::= { fsDot11ACConfigEntry 2 }

fsDot11ACVHTMaxRxAMPDUFactor OBJECT-TYPE
	SYNTAX Unsigned32 (0..7)
	MAX-ACCESS read-write
	STATUS current
	DESCRIPTION
		"This object specifies the maximum length of A-MPDU that the STA can
		receive. The Maximum Rx A-MPDU defined by this field is equal to
		2^(13+fsDot11ACVHTMaxRxAMPDUFactor) -1 octets."
	DEFVAL { 0 }
	::= { fsDot11ACConfigEntry 3 }

fsDot11ACVHTMaxRxAMPDUFactorConfig  OBJECT-TYPE
        SYNTAX Unsigned32 (0..7)
        MAX-ACCESS read-write
        STATUS current
        DESCRIPTION
                "This object specifies the maximum length of A-MPDU that the STA can
                receive. The Maximum Rx A-MPDU defined by this field is equal to
                2^(13+fsDot11ACVHTMaxRxAMPDUFactorConfig) -1 octets and its value can
		only be less than or equal to the device capability
		(fsDot11ACVHTMaxRxAMPDUFactor)"
        DEFVAL { 0 }
        ::= { fsDot11ACConfigEntry 4 }


fsDot11ACVHTControlFieldSupported OBJECT-TYPE
	SYNTAX TruthValue
	MAX-ACCESS read-write
	STATUS current
	DESCRIPTION
		"This object specifies that the station implementation is
		capable of receiving the VHT variant HT Control field."
	DEFVAL { false }
	::= { fsDot11ACConfigEntry 5 }


fsDot11ACVHTTXOPPowerSaveOptionImplemented OBJECT-TYPE
	SYNTAX TruthValue
	MAX-ACCESS read-write
	STATUS current
	DESCRIPTION
		"This object specifies that the station implementation is
		capable of TXOP Power Save operation."
	DEFVAL { false }
	::= { fsDot11ACConfigEntry 6 }


fsDot11ACVHTRxMCSMap OBJECT-TYPE
	SYNTAX OCTET STRING (SIZE(8))
	MAX-ACCESS read-write
	STATUS current
	DESCRIPTION
		"This object specifies the highest MCS supported (for Rx) on the number of
		streams represented by the octet position (first octet represents 1
		stream, second octet represents 2 streams, etc.). A value 0 indicates that
		MCSs 0-7 are supported. A value 1 indicates that MCSs 0-8 are supported. A
		value 2 indicates that MCSs 0-9 are supported. A value 3 indicates no support
		for that number of spatial streams."
	::= { fsDot11ACConfigEntry 7 }

fsDot11ACVHTRxHighestDataRateSupported OBJECT-TYPE
	SYNTAX Unsigned32
	MAX-ACCESS read-write
	STATUS current
	DESCRIPTION
		"This object specifies the highest data rate in Mb/s
        that the STA is capable of receiving."
	::= { fsDot11ACConfigEntry 8 }


fsDot11ACVHTTxMCSMap OBJECT-TYPE
	SYNTAX OCTET STRING (SIZE(8))
	MAX-ACCESS read-write
	STATUS current
	DESCRIPTION
		"This object specifies the highest MCS supported (for Tx) on the number of
		streams represented by the octet position (first octet represents 1
		stream, second octet represents 2 streams, etc.). A value 0 indicates that
		MCSs 0-7 are supported. A value 1 indicates that MCSs 0-8 are supported. A
		value 2 indicates that MCSs 0-9 are supported. A value 3 indicates no support
		for that number of spatial streams."
	::= { fsDot11ACConfigEntry 9 }


fsDot11ACVHTTxHighestDataRateSupported OBJECT-TYPE
	SYNTAX Unsigned32
	MAX-ACCESS read-write
	STATUS current
	DESCRIPTION
		"This object specifies the highest data rate in Mb/s
        that the STA is capable of transmitting."
	DEFVAL { 0 }
	::= { fsDot11ACConfigEntry 10 }


fsDot11ACVHTOBSSScanCount OBJECT-TYPE
	SYNTAX Unsigned32 (3..100)
	MAX-ACCESS read-write
	STATUS current
	DESCRIPTION
		"This object specifies the minimum number of scan operations performed on
		a channel to detect another OBSS."
	DEFVAL { 3 }
	::= { fsDot11ACConfigEntry 11 }

fsDot11ACCurrentChannelBandwidth OBJECT-TYPE
	SYNTAX INTEGER { cbw20(0), cbw40(1), cbw80(2), cbw160(3), cbw80p80(4) }
	MAX-ACCESS read-write
	STATUS current
	DESCRIPTION
		"This object specifies the operating channel width."
	DEFVAL { cbw20 }
	::= { fsDot11ACConfigEntry 12 }

fsDot11ACCurrentChannelBandwidthConfig OBJECT-TYPE
        SYNTAX INTEGER { cbw20(0), cbw40(1), cbw80(2), cbw160(3), cbw80p80(4) }
        MAX-ACCESS read-write
        STATUS current
        DESCRIPTION
        "This object specifies the operating channel width and its
		value that can  be less than or equal to the status variable
		(fsDot11ACCurrentChannelBandwidth)"
        DEFVAL { cbw20 }
        ::= { fsDot11ACConfigEntry 13 }

fsDot11ACCurrentChannelCenterFrequencyIndex0 OBJECT-TYPE
	SYNTAX Unsigned32 (0..200)
	MAX-ACCESS read-write
	STATUS current
	DESCRIPTION
		"This object specifies the channel center frequency such as
		20 MHz, 40 MHz, 80 MHz or 160 MHz channel(Ed) where an
		80+80 MHz channel(Ed), denotes the center frequency of frequency
		segment 0."
	DEFVAL { 0 }
	::= { fsDot11ACConfigEntry 14 }

fsDot11ACCurrentChannelCenterFrequencyIndex0Config OBJECT-TYPE
        SYNTAX Unsigned32 (0..200)
        MAX-ACCESS read-write
        STATUS current
        DESCRIPTION
        "This object specifies the channel
        center frequency such as 20 MHz, 40 MHz, 80 MHz or 160
        MHz channel(Ed), where an 80+80 MHz channel(Ed), denotes
        the center frequency of frequency segment 0.
		The value of the frequency cannot exceed the status variable's value
		(fsDot11ACCurrentChannelCenterFrequencyIndex0)."
        DEFVAL { 0 }
        ::= { fsDot11ACConfigEntry 15 }

fsDot11ACCurrentChannelCenterFrequencyIndex1 OBJECT-TYPE
	SYNTAX Unsigned32 (0..200)
	MAX-ACCESS read-write
	STATUS current
	DESCRIPTION
		"This object specifies the channel
         center frequency such as 20 MHz, 40 MHz, 80 MHz or 160
         MHz channel(Ed), where an 80+80 MHz channel(Ed), denotes
         the center frequency of frequency segment 1."
	DEFVAL { 0 }
	::= { fsDot11ACConfigEntry 16 }


fsDot11ACVHTShortGIOptionIn80Implemented OBJECT-TYPE
	SYNTAX TruthValue
	MAX-ACCESS read-write
	STATUS current
	DESCRIPTION
		"This object specifies that the device is capable of receiving
		80 MHz short guard interval packets."
	DEFVAL { false }
	::= { fsDot11ACConfigEntry 17 }


fsDot11ACVHTShortGIOptionIn80Activated OBJECT-TYPE
	SYNTAX TruthValue
	MAX-ACCESS read-write
	STATUS current
	DESCRIPTION
		"This object specifies that the reception of 80 MHz short
		guard interval packets is enabled. Changes
        made while associated with an AP or while operating a BSS should
        take effect only after disassociation or the deactivation of
        the BSS, respectively."

	DEFVAL { false }
	::= { fsDot11ACConfigEntry 18 }


fsDot11ACVHTShortGIOptionIn160and80p80Implemented OBJECT-TYPE
	SYNTAX TruthValue
	MAX-ACCESS read-write
	STATUS current
	DESCRIPTION
		"This object specifies that the device is capable of receiving
		160 MHz and 80+80 MHz short guard interval packets."
	DEFVAL { false }
	::= { fsDot11ACConfigEntry 19 }


fsDot11ACVHTShortGIOptionIn160and80p80Activated OBJECT-TYPE
	SYNTAX TruthValue
	MAX-ACCESS read-write
	STATUS current
	DESCRIPTION
		"This object specifies that the reception of 160 MHz and
        80+80 MHz short guard interval packets is enabled.
		Changes take effect as soon as practical in the implementation. Changes
		made while associated with an AP or while operating a BSS should take
		effect only after disassociation or the deactivation of the BSS, respectively."
	DEFVAL { false }
	::= { fsDot11ACConfigEntry 20 }


fsDot11ACVHTLDPCCodingOptionImplemented OBJECT-TYPE
	SYNTAX TruthValue
	MAX-ACCESS read-write
	STATUS current
	DESCRIPTION
		"This object specifies that the LDPC coding option for VHT
		packets is implemented."
	DEFVAL { false }
	::= { fsDot11ACConfigEntry 21 }


fsDot11ACVHTLDPCCodingOptionActivated OBJECT-TYPE
	SYNTAX TruthValue
	MAX-ACCESS read-write
	STATUS current
	DESCRIPTION
		"This object specifies that the LDPC coding option for VHT
        packets is enabled.
        Changes take effect as soon as practical in the implementation. Changes
		made while associated with an AP or while operating a BSS should take
		effect only after disassociation or the deactivation of the BSS, respectively."
	DEFVAL { false }
	::= { fsDot11ACConfigEntry 22 }


fsDot11ACVHTTxSTBCOptionImplemented OBJECT-TYPE
	SYNTAX TruthValue
	MAX-ACCESS read-write
	STATUS current
	DESCRIPTION
		"This object specifies that the device is capable of transmitting
		VHT PPDUs using STBC."
	DEFVAL { false }
	::= { fsDot11ACConfigEntry 23 }


fsDot11ACVHTTxSTBCOptionActivated OBJECT-TYPE
	SYNTAX TruthValue
	MAX-ACCESS read-write
	STATUS current
	DESCRIPTION
		"This object specifies that the entity's capability for
        transmitting VHT PPDUs using STBC is enabled.
		Changes take effect as soon as practical in the implementation. Changes
		made while associated with an AP or while operating a BSS should take
		effect only after disassociation or the deactivation of the BSS, respectively."
	DEFVAL { false }
	::= { fsDot11ACConfigEntry 24 }


fsDot11ACVHTRxSTBCOptionImplemented OBJECT-TYPE
	SYNTAX TruthValue
	MAX-ACCESS read-write
	STATUS current
	DESCRIPTION
		"This object specifies that the device is capable of receiving
		VHT PPDUs using STBC."
	DEFVAL { false }
	::= { fsDot11ACConfigEntry 25 }


fsDot11ACVHTRxSTBCOptionActivated OBJECT-TYPE
	SYNTAX TruthValue
	MAX-ACCESS read-write
	STATUS current
	DESCRIPTION
		"This object specifies that the entity's capability for
        receiving VHT PPDUs using STBC is enabled.
		Changes take effect as soon as practical in the implementation. Changes
		made while associated with an AP or while operating a BSS should take
		effect only after disassociation or the deactivation of the BSS, respectively."
	DEFVAL { false }
	::= { fsDot11ACConfigEntry 26 }


fsDot11ACVHTMUMaxUsersImplemented OBJECT-TYPE
	SYNTAX Unsigned32
	MAX-ACCESS read-write
	STATUS current
	DESCRIPTION
		"This object specifies the maximum number of users to which the device
		is capable of transmitting within a MU PPDU."
	DEFVAL { 1 }
	::= { fsDot11ACConfigEntry 27 }


fsDot11ACVHTMUMaxNSTSPerUserImplemented OBJECT-TYPE
	SYNTAX Unsigned32
	MAX-ACCESS read-write
	STATUS current
	DESCRIPTION
		"This object specifies the maximum number of space-time streams per user
		that the device is capable of transmitting within a MU PPDU."
	DEFVAL { 1 }
	::= { fsDot11ACConfigEntry 28 }


fsDot11ACVHTMUMaxNSTSTotalImplemented OBJECT-TYPE
	SYNTAX Unsigned32
	MAX-ACCESS read-write
	STATUS current
	DESCRIPTION
		"This object specifies the maximum number of space-time streams for all
		users that the device is capable of transmitting within a MU DU."
	DEFVAL { 1 }
	::= { fsDot11ACConfigEntry 29 }

fsDot11ACSuBeamFormer OBJECT-TYPE
        SYNTAX Integer32
        MAX-ACCESS read-write
        STATUS current
        DESCRIPTION
            "This object specifies the support for operation
		    as an SU beamformer where the value is set to
            0 if not supported or is set to 1 if supported."
        DEFVAL { 0 }
        ::= { fsDot11ACConfigEntry 30 }

fsDot11ACSuBeamFormee OBJECT-TYPE
        SYNTAX Integer32
        MAX-ACCESS read-write
        STATUS current
        DESCRIPTION
                "This object specifies the support for operation
                as an SU beamformee where the value is set to
                0 if not supported or is set to 1 if supported."
        DEFVAL { 0 }
        ::= { fsDot11ACConfigEntry 31 }

fsDot11ACMuBeamFormer OBJECT-TYPE
        SYNTAX Integer32
        MAX-ACCESS read-write
        STATUS current
        DESCRIPTION
                "This object specifies the support for operation
                as an MU beamformer where the value is
                set to 0 if not supported or if SU Beamformer Capable
                or if sent by a non-AP STA
		        or is set to 1 if supported and SU Beamformer
		        Capable."
        DEFVAL { 0 }
        ::= { fsDot11ACConfigEntry 32 }

fsDot11ACMuBeamFormee OBJECT-TYPE
        SYNTAX Integer32
        MAX-ACCESS read-write
        STATUS current
        DESCRIPTION
                "This object specifies the support for operation
                as an MU beamformee where the value is
                set to 0 if not supported or if SU Beamformee Capable
                or if sent by an AP
		        or is set to 1 if supported and SU Beamformee
		        Capable."
        DEFVAL { 0 }
        ::= { fsDot11ACConfigEntry 33 }

fsDot11ACVHTLinkAdaption OBJECT-TYPE
        SYNTAX Integer32 (0..3)
        MAX-ACCESS read-write
        STATUS current
        DESCRIPTION
                "This object specifies whether or not the
		        STA supports link adaptation using VHT variant HT Control
		        field. If +HTC-VHT Capable is 1:
		        Set to 0 (No Feedback) if the STA does not
		        provide VHT MFB.
		        Set to 2 (Unsolicited) if the STA provides
		        only unsolicited VHT MFB.
		        Set to 3 (Both) if the STA can provide VHT
		        MFB in response to VHT MRQ and if the
		        STA provides unsolicited VHT MFB.
		        The value 1 is reserved.
		        it is reserved even when +HTC-VHT Capable is 0."
        DEFVAL { 1 }
        ::= { fsDot11ACConfigEntry 34 }

fsDot11ACRxAntennaPattern OBJECT-TYPE
        SYNTAX Integer32
        MAX-ACCESS read-write
        STATUS current
        DESCRIPTION
                "This object specifies the possibility of Rx
		        antenna pattern change where the value is set
                to 0 if Rx antenna pattern might change
		        during the lifetime of the current association.
		        or is set to 1 if Rx antenna pattern does not change
		        during the lifetime of the current association."
        DEFVAL { 1 }
        ::= { fsDot11ACConfigEntry 35 }

fsDot11ACTxAntennaPattern OBJECT-TYPE
        SYNTAX Integer32
        MAX-ACCESS read-write
        STATUS current
        DESCRIPTION
                "This object specifies the possibility of Tx
                antenna pattern change where the value is set
                to 0 if Rx antenna pattern might change
                during the lifetime of the current association.
                or is set to 1 if Tx antenna pattern does not change
                during the lifetime of the current association."
        DEFVAL { 1 }
        ::= { fsDot11ACConfigEntry 36 }

fsDot11ACBasicMCSMap OBJECT-TYPE
        SYNTAX OCTET STRING (SIZE(8))
        MAX-ACCESS read-write
        STATUS current
        DESCRIPTION
                "This object specifies the MCSs for each number of spatial
		        streams in VHT PPDUs that
		        are supported by all VHT STAs in the BSS (including IBSS and MBSS).
		        It is a bitmap of size 16 bits; each 2 bits indicates the supported
		        MCS set for NSS from 1 to 8."
        ::= { fsDot11ACConfigEntry 37 }

fsDot11ACVHTRxMCSMapConfig OBJECT-TYPE
        SYNTAX OCTET STRING (SIZE(8))
        MAX-ACCESS read-write
        STATUS current
        DESCRIPTION
                "This object specifies the Rx MCS Map that is to be configured
                to the access point from the controller.
                Its value depends on the capability variable(fsDot11ACVHTRxMCSMap).
                Each octet represents the highest MCS supported (for Rx) on the number of
                streams represented by the octet position (first octet represents 1
                stream, second octet represents 2 streams, etc.). A value 0 indicates that
                MCSs 0-7 are supported. A value 1 indicates that MCSs 0-8 are supported. A
                value 2 indicates that MCSs 0-9 are supported. A value 3 indicates no support
                for that number of spatial streams."
        ::= { fsDot11ACConfigEntry 38 }

fsDot11ACVHTTxMCSMapConfig OBJECT-TYPE
        SYNTAX OCTET STRING (SIZE(8))
        MAX-ACCESS read-write
        STATUS current
        DESCRIPTION
                "This object specifies the Tx MCS Map that is to be configured
                to the access point from the controller.
                Its value depends on the capability variable(fsDot11ACVHTTxMCSMap).
                Each octet represents the highest MCS supported (for Rx) on the number of
                streams represented by the octet position (first octet represents 1
                stream, second octet represents 2 streams, etc.). A value 0 indicates that
                MCSs 0-7 are supported. A value 1 indicates that MCSs 0-8 are supported. A
                value 2 indicates that MCSs 0-9 are supported. A value 3 indicates no support
                for that number of spatial streams."
        ::= { fsDot11ACConfigEntry 39 }

fsDot11ACCurrentChannelCenterFrequencyIndex1Config OBJECT-TYPE
        SYNTAX Unsigned32 (0..200)
        MAX-ACCESS read-write
        STATUS current
        DESCRIPTION
                "This object specifies the channel
                 center frequency such as 20 MHz, 40 MHz, 80 MHz or 160
                 MHz channel(Ed), where an 80+80 MHz channel(Ed),
                 denotes the center frequency of frequency segment 1.
                 The value of this cannot exceed the status variable's value
                (fsDot11ACCurrentChannelCenterFrequencyIndex1)."
        DEFVAL { 0 }
        ::= { fsDot11ACConfigEntry 40 }

fsDot11VHTOptionImplemented OBJECT-TYPE
        SYNTAX TruthValue
        MAX-ACCESS read-write
        STATUS current
        DESCRIPTION
                "This object indicates whether the entity is VHT capable."
        ::= { fsDot11ACConfigEntry 41}


fsDot11OperatingModeNotificationImplemented OBJECT-TYPE
        SYNTAX TruthValue
        MAX-ACCESS read-write
        STATUS current
        DESCRIPTION
                "This object indicates whether the entity is
                Operating Mode Notification capable."
        ::= { fsDot11ACConfigEntry 42 }

fsDot11ExtendedChannelSwitchActivated OBJECT-TYPE
        SYNTAX TruthValue
        MAX-ACCESS read-write
        STATUS current
        DESCRIPTION
                "This object when true, indicates that the station implementation is
                capable of supporting Extended Channel Switch Announcement. The capability
                is disabled, otherwise."
        DEFVAL { false }
        ::= { fsDot11ACConfigEntry 43 }

fsDot11FragmentationThreshold OBJECT-TYPE
        SYNTAX Unsigned32 (256..11500)
        MAX-ACCESS read-write
        STATUS current
        DESCRIPTION
                "This object specifies the current maximum size of the MPDU (in octets)
                that may be delivered to the security encapsulation. This maximum size
                does not apply when an MSDU is transmitted using an HT-immediate or
                HTdelayed Block Ack agreement, or when an MSDU or MMPDU is carried in
                an AMPDU that does not contain a VHT single MPDU. Fields added to the
                frame by security encapsulation are not counted against the limit specified
                by this object. Except as described above, an MSDU or MMPDU is fragmented
                when the resulting frame has an individual address in the Address1 field,
                and the length of the frame is larger than this threshold, excluding security
                encapsulation fields. The default value for this object is less than 11500
                or the aMPDUMaxLength or the aPSDUMaxLength of the attached PHY. This
                object is the extension of the previously available fragmentation
                threshold Mib available in fswlan.mib"
        ::= { fsDot11ACConfigEntry 44 }

-- ********************************************************************
-- * End of 11acConfigTable TABLE
-- ********************************************************************


-- ********************************************************************
-- * fsDot11VHTStationConfigTABLE
-- ********************************************************************
fsDot11VHTStationConfigTable OBJECT-TYPE
    SYNTAX SEQUENCE OF FsDot11VHTStationConfigEntry
    MAX-ACCESS not-accessible
    STATUS current
    DESCRIPTION
                "This object specifies the entry in VHTStationConfig TABLE
                to allow multiple instances on an agent."
    ::= { fsDot11VHTStationConfig 1 }

fsDot11VHTStationConfigEntry OBJECT-TYPE
    SYNTAX FsDot11VHTStationConfigEntry
    MAX-ACCESS not-accessible
    STATUS current
    DESCRIPTION
                "This object specifies an entry (conceptual row) in the
                dot11VHTStationConfig Table. ifIndex - Each IEEE 802.11
                interface is represented by an ifEntry.
                Interface tables in this MIB module are indexed by ifIndex."
    INDEX { ifIndex }
    ::= { fsDot11VHTStationConfigTable 1 }

FsDot11VHTStationConfigEntry ::= SEQUENCE {
                            fsDot11VHTRxHighestDataRateConfig Unsigned32,
                            fsDot11VHTTxHighestDataRateConfig Unsigned32
                        }

fsDot11VHTRxHighestDataRateConfig OBJECT-TYPE
        SYNTAX Unsigned32
        MAX-ACCESS read-write
        STATUS current
        DESCRIPTION
                "This object specifies the highest data rate in Mb/s that
                the STA is capable of receiving."
        DEFVAL { 0 }
        ::= { fsDot11VHTStationConfigEntry 1 }

fsDot11VHTTxHighestDataRateConfig OBJECT-TYPE
        SYNTAX Unsigned32
        MAX-ACCESS read-write
        STATUS current
        DESCRIPTION
                "This object specifies the highest data rate in Mb/s that
                the STA is capable of transmitting."
        DEFVAL { 0 }
        ::= { fsDot11VHTStationConfigEntry 2 }


-- ********************************************************************
-- * End of fsDot11VHTStationConfig TABLE
-- ********************************************************************

-- ****************************** **************************************
-- * fsDot11PhyVHT  TABLE
-- ********************************************************************
fsDot11PhyVHTTable OBJECT-TYPE
    SYNTAX SEQUENCE OF FsDot11PhyVHTEntry
    MAX-ACCESS not-accessible
    STATUS current
    DESCRIPTION
    "This object specifies the entry of attributes in dot11PhyVHTTable.
    Implemented as a table indexed on ifIndex to allow for multiple
    instances on an agent."
    ::= { fsDot11PhyVHT 1 }

fsDot11PhyVHTEntry OBJECT-TYPE
    SYNTAX FsDot11PhyVHTEntry
    MAX-ACCESS not-accessible
    STATUS current
    DESCRIPTION
    "This object specifies an entry in the dot11PhyVHTEntry Table.
    ifIndex - Each IEEE 802.11 interface is represented by an ifEntry.
    Interface tables in this MIB module are indexed by ifIndex."
    INDEX {ifIndex}
    ::= { fsDot11PhyVHTTable 1 }

FsDot11PhyVHTEntry ::= SEQUENCE {
                    fsDot11NumberOfSpatialStreamsImplemented Unsigned32,
                    fsDot11NumberOfSpatialStreamsActivated Unsigned32
                }

fsDot11NumberOfSpatialStreamsImplemented OBJECT-TYPE
        SYNTAX Unsigned32 (1..8)
        MAX-ACCESS read-write
        STATUS current
        DESCRIPTION
                "This object specifies the maximum number of
                spatial streams implemented."
        DEFVAL { 3 }
        ::= { fsDot11PhyVHTEntry 1 }

fsDot11NumberOfSpatialStreamsActivated OBJECT-TYPE
        SYNTAX Unsigned32 (1..8)
        MAX-ACCESS read-write
        STATUS current
        DESCRIPTION
                "This object specifies the maximum number of
                spatial streams enabled."
        DEFVAL { 3 }
        ::= { fsDot11PhyVHTEntry 2 }

-- ********************************************************************
-- * End of fsDot11PhyVHT TABLE
-- ********************************************************************


END
