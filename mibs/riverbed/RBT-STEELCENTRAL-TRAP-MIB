--
-- Riverbed SteelCentral Generic MIB (NPM platform)
-- Copyright 2017 Riverbed Technology. All rights reserved.
--

RBT-STEELCENTRAL-TRAP-MIB DEFINITIONS ::= BEGIN


    IMPORTS
    OBJECT-TYPE, NOTIFICATION-TYPE, MODULE-IDENTITY, Unsigned32,
    enterprises, IpAddress, Integer32
        FROM SNMPv2-SMI
    DisplayString, DateAndTime
        FROM SNMPv2-TC
    OBJECT-GROUP
        FROM SNMPv2-CONF
    InetAddress, InetAddressType
        FROM INET-ADDRESS-MIB
    products, rbtTrap, rbtTrapInfo
	FROM RBT-MIB;
--
-- Riverbed SteelCentral Trap
--


steelcentralTrapModule MODULE-IDENTITY
    LAST-UPDATED "201604300000Z"
    ORGANIZATION "Riverbed Technology"
    CONTACT-INFO "
    Riverbed Technology
	  680 Folsom St
    San Francisco, CA 94107

	+1-415-247-7381
    email:  support@riverbed.com
    "
    DESCRIPTION "Riverbed SteelCentral Product"

    REVISION	"201604300000Z"
    DESCRIPTION	"Initial development"

    ::= { rbtTrap 1 }

steelcentralTraps OBJECT IDENTIFIER ::= { steelcentralTrapModule 1 }
steelcentralTrapInfo OBJECT IDENTIFIER ::= { steelcentralTrapModule 2 }

--- Alert object definition

alertSeverity OBJECT-TYPE
    SYNTAX      INTEGER (0..100)
    MAX-ACCESS  accessible-for-notify
    STATUS      current
    DESCRIPTION "Severity of the alert"
    ::= { steelcentralTrapInfo 1 }

alertSeverityLevel OBJECT-TYPE
    SYNTAX      INTEGER { minor(1), major(2), critical(3) }
    MAX-ACCESS  accessible-for-notify
    STATUS      current
    DESCRIPTION "Severity Level from 1 to 3: 1 is Minor, 2 is Major, 3 is Critical"
    ::= { steelcentralTrapInfo 2 }

alertPolicyName OBJECT-TYPE
    SYNTAX      OCTET STRING
    MAX-ACCESS  accessible-for-notify
    STATUS      current
    DESCRIPTION "Name of the policy generating the alert"
    ::= { steelcentralTrapInfo 3 }

alertPolicyDescription OBJECT-TYPE
    SYNTAX      OCTET STRING
    MAX-ACCESS  accessible-for-notify
    STATUS      current
    DESCRIPTION "Description of the policy generating the alert"
    ::= { steelcentralTrapInfo 4 }

alertPolicyID OBJECT-TYPE
    SYNTAX      INTEGER
    MAX-ACCESS  accessible-for-notify
    STATUS      current
    DESCRIPTION "Appliance Policy identifier for the policy generating the alert"
    ::= {steelcentralTrapInfo 5 }

alertPolicyType OBJECT-TYPE
    SYNTAX      INTEGER { traffic(1), storage(2), watch(3), pcap(4), autobaseline(5) }
    MAX-ACCESS  accessible-for-notify
    STATUS      current
    DESCRIPTION "Type of the policy generating the alert"
    ::= { steelcentralTrapInfo 6 }

alertPolicyEvalPeriod OBJECT-TYPE
    SYNTAX      INTEGER
    MAX-ACCESS  accessible-for-notify
    STATUS      current
    DESCRIPTION "Evaluation period (in seconds) of the policy generating the alert"
    ::= { steelcentralTrapInfo 7 }

alertID OBJECT-TYPE
    SYNTAX      INTEGER
    MAX-ACCESS  accessible-for-notify
    STATUS      current
    DESCRIPTION "Appliance ID number for the alert"
    ::= { steelcentralTrapInfo 8 }

alertStart OBJECT-TYPE
    SYNTAX      OCTET STRING
    MAX-ACCESS  accessible-for-notify
    STATUS      current
    DESCRIPTION "Time alert started, in epoch time"
    ::= { steelcentralTrapInfo 9 }

alertURL OBJECT-TYPE
    SYNTAX      OCTET STRING
    MAX-ACCESS  accessible-for-notify
    STATUS      current
    DESCRIPTION "URL to access the alert report on the device"
    ::= { steelcentralTrapInfo 10 }

alertInfoURL OBJECT-TYPE
    SYNTAX      OCTET STRING
    MAX-ACCESS  accessible-for-notify
    STATUS      current
    DESCRIPTION "URL to access related information"
    ::= { steelcentralTrapInfo 11 }

alertMessage OBJECT-TYPE
    SYNTAX      OCTET STRING
    MAX-ACCESS  accessible-for-notify
    STATUS      current
    DESCRIPTION "Description of the problem"
    ::= { steelcentralTrapInfo 12 }

-- Traps

testTrap NOTIFICATION-TYPE
    STATUS      current
    DESCRIPTION "SteelCentral test trap"
    ::= { steelcentralTraps 1 }

policyTrap NOTIFICATION-TYPE
    OBJECTS {
        alertSeverity,
        alertSeverityLevel,
        alertPolicyName,
        alertPolicyDescription,
        alertPolicyID,
        alertPolicyType,
        alertPolicyEvalPeriod,
        alertID,
        alertStart,
        alertURL
    }
    STATUS      current
    DESCRIPTION "Traffic violated policy thresholds"
    ::= { steelcentralTraps 2 }

hardwareTrap NOTIFICATION-TYPE
    OBJECTS {
        alertSeverity,
        alertSeverityLevel,
        alertPolicyName,
        alertPolicyDescription,
        alertPolicyID,
        alertPolicyType,
        alertPolicyEvalPeriod,
        alertID,
        alertStart,
        alertURL,
        alertInfoURL,
        alertMessage
    }
    STATUS      current
    DESCRIPTION "Hardware problem detected"
    ::= { steelcentralTraps 3 }

END
