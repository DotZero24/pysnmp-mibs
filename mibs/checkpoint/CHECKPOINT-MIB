CHECKPOINT-MIB DEFINITIONS ::= BEGIN

	  -- SUBTREE: 1.3.6.1.4.1.2620.1
	  -- iso.org.dod.internet.private.enterprises.checkpoint.products

          IMPORTS
                  MODULE-IDENTITY, OBJECT-TYPE, Integer32, Unsigned32, IpAddress, Counter32, Counter64, Gauge32, enterprises
                      	FROM SNMPv2-SMI
				  MODULE-COMPLIANCE, OBJECT-GROUP
                      	FROM SNMPv2-CONF
                  DisplayString
                  		FROM SNMPv2-TC;

    checkpoint MODULE-IDENTITY
		LAST-UPDATED "202101310000Z"
		ORGANIZATION "Check Point"
		CONTACT-INFO "Check Point"
		DESCRIPTION "Check Point MIB
					 See the most common OIDs, with detailed descriptions, in the SNMP Best Practices Guide - sk98552
					(https://supportcenter.checkpoint.com/supportcenter/portal?eventSubmit_doGoviewsolutiondetails=&solutionid=sk98552)"
		REVISION    "202101310000Z"  -- January 31, 2021
        DESCRIPTION "Fix MIB errors and warnings based on RFC"
		REVISION "201312261309Z"
		DESCRIPTION "Update the SMIv1 MIB to SMIv2"
		::= { enterprises 2620 }


--	checkpoint				OBJECT IDENTIFIER ::= { enterprises 2620 }
	products				OBJECT IDENTIFIER ::= { checkpoint 1 }
	tables					OBJECT IDENTIFIER ::= { checkpoint 500 }
	fw						OBJECT IDENTIFIER ::= { products 1 }
	vpn						OBJECT IDENTIFIER ::= { products 2 }
	fg						OBJECT IDENTIFIER ::= { products 3 }
	ha						OBJECT IDENTIFIER ::= { products 5 }
	svn						OBJECT IDENTIFIER ::= { products 6 }
	mngmt					OBJECT IDENTIFIER ::= { products 7 }
	wam						OBJECT IDENTIFIER ::= { products 8 }
	dtps					OBJECT IDENTIFIER ::= { products 9 }
	ls						OBJECT IDENTIFIER ::= { products 11 }
	vsx						OBJECT IDENTIFIER ::= { products 16 }
	smartDefense			OBJECT IDENTIFIER ::= { products 17 }
	gx						OBJECT IDENTIFIER ::= { products 20 }
	avi 					OBJECT IDENTIFIER ::= { products 24 }
	eventiaAnalyzer			OBJECT IDENTIFIER ::= { products 25 }
	uf						OBJECT IDENTIFIER ::= { products 29 }
	ms						OBJECT IDENTIFIER ::= { products 30 }
	voip					OBJECT IDENTIFIER ::= { products 31 }
	identityAwareness		OBJECT IDENTIFIER ::= { products 38 }
	applicationControl		OBJECT IDENTIFIER ::= { products 39 }
	thresholds				OBJECT IDENTIFIER ::= { products 42 }
	advancedUrlFiltering	OBJECT IDENTIFIER ::= { products 43 }
	dlp						OBJECT IDENTIFIER ::= { products 44 }
	amw						OBJECT IDENTIFIER ::= { products 46 }
	asg						OBJECT IDENTIFIER ::= { products 48 }
	te						OBJECT IDENTIFIER ::= { products 49 }
	threatExtraction		OBJECT IDENTIFIER ::= { products 50 }
	sxl						OBJECT IDENTIFIER ::= { products 36 }
	vsecController			OBJECT IDENTIFIER ::= { products 52 }
	ips						OBJECT IDENTIFIER ::= { products 53 }
	httpsInspection			OBJECT IDENTIFIER ::= { products 54 }
	mho						OBJECT IDENTIFIER ::= { products 55 }

	-- conformance information
	chkpntMIBConformance  OBJECT IDENTIFIER ::= { checkpoint 2 }

	chkpntMIBCompliances  OBJECT IDENTIFIER ::= { chkpntMIBConformance 1 }
	chkpntMIBGroups  OBJECT IDENTIFIER ::= { chkpntMIBConformance 2 }

	-- compliance statements

	chkpntBasicCompliance MODULE-COMPLIANCE
		STATUS  current
		DESCRIPTION
				"The compliance statement for Check Point entities which implement the chkpnt MIB."
		MODULE  -- this module
			GROUP   fwProductsGroup
			DESCRIPTION
				"This group is for Check Point entities which support FW statistics"

			GROUP   vpnProductsGroup
			DESCRIPTION
				"This group is for Check Point entities which support VPN statistics"

			GROUP   fgProductsGroup
			DESCRIPTION
				"This group is for Check Point entities which support FG statistics"

			GROUP   haProductsGroup
			DESCRIPTION
				"This group is for Check Point entities which support HA statistics"

			GROUP   svnProductsGroup
			DESCRIPTION
				"This group is for Check Point entities which support SVN statistics"

			GROUP   mngmtProductsGroup
			DESCRIPTION
				"This group is for Check Point entities which support MNGMT statistics"

			GROUP   wamProductsGroup
			DESCRIPTION
				"This group is for Check Point entities which support WAM statistics"

			GROUP   dtpsProductsGroup
			DESCRIPTION
				"This group is for Check Point entities which support DTPS statistics"

			GROUP   lsProductsGroup
			DESCRIPTION
				"This group is for Check Point entities which support LS statistics"

			GROUP   vsxProductsGroup
			DESCRIPTION
				"This group is for Check Point entities which support VSX statistics"

			GROUP   smartDefenseProductsGroup
			DESCRIPTION
				"This group is for Check Point entities which support SmartDefense statistics"

			GROUP   gxProductsGroup
			DESCRIPTION
				"This group is for Check Point entities which support GX statistics"

			GROUP   aviProductsGroup
			DESCRIPTION
				"This group is for Check Point entities which support AVI statistics"

			GROUP   eventiaAnalyzerProductsGroup
			DESCRIPTION
				"This group is for Check Point entities which support Eventia Analyzer statistics"

			GROUP   ufProductsGroup
			DESCRIPTION
				"This group is for Check Point entities which support UF statistics"

			GROUP   msProductsGroup
			DESCRIPTION
				"This group is for Check Point entities which support MS statistics"

			GROUP   voipProductsGroup
			DESCRIPTION
				"This group is for Check Point entities which support VOIP statistics"

			GROUP   identityAwarenessProductsGroup
			DESCRIPTION
				"This group is for Check Point entities which support IDA statistics"

			GROUP   applicationControlProductsGroup
			DESCRIPTION
				"This group is for Check Point entities which support APPI statistics"

			GROUP   thresholdsProductsGroup
			DESCRIPTION
				"This group is for Check Point entities which support Thresholds statistics"

			GROUP   advancedUrlFilteringProductsGroup
			DESCRIPTION
				"This group is for Check Point entities which support Advanced URLF statistics"

			GROUP   dlpProductsGroup
			DESCRIPTION
				"This group is for Check Point entities which support DLP statistics"

			GROUP   amwProductsGroup
			DESCRIPTION
				"This group is for Check Point entities which support AMW statistics"

			GROUP   asgProductsGroup
			DESCRIPTION
				"This group is for Check Point entities which support ASG statistics"

			GROUP   teProductsGroup
			DESCRIPTION
				"This group is for Check Point entities which support TE statistics"

			GROUP   threatExtractionProductsGroup
			DESCRIPTION
				"This group is for Check Point entities which support TEX statistics"

			GROUP   sxlProductsGroup
			DESCRIPTION
				"This group is for Check Point entities which support SXL statistics"

			GROUP   vsecControllerProductsGroup
			DESCRIPTION
				"This group is for Check Point entities which support VSec Controller statistics"

			GROUP   ipsProductsGroup
			DESCRIPTION
				"This group is for Check Point entities which support IPS statistics"

			GROUP   httpsInspectionProductsGroup
			DESCRIPTION
				"This group is for Check Point entities which support HTTPS Inspection statistics"

			GROUP   mhoProductsGroup
			DESCRIPTION
				"This group is for Check Point entities which support Maestro Hyperscale Orchestrator"

		::= { chkpntMIBCompliances 1 }

	-- units of conformance

	fwProductsGroup OBJECT-GROUP
		OBJECTS { fwPolicyName, fwInstallTime, fwNumConn, fwPeakNumConn, fwIspName, fwIspStatus, fwIspRole, unknown, fwIfName, fwAcceptPcktsIn, fwAcceptPcktsOut, fwAcceptBytesIn, fwAcceptBytesOut, fwDropPcktsIn, fwDropPcktsOut, fwRejectPcktsIn, fwRejectPcktsOut, fwLogIn, fwLogOut, fwConnTableLimit, fwAcceptedTotal, fwDroppedTotal, fwRejectedTotal, fwLoggedTotal, fwAcceptedBytesTotal, fwDroppedBytesTotal, fwRejectedBytesTotal, fwAcceptedBytesRates, fwAcceptedPcktsRates, fwConnsRate, fwIfName64, fwAcceptPcktsIn64, fwAcceptPcktsOut64, fwAcceptBytesIn64, fwAcceptBytesOut64, fwDropPcktsIn64, fwDropPcktsOut64, fwRejectPcktsIn64, fwRejectPcktsOut64, fwLogIn64, fwLogOut64, fwFullyUtilizedDrops, fwHmem-block-size, fwHmem-requested-bytes, fwHmem-initial-allocated-bytes, fwHmem-initial-allocated-blocks, fwHmem-initial-allocated-pools, fwHmem-current-allocated-bytes, fwHmem-current-allocated-blocks, fwHmem-current-allocated-pools, fwHmem-maximum-bytes, fwHmem-maximum-pools, fwHmem-bytes-used, fwHmem-blocks-used, fwHmem-bytes-unused, fwHmem-blocks-unused, fwHmem-bytes-peak, fwHmem-blocks-peak, fwHmem-bytes-internal-use, fwHmem-number-of-items, fwHmem-alloc-operations, fwHmem-free-operations, fwHmem-failed-alloc, fwHmem-failed-free, fwKmem-system-physical-mem, fwKmem-available-physical-mem, fwKmem-aix-heap-size, fwKmem-bytes-used, fwKmem-blocking-bytes-used, fwKmem-non-blocking-bytes-used, fwKmem-bytes-unused, fwKmem-bytes-peak, fwKmem-blocking-bytes-peak, fwKmem-non-blocking-bytes-peak, fwKmem-bytes-internal-use, fwKmem-number-of-items, fwKmem-alloc-operations, fwKmem-free-operations, fwKmem-failed-alloc, fwKmem-failed-free, fwInspect-packets, fwInspect-operations, fwInspect-lookups, fwInspect-record, fwInspect-extract, fwCookies-total, fwCookies-allocfwCookies-total, fwCookies-freefwCookies-total, fwCookies-dupfwCookies-total, fwCookies-getfwCookies-total, fwCookies-putfwCookies-total, fwCookies-lenfwCookies-total, fwChains-alloc, fwChains-free, fwFrag-fragments, fwFrag-expired, fwFrag-packets, fwUfpHitRatio, fwUfpInspected, fwUfpHits, fwSS-http-pid, fwSS-http-proto, fwSS-http-port, fwSS-http-logical-port, fwSS-http-max-avail-socket, fwSS-http-socket-in-use-max, fwSS-http-socket-in-use-curr, fwSS-http-socket-in-use-count, fwSS-http-sess-max, fwSS-http-sess-curr, fwSS-http-sess-count, fwSS-http-auth-sess-max, fwSS-http-auth-sess-curr, fwSS-http-auth-sess-count, fwSS-http-accepted-sess, fwSS-http-rejected-sess, fwSS-http-auth-failures, fwSS-http-ops-cvp-sess-max, fwSS-http-ops-cvp-sess-curr, fwSS-http-ops-cvp-sess-count, fwSS-http-ops-cvp-rej-sess, fwSS-http-ssl-encryp-sess-max, fwSS-http-ssl-encryp-sess-curr, fwSS-http-ssl-encryp-sess-count, fwSS-http-transp-sess-max, fwSS-http-transp-sess-curr, fwSS-http-transp-sess-count, fwSS-http-proxied-sess-max, fwSS-http-proxied-sess-curr, fwSS-http-proxied-sess-count, fwSS-http-tunneled-sess-max, fwSS-http-tunneled-sess-curr, fwSS-http-tunneled-sess-count, fwSS-http-ftp-sess-max, fwSS-http-ftp-sess-curr, fwSS-http-ftp-sess-count, fwSS-http-time-stamp, fwSS-http-is-alive, fwSS-http-blocked-cnt, fwSS-http-blocked-total, fwSS-http-scanned-total, fwSS-http-blocked-by-file-type, fwSS-http-blocked-by-size-limit, fwSS-http-blocked-by-archive-limit, fwSS-http-blocked-by-internal-error, fwSS-http-passed-cnt, fwSS-http-passed-by-file-type, fwSS-http-passed-by-size-limit, fwSS-http-passed-by-archive-limit, fwSS-http-passed-by-internal-error, fwSS-http-passed-total, fwSS-http-blocked-by-AV-settings, fwSS-http-passed-by-AV-settings, fwSS-http-blocked-by-URL-filter-category, fwSS-http-blocked-by-URL-block-list, fwSS-http-passed-by-URL-allow-list, fwSS-http-passed-by-URL-filter-category, fwSS-ftp-pid, fwSS-ftp-proto, fwSS-ftp-port, fwSS-ftp-logical-port, fwSS-ftp-max-avail-socket, fwSS-ftp-socket-in-use-max, fwSS-ftp-socket-in-use-curr, fwSS-ftp-socket-in-use-count, fwSS-ftp-sess-max, fwSS-ftp-sess-curr, fwSS-ftp-sess-count, fwSS-ftp-auth-sess-max, fwSS-ftp-auth-sess-curr, fwSS-ftp-auth-sess-count, fwSS-ftp-accepted-sess, fwSS-ftp-rejected-sess, fwSS-ftp-auth-failures, fwSS-ftp-ops-cvp-sess-max, fwSS-ftp-ops-cvp-sess-curr, fwSS-ftp-ops-cvp-sess-count, fwSS-ftp-ops-cvp-rej-sess, fwSS-ftp-time-stamp, fwSS-ftp-is-alive, fwSS-ftp-blocked-cnt, fwSS-ftp-blocked-total, fwSS-ftp-scanned-total, fwSS-ftp-blocked-by-file-type, fwSS-ftp-blocked-by-size-limit, fwSS-ftp-blocked-by-archive-limit, fwSS-ftp-blocked-by-internal-error, fwSS-ftp-passed-cnt, fwSS-ftp-passed-by-file-type, fwSS-ftp-passed-by-size-limit, fwSS-ftp-passed-by-archive-limit, fwSS-ftp-passed-by-internal-error, fwSS-ftp-passed-total, fwSS-ftp-blocked-by-AV-settings, fwSS-ftp-passed-by-AV-settings, fwSS-telnet-pid, fwSS-telnet-proto, fwSS-telnet-port, fwSS-telnet-logical-port, fwSS-telnet-max-avail-socket, fwSS-telnet-socket-in-use-max, fwSS-telnet-socket-in-use-curr, fwSS-telnet-socket-in-use-count, fwSS-telnet-sess-max, fwSS-telnet-sess-curr, fwSS-telnet-sess-count, fwSS-telnet-auth-sess-max, fwSS-telnet-auth-sess-curr, fwSS-telnet-auth-sess-count, fwSS-telnet-accepted-sess, fwSS-telnet-rejected-sess, fwSS-telnet-auth-failures, fwSS-telnet-time-stamp, fwSS-telnet-is-alive, fwSS-rlogin-pid, fwSS-rlogin-proto, fwSS-rlogin-port, fwSS-rlogin-logical-port, fwSS-rlogin-max-avail-socket, fwSS-rlogin-socket-in-use-max, fwSS-rlogin-socket-in-use-curr, fwSS-rlogin-socket-in-use-count, fwSS-rlogin-sess-max, fwSS-rlogin-sess-curr, fwSS-rlogin-sess-count, fwSS-rlogin-auth-sess-max, fwSS-rlogin-auth-sess-curr, fwSS-rlogin-auth-sess-count, fwSS-rlogin-accepted-sess, fwSS-rlogin-rejected-sess, fwSS-rlogin-auth-failures, fwSS-rlogin-time-stamp, fwSS-rlogin-is-alive, fwSS-ufp-ops-ufp-sess-max, fwSS-ufp-ops-ufp-sess-curr, fwSS-ufp-ops-ufp-sess-count, fwSS-ufp-ops-ufp-rej-sess, fwSS-ufp-time-stamp, fwSS-ufp-is-alive, fwSS-smtp-pid, fwSS-smtp-proto, fwSS-smtp-port, fwSS-smtp-logical-port, fwSS-smtp-max-avail-socket, fwSS-smtp-socket-in-use-max, fwSS-smtp-socket-in-use-curr, fwSS-smtp-socket-in-use-count, fwSS-smtp-sess-max, fwSS-smtp-sess-curr, fwSS-smtp-sess-count, fwSS-smtp-auth-sess-max, fwSS-smtp-auth-sess-curr, fwSS-smtp-auth-sess-count, fwSS-smtp-accepted-sess, fwSS-smtp-rejected-sess, fwSS-smtp-auth-failures, fwSS-smtp-mail-max, fwSS-smtp-mail-curr, fwSS-smtp-mail-count, fwSS-smtp-outgoing-mail-max, fwSS-smtp-outgoing-mail-curr, fwSS-smtp-outgoing-mail-count, fwSS-smtp-max-mail-on-conn, fwSS-smtp-total-mails, fwSS-smtp-time-stamp, fwSS-smtp-is-alive, fwSS-smtp-blocked-cnt, fwSS-smtp-blocked-total, fwSS-smtp-scanned-total, fwSS-smtp-blocked-by-file-type, fwSS-smtp-blocked-by-size-limit, fwSS-smtp-blocked-by-archive-limit, fwSS-smtp-blocked-by-internal-error, fwSS-smtp-passed-cnt, fwSS-smtp-passed-by-file-type, fwSS-smtp-passed-by-size-limit, fwSS-smtp-passed-by-archive-limit, fwSS-smtp-passed-by-internal-error, fwSS-smtp-passed-total, fwSS-smtp-blocked-by-AV-settings, fwSS-smtp-passed-by-AV-settings, fwSS-POP3-pid, fwSS-POP3-proto, fwSS-POP3-port, fwSS-POP3-logical-port, fwSS-POP3-max-avail-socket, fwSS-POP3-socket-in-use-max, fwSS-POP3-socket-in-use-curr, fwSS-POP3-socket-in-use-count, fwSS-POP3-sess-max, fwSS-POP3-sess-curr, fwSS-POP3-sess-count, fwSS-POP3-auth-sess-max, fwSS-POP3-auth-sess-curr, fwSS-POP3-auth-sess-count, fwSS-POP3-accepted-sess, fwSS-POP3-rejected-sess, fwSS-POP3-auth-failures, fwSS-POP3-mail-max, fwSS-POP3-mail-curr, fwSS-POP3-mail-count, fwSS-POP3-outgoing-mail-max, fwSS-POP3-outgoing-mail-curr, fwSS-POP3-outgoing-mail-count, fwSS-POP3-max-mail-on-conn, fwSS-POP3-total-mails, fwSS-POP3-time-stamp, fwSS-POP3-is-alive, fwSS-POP3-blocked-cnt, fwSS-POP3-blocked-total, fwSS-POP3-scanned-total, fwSS-POP3-blocked-by-file-type, fwSS-POP3-blocked-by-size-limit, fwSS-POP3-blocked-by-archive-limit, fwSS-POP3-blocked-by-internal-error, fwSS-POP3-passed-cnt, fwSS-POP3-passed-by-file-type, fwSS-POP3-passed-by-size-limit, fwSS-POP3-passed-by-archive-limit, fwSS-POP3-passed-by-internal-error, fwSS-POP3-passed-total, fwSS-POP3-blocked-by-AV-settings, fwSS-POP3-passed-by-AV-settings, fwSS-total-blocked-by-av, fwSS-total-blocked, fwSS-total-scanned, fwSS-total-blocked-by-file-type, fwSS-total-blocked-by-size-limit, fwSS-total-blocked-by-archive-limit, fwSS-total-blocked-by-interal-error, fwSS-total-passed-by-av, fwSS-total-passed-by-file-type, fwSS-total-passed-by-size-limit, fwSS-total-passed-by-archive-limit, fwSS-total-passed-by-interal-error, fwSS-total-passed, fwSS-total-blocked-by-av-settings, fwSS-total-passed-by-av-settings, fwConnectionsStatConnectionsTcp, fwConnectionsStatConnectionsUdp, fwConnectionsStatConnectionsIcmp, fwConnectionsStatConnectionsOther, fwConnectionsStatConnections, fwConnectionsStatConnectionRate, fwHmem64-block-size, fwHmem64-requested-bytes, fwHmem64-initial-allocated-bytes, fwHmem64-initial-allocated-blocks, fwHmem64-initial-allocated-pools, fwHmem64-current-allocated-bytes, fwHmem64-current-allocated-blocks, fwHmem64-current-allocated-pools, fwHmem64-maximum-bytes, fwHmem64-maximum-pools, fwHmem64-bytes-used, fwHmem64-blocks-used, fwHmem64-bytes-unused, fwHmem64-blocks-unused, fwHmem64-bytes-peak, fwHmem64-blocks-peak, fwHmem64-bytes-internal-use, fwHmem64-number-of-items, fwHmem64-alloc-operations, fwHmem64-free-operations, fwHmem64-failed-alloc, fwHmem64-failed-free, fwModuleState, fwFilterName, fwFilterDate, fwAccepted, fwRejected, fwDropped, fwLogged, fwMajor, fwMinor, fwProduct, fwSICTrustState, fwProdName, fwVerMajor, fwVerMinor, fwKernelBuild, fwNetIfName, fwNetIfIPAddr, fwNetIfNetmask, fwNetIfFlags, fwNetIfPeerName, fwNetIfRemoteIp, fwNetIfTopology, fwNetIfProxyName, fwNetIfSlaves, fwNetIfPorts, fwNetIfIPV6Addr, fwNetIfIPV6AddrLen, fwLSConnOverall, fwLSConnOverallDesc, fwLSConnName, fwLSConnState, fwLSConnStateDesc, fwLSConnSendRate, fwLocalLoggingDesc, fwLocalLoggingStat, fwLocalLoggingWriteRate, fwLoggingHandlingRate, fwInstancesCPUInstanceName, fwInstancesCPUUsage, fwInstancesCPUTotal }
		STATUS  current
		DESCRIPTION
				"A collection of managed objects that provide information about FW objects"
		::= { chkpntMIBGroups 1 }

	vpnProductsGroup OBJECT-GROUP
		OBJECTS { cpvEncPackets, cpvDecPackets, cpvErrOut, cpvErrIn, cpvErrIke, cpvErrPolicy, cpvCurrEspSAsIn, cpvTotalEspSAsIn, cpvCurrEspSAsOut, cpvTotalEspSAsOut, cpvCurrAhSAsIn, cpvTotalAhSAsIn, cpvCurrAhSAsOut, cpvTotalAhSAsOut, cpvMaxConncurEspSAsIn, cpvMaxConncurEspSAsOut, cpvMaxConncurAhSAsIn, cpvMaxConncurAhSAsOut, cpvSaDecrErr, cpvSaAuthErr, cpvSaReplayErr, cpvSaPolicyErr, cpvSaOtherErrIn, cpvSaOtherErrOut, cpvSaUnknownSpiErr, cpvIpsecUdpEspEncPkts, cpvIpsecUdpEspDecPkts, cpvIpsecAhEncPkts, cpvIpsecAhDecPkts, cpvIpsecEspEncPkts, cpvIpsecEspDecPkts, cpvIpsecDecomprBytesBefore, cpvIpsecDecomprBytesAfter, cpvIpsecDecomprOverhead, cpvIpsecDecomprPkts, cpvIpsecDecomprErr, cpvIpsecComprBytesBefore, cpvIpsecComprBytesAfter, cpvIpsecComprOverhead, cpvIpsecNonCompressibleBytes, cpvIpsecCompressiblePkts, cpvIpsecNonCompressiblePkts, cpvIpsecComprErrors, cpvIpsecEspEncBytes, cpvIpsecEspDecBytes, cpvFwzEncapsEncPkts, cpvFwzEncapsDecPkts, cpvFwzEncPkts, cpvFwzDecPkts, cpvFwzEncapsEncErrs, cpvFwzEncapsDecErrs, cpvFwzEncErrs, cpvFwzDecErrs, cpvHwAccelVendor, cpvHwAccelStatus, cpvHwAccelDriverMajorVer, cpvHwAccelDriverMinorVer, cpvHwAccelEspEncPkts, cpvHwAccelEspDecPkts, cpvHwAccelEspEncBytes, cpvHwAccelEspDecBytes, cpvHwAccelAhEncPkts, cpvHwAccelAhDecPkts, cpvHwAccelAhEncBytes, cpvHwAccelAhDecBytes, cpvIKECurrSAs, cpvIKECurrInitSAs, cpvIKECurrRespSAs, cpvIKETotalSAs, cpvIKETotalInitSAs, cpvIKETotalRespSAs, cpvIKETotalSAsAttempts, cpvIKETotalSAsInitAttempts, cpvIKETotalSAsRespAttempts, cpvIKEMaxConncurSAs, cpvIKEMaxConncurInitSAs, cpvIKEMaxConncurRespSAs, cpvIKETotalFailuresInit, cpvIKENoResp, cpvIKETotalFailuresResp, cpvIPsecNICsNum, cpvIPsecNICTotalDownLoadedSAs, cpvIPsecNICCurrDownLoadedSAs, cpvIPsecNICDecrBytes, cpvIPsecNICEncrBytes, cpvIPsecNICDecrPackets, cpvIPsecNICEncrPackets, cpvProdName, cpvVerMajor, cpvVerMinor }
		STATUS  current
		DESCRIPTION
				"A collection of managed objects that provide information about VPN objects"
		::= { chkpntMIBGroups 2 }

	fgProductsGroup OBJECT-GROUP
		OBJECTS { fgProdName, fgVerMajor, fgVerMinor, fgVersionString, fgModuleKernelBuild, fgStrPolicyName, fgInstallTime, fgNumInterfaces, fgIfName, fgPolicyName, fgRateLimitIn, fgRateLimitOut, fgAvrRateIn, fgAvrRateOut, fgRetransPcktsIn, fgRetransPcktsOut, fgPendPcktsIn, fgPendPcktsOut, fgPendBytesIn, fgPendBytesOut, fgNumConnIn, fgNumConnOut }
		STATUS  current
		DESCRIPTION
				"A collection of managed objects that provide information about FG objects"
		::= { chkpntMIBGroups 3 }

	haProductsGroup OBJECT-GROUP
		OBJECTS { haProdName, haInstalled, haVerMajor, haVerMinor, haStarted, haState, haBlockState, haIdentifier, haProtoVersion, haWorkMode, haVersionSting, haClusterXLFailover, haStatCode, haStatShort, haStatLong, haServicePack, haIfName, haIP, haStatus, haVerified, haTrusted, haShared, haProblemIndex, haProblemName, haProblemStatus, haProblemPriority, haProblemVerified, haProblemDescr, haClusterIpIfName, haClusterIpAddr, haClusterIpNetMask, haClusterIpMemberNet, haClusterIpMemberNetMask, haClusterSyncName, haClusterSyncAddr, haClusterSyncNetMask }
		STATUS  current
		DESCRIPTION
				"A collection of managed objects that provide information about HA objects"
		::= { chkpntMIBGroups 4 }

	svnProductsGroup OBJECT-GROUP
		OBJECTS { svnVersion, svnBuild, osName, osMajorVer, osMinorVer, osBuildNum, osSPmajor, osSPminor, osVersionLevel, memTotalVirtual, memActiveVirtual, memTotalReal, memActiveReal, memFreeReal, memSwapsSec, memDiskTransfers, procUsrTime, procSysTime, procIdleTime, procUsage, procQueue, procInterrupts, procNum, diskTime, diskQueue, diskPercent, diskFreeTotal, diskFreeAvail, diskTotal, memTotalVirtual64, memActiveVirtual64, memTotalReal64, memActiveReal64, memFreeReal64, memSwapsSec64, memDiskTransfers64, multiProcUserTime, multiProcSystemTime, multiProcIdleTime, multiProcUsage, multiProcRunQueue, multiProcInterrupts, multiDiskName, multiDiskSize, multiDiskUsed, multiDiskFreeTotalBytes, multiDiskFreeTotalPercent, multiDiskFreeAvailableBytes, multiDiskFreeAvailablePercent, raidVolumeID, raidVolumeType, numOfDisksOnRaid, raidVolumeMaxLBA, raidVolumeState, raidVolumeFlags, raidVolumeSize, raidDiskVolumeID, raidDiskID, raidDiskNumber, raidDiskVendor, raidDiskProductID, raidDiskRevision, raidDiskMaxLBA, raidDiskState, raidDiskFlags, raidDiskSyncState, raidDiskSize, tempertureSensorName, tempertureSensorValue, tempertureSensorUnit, tempertureSensorType, tempertureSensorStatus, fanSpeedSensorName, fanSpeedSensorValue, fanSpeedSensorUnit, fanSpeedSensorType, fanSpeedSensorStatus, voltageSensorName, voltageSensorValue, voltageSensorUnit, voltageSensorType, voltageSensorStatus, powerSupplyStatus, svnApplianceSerialNumber, svnApplianceManufacturer, svnApplianceProductName, svnApplianceSeriesString, svnRouteModDest, svnRouteModMask, svnRouteModIfIndex, svnRouteModGateway, svnRouteModIfName, svnRouteModAction, svnLogDStat, svnUpdatesInfoBuild, svnUpdatesInfoStatus, svnUpdatesInfoConnection, svnUpdatesInfoAvailablePackages, svnUpdatesInfoAvailableRecommended, svnUpdatesInfoAvailableHotfixes, updatesInstalledName, updatesInstalledType, updatesRecommendedName, updatesRecommendedType, updatesRecommendedStatus, vdName, vdType, ctxId, svnProdName, svnProdVerMajor, svnProdVerMinor, routingDest, routingMask, routingGatweway, routingIntrfName, svnSysTime, svnUTCTimeOffset, svnSysStartTime, svnSysUniqId, svnWebUIPort, checkPointUTM-1450, checkPointUTM-11050, checkPointUTM-12050, checkPointUTM-1130, checkPointUTM-1270, checkPointUTM-1570, checkPointUTM-11070, checkPointUTM-12070, checkPointUTM-13070, checkPointPower-15070, checkPointPower-19070, checkPointPower-111000, checkPointSmart-15, checkPointSmart-125, checkPointSmart-150, checkPointSmart-1150, checkPointIP150, checkPointIP280, checkPointIP290, checkPointIP390, checkPointIP560, checkPointIP690, checkPointIP1280, checkPointIP2450, checkPointUNIVERGEUnifiedWall1000, checkPointUNIVERGEUnifiedWall2000, checkPointUNIVERGEUnifiedWall4000, checkPointUNIVERGEUnifiedWall100, checkPointDLP-19571, checkPointDLP-12571, checkPointIPS-12076, checkPointIPS-15076, checkPointIPS-19076, checkPoint2200, checkPoint4200, checkPoint4400, checkPoint4600, checkPoint4800, checkPointTE250, checkPoint12200, checkPoint12400, checkPoint12600, checkPointTE1000, checkPoint13500, checkPoint21400, checkPoint21600, checkPoint21700, checkPointVMware, checkPointOpenServer, checkPointSmart-1205, checkPointSmart-1210, checkPointSmart-1225, checkPointSmart-13050, checkPointSmart-13150, checkPoint13800, checkPoint21800, checkPointTE250X, checkPointTE1000X, checkPointTE2000X, checkPointTE100X, checkPoint23500, checkPoint23800, checkPoint15400, checkPoint15600, checkPoint3200, checkPoint5200, checkPoint5400, checkPoint5600, checkPoint5800, checkPoint5900, checkPoint3100, checkPoint5100, checkPointSmart-1405, checkPointSmart-1410, checkPointSmart-5050, checkPointSmart-525, checkPointSmart-5150, checkPoint23900, checkPoint6500, checkPoint6800, checkPoint16000T, checkPoint26000, checkPointSmart-625, checkPoint16000, checkPoint26000T, checkPoint61000, checkPoint64000, checkPoint41000, checkPoint44000, checkPoint3600, checkPoint3600T, checkPoint6200B, checkPoint6200P, checkPoint6200T, checkPoint6600, checkPoint6900, checkPoint16600HS, checkPoint28600HS, checkPoint6700, checkPoint7000, checkPoint16200, checkPoint28000, checkPoint6400, checkPoint3800, checkPointMHO140, checkPointMHO170, checkPointMHO175, licensingID, licensingBladeGUIOrder, licensingBladeName, licensingState, licensingExpirationDate, licensingImpact, licensingBladeActive, licensingTotalQuota, licensingUsedQuota, licensingAssetAccountId, licensingAssetPackageDescription, licensingAssetContainerCK, licensingAssetCKSignature, licensingAssetContainerSKU, licensingAssetSupportLevel, licensingAssetSupportExpiration, licensingAssetActivationStatus, svnConnectivity, svnNetIfVsid, svnNetIfName, svnNetIfAddress, svnNetIfMask, svnNetIfMTU, svnNetIfState, svnNetIfMAC, svnNetIfDescription, svnNetIfOperState, svnNetIfRXBytes, svnNetIfRXDrops, svnNetIfRXErrors, svnNetIfRXPackets, svnNetIfTXBytes, svnNetIfTXDrops, svnNetIfTXErrors, svnNetIfTXPackets, vsRoutingDest, vsRoutingMask, vsRoutingGateway, vsRoutingIntrfName, vsRoutingVsId, svnStatCode, svnStatShortDescr, svnStatLongDescr, svnServicePack , checkPointSmart-6000-L , checkPointSmart-6000-XL , checkPointSmart-600-S , checkPointSmart-600-M }
		STATUS  current
		DESCRIPTION
				"A collection of managed objects that provide information about SVN objects"
		::= { chkpntMIBGroups 5 }

	mngmtProductsGroup OBJECT-GROUP
		OBJECTS { mgProdName, mgVerMajor, mgVerMinor, mgBuildNumber, mgActiveStatus, mgFwmIsAlive, mgClientName, mgClientHost, mgClientDbLock, mgApplicationType, mgMgmtHAJournals, mgIsLicenseViolation, mgLicenseViolationMsg, mglsGWIP, mglsGWState, mglsGWLastLoginTime, mglsGWLogReceiveRate, mgStatCode, mgStatShortDescr, mgStatLongDescr }
		STATUS  current
		DESCRIPTION
				"A collection of managed objects that provide information about MNGMT objects"
		::= { chkpntMIBGroups 6 }

	wamProductsGroup OBJECT-GROUP
		OBJECTS { wamAcceptReq, wamRejectReq, wamPolicyName, wamPolicyUpdate, wamUagHost, wamUagIp, wamUagPort, wamUagNoQueries, wamUagLastQuery, wamOpenSessions, wamLastSession, wamProdName, wamVerMajor, wamVerMinor, wamState, wamName, wamStatCode, wamStatShortDescr, wamStatLongDescr }
		STATUS  current
		DESCRIPTION
				"A collection of managed objects that provide information about WAM objects"
		::= { chkpntMIBGroups 7 }

	dtpsProductsGroup OBJECT-GROUP
		OBJECTS { dtpsProdName, dtpsVerMajor, dtpsVerMinor, dtpsLicensedUsers, dtpsConnectedUsers, dtpsStatCode, dtpsStatShortDescr, dtpsStatLongDescr }
		STATUS  current
		DESCRIPTION
				"A collection of managed objects that provide information about DTPS objects"
		::= { chkpntMIBGroups 8 }

	lsProductsGroup OBJECT-GROUP
		OBJECTS { lsProdName, lsVerMajor, lsVerMinor, lsBuildNumber, lsFwmIsAlive, lsGWIP, lsGWState, lsGWLastLoginTime, lsGWLogReceiveRate, lsStatCode, lsStatShortDescr, lsStatLongDescr, lsClientName, lsClientHost, lsClientDbLock, lsApplicationType }
		STATUS  current
		DESCRIPTION
				"A collection of managed objects that provide information about LS objects"
		::= { chkpntMIBGroups 9 }

	vsxProductsGroup OBJECT-GROUP
		OBJECTS { vsxVsSupported, vsxVsConfigured, vsxVsInstalled, vsxVsidConfigured, vsxAllVSsConnsSum, vsxStatusVRId, vsxStatusVsName, vsxStatusVsType, vsxStatusMainIP, vsxStatusPolicyName, vsxStatusVsPolicyType, vsxStatusSicTrustState, vsxStatusHAState, vsxStatusVSWeight, vsxStatusMemoryUsageVSName, vsxStatusMemoryUsage, vsxStatusMemoryUsageVSMaxMem, vsxStatusInterfaceVSName, vsxStatusInterfaceIfName, vsxStatusInterfaceAdminState, vsxStatusInterfaceOperState, vsxStatusInterfaceRxBytes, vsxStatusInterfaceTxBytes, vsxStatusInterfaceOverallBytes, vsxStatusInterfaceRxErrors, vsxStatusInterfaceTxErrors, vsxCountersVSId, vsxCountersConnNum, vsxCountersConnPeakNum, vsxCountersConnTableLimit, vsxCountersPackets, vsxCountersDroppedTotal, vsxCountersAcceptedTotal, vsxCountersRejectedTotal, vsxCountersBytesAcceptedTotal, vsxCountersBytesDroppedTotal, vsxCountersBytesRejectedTotal, vsxCountersLoggedTotal, vsxCountersIsDataValid, vsxCountersDropVSID, vsxCountersDropVsName, vsxCountersDropCount, raExternalIpAddr, raOfficeMode, raIkeOverTCP, raUseUDPEncap, raVisitorMode, raRouteTraffic, raCommunity, raTunnelEncAlgorithm, raTunnelAuthMethod, raLogonTime, tunnelPeerObjName, tunnelState, tunnelCommunity, tunnelNextHop, tunnelInterface, tunnelSourceIpAddr, tunnelLinkPriority, tunnelProbState, tunnelPeerType, tunnelType, permanentTunnelPeerObjName, permanentTunnelState, permanentTunnelCommunity, permanentTunnelNextHop, permanentTunnelInterface, permanentTunnelSourceIpAddr, permanentTunnelLinkPriority, permanentTunnelProbState, permanentTunnelPeerType, vsxTunnelsVSidName, vsxS2SIpsecTunnelsCounter, vsxVSStateChangedVSIdName, vsxVSStateChangedChangeOccurred }
		STATUS  current
		DESCRIPTION
				"A collection of managed objects that provide information about VSX objects"
		::= { chkpntMIBGroups 10 }

	smartDefenseProductsGroup OBJECT-GROUP
		OBJECTS { asmSynatkSynAckTimeout, asmSynatkSynAckReset, asmSynatkModeChange, asmSynatkCurrentMode, asmSynatkNumberofunAckedSyns, smallPMTUNumberOfAttacks, smallPMTUValueOfMinimalMTUsize, sequenceVerifierInvalidAck, sequenceVerifierInvalidSequence, sequenceVerifierInvalidretransmit, numOfhostPortScan, numOfIpSweep, httpWorms, httpURLLengthViolation, httpHeaderLengthViolations, httpMaxHeaderReached, numOfHttpASCIIViolations, numOfHttpP2PHeaders, numOfCIFSworms, numOfCIFSNullSessions, numOfCIFSBlockedPopUps, numOfCIFSBlockedCommands, numOfCIFSPasswordLengthViolations, numOfP2POtherConAttempts, numOfP2PKazaaConAttempts, numOfP2PeMuleConAttempts, numOfGnutellaConAttempts, numOfP2PSkypeCon, numOfBitTorrentCon }
		STATUS  current
		DESCRIPTION
				"A collection of managed objects that provide information about SmartDefense objects"
		::= { chkpntMIBGroups 11 }

	gxProductsGroup OBJECT-GROUP
		OBJECTS { gxProdName, gxProdVersion, gxCreateSinceInstall, gxActContxt, gxDropPlicyCreate, gxDropMalformedReqCreate, gxDropMalformedRespCreate, gxExpiredCreate, gxBadCauseCreate, gxSecondaryNsapiEntries, gxActv0v1PdnConns, gxTunnelApnsEntries, gxTunnelsEntries, gxDeleteSinceInstall, gxDropOutOfContxtDelete, gxDropMalformedReqDelete, gxDropMalformedRespDelete, gxExpiredDelete, gxBadCauseDelete, gxUpdateSinceInstall, gxDropOutOfContxtUpdate, gxDropMalformedReqUpdate, gxDropMalformedRespUpdate, gxExpiredUpdate, gxBadCauseUpdate, gxEchoSinceInstall, gxVnspSinceInstall, gxDropPolicyEcho, gxDropMalformedReqEcho, gxDropMalformedRespEcho, gxExpiredEcho, gxDropVnsp, gxGtpPathEntries, gxGpdu1MinAvgRate, gxDropOutOfContxtGpdu, gxDropAnti-spoofingGpdu, gxDropMs-MsGpdu, gxDropBadSeqGpdu, gxDropBadGpdu, gxGpduExpiredTunnel, gxInitiateSinceInstall, gxDropInitiationReq, gxDropInitiationResp, gxExpiredInitiateAct, gxGTPv2CreateSessionSinceInstall, gxGTPv2CreateBearerSinceInstall, gxGTPv2ExpiredCreateSession, gxGTPv2ExpiredCreateBearer, gxGTPv2DropMalformedCreateSessionReq, gxGTPv2DropMalformedCreateSessionResp, gxGTPv2DropMalformedCreateBearerReq, gxGTPv2DropMalformedCreateBearerResp, gxGTPv2DropPolicyCreateSession, gxGTPv2DropPolicyCreateBearer, gxGTPv2ActPDN, gxGTPv2ActDataBearers, gxGTPv2DeleteSessionSinceInstall, gxGTPv2DeleteBearerSinceInstall, gxGTPv2ExpiredDeleteSession, gxGTPv2ExpiredDeleteBearer, gxGTPv2DropMalformedDeleteSessionReq, gxGTPv2DropMalformedDeleteSessionResp, gxGTPv2DropMalformedDeleteBearerReq, gxGTPv2DropMalformedDeleteBearerResp, gxGTPv2DropPolicyDeleteSession, gxGTPv2DropPolicyDeleteBearer, gxGTPv2UpdateBearerSinceInstall, gxGTPv2ExpiredUpdateBearer, gxGTPv2ModifyBearerSinceInstall, gxGTPv2ExpiredModifyBearer, gxGTPv2DropMalformedUpdateBearerReq, gxGTPv2DropMalformedUpdateBearerResp, gxGTPv2DropMalformedModifyBearerReq, gxGTPv2DropMalformedModifyBearerResp, gxGTPv2DropPolicyUpdateBearer, gxGTPv2DropPolicyModifyBearer, gxGTPv2EchoSinceInstall, gxGTPv2VnspSinceInstall, gxGTPv2ExpiredEcho, gxGTPv2DropMalformedEchoReq, gxGTPv2DropMalformedEchoResp, gxGTPv2DropPolicyEcho, gxGTPv2ModifyBearerCmdSinceInstall, gxGTPv2ModifyBearerFailIndSinceInstall, gxGTPv2DeleteBearerCmdSinceInstall, gxGTPv2DeleteBearerFailIndSinceInstall, gxGTPv2BearerResourceCmdSinceInstall, gxGTPv2BearerResourceFailIndSinceInstall, gxProdVerMajor, gxProdVerMinor, gxBuild }
		STATUS  current
		DESCRIPTION
				"A collection of managed objects that provide information about GX objects"
		::= { chkpntMIBGroups 12 }

	aviProductsGroup OBJECT-GROUP
		OBJECTS {  aviEngineName, aviEngineVer, aviEngineDate, aviSignatureName, aviSignatureVer, aviSignatureDate, aviLastSigCheckTime, aviLastSigLocation, aviLastLicExp, aviTopVirusesName, aviTopVirusesCnt, aviTopEverVirusesName, aviTopEverVirusesCnt, aviHTTPState, aviHTTPLastVirusName, aviHTTPLastVirusTime, aviHTTPTopVirusesName, aviHTTPTopVirusesCnt, aviFTPState, aviFTPLastVirusName, aviFTPLastVirusTime, aviFTPTopVirusesName, aviFTPTopVirusesCnt, aviSMTPState, aviSMTPLastVirusName, aviSMTPLastVirusTime, aviSMTPTopVirusesName, aviSMTPTopVirusesCnt, aviPOP3State, aviPOP3LastVirusName, aviPOP3LastVirusTime, aviPOP3TopVirusesName, aviPOP3TopVirusesCnt, aviStatCode, aviStatShortDescr, aviStatLongDescr }
		STATUS  current
		DESCRIPTION
				"A collection of managed objects that provide information about AVI objects"
		::= { chkpntMIBGroups 13 }

	eventiaAnalyzerProductsGroup OBJECT-GROUP
		OBJECTS { cpsemdStatCode, cpsemdStatShortDescr, cpsemdStatLongDescr, cpsemdProcAlive, cpsemdNewEventsHandled, cpsemdUpdatesHandled, cpsemdLastEventTime, cpsemdCurrentDBSize, cpsemdDBCapacity, cpsemdNumEvents, cpsemdDBDiskSpace, cpsemdCorrelationUnitIP, cpsemdCorrelationUnitLastRcvdTime, cpsemdCorrelationUnitNumEventsRcvd, cpsemdConnectionDuration, cpsemdDBIsFull, cpseadStatCode, cpseadStatShortDescr, cpseadStatLongDescr, cpseadProcAlive, cpseadConnectedToSem, cpseadNumProcessedLogs, cpseadJobID, cpseadJobName, cpseadJobState, cpseadJobIsOnline, cpseadJobLogServer, cpseadJobDataType, cpseadConnectedToLogServer, cpseadNumAnalyzedLogs, cpseadFileName, cpseadFileCurrentPosition, cpseadStateDescriptionCode, cpseadStateDescription, cpseadNoFreeDiskSpace }
		STATUS  current
		DESCRIPTION
				"A collection of managed objects that provide information about Eventia Analyzer objects"
		::= { chkpntMIBGroups 14 }

	ufProductsGroup OBJECT-GROUP
		OBJECTS { ufEngineName, ufEngineVer, ufEngineDate, ufSignatureDate, ufSignatureVer, ufLastSigCheckTime, ufLastSigLocation, ufLastLicExp, ufIsMonitor, ufScannedCnt, ufBlockedCnt, ufTopBlockedCatName, ufTopBlockedCatCnt, ufTopBlockedSiteName, ufTopBlockedSiteCnt, ufTopBlockedUserName, ufTopBlockedUserCnt, ufStatCode, ufStatShortDescr, ufStatLongDescr }
		STATUS  current
		DESCRIPTION
				"A collection of managed objects that provide information about UF objects"
		::= { chkpntMIBGroups 15 }

	msProductsGroup OBJECT-GROUP
		OBJECTS { msProductName, msMajorVersion, msMinorVersion, msBuildNumber, msVersionStr, msSpamNumScannedEmails, msSpamNumSpamEmails, msSpamNumHandledSpamEmails, msSpamControlsSpamEngine, msSpamControlsIpRepuatation, msSpamControlsSPF, msSpamControlsDomainKeys, msSpamControlsRDNS, msSpamControlsRBL, msExpirationDate, msEngineVer, msEngineDate, msStatCode, msStatShortDescr, msStatLongDescr, msServicePack }
		STATUS  current
		DESCRIPTION
				"A collection of managed objects that provide information about MS objects"
		::= { chkpntMIBGroups 16 }

	voipProductsGroup OBJECT-GROUP
		OBJECTS { voipProductName, voipMajorVersion, voipMinorVersion, voipBuildNumber, voipVersionStr, voipDOSSipNetworkReqInterval, voipDOSSipNetworkReqConfThreshold, voipDOSSipNetworkReqCurrentVal, voipDOSSipNetworkRegInterval, voipDOSSipNetworkRegConfThreshold, voipDOSSipNetworkRegCurrentVal, voipDOSSipNetworkCallInitInterval, voipDOSSipNetworkCallInitConfThreshold, voipDOSSipNetworkCallInitICurrentVal, voipDOSSipRateLimitingTableIpAddress, voipDOSSipRateLimitingTableInterval, voipDOSSipRateLimitingTableConfThreshold, voipDOSSipRateLimitingTableNumDOSSipRequests, voipDOSSipRateLimitingTableNumTrustedRequests, voipDOSSipRateLimitingTableNumNonTrustedRequests, voipDOSSipRateLimitingTableNumRequestsfromServers, voipCACConcurrentCallsConfThreshold, voipCACConcurrentCallsCurrentVal, voipStatCode, voipStatShortDescr, voipStatLongDescr, voipServicePack }
		STATUS  current
		DESCRIPTION
				"A collection of managed objects that provide information about VOIP objects"
		::= { chkpntMIBGroups 17 }

	identityAwarenessProductsGroup OBJECT-GROUP
		OBJECTS { identityAwarenessProductName, identityAwarenessAuthUsers, identityAwarenessUnAuthUsers, identityAwarenessAuthUsersKerberos, identityAwarenessAuthMachKerberos, identityAwarenessAuthUsersPass, identityAwarenessAuthUsersADQuery, identityAwarenessAuthMachADQuery, identityAwarenessLoggedInAgent, identityAwarenessLoggedInCaptivePortal, identityAwarenessLoggedInADQuery, identityAwarenessAntiSpoffProtection, identityAwarenessSuccUserLoginKerberos, identityAwarenessSuccMachLoginKerberos, identityAwarenessSuccUserLoginPass, identityAwarenessSuccUserLoginADQuery, identityAwarenessSuccMachLoginADQuery, identityAwarenessUnSuccUserLoginKerberos, identityAwarenessUnSuccMachLoginKerberos, identityAwarenessUnSuccUserLoginPass, identityAwarenessSuccUserLDAP, identityAwarenessUnSuccUserLDAP, identityAwarenessDataTrans, identityAwarenessDistributedEnvTableGwName, identityAwarenessDistributedEnvTableDisconnections, identityAwarenessDistributedEnvTableBruteForceAtt, identityAwarenessDistributedEnvTableStatus, identityAwarenessDistributedEnvTableIsLocal, identityAwarenessADQueryStatusCurrStatus, identityAwarenessADQueryStatusDomainName, identityAwarenessADQueryStatusDomainIP, identityAwarenessADQueryStatusEvents, identityAwarenessRADIUSAccounting, identityAwarenessIdentityCollectorActiveDirectory, identityAwarenessIdentityCollectorCiscoISE, identityAwarenessTerminalServer, identityAwarenessRemoteAccess, identityAwarenessIdentityWebAPI, identityAwarenessStatus, identityAwarenessStatusShortDesc, identityAwarenessStatusLongDesc }
		STATUS  current
		DESCRIPTION
				"A collection of managed objects that provide information about Identity Awarness objects"
		::= { chkpntMIBGroups 18 }

	applicationControlProductsGroup OBJECT-GROUP
		OBJECTS { applicationControlSubscriptionStatus, applicationControlSubscriptionExpDate, applicationControlSubscriptionDesc, applicationControlUpdateStatus, applicationControlUpdateDesc, applicationControlNextUpdate, applicationControlVersion, applicationControlStatusCode, applicationControlStatusShortDesc, applicationControlStatusLongDesc }
		STATUS  current
		DESCRIPTION
				"A collection of managed objects that provide information about APPI objects"
		::= { chkpntMIBGroups 19 }

	thresholdsProductsGroup OBJECT-GROUP
		OBJECTS { thresholdPolicy, thresholdState, thresholdStateDesc, thresholdEnabled, thresholdActive, thresholdEventsSinceStartup, thresholdActiveEventName, thresholdActiveEventCategory, thresholdActiveEventSeverity, thresholdActiveEventSubject, thresholdActiveEventSubjectValue, thresholdActiveEventActivationTime, thresholdActiveEventState, thresholdDestinationName, thresholdDestinationType, thresholdSendingState, thresholdSendingStateDesc, thresholdAlertCount, thresholdName, thresholdThresholdOID, thresholdErrorDesc, thresholdErrorTime }
		STATUS  current
		DESCRIPTION
				"A collection of managed objects that provide information about Thresholds objects"
		::= { chkpntMIBGroups 20 }

	advancedUrlFilteringProductsGroup OBJECT-GROUP
		OBJECTS { advancedUrlFilteringSubscriptionStatus, advancedUrlFilteringSubscriptionExpDate, advancedUrlFilteringSubscriptionDesc, advancedUrlFilteringUpdateStatus, advancedUrlFilteringUpdateDesc, advancedUrlFilteringNextUpdate, advancedUrlFilteringVersion, advancedUrlFilteringRADStatusCode, advancedUrlFilteringRADStatusDesc, advancedUrlFilteringStatusCode, advancedUrlFilteringStatusShortDesc, advancedUrlFilteringStatusLongDesc }
		STATUS  current
		DESCRIPTION
				"A collection of managed objects that provide information about Advanced URLF objects"
		::= { chkpntMIBGroups 21 }

	dlpProductsGroup OBJECT-GROUP
		OBJECTS { exchangeAgentName, exchangeAgentStatus, exchangeAgentTotalMsg, exchangeAgentTotalScannedMsg, exchangeAgentDroppedMsg, exchangeAgentUpTime, exchangeAgentTimeSinceLastMsg, exchangeAgentQueueLen, exchangeQueueLen, exchangeAgentAvgTimePerMsg, exchangeAgentAvgTimePerScannedMsg, exchangeAgentVersion, exchangeCPUUsage, exchangeMemoryUsage, exchangeAgentPolicyTimeStamp, dlpVersionString, dlpLicenseStatus, dlpLdapStatus, dlpTotalScans, dlpSMTPScans, dlpSMTPIncidents, dlpLastSMTPScan, dlpNumQuarantined, dlpQrntMsgsSize, dlpSentEMails, dlpExpiredEMails, dlpDiscardEMails, dlpPostfixQLen, dlpPostfixErrors, dlpPostfixQOldMsg, dlpPostfixQMsgsSz, dlpPostfixQFreeSp, dlpQrntFreeSpace, dlpQrntStatus, dlpHttpScans, dlpHttpIncidents, dlpHttpLastScan, dlpFtpScans, dlpFtpIncidents, dlpFtpLastScan, dlpBypassStatus, dlpUserCheckClnts, dlpLastPolStatus, dlpStatusCode, dlpStatusShortDesc, dlpStatusLongDesc }
		STATUS  current
		DESCRIPTION
				"A collection of managed objects that provide information about DLP objects"
		::= { chkpntMIBGroups 22 }

	amwProductsGroup OBJECT-GROUP
		OBJECTS { antiBotSubscriptionStatus, antiBotSubscriptionExpDate, antiBotSubscriptionDesc, antiVirusSubscriptionStatus, antiVirusSubscriptionExpDate, antiVirusSubscriptionDesc, antiSpamSubscriptionStatus, antiSpamSubscriptionExpDate, antiSpamSubscriptionDesc, amwABUpdateStatus, amwABUpdateDesc, amwABNextUpdate, amwABVersion, amwAVUpdateStatus, amwAVUpdateDesc, amwAVNextUpdate, amwAVVersion, amwStatusCode, amwStatusShortDesc, amwStatusLongDesc }
		STATUS  current
		DESCRIPTION
				"A collection of managed objects that provide information about AMW objects"
		::= { chkpntMIBGroups 23 }

	asgProductsGroup OBJECT-GROUP
		OBJECTS { asgProductName, asgVer, asgKernelVer, asgBuildNum, asgMaximumBladesPerChassis, asgActiveBladesBitmask, asgInstalledBladesBitmask, asgInstalled, asgSystemUp, asgEvent, asgStatusCode, asgStatShort, asgStatLong, asgSecureXLStatusBitmask, asgAttachedBladesBitmask, asgThroughput, asgConnectionRate, asgPacketRate, asgConcurrConn, asgAccelConnectionRate, asgNonAccelConnectionRate, asgAccelConcurrConn, asgNonAccelConcurrConn, asgLoad, asgAccelLoadAvg, asgAccelLoadMin, asgAccelLoadMax, asgInstancesLoadAvg, asgInstancesLoadMin, asgInstancesLoadMax, asgVpnThroughput, asgVpnConn, asgNatConnRate, asgNatConn, asgVsxCpu1MinAvg, asgStatName, asgAccelPath, asgMediumPath, asgFirewallPath, asgDropped, asgCountersBladeId, asgCountersThroughput, asgCountersConnRate, asgCountersPacketRate, asgCountersConcurrConnNum, asgCountersAccelLoadAverage, asgCountersAccelLoadMin, asgCountersAccelLoadMax, asgCountersInstanceLoadAverage, asgCountersInstanceLoadMin, asgCountersInstanceLoadMax, asgPeakCriteria, asgPeakName, asgPeakValue, asgPeakTimeStamp, asgPeakUnits, asgAcceptedBytesTotal, asgDroppedBytesTotal, asgRejectedTotal, asgIPv6Throughput, asgIPv6ConnectionRate, asgIPv6PacketRate, asgIPv6ConcurrConn, asgIPv6AccelConnectionRate, asgIPv6NonAccelConnectionRate, asgIPv6AccelConcurrConn, asgIPv6NonAccelConcurrConn, asgIPv6Load, asgIPv6AccelLoadAvg, asgIPv6AccelLoadMin, asgIPv6AccelLoadMax, asgIPv6InstancesLoadAvg, asgIPv6InstancesLoadMin, asgIPv6InstancesLoadMax, asgIPv6VpnThroughput, asgIPv6VpnConn, asgIPv6NatConnRate, asgIPv6NatConn, asgIPv6VsxCpu1MinAvg, asgIPv6StatName, asgIPv6AccelPath, asgIPv6MediumPath, asgIPv6FirewallPath, asgIPv6Dropped, asgIPv6CountersBladeId, asgIPv6CountersThroughput, asgIPv6CountersConnRate, asgIPv6CountersPacketRate, asgIPv6CountersConcurrConnNum, asgIPv6CountersAccelLoadAverage, asgIPv6CountersAccelLoadMin, asgIPv6CountersAccelLoadMax, asgIPv6CountersInstanceLoadAverage, asgIPv6CountersInstanceLoadMin, asgIPv6CountersInstanceLoadMax, asgIPv6PeakCriteria, asgIPv6PeakName, asgIPv6PeakValue, asgIPv6PeakTimeStamp, asgIPv6PeakUnits, asgIPv6AcceptedBytesTotalRate, asgIPv6DroppedBytesTotalRate, asgIPv6DroppedTotalRate, asgIPv6RulebaseBladeId, asgIPv6RulebaseDroppedTotal, asgIPv6RulebaseAcceptedTotal, asgIPv6RulebaseRejectedTotal, asgIPv6RulebaseBytesDroppedTotal, asgIPv6RulebaseBytesAcceptedTotal, asgIPv6RulebaseBytesRejectedTotal, asgSensorName, asgSensorLocation, asgSensorCurrValue, asgSensorMinValue, asgSensorMaxValue, asgSensorThreshold, asgSensorUnit, asgSensorIdentity, asgSensorStatus, asgResourceName, asgResourceLocation, asgResourceCurrValue, asgResourceThreshold, asgResourceUnit, asgResourceTotalVal, asgResourceTitle, asgProtocolName, asgProtocolConns, asgProtocolTotalPkts, asgProtocolTotalBytes, asgServiceName, asgServiceConns, asgServiceTotalPkts, asgServiceTotalBytes, asgNetIfName, asgNetIfIPv4Addr, asgNetIfIPv6Addr, asgNetIfMACAddr, asgNetIfInfo, asgNetIfState, asgNetIfSpeed, asgNetIfMTU, asgNetIfDuplex, asgNetIfRx, asgNetIfTx, asgProblemName, asgProblemStatus, asgProblemPriority, asgProblemVerified, asgProblemDescr, asgChassisMode, asgChassisHAMode, asgSyncToActive, asgSyncToStandby, asgSyncExceptionsID, asgSyncExceptionsSource, asgSyncExceptionsSourceMask, asgSyncExceptionsDestination, asgSyncExceptionsDestinationMask, asgSyncExceptionsIpProtocol, asgSyncExceptionsSync, asgSyncExceptionsDelay, asgChassisParamsID, asgChassisParamsStatus, asgChassisParamsGrade, asgChassisParamsMaxGrade, asgChassisParamsUniqueIP, asgSGMID, asgSGMStatus, asgSGMProcess, asgSGMPolicyTime, asgFactorName, asgFactorValue, asgPriorityPortName, asgPortPriority, asgCoreRowTitle, blade1, blade2, blade3, blade4, blade5, blade6, blade7, blade8, blade9, blade10, blade11, blade12, blade13, blade14, blade15, blade16, blade17, blade18, blade19, blade20, blade21, blade22, blade23, blade24, blade25, blade26, blade27, blade28, blade29, blade30, blade31, blade32, blade33, blade34, blade35, blade36, blade37, blade38, blade39, blade40, blade41, blade42, blade43, blade44, blade45, blade46, blade47, blade48, asgVslsSgmRatio, asgVslsSystemPrimaryChassis, asgVslsVsName, asgVslsVsPrimaryChassis, asgVslsVsActiveChassis, asgVslsVsHealth, asgVslsVsReason, asgVslsVsChassis1InterfacesUp, asgVslsVsChassis1InterfacesTotal, asgVslsVsChassis1FwksUp, asgVslsVsChassis1FwksTotal, asgVslsVsChassis2InterfacesUp, asgVslsVsChassis2InterfacesTotal, asgVslsVsChassis2FwksUp, asgVslsVsChassis2FwksTotal, asgVslsVsChassis3InterfacesUp, asgVslsVsChassis3InterfacesTotal, asgVslsVsChassis3FwksUp, asgVslsVsChassis3FwksTotal, asgVslsVsChassis4InterfacesUp, asgVslsVsChassis4InterfacesTotal, asgVslsVsChassis4FwksUp, asgVslsVsChassis4FwksTotal, asgVSXConnBladeID, asgVSXIPver, asgVSXConcurrentConns, asgVSXPeakConns, asgVSXConnLimit, asgVSXConnectionsNumberPerSystem, asgVSXMemBladeid, asgVSXOverallMem, asgVSXCoreUtilBladeid, asgVSXCoreUtilCPUID, asgVSXCoreUtilUsage, asgVSXRateBladeid, asgVSXRateValue, asgVSXPacketRatePerSystem, asgVSXThroughputBladeid, asgVSXThroughputValue, asgVSXThroughputPerSystem, asgVSXThroughputPerInterfaceBladeid, asgVSXThroughputPerInterfaceName, asgVSXThroughputPerInterfaceValue, asgVSXPerSystemThroughputPerInterfaceName, asgVSXPerSystemThroughputPerInterfaceValue, asgVSXConnectionRateBladeid, asgVSXConnectionRateValue, asgVSXConnectionRatePerSystem, asgVSXVirtualMemoryBladeid, asgVSXVirtualMemoryValue, asgDiagnosticTestName, asgDiagnosticLastRun, asgDiagnosticResult, asgDiagnosticComment, asgDiagSummary }
		STATUS  current
		DESCRIPTION
				"A collection of managed objects that provide information about ASG objects"
		::= { chkpntMIBGroups 24 }

	teProductsGroup OBJECT-GROUP
		OBJECTS { teSubscriptionStatus, teCloudSubscriptionStatus, teSubscriptionExpDate, teSubscriptionDesc, teUpdateStatus, teUpdateDesc, teStatusCode, teStatusShortDesc, teStatusLongDesc }
		STATUS  current
		DESCRIPTION
				"A collection of managed objects that provide information about TE objects"
		::= { chkpntMIBGroups 25 }

	threatExtractionProductsGroup OBJECT-GROUP
		OBJECTS { threatExtractionSubscriptionStatus, threatExtractionSubscriptionExpDate, threatExtractionSubscriptionDesc, threatExtractionTotalScannedAttachments, threatExtractionCleanedAttachments, threatExtractionOriginalAttachmentsAccesses, threatExtractionStatusCode, threatExtractionStatusShortDesc, threatExtractionStatusLongDesc, threatExtractionEngineVersion }
		STATUS  current
		DESCRIPTION
				"A collection of managed objects that provide information about TEX objects"
		::= { chkpntMIBGroups 26 }

	sxlProductsGroup OBJECT-GROUP
		OBJECTS { fwSXLStatus, fwSXLConnsExisting, fwSXLConnsAdded, fwSXLConnsDeleted, fwSXLAggrRxMbits, fwSXLAggrTxMbits, fwSXLAggrInboundKbitsPerSecond, fwSXLAggrOutboundKbitsPerSecond, fwSXLAggrInboundpacketsPerSecond, fwSXLAggrOutboundpacketsPerSecond, fwSXLAggrConnectionsPerSecond, fwSXLAggrConcurrentConnections, fwSXLAggrPpak2FwNotificationsSuccessful, fwSXLAggrPpak2FwNotificationsFailure, fwSXLAggrFw2PpakNotificationsSuccessful, fwSXLAggrFw2PpakNotificationsFailure, fwSXLAggrDropsTotPackets, fwSXLAggrDropsPxlDecision, fwSXLAggrDropsFragmentationError, fwSXLAggrDropsF2FNotAllowed, fwSXLAggrDropsHeavyLoadTcpViolation, fwSXLAggrDropsCorruptPacket, fwSXLAggrDropsHeavyLoadNewConnection, fwSXLAggrDropsClearPacketOnVPN, fwSXLAggrDropsEncryptionFailed, fwSXLAggrDropsDropTemplate, fwSXLAggrDropsDecryptionFailed, fwSXLAggrDropsOutboundConnNotFound, fwSXLAggrDropsInterfaceDown, fwSXLAggrDropsClusterError, fwSXLAggrDropsXmlError, fwSXLAggrDropsAntiSpoofing, fwSXLAggrDropsSanityError, fwSXLAggrDropsQxlDecision, fwSXLAggrDropsLoopPrevention, fwSXLHostRxMbits, fwSXLHostTxMbits, fwSXLHostInboundKbitsPerSecond, fwSXLHostOutboundKbitsPerSecond, fwSXLHostInboundpacketsPerSecond, fwSXLHostOutboundpacketsPerSecond, fwSXLHostConnectionsPerSecond, fwSXLHostConcurrentConnections, fwSXLHostPpak2FwNotificationsSuccessful, fwSXLHostPpak2FwNotificationsFailure, fwSXLHostFw2PpakNotificationsSuccessful, fwSXLHostFw2PpakNotificationsFailure, fwSXLHostDropsTotPackets, fwSXLHostDropsPxlDecision, fwSXLHostDropsFragmentationError, fwSXLHostDropsF2FNotAllowed, fwSXLHostDropsHeavyLoadTcpViolation, fwSXLHostDropsCorruptPacket, fwSXLHostDropsHeavyLoadNewConnection, fwSXLHostDropsClearPacketOnVPN, fwSXLHostDropsEncryptionFailed, fwSXLHostDropsDropTemplate, fwSXLHostDropsDecryptionFailed, fwSXLHostDropsOutboundConnNotFound, fwSXLHostDropsInterfaceDown, fwSXLHostDropsClusterError, fwSXLHostDropsXmlError, fwSXLHostDropsAntiSpoofing, fwSXLHostDropsSanityError, fwSXLHostDropsQxlDecision, fwSXLHostDropsLoopPrevention, fwSXLHostInterface0Name, fwSXLHostInterface1Name, fwSXLHostInterface2Name, fwSXLHostInterface3Name, fwSXLHostInterface4Name, fwSXLHostInterface5Name, fwSXLHostInterface6Name, fwSXLHostInterface7Name, fwSXLHostInterface0Speed, fwSXLHostInterface1Speed, fwSXLHostInterface2Speed, fwSXLHostInterface3Speed, fwSXLHostInterface4Speed, fwSXLHostInterface5Speed, fwSXLHostInterface6Speed, fwSXLHostInterface7Speed, fwSXLHostInterface0State, fwSXLHostInterface1State, fwSXLHostInterface2State, fwSXLHostInterface3State, fwSXLHostInterface4State, fwSXLHostInterface5State, fwSXLHostInterface6State, fwSXLHostInterface7State, fwSXLHostState, fwSXLFalconsRxMbits, fwSXLFalconsTxMbits, fwSXLFalconsInboundKbitsPerSecond, fwSXLFalconsOutboundKbitsPerSecond, fwSXLFalconsInboundpacketsPerSecond, fwSXLFalconsOutboundpacketsPerSecond, fwSXLFalconsConnectionsPerSecond, fwSXLFalconsConcurrentConnections, fwSXLFalconsPpak2FwNotificationsSuccessful, fwSXLFalconsPpak2FwNotificationsFailure, fwSXLFalconsFw2PpakNotificationsSuccessful, fwSXLFalconsFw2PpakNotificationsFailure, fwSXLFalconsDropsTotPackets, fwSXLFalconsDropsPxlDecision, fwSXLFalconsDropsFragmentationError, fwSXLFalconsDropsF2FNotAllowed, fwSXLFalconsDropsHeavyLoadTcpViolation, fwSXLFalconsDropsCorruptPacket, fwSXLFalconsDropsHeavyLoadNewConnection, fwSXLFalconsDropsClearPacketOnVPN, fwSXLFalconsDropsEncryptionFailed, fwSXLFalconsDropsDropTemplate, fwSXLFalconsDropsDecryptionFailed, fwSXLFalconsDropsOutboundConnNotFound, fwSXLFalconsDropsInterfaceDown, fwSXLFalconsDropsClusterError, fwSXLFalconsDropsXmlError, fwSXLFalconsDropsAntiSpoofing, fwSXLFalconsDropsSanityError, fwSXLFalconsDropsQxlDecision, fwSXLFalconsDropsLoopPrevention, fwSXLFalconsInterface0Name, fwSXLFalconsInterface1Name, fwSXLFalconsInterface2Name, fwSXLFalconsInterface3Name, fwSXLFalconsInterface4Name, fwSXLFalconsInterface5Name, fwSXLFalconsInterface6Name, fwSXLFalconsInterface7Name, fwSXLFalconsInterface0Speed, fwSXLFalconsInterface1Speed, fwSXLFalconsInterface2Speed, fwSXLFalconsInterface3Speed, fwSXLFalconsInterface4Speed, fwSXLFalconsInterface5Speed, fwSXLFalconsInterface6Speed, fwSXLFalconsInterface7Speed, fwSXLFalconsInterface0State, fwSXLFalconsInterface1State, fwSXLFalconsInterface2State, fwSXLFalconsInterface3State, fwSXLFalconsInterface4State, fwSXLFalconsInterface5State, fwSXLFalconsInterface6State, fwSXLFalconsInterface7State, fwSXLFalconsSxlTotMemory, fwSXLFalconsSxlUsedMemory, fwSXLFalconsSxlFreeMemory, fwSXLFalconsPacketPoolTotMemory, fwSXLFalconsPacketPoolUsedMemory, fwSXLFalconsPacketPoolFreeMemory, fwSXLFalconsCpu0Usage, fwSXLFalconsCpu1Usage, fwSXLFalconsCpu2Usage, fwSXLFalconsCpu3Usage, fwSXLFalconsCpu4Usage, fwSXLFalconsCpu5Usage, fwSXLFalconsCpu6Usage, fwSXLFalconsCpu7Usage, fwSXLFalconsCpu8Usage, fwSXLFalconsCpu9Usage, fwSXLFalconsCpu10Usage, fwSXLFalconsCpu11Usage, fwSXLFalconsCpu12Usage, fwSXLFalconsCpu13Usage, fwSXLFalconsCpu14Usage, fwSXLFalconsCpu15Usage, fwSXLFalconsCpu16Usage, fwSXLFalconsCpu17Usage, fwSXLFalconsCpu18Usage, fwSXLFalconsCpu19Usage, fwSXLFalconsCpu20Usage, fwSXLFalconsCpu21Usage, fwSXLFalconsCpu22Usage, fwSXLFalconsCpu23Usage, fwSXLFalconsCpu24Usage, fwSXLFalconsCpu25Usage, fwSXLFalconsCpu26Usage, fwSXLFalconsCpu27Usage, fwSXLFalconsCpu28Usage, fwSXLFalconsCpu29Usage, fwSXLFalconsCpu30Usage, fwSXLFalconsCpu31Usage, fwSXLFalconsGeneralIndex, fwSXLFalconsState, fwSXLFalconsType, fwSXLFalconsSerialNumber, fwSXLFalconsSlotNumber }
		STATUS  current
		DESCRIPTION
				"A collection of managed objects that provide information about SXL objects"
		::= { chkpntMIBGroups 27 }

	vsecControllerProductsGroup OBJECT-GROUP
		OBJECTS { vsecVsecStatus, vsecNumberOfDisconnectedDataCenters, vsecTotalNumberOfDataCenters, vsecTotalNumberOfImportedDataCenterObjects, vsecTotalNumberOfGwWithDataCenterObjects, vsecDataCenterName, vsecDataCenterType, vsecConnectionStatus, vsecNumberOfImportedObjects, vsecNumberOfAutoUpdate, vsecGatewayName, vsecGatewayIP, vsecGatewayVersion, vsecGatewayUpdateSucceeded }
		STATUS  current
		DESCRIPTION
				"A collection of managed objects that provide information about VSec Controller objects"
		::= { chkpntMIBGroups 28 }

	ipsProductsGroup OBJECT-GROUP
		OBJECTS { ipsStatus, ipsUpdateStatus, ipsUpdateDescription, ipsNextUpdateDescription, ipsDBVersion, ipsState, ipsStateShortDesc, ipsStateLongDesc }
		STATUS  current
		DESCRIPTION
				"A collection of managed objects that provide information about IPS objects"
		::= { chkpntMIBGroups 29 }

	httpsInspectionProductsGroup OBJECT-GROUP
		OBJECTS { httpsInspectionStatus, httpsInspectionStatusDescription, hsmEnabled, hsmEnabledDescription, hsmPartitionAccess, hsmPartitionAccessDescription, outboundStatus, outboundStatusDescription }
		STATUS  current
		DESCRIPTION
				"A collection of managed objects that provide information about HTTPS Inspection objects"
		::= { chkpntMIBGroups 30 }

	mhoProductsGroup OBJECT-GROUP
		OBJECTS { mhoRxPortLabel, mhoRxUcast,  mhoRxMcast, mhoRxBcast, mhoRxErr, mhoRxFrames, mhoRxBytes, mhoRxFcsErr, mhoTxPortLabel, mhoTxUcast, mhoTxMcast, mhoTxBcast, mhoTxErr, mhoTxFrames, mhoTxBytes, mhoRxBuffPortLabel, mhoRxBuff0Frames, mhoRxBuff0Octet, mhoRxBuff0Discard, mhoRxBuff1Frames, mhoRxBuff1Octet, mhoRxBuff1Discard, mhoRxBuff2Frames, mhoRxBuff2Octet, mhoRxBuff2Discard, mhoRxBuff3Frames, mhoRxBuff3Octet, mhoRxBuff3Discard, mhoRxBuff4Frames, mhoRxBuff4Octet, mhoRxBuff4Discard, mhoRxBuff5Frames, mhoRxBuff5Octet, mhoRxBuff5Discard, mhoRxBuff6Frames, mhoRxBuff6Octet, mhoRxBuff6Discard, mhoRxBuff7Frames, mhoRxBuff7Octet, mhoRxBuff7Discard, mhoStatePortLabel, mhoStateLinkState, mhoStateAdminState, mhoStateSpeed, mhoSummaryPortLabel, mhoSummaryLinkState, mhoSummaryAdminState, mhoSummarySpeed, mhoSummaryRxFcsErr, mhoSummaryRxErr, mhoSummaryRxFrames, mhoSummaryRxBytes, mhoSummaryTxErr, mhoSummaryTxFrames, mhoSummaryTxBytes, mhoACLsUsed, mhoACLsTotal, mhoACLsAvailable }
		STATUS current
		DESCRIPTION
				"A collection of managed objects that provide information about MHO objects"
		::= { chkpntMIBGroups 31 }

	--mho statuses:

	mhoPortsStatus          OBJECT IDENTIFIER ::= { mho 1 }
	mhoAcls                 OBJECT IDENTIFIER ::= { mho 2 }

	mhoRxTable OBJECT-TYPE
		SYNTAX  SEQUENCE OF  MhoRxEntry
		MAX-ACCESS    not-accessible
		STATUS        current
		DESCRIPTION   "A table showing ports RX counters."
		::= { mhoPortsStatus 1 }

	mhoTxTable OBJECT-TYPE
		SYNTAX  SEQUENCE OF  MhoTxEntry
		MAX-ACCESS  	not-accessible
		STATUS  		current
		DESCRIPTION   "A table showing ports TX counters."
		::= { mhoPortsStatus 2 }

	mhoRxBuffTable OBJECT-TYPE
		SYNTAX  SEQUENCE OF  MhoRxBuffEntry
		MAX-ACCESS    not-accessible
		STATUS        current
		DESCRIPTION   "A table showing ports RX buffers counters."
		::= { mhoPortsStatus 3 }

	mhoStateTable OBJECT-TYPE
		SYNTAX  SEQUENCE OF  MhoStateEntry
		MAX-ACCESS    not-accessible
		STATUS        current
		DESCRIPTION   "A table showing ports states."
		::= { mhoPortsStatus 4 }

	mhoSummaryTable OBJECT-TYPE
		SYNTAX  SEQUENCE OF  MhoSummaryEntry
		MAX-ACCESS    not-accessible
		STATUS        current
		DESCRIPTION   "A table showing essential ports data."
		::= { mhoPortsStatus 5 }


	mhoRxEntry OBJECT-TYPE
	        SYNTAX  MhoRxEntry
	        MAX-ACCESS  not-accessible
	        STATUS  current
	        DESCRIPTION
				"MHO RX Entry"
	        INDEX { mhoRxPortIndex }
	        ::= { mhoRxTable 1 }

	MhoRxEntry ::=
            SEQUENCE {
                mhoRxPortIndex Unsigned32,
                mhoRxPortLabel DisplayString,
                mhoRxUcast Counter64,
                mhoRxMcast Counter64,
                mhoRxBcast Counter64,
                mhoRxErr Counter64,
                mhoRxFrames Counter64,
                mhoRxBytes Counter64,
                mhoRxFcsErr Counter64
              }

	mhoTxEntry OBJECT-TYPE
	        SYNTAX  MhoTxEntry
	        MAX-ACCESS  not-accessible
	        STATUS  current
	        DESCRIPTION
				"MHO TX Entry"
	        INDEX { mhoTxPortIndex }
	        ::= { mhoTxTable 1 }

	MhoTxEntry ::=
            SEQUENCE {
                mhoTxPortIndex Unsigned32,
                mhoTxPortLabel DisplayString,
                mhoTxUcast Counter64,
                mhoTxMcast Counter64,
                mhoTxBcast Counter64,
                mhoTxErr Counter64,
                mhoTxFrames Counter64,
                mhoTxBytes Counter64
              }

	mhoRxBuffEntry OBJECT-TYPE
	        SYNTAX  MhoRxBuffEntry
	        MAX-ACCESS  not-accessible
	        STATUS  current
	        DESCRIPTION
				"MHO RX Buffer Entry"
	        INDEX { mhoRxBuffPortIndex }
	        ::= { mhoRxBuffTable 1 }

	MhoRxBuffEntry ::=
            SEQUENCE {
                mhoRxBuffPortIndex Unsigned32,
                mhoRxBuffPortLabel DisplayString,
                mhoRxBuff0Frames Counter64,
                mhoRxBuff0Octet Counter64,
                mhoRxBuff0Discard Counter64,
                mhoRxBuff1Frames Counter64,
                mhoRxBuff1Octet  Counter64,
                mhoRxBuff1Discard Counter64,
                mhoRxBuff2Frames Counter64,
                mhoRxBuff2Octet Counter64,
                mhoRxBuff2Discard Counter64,
                mhoRxBuff3Frames Counter64,
                mhoRxBuff3Octet Counter64,
                mhoRxBuff3Discard Counter64,
                mhoRxBuff4Frames Counter64,
                mhoRxBuff4Octet Counter64,
                mhoRxBuff4Discard Counter64,
                mhoRxBuff5Frames Counter64,
                mhoRxBuff5Octet Counter64,
                mhoRxBuff5Discard Counter64,
                mhoRxBuff6Frames Counter64,
                mhoRxBuff6Octet Counter64,
                mhoRxBuff6Discard  Counter64,
                mhoRxBuff7Frames Counter64,
                mhoRxBuff7Octet Counter64,
                mhoRxBuff7Discard Counter64
              }

	mhoStateEntry OBJECT-TYPE
	        SYNTAX  MhoStateEntry
	        MAX-ACCESS  not-accessible
	        STATUS  current
	        DESCRIPTION
				"MHO State Entry"
	        INDEX { mhoStatePortIndex }
	        ::= { mhoStateTable 1 }

	MhoStateEntry ::=
            SEQUENCE {
                mhoStatePortIndex Unsigned32,
                mhoStatePortLabel DisplayString,
                mhoStateLinkState DisplayString,
                mhoStateAdminState DisplayString,
                mhoStateSpeed DisplayString
              }


	mhoSummaryEntry OBJECT-TYPE
	        SYNTAX  MhoSummaryEntry
	        MAX-ACCESS  not-accessible
	        STATUS  current
	        DESCRIPTION
				"MHO Summary Entry"
	        INDEX { mhoSummaryPortIndex }
	        ::= { mhoSummaryTable 1 }

	MhoSummaryEntry ::=
            SEQUENCE {
                mhoSummaryPortIndex Unsigned32,
                mhoSummaryPortLabel DisplayString,
                mhoSummaryLinkState DisplayString,
                mhoSummaryAdminState DisplayString,
                mhoSummarySpeed DisplayString,
                mhoSummaryRxFcsErr Counter64,
                mhoSummaryRxErr Counter64,
                mhoSummaryRxFrames Counter64,
                mhoSummaryRxBytes Counter64,
                mhoSummaryTxErr Counter64,
                mhoSummaryTxFrames Counter64,
                mhoSummaryTxBytes Counter64
              }

	mhoRxPortIndex OBJECT-TYPE
			SYNTAX  Unsigned32
			MAX-ACCESS not-accessible
			STATUS  current
			DESCRIPTION "The number of the logical port."
			::= { mhoRxEntry 1 }

	mhoRxPortLabel OBJECT-TYPE
			SYNTAX  DisplayString
			MAX-ACCESS read-only
			STATUS  current
			DESCRIPTION "The number of the physical port."
			::= { mhoRxEntry 2 }

	mhoRxUcast OBJECT-TYPE
			SYNTAX  Counter64
			MAX-ACCESS read-only
			STATUS  current
			DESCRIPTION "The number of unicast frames received."
			::= { mhoRxEntry 3 }

	mhoRxMcast OBJECT-TYPE
			SYNTAX  Counter64
			MAX-ACCESS read-only
			STATUS  current
			DESCRIPTION "The number of multicast frames received."
			::= { mhoRxEntry 4 }

	mhoRxBcast OBJECT-TYPE
			SYNTAX  Counter64
			MAX-ACCESS read-only
			STATUS  current
			DESCRIPTION "The number of broadcast frames received."
			::= { mhoRxEntry 5 }

	mhoRxErr OBJECT-TYPE
			SYNTAX  Counter64
			MAX-ACCESS read-only
			STATUS  current
			DESCRIPTION "The number of ingress packets that contained errors preventing them from being deliverable to a higher-layer protocol."
			::= { mhoRxEntry 6 }

	mhoRxFrames OBJECT-TYPE
			SYNTAX  Counter64
			MAX-ACCESS read-only
			STATUS  current
			DESCRIPTION "The number of received frames."
			::= { mhoRxEntry 7 }

	mhoRxBytes OBJECT-TYPE
			SYNTAX  Counter64
			MAX-ACCESS read-only
			STATUS  current
			DESCRIPTION "The volume of received data in bytes."
			::= { mhoRxEntry 8 }

    mhoRxFcsErr OBJECT-TYPE
			SYNTAX  Counter64
			MAX-ACCESS read-only
			STATUS  current
			DESCRIPTION "The number of ingress packages that are not an integral number of octets in length and do not pass the FCS check."
			::= { mhoRxEntry 9 }

	mhoTxPortIndex OBJECT-TYPE
			SYNTAX  Unsigned32
			MAX-ACCESS not-accessible
			STATUS  current
			DESCRIPTION "The number of the logical port."
			::= { mhoTxEntry 1 }

	mhoTxPortLabel OBJECT-TYPE
			SYNTAX  DisplayString
			MAX-ACCESS read-only
			STATUS  current
			DESCRIPTION "The number of the physical port."
			::= { mhoTxEntry 2 }

	mhoTxUcast OBJECT-TYPE
			SYNTAX  Counter64
			MAX-ACCESS read-only
			STATUS  current
			DESCRIPTION "The number of unicast frames transmitted."
			::= { mhoTxEntry 3 }

	mhoTxMcast OBJECT-TYPE
			SYNTAX  Counter64
			MAX-ACCESS read-only
			STATUS  current
			DESCRIPTION "The number of multicast frames transmitted."
			::= { mhoTxEntry 4 }

	mhoTxBcast OBJECT-TYPE
			SYNTAX  Counter64
			MAX-ACCESS read-only
			STATUS  current
			DESCRIPTION "The number of broadcast frames transmitted."
			::= { mhoTxEntry 5 }

	mhoTxErr OBJECT-TYPE
			SYNTAX  Counter64
			MAX-ACCESS read-only
			STATUS  current
			DESCRIPTION "The number of error packets intended to be sent."
			::= { mhoTxEntry 6 }

	mhoTxFrames OBJECT-TYPE
			SYNTAX  Counter64
			MAX-ACCESS read-only
			STATUS  current
			DESCRIPTION "The number of transmitted frames."
			::= { mhoTxEntry 7 }

	mhoTxBytes OBJECT-TYPE
			SYNTAX  Counter64
			MAX-ACCESS read-only
			STATUS  current
			DESCRIPTION "The volume of transmitted data in bytes."
			::= { mhoTxEntry 8 }

	mhoRxBuffPortIndex OBJECT-TYPE
			SYNTAX  Unsigned32
			MAX-ACCESS not-accessible
			STATUS  current
			DESCRIPTION "The number of the logical port."
			::= { mhoRxBuffEntry 1 }

	mhoRxBuffPortLabel OBJECT-TYPE
			SYNTAX  DisplayString
			MAX-ACCESS read-only
			STATUS  current
			DESCRIPTION "The number of the physical port."
			::= { mhoRxBuffEntry 2 }

	mhoRxBuff0Frames OBJECT-TYPE
			SYNTAX  Counter64
			MAX-ACCESS read-only
			STATUS  current
			DESCRIPTION "The number of received frames which are mapped into PG0. PG is the priority group used on the ingress packets."
			::= { mhoRxBuffEntry 3 }

	mhoRxBuff0Octet OBJECT-TYPE
			SYNTAX  Counter64
			MAX-ACCESS read-only
			STATUS  current
			DESCRIPTION "The volume of received data in bytes which are mapped into PG0. PG is the priority group used on the ingress packets."
			::= { mhoRxBuffEntry 4 }

	mhoRxBuff0Discard OBJECT-TYPE
			SYNTAX  Counter64
			MAX-ACCESS read-only
			STATUS  current
			DESCRIPTION "The number of ingress packets mapped to PG0 (PG is the priority group used on the ingress packets) which were chosen to be discarded even though no errors had been detected to prevent them being delivered to higher-layer protocol."
			::= { mhoRxBuffEntry 5 }

	mhoRxBuff1Frames OBJECT-TYPE
			SYNTAX  Counter64
			MAX-ACCESS read-only
			STATUS  current
			DESCRIPTION "The number of received frames which are mapped into PG1. PG is the priority group used on the ingress packets."
			::= { mhoRxBuffEntry 6 }

	mhoRxBuff1Octet OBJECT-TYPE
			SYNTAX  Counter64
			MAX-ACCESS read-only
			STATUS  current
			DESCRIPTION "The volume of received data in bytes which are mapped into PG1. PG is the priority group used on the ingress packets."
			::= { mhoRxBuffEntry 7 }

	mhoRxBuff1Discard OBJECT-TYPE
			SYNTAX  Counter64
			MAX-ACCESS read-only
			STATUS  current
			DESCRIPTION "The number of ingress packets mapped to PG1 (PG is the priority group used on the ingress packets) which were chosen to be discarded even though no errors had been detected to prevent them being delivered to higher-layer protocol."
			::= { mhoRxBuffEntry 8 }

	mhoRxBuff2Frames OBJECT-TYPE
			SYNTAX  Counter64
			MAX-ACCESS read-only
			STATUS  current
			DESCRIPTION "The number of received frames which are mapped into PG2. PG is the priority group used on the ingress packets."
			::= { mhoRxBuffEntry 9 }

	mhoRxBuff2Octet OBJECT-TYPE
			SYNTAX  Counter64
			MAX-ACCESS read-only
			STATUS  current
			DESCRIPTION "The volume of received data in bytes which are mapped into PG2. PG is the priority group used on the ingress packets."
			::= { mhoRxBuffEntry 10 }

	mhoRxBuff2Discard OBJECT-TYPE
			SYNTAX  Counter64
			MAX-ACCESS read-only
			STATUS  current
			DESCRIPTION "The number of ingress packets mapped to PG2 (PG is the priority group used on the ingress packets) which were chosen to be discarded even though no errors had been detected to prevent them being delivered to higher-layer protocol."
			::= { mhoRxBuffEntry 11 }

	mhoRxBuff3Frames OBJECT-TYPE
			SYNTAX  Counter64
			MAX-ACCESS read-only
			STATUS  current
			DESCRIPTION "The number of received frames which are mapped into PG3. PG is the priority group used on the ingress packets."
			::= { mhoRxBuffEntry 12 }

	mhoRxBuff3Octet OBJECT-TYPE
			SYNTAX  Counter64
			MAX-ACCESS read-only
			STATUS  current
			DESCRIPTION "The volume of received data in bytes which are mapped into PG3. PG is the priority group used on the ingress packets."
			::= { mhoRxBuffEntry 13 }

	mhoRxBuff3Discard OBJECT-TYPE
			SYNTAX  Counter64
			MAX-ACCESS read-only
			STATUS  current
			DESCRIPTION "The number of ingress packets mapped to PG3 (PG is the priority group used on the ingress packets) which were chosen to be discarded even though no errors had been detected to prevent them being delivered to higher-layer protocol."
			::= { mhoRxBuffEntry 14 }

	mhoRxBuff4Frames OBJECT-TYPE
			SYNTAX  Counter64
			MAX-ACCESS read-only
			STATUS  current
			DESCRIPTION "The number of received frames which are mapped into PG4. PG is the priority group used on the ingress packets."
			::= { mhoRxBuffEntry 15 }

	mhoRxBuff4Octet OBJECT-TYPE
			SYNTAX  Counter64
			MAX-ACCESS read-only
			STATUS  current
			DESCRIPTION "The volume of received data in bytes which are mapped into PG4. PG is the priority group used on the ingress packets."
			::= { mhoRxBuffEntry 16 }

	mhoRxBuff4Discard OBJECT-TYPE
			SYNTAX  Counter64
			MAX-ACCESS read-only
			STATUS  current
			DESCRIPTION "The number of ingress packets mapped to PG4 (PG is the priority group used on the ingress packets) which were chosen to be discarded even though no errors had been detected to prevent them being delivered to higher-layer protocol."
			::= { mhoRxBuffEntry 17 }

	mhoRxBuff5Frames OBJECT-TYPE
			SYNTAX  Counter64
			MAX-ACCESS read-only
			STATUS  current
			DESCRIPTION "The number of received frames which are mapped into PG5. PG is the priority group used on the ingress packets."
			::= { mhoRxBuffEntry 18 }

	mhoRxBuff5Octet OBJECT-TYPE
			SYNTAX  Counter64
			MAX-ACCESS read-only
			STATUS  current
			DESCRIPTION "The volume of received data in bytes which are mapped into PG5. PG is the priority group used on the ingress packets."
			::= { mhoRxBuffEntry 19 }

	mhoRxBuff5Discard OBJECT-TYPE
			SYNTAX  Counter64
			MAX-ACCESS read-only
			STATUS  current
			DESCRIPTION "The number of ingress packets mapped to PG5 (PG is the priority group used on the ingress packets) which were chosen to be discarded even though no errors had been detected to prevent them being delivered to higher-layer protocol."
			::= { mhoRxBuffEntry 20 }

	mhoRxBuff6Frames OBJECT-TYPE
			SYNTAX  Counter64
			MAX-ACCESS read-only
			STATUS  current
			DESCRIPTION "The number of received frames which are mapped into PG6. PG is the priority group used on the ingress packets."
			::= { mhoRxBuffEntry 21 }

	mhoRxBuff6Octet OBJECT-TYPE
			SYNTAX  Counter64
			MAX-ACCESS read-only
			STATUS  current
			DESCRIPTION "The volume of received data in bytes which are mapped into PG6. PG is the priority group used on the ingress packets."
			::= { mhoRxBuffEntry 22 }

	mhoRxBuff6Discard OBJECT-TYPE
			SYNTAX  Counter64
			MAX-ACCESS read-only
			STATUS  current
			DESCRIPTION "The number of ingress packets mapped to PG6 (PG is the priority group used on the ingress packets) which were chosen to be discarded even though no errors had been detected to prevent them being delivered to higher-layer protocol."
			::= { mhoRxBuffEntry 23 }

	mhoRxBuff7Frames OBJECT-TYPE
			SYNTAX  Counter64
			MAX-ACCESS read-only
			STATUS  current
			DESCRIPTION "The number of received frames which are mapped into PG7. PG is the priority group used on the ingress packets."
			::= { mhoRxBuffEntry 24 }

	mhoRxBuff7Octet OBJECT-TYPE
			SYNTAX  Counter64
			MAX-ACCESS read-only
			STATUS  current
			DESCRIPTION "The volume of received data in bytes which are mapped into PG7. PG is the priority group used on the ingress packets."
			::= { mhoRxBuffEntry 25 }

	mhoRxBuff7Discard OBJECT-TYPE
			SYNTAX  Counter64
			MAX-ACCESS read-only
			STATUS  current
			DESCRIPTION "The number of ingress packets mapped to PG7 (PG is the priority group used on the ingress packets) which were chosen to be discarded even though no errors had been detected to prevent them being delivered to higher-layer protocol."
			::= { mhoRxBuffEntry 26 }

	mhoStatePortIndex OBJECT-TYPE
			SYNTAX  Unsigned32
			MAX-ACCESS not-accessible
			STATUS  current
			DESCRIPTION "The number of the logical port."
			::= { mhoStateEntry 1 }

	mhoStatePortLabel OBJECT-TYPE
			SYNTAX  DisplayString
			MAX-ACCESS read-only
			STATUS  current
			DESCRIPTION "The number of the physical port."
			::= { mhoStateEntry 2 }

	mhoStateLinkState OBJECT-TYPE
			SYNTAX  DisplayString
			MAX-ACCESS read-only
			STATUS  current
			DESCRIPTION "The port link-state."
			::= { mhoStateEntry 3 }

	mhoStateAdminState OBJECT-TYPE
			SYNTAX  DisplayString
			MAX-ACCESS read-only
			STATUS  current
			DESCRIPTION "The port admin-state."
			::= { mhoStateEntry 4 }

	mhoStateSpeed OBJECT-TYPE
			SYNTAX  DisplayString
			MAX-ACCESS read-only
			STATUS  current
			DESCRIPTION "The physical port speed supported."
			::= { mhoStateEntry 5 }

	mhoSummaryPortIndex OBJECT-TYPE
			SYNTAX  Unsigned32
			MAX-ACCESS not-accessible
			STATUS  current
			DESCRIPTION "The number of the logical port."
			::= { mhoSummaryEntry 1 }

	mhoSummaryPortLabel OBJECT-TYPE
			SYNTAX  DisplayString
			MAX-ACCESS read-only
			STATUS  current
			DESCRIPTION "The number of the physical port."
			::= { mhoSummaryEntry 2 }

	mhoSummaryLinkState OBJECT-TYPE
			SYNTAX  DisplayString
			MAX-ACCESS read-only
			STATUS  current
			DESCRIPTION "The port link-state."
			::= { mhoSummaryEntry 3 }

	mhoSummaryAdminState OBJECT-TYPE
			SYNTAX  DisplayString
			MAX-ACCESS read-only
			STATUS  current
			DESCRIPTION "The port admin-state."
			::= { mhoSummaryEntry 4 }

	mhoSummarySpeed OBJECT-TYPE
			SYNTAX  DisplayString
			MAX-ACCESS read-only
			STATUS  current
			DESCRIPTION "The physical port speed supported."
			::= { mhoSummaryEntry 5 }

	mhoSummaryRxFcsErr OBJECT-TYPE
			SYNTAX  Counter64
			MAX-ACCESS read-only
			STATUS  current
			DESCRIPTION "The number of ingress packages that are not an integral number of octets in length and do not pass the FCS check."
			::= { mhoSummaryEntry 6 }

	mhoSummaryRxErr OBJECT-TYPE
			SYNTAX  Counter64
			MAX-ACCESS read-only
			STATUS  current
			DESCRIPTION "The number of ingress packets that contained errors preventing them from being deliverable to a higher-layer protocol."
			::= { mhoSummaryEntry 7 }

	mhoSummaryRxFrames OBJECT-TYPE
			SYNTAX  Counter64
			MAX-ACCESS read-only
			STATUS  current
			DESCRIPTION "The number of received frames."
			::= { mhoSummaryEntry 8 }

    mhoSummaryRxBytes OBJECT-TYPE
			SYNTAX  Counter64
			MAX-ACCESS read-only
			STATUS  current
			DESCRIPTION "The volume of received data in bytes."
			::= { mhoSummaryEntry 9 }

    mhoSummaryTxErr OBJECT-TYPE
			SYNTAX  Counter64
			MAX-ACCESS read-only
			STATUS  current
			DESCRIPTION "The number of error packets intended to be sent."
			::= { mhoSummaryEntry 10 }

    mhoSummaryTxFrames OBJECT-TYPE
			SYNTAX  Counter64
			MAX-ACCESS read-only
			STATUS  current
			DESCRIPTION "The number of transmitted frames."
			::= { mhoSummaryEntry 11 }

    mhoSummaryTxBytes OBJECT-TYPE
			SYNTAX  Counter64
			MAX-ACCESS read-only
			STATUS  current
			DESCRIPTION "The volume of transmitted data in bytes."
			::= { mhoSummaryEntry 12 }

	mhoACLsUsed OBJECT-TYPE
			SYNTAX  Counter64
			MAX-ACCESS read-only
			STATUS  current
			DESCRIPTION "Number of used ACL rule memory entries."
			::= { mhoAcls 1 }

	mhoACLsTotal OBJECT-TYPE
			SYNTAX  Counter64
			MAX-ACCESS read-only
			STATUS  current
			DESCRIPTION "Orchestrator total amount of ACL rule memory entries."
			::= { mhoAcls 2 }

	mhoACLsAvailable OBJECT-TYPE
			SYNTAX  Counter64
			MAX-ACCESS read-only
			STATUS  current
			DESCRIPTION "Number of free/unused ACL rule memory entries."
			::= { mhoAcls 3 }

	-- End mho statuses:

	-- ips statuses

	ipsStatus OBJECT-TYPE
			SYNTAX  DisplayString
			MAX-ACCESS read-only
			STATUS  current
			DESCRIPTION
				  "ips status (Running/Stopped)"
			::= { ips 1 }

	ipsUpdateStatusInfo OBJECT IDENTIFIER ::= { ips 11 }

	ipsUpdateStatus OBJECT-TYPE
			SYNTAX  DisplayString
			MAX-ACCESS read-only
			STATUS  current
			DESCRIPTION
				  "ips update status"
			::= { ipsUpdateStatusInfo 1 }

	ipsUpdateDescription OBJECT-TYPE
			SYNTAX  DisplayString
			MAX-ACCESS read-only
			STATUS  current
			DESCRIPTION
				  "IPS update description"
			::= { ipsUpdateStatusInfo 2 }

	ipsNextUpdateDescription OBJECT-TYPE
			SYNTAX  DisplayString
			MAX-ACCESS read-only
			STATUS  current
			DESCRIPTION
				  "IPS next update description"
			::= { ipsUpdateStatusInfo 3 }

	ipsDBVersion OBJECT-TYPE
			SYNTAX  DisplayString
			MAX-ACCESS read-only
			STATUS  current
			DESCRIPTION
				  "IPS DB version"
			::= { ipsUpdateStatusInfo 4 }

	ipsState OBJECT-TYPE
			SYNTAX  Unsigned32
			MAX-ACCESS read-only
			STATUS  current
			DESCRIPTION
				  "ips state (0 - ok, 1 - warning, 2 - problem)"
			::= { ips 101 }

	ipsStateShortDesc OBJECT-TYPE
			SYNTAX  DisplayString
			MAX-ACCESS read-only
			STATUS  current
			DESCRIPTION
				  "IPS short state description"
			::= { ips 102 }

	ipsStateLongDesc OBJECT-TYPE
			SYNTAX  DisplayString
			MAX-ACCESS read-only
			STATUS  current
			DESCRIPTION
				  "IPS long state description"
			::= { ips 103 }

	--httpsInspection statuses:

	httpsInspectionStatus OBJECT-TYPE
			SYNTAX  DisplayString
			MAX-ACCESS read-only
			STATUS  current
			DESCRIPTION
				  "HTTPS inspection status (On/Off)"
			::= { httpsInspection 1 }

	httpsInspectionStatusDescription OBJECT-TYPE
			SYNTAX  DisplayString
			MAX-ACCESS read-only
			STATUS  current
			DESCRIPTION
				  "HTTPS inspection status description"
			::= { httpsInspection 2 }

	hsmStatus OBJECT IDENTIFIER ::= { httpsInspection 3 }

	hsmEnabled OBJECT-TYPE
			SYNTAX  DisplayString
			MAX-ACCESS read-only
			STATUS  current
			DESCRIPTION
				  "HSM enabled (Enabled/Disabled)"
			::= { hsmStatus 1 }

	hsmEnabledDescription OBJECT-TYPE
			SYNTAX  DisplayString
			MAX-ACCESS read-only
			STATUS  current
			DESCRIPTION
				  "HSM enabled description"
			::= { hsmStatus 2 }

	hsmPartitionAccess OBJECT-TYPE
			SYNTAX  DisplayString
			MAX-ACCESS read-only
			STATUS  current
			DESCRIPTION
				  "HSM partition access (Accessible/Not Accessible)"
			::= { hsmStatus 3 }

	hsmPartitionAccessDescription OBJECT-TYPE
			SYNTAX  DisplayString
			MAX-ACCESS read-only
			STATUS  current
			DESCRIPTION
				  "HSM partition access description"
			::= { hsmStatus 4 }

	outboundStatus OBJECT-TYPE
			SYNTAX  DisplayString
			MAX-ACCESS read-only
			STATUS  current
			DESCRIPTION
				  "HTTPS inspection outbound status (HSM on/HSM off/HSM error)"
			::= { hsmStatus 5 }

	outboundStatusDescription OBJECT-TYPE
			SYNTAX  DisplayString
			MAX-ACCESS read-only
			STATUS  current
			DESCRIPTION
				  "HTTPS inspection outbound status description"
			::= { hsmStatus 6 }

	-- End httpsInspection statuses:

	--VsecController statuses:


	vsecVsecStatus OBJECT-TYPE
              SYNTAX  DisplayString
              MAX-ACCESS read-only
              STATUS  current
              DESCRIPTION
                      "vSEC Controller status"
              ::= {vsecController 1 }

	vsecNumberOfDisconnectedDataCenters OBJECT-TYPE
              SYNTAX  Unsigned32
              MAX-ACCESS read-only
              STATUS  current
              DESCRIPTION
                      "Number of disconnected data centers"
              ::= {vsecController 2 }

	vsecTotalNumberOfDataCenters OBJECT-TYPE
              SYNTAX  Unsigned32
              MAX-ACCESS read-only
              STATUS  current
              DESCRIPTION
                      "Number of data centers"
              ::= {vsecController 3 }

	vsecTotalNumberOfImportedDataCenterObjects OBJECT-TYPE
              SYNTAX  Unsigned32
              MAX-ACCESS read-only
              STATUS  current
              DESCRIPTION
                      "Number of imported data center objects"
              ::= {vsecController 4 }

	vsecTotalNumberOfGwWithDataCenterObjects OBJECT-TYPE
              SYNTAX  Unsigned32
              MAX-ACCESS read-only
              STATUS  current
              DESCRIPTION
                      "Number of gateways enforcing data center objects"
              ::= {vsecController 5 }

	  vsecDataCenterTable OBJECT-TYPE
              SYNTAX  SEQUENCE OF  VsecDataCenterEntry
			  MAX-ACCESS  not-accessible
			  STATUS  current
			  DESCRIPTION "Data Centers"
			  ::= { vsecController 6 }


	  vsecDataCenterEntry OBJECT-TYPE
	          SYNTAX VsecDataCenterEntry
			  MAX-ACCESS  not-accessible
			  STATUS  current
			  DESCRIPTION "No description available"
			  INDEX   { vsecDataCenterIndex }
			  ::= { vsecDataCenterTable 1 }

	  VsecDataCenterEntry ::=
	          SEQUENCE {
				vsecDataCenterIndex
				      Unsigned32,
				vsecDataCenterName
				      DisplayString,
				vsecDataCenterType
					  DisplayString,
				vsecConnectionStatus
				      DisplayString,
				vsecNumberOfImportedObjects
				      Unsigned32,
				vsecNumberOfAutoUpdate
				      Unsigned32
			  }

      vsecDataCenterIndex OBJECT-TYPE
              SYNTAX  Unsigned32
              MAX-ACCESS not-accessible
              STATUS  current
              DESCRIPTION "No description available"
              ::= { vsecDataCenterEntry 1 }

	 vsecDataCenterName OBJECT-TYPE
              SYNTAX  DisplayString
              MAX-ACCESS read-only
              STATUS  current
              DESCRIPTION "Name"
              ::= { vsecDataCenterEntry 2 }

      vsecDataCenterType OBJECT-TYPE
              SYNTAX  DisplayString
              MAX-ACCESS read-only
              STATUS  current
              DESCRIPTION "Type"
              ::= { vsecDataCenterEntry 3 }

      vsecConnectionStatus OBJECT-TYPE
              SYNTAX  DisplayString
              MAX-ACCESS read-only
              STATUS  current
              DESCRIPTION "ConnectionStatus"
              ::= { vsecDataCenterEntry 4 }

     vsecNumberOfImportedObjects OBJECT-TYPE
              SYNTAX  Unsigned32
              MAX-ACCESS read-only
              STATUS  current
              DESCRIPTION "Imported data center objects"
              ::= { vsecDataCenterEntry 6 }

	   vsecNumberOfAutoUpdate OBJECT-TYPE
              SYNTAX  Unsigned32
              MAX-ACCESS read-only
              STATUS  current
              DESCRIPTION "vSEC Controller update"
              ::= { vsecDataCenterEntry 7 }

		vsecEnforcingGatewaysTable OBJECT-TYPE
              SYNTAX  SEQUENCE OF  VsecEnforcingGatewayEntry
			  MAX-ACCESS  not-accessible
			  STATUS  current
			  DESCRIPTION "Gateways Enforcing Data Center Objects"
			  ::= { vsecController 7 }

		vsecEnforcingGatewayEntry OBJECT-TYPE
	          SYNTAX VsecEnforcingGatewayEntry
			  MAX-ACCESS  not-accessible
			  STATUS  current
			  DESCRIPTION "No description available"
			  INDEX   { vsecGatewayIndex }
			  ::= { vsecEnforcingGatewaysTable 1 }

	  VsecEnforcingGatewayEntry ::=
	          SEQUENCE {
				vsecGatewayIndex
				      Unsigned32,
				vsecGatewayName
				      DisplayString,
				vsecGatewayIP
					  DisplayString,
				vsecGatewayVersion
				      DisplayString,
				vsecGatewayUpdateSucceeded
				      DisplayString
			  }

      vsecGatewayIndex OBJECT-TYPE
              SYNTAX  Unsigned32
              MAX-ACCESS not-accessible
              STATUS  current
              DESCRIPTION "No description available"
              ::= { vsecEnforcingGatewayEntry 1 }

	 vsecGatewayName OBJECT-TYPE
              SYNTAX  DisplayString
              MAX-ACCESS read-only
              STATUS  current
              DESCRIPTION "Name"
              ::= { vsecEnforcingGatewayEntry 2 }

      vsecGatewayIP OBJECT-TYPE
              SYNTAX  DisplayString
              MAX-ACCESS read-only
              STATUS  current
              DESCRIPTION "IP"
              ::= { vsecEnforcingGatewayEntry 3 }

      vsecGatewayVersion OBJECT-TYPE
              SYNTAX  DisplayString
              MAX-ACCESS read-only
              STATUS  current
              DESCRIPTION "Version"
              ::= { vsecEnforcingGatewayEntry 4 }

     vsecGatewayUpdateSucceeded OBJECT-TYPE
              SYNTAX  DisplayString
              MAX-ACCESS read-only
              STATUS  current
              DESCRIPTION "Update Status"
              ::= { vsecEnforcingGatewayEntry 5 }

	-- End VsecController statuses:


	vsxVsSupported OBJECT-TYPE
              SYNTAX  Gauge32
              MAX-ACCESS read-only
              STATUS  current
              DESCRIPTION
                      "The maximum number of supported Virtual Systems"
              ::= {vsx 11 }

	vsxVsConfigured OBJECT-TYPE
              SYNTAX  Gauge32
              MAX-ACCESS read-only
              STATUS  current
              DESCRIPTION
                      "The number of configured Virtual Systems"
              ::= {vsx 12 }

	vsxVsInstalled OBJECT-TYPE
              SYNTAX  Gauge32
              MAX-ACCESS read-only
              STATUS  current
              DESCRIPTION
                      "The number of installed Virtual Systems"
              ::= {vsx 13 }

	vsxVsidConfigured OBJECT-TYPE
              SYNTAX  Unsigned32
              MAX-ACCESS read-only
              STATUS  current
              DESCRIPTION
                      "The number of configured VSIDs"
              ::= {vsx 14 }

	vsxAllVSsConnsSum OBJECT-TYPE
              SYNTAX  Unsigned32
              MAX-ACCESS read-only
              STATUS  current
              DESCRIPTION
                      "The sum of current connections on all VSs"
              ::= {vsx 15 }

	vsxStatus OBJECT IDENTIFIER ::= { vsx 22 }

	 vsxStatusTable OBJECT-TYPE
	          SYNTAX  SEQUENCE OF  VsxStatusEntry
			  MAX-ACCESS  not-accessible
			  STATUS  current
			  DESCRIPTION
                      "No description available"
			   ::= { vsxStatus 1 }

	vsxStatusEntry OBJECT-TYPE
	          SYNTAX  VsxStatusEntry
	          MAX-ACCESS  not-accessible
	          STATUS  current
	          DESCRIPTION
                      "No description available"
		      INDEX { vsxStatusVSId }
	          ::= { vsxStatusTable 1 }

     VsxStatusEntry ::=
              SEQUENCE {
                 vsxStatusVSId
                      INTEGER,
                 vsxStatusVRId
                      INTEGER,
                 vsxStatusVsName
                      DisplayString,
                 vsxStatusVsType
                      DisplayString,
                 vsxStatusMainIP
                      DisplayString,
                 vsxStatusPolicyName
                      DisplayString,
                 vsxStatusVsPolicyType
                      DisplayString,
                 vsxStatusSicTrustState
                      DisplayString,
                 vsxStatusHAState
                      DisplayString,
                 vsxStatusVSWeight
                      Gauge32
              }

      vsxStatusVSId OBJECT-TYPE
            SYNTAX  Integer32 (0..250)
            MAX-ACCESS not-accessible
            STATUS  current
            DESCRIPTION
                    "Virtual System ID"
            ::= { vsxStatusEntry 1 }

      vsxStatusVRId OBJECT-TYPE
            SYNTAX  Integer32 (0..250)
            MAX-ACCESS read-only
            STATUS  current
            DESCRIPTION
                    "Operating System ID (VSID)"
            ::= { vsxStatusEntry 2 }

      vsxStatusVsName OBJECT-TYPE
            SYNTAX  DisplayString
            MAX-ACCESS read-only
            STATUS  current
            DESCRIPTION
                     "Virtual System's name"
            ::= { vsxStatusEntry 3 }

      vsxStatusVsType OBJECT-TYPE
            SYNTAX  DisplayString
            MAX-ACCESS read-only
            STATUS  current
            DESCRIPTION
                     "Virtual System's type"
            ::= { vsxStatusEntry 4 }

      vsxStatusMainIP OBJECT-TYPE
            SYNTAX  DisplayString
            MAX-ACCESS read-only
            STATUS  current
            DESCRIPTION
                    "Virtual System's Main IP"
            ::= { vsxStatusEntry 5 }

      vsxStatusPolicyName OBJECT-TYPE
            SYNTAX  DisplayString
            MAX-ACCESS read-only
            STATUS  current
            DESCRIPTION
                    "Security Policy name"
            ::= { vsxStatusEntry 6 }

      vsxStatusVsPolicyType OBJECT-TYPE
            SYNTAX  DisplayString
            MAX-ACCESS read-only
            STATUS  current
            DESCRIPTION
                    "Security Policy type"
            ::= { vsxStatusEntry 7 }

      vsxStatusSicTrustState OBJECT-TYPE
            SYNTAX  DisplayString
            MAX-ACCESS read-only
            STATUS  current
            DESCRIPTION
                    "SIC status"
            ::= { vsxStatusEntry 8 }

      vsxStatusHAState OBJECT-TYPE
            SYNTAX  DisplayString (SIZE (0..255))
            MAX-ACCESS read-only
            STATUS  current
            DESCRIPTION
                "High Availability Status"
            ::= { vsxStatusEntry 9 }

      vsxStatusVSWeight OBJECT-TYPE
            SYNTAX  Gauge32
            MAX-ACCESS read-only
            STATUS  current
            DESCRIPTION
                "Virtual System Resource Control Weight"
            ::= { vsxStatusEntry 10 }


	  vsxStatusMemoryUsageTable OBJECT-TYPE
		  SYNTAX  SEQUENCE OF  VsxStatusMemoryUsageEntry
		  MAX-ACCESS  not-accessible
		  STATUS  current
		  DESCRIPTION "VS memory usage table per-VS."
		   ::= { vsxStatus 3 }

		vsxStatusMemoryUsageEntry OBJECT-TYPE
		          SYNTAX  VsxStatusMemoryUsageEntry
		          MAX-ACCESS  not-accessible
		          STATUS  current
		          DESCRIPTION "No description available"
			      INDEX { vsxStatusMemoryUsageVSId }
		          ::= { vsxStatusMemoryUsageTable 1 }

	    VsxStatusMemoryUsageEntry ::=
	              SEQUENCE {
					vsxStatusMemoryUsageVSId 	INTEGER,
					vsxStatusMemoryUsageVSName 	DisplayString,
					vsxStatusMemoryUsage 		Counter64,
					vsxStatusMemoryUsageVSMaxMem Counter64
	                      }

      vsxStatusMemoryUsageVSId OBJECT-TYPE
              SYNTAX  Integer32(0..250)
              MAX-ACCESS not-accessible
              STATUS  current
              DESCRIPTION "Virtual System ID"
              ::= { vsxStatusMemoryUsageEntry 1 }

      vsxStatusMemoryUsageVSName OBJECT-TYPE
              SYNTAX  DisplayString
              MAX-ACCESS read-only
              STATUS  current
              DESCRIPTION "Virtual-System name"
              ::= { vsxStatusMemoryUsageEntry 2 }

      vsxStatusMemoryUsage OBJECT-TYPE
              SYNTAX  Counter64
              MAX-ACCESS read-only
              STATUS  current
              DESCRIPTION "VS memory usage (Bytes)"
              ::= { vsxStatusMemoryUsageEntry 3 }

      vsxStatusMemoryUsageVSMaxMem OBJECT-TYPE
              SYNTAX  Counter64
              MAX-ACCESS read-only
              STATUS  current
              DESCRIPTION "Maximum memory possible for allocation to the vs (Bytes)"
              ::= { vsxStatusMemoryUsageEntry 4 }



	vsxStatusInterfacesTable OBJECT-TYPE
		  SYNTAX  SEQUENCE OF  VsxStatusInterfacesEntry
		  MAX-ACCESS  not-accessible
		  STATUS  current
		  DESCRIPTION "Interfaces table per VS"
		   ::= { vsxStatus 5 }

		vsxStatusInterfacesEntry OBJECT-TYPE
		          SYNTAX  VsxStatusInterfacesEntry
		          MAX-ACCESS  not-accessible
		          STATUS  current
		          DESCRIPTION "No description available"
			      INDEX { vsxStatusInterfaceVSID }
		          ::= { vsxStatusInterfacesTable 1 }

	     VsxStatusInterfacesEntry ::=
	              SEQUENCE {
					vsxStatusInterfaceVSID 			INTEGER,
					vsxStatusInterfaceVSName 		DisplayString,
					vsxStatusInterfaceIfName 		DisplayString,
					vsxStatusInterfaceAdminState	INTEGER,
					vsxStatusInterfaceOperState		INTEGER,
					vsxStatusInterfaceRxBytes 		Counter64,
					vsxStatusInterfaceTxBytes 		Counter64,
					vsxStatusInterfaceOverallBytes 	Counter64,
					vsxStatusInterfaceRxErrors 		Counter64,
					vsxStatusInterfaceTxErrors 		Counter64
	                      }

      vsxStatusInterfaceVSID OBJECT-TYPE
              SYNTAX  Integer32 (0..250)
              MAX-ACCESS not-accessible
              STATUS  current
              DESCRIPTION "Virtual-System ID"
              ::= { vsxStatusInterfacesEntry 1 }

      vsxStatusInterfaceVSName OBJECT-TYPE
              SYNTAX  DisplayString
              MAX-ACCESS read-only
              STATUS  current
              DESCRIPTION "Virtual-System name"
              ::= { vsxStatusInterfacesEntry 2 }

      vsxStatusInterfaceIfName OBJECT-TYPE
              SYNTAX  DisplayString
              MAX-ACCESS read-only
              STATUS  current
              DESCRIPTION "Interface name"
              ::= { vsxStatusInterfacesEntry 3 }

	  vsxStatusInterfaceAdminState OBJECT-TYPE
			  SYNTAX  INTEGER {
					up(1),
					down(2)
              }
				MAX-ACCESS  read-only
				STATUS  current
				DESCRIPTION
						"The desired state of the interface."
			  ::= { vsxStatusInterfacesEntry 4 }

	  vsxStatusInterfaceOperState OBJECT-TYPE
			  SYNTAX  INTEGER {
                   up(1),       -- ready to pass packets
                   down(2)
              }
				MAX-ACCESS  read-only
				STATUS  current
				DESCRIPTION
						"The current operational state of the interface."
			  ::= { vsxStatusInterfacesEntry 5 }

      vsxStatusInterfaceRxBytes OBJECT-TYPE
              SYNTAX  Counter64
              MAX-ACCESS read-only
              STATUS  current
              DESCRIPTION "RX Bytes"
              ::= { vsxStatusInterfacesEntry 6 }

      vsxStatusInterfaceTxBytes OBJECT-TYPE
              SYNTAX  Counter64
              MAX-ACCESS read-only
              STATUS  current
              DESCRIPTION "TX Bytes"
              ::= { vsxStatusInterfacesEntry 7 }

      vsxStatusInterfaceOverallBytes OBJECT-TYPE
              SYNTAX  Counter64
              MAX-ACCESS read-only
              STATUS  current
              DESCRIPTION "Overall Bytes"
              ::= { vsxStatusInterfacesEntry 8 }

      vsxStatusInterfaceRxErrors OBJECT-TYPE
              SYNTAX  Counter64
              MAX-ACCESS read-only
              STATUS  current
              DESCRIPTION "RX Erros"
              ::= { vsxStatusInterfacesEntry 9 }

      vsxStatusInterfaceTxErrors OBJECT-TYPE
              SYNTAX  Counter64
              MAX-ACCESS read-only
              STATUS  current
              DESCRIPTION "TX Erros"
              ::= { vsxStatusInterfacesEntry 10 }

      vsxCounters OBJECT IDENTIFIER ::= { vsx 23 }

	vsxCountersTable OBJECT-TYPE
	          SYNTAX  SEQUENCE OF  VsxCountersEntry
			  MAX-ACCESS  not-accessible
			  STATUS  current
			  DESCRIPTION
                      "No description available"
			   ::= { vsxCounters 1 }

	vsxCountersEntry OBJECT-TYPE
	          SYNTAX  VsxCountersEntry
	          MAX-ACCESS  not-accessible
	          STATUS  current
	          DESCRIPTION
                      "No description available"
		      INDEX { vsxStatusVSId }
	          ::= { vsxCountersTable 1 }

     VsxCountersEntry ::=
              SEQUENCE {
                 vsxCountersVSId
                      INTEGER,
                 vsxCountersConnNum
                      Gauge32,
                 vsxCountersConnPeakNum
                      Gauge32,
                 vsxCountersConnTableLimit
                      Gauge32,
                 vsxCountersPackets
                      Counter64,
                 vsxCountersDroppedTotal
                      Counter64,
                 vsxCountersAcceptedTotal
		      		  Counter64,
                 vsxCountersRejectedTotal
     		      	  Counter64,
                 vsxCountersBytesAcceptedTotal
                      Counter64,
                 vsxCountersBytesDroppedTotal
                      Counter64,
                 vsxCountersBytesRejectedTotal
                      Counter64,
                 vsxCountersLoggedTotal
                      Counter64,
                 vsxCountersIsDataValid
                      INTEGER
              }

      vsxCountersVSId OBJECT-TYPE
            SYNTAX  Integer32 (0..250)
            MAX-ACCESS read-only
            STATUS  current
            DESCRIPTION
                    "Virtual System ID"
            ::= { vsxCountersEntry 1 }

      vsxCountersConnNum OBJECT-TYPE
            SYNTAX  Gauge32
            MAX-ACCESS read-only
            STATUS  current
            DESCRIPTION
                    "Number of active connections"
            ::= { vsxCountersEntry 2 }

      vsxCountersConnPeakNum OBJECT-TYPE
            SYNTAX  Gauge32
            MAX-ACCESS read-only
            STATUS  current
            DESCRIPTION
                    "Peak number of active connections"
            ::= { vsxCountersEntry 3 }

      vsxCountersConnTableLimit OBJECT-TYPE
            SYNTAX  Gauge32
            MAX-ACCESS read-only
            STATUS  current
            DESCRIPTION
                    "Connection table limit"
            ::= { vsxCountersEntry 4 }

      vsxCountersPackets OBJECT-TYPE
            SYNTAX  Counter64
            MAX-ACCESS read-only
            STATUS  current
            DESCRIPTION
                    "Total number of packets processed"
            ::= { vsxCountersEntry 5 }


	vsxS2SIpsecTunnels OBJECT IDENTIFIER ::= { vsx 31 }

	vsxS2SIpsecTunnelsTable OBJECT-TYPE
	          SYNTAX  SEQUENCE OF  VsxS2SIpsecTunnelsEntry
			  MAX-ACCESS  not-accessible
			  STATUS  current
			  DESCRIPTION
                      "OID to present the number of S2S Ipsec tunnels for each VS"
			   ::= { vsxS2SIpsecTunnels 1 }


	vsxS2SIpsecTunnelsEntry OBJECT-TYPE
		  SYNTAX  VsxS2SIpsecTunnelsEntry
		  MAX-ACCESS  not-accessible
		  STATUS  current
		  DESCRIPTION
				  "No description available"
		  INDEX { vsxStatusVSId }
		  ::= { vsxS2SIpsecTunnelsTable 1 }

     VsxS2SIpsecTunnelsEntry ::=
              SEQUENCE {
                 vsxTunnelsVSidName
                      DisplayString,
                 vsxS2SIpsecTunnelsCounter
                      Unsigned32
              }

      vsxTunnelsVSidName OBJECT-TYPE
            SYNTAX  DisplayString
            MAX-ACCESS read-only
            STATUS  current
            DESCRIPTION
                    "VS id and name"
            ::= { vsxS2SIpsecTunnelsEntry 1 }


      vsxS2SIpsecTunnelsCounter OBJECT-TYPE
            SYNTAX  Unsigned32
            MAX-ACCESS read-only
            STATUS  current
            DESCRIPTION
                    "counter for all active S2S tunnels, accumulating  ipv4 ipv6, ike1 & ike2"
            ::= { vsxS2SIpsecTunnelsEntry 2 }

	vsxVSStateChanged OBJECT IDENTIFIER ::= { vsx 32 }

	vsxVSStateChangedTable OBJECT-TYPE
	          SYNTAX  SEQUENCE OF  VsxVSStateChangedEntry
			  MAX-ACCESS  not-accessible
			  STATUS  current
			  DESCRIPTION
                      "OID to detect the change of a VS state when it occurs. The value will be 0 if no change occurred in the defined time window, otherwise the value will be 1."
			   ::= { vsxVSStateChanged 1 }


	vsxVSStateChangedEntry OBJECT-TYPE
		  SYNTAX  VsxVSStateChangedEntry
		  MAX-ACCESS  not-accessible
		  STATUS  current
		  DESCRIPTION
				  "No description available"
		  INDEX { vsxStatusVSId }
		  ::= { vsxVSStateChangedTable 1 }

     VsxVSStateChangedEntry ::=
              SEQUENCE {
                 vsxVSStateChangedVSIdName
                      DisplayString,
                 vsxVSStateChangedChangeOccurred
                      Unsigned32
              }

      vsxVSStateChangedVSIdName OBJECT-TYPE
            SYNTAX  DisplayString
            MAX-ACCESS read-only
            STATUS  current
            DESCRIPTION
                    "VS id and name"
            ::= { vsxVSStateChangedEntry 1 }

      vsxVSStateChangedChangeOccurred OBJECT-TYPE
            SYNTAX  Unsigned32
            MAX-ACCESS read-only
            STATUS  current
            DESCRIPTION
                    "Indicator whether the VS changed its state in the time window"
            ::= { vsxVSStateChangedEntry 2 }


      vsxCountersDroppedTotal OBJECT-TYPE
            SYNTAX  Counter64
            MAX-ACCESS read-only
            STATUS  current
            DESCRIPTION
                    "Total number of dropped packets"
            ::= { vsxCountersEntry 6 }

      vsxCountersAcceptedTotal OBJECT-TYPE
            SYNTAX  Counter64
            MAX-ACCESS read-only
            STATUS  current
            DESCRIPTION
                    "Total number of accepted packets"
            ::= { vsxCountersEntry 7 }

      vsxCountersRejectedTotal OBJECT-TYPE
            SYNTAX  Counter64
            MAX-ACCESS read-only
            STATUS  current
            DESCRIPTION
                    "Total number of rejected packets"
            ::= { vsxCountersEntry 8 }

      vsxCountersBytesAcceptedTotal OBJECT-TYPE
            SYNTAX  Counter64
            MAX-ACCESS read-only
            STATUS  current
            DESCRIPTION
                    "Total number of accepted bytes"
            ::= { vsxCountersEntry 9 }

      vsxCountersBytesDroppedTotal OBJECT-TYPE
            SYNTAX  Counter64
            MAX-ACCESS read-only
            STATUS  current
            DESCRIPTION
                    "Total number of dropped bytes"
            ::= { vsxCountersEntry 10 }

      vsxCountersBytesRejectedTotal OBJECT-TYPE
            SYNTAX  Counter64
            MAX-ACCESS read-only
            STATUS  current
            DESCRIPTION
                    "Total number of rejected bytes"
            ::= { vsxCountersEntry 11 }

      vsxCountersLoggedTotal OBJECT-TYPE
            SYNTAX  Counter64
            MAX-ACCESS read-only
            STATUS  current
            DESCRIPTION
                    "Total number of logs sent"
            ::= { vsxCountersEntry 12 }

      vsxCountersIsDataValid OBJECT-TYPE
            SYNTAX  Integer32
            MAX-ACCESS read-only
            STATUS  current
            DESCRIPTION
                    "Data validity indicator
					 invalid(0)
					 valid(1)"
            ::= { vsxCountersEntry 13 }

      vsxCountersDropTable OBJECT-TYPE
	          SYNTAX  SEQUENCE OF  VsxCountersDropEntry
			  MAX-ACCESS  not-accessible
			  STATUS  current
			  DESCRIPTION
                      "No description available"
			   ::= { vsxCounters 2 }

	vsxCountersDropEntry OBJECT-TYPE
	          SYNTAX  VsxCountersDropEntry
	          MAX-ACCESS  not-accessible
	          STATUS  current
	          DESCRIPTION
                      "No description available"
		      INDEX { vsxStatusVSId }
	          ::= { vsxCountersDropTable 1 }

     VsxCountersDropEntry ::=
              SEQUENCE {
                 vsxCountersDropVSID
                      INTEGER,
                 vsxCountersDropVsName
                      DisplayString,
                 vsxCountersDropCount
                      Counter64
              }

      vsxCountersDropVSID OBJECT-TYPE
            SYNTAX  Integer32 (0..250)
            MAX-ACCESS read-only
            STATUS  current
            DESCRIPTION
                    "Virtual System ID"
            ::= { vsxCountersDropEntry 1 }

      vsxCountersDropVsName OBJECT-TYPE
            SYNTAX  DisplayString
            MAX-ACCESS read-only
            STATUS  current
            DESCRIPTION
                     "Virtual System's name"
            ::= { vsxCountersDropEntry 2 }

      vsxCountersDropCount OBJECT-TYPE
            SYNTAX  Counter64
            MAX-ACCESS read-only
            STATUS  current
            DESCRIPTION
                     "Virtual System's drops due to instance fully utilized"
            ::= { vsxCountersDropEntry 3 }


	  raUsersTable OBJECT-TYPE
	          SYNTAX  SEQUENCE OF  RaUsersEntry
			  MAX-ACCESS  not-accessible
			  STATUS  current
              DESCRIPTION
                      "A table containing Remote Access users tunnel information."
			   ::= { tables 9000 }


	  raUsersEntry OBJECT-TYPE
	          SYNTAX  RaUsersEntry
	          MAX-ACCESS  not-accessible
	          STATUS  current
	          DESCRIPTION "No description available"
	          INDEX   { raInternalIpAddr }
	          ::= { raUsersTable 1 }

      RaUsersEntry ::=
              SEQUENCE {
                 raInternalIpAddr
                      IpAddress,
                 raExternalIpAddr
                      IpAddress,
                 raUserState
                      INTEGER,
                 raOfficeMode
                      INTEGER,
                 raIkeOverTCP
                      INTEGER,
                 raUseUDPEncap
                      INTEGER,
                 raVisitorMode
				      INTEGER,
     		     raRouteTraffic
     		          INTEGER,
     		     raCommunity
     		          DisplayString,
     		     raTunnelEncAlgorithm
     		          INTEGER,
     		     raTunnelAuthMethod
     		          INTEGER,
     		     raLogonTime
     		          INTEGER
              }

      raInternalIpAddr OBJECT-TYPE
            SYNTAX  IpAddress
            MAX-ACCESS not-accessible
            STATUS  current
            DESCRIPTION "No description available"
            ::= { raUsersEntry 1 }

      raExternalIpAddr OBJECT-TYPE
            SYNTAX  IpAddress
            MAX-ACCESS read-only
            STATUS  current
            DESCRIPTION "No description available"
            ::= { raUsersEntry 19 }

      raUserState OBJECT-TYPE
            SYNTAX  Integer32
            MAX-ACCESS  read-write
            STATUS  current
            DESCRIPTION "No description available"
            ::= { raUsersEntry 20 }

      raOfficeMode OBJECT-TYPE
            SYNTAX  Integer32
            MAX-ACCESS read-only
            STATUS  current
            DESCRIPTION "No description available"
            ::= { raUsersEntry 21 }

      raIkeOverTCP OBJECT-TYPE
            SYNTAX  Integer32
            MAX-ACCESS read-only
            STATUS  current
            DESCRIPTION "No description available"
            ::= { raUsersEntry 22 }

      raUseUDPEncap OBJECT-TYPE
            SYNTAX  Integer32
            MAX-ACCESS read-only
            STATUS  current
            DESCRIPTION "No description available"
            ::= { raUsersEntry 23 }

      raVisitorMode OBJECT-TYPE
            SYNTAX  Integer32
            MAX-ACCESS read-only
            STATUS  current
            DESCRIPTION "No description available"
            ::= { raUsersEntry 24 }

      raRouteTraffic OBJECT-TYPE
            SYNTAX  Integer32
            MAX-ACCESS read-only
            STATUS  current
            DESCRIPTION "No description available"
            ::= { raUsersEntry 25 }

      raCommunity OBJECT-TYPE
            SYNTAX  DisplayString
            MAX-ACCESS read-only
            STATUS  current
            DESCRIPTION "No description available"
            ::= { raUsersEntry 26 }

      raTunnelEncAlgorithm OBJECT-TYPE
            SYNTAX  INTEGER {
                          espDES(1),
                          esp3DES(2),
                          espCAST(5),
                          esp3IDEA(7),
                          espNULL(9),
                          espAES128(129),
                          espAES256(130)
             		}
            MAX-ACCESS read-only
            STATUS  current
            DESCRIPTION "No description available"
            ::= { raUsersEntry 27 }

      raTunnelAuthMethod OBJECT-TYPE
            SYNTAX  INTEGER {
                          preshared-key(1),
                          dss-signature(2),
                          rsa-signature(3),
                          rsa-encryption(4),
                          rev-rsa-encryption(5),
                          xauth(129),
                          crack(130)
             		}
            MAX-ACCESS read-only
            STATUS  current
            DESCRIPTION "No description available"
            ::= { raUsersEntry 28 }

      raLogonTime OBJECT-TYPE
            SYNTAX  Integer32
            MAX-ACCESS read-only
            STATUS  current
            DESCRIPTION "No description available"
            ::= { raUsersEntry 29 }

	  tunnelTable OBJECT-TYPE
	          SYNTAX  SEQUENCE OF  TunnelEntry
			  MAX-ACCESS  not-accessible
			  STATUS  current
              DESCRIPTION
                      "A table containing VPN tunnel information."
			   ::= { tables 9002 }


	  tunnelEntry OBJECT-TYPE
	          SYNTAX  TunnelEntry
	          MAX-ACCESS  not-accessible
	          STATUS  current
	          DESCRIPTION "No description available"
	          INDEX   { tunnelPeerIpAddr }
	          ::= { tunnelTable 1 }

      TunnelEntry ::=
              SEQUENCE {
                 tunnelPeerIpAddr
                      IpAddress,
                 tunnelPeerObjName
                      DisplayString,
                 tunnelState
                      INTEGER,
                 tunnelCommunity
                      DisplayString,
                 tunnelNextHop
                      IpAddress,
                 tunnelInterface
                      DisplayString,
                 tunnelSourceIpAddr
                      IpAddress,
                 tunnelLinkPriority
                      INTEGER,
                 tunnelProbState
                      INTEGER,
                 tunnelPeerType
                      INTEGER,
                 tunnelType
                      INTEGER
              }

      tunnelPeerIpAddr OBJECT-TYPE
            SYNTAX  IpAddress
            MAX-ACCESS not-accessible
            STATUS  current
            DESCRIPTION "No description available"
            ::= { tunnelEntry 1 }

      tunnelPeerObjName OBJECT-TYPE
            SYNTAX  DisplayString
            MAX-ACCESS read-only
            STATUS  current
            DESCRIPTION "No description available"
            ::= { tunnelEntry 2 }

      tunnelState OBJECT-TYPE
            SYNTAX  INTEGER {
                          active(3),
                          destroy(4),
                          idle(129),
                          phase1(130),
                          down(131),
                          init(132)
             		}
            MAX-ACCESS  read-write
            STATUS  current
            DESCRIPTION "No description available"
            ::= { tunnelEntry 3 }

      tunnelCommunity OBJECT-TYPE
            SYNTAX  DisplayString
            MAX-ACCESS read-only
            STATUS  current
            DESCRIPTION "No description available"
            ::= { tunnelEntry 4 }

      tunnelNextHop OBJECT-TYPE
            SYNTAX  IpAddress
            MAX-ACCESS read-only
            STATUS  current
            DESCRIPTION "No description available"
            ::= { tunnelEntry 5 }

      tunnelInterface OBJECT-TYPE
            SYNTAX  DisplayString
            MAX-ACCESS read-only
            STATUS  current
            DESCRIPTION "No description available"
            ::= { tunnelEntry 6 }

      tunnelSourceIpAddr OBJECT-TYPE
            SYNTAX  IpAddress
            MAX-ACCESS read-only
            STATUS  current
            DESCRIPTION "No description available"
            ::= { tunnelEntry 7 }

      tunnelLinkPriority OBJECT-TYPE
            SYNTAX  INTEGER {
                          primary(0),
                          backup(1),
                          on-demand(2)
             		}
            MAX-ACCESS read-only
            STATUS  current
            DESCRIPTION "No description available"
            ::= { tunnelEntry 8 }

      tunnelProbState OBJECT-TYPE
            SYNTAX  INTEGER {
                          unknown(0),
                          alive(1),
                          dead(2)
             		}
            MAX-ACCESS read-only
            STATUS  current
            DESCRIPTION "No description available"
            ::= { tunnelEntry 9 }

      tunnelPeerType OBJECT-TYPE
            SYNTAX  INTEGER {
                          regular(1),
                          daip(2),
                          robo(3),
			  lsv(4)
             		}
            MAX-ACCESS read-only
            STATUS  current
            DESCRIPTION "No description available"
            ::= { tunnelEntry 10 }

      tunnelType OBJECT-TYPE
            SYNTAX  INTEGER {
                          regular(1),
                          permanent(2)
             		}
            MAX-ACCESS read-only
            STATUS  current
            DESCRIPTION "No description available"
            ::= { tunnelEntry 11 }

	  permanentTunnelTable OBJECT-TYPE
	          SYNTAX  SEQUENCE OF  PermanentTunnelEntry
			  MAX-ACCESS  not-accessible
			  STATUS  current
              DESCRIPTION
                      "A table containing VPN permanent tunnel information."
			   ::= { tables 9003 }


	  permanentTunnelEntry OBJECT-TYPE
	          SYNTAX  PermanentTunnelEntry
	          MAX-ACCESS  not-accessible
	          STATUS  current
	          DESCRIPTION "No description available"
	          INDEX   { permanentTunnelPeerIpAddr }
	          ::= { permanentTunnelTable 1 }

      PermanentTunnelEntry ::=
              SEQUENCE {
                 permanentTunnelPeerIpAddr
                      IpAddress,
                 permanentTunnelPeerObjName
                      DisplayString,
                 permanentTunnelState
                      INTEGER,
                 permanentTunnelCommunity
                      DisplayString,
                 permanentTunnelNextHop
                      IpAddress,
                 permanentTunnelInterface
                      IpAddress,
                 permanentTunnelSourceIpAddr
                      IpAddress,
                 permanentTunnelLinkPriority
                      INTEGER,
                 permanentTunnelProbState
                      INTEGER,
                 permanentTunnelPeerType
                      INTEGER
              }

      permanentTunnelPeerIpAddr OBJECT-TYPE
            SYNTAX  IpAddress
            MAX-ACCESS not-accessible
            STATUS  current
            DESCRIPTION "No description available"
            ::= { permanentTunnelEntry 1 }

      permanentTunnelPeerObjName OBJECT-TYPE
            SYNTAX  DisplayString
            MAX-ACCESS read-only
            STATUS  current
            DESCRIPTION "No description available"
            ::= { permanentTunnelEntry 2 }

      permanentTunnelState OBJECT-TYPE
            SYNTAX  INTEGER {
                          active(3),
                          destroy(4),
                          idle(129),
                          phase1(130),
                          down(131),
                          init(132)
             		}
            MAX-ACCESS  read-write
            STATUS  current
            DESCRIPTION "No description available"
            ::= { permanentTunnelEntry 3 }

      permanentTunnelCommunity OBJECT-TYPE
            SYNTAX  DisplayString
            MAX-ACCESS read-only
            STATUS  current
            DESCRIPTION "No description available"
            ::= { permanentTunnelEntry 4 }

      permanentTunnelNextHop OBJECT-TYPE
            SYNTAX  IpAddress
            MAX-ACCESS read-only
            STATUS  current
            DESCRIPTION "No description available"
            ::= { permanentTunnelEntry 5 }

      permanentTunnelInterface OBJECT-TYPE
            SYNTAX  IpAddress
            MAX-ACCESS read-only
            STATUS  current
            DESCRIPTION "No description available"
            ::= { permanentTunnelEntry 6 }

      permanentTunnelSourceIpAddr OBJECT-TYPE
            SYNTAX  IpAddress
            MAX-ACCESS read-only
            STATUS  current
            DESCRIPTION "No description available"
            ::= { permanentTunnelEntry 7 }

      permanentTunnelLinkPriority OBJECT-TYPE
            SYNTAX  INTEGER {
                          primary(0),
                          backup(1),
                          on-demand(2)
             		}
            MAX-ACCESS read-only
            STATUS  current
            DESCRIPTION "No description available"
            ::= { permanentTunnelEntry 8 }

      permanentTunnelProbState OBJECT-TYPE
            SYNTAX  INTEGER {
                          unknown(0),
                          alive(1),
                          dead(2)
             		}
            MAX-ACCESS read-only
            STATUS  current
            DESCRIPTION "No description available"
            ::= { permanentTunnelEntry 9 }

      permanentTunnelPeerType OBJECT-TYPE
            SYNTAX  INTEGER {
                          regular(1),
                          daip(2),
                          robo(3)
             		}
            MAX-ACCESS read-only
            STATUS  current
            DESCRIPTION "No description available"
            ::= { permanentTunnelEntry 10 }

	  -- the FW group
	  -- Overall statistics and state


	  fwPolicyStat  OBJECT IDENTIFIER ::= { fw 25 }
      fwPerfStat    OBJECT IDENTIFIER ::= { fw 26 }

	  fwHmem      OBJECT IDENTIFIER ::= { fwPerfStat 1 }
	  fwKmem      OBJECT IDENTIFIER ::= { fwPerfStat 2 }
	  fwInspect   OBJECT IDENTIFIER ::= { fwPerfStat 3 }
	  fwCookies   OBJECT IDENTIFIER ::= { fwPerfStat 4 }
	  fwChains    OBJECT IDENTIFIER ::= { fwPerfStat 5 }
	  fwFragments OBJECT IDENTIFIER ::= { fwPerfStat 6 }
	  fwUfp       OBJECT IDENTIFIER ::= { fwPerfStat 8 }
	  fwSS        OBJECT IDENTIFIER ::= { fwPerfStat 9 }
	  fwConnectionsStat OBJECT IDENTIFIER ::= { fwPerfStat 11 }
	  fwHmem64 OBJECT IDENTIFIER ::= { fwPerfStat 12 }
	  fwSS-http   OBJECT IDENTIFIER ::= { fwSS 1 }
	  fwSS-ftp    OBJECT IDENTIFIER ::= { fwSS 2 }
	  fwSS-telnet OBJECT IDENTIFIER ::= { fwSS 3 }
	  fwSS-rlogin OBJECT IDENTIFIER ::= { fwSS 4 }
	  fwSS-ufp    OBJECT IDENTIFIER ::= { fwSS 5 }
	  fwSS-smtp   OBJECT IDENTIFIER ::= { fwSS 6 }
	  fwSS-POP3	  OBJECT IDENTIFIER ::= { fwSS 7 }
	  fwSS-av-total	  OBJECT IDENTIFIER ::= { fwSS 10 }


	  fwModuleState OBJECT-TYPE
              SYNTAX  DisplayString (SIZE (0..255))
              MAX-ACCESS read-only
              STATUS  current
              DESCRIPTION
                      "The state of the fw module"
              ::= { fw 1 }

	  fwFilterName OBJECT-TYPE
              SYNTAX  DisplayString (SIZE (0..255))
              MAX-ACCESS read-only
              STATUS  current
              DESCRIPTION
                      "The name of the loaded filter"
              ::= { fw 2 }

	  fwFilterDate OBJECT-TYPE
              SYNTAX  DisplayString (SIZE (0..255))
              MAX-ACCESS read-only
              STATUS  current
              DESCRIPTION
                      "Install time"
              ::= { fw 3 }

	  fwAccepted OBJECT-TYPE
              SYNTAX  Unsigned32
              MAX-ACCESS read-only
              STATUS  current
              DESCRIPTION
                      "The number of accepted packets."
              ::= { fw 4 }

	  fwRejected OBJECT-TYPE
              SYNTAX  Unsigned32
              MAX-ACCESS read-only
              STATUS  current
              DESCRIPTION
                      "The number of rejected  packets."
              ::= { fw 5 }

	  fwDropped OBJECT-TYPE
              SYNTAX  Unsigned32
              MAX-ACCESS read-only
              STATUS  current
              DESCRIPTION
                      "The number of dropped packets."
              ::= { fw 6 }

	  fwLogged OBJECT-TYPE
              SYNTAX  Unsigned32
              MAX-ACCESS read-only
              STATUS  current
              DESCRIPTION
                      "The number of logged packets."
              ::= { fw 7 }

	  fwMajor OBJECT-TYPE
              SYNTAX  Gauge32
              MAX-ACCESS read-only
              STATUS  current
              DESCRIPTION
                      "Major version"
              ::= { fw 8 }

	  fwMinor OBJECT-TYPE
              SYNTAX  Gauge32
              MAX-ACCESS read-only
              STATUS  current
              DESCRIPTION
                      "Minor version"
              ::= { fw 9 }

	  fwProduct OBJECT-TYPE
              SYNTAX  DisplayString (SIZE (0..255))
              MAX-ACCESS read-only
              STATUS  current
              DESCRIPTION
                      "Product name"
              ::= { fw 10 }

	  fwSICTrustState OBJECT-TYPE
              SYNTAX  Unsigned32
              MAX-ACCESS read-only
              STATUS  current
              DESCRIPTION
                      "SIC Trust State : Possible values include:
                                            Not initialized 0
                                            Initialized but not established 1
                                            Established 2
                                            Error 3
                                            Unknown 4"

              ::= { fw 12 }

      fwProdName OBJECT-TYPE
              SYNTAX  DisplayString (SIZE (0..255))
              MAX-ACCESS read-only
              STATUS  current
              DESCRIPTION
                      "Product name"
             ::= { fw 21 }

	  fwVerMajor OBJECT-TYPE
              SYNTAX  Gauge32
              MAX-ACCESS read-only
              STATUS  current
              DESCRIPTION
                      "Major version"
              ::= { fw 22 }

	  fwVerMinor OBJECT-TYPE
              SYNTAX  Gauge32
              MAX-ACCESS read-only
              STATUS  current
              DESCRIPTION
                      "Minor version"
              ::= { fw 23 }

	  fwKernelBuild OBJECT-TYPE
              SYNTAX  Unsigned32
              MAX-ACCESS read-only
              STATUS  current
              DESCRIPTION
                      "Kernel build num"
              ::= { fw 24 }

	  fwPolicyName OBJECT-TYPE
	  		  SYNTAX  DisplayString (SIZE (0..255))
	  		  MAX-ACCESS read-only
	  		  STATUS  current
	  		  DESCRIPTION
	  		          "Policy Name"
	  		  ::= { fwPolicyStat 1 }

	  fwInstallTime OBJECT-TYPE
	  		  SYNTAX  DisplayString (SIZE (0..255))
	  		  MAX-ACCESS read-only
	  		  STATUS  current
	  		  DESCRIPTION
	  		          "Policy install time"
	  		  ::= { fwPolicyStat 2 }
      fwNumConn OBJECT-TYPE
	  		  SYNTAX  Unsigned32
	  		  MAX-ACCESS read-only
	  		  STATUS  current
	  		  DESCRIPTION
	  		          "Number of connections"
	  		  ::= { fwPolicyStat 3 }

	  fwPeakNumConn OBJECT-TYPE
	  		  SYNTAX  Unsigned32
	  		  MAX-ACCESS read-only
	  		  STATUS  current
	  		  DESCRIPTION
	  		          "Peak number of connections"
	  		  ::= { fwPolicyStat 4 }

	  fwIspTable OBJECT-TYPE
	          SYNTAX  SEQUENCE OF  FwIspEntry
			  MAX-ACCESS  not-accessible
			  STATUS  current
			  DESCRIPTION "No description available"
			   ::= { fwPolicyStat 7 }


	  fwIspEntry OBJECT-TYPE
	          SYNTAX  FwIspEntry
	          MAX-ACCESS  not-accessible
	          STATUS  current
	          DESCRIPTION "No description available"
	          INDEX   { fwIspIndex }
	          ::= { fwIspTable 1 }

      FwIspEntry ::=
              SEQUENCE {
                 fwIspIndex
                      Unsigned32,
                 fwIspName
                      DisplayString,
                 fwIspStatus
                      DisplayString,
                 fwIspRole
                      DisplayString,
                 unknown
                      Unsigned32
              }

      fwIspIndex OBJECT-TYPE
            SYNTAX Unsigned32
            MAX-ACCESS not-accessible
            STATUS  current
            DESCRIPTION "Index"
            ::= { fwIspEntry 1 }

      fwIspName OBJECT-TYPE
            SYNTAX  DisplayString
            MAX-ACCESS read-only
            STATUS  current
            DESCRIPTION "Name"
            ::= { fwIspEntry 2 }

      fwIspStatus OBJECT-TYPE
            SYNTAX  DisplayString
            MAX-ACCESS read-only
            STATUS  current
            DESCRIPTION "Status"
            ::= { fwIspEntry 3 }

      fwIspRole OBJECT-TYPE
            SYNTAX  DisplayString
            MAX-ACCESS read-only
            STATUS  current
            DESCRIPTION "Role"
            ::= { fwIspEntry 4 }

	  unknown OBJECT-TYPE
            SYNTAX  Unsigned32
            MAX-ACCESS read-only
            STATUS  current
            DESCRIPTION "No description available"
            ::= { fwIspEntry 5 }




	  fwIfTable OBJECT-TYPE
	          SYNTAX  SEQUENCE OF  FwIfEntry
			  MAX-ACCESS  not-accessible
			  STATUS  current
			  DESCRIPTION "No description available"
			   ::= { fwPolicyStat 5 }

      fwConnTableLimit OBJECT-TYPE
	  		  SYNTAX  Unsigned32
	  		  MAX-ACCESS read-only
	  		  STATUS  current
	  		  DESCRIPTION
	  		          "Connection table limit"
	  		  ::= { fwPolicyStat 10 }


	  fwIfEntry OBJECT-TYPE
	          SYNTAX  FwIfEntry
	          MAX-ACCESS  not-accessible
	          STATUS  current
	          DESCRIPTION "No description available"
	          INDEX   { fwIfIndex }
	          ::= { fwIfTable 1 }

      FwIfEntry ::=
              SEQUENCE {
                 fwIfIndex
                      Unsigned32,
                 fwIfName
                      DisplayString,
                 fwAcceptPcktsIn
                      Unsigned32,
                 fwAcceptPcktsOut
                      Unsigned32,
                 fwAcceptBytesIn
                      Unsigned32,
                 fwAcceptBytesOut
                      Unsigned32,
                 fwDropPcktsIn
                      Unsigned32,
                 fwDropPcktsOut
                      Unsigned32,
                 fwRejectPcktsIn
                      Unsigned32,
                 fwRejectPcktsOut
                      Unsigned32,
                 fwLogIn
                      Unsigned32,
                 fwLogOut
                      Unsigned32
              }

      fwIfIndex OBJECT-TYPE
            SYNTAX Unsigned32
            MAX-ACCESS not-accessible
            STATUS  current
            DESCRIPTION "No description available"
            ::= { fwIfEntry 1 }

      fwIfName OBJECT-TYPE
            SYNTAX  DisplayString
            MAX-ACCESS read-only
            STATUS  current
            DESCRIPTION "No description available"
            ::= { fwIfEntry 2 }

      fwAcceptPcktsIn OBJECT-TYPE
            SYNTAX  Unsigned32
            MAX-ACCESS read-only
            STATUS  current
            DESCRIPTION "No description available"
            ::= { fwIfEntry 5 }

      fwAcceptPcktsOut OBJECT-TYPE
            SYNTAX  Unsigned32
            MAX-ACCESS read-only
            STATUS  current
            DESCRIPTION "No description available"
            ::= { fwIfEntry 6 }

	  fwAcceptBytesIn OBJECT-TYPE
            SYNTAX  Unsigned32
            MAX-ACCESS read-only
            STATUS  current
            DESCRIPTION "No description available"
            ::= { fwIfEntry 7 }

	  fwAcceptBytesOut OBJECT-TYPE
            SYNTAX  Unsigned32
            MAX-ACCESS read-only
            STATUS  current
            DESCRIPTION "No description available"
            ::= { fwIfEntry 8 }


      fwDropPcktsIn OBJECT-TYPE
            SYNTAX  Unsigned32
            MAX-ACCESS read-only
            STATUS  current
            DESCRIPTION "No description available"
            ::= { fwIfEntry 9 }

      fwDropPcktsOut OBJECT-TYPE
            SYNTAX  Unsigned32
            MAX-ACCESS read-only
            STATUS  current
            DESCRIPTION "No description available"
            ::= { fwIfEntry 10 }


      fwRejectPcktsIn OBJECT-TYPE
            SYNTAX  Unsigned32
            MAX-ACCESS read-only
            STATUS  current
            DESCRIPTION "No description available"
            ::= { fwIfEntry 11 }

      fwRejectPcktsOut OBJECT-TYPE
            SYNTAX  Unsigned32
            MAX-ACCESS read-only
            STATUS  current
            DESCRIPTION "No description available"
            ::= { fwIfEntry 12 }

      fwLogIn OBJECT-TYPE
            SYNTAX  Unsigned32
            MAX-ACCESS read-only
            STATUS  current
            DESCRIPTION "No description available"
            ::= { fwIfEntry 13 }

      fwLogOut OBJECT-TYPE
            SYNTAX  Unsigned32
            MAX-ACCESS read-only
            STATUS  current
            DESCRIPTION "No description available"
            ::= { fwIfEntry 14 }

	  fwAcceptedTotal OBJECT-TYPE
	  		  SYNTAX  Counter64
	  		  MAX-ACCESS read-only
	  		  STATUS  current
	  		  DESCRIPTION
	  		          "Total number of accepted packets"
	  		  ::= { fwPolicyStat 6 }

	  fwDroppedTotal OBJECT-TYPE
	  		  SYNTAX  Counter64
	  		  MAX-ACCESS read-only
	  		  STATUS  current
	  		  DESCRIPTION
	  		          "Total number of dropped packets"
	  		  ::= { fwPolicyStat 16 }

          fwRejectedTotal OBJECT-TYPE
                          SYNTAX Counter64
	  		  MAX-ACCESS read-only
                          STATUS  current
                          DESCRIPTION
                                  "Total number of rejected packets"
                          ::= { fwPolicyStat 14 }

          fwLoggedTotal OBJECT-TYPE
	  		  SYNTAX  Counter64
	  		  MAX-ACCESS read-only
	  		  STATUS  current
	  		  DESCRIPTION
                                  "Total number of logs sent"
                          ::= { fwPolicyStat 13 }

	  fwAcceptedBytesTotal OBJECT-TYPE
	  		  SYNTAX  Counter64
	  		  MAX-ACCESS read-only
	  		  STATUS  current
	  		  DESCRIPTION
	  		          "Total number of accepted bytes"
	  		  ::= { fwPolicyStat 8 }

	  fwDroppedBytesTotal OBJECT-TYPE
	  		  SYNTAX  Counter64
	  		  MAX-ACCESS read-only
	  		  STATUS  current
	  		  DESCRIPTION
	  		          "Total number of dropped bytes"
	  		  ::= { fwPolicyStat 9 }

	  fwRejectedBytesTotal OBJECT-TYPE
	  		  SYNTAX  Counter64
	  		  MAX-ACCESS read-only
	  		  STATUS  current
	  		  DESCRIPTION
	  		          "Total number of rejected bytes"
	  		  ::= { fwPolicyStat 15 }

	  fwAcceptedBytesRates OBJECT-TYPE
	  		  SYNTAX  Counter64
	  		  MAX-ACCESS read-only
	  		  STATUS  current
	  		  DESCRIPTION
	  		          "Accepted bytes rates"
	  		  ::= { fwPolicyStat 20 }

	  fwAcceptedPcktsRates OBJECT-TYPE
	  		  SYNTAX  Counter64
	  		  MAX-ACCESS read-only
	  		  STATUS  current
	  		  DESCRIPTION
	  		          "Accepted packets rates"
	  		  ::= { fwPolicyStat 21 }

	  fwConnsRate OBJECT-TYPE
	  		  SYNTAX  Integer32
	  		  MAX-ACCESS read-only
	  		  STATUS  current
	  		  DESCRIPTION
	  		          "Connection Rates"
	  		  ::= { fwPolicyStat 22 }

	fwIf64Table OBJECT-TYPE
		SYNTAX  SEQUENCE OF  FwIf64Entry
		MAX-ACCESS  not-accessible
		STATUS  current
		DESCRIPTION "No description available"
		::= { fwPolicyStat 25 }

	fwFullyUtilizedDrops OBJECT-TYPE
	  		  SYNTAX  Counter64
	  		  MAX-ACCESS read-only
	  		  STATUS  current
	  		  DESCRIPTION
	  		          "Total number of dropped packets due to instance being fully utilized"
	  		  ::= { fwPolicyStat 26 }

	fwIf64Entry OBJECT-TYPE
		SYNTAX  FwIf64Entry
		MAX-ACCESS  not-accessible
		STATUS  current
		DESCRIPTION "No description available"
		INDEX   { fwIfIndex64 }
		::= { fwIf64Table 1 }

	FwIf64Entry ::=
		SEQUENCE {
			fwIfIndex64
				Unsigned32,
			fwIfName64
				DisplayString,
			fwAcceptPcktsIn64
				Counter64,
			fwAcceptPcktsOut64
				Counter64,
			fwAcceptBytesIn64
				Counter64,
			fwAcceptBytesOut64
				Counter64,
			fwDropPcktsIn64
				Counter64,
			fwDropPcktsOut64
				Counter64,
			fwRejectPcktsIn64
				Counter64,
			fwRejectPcktsOut64
				Counter64,
			fwLogIn64
				Counter64,
			fwLogOut64
				Counter64
		}

	fwIfIndex64 OBJECT-TYPE
		SYNTAX Unsigned32
		MAX-ACCESS not-accessible
		STATUS  current
		DESCRIPTION "No description available"
		::= { fwIf64Entry 1 }

	fwIfName64 OBJECT-TYPE
		SYNTAX  DisplayString
		MAX-ACCESS read-only
		STATUS  current
		DESCRIPTION "No description available"
		::= { fwIf64Entry 2 }

	fwAcceptPcktsIn64 OBJECT-TYPE
		SYNTAX  Counter64
		MAX-ACCESS read-only
		STATUS  current
		DESCRIPTION "No description available"
		::= { fwIf64Entry 5 }

	fwAcceptPcktsOut64 OBJECT-TYPE
		SYNTAX  Counter64
		MAX-ACCESS read-only
		STATUS  current
		DESCRIPTION "No description available"
		::= { fwIf64Entry 6 }

	fwAcceptBytesIn64 OBJECT-TYPE
		SYNTAX  Counter64
		MAX-ACCESS read-only
		STATUS  current
		DESCRIPTION "No description available"
		::= { fwIf64Entry 7 }

	fwAcceptBytesOut64 OBJECT-TYPE
		SYNTAX  Counter64
		MAX-ACCESS read-only
		STATUS  current
		DESCRIPTION "No description available"
		::= { fwIf64Entry 8 }

	fwDropPcktsIn64 OBJECT-TYPE
		SYNTAX  Counter64
		MAX-ACCESS read-only
		STATUS  current
		DESCRIPTION "No description available"
		::= { fwIf64Entry 9 }

	fwDropPcktsOut64 OBJECT-TYPE
		SYNTAX  Counter64
		MAX-ACCESS read-only
		STATUS  current
		DESCRIPTION "No description available"
		::= { fwIf64Entry 10 }

	fwRejectPcktsIn64 OBJECT-TYPE
		SYNTAX  Counter64
		MAX-ACCESS read-only
		STATUS  current
		DESCRIPTION "No description available"
		::= { fwIf64Entry 11 }

	fwRejectPcktsOut64 OBJECT-TYPE
		SYNTAX  Counter64
		MAX-ACCESS read-only
		STATUS  current
		DESCRIPTION "No description available"
		::= { fwIf64Entry 12 }

	fwLogIn64 OBJECT-TYPE
		SYNTAX  Counter64
		MAX-ACCESS read-only
		STATUS  current
		DESCRIPTION "No description available"
		::= { fwIf64Entry 13 }

	fwLogOut64 OBJECT-TYPE
		SYNTAX  Counter64
		MAX-ACCESS read-only
		STATUS  current
		DESCRIPTION "No description available"
		::= { fwIf64Entry 14 }


	  fwHmem-block-size	 OBJECT-TYPE
            SYNTAX  Unsigned32
            MAX-ACCESS read-only
            STATUS  current
            DESCRIPTION
	  		        "hmem - block size"
            ::= { fwHmem 1 }

	  fwHmem-requested-bytes  OBJECT-TYPE
            SYNTAX  Unsigned32
            MAX-ACCESS read-only
            STATUS  current
            DESCRIPTION
	  		        "hmem - requested bytes"
            ::= { fwHmem 2 }

	  fwHmem-initial-allocated-bytes  OBJECT-TYPE
            SYNTAX  Unsigned32
            MAX-ACCESS read-only
            STATUS  current
            DESCRIPTION
	  		        "hmem - initial allocated bytes"
            ::= { fwHmem 3 }

	  fwHmem-initial-allocated-blocks OBJECT-TYPE
            SYNTAX  Unsigned32
            MAX-ACCESS read-only
            STATUS  current
            DESCRIPTION
	  		        "hmem - initial allocated blocks"
            ::= { fwHmem 4 }

	  fwHmem-initial-allocated-pools  OBJECT-TYPE
            SYNTAX  Unsigned32
            MAX-ACCESS read-only
            STATUS  current
            DESCRIPTION
	  		        "hmem - initial allocated pools"
            ::= { fwHmem 5 }

	  fwHmem-current-allocated-bytes OBJECT-TYPE
            SYNTAX  Unsigned32
            MAX-ACCESS read-only
            STATUS  current
            DESCRIPTION
	  		        "hmem - current allocated bytes"
            ::= { fwHmem 6 }

	  fwHmem-current-allocated-blocks OBJECT-TYPE
            SYNTAX  Unsigned32
            MAX-ACCESS read-only
            STATUS  current
            DESCRIPTION
	  		        "hmem - current allocated blocks"
            ::= { fwHmem 7 }

	  fwHmem-current-allocated-pools  OBJECT-TYPE
            SYNTAX  Unsigned32
            MAX-ACCESS read-only
            STATUS  current
            DESCRIPTION
	  		        "hmem - current allocated pools"
            ::= { fwHmem 8 }

	  fwHmem-maximum-bytes  OBJECT-TYPE
            SYNTAX  Unsigned32
            MAX-ACCESS read-only
            STATUS  current
            DESCRIPTION
	  		        "hmem - maximum bytes"
            ::= { fwHmem 9 }

	  fwHmem-maximum-pools  OBJECT-TYPE
            SYNTAX  Unsigned32
            MAX-ACCESS read-only
            STATUS  current
            DESCRIPTION
	  		        "hmem - maximum pools"
            ::= { fwHmem 10 }

	  fwHmem-bytes-used  OBJECT-TYPE
            SYNTAX  Unsigned32
            MAX-ACCESS read-only
            STATUS  current
            DESCRIPTION
	  		        "hmem - bytes used"
            ::= { fwHmem 11 }

	  fwHmem-blocks-used  OBJECT-TYPE
            SYNTAX  Unsigned32
            MAX-ACCESS read-only
            STATUS  current
            DESCRIPTION
	  		        "hmem - blocks used"
            ::= { fwHmem 12 }

	  fwHmem-bytes-unused  OBJECT-TYPE
            SYNTAX  Unsigned32
            MAX-ACCESS read-only
            STATUS  current
            DESCRIPTION
	  		        "hmem - bytes unused"
            ::= { fwHmem 13 }

	  fwHmem-blocks-unused  OBJECT-TYPE
            SYNTAX  Unsigned32
            MAX-ACCESS read-only
            STATUS  current
            DESCRIPTION
	  		        "hmem - blocks unused"
            ::= { fwHmem 14 }

	  fwHmem-bytes-peak  OBJECT-TYPE
            SYNTAX  Unsigned32
            MAX-ACCESS read-only
            STATUS  current
            DESCRIPTION
	  		        "hmem - bytes peak"
            ::= { fwHmem 15 }

	  fwHmem-blocks-peak  OBJECT-TYPE
            SYNTAX  Unsigned32
            MAX-ACCESS read-only
            STATUS  current
            DESCRIPTION
	  		        "hmem - blocks peak"
            ::= { fwHmem 16 }

	  fwHmem-bytes-internal-use  OBJECT-TYPE
            SYNTAX  Unsigned32
            MAX-ACCESS read-only
            STATUS  current
            DESCRIPTION
	  		        "hmem - bytes internal use"
            ::= { fwHmem 17 }

	  fwHmem-number-of-items  OBJECT-TYPE
            SYNTAX  Unsigned32
            MAX-ACCESS read-only
            STATUS  current
            DESCRIPTION
	  		        "hmem - number of items"
            ::= { fwHmem 18 }

	  fwHmem-alloc-operations OBJECT-TYPE
            SYNTAX  Unsigned32
            MAX-ACCESS read-only
            STATUS  current
            DESCRIPTION
	  		        "hmem - alloc operations"
            ::= { fwHmem 19 }

	  fwHmem-free-operations OBJECT-TYPE
            SYNTAX  Unsigned32
            MAX-ACCESS read-only
            STATUS  current
            DESCRIPTION
	  		        "hmem - free operations"
            ::= { fwHmem 20 }

	  fwHmem-failed-alloc  OBJECT-TYPE
            SYNTAX  Unsigned32
            MAX-ACCESS read-only
            STATUS  current
            DESCRIPTION
	  		        "hmem - failed alloc"
            ::= { fwHmem 21 }

	  fwHmem-failed-free  OBJECT-TYPE
            SYNTAX  Unsigned32
            MAX-ACCESS read-only
            STATUS  current
            DESCRIPTION
	  		        "hmem - failed free"
            ::= { fwHmem 22 }


	  fwKmem-system-physical-mem  OBJECT-TYPE
            SYNTAX  Unsigned32
            MAX-ACCESS read-only
            STATUS  current
            DESCRIPTION
	  		        "kmem - system physical mem"
            ::= { fwKmem 1 }

	  fwKmem-available-physical-mem  OBJECT-TYPE
            SYNTAX  Unsigned32
            MAX-ACCESS read-only
            STATUS  current
            DESCRIPTION
	  		        "kmem - available physical mem"
            ::= { fwKmem 2 }

	  fwKmem-aix-heap-size  OBJECT-TYPE
            SYNTAX  Unsigned32
            MAX-ACCESS read-only
            STATUS  current
            DESCRIPTION
	  		        "kmem - aix heap size"
            ::= { fwKmem 3 }

	  fwKmem-bytes-used  OBJECT-TYPE
            SYNTAX  Unsigned32
            MAX-ACCESS read-only
            STATUS  current
            DESCRIPTION
	  		        "kmem - bytes used"
            ::= { fwKmem 4 }

	  fwKmem-blocking-bytes-used  OBJECT-TYPE
            SYNTAX  Unsigned32
            MAX-ACCESS read-only
            STATUS  current
            DESCRIPTION
	  		        "kmem - blocking bytes used"
            ::= { fwKmem 5 }

	  fwKmem-non-blocking-bytes-used  OBJECT-TYPE
            SYNTAX  Unsigned32
            MAX-ACCESS read-only
            STATUS  current
            DESCRIPTION
	  		        "kmem - non blocking bytes used"
            ::= { fwKmem 6 }

	  fwKmem-bytes-unused  OBJECT-TYPE
            SYNTAX  Unsigned32
            MAX-ACCESS read-only
            STATUS  current
            DESCRIPTION
	  		        "kmem - bytes unused"
            ::= { fwKmem 7 }

	  fwKmem-bytes-peak  OBJECT-TYPE
            SYNTAX  Unsigned32
            MAX-ACCESS read-only
            STATUS  current
            DESCRIPTION
	  		        "kmem - bytes peak"
            ::= { fwKmem 8 }

	  fwKmem-blocking-bytes-peak  OBJECT-TYPE
            SYNTAX  Unsigned32
            MAX-ACCESS read-only
            STATUS  current
            DESCRIPTION
	  		        "kmem - blocking bytes peak"
            ::= { fwKmem 9 }

	  fwKmem-non-blocking-bytes-peak  OBJECT-TYPE
            SYNTAX  Unsigned32
            MAX-ACCESS read-only
            STATUS  current
            DESCRIPTION
	  		        "kmem - non blocking bytes peak"
            ::= { fwKmem 10 }

	  fwKmem-bytes-internal-use  OBJECT-TYPE
            SYNTAX  Unsigned32
            MAX-ACCESS read-only
            STATUS  current
            DESCRIPTION
	  		        "kmem - bytes internal use"
            ::= { fwKmem 11 }

	  fwKmem-number-of-items  OBJECT-TYPE
            SYNTAX  Unsigned32
            MAX-ACCESS read-only
            STATUS  current
            DESCRIPTION
	  		        "kmem - number of items"
            ::= { fwKmem 12 }

	  fwKmem-alloc-operations  OBJECT-TYPE
            SYNTAX  Unsigned32
            MAX-ACCESS read-only
            STATUS  current
            DESCRIPTION
	  		        "kmem - alloc operations"
            ::= { fwKmem 13 }

	  fwKmem-free-operations  OBJECT-TYPE
            SYNTAX  Unsigned32
            MAX-ACCESS read-only
            STATUS  current
            DESCRIPTION
	  		        "kmem - free operations"
            ::= { fwKmem 14 }

	  fwKmem-failed-alloc  OBJECT-TYPE
            SYNTAX  Unsigned32
            MAX-ACCESS read-only
            STATUS  current
            DESCRIPTION
	  		        "kmem - failed alloc"
            ::= { fwKmem 15 }

	  fwKmem-failed-free  OBJECT-TYPE
            SYNTAX  Unsigned32
            MAX-ACCESS read-only
            STATUS  current
            DESCRIPTION
	  		        "kmem - failed free"
            ::= { fwKmem 16 }

	  fwInspect-packets  OBJECT-TYPE
            SYNTAX  Unsigned32
            MAX-ACCESS read-only
            STATUS  current
            DESCRIPTION
	  		        "inspect - packets"
            ::= { fwInspect 1 }

	  fwInspect-operations  OBJECT-TYPE
            SYNTAX  Unsigned32
            MAX-ACCESS read-only
            STATUS  current
            DESCRIPTION
	  		        "inspect - operations"
            ::= { fwInspect 2 }

	  fwInspect-lookups  OBJECT-TYPE
            SYNTAX  Unsigned32
            MAX-ACCESS read-only
            STATUS  current
            DESCRIPTION
	  		        "inspect - lookups"
            ::= { fwInspect 3 }

	  fwInspect-record  OBJECT-TYPE
            SYNTAX  Unsigned32
            MAX-ACCESS read-only
            STATUS  current
            DESCRIPTION
	  		        "inspect - record"
            ::= { fwInspect 4 }

	  fwInspect-extract  OBJECT-TYPE
            SYNTAX  Unsigned32
            MAX-ACCESS read-only
            STATUS  current
            DESCRIPTION
	  		        "inspect - extract"
            ::= { fwInspect 5 }

      fwCookies-total  OBJECT-TYPE
            SYNTAX  Unsigned32
            MAX-ACCESS read-only
            STATUS  current
            DESCRIPTION
	  		        "cookies - total"
            ::= { fwCookies 1 }

	  fwCookies-allocfwCookies-total  OBJECT-TYPE
            SYNTAX  Unsigned32
            MAX-ACCESS read-only
            STATUS  current
            DESCRIPTION
	  		        "cookies - alloc"
            ::= { fwCookies 2 }

	  fwCookies-freefwCookies-total  OBJECT-TYPE
            SYNTAX  Unsigned32
            MAX-ACCESS read-only
            STATUS  current
            DESCRIPTION
	  		        "cookies - free"
            ::= { fwCookies 3 }

	  fwCookies-dupfwCookies-total  OBJECT-TYPE
            SYNTAX  Unsigned32
            MAX-ACCESS read-only
            STATUS  current
            DESCRIPTION
	  		        "cookies - dup"
            ::= { fwCookies 4 }

	  fwCookies-getfwCookies-total  OBJECT-TYPE
            SYNTAX  Unsigned32
            MAX-ACCESS read-only
            STATUS  current
            DESCRIPTION
	  		        "cookies - get"
            ::= { fwCookies 5 }

	  fwCookies-putfwCookies-total  OBJECT-TYPE
            SYNTAX  Unsigned32
            MAX-ACCESS read-only
            STATUS  current
            DESCRIPTION
	  		        "cookies - put"
            ::= { fwCookies 6 }

	  fwCookies-lenfwCookies-total  OBJECT-TYPE
            SYNTAX  Unsigned32
            MAX-ACCESS read-only
            STATUS  current
            DESCRIPTION
	  		        "cookies - len"
            ::= { fwCookies 7 }

	  fwChains-alloc  OBJECT-TYPE
            SYNTAX  Unsigned32
            MAX-ACCESS read-only
            STATUS  current
            DESCRIPTION
	  		        "chains - alloc"
            ::= { fwChains 1 }

      fwChains-free  OBJECT-TYPE
            SYNTAX  Unsigned32
            MAX-ACCESS read-only
            STATUS  current
            DESCRIPTION
	  		        "chains - free"
            ::= { fwChains 2 }

      fwFrag-fragments  OBJECT-TYPE
            SYNTAX  Unsigned32
            MAX-ACCESS read-only
            STATUS  current
            DESCRIPTION
	  		        "fragments - fragments"
            ::= { fwFragments 1 }

      fwFrag-expired  OBJECT-TYPE
            SYNTAX  Unsigned32
            MAX-ACCESS read-only
            STATUS  current
            DESCRIPTION
	  		        "fragments - expired"
            ::= { fwFragments 2 }

      fwFrag-packets  OBJECT-TYPE
            SYNTAX  Unsigned32
            MAX-ACCESS read-only
            STATUS  current
            DESCRIPTION
	  		        "fragments - packets"
            ::= { fwFragments 3 }

      fwUfpHitRatio  OBJECT-TYPE
            SYNTAX  Unsigned32
            MAX-ACCESS read-only
            STATUS  current
            DESCRIPTION
	  		        "ufp - % hits ratio"
            ::= { fwUfp 1 }

      fwUfpInspected  OBJECT-TYPE
            SYNTAX  Unsigned32
            MAX-ACCESS read-only
            STATUS  current
            DESCRIPTION
	  		        "ufp - total connections"
            ::= { fwUfp 2 }

      fwUfpHits  OBJECT-TYPE
            SYNTAX  Unsigned32
            MAX-ACCESS read-only
            STATUS  current
            DESCRIPTION
	  		        "ufp - hits connections"
            ::= { fwUfp 3 }

      fwSS-http-pid  OBJECT-TYPE
            SYNTAX  Unsigned32
            MAX-ACCESS read-only
            STATUS  current
            DESCRIPTION
	  		        "http - pid"
            ::= { fwSS-http 1 }

      fwSS-http-proto  OBJECT-TYPE
            SYNTAX  Unsigned32
            MAX-ACCESS read-only
            STATUS  current
            DESCRIPTION
	  		        "http - proto"
            ::= { fwSS-http 2 }

      fwSS-http-port  OBJECT-TYPE
            SYNTAX  Gauge32
            MAX-ACCESS read-only
            STATUS  current
            DESCRIPTION
	  		        "http - port"
            ::= { fwSS-http 3 }

      fwSS-http-logical-port  OBJECT-TYPE
            SYNTAX  Gauge32
            MAX-ACCESS read-only
            STATUS  current
            DESCRIPTION
	  		        "http - logical port"
            ::= { fwSS-http 4 }

      fwSS-http-max-avail-socket  OBJECT-TYPE
            SYNTAX  Unsigned32
            MAX-ACCESS read-only
            STATUS  current
            DESCRIPTION
	  		        "http - max avail socket"
            ::= { fwSS-http 5 }

      fwSS-http-socket-in-use-max  OBJECT-TYPE
            SYNTAX  Unsigned32
            MAX-ACCESS read-only
            STATUS  current
            DESCRIPTION
	  		        "http - socket in use max"
            ::= { fwSS-http 6 }

      fwSS-http-socket-in-use-curr  OBJECT-TYPE
            SYNTAX  Unsigned32
            MAX-ACCESS read-only
            STATUS  current
            DESCRIPTION
	  		        "http - socket in use current"
            ::= { fwSS-http 7 }

      fwSS-http-socket-in-use-count  OBJECT-TYPE
            SYNTAX  Unsigned32
            MAX-ACCESS read-only
            STATUS  current
            DESCRIPTION
	  		        "http - socket in use count"
            ::= { fwSS-http 8 }

      fwSS-http-sess-max  OBJECT-TYPE
            SYNTAX  Unsigned32
            MAX-ACCESS read-only
            STATUS  current
            DESCRIPTION
	  		        "http - session max"
            ::= { fwSS-http 9 }

      fwSS-http-sess-curr  OBJECT-TYPE
            SYNTAX  Unsigned32
            MAX-ACCESS read-only
            STATUS  current
            DESCRIPTION
	  		        "http - session current"
            ::= { fwSS-http 10 }

      fwSS-http-sess-count  OBJECT-TYPE
            SYNTAX  Unsigned32
            MAX-ACCESS read-only
            STATUS  current
            DESCRIPTION
	  		        "http - session count"
            ::= { fwSS-http 11 }

      fwSS-http-auth-sess-max  OBJECT-TYPE
            SYNTAX  Unsigned32
            MAX-ACCESS read-only
            STATUS  current
            DESCRIPTION
	  		        "http - auth session max"
            ::= { fwSS-http 12 }

      fwSS-http-auth-sess-curr  OBJECT-TYPE
            SYNTAX  Unsigned32
            MAX-ACCESS read-only
            STATUS  current
            DESCRIPTION
	  		        "http - auth session current"
            ::= { fwSS-http 13 }

      fwSS-http-auth-sess-count  OBJECT-TYPE
            SYNTAX  Unsigned32
            MAX-ACCESS read-only
            STATUS  current
            DESCRIPTION
	  		        "http - auth session count"
            ::= { fwSS-http 14 }

      fwSS-http-accepted-sess  OBJECT-TYPE
            SYNTAX  Unsigned32
            MAX-ACCESS read-only
            STATUS  current
            DESCRIPTION
	  		        "http - accepted session"
            ::= { fwSS-http 15 }

      fwSS-http-rejected-sess  OBJECT-TYPE
            SYNTAX  Unsigned32
            MAX-ACCESS read-only
            STATUS  current
            DESCRIPTION
	  		        "http - rejected session"
            ::= { fwSS-http 16 }

      fwSS-http-auth-failures  OBJECT-TYPE
            SYNTAX  Unsigned32
            MAX-ACCESS read-only
            STATUS  current
            DESCRIPTION
	  		        "http - auth failures"
            ::= { fwSS-http 17 }

      fwSS-http-ops-cvp-sess-max  OBJECT-TYPE
            SYNTAX  Unsigned32
            MAX-ACCESS read-only
            STATUS  current
            DESCRIPTION
	  		        "http - opsec cvp session max"
            ::= { fwSS-http 18 }

      fwSS-http-ops-cvp-sess-curr  OBJECT-TYPE
            SYNTAX  Unsigned32
            MAX-ACCESS read-only
            STATUS  current
            DESCRIPTION
	  		        "http - opsec cvp session current"
            ::= { fwSS-http 19 }

      fwSS-http-ops-cvp-sess-count  OBJECT-TYPE
            SYNTAX  Unsigned32
            MAX-ACCESS read-only
            STATUS  current
            DESCRIPTION
	  		        "http - opsec cvp session count"
            ::= { fwSS-http 20 }

      fwSS-http-ops-cvp-rej-sess  OBJECT-TYPE
            SYNTAX  Unsigned32
            MAX-ACCESS read-only
            STATUS  current
            DESCRIPTION
	  		        "http - opsec cvp rej session"
            ::= { fwSS-http 21 }

      fwSS-http-ssl-encryp-sess-max  OBJECT-TYPE
            SYNTAX  Unsigned32
            MAX-ACCESS read-only
            STATUS  current
            DESCRIPTION
	  		        "http - ssl encryp session max"
            ::= { fwSS-http 22 }

      fwSS-http-ssl-encryp-sess-curr  OBJECT-TYPE
            SYNTAX  Unsigned32
            MAX-ACCESS read-only
            STATUS  current
            DESCRIPTION
	  		        "http - ssl encryp session current"
            ::= { fwSS-http 23 }

      fwSS-http-ssl-encryp-sess-count  OBJECT-TYPE
            SYNTAX  Unsigned32
            MAX-ACCESS read-only
            STATUS  current
            DESCRIPTION
	  		        "http - ssl encryp session count"
            ::= { fwSS-http 24 }

      fwSS-http-transp-sess-max  OBJECT-TYPE
            SYNTAX  Unsigned32
            MAX-ACCESS read-only
            STATUS  current
            DESCRIPTION
	  		        "http - transparent session max"
            ::= { fwSS-http 25 }

      fwSS-http-transp-sess-curr  OBJECT-TYPE
            SYNTAX  Unsigned32
            MAX-ACCESS read-only
            STATUS  current
            DESCRIPTION
	  		        "http - transparent session current"
            ::= { fwSS-http 26 }

      fwSS-http-transp-sess-count  OBJECT-TYPE
            SYNTAX  Unsigned32
            MAX-ACCESS read-only
            STATUS  current
            DESCRIPTION
	  		        "http - transparent session count"
            ::= { fwSS-http 27 }

      fwSS-http-proxied-sess-max  OBJECT-TYPE
            SYNTAX  Unsigned32
            MAX-ACCESS read-only
            STATUS  current
            DESCRIPTION
	  		        "http - proxied session max"
            ::= { fwSS-http 28 }

      fwSS-http-proxied-sess-curr  OBJECT-TYPE
            SYNTAX  Unsigned32
            MAX-ACCESS read-only
            STATUS  current
            DESCRIPTION
	  		        "http - proxied session current"
            ::= { fwSS-http 29 }

      fwSS-http-proxied-sess-count  OBJECT-TYPE
            SYNTAX  Unsigned32
            MAX-ACCESS read-only
            STATUS  current
            DESCRIPTION
	  		        "http - proxied session count"
            ::= { fwSS-http 30 }

      fwSS-http-tunneled-sess-max  OBJECT-TYPE
            SYNTAX  Unsigned32
            MAX-ACCESS read-only
            STATUS  current
            DESCRIPTION
	  		        "http - tunneled session max"
            ::= { fwSS-http 31 }

      fwSS-http-tunneled-sess-curr  OBJECT-TYPE
            SYNTAX  Unsigned32
            MAX-ACCESS read-only
            STATUS  current
            DESCRIPTION
	  		        "http - tunneled session current"
            ::= { fwSS-http 32 }

      fwSS-http-tunneled-sess-count  OBJECT-TYPE
            SYNTAX  Unsigned32
            MAX-ACCESS read-only
            STATUS  current
            DESCRIPTION
	  		        "http - tunneled session count"
            ::= { fwSS-http 33 }

      fwSS-http-ftp-sess-max  OBJECT-TYPE
            SYNTAX  Unsigned32
            MAX-ACCESS read-only
            STATUS  current
            DESCRIPTION
	  		        "http - ftp session max"
            ::= { fwSS-http 34 }

      fwSS-http-ftp-sess-curr  OBJECT-TYPE
            SYNTAX  Unsigned32
            MAX-ACCESS read-only
            STATUS  current
            DESCRIPTION
	  		        "http - ftp session current"
            ::= { fwSS-http 35 }

      fwSS-http-ftp-sess-count  OBJECT-TYPE
            SYNTAX  Unsigned32
            MAX-ACCESS read-only
            STATUS  current
            DESCRIPTION
	  		        "http - ftp session count"
            ::= { fwSS-http 36 }

      fwSS-http-time-stamp  OBJECT-TYPE
            SYNTAX  DisplayString (SIZE (0..255))
            MAX-ACCESS read-only
            STATUS  current
            DESCRIPTION
	  		        "http - time stamp"
            ::= { fwSS-http 37 }

      fwSS-http-is-alive  OBJECT-TYPE
            SYNTAX  Unsigned32
            MAX-ACCESS read-only
            STATUS  current
            DESCRIPTION
	  		        "http - is alive"
            ::= { fwSS-http 38 }

      fwSS-http-blocked-cnt  OBJECT-TYPE
            SYNTAX  Unsigned32
            MAX-ACCESS read-only
            STATUS  current
            DESCRIPTION
	  		        "count of HTTP items blocked, being classified as 'infected' by Anti Virus"
            ::= { fwSS-http 39 }

      fwSS-http-blocked-total  OBJECT-TYPE
            SYNTAX  Unsigned32
            MAX-ACCESS read-only
            STATUS  current
            DESCRIPTION
	  		        "sum of all the counts of the previous OID (fwss-http-blocked-cnt)"
            ::= { fwSS-http 40 }

      fwSS-http-scanned-total  OBJECT-TYPE
            SYNTAX  Unsigned32
            MAX-ACCESS read-only
            STATUS  current
            DESCRIPTION
	  		        "sum of all the counts of 'blocked' (infected) and 'passed' items"
            ::= { fwSS-http 41 }

      fwSS-http-blocked-by-file-type  OBJECT-TYPE
            SYNTAX  Unsigned32
            MAX-ACCESS read-only
            STATUS  current
            DESCRIPTION
	  		        "count of HTTP items blocked by 'file type' policy in Content Inspection tab in SmartDashboard"
            ::= { fwSS-http 42 }

      fwSS-http-blocked-by-size-limit  OBJECT-TYPE
            SYNTAX  Unsigned32
            MAX-ACCESS read-only
            STATUS  current
            DESCRIPTION
	  		        "count of HTTP items blocked by 'size limit' policy in Content Inspection tab in SmartDashboard"
            ::= { fwSS-http 43 }

      fwSS-http-blocked-by-archive-limit  OBJECT-TYPE
            SYNTAX  Unsigned32
            MAX-ACCESS read-only
            STATUS  current
            DESCRIPTION
	  		        "count of HTTP items blocked by 'archive limit' policy in Content Inspection tab in SmartDashboard"
            ::= { fwSS-http 44 }

      fwSS-http-blocked-by-internal-error  OBJECT-TYPE
            SYNTAX  Unsigned32
            MAX-ACCESS read-only
            STATUS  current
            DESCRIPTION
	  		        "count of HTTP items blocked because of 'internal error' in Content Inspection tab in SmartDashboard"
	  ::= { fwSS-http 45 }


      fwSS-http-passed-cnt  OBJECT-TYPE
            SYNTAX  Unsigned32
            MAX-ACCESS read-only
            STATUS  current
            DESCRIPTION
	  		        "count of HTTP items passed, being classified as 'safe' by Anti Virus"
            ::= { fwSS-http 46 }

      fwSS-http-passed-by-file-type  OBJECT-TYPE
            SYNTAX  Unsigned32
            MAX-ACCESS read-only
            STATUS  current
            DESCRIPTION
	  		        "count of HTTP items allowed (without AV scan) by 'File Type' policy in Content Inspection tab in
	  		         SmartDashboard"
            ::= { fwSS-http 47 }

      fwSS-http-passed-by-size-limit  OBJECT-TYPE
            SYNTAX  Unsigned32
            MAX-ACCESS read-only
            STATUS  current
            DESCRIPTION
	  		        "count of HTTP items allowed (without AV scan) by 'Size Limit' policy in Content Inspection tab in
	  		         SmartDashboard"
            ::= { fwSS-http 48 }

      fwSS-http-passed-by-archive-limit  OBJECT-TYPE
            SYNTAX  Unsigned32
            MAX-ACCESS read-only
            STATUS  current
            DESCRIPTION
	  		        "count of HTTP items allowed (without AV scan) by 'Archive Limit' policy in Content Inspection tab in
	  		         SmartDashboard"
            ::= { fwSS-http 49 }

      fwSS-http-passed-by-internal-error  OBJECT-TYPE
            SYNTAX  Unsigned32
            MAX-ACCESS read-only
            STATUS  current
            DESCRIPTION
	  		        "count of HTTP items allowed (without AV scan) by 'internal error' in Content Inspection tab in
	  		         SmartDashboard"
            ::= { fwSS-http 50 }

      fwSS-http-passed-total  OBJECT-TYPE
            SYNTAX  Unsigned32
            MAX-ACCESS read-only
            STATUS  current
            DESCRIPTION
	  		        "sum of all the above 'passed' counts - OIDs .46 to .50"
            ::= { fwSS-http 51 }

      fwSS-http-blocked-by-AV-settings  OBJECT-TYPE
            SYNTAX  Unsigned32
            MAX-ACCESS read-only
            STATUS  current
            DESCRIPTION
	  		        "count of HTTP items rejected by Anti Virus as either:
	  		        exceeding size or archive limits, or failed scan due to
	  		        internal error (configured in the 'settings' pane in
	  		        'Content Inspection' tab in SmartDashboard)"
            ::= { fwSS-http 52 }

      fwSS-http-passed-by-AV-settings  OBJECT-TYPE
            SYNTAX  Unsigned32
            MAX-ACCESS read-only
            STATUS  current
            DESCRIPTION
	  		        "count of HTTP items allowed by Anti Virus as either:
	  		        exceeding size or archive limits, or failed scan due to
	  		        internal error (configured in the 'settings' pane in
	  		        'Content Inspection' tab in SmartDashboard)"
            ::= { fwSS-http 53 }

      fwSS-http-blocked-by-URL-filter-category  OBJECT-TYPE
            SYNTAX  Unsigned32
            MAX-ACCESS read-only
            STATUS  current
            DESCRIPTION
	  		        "count of URLs blocked by 'Web Filtering Policy' in 'Content Inspection' tab in SmartDashboard"
            ::= { fwSS-http 54 }

      fwSS-http-blocked-by-URL-block-list  OBJECT-TYPE
            SYNTAX  Unsigned32
            MAX-ACCESS read-only
            STATUS  current
            DESCRIPTION
	  		        "count of URLs blocked by 'Blocked URLs/IPs' in 'Content Inspection' tab in SmartDashboard
	  		        (overriding 'Web Filtering Policy')."
            ::= { fwSS-http 55 }

      fwSS-http-passed-by-URL-allow-list  OBJECT-TYPE
            SYNTAX  Unsigned32
            MAX-ACCESS read-only
            STATUS  current
            DESCRIPTION
	  		        "count of Allowed by 'allowed URLs/IPs' in 'Content Inspection' tab in SmartDashboard
	  		        (overriding 'Web Filtering Policy')"
            ::= { fwSS-http 56 }

      fwSS-http-passed-by-URL-filter-category  OBJECT-TYPE
            SYNTAX  Unsigned32
            MAX-ACCESS read-only
            STATUS  current
            DESCRIPTION
	  		        "count of URLs allowed by 'Web Filtering Policy' in 'Content Inspection' tab in SmartDashboard."
            ::= { fwSS-http 57 }

      fwSS-ftp-pid  OBJECT-TYPE
            SYNTAX  Unsigned32
            MAX-ACCESS read-only
            STATUS  current
            DESCRIPTION
	  		        "ftp - pid"
            ::= { fwSS-ftp 1 }

      fwSS-ftp-proto  OBJECT-TYPE
            SYNTAX  Unsigned32
            MAX-ACCESS read-only
            STATUS  current
            DESCRIPTION
	  		        "ftp - proto"
            ::= { fwSS-ftp 2 }

      fwSS-ftp-port  OBJECT-TYPE
            SYNTAX  Gauge32
            MAX-ACCESS read-only
            STATUS  current
            DESCRIPTION
	  		        "ftp - port"
            ::= { fwSS-ftp 3 }

      fwSS-ftp-logical-port  OBJECT-TYPE
            SYNTAX  Gauge32
            MAX-ACCESS read-only
            STATUS  current
            DESCRIPTION
	  		        "ftp - logical port"
            ::= { fwSS-ftp 4 }

      fwSS-ftp-max-avail-socket  OBJECT-TYPE
            SYNTAX  Unsigned32
            MAX-ACCESS read-only
            STATUS  current
            DESCRIPTION
	  		        "ftp - max avail socket"
            ::= { fwSS-ftp 5 }

      fwSS-ftp-socket-in-use-max  OBJECT-TYPE
            SYNTAX  Unsigned32
            MAX-ACCESS read-only
            STATUS  current
            DESCRIPTION
	  		        "ftp - socket in use max"
            ::= { fwSS-ftp 6 }

      fwSS-ftp-socket-in-use-curr  OBJECT-TYPE
            SYNTAX  Unsigned32
            MAX-ACCESS read-only
            STATUS  current
            DESCRIPTION
	  		        "ftp - socket in use current"
            ::= { fwSS-ftp 7 }

      fwSS-ftp-socket-in-use-count  OBJECT-TYPE
            SYNTAX  Unsigned32
            MAX-ACCESS read-only
            STATUS  current
            DESCRIPTION
	  		        "ftp - socket in use count"
            ::= { fwSS-ftp 8 }

      fwSS-ftp-sess-max  OBJECT-TYPE
            SYNTAX  Unsigned32
            MAX-ACCESS read-only
            STATUS  current
            DESCRIPTION
	  		        "ftp - session max"
            ::= { fwSS-ftp 9 }

      fwSS-ftp-sess-curr  OBJECT-TYPE
            SYNTAX  Unsigned32
            MAX-ACCESS read-only
            STATUS  current
            DESCRIPTION
	  		        "ftp - session current"
            ::= { fwSS-ftp 10 }

      fwSS-ftp-sess-count  OBJECT-TYPE
            SYNTAX  Unsigned32
            MAX-ACCESS read-only
            STATUS  current
            DESCRIPTION
	  		        "ftp - session count"
            ::= { fwSS-ftp 11 }

      fwSS-ftp-auth-sess-max  OBJECT-TYPE
            SYNTAX  Unsigned32
            MAX-ACCESS read-only
            STATUS  current
            DESCRIPTION
	  		        "ftp - auth session max"
            ::= { fwSS-ftp 12 }

      fwSS-ftp-auth-sess-curr  OBJECT-TYPE
            SYNTAX  Unsigned32
            MAX-ACCESS read-only
            STATUS  current
            DESCRIPTION
	  		        "ftp - auth session current"
            ::= { fwSS-ftp 13 }

      fwSS-ftp-auth-sess-count  OBJECT-TYPE
            SYNTAX  Unsigned32
            MAX-ACCESS read-only
            STATUS  current
            DESCRIPTION
	  		        "ftp - auth session count"
            ::= { fwSS-ftp 14 }

      fwSS-ftp-accepted-sess  OBJECT-TYPE
            SYNTAX  Unsigned32
            MAX-ACCESS read-only
            STATUS  current
            DESCRIPTION
	  		        "ftp - accepted session"
            ::= { fwSS-ftp 15 }

      fwSS-ftp-rejected-sess  OBJECT-TYPE
            SYNTAX  Unsigned32
            MAX-ACCESS read-only
            STATUS  current
            DESCRIPTION
	  		        "ftp - rejected session"
            ::= { fwSS-ftp 16 }

      fwSS-ftp-auth-failures  OBJECT-TYPE
            SYNTAX  Unsigned32
            MAX-ACCESS read-only
            STATUS  current
            DESCRIPTION
	  		        "ftp - auth failures"
            ::= { fwSS-ftp 17 }

      fwSS-ftp-ops-cvp-sess-max  OBJECT-TYPE
            SYNTAX  Unsigned32
            MAX-ACCESS read-only
            STATUS  current
            DESCRIPTION
	  		        "ftp - opsec cvp session max"
            ::= { fwSS-ftp 18 }

      fwSS-ftp-ops-cvp-sess-curr  OBJECT-TYPE
            SYNTAX  Unsigned32
            MAX-ACCESS read-only
            STATUS  current
            DESCRIPTION
	  		        "ftp - opsec cvp session current"
            ::= { fwSS-ftp 19 }

      fwSS-ftp-ops-cvp-sess-count  OBJECT-TYPE
            SYNTAX  Unsigned32
            MAX-ACCESS read-only
            STATUS  current
            DESCRIPTION
	  		        "ftp - opsec cvp session count"
            ::= { fwSS-ftp 20 }

      fwSS-ftp-ops-cvp-rej-sess  OBJECT-TYPE
            SYNTAX  Unsigned32
            MAX-ACCESS read-only
            STATUS  current
            DESCRIPTION
	  		        "ftp - opsec cvp rej session"
            ::= { fwSS-ftp 21 }

      fwSS-ftp-time-stamp  OBJECT-TYPE
            SYNTAX  DisplayString (SIZE (0..255))
            MAX-ACCESS read-only
            STATUS  current
            DESCRIPTION
	  		        "ftp - time stamp"
            ::= { fwSS-ftp 22 }

      fwSS-ftp-is-alive  OBJECT-TYPE
            SYNTAX  Unsigned32
            MAX-ACCESS read-only
            STATUS  current
            DESCRIPTION
	  		        "ftp - is alive"
            ::= { fwSS-ftp 23 }

      fwSS-ftp-blocked-cnt  OBJECT-TYPE
            SYNTAX  Unsigned32
            MAX-ACCESS read-only
            STATUS  current
            DESCRIPTION
	  		        "count of ftp items blocked, being classified as 'infected' by Anti Virus"
            ::= { fwSS-ftp 24 }

      fwSS-ftp-blocked-total  OBJECT-TYPE
            SYNTAX  Unsigned32
            MAX-ACCESS read-only
            STATUS  current
            DESCRIPTION
	  		        "sum of all the counts of the previous OID (fwss-ftp-blocked-cnt)"
            ::= { fwSS-ftp 25 }

      fwSS-ftp-scanned-total  OBJECT-TYPE
            SYNTAX  Unsigned32
            MAX-ACCESS read-only
            STATUS  current
            DESCRIPTION
	  		        "sum of all the counts of 'blocked' (infected) and 'passed' items"
            ::= { fwSS-ftp 26 }

      fwSS-ftp-blocked-by-file-type  OBJECT-TYPE
            SYNTAX  Unsigned32
            MAX-ACCESS read-only
            STATUS  current
            DESCRIPTION
	  		        "count of ftp items blocked by 'file type' policy in Content Inspection tab in SmartDashboard"
            ::= { fwSS-ftp 27 }

      fwSS-ftp-blocked-by-size-limit  OBJECT-TYPE
            SYNTAX  Unsigned32
            MAX-ACCESS read-only
            STATUS  current
            DESCRIPTION
	  		        "count of ftp items blocked by 'size limit' policy in Content Inspection tab in SmartDashboard"
            ::= { fwSS-ftp 28 }

      fwSS-ftp-blocked-by-archive-limit  OBJECT-TYPE
            SYNTAX  Unsigned32
            MAX-ACCESS read-only
            STATUS  current
            DESCRIPTION
	  		        "count of ftp items blocked by 'archive limit' policy in Content Inspection tab in SmartDashboard"
            ::= { fwSS-ftp 29 }

      fwSS-ftp-blocked-by-internal-error  OBJECT-TYPE
            SYNTAX  Unsigned32
            MAX-ACCESS read-only
            STATUS  current
            DESCRIPTION
	  		        "count of ftp items blocked because of 'internal error' in Content Inspection tab in SmartDashboard"
	  		::= { fwSS-ftp 30 }


      fwSS-ftp-passed-cnt  OBJECT-TYPE
            SYNTAX  Unsigned32
            MAX-ACCESS read-only
            STATUS  current
            DESCRIPTION
	  		        "count of ftp items passed, being classified as 'safe' by Anti Virus"
            ::= { fwSS-ftp 31 }

      fwSS-ftp-passed-by-file-type  OBJECT-TYPE
            SYNTAX  Unsigned32
            MAX-ACCESS read-only
            STATUS  current
            DESCRIPTION
	  		        "count of ftp items allowed (without AV scan) by 'File Type' policy in Content Inspection tab in
	  		         SmartDashboard"
            ::= { fwSS-ftp 32 }

      fwSS-ftp-passed-by-size-limit  OBJECT-TYPE
            SYNTAX  Unsigned32
            MAX-ACCESS read-only
            STATUS  current
            DESCRIPTION
	  		        "count of ftp items allowed (without AV scan) by 'Size Limit' policy in Content Inspection tab in
	  		         SmartDashboard"
            ::= { fwSS-ftp 33 }

      fwSS-ftp-passed-by-archive-limit  OBJECT-TYPE
            SYNTAX  Unsigned32
            MAX-ACCESS read-only
            STATUS  current
            DESCRIPTION
	  		        "count of ftp items allowed (without AV scan) by 'Archive Limit' policy in Content Inspection tab in
	  		         SmartDashboard"
            ::= { fwSS-ftp 34 }

      fwSS-ftp-passed-by-internal-error  OBJECT-TYPE
            SYNTAX  Unsigned32
            MAX-ACCESS read-only
            STATUS  current
            DESCRIPTION
	  		        "count of ftp items allowed (without AV scan) by 'internal error' in Content Inspection tab in
	  		         SmartDashboard"
            ::= { fwSS-ftp 35 }

      fwSS-ftp-passed-total  OBJECT-TYPE
            SYNTAX  Unsigned32
            MAX-ACCESS read-only
            STATUS  current
            DESCRIPTION
	  		        "sum of all the above 'passed' counts - OIDs .31 to .35"
            ::= { fwSS-ftp 36 }

      fwSS-ftp-blocked-by-AV-settings  OBJECT-TYPE
            SYNTAX  Unsigned32
            MAX-ACCESS read-only
            STATUS  current
            DESCRIPTION
	  		        "count of ftp items rejected by Anti Virus as either:
	  		        exceeding size or archive limits, or failed scan due to
	  		        internal error (configured in the 'settings' pane in
	  		        'Content Inspection' tab in SmartDashboard)"
            ::= { fwSS-ftp 37 }

      fwSS-ftp-passed-by-AV-settings  OBJECT-TYPE
            SYNTAX  Unsigned32
            MAX-ACCESS read-only
            STATUS  current
            DESCRIPTION
	  		        "count of ftp items allowed by Anti Virus as either:
	  		        exceeding size or archive limits, or failed scan due to
	  		        internal error (configured in the 'settings' pane in
	  		        'Content Inspection' tab in SmartDashboard)"
            ::= { fwSS-ftp 38 }

      fwSS-telnet-pid  OBJECT-TYPE
            SYNTAX  Unsigned32
            MAX-ACCESS read-only
            STATUS  current
            DESCRIPTION
	  		        "telnet - pid"
            ::= { fwSS-telnet 1 }

      fwSS-telnet-proto  OBJECT-TYPE
            SYNTAX  Unsigned32
            MAX-ACCESS read-only
            STATUS  current
            DESCRIPTION
	  		        "telnet - proto"
            ::= { fwSS-telnet 2 }

      fwSS-telnet-port  OBJECT-TYPE
            SYNTAX  Gauge32
            MAX-ACCESS read-only
            STATUS  current
            DESCRIPTION
	  		        "telnet - port"
            ::= { fwSS-telnet 3 }

      fwSS-telnet-logical-port  OBJECT-TYPE
            SYNTAX  Gauge32
            MAX-ACCESS read-only
            STATUS  current
            DESCRIPTION
	  		        "telnet - logical port"
            ::= { fwSS-telnet 4 }

      fwSS-telnet-max-avail-socket  OBJECT-TYPE
            SYNTAX  Unsigned32
            MAX-ACCESS read-only
            STATUS  current
            DESCRIPTION
	  		        "telnet - max avail socket"
            ::= { fwSS-telnet 5 }

      fwSS-telnet-socket-in-use-max  OBJECT-TYPE
            SYNTAX  Unsigned32
            MAX-ACCESS read-only
            STATUS  current
            DESCRIPTION
	  		        "telnet - socket in use max"
            ::= { fwSS-telnet 6 }

      fwSS-telnet-socket-in-use-curr  OBJECT-TYPE
            SYNTAX  Unsigned32
            MAX-ACCESS read-only
            STATUS  current
            DESCRIPTION
	  		        "telnet - socket in use current"
            ::= { fwSS-telnet 7 }

      fwSS-telnet-socket-in-use-count  OBJECT-TYPE
            SYNTAX  Unsigned32
            MAX-ACCESS read-only
            STATUS  current
            DESCRIPTION
	  		        "telnet - socket in use count"
            ::= { fwSS-telnet 8 }

      fwSS-telnet-sess-max  OBJECT-TYPE
            SYNTAX  Unsigned32
            MAX-ACCESS read-only
            STATUS  current
            DESCRIPTION
	  		        "telnet - session max"
            ::= { fwSS-telnet 9 }

      fwSS-telnet-sess-curr  OBJECT-TYPE
            SYNTAX  Unsigned32
            MAX-ACCESS read-only
            STATUS  current
            DESCRIPTION
	  		        "telnet - session current"
            ::= { fwSS-telnet 10 }

      fwSS-telnet-sess-count  OBJECT-TYPE
            SYNTAX  Unsigned32
            MAX-ACCESS read-only
            STATUS  current
            DESCRIPTION
	  		        "telnet - session count"
            ::= { fwSS-telnet 11 }

      fwSS-telnet-auth-sess-max  OBJECT-TYPE
            SYNTAX  Unsigned32
            MAX-ACCESS read-only
            STATUS  current
            DESCRIPTION
	  		        "telnet - auth session max"
            ::= { fwSS-telnet 12 }

      fwSS-telnet-auth-sess-curr  OBJECT-TYPE
            SYNTAX  Unsigned32
            MAX-ACCESS read-only
            STATUS  current
            DESCRIPTION
	  		        "telnet - auth session current"
            ::= { fwSS-telnet 13 }

      fwSS-telnet-auth-sess-count  OBJECT-TYPE
            SYNTAX  Unsigned32
            MAX-ACCESS read-only
            STATUS  current
            DESCRIPTION
	  		        "telnet - auth session count"
            ::= { fwSS-telnet 14 }

      fwSS-telnet-accepted-sess  OBJECT-TYPE
            SYNTAX  Unsigned32
            MAX-ACCESS read-only
            STATUS  current
            DESCRIPTION
	  		        "telnet - accepted session"
            ::= { fwSS-telnet 15 }

      fwSS-telnet-rejected-sess  OBJECT-TYPE
            SYNTAX  Unsigned32
            MAX-ACCESS read-only
            STATUS  current
            DESCRIPTION
	  		        "telnet - rejected session"
            ::= { fwSS-telnet 16 }

      fwSS-telnet-auth-failures  OBJECT-TYPE
            SYNTAX  Unsigned32
            MAX-ACCESS read-only
            STATUS  current
            DESCRIPTION
	  		        "telnet - auth failures"
            ::= { fwSS-telnet 17 }

      fwSS-telnet-time-stamp  OBJECT-TYPE
            SYNTAX  DisplayString (SIZE (0..255))
            MAX-ACCESS read-only
            STATUS  current
            DESCRIPTION
	  		        "telnet - time stamp"
            ::= { fwSS-telnet 18 }

      fwSS-telnet-is-alive  OBJECT-TYPE
            SYNTAX  Unsigned32
            MAX-ACCESS read-only
            STATUS  current
            DESCRIPTION
	  		        "telnet - is alive"
            ::= { fwSS-telnet 19 }

      fwSS-rlogin-pid  OBJECT-TYPE
            SYNTAX  Unsigned32
            MAX-ACCESS read-only
            STATUS  current
            DESCRIPTION
	  		        "rlogin - pid"
            ::= { fwSS-rlogin 1 }

      fwSS-rlogin-proto  OBJECT-TYPE
            SYNTAX  Unsigned32
            MAX-ACCESS read-only
            STATUS  current
            DESCRIPTION
	  		        "rlogin - proto"
            ::= { fwSS-rlogin 2 }

      fwSS-rlogin-port  OBJECT-TYPE
            SYNTAX  Gauge32
            MAX-ACCESS read-only
            STATUS  current
            DESCRIPTION
	  		        "rlogin - port"
            ::= { fwSS-rlogin 3 }

      fwSS-rlogin-logical-port  OBJECT-TYPE
            SYNTAX  Gauge32
            MAX-ACCESS read-only
            STATUS  current
            DESCRIPTION
	  		        "rlogin - logical port"
            ::= { fwSS-rlogin 4 }

      fwSS-rlogin-max-avail-socket  OBJECT-TYPE
            SYNTAX  Unsigned32
            MAX-ACCESS read-only
            STATUS  current
            DESCRIPTION
	  		        "rlogin - max avail socket"
            ::= { fwSS-rlogin 5 }

      fwSS-rlogin-socket-in-use-max  OBJECT-TYPE
            SYNTAX  Unsigned32
            MAX-ACCESS read-only
            STATUS  current
            DESCRIPTION
	  		        "rlogin - socket in use max"
            ::= { fwSS-rlogin 6 }

      fwSS-rlogin-socket-in-use-curr  OBJECT-TYPE
            SYNTAX  Unsigned32
            MAX-ACCESS read-only
            STATUS  current
            DESCRIPTION
	  		        "rlogin - socket in use current"
            ::= { fwSS-rlogin 7 }

      fwSS-rlogin-socket-in-use-count  OBJECT-TYPE
            SYNTAX  Unsigned32
            MAX-ACCESS read-only
            STATUS  current
            DESCRIPTION
	  		        "rlogin - socket in use count"
            ::= { fwSS-rlogin 8 }

      fwSS-rlogin-sess-max  OBJECT-TYPE
            SYNTAX  Unsigned32
            MAX-ACCESS read-only
            STATUS  current
            DESCRIPTION
	  		        "rlogin - session max"
            ::= { fwSS-rlogin 9 }

      fwSS-rlogin-sess-curr  OBJECT-TYPE
            SYNTAX  Unsigned32
            MAX-ACCESS read-only
            STATUS  current
            DESCRIPTION
	  		        "rlogin - session current"
            ::= { fwSS-rlogin 10 }

      fwSS-rlogin-sess-count  OBJECT-TYPE
            SYNTAX  Unsigned32
            MAX-ACCESS read-only
            STATUS  current
            DESCRIPTION
	  		        "rlogin - session count"
            ::= { fwSS-rlogin 11 }

      fwSS-rlogin-auth-sess-max  OBJECT-TYPE
            SYNTAX  Unsigned32
            MAX-ACCESS read-only
            STATUS  current
            DESCRIPTION
	  		        "rlogin - auth session max"
            ::= { fwSS-rlogin 12 }

      fwSS-rlogin-auth-sess-curr  OBJECT-TYPE
            SYNTAX  Unsigned32
            MAX-ACCESS read-only
            STATUS  current
            DESCRIPTION
	  		        "rlogin - auth session current"
            ::= { fwSS-rlogin 13 }

      fwSS-rlogin-auth-sess-count  OBJECT-TYPE
            SYNTAX  Unsigned32
            MAX-ACCESS read-only
            STATUS  current
            DESCRIPTION
	  		        "rlogin - auth session count"
            ::= { fwSS-rlogin 14 }

      fwSS-rlogin-accepted-sess  OBJECT-TYPE
            SYNTAX  Unsigned32
            MAX-ACCESS read-only
            STATUS  current
            DESCRIPTION
	  		        "rlogin - accepted session"
            ::= { fwSS-rlogin 15 }

      fwSS-rlogin-rejected-sess  OBJECT-TYPE
            SYNTAX  Unsigned32
            MAX-ACCESS read-only
            STATUS  current
            DESCRIPTION
	  		        "rlogin - rejected session"
            ::= { fwSS-rlogin 16 }

      fwSS-rlogin-auth-failures  OBJECT-TYPE
            SYNTAX  Unsigned32
            MAX-ACCESS read-only
            STATUS  current
            DESCRIPTION
	  		        "rlogin - auth failures"
            ::= { fwSS-rlogin 17 }

      fwSS-rlogin-time-stamp  OBJECT-TYPE
            SYNTAX  DisplayString (SIZE (0..255))
            MAX-ACCESS read-only
            STATUS  current
            DESCRIPTION
	  		        "rlogin - time stamp"
            ::= { fwSS-rlogin 18 }

      fwSS-rlogin-is-alive  OBJECT-TYPE
            SYNTAX  Unsigned32
            MAX-ACCESS read-only
            STATUS  current
            DESCRIPTION
	  		        "rlogin - is alive"
            ::= { fwSS-rlogin 19 }

      fwSS-ufp-ops-ufp-sess-max  OBJECT-TYPE
            SYNTAX  Unsigned32
            MAX-ACCESS read-only
            STATUS  current
            DESCRIPTION
	  		        "ufp - session max"
            ::= { fwSS-ufp 1 }

      fwSS-ufp-ops-ufp-sess-curr  OBJECT-TYPE
            SYNTAX  Unsigned32
            MAX-ACCESS read-only
            STATUS  current
            DESCRIPTION
	  		        "ufp - session current"
            ::= { fwSS-ufp 2 }

      fwSS-ufp-ops-ufp-sess-count  OBJECT-TYPE
            SYNTAX  Unsigned32
            MAX-ACCESS read-only
            STATUS  current
            DESCRIPTION
	  		        "ufp - session count"
            ::= { fwSS-ufp 3 }

      fwSS-ufp-ops-ufp-rej-sess  OBJECT-TYPE
            SYNTAX  Unsigned32
            MAX-ACCESS read-only
            STATUS  current
            DESCRIPTION
	  		        "ufp - rej session"
            ::= { fwSS-ufp 4 }

      fwSS-ufp-time-stamp  OBJECT-TYPE
            SYNTAX  DisplayString (SIZE (0..255))
            MAX-ACCESS read-only
            STATUS  current
            DESCRIPTION
	  		        "ufp - time stamp"
            ::= { fwSS-ufp 5 }

      fwSS-ufp-is-alive  OBJECT-TYPE
            SYNTAX  Unsigned32
            MAX-ACCESS read-only
            STATUS  current
            DESCRIPTION
	  		        "ufp - is alive"
            ::= { fwSS-ufp 6 }

      fwSS-smtp-pid  OBJECT-TYPE
            SYNTAX  Unsigned32
            MAX-ACCESS read-only
            STATUS  current
            DESCRIPTION
	  		        "smtp - pid"
            ::= { fwSS-smtp 1 }

      fwSS-smtp-proto  OBJECT-TYPE
            SYNTAX  Unsigned32
            MAX-ACCESS read-only
            STATUS  current
            DESCRIPTION
	  		        "smtp - proto"
            ::= { fwSS-smtp 2 }

      fwSS-smtp-port  OBJECT-TYPE
            SYNTAX  Gauge32
            MAX-ACCESS read-only
            STATUS  current
            DESCRIPTION
	  		        "smtp - port"
            ::= { fwSS-smtp 3 }

      fwSS-smtp-logical-port  OBJECT-TYPE
            SYNTAX  Gauge32
            MAX-ACCESS read-only
            STATUS  current
            DESCRIPTION
	  		        "smtp - logical port"
            ::= { fwSS-smtp 4 }

      fwSS-smtp-max-avail-socket  OBJECT-TYPE
            SYNTAX  Unsigned32
            MAX-ACCESS read-only
            STATUS  current
            DESCRIPTION
	  		        "smtp - max avail socket"
            ::= { fwSS-smtp 5 }

      fwSS-smtp-socket-in-use-max  OBJECT-TYPE
            SYNTAX  Unsigned32
            MAX-ACCESS read-only
            STATUS  current
            DESCRIPTION
	  		        "smtp - socket in use max"
            ::= { fwSS-smtp 6 }

      fwSS-smtp-socket-in-use-curr  OBJECT-TYPE
            SYNTAX  Unsigned32
            MAX-ACCESS read-only
            STATUS  current
            DESCRIPTION
	  		        "smtp - socket in use current"
            ::= { fwSS-smtp 7 }

      fwSS-smtp-socket-in-use-count  OBJECT-TYPE
            SYNTAX  Unsigned32
            MAX-ACCESS read-only
            STATUS  current
            DESCRIPTION
	  		        "smtp - socket in use count"
            ::= { fwSS-smtp 8 }

      fwSS-smtp-sess-max  OBJECT-TYPE
            SYNTAX  Unsigned32
            MAX-ACCESS read-only
            STATUS  current
            DESCRIPTION
	  		        "smtp - session max"
            ::= { fwSS-smtp 9 }

      fwSS-smtp-sess-curr  OBJECT-TYPE
            SYNTAX  Unsigned32
            MAX-ACCESS read-only
            STATUS  current
            DESCRIPTION
	  		        "smtp - session current"
            ::= { fwSS-smtp 10 }

      fwSS-smtp-sess-count  OBJECT-TYPE
            SYNTAX  Unsigned32
            MAX-ACCESS read-only
            STATUS  current
            DESCRIPTION
	  		        "smtp - session count"
            ::= { fwSS-smtp 11 }

      fwSS-smtp-auth-sess-max  OBJECT-TYPE
            SYNTAX  Unsigned32
            MAX-ACCESS read-only
            STATUS  current
            DESCRIPTION
	  		        "smtp - auth session max"
            ::= { fwSS-smtp 12 }

      fwSS-smtp-auth-sess-curr  OBJECT-TYPE
            SYNTAX  Unsigned32
            MAX-ACCESS read-only
            STATUS  current
            DESCRIPTION
	  		        "smtp - auth session current"
            ::= { fwSS-smtp 13 }

      fwSS-smtp-auth-sess-count  OBJECT-TYPE
            SYNTAX  Unsigned32
            MAX-ACCESS read-only
            STATUS  current
            DESCRIPTION
	  		        "smtp - auth session count"
            ::= { fwSS-smtp 14 }

      fwSS-smtp-accepted-sess  OBJECT-TYPE
            SYNTAX  Unsigned32
            MAX-ACCESS read-only
            STATUS  current
            DESCRIPTION
	  		        "smtp - accepted session"
            ::= { fwSS-smtp 15 }

      fwSS-smtp-rejected-sess  OBJECT-TYPE
            SYNTAX  Unsigned32
            MAX-ACCESS read-only
            STATUS  current
            DESCRIPTION
	  		        "smtp - rejected session"
            ::= { fwSS-smtp 16 }

      fwSS-smtp-auth-failures  OBJECT-TYPE
            SYNTAX  Unsigned32
            MAX-ACCESS read-only
            STATUS  current
            DESCRIPTION
	  		        "smtp - auth failures"
            ::= { fwSS-smtp 17 }

      fwSS-smtp-mail-max  OBJECT-TYPE
            SYNTAX  Unsigned32
            MAX-ACCESS read-only
            STATUS  current
            DESCRIPTION
	  		        "smtp - mail max"
            ::= { fwSS-smtp 18 }

      fwSS-smtp-mail-curr  OBJECT-TYPE
            SYNTAX  Unsigned32
            MAX-ACCESS read-only
            STATUS  current
            DESCRIPTION
	  		        "smtp - mail curr"
            ::= { fwSS-smtp 19 }

      fwSS-smtp-mail-count  OBJECT-TYPE
            SYNTAX  Unsigned32
            MAX-ACCESS read-only
            STATUS  current
            DESCRIPTION
	  		        "smtp - mail count"
            ::= { fwSS-smtp 20 }

      fwSS-smtp-outgoing-mail-max  OBJECT-TYPE
            SYNTAX  Unsigned32
            MAX-ACCESS read-only
            STATUS  current
            DESCRIPTION
	  		        "smtp - outgoing mail max"
            ::= { fwSS-smtp 21 }

      fwSS-smtp-outgoing-mail-curr  OBJECT-TYPE
            SYNTAX  Unsigned32
            MAX-ACCESS read-only
            STATUS  current
            DESCRIPTION
	  		        "smtp - outgoing mail curr"
            ::= { fwSS-smtp 22 }

      fwSS-smtp-outgoing-mail-count  OBJECT-TYPE
            SYNTAX  Unsigned32
            MAX-ACCESS read-only
            STATUS  current
            DESCRIPTION
	  		        "smtp - outgoing mail count"
            ::= { fwSS-smtp 23 }

      fwSS-smtp-max-mail-on-conn  OBJECT-TYPE
            SYNTAX  Unsigned32
            MAX-ACCESS read-only
            STATUS  current
            DESCRIPTION
	  		        "smtp - max mail on conn"
            ::= { fwSS-smtp 24 }

      fwSS-smtp-total-mails  OBJECT-TYPE
            SYNTAX  Unsigned32
            MAX-ACCESS read-only
            STATUS  current
            DESCRIPTION
	  		        "smtp - total mails"
            ::= { fwSS-smtp 25 }

      fwSS-smtp-time-stamp  OBJECT-TYPE
            SYNTAX  DisplayString (SIZE (0..255))
            MAX-ACCESS read-only
            STATUS  current
            DESCRIPTION
	  		        "smtp - time stamp"
            ::= { fwSS-smtp 26 }

      fwSS-smtp-is-alive  OBJECT-TYPE
            SYNTAX  Unsigned32
            MAX-ACCESS read-only
            STATUS  current
            DESCRIPTION
	  		        "smtp - is alive"
            ::= { fwSS-smtp 27 }

      fwSS-smtp-blocked-cnt  OBJECT-TYPE
            SYNTAX  Unsigned32
            MAX-ACCESS read-only
            STATUS  current
            DESCRIPTION
	  		        "count of smtp items blocked, being classified as 'infected' by Anti Virus"
            ::= { fwSS-smtp 28 }

      fwSS-smtp-blocked-total  OBJECT-TYPE
            SYNTAX  Unsigned32
            MAX-ACCESS read-only
            STATUS  current
            DESCRIPTION
	  		        "sum of all the counts of the previous OID (fwss-smtp-blocked-cnt)"
            ::= { fwSS-smtp 29 }

      fwSS-smtp-scanned-total  OBJECT-TYPE
            SYNTAX  Unsigned32
            MAX-ACCESS read-only
            STATUS  current
            DESCRIPTION
	  		        "sum of all the counts of 'blocked' (infected) and 'passed' items"
            ::= { fwSS-smtp 30 }

      fwSS-smtp-blocked-by-file-type  OBJECT-TYPE
            SYNTAX  Unsigned32
            MAX-ACCESS read-only
            STATUS  current
            DESCRIPTION
	  		        "count of smtp items blocked by 'file type' policy in Content Inspection tab in SmartDashboard"
            ::= { fwSS-smtp 31 }

      fwSS-smtp-blocked-by-size-limit  OBJECT-TYPE
            SYNTAX  Unsigned32
            MAX-ACCESS read-only
            STATUS  current
            DESCRIPTION
	  		        "count of smtp items blocked by 'size limit' policy in Content Inspection tab in SmartDashboard"
            ::= { fwSS-smtp 32 }

      fwSS-smtp-blocked-by-archive-limit  OBJECT-TYPE
            SYNTAX  Unsigned32
            MAX-ACCESS read-only
            STATUS  current
            DESCRIPTION
	  		        "count of smtp items blocked by 'archive limit' policy in Content Inspection tab in SmartDashboard"
            ::= { fwSS-smtp 33 }

      fwSS-smtp-blocked-by-internal-error  OBJECT-TYPE
            SYNTAX  Unsigned32
            MAX-ACCESS read-only
            STATUS  current
            DESCRIPTION
	  		        "count of smtp items blocked because of 'internal error' in Content Inspection tab in SmartDashboard"
	  		::= { fwSS-smtp 34 }


      fwSS-smtp-passed-cnt  OBJECT-TYPE
            SYNTAX  Unsigned32
            MAX-ACCESS read-only
            STATUS  current
            DESCRIPTION
	  		        "count of smtp items passed, being classified as 'safe' by Anti Virus"
            ::= { fwSS-smtp 35 }

      fwSS-smtp-passed-by-file-type  OBJECT-TYPE
            SYNTAX  Unsigned32
            MAX-ACCESS read-only
            STATUS  current
            DESCRIPTION
	  		        "count of smtp items allowed (without AV scan) by 'File Type' policy in Content Inspection tab in
	  		         SmartDashboard"
            ::= { fwSS-smtp 36 }

      fwSS-smtp-passed-by-size-limit  OBJECT-TYPE
            SYNTAX  Unsigned32
            MAX-ACCESS read-only
            STATUS  current
            DESCRIPTION
	  		        "count of smtp items allowed (without AV scan) by 'Size Limit' policy in Content Inspection tab in
	  		         SmartDashboard"
            ::= { fwSS-smtp 37 }

      fwSS-smtp-passed-by-archive-limit  OBJECT-TYPE
            SYNTAX  Unsigned32
            MAX-ACCESS read-only
            STATUS  current
            DESCRIPTION
	  		        "count of smtp items allowed (without AV scan) by 'Archive Limit' policy in Content Inspection tab in
	  		         SmartDashboard"
            ::= { fwSS-smtp 38 }

      fwSS-smtp-passed-by-internal-error  OBJECT-TYPE
            SYNTAX  Unsigned32
            MAX-ACCESS read-only
            STATUS  current
            DESCRIPTION
	  		        "count of smtp items allowed (without AV scan) by 'internal error' in Content Inspection tab in
	  		         SmartDashboard"
            ::= { fwSS-smtp 39 }

      fwSS-smtp-passed-total  OBJECT-TYPE
            SYNTAX  Unsigned32
            MAX-ACCESS read-only
            STATUS  current
            DESCRIPTION
	  		        "sum of all the above 'passed' counts - OIDs .35 to .39"
            ::= { fwSS-smtp 40 }

      fwSS-smtp-blocked-by-AV-settings  OBJECT-TYPE
            SYNTAX  Unsigned32
            MAX-ACCESS read-only
            STATUS  current
            DESCRIPTION
	  		        "count of smtp items rejected by Anti Virus as either:
	  		        exceeding size or archive limits, or failed scan due to
	  		        internal error (configured in the 'settings' pane in
	  		        'Content Inspection' tab in SmartDashboard)"
            ::= { fwSS-smtp 41 }

      fwSS-smtp-passed-by-AV-settings  OBJECT-TYPE
            SYNTAX  Unsigned32
            MAX-ACCESS read-only
            STATUS  current
            DESCRIPTION
	  		        "count of smtp items allowed by Anti Virus as either:
	  		        exceeding size or archive limits, or failed scan due to
	  		        internal error (configured in the 'settings' pane in
	  		        'Content Inspection' tab in SmartDashboard)"
            ::= { fwSS-smtp 42 }


      fwSS-POP3-pid  OBJECT-TYPE
            SYNTAX  Unsigned32
            MAX-ACCESS read-only
            STATUS  current
            DESCRIPTION
	  		        "POP3 - pid"
            ::= { fwSS-POP3 1 }

      fwSS-POP3-proto  OBJECT-TYPE
            SYNTAX  Unsigned32
            MAX-ACCESS read-only
            STATUS  current
            DESCRIPTION
	  		        "POP3 - proto"
            ::= { fwSS-POP3 2 }

      fwSS-POP3-port  OBJECT-TYPE
            SYNTAX  Gauge32
            MAX-ACCESS read-only
            STATUS  current
            DESCRIPTION
	  		        "POP3 - port"
            ::= { fwSS-POP3 3 }

      fwSS-POP3-logical-port  OBJECT-TYPE
            SYNTAX  Gauge32
            MAX-ACCESS read-only
            STATUS  current
            DESCRIPTION
	  		        "POP3 - logical port"
            ::= { fwSS-POP3 4 }

      fwSS-POP3-max-avail-socket  OBJECT-TYPE
            SYNTAX  Unsigned32
            MAX-ACCESS read-only
            STATUS  current
            DESCRIPTION
	  		        "POP3 - max avail socket"
            ::= { fwSS-POP3 5 }

      fwSS-POP3-socket-in-use-max  OBJECT-TYPE
            SYNTAX  Unsigned32
            MAX-ACCESS read-only
            STATUS  current
            DESCRIPTION
	  		        "POP3 - socket in use max"
            ::= { fwSS-POP3 6 }

      fwSS-POP3-socket-in-use-curr  OBJECT-TYPE
            SYNTAX  Unsigned32
            MAX-ACCESS read-only
            STATUS  current
            DESCRIPTION
	  		        "POP3 - socket in use current"
            ::= { fwSS-POP3 7 }

      fwSS-POP3-socket-in-use-count  OBJECT-TYPE
            SYNTAX  Unsigned32
            MAX-ACCESS read-only
            STATUS  current
            DESCRIPTION
	  		        "POP3 - socket in use count"
            ::= { fwSS-POP3 8 }

      fwSS-POP3-sess-max  OBJECT-TYPE
            SYNTAX  Unsigned32
            MAX-ACCESS read-only
            STATUS  current
            DESCRIPTION
	  		        "POP3 - session max"
            ::= { fwSS-POP3 9 }

      fwSS-POP3-sess-curr  OBJECT-TYPE
            SYNTAX  Unsigned32
            MAX-ACCESS read-only
            STATUS  current
            DESCRIPTION
	  		        "POP3 - session current"
            ::= { fwSS-POP3 10 }

      fwSS-POP3-sess-count  OBJECT-TYPE
            SYNTAX  Unsigned32
            MAX-ACCESS read-only
            STATUS  current
            DESCRIPTION
	  		        "POP3 - session count"
            ::= { fwSS-POP3 11 }

      fwSS-POP3-auth-sess-max  OBJECT-TYPE
            SYNTAX  Unsigned32
            MAX-ACCESS read-only
            STATUS  current
            DESCRIPTION
	  		        "POP3 - auth session max"
            ::= { fwSS-POP3 12 }

      fwSS-POP3-auth-sess-curr  OBJECT-TYPE
            SYNTAX  Unsigned32
            MAX-ACCESS read-only
            STATUS  current
            DESCRIPTION
	  		        "POP3 - auth session current"
            ::= { fwSS-POP3 13 }

      fwSS-POP3-auth-sess-count  OBJECT-TYPE
            SYNTAX  Unsigned32
            MAX-ACCESS read-only
            STATUS  current
            DESCRIPTION
	  		        "POP3 - auth session count"
            ::= { fwSS-POP3 14 }

      fwSS-POP3-accepted-sess  OBJECT-TYPE
            SYNTAX  Unsigned32
            MAX-ACCESS read-only
            STATUS  current
            DESCRIPTION
	  		        "POP3 - accepted session"
            ::= { fwSS-POP3 15 }

      fwSS-POP3-rejected-sess  OBJECT-TYPE
            SYNTAX  Unsigned32
            MAX-ACCESS read-only
            STATUS  current
            DESCRIPTION
	  		        "POP3 - rejected session"
            ::= { fwSS-POP3 16 }

      fwSS-POP3-auth-failures  OBJECT-TYPE
            SYNTAX  Unsigned32
            MAX-ACCESS read-only
            STATUS  current
            DESCRIPTION
	  		        "POP3 - auth failures"
            ::= { fwSS-POP3 17 }

      fwSS-POP3-mail-max  OBJECT-TYPE
            SYNTAX  Unsigned32
            MAX-ACCESS read-only
            STATUS  current
            DESCRIPTION
	  		        "POP3 - mail max"
            ::= { fwSS-POP3 18 }

      fwSS-POP3-mail-curr  OBJECT-TYPE
            SYNTAX  Unsigned32
            MAX-ACCESS read-only
            STATUS  current
            DESCRIPTION
	  		        "POP3 - mail curr"
            ::= { fwSS-POP3 19 }

      fwSS-POP3-mail-count  OBJECT-TYPE
            SYNTAX  Unsigned32
            MAX-ACCESS read-only
            STATUS  current
            DESCRIPTION
	  		        "POP3 - mail count"
            ::= { fwSS-POP3 20 }

      fwSS-POP3-outgoing-mail-max  OBJECT-TYPE
            SYNTAX  Unsigned32
            MAX-ACCESS read-only
            STATUS  current
            DESCRIPTION
	  		        "POP3 - outgoing mail max"
            ::= { fwSS-POP3 21 }

      fwSS-POP3-outgoing-mail-curr  OBJECT-TYPE
            SYNTAX  Unsigned32
            MAX-ACCESS read-only
            STATUS  current
            DESCRIPTION
	  		        "POP3 - outgoing mail curr"
            ::= { fwSS-POP3 22 }

      fwSS-POP3-outgoing-mail-count  OBJECT-TYPE
            SYNTAX  Unsigned32
            MAX-ACCESS read-only
            STATUS  current
            DESCRIPTION
	  		        "POP3 - outgoing mail count"
            ::= { fwSS-POP3 23 }

      fwSS-POP3-max-mail-on-conn  OBJECT-TYPE
            SYNTAX  Unsigned32
            MAX-ACCESS read-only
            STATUS  current
            DESCRIPTION
	  		        "POP3 - max mail on conn"
            ::= { fwSS-POP3 24 }

      fwSS-POP3-total-mails  OBJECT-TYPE
            SYNTAX  Unsigned32
            MAX-ACCESS read-only
            STATUS  current
            DESCRIPTION
	  		        "POP3 - total mails"
            ::= { fwSS-POP3 25 }

      fwSS-POP3-time-stamp  OBJECT-TYPE
            SYNTAX  DisplayString (SIZE (0..255))
            MAX-ACCESS read-only
            STATUS  current
            DESCRIPTION
	  		        "POP3 - time stamp"
            ::= { fwSS-POP3 26 }

      fwSS-POP3-is-alive  OBJECT-TYPE
            SYNTAX  Unsigned32
            MAX-ACCESS read-only
            STATUS  current
            DESCRIPTION
	  		        "POP3 - is alive"
            ::= { fwSS-POP3 27 }

      fwSS-POP3-blocked-cnt  OBJECT-TYPE
            SYNTAX  Unsigned32
            MAX-ACCESS read-only
            STATUS  current
            DESCRIPTION
	  		        "count of POP3 items blocked, being classified as 'infected' by Anti Virus"
            ::= { fwSS-POP3 28 }

      fwSS-POP3-blocked-total  OBJECT-TYPE
            SYNTAX  Unsigned32
            MAX-ACCESS read-only
            STATUS  current
            DESCRIPTION
	  		        "sum of all the counts of the previous OID (fwss-POP3-blocked-cnt)"
            ::= { fwSS-POP3 29 }

      fwSS-POP3-scanned-total  OBJECT-TYPE
            SYNTAX  Unsigned32
            MAX-ACCESS read-only
            STATUS  current
            DESCRIPTION
	  		        "sum of all the counts of 'blocked' (infected) and 'passed' items"
            ::= { fwSS-POP3 30 }

      fwSS-POP3-blocked-by-file-type  OBJECT-TYPE
            SYNTAX  Unsigned32
            MAX-ACCESS read-only
            STATUS  current
            DESCRIPTION
	  		        "count of POP3 items blocked by 'file type' policy in Content Inspection tab in SmartDashboard"
            ::= { fwSS-POP3 31 }

      fwSS-POP3-blocked-by-size-limit  OBJECT-TYPE
            SYNTAX  Unsigned32
            MAX-ACCESS read-only
            STATUS  current
            DESCRIPTION
	  		        "count of POP3 items blocked by 'size limit' policy in Content Inspection tab in SmartDashboard"
            ::= { fwSS-POP3 32 }

      fwSS-POP3-blocked-by-archive-limit  OBJECT-TYPE
            SYNTAX  Unsigned32
            MAX-ACCESS read-only
            STATUS  current
            DESCRIPTION
	  		        "count of POP3 items blocked by 'archive limit' policy in Content Inspection tab in SmartDashboard"
            ::= { fwSS-POP3 33 }

      fwSS-POP3-blocked-by-internal-error  OBJECT-TYPE
            SYNTAX  Unsigned32
            MAX-ACCESS read-only
            STATUS  current
            DESCRIPTION
	  		        "count of POP3 items blocked because of 'internal error' in Content Inspection tab in SmartDashboard"
	  		::= { fwSS-POP3 34 }


      fwSS-POP3-passed-cnt  OBJECT-TYPE
            SYNTAX  Unsigned32
            MAX-ACCESS read-only
            STATUS  current
            DESCRIPTION
	  		        "count of POP3 items passed, being classified as 'safe' by Anti Virus"
            ::= { fwSS-POP3 35 }

      fwSS-POP3-passed-by-file-type  OBJECT-TYPE
            SYNTAX  Unsigned32
            MAX-ACCESS read-only
            STATUS  current
            DESCRIPTION
	  		        "count of POP3 items allowed (without AV scan) by 'File Type' policy in Content Inspection tab in
	  		         SmartDashboard"
            ::= { fwSS-POP3 36 }

      fwSS-POP3-passed-by-size-limit  OBJECT-TYPE
            SYNTAX  Unsigned32
            MAX-ACCESS read-only
            STATUS  current
            DESCRIPTION
	  		        "count of POP3 items allowed (without AV scan) by 'Size Limit' policy in Content Inspection tab in
	  		         SmartDashboard"
            ::= { fwSS-POP3 37 }

      fwSS-POP3-passed-by-archive-limit  OBJECT-TYPE
            SYNTAX  Unsigned32
            MAX-ACCESS read-only
            STATUS  current
            DESCRIPTION
	  		        "count of POP3 items allowed (without AV scan) by 'Archive Limit' policy in Content Inspection tab in
	  		         SmartDashboard"
            ::= { fwSS-POP3 38 }

      fwSS-POP3-passed-by-internal-error  OBJECT-TYPE
            SYNTAX  Unsigned32
            MAX-ACCESS read-only
            STATUS  current
            DESCRIPTION
	  		        "count of POP3 items allowed (without AV scan) by 'internal error' in Content Inspection tab in
	  		         SmartDashboard"
            ::= { fwSS-POP3 39 }

      fwSS-POP3-passed-total  OBJECT-TYPE
            SYNTAX  Unsigned32
            MAX-ACCESS read-only
            STATUS  current
            DESCRIPTION
	  		        "sum of all the above 'passed' counts - OIDs .35 to .39"
            ::= { fwSS-POP3 40 }

      fwSS-POP3-blocked-by-AV-settings  OBJECT-TYPE
            SYNTAX  Unsigned32
            MAX-ACCESS read-only
            STATUS  current
            DESCRIPTION
	  		        "count of POP3 items rejected by Anti Virus as either:
	  		        exceeding size or archive limits, or failed scan due to
	  		        internal error (configured in the 'settings' pane in
	  		        'Content Inspection' tab in SmartDashboard)"
            ::= { fwSS-POP3 41 }

      fwSS-POP3-passed-by-AV-settings  OBJECT-TYPE
            SYNTAX  Unsigned32
            MAX-ACCESS read-only
            STATUS  current
            DESCRIPTION
	  		        "count of POP3 items allowed by Anti Virus as either:
	  		        exceeding size or archive limits, or failed scan due to
	  		        internal error (configured in the 'settings' pane in
	  		        'Content Inspection' tab in SmartDashboard)"
            ::= { fwSS-POP3 42 }

      fwSS-total-blocked-by-av  OBJECT-TYPE
            SYNTAX  Unsigned32
            MAX-ACCESS read-only
            STATUS  current
            DESCRIPTION
	  		        "total blocked items for all services (HTTP,FTP,POP3,SMTP)"
            ::= { fwSS-av-total 1 }

      fwSS-total-blocked  OBJECT-TYPE
            SYNTAX  Unsigned32
            MAX-ACCESS read-only
            STATUS  current
            DESCRIPTION
	  		        "total blocked items for all policies (filetype,size limit, archive limit,internal error)"
            ::= { fwSS-av-total 2 }

      fwSS-total-scanned  OBJECT-TYPE
            SYNTAX  Unsigned32
            MAX-ACCESS read-only
            STATUS  current
            DESCRIPTION
	  		        "total scanned items for all services (HTTP,FTP,POP3,SMTP)"
            ::= { fwSS-av-total 3 }

      fwSS-total-blocked-by-file-type  OBJECT-TYPE
            SYNTAX  Unsigned32
            MAX-ACCESS read-only
            STATUS  current
            DESCRIPTION
	  		        "total blocked items by 'File Type' policy for all services (HTTP,FTP,POP3,SMTP)"
            ::= { fwSS-av-total 4 }

      fwSS-total-blocked-by-size-limit  OBJECT-TYPE
            SYNTAX  Unsigned32
            MAX-ACCESS read-only
            STATUS  current
            DESCRIPTION
	  		        "total blocked items by 'Size Limit' policy for all services (HTTP,FTP,POP3,SMTP)"
            ::= { fwSS-av-total 5 }

      fwSS-total-blocked-by-archive-limit  OBJECT-TYPE
            SYNTAX  Unsigned32
            MAX-ACCESS read-only
            STATUS  current
            DESCRIPTION
	  		        "total blocked items by 'Archive Limit' policy for all services (HTTP,FTP,POP3,SMTP)"
            ::= { fwSS-av-total 6 }

      fwSS-total-blocked-by-interal-error  OBJECT-TYPE
            SYNTAX  Unsigned32
            MAX-ACCESS read-only
            STATUS  current
            DESCRIPTION
	  		        "total blocked items by 'Internal Error' for all services (HTTP,FTP,POP3,SMTP)"
            ::= { fwSS-av-total 7 }

       fwSS-total-passed-by-av  OBJECT-TYPE
            SYNTAX  Unsigned32
            MAX-ACCESS read-only
            STATUS  current
            DESCRIPTION
	  		        "total passed items for all services (HTTP,FTP,POP3,SMTP)"
            ::= { fwSS-av-total 8 }

      fwSS-total-passed-by-file-type  OBJECT-TYPE
            SYNTAX  Unsigned32
            MAX-ACCESS read-only
            STATUS  current
            DESCRIPTION
	  		        "total passed items by 'File Type' policy for all services (HTTP,FTP,POP3,SMTP)"
            ::= { fwSS-av-total 9 }

      fwSS-total-passed-by-size-limit  OBJECT-TYPE
            SYNTAX  Unsigned32
            MAX-ACCESS read-only
            STATUS  current
            DESCRIPTION
	  		        "total passed items by 'Size Limit' policy for all services (HTTP,FTP,POP3,SMTP)"
            ::= { fwSS-av-total 10 }

      fwSS-total-passed-by-archive-limit  OBJECT-TYPE
            SYNTAX  Unsigned32
            MAX-ACCESS read-only
            STATUS  current
            DESCRIPTION
	  		        "total blocked items by 'Archive Limit' policy for all services (HTTP,FTP,POP3,SMTP)"
            ::= { fwSS-av-total 11 }

      fwSS-total-passed-by-interal-error  OBJECT-TYPE
            SYNTAX  Unsigned32
            MAX-ACCESS read-only
            STATUS  current
            DESCRIPTION
	  		        "total blocked items by 'Internal Error' for all services (HTTP,FTP,POP3,SMTP)"
            ::= { fwSS-av-total 12 }

      fwSS-total-passed  OBJECT-TYPE
            SYNTAX  Unsigned32
            MAX-ACCESS read-only
            STATUS  current
            DESCRIPTION
	  		        "total passed items for all policies (filetype,size limit, archive limit,internal error)"
            ::= { fwSS-av-total 13 }

	  fwSS-total-blocked-by-av-settings  OBJECT-TYPE
            SYNTAX  Unsigned32
            MAX-ACCESS read-only
            STATUS  current
            DESCRIPTION
	  		        "total blocked items by AV settings"
            ::= { fwSS-av-total 14 }

      fwSS-total-passed-by-av-settings  OBJECT-TYPE
            SYNTAX  Unsigned32
            MAX-ACCESS read-only
            STATUS  current
            DESCRIPTION
	  		        "total passed items by AV settings"
            ::= { fwSS-av-total 15 }

      fwConnectionsStatConnectionsTcp  OBJECT-TYPE
            SYNTAX  Unsigned32
            MAX-ACCESS read-only
            STATUS  current
            DESCRIPTION
                                "tcp connections passing through the FireWall-1 Module"
            ::= { fwConnectionsStat 1 }

      fwConnectionsStatConnectionsUdp  OBJECT-TYPE
            SYNTAX  Unsigned32
            MAX-ACCESS read-only
            STATUS  current
            DESCRIPTION
                                "udp connections passing through the FireWall-1 Module"
            ::= { fwConnectionsStat 2 }

      fwConnectionsStatConnectionsIcmp  OBJECT-TYPE
            SYNTAX  Unsigned32
            MAX-ACCESS read-only
            STATUS  current
            DESCRIPTION
                                "icmp connections passing through the FireWall-1 Module"
            ::= { fwConnectionsStat 3 }

      fwConnectionsStatConnectionsOther  OBJECT-TYPE
            SYNTAX  Unsigned32
            MAX-ACCESS read-only
            STATUS  current
            DESCRIPTION
                                "other connections passing through the FireWall-1 Module"
            ::= { fwConnectionsStat 4 }

      fwConnectionsStatConnections  OBJECT-TYPE
            SYNTAX  Unsigned32
            MAX-ACCESS read-only
            STATUS  current
            DESCRIPTION
	  		        "total connections passing through the FireWall-1 Module"
            ::= { fwConnectionsStat 5 }

      fwConnectionsStatConnectionRate  OBJECT-TYPE
            SYNTAX  Unsigned32
            MAX-ACCESS read-only
            STATUS  current
            DESCRIPTION
	  		        "connection rate (per second) passing through the FireWall-1 Module"
            ::= { fwConnectionsStat 6 }


      fwHmem64-block-size	 OBJECT-TYPE
            SYNTAX  Counter64
            MAX-ACCESS read-only
            STATUS  current
            DESCRIPTION
	  		        "hmem - block size"
            ::= { fwHmem64 1 }

	  fwHmem64-requested-bytes  OBJECT-TYPE
            SYNTAX  Counter64
            MAX-ACCESS read-only
            STATUS  current
            DESCRIPTION
	  		        "hmem - requested bytes"
            ::= { fwHmem64 2 }

	  fwHmem64-initial-allocated-bytes  OBJECT-TYPE
            SYNTAX  Counter64
            MAX-ACCESS read-only
            STATUS  current
            DESCRIPTION
	  		        "hmem - initial allocated bytes"
            ::= { fwHmem64 3 }

	  fwHmem64-initial-allocated-blocks OBJECT-TYPE
            SYNTAX  Unsigned32
            MAX-ACCESS read-only
            STATUS  current
            DESCRIPTION
	  		        "hmem - initial allocated blocks"
            ::= { fwHmem64 4 }

	  fwHmem64-initial-allocated-pools  OBJECT-TYPE
            SYNTAX  Unsigned32
            MAX-ACCESS read-only
            STATUS  current
            DESCRIPTION
	  		        "hmem - initial allocated pools"
            ::= { fwHmem64 5 }

	  fwHmem64-current-allocated-bytes OBJECT-TYPE
            SYNTAX  Counter64
            MAX-ACCESS read-only
            STATUS  current
            DESCRIPTION
	  		        "hmem - current allocated bytes"
            ::= { fwHmem64 6 }

	  fwHmem64-current-allocated-blocks OBJECT-TYPE
            SYNTAX  Unsigned32
            MAX-ACCESS read-only
            STATUS  current
            DESCRIPTION
	  		        "hmem - current allocated blocks"
            ::= { fwHmem64 7 }

	  fwHmem64-current-allocated-pools  OBJECT-TYPE
            SYNTAX  Unsigned32
            MAX-ACCESS read-only
            STATUS  current
            DESCRIPTION
	  		        "hmem - current allocated pools"
            ::= { fwHmem64 8 }

	  fwHmem64-maximum-bytes  OBJECT-TYPE
            SYNTAX  Counter64
            MAX-ACCESS read-only
            STATUS  current
            DESCRIPTION
	  		        "hmem - maximum bytes"
            ::= { fwHmem64 9 }

	  fwHmem64-maximum-pools  OBJECT-TYPE
            SYNTAX  Unsigned32
            MAX-ACCESS read-only
            STATUS  current
            DESCRIPTION
	  		        "hmem - maximum pools"
            ::= { fwHmem64 10 }

	  fwHmem64-bytes-used  OBJECT-TYPE
            SYNTAX  Counter64
            MAX-ACCESS read-only
            STATUS  current
            DESCRIPTION
	  		        "hmem - bytes used"
            ::= { fwHmem64 11 }

	  fwHmem64-blocks-used  OBJECT-TYPE
            SYNTAX  Unsigned32
            MAX-ACCESS read-only
            STATUS  current
            DESCRIPTION
	  		        "hmem - blocks used"
            ::= { fwHmem64 12 }

	  fwHmem64-bytes-unused  OBJECT-TYPE
            SYNTAX  Counter64
            MAX-ACCESS read-only
            STATUS  current
            DESCRIPTION
	  		        "hmem - bytes unused"
            ::= { fwHmem64 13 }

	  fwHmem64-blocks-unused  OBJECT-TYPE
            SYNTAX  Unsigned32
            MAX-ACCESS read-only
            STATUS  current
            DESCRIPTION
	  		        "hmem - blocks unused"
            ::= { fwHmem64 14 }

	  fwHmem64-bytes-peak  OBJECT-TYPE
            SYNTAX  Counter64
            MAX-ACCESS read-only
            STATUS  current
            DESCRIPTION
	  		        "hmem - bytes peak"
            ::= { fwHmem64 15 }

	  fwHmem64-blocks-peak  OBJECT-TYPE
            SYNTAX  Unsigned32
            MAX-ACCESS read-only
            STATUS  current
            DESCRIPTION
	  		        "hmem - blocks peak"
            ::= { fwHmem64 16 }

	  fwHmem64-bytes-internal-use  OBJECT-TYPE
            SYNTAX  Unsigned32
            MAX-ACCESS read-only
            STATUS  current
            DESCRIPTION
	  		        "hmem - bytes internal use"
            ::= { fwHmem64 17 }

	  fwHmem64-number-of-items  OBJECT-TYPE
            SYNTAX  Counter64
            MAX-ACCESS read-only
            STATUS  current
            DESCRIPTION
	  		        "hmem - number of items"
            ::= { fwHmem64 18 }

	  fwHmem64-alloc-operations OBJECT-TYPE
            SYNTAX  Unsigned32
            MAX-ACCESS read-only
            STATUS  current
            DESCRIPTION
	  		        "hmem - alloc operations"
            ::= { fwHmem64 19 }

	  fwHmem64-free-operations OBJECT-TYPE
            SYNTAX  Unsigned32
            MAX-ACCESS read-only
            STATUS  current
            DESCRIPTION
	  		        "hmem - free operations"
            ::= { fwHmem64 20 }

	  fwHmem64-failed-alloc  OBJECT-TYPE
            SYNTAX  Unsigned32
            MAX-ACCESS read-only
            STATUS  current
            DESCRIPTION
	  		        "hmem - failed alloc"
            ::= { fwHmem64 21 }

	  fwHmem64-failed-free  OBJECT-TYPE
            SYNTAX  Unsigned32
            MAX-ACCESS read-only
            STATUS  current
            DESCRIPTION
	  		        "hmem - failed free"
            ::= { fwHmem64 22 }


	  fwNetIfTable OBJECT-TYPE
	          SYNTAX  SEQUENCE OF  FwNetIfEntry
			  MAX-ACCESS  not-accessible
			  STATUS  current
			  DESCRIPTION "No description available"
			   ::= { fw 27 }


	  fwNetIfEntry OBJECT-TYPE
	          SYNTAX  FwNetIfEntry
	          MAX-ACCESS  not-accessible
	          STATUS  current
	          DESCRIPTION "No description available"
	          INDEX   { fwNetIfIndex }
	          ::= { fwNetIfTable 1 }

      FwNetIfEntry ::=
              SEQUENCE {
                 fwNetIfIndex
                      Unsigned32,
                 fwNetIfName
                      DisplayString,
                 fwNetIfIPAddr
					  IpAddress,
				 fwNetIfNetmask
					  IpAddress,
	             fwNetIfFlags
					  Unsigned32,
                 fwNetIfPeerName
                      DisplayString,
                 fwNetIfRemoteIp
                     IpAddress,
				 fwNetIfTopology
                      Unsigned32,
				 fwNetIfProxyName
                      DisplayString,
				 fwNetIfSlaves
                      DisplayString,
                 fwNetIfPorts
                 	  DisplayString,
		fwNetIfIPV6Addr
                      OCTET STRING,
                 fwNetIfIPV6AddrLen
                 	  Unsigned32
              }

      fwNetIfIndex OBJECT-TYPE
            SYNTAX Unsigned32
            MAX-ACCESS not-accessible
            STATUS  current
            DESCRIPTION "No description available"
            ::= { fwNetIfEntry 1 }

      fwNetIfName OBJECT-TYPE
            SYNTAX  DisplayString
            MAX-ACCESS read-only
            STATUS  current
			DESCRIPTION
	  		        "Interface Name"
            ::= { fwNetIfEntry 2 }

      fwNetIfIPAddr OBJECT-TYPE
            SYNTAX  IpAddress
            MAX-ACCESS read-only
            STATUS  current
            DESCRIPTION
	  		        "IPv4 Address (an empty address will be denoted by 0.0.0.0)"
            ::= { fwNetIfEntry 3 }

      fwNetIfNetmask OBJECT-TYPE
            SYNTAX  IpAddress
            MAX-ACCESS read-only
            STATUS  current
            DESCRIPTION
	  		        "Network Mask of the GW behind the Bridge (an empty mask will be denoted by 0.0.0.0)"
            ::= { fwNetIfEntry 4 }

	  fwNetIfFlags OBJECT-TYPE
            SYNTAX  Unsigned32
            MAX-ACCESS read-only
            STATUS  current
            DESCRIPTION
	  		        "Flags indicating the type(s) of the device:
	  		         Possible values include:
	  		         VPN tunnel device	1
					 Unnumbered device	2
					 Proxy device		4
					 Bridge			8
					 Bond			16
					 Slave			32 (e.g. belongs to a bond or bridge device)"
            ::= { fwNetIfEntry 5 }

	  fwNetIfPeerName OBJECT-TYPE
            SYNTAX  DisplayString
            MAX-ACCESS read-only
            STATUS  current
            DESCRIPTION
	  		        "VPN Tunnel Peer Name"
            ::= { fwNetIfEntry 6 }


      fwNetIfRemoteIp OBJECT-TYPE
            SYNTAX  IpAddress
            MAX-ACCESS read-only
            STATUS  current
            DESCRIPTION
	  		        "VPN Tunnel Remote IP"
            ::= { fwNetIfEntry 7 }

      fwNetIfTopology OBJECT-TYPE
            SYNTAX  Unsigned32
            MAX-ACCESS read-only
            STATUS  current
            DESCRIPTION
	  		        "Planned for future use only - currently should have the constant value of 4"
            ::= { fwNetIfEntry 8 }

      fwNetIfProxyName OBJECT-TYPE
            SYNTAX  DisplayString
            MAX-ACCESS read-only
            STATUS  current
            DESCRIPTION
	  		        "VPN Tunnel Proxy Name"
            ::= { fwNetIfEntry 9 }

      fwNetIfSlaves OBJECT-TYPE
            SYNTAX  DisplayString
            MAX-ACCESS read-only
            STATUS  current
            DESCRIPTION
	  		        "If this device is acting as a master, this string contains space separated names of all its slave devices."
            ::= { fwNetIfEntry 10 }

      fwNetIfPorts OBJECT-TYPE
            SYNTAX  DisplayString
            MAX-ACCESS read-only
            STATUS  current
            DESCRIPTION
            		"Given an interface which is a port in a bridge, list all its siblings interfaces. The interfaces are separated by a single space."
            ::= { fwNetIfEntry 11 }

      fwNetIfIPV6Addr OBJECT-TYPE
            SYNTAX OCTET STRING
            MAX-ACCESS read-only
            STATUS  current
            DESCRIPTION
                        " IPv6 Address given in an hexa format ."
            ::= { fwNetIfEntry 12 }

      fwNetIfIPV6AddrLen OBJECT-TYPE
            SYNTAX  Unsigned32
            MAX-ACCESS read-only
            STATUS  current
            DESCRIPTION
                        "IPv6 Address length"
            ::= { fwNetIfEntry 13 }

      fwLSConn    OBJECT IDENTIFIER ::= { fw 30 }

	  fwLSConnOverall  OBJECT-TYPE
            SYNTAX  Integer32
            MAX-ACCESS read-only
            STATUS  current
            DESCRIPTION
	  		        "Connectivity with log servers, Ok(0), Warnning(1) and Error(2)"
            ::= { fwLSConn 1 }

      fwLSConnOverallDesc  OBJECT-TYPE
            SYNTAX  DisplayString
            MAX-ACCESS read-only
            STATUS  current
            DESCRIPTION
	  		        "Description of connectivity status with log servers"
            ::= { fwLSConn 2 }

	  fwLSConnTable OBJECT-TYPE
	          SYNTAX  SEQUENCE OF  FwLSConnEntry
			  MAX-ACCESS  not-accessible
			  STATUS  current
			  DESCRIPTION "No description available"
			   ::= { fwLSConn 3 }

	  fwLocalLoggingDesc  OBJECT-TYPE
            SYNTAX  DisplayString
            MAX-ACCESS read-only
            STATUS  current
            DESCRIPTION
	  		        "Description of local logging status"
            ::= { fwLSConn 4 }

	  fwLocalLoggingStat  OBJECT-TYPE
            SYNTAX  Integer32
            MAX-ACCESS read-only
            STATUS  current
            DESCRIPTION
	  		        "Writing logs localy, To log servers(0), Local configured (1) Local due to connectivity(2) Local due to high rate(3)"
            ::= { fwLSConn 5 }

	  fwLocalLoggingWriteRate  OBJECT-TYPE
            SYNTAX  Unsigned32
            MAX-ACCESS read-only
            STATUS  current
            DESCRIPTION
	  		        "Local Logging Writing Rate"
            ::= { fwLSConn 6 }

	  fwLoggingHandlingRate  OBJECT-TYPE
            SYNTAX  Unsigned32
            MAX-ACCESS read-only
            STATUS  current
            DESCRIPTION
	  		        "Total Logging Handling Rate (Local writing and Sending to Log Server)"
            ::= { fwLSConn 7 }

	  fwLSConnEntry OBJECT-TYPE
	          SYNTAX  FwLSConnEntry
	          MAX-ACCESS  not-accessible
	          STATUS  current
	          DESCRIPTION "No description available"
	          INDEX   { fwLSConnIndex }
	          ::= { fwLSConnTable 1 }

      FwLSConnEntry ::=
              SEQUENCE {
                 fwLSConnIndex
                      Unsigned32,
                 fwLSConnName
                      DisplayString,
                 fwLSConnState
					  Unsigned32,
				 fwLSConnStateDesc
					  DisplayString,
				fwLSConnSendRate
                      Unsigned32
              }

      fwLSConnIndex OBJECT-TYPE
            SYNTAX  Unsigned32
            MAX-ACCESS not-accessible
            STATUS  current
            DESCRIPTION "No description available"
            ::= { fwLSConnEntry 1 }

      fwLSConnName OBJECT-TYPE
            SYNTAX  DisplayString
            MAX-ACCESS read-only
            STATUS  current
			DESCRIPTION
	  		        "Log Server Name\IP"
            ::= { fwLSConnEntry 2 }

      fwLSConnState OBJECT-TYPE
            SYNTAX  Unsigned32
            MAX-ACCESS read-only
            STATUS  current
            DESCRIPTION
	  		        "Connectivity state with the log server Ok(0), Error(1) and Not Active(2)"
            ::= { fwLSConnEntry 3 }

      fwLSConnStateDesc OBJECT-TYPE
            SYNTAX  DisplayString
            MAX-ACCESS read-only
            STATUS  current
            DESCRIPTION
	  		        "Description of connectivity state with the log server"
            ::= { fwLSConnEntry 4 }

      fwLSConnSendRate OBJECT-TYPE
            SYNTAX  Unsigned32
            MAX-ACCESS read-only
            STATUS  current
            DESCRIPTION
	  		        "Logs Sending Rate to the Log Server"
            ::= { fwLSConnEntry 5 }

      fwInstancesCPU OBJECT IDENTIFIER ::= { fw 31 }

      fwInstancesCPUTable OBJECT-TYPE
            SYNTAX  SEQUENCE OF  FwInstancesCPUEntry
            MAX-ACCESS  not-accessible
            STATUS  current
            DESCRIPTION
	  		        "OID to present the CPU usage of all instances of the fw"
            ::= { fwInstancesCPU 1 }

      fwInstancesCPUEntry OBJECT-TYPE
            SYNTAX  FwInstancesCPUEntry
            MAX-ACCESS  not-accessible
            STATUS  current
            DESCRIPTION
	  		        "No description available"
			INDEX   { fwInstancesCPUInstanceName }
            ::= { fwInstancesCPUTable 1 }

      FwInstancesCPUEntry ::=
              SEQUENCE {
                 fwInstancesCPUInstanceName
                      DisplayString,
                 fwInstancesCPUUsage
                      Unsigned32
              }

      fwInstancesCPUInstanceName OBJECT-TYPE
            SYNTAX  DisplayString
            MAX-ACCESS read-only
            STATUS  current
            DESCRIPTION
	  		        "Name of instance thread"
            ::= { fwInstancesCPUEntry 1 }


      fwInstancesCPUUsage OBJECT-TYPE
            SYNTAX  Unsigned32
            MAX-ACCESS read-only
            STATUS  current
            DESCRIPTION
	  		        "Current CPU usage percent"
            ::= { fwInstancesCPUEntry 2 }

      fwInstancesCPUTotal OBJECT-TYPE
            SYNTAX  Unsigned32
            MAX-ACCESS  read-only
            STATUS  current
            DESCRIPTION
	  		        "OID to present the total CPU usage of all instances of the fw"
            ::= { fwInstancesCPU 2 }


	fwSXLGroup OBJECT IDENTIFIER ::= { sxl 1 }

	fwSXLStatus OBJECT-TYPE
	SYNTAX Gauge32
	MAX-ACCESS read-only
	STATUS current
	DESCRIPTION
		"The current status of SecureXL. "
	::= { fwSXLGroup 1 }

	fwSXLConnsExisting OBJECT-TYPE
	SYNTAX Gauge32
	MAX-ACCESS read-only
	STATUS current
	DESCRIPTION
                "The number of existing connections handled by SecureXL. "
        ::= { fwSXLGroup 2 }

	fwSXLConnsAdded OBJECT-TYPE
	SYNTAX Gauge32
	MAX-ACCESS read-only
	STATUS current
	DESCRIPTION
                "The number of connections added by SecureXL. "
        ::= { fwSXLGroup 3 }

	fwSXLConnsDeleted OBJECT-TYPE
	SYNTAX Gauge32
	MAX-ACCESS read-only
	STATUS current
	DESCRIPTION
                "The number of connections deleted by SecureXL. "
        ::= { fwSXLGroup 4 }

	fwSXLStatistics OBJECT IDENTIFIER ::= { fwSXLGroup 5 }

	fwSXLStatisticsAggregate OBJECT IDENTIFIER ::= { fwSXLStatistics 1 }

	fwSXLStatAggregateThroughputTable OBJECT-TYPE
	          SYNTAX  SEQUENCE OF  FwSXLStatAggregateThroughputEntry
			  MAX-ACCESS  not-accessible
			  STATUS  current
			  DESCRIPTION "No description available"
			   ::= { fwSXLStatisticsAggregate 1 }

	fwSXLStatAggregateThroughputEntry OBJECT-TYPE
	          SYNTAX  FwSXLStatAggregateThroughputEntry
	          MAX-ACCESS  not-accessible
	          STATUS  current
	          DESCRIPTION "No description available"
	          INDEX   { fwSXLAggrThroughputIndex }
	          ::= { fwSXLStatAggregateThroughputTable 1 }

    FwSXLStatAggregateThroughputEntry ::=
              SEQUENCE {
                 fwSXLAggrThroughputIndex
                      Unsigned32,
                 fwSXLAggrRxMbits
					  Gauge32,
				 fwSXLAggrTxMbits
					  Gauge32,
				 fwSXLAggrInboundKbitsPerSecond
        		      Counter64,
				 fwSXLAggrOutboundKbitsPerSecond
					  Counter64,
				 fwSXLAggrInboundpacketsPerSecond
					  Counter64,
				 fwSXLAggrOutboundpacketsPerSecond
					  Counter64,
				 fwSXLAggrConnectionsPerSecond
					  Counter64,
				 fwSXLAggrConcurrentConnections
					  Counter64
				}

	fwSXLAggrThroughputIndex OBJECT-TYPE
	SYNTAX Unsigned32
	MAX-ACCESS not-accessible
	STATUS current
	DESCRIPTION
                "Dummy index. "
        ::= { fwSXLStatAggregateThroughputEntry 1 }

	fwSXLAggrRxMbits OBJECT-TYPE
	SYNTAX Gauge32
	MAX-ACCESS read-only
	STATUS current
	DESCRIPTION
                "Number of RX bytes. "
        ::= { fwSXLStatAggregateThroughputEntry 2 }

	fwSXLAggrTxMbits OBJECT-TYPE
	SYNTAX Gauge32
	MAX-ACCESS read-only
	STATUS current
	DESCRIPTION
                "Number of TX bytes. "
        ::= { fwSXLStatAggregateThroughputEntry 3 }

	fwSXLAggrInboundKbitsPerSecond OBJECT-TYPE
	SYNTAX Counter64
	MAX-ACCESS read-only
	STATUS current
	DESCRIPTION
                "Inbound Kbits per second. "
        ::= { fwSXLStatAggregateThroughputEntry 4 }

	fwSXLAggrOutboundKbitsPerSecond OBJECT-TYPE
	SYNTAX Counter64
	MAX-ACCESS read-only
	STATUS current
	DESCRIPTION
                "Outbound Kbits per second. "
        ::= { fwSXLStatAggregateThroughputEntry 5 }

	fwSXLAggrInboundpacketsPerSecond OBJECT-TYPE
	SYNTAX Counter64
	MAX-ACCESS read-only
	STATUS current
	DESCRIPTION
                "Inbound packets per second. "
        ::= { fwSXLStatAggregateThroughputEntry 6 }

	fwSXLAggrOutboundpacketsPerSecond OBJECT-TYPE
	SYNTAX Counter64
	MAX-ACCESS read-only
	STATUS current
	DESCRIPTION
                "Outbound packets per second. "
        ::= { fwSXLStatAggregateThroughputEntry 7 }

	fwSXLAggrConnectionsPerSecond OBJECT-TYPE
	SYNTAX Counter64
	MAX-ACCESS read-only
	STATUS current
	DESCRIPTION
                "Connection rate per second. "
        ::= { fwSXLStatAggregateThroughputEntry 8 }

	fwSXLAggrConcurrentConnections OBJECT-TYPE
	SYNTAX Counter64
	MAX-ACCESS read-only
	STATUS current
	DESCRIPTION
                "Concurrent connections number. "
        ::= { fwSXLStatAggregateThroughputEntry 9 }

	fwSXLStatAggregateNotificationsTable OBJECT-TYPE
	          SYNTAX  SEQUENCE OF  FwSXLStatAggregateNotificationsEntry
			  MAX-ACCESS  not-accessible
			  STATUS  current
			  DESCRIPTION "No description available"
			   ::= { fwSXLStatisticsAggregate 2 }

	fwSXLStatAggregateNotificationsEntry OBJECT-TYPE
	          SYNTAX  FwSXLStatAggregateNotificationsEntry
	          MAX-ACCESS  not-accessible
	          STATUS  current
	          DESCRIPTION "No description available"
	          INDEX   { fwSXLAggrNotificationsIndex }
	          ::= { fwSXLStatAggregateNotificationsTable 1 }

	FwSXLStatAggregateNotificationsEntry ::=
              SEQUENCE {
                 fwSXLAggrNotificationsIndex
                      Unsigned32,
				 fwSXLAggrPpak2FwNotificationsSuccessful
					  Counter64,
				 fwSXLAggrPpak2FwNotificationsFailure
					  Counter64,
				 fwSXLAggrFw2PpakNotificationsSuccessful
					  Counter64,
				 fwSXLAggrFw2PpakNotificationsFailure
					  Counter64
				}

	fwSXLAggrNotificationsIndex OBJECT-TYPE
	SYNTAX Unsigned32
	MAX-ACCESS not-accessible
	STATUS current
	DESCRIPTION
                "Dummy index. "
        ::= { fwSXLStatAggregateNotificationsEntry 1 }

	fwSXLAggrPpak2FwNotificationsSuccessful OBJECT-TYPE
	SYNTAX Counter64
	MAX-ACCESS read-only
	STATUS current
	DESCRIPTION
                "Number of successful notifications from ppak to firewall. "
        ::= { fwSXLStatAggregateNotificationsEntry 2 }

	fwSXLAggrPpak2FwNotificationsFailure OBJECT-TYPE
	SYNTAX Counter64
	MAX-ACCESS read-only
	STATUS current
	DESCRIPTION
                "Number of failed notifications from ppak to firewall. "
        ::= { fwSXLStatAggregateNotificationsEntry 3 }

	fwSXLAggrFw2PpakNotificationsSuccessful OBJECT-TYPE
	SYNTAX Counter64
	MAX-ACCESS read-only
	STATUS current
	DESCRIPTION
                "Number of successful notifications from firewall to ppak. "
        ::= { fwSXLStatAggregateNotificationsEntry 4 }

	fwSXLAggrFw2PpakNotificationsFailure OBJECT-TYPE
	SYNTAX Counter64
	MAX-ACCESS read-only
	STATUS current
	DESCRIPTION
                "Number of failed notifications from firewall to ppak. "
        ::= { fwSXLStatAggregateNotificationsEntry 5 }

	fwSXLStatAggregateDropsTable OBJECT-TYPE
	          SYNTAX  SEQUENCE OF  FwSXLStatAggregateDropsEntry
			  MAX-ACCESS  not-accessible
			  STATUS  current
			  DESCRIPTION "No description available"
			   ::= { fwSXLStatisticsAggregate 3 }

	fwSXLStatAggregateDropsEntry OBJECT-TYPE
	          SYNTAX  FwSXLStatAggregateDropsEntry
	          MAX-ACCESS  not-accessible
	          STATUS  current
	          DESCRIPTION "No description available"
	          INDEX   { fwSXLAggrDropsIndex }
	          ::= { fwSXLStatAggregateDropsTable 1 }

	FwSXLStatAggregateDropsEntry ::=
              SEQUENCE {
                 fwSXLAggrDropsIndex
                      Unsigned32,
				 fwSXLAggrDropsTotPackets
					  Counter64,
				 fwSXLAggrDropsPxlDecision
					  INTEGER,
				 fwSXLAggrDropsFragmentationError
					  INTEGER,
				 fwSXLAggrDropsF2FNotAllowed
					  INTEGER,
				 fwSXLAggrDropsHeavyLoadTcpViolation
					  INTEGER,
				 fwSXLAggrDropsCorruptPacket
					  INTEGER,
				 fwSXLAggrDropsHeavyLoadNewConnection
					  INTEGER,
				 fwSXLAggrDropsClearPacketOnVPN
					  INTEGER,
				 fwSXLAggrDropsEncryptionFailed
					  INTEGER,
				 fwSXLAggrDropsDropTemplate
					  INTEGER,
				 fwSXLAggrDropsDecryptionFailed
					  INTEGER,
				 fwSXLAggrDropsOutboundConnNotFound
					  INTEGER,
				 fwSXLAggrDropsInterfaceDown
					  INTEGER,
				 fwSXLAggrDropsClusterError
					  INTEGER,
				 fwSXLAggrDropsXmlError
					  INTEGER,
				 fwSXLAggrDropsAntiSpoofing
					  INTEGER,
				 fwSXLAggrDropsSanityError
					  INTEGER,
				 fwSXLAggrDropsQxlDecision
					  INTEGER,
				 fwSXLAggrDropsLoopPrevention
					  INTEGER
				}

	fwSXLAggrDropsIndex OBJECT-TYPE
	SYNTAX Unsigned32
	MAX-ACCESS not-accessible
	STATUS current
	DESCRIPTION
                "Dummy index. "
        ::= { fwSXLStatAggregateDropsEntry 1 }

	fwSXLAggrDropsTotPackets OBJECT-TYPE
	SYNTAX Counter64
	MAX-ACCESS read-only
	STATUS current
	DESCRIPTION
                "Total dropped packets number. "
        ::= { fwSXLStatAggregateDropsEntry 2 }

	fwSXLAggrDropsPxlDecision OBJECT-TYPE
	SYNTAX  Integer32
	MAX-ACCESS read-only
	STATUS current
	DESCRIPTION
                "Packets dropped due to PXL decision. "
        ::= { fwSXLStatAggregateDropsEntry 3 }

	fwSXLAggrDropsFragmentationError OBJECT-TYPE
	SYNTAX  Integer32
	MAX-ACCESS read-only
	STATUS current
	DESCRIPTION
                "Packets dropped due to fragmentation error. "
        ::= { fwSXLStatAggregateDropsEntry 4 }

	fwSXLAggrDropsF2FNotAllowed OBJECT-TYPE
	SYNTAX  Integer32
	MAX-ACCESS read-only
	STATUS current
	DESCRIPTION
                "Packets dropped due to F2F not being allowed. "
        ::= { fwSXLStatAggregateDropsEntry 5 }

	fwSXLAggrDropsHeavyLoadTcpViolation OBJECT-TYPE
	SYNTAX  Integer32
	MAX-ACCESS read-only
	STATUS current
	DESCRIPTION
                "Packets dropped due to TCP violation during heavy load. "
        ::= { fwSXLStatAggregateDropsEntry 6 }

	fwSXLAggrDropsCorruptPacket OBJECT-TYPE
	SYNTAX  Integer32
	MAX-ACCESS read-only
	STATUS current
	DESCRIPTION
                "Packets dropped due to being corrupt. "
        ::= { fwSXLStatAggregateDropsEntry 7 }

	fwSXLAggrDropsHeavyLoadNewConnection OBJECT-TYPE
	SYNTAX  Integer32
	MAX-ACCESS read-only
	STATUS current
	DESCRIPTION
                "Packets dropped due to being new connections during heavy load. "
        ::= { fwSXLStatAggregateDropsEntry 8 }

	fwSXLAggrDropsClearPacketOnVPN OBJECT-TYPE
	SYNTAX  Integer32
	MAX-ACCESS read-only
	STATUS current
	DESCRIPTION
                "VPN packets dropped due to being sent unencrypted. "
        ::= { fwSXLStatAggregateDropsEntry 9 }

	fwSXLAggrDropsEncryptionFailed OBJECT-TYPE
	SYNTAX  Integer32
	MAX-ACCESS read-only
	STATUS current
	DESCRIPTION
                "Packets dropped due to encryption failure. "
        ::= { fwSXLStatAggregateDropsEntry 10 }

	fwSXLAggrDropsDropTemplate OBJECT-TYPE
	SYNTAX  Integer32
	MAX-ACCESS read-only
	STATUS current
	DESCRIPTION
                "Packets dropped due to drop template. "
        ::= { fwSXLStatAggregateDropsEntry 11 }

	fwSXLAggrDropsDecryptionFailed OBJECT-TYPE
	SYNTAX  Integer32
	MAX-ACCESS read-only
	STATUS current
	DESCRIPTION
                "Packets dropped due to decryption failure. "
        ::= { fwSXLStatAggregateDropsEntry 12 }

	fwSXLAggrDropsOutboundConnNotFound OBJECT-TYPE
	SYNTAX  Integer32
	MAX-ACCESS read-only
	STATUS current
	DESCRIPTION
                "Packets dropped due to missing outbound connection. "
        ::= { fwSXLStatAggregateDropsEntry 13 }

	fwSXLAggrDropsInterfaceDown OBJECT-TYPE
	SYNTAX  Integer32
	MAX-ACCESS read-only
	STATUS current
	DESCRIPTION
                "Packets dropped due to interface being down. "
        ::= { fwSXLStatAggregateDropsEntry 14 }

	fwSXLAggrDropsClusterError OBJECT-TYPE
	SYNTAX  Integer32
	MAX-ACCESS read-only
	STATUS current
	DESCRIPTION
                "Packets dropped due to cluster error. "
        ::= { fwSXLStatAggregateDropsEntry 15 }

	fwSXLAggrDropsXmlError OBJECT-TYPE
	SYNTAX  Integer32
	MAX-ACCESS read-only
	STATUS current
	DESCRIPTION
                "Packets dropped due to XML error. "
        ::= { fwSXLStatAggregateDropsEntry 16 }

	fwSXLAggrDropsAntiSpoofing OBJECT-TYPE
	SYNTAX  Integer32
	MAX-ACCESS read-only
	STATUS current
	DESCRIPTION
                "Packets dropped due to anti spoofing. "
        ::= { fwSXLStatAggregateDropsEntry 17 }

	fwSXLAggrDropsSanityError OBJECT-TYPE
	SYNTAX  Integer32
	MAX-ACCESS read-only
	STATUS current
	DESCRIPTION
                "Packets dropped due to sanity error. "
        ::= { fwSXLStatAggregateDropsEntry 18 }

	fwSXLAggrDropsQxlDecision OBJECT-TYPE
	SYNTAX  Integer32
	MAX-ACCESS read-only
	STATUS current
	DESCRIPTION
                "Packets dropped due to QXL decision. "
        ::= { fwSXLStatAggregateDropsEntry 19 }

	fwSXLAggrDropsLoopPrevention OBJECT-TYPE
	SYNTAX  Integer32
	MAX-ACCESS read-only
	STATUS current
	DESCRIPTION
                "Packets dropped due to loop prevention. "
        ::= { fwSXLStatAggregateDropsEntry 20 }

	fwSXLStatisticsHost OBJECT IDENTIFIER ::= { fwSXLStatistics 2 }

	fwSXLStatHostThroughputTable OBJECT-TYPE
	          SYNTAX  SEQUENCE OF  FwSXLStatHostThroughputEntry
			  MAX-ACCESS  not-accessible
			  STATUS  current
			  DESCRIPTION "No description available"
			   ::= { fwSXLStatisticsHost 1 }

	fwSXLStatHostThroughputEntry OBJECT-TYPE
	          SYNTAX  FwSXLStatHostThroughputEntry
	          MAX-ACCESS  not-accessible
	          STATUS  current
	          DESCRIPTION "No description available"
	          INDEX   { fwSXLHostThroughputIndex }
	          ::= { fwSXLStatHostThroughputTable 1 }

      FwSXLStatHostThroughputEntry ::=
              SEQUENCE {
                 fwSXLHostThroughputIndex
                      Unsigned32,
                 fwSXLHostRxMbits
					  Gauge32,
				 fwSXLHostTxMbits
					  Gauge32,
				 fwSXLHostInboundKbitsPerSecond
        		      Counter64,
				 fwSXLHostOutboundKbitsPerSecond
					  Counter64,
				 fwSXLHostInboundpacketsPerSecond
					  Counter64,
				 fwSXLHostOutboundpacketsPerSecond
					  Counter64,
				 fwSXLHostConnectionsPerSecond
					  Counter64,
				 fwSXLHostConcurrentConnections
					  Counter64
				}

	fwSXLHostThroughputIndex OBJECT-TYPE
	SYNTAX Unsigned32
	MAX-ACCESS not-accessible
	STATUS current
	DESCRIPTION
                "Dummy index. "
        ::= { fwSXLStatHostThroughputEntry 1 }

	fwSXLHostRxMbits OBJECT-TYPE
	SYNTAX Gauge32
	MAX-ACCESS read-only
	STATUS current
	DESCRIPTION
                "Number of RX bytes. "
        ::= { fwSXLStatHostThroughputEntry 2 }

	fwSXLHostTxMbits OBJECT-TYPE
	SYNTAX Gauge32
	MAX-ACCESS read-only
	STATUS current
	DESCRIPTION
                "Number of TX bytes. "
        ::= { fwSXLStatHostThroughputEntry 3 }

	fwSXLHostInboundKbitsPerSecond OBJECT-TYPE
	SYNTAX Counter64
	MAX-ACCESS read-only
	STATUS current
	DESCRIPTION
                "Inbound Kbits per second. "
        ::= { fwSXLStatHostThroughputEntry 4 }

	fwSXLHostOutboundKbitsPerSecond OBJECT-TYPE
	SYNTAX Counter64
	MAX-ACCESS read-only
	STATUS current
	DESCRIPTION
                "Outbound Kbits per second. "
        ::= { fwSXLStatHostThroughputEntry 5 }

	fwSXLHostInboundpacketsPerSecond OBJECT-TYPE
	SYNTAX Counter64
	MAX-ACCESS read-only
	STATUS current
	DESCRIPTION
                "Inbound packets per second. "
        ::= { fwSXLStatHostThroughputEntry 6 }

	fwSXLHostOutboundpacketsPerSecond OBJECT-TYPE
	SYNTAX Counter64
	MAX-ACCESS read-only
	STATUS current
	DESCRIPTION
                "Outbound packets per second. "
        ::= { fwSXLStatHostThroughputEntry 7 }

	fwSXLHostConnectionsPerSecond OBJECT-TYPE
	SYNTAX Counter64
	MAX-ACCESS read-only
	STATUS current
	DESCRIPTION
                "Connection rate per second. "
        ::= { fwSXLStatHostThroughputEntry 8 }

	fwSXLHostConcurrentConnections OBJECT-TYPE
	SYNTAX Counter64
	MAX-ACCESS read-only
	STATUS current
	DESCRIPTION
                "Concurrent connections number. "
        ::= { fwSXLStatHostThroughputEntry 9 }

	fwSXLStatHostNotificationsTable OBJECT-TYPE
	          SYNTAX  SEQUENCE OF  FwSXLStatHostNotificationsEntry
			  MAX-ACCESS  not-accessible
			  STATUS  current
			  DESCRIPTION "No description available"
			   ::= { fwSXLStatisticsHost 2 }

	fwSXLStatHostNotificationsEntry OBJECT-TYPE
	          SYNTAX  FwSXLStatHostNotificationsEntry
	          MAX-ACCESS  not-accessible
	          STATUS  current
	          DESCRIPTION "No description available"
	          INDEX   { fwSXLHostNotificationsIndex }
	          ::= { fwSXLStatHostNotificationsTable 1 }

      FwSXLStatHostNotificationsEntry ::=
              SEQUENCE {
                 fwSXLHostNotificationsIndex
                      Unsigned32,
				 fwSXLHostPpak2FwNotificationsSuccessful
					  Counter64,
				 fwSXLHostPpak2FwNotificationsFailure
					  Counter64,
				 fwSXLHostFw2PpakNotificationsSuccessful
					  Counter64,
				 fwSXLHostFw2PpakNotificationsFailure
					  Counter64
				}

	fwSXLHostNotificationsIndex OBJECT-TYPE
	SYNTAX Unsigned32
	MAX-ACCESS not-accessible
	STATUS current
	DESCRIPTION
                "Dummy index. "
        ::= { fwSXLStatHostNotificationsEntry 1 }

	fwSXLHostPpak2FwNotificationsSuccessful OBJECT-TYPE
	SYNTAX Counter64
	MAX-ACCESS read-only
	STATUS current
	DESCRIPTION
                "Number of successful notifications from ppak to firewall. "
        ::= { fwSXLStatHostNotificationsEntry 2 }

	fwSXLHostPpak2FwNotificationsFailure OBJECT-TYPE
	SYNTAX Counter64
	MAX-ACCESS read-only
	STATUS current
	DESCRIPTION
                "Number of failed notifications from ppak to firewall. "
        ::= { fwSXLStatHostNotificationsEntry 3 }

	fwSXLHostFw2PpakNotificationsSuccessful OBJECT-TYPE
	SYNTAX Counter64
	MAX-ACCESS read-only
	STATUS current
	DESCRIPTION
                "Number of successful notifications from firewall to ppak. "
        ::= { fwSXLStatHostNotificationsEntry 4 }

	fwSXLHostFw2PpakNotificationsFailure OBJECT-TYPE
	SYNTAX Counter64
	MAX-ACCESS read-only
	STATUS current
	DESCRIPTION
                "Number of failed notifications from firewall to ppak. "
        ::= { fwSXLStatHostNotificationsEntry 5 }

	fwSXLStatHostDropsTable OBJECT-TYPE
	          SYNTAX  SEQUENCE OF  FwSXLStatHostDropsEntry
			  MAX-ACCESS  not-accessible
			  STATUS  current
			  DESCRIPTION "No description available"
			   ::= { fwSXLStatisticsHost 3 }

	fwSXLStatHostDropsEntry OBJECT-TYPE
	          SYNTAX  FwSXLStatHostDropsEntry
	          MAX-ACCESS  not-accessible
	          STATUS  current
	          DESCRIPTION "No description available"
	          INDEX   { fwSXLHostDropsIndex }
	          ::= { fwSXLStatHostDropsTable 1 }

      FwSXLStatHostDropsEntry ::=
              SEQUENCE {
                 fwSXLHostDropsIndex
                      Unsigned32,
				 fwSXLHostDropsTotPackets
					  Counter64,
				 fwSXLHostDropsPxlDecision
					  INTEGER,
				 fwSXLHostDropsFragmentationError
					  INTEGER,
				 fwSXLHostDropsF2FNotAllowed
					  INTEGER,
				 fwSXLHostDropsHeavyLoadTcpViolation
					  INTEGER,
				 fwSXLHostDropsCorruptPacket
					  INTEGER,
				 fwSXLHostDropsHeavyLoadNewConnection
					  INTEGER,
				 fwSXLHostDropsClearPacketOnVPN
					  INTEGER,
				 fwSXLHostDropsEncryptionFailed
					  INTEGER,
				 fwSXLHostDropsDropTemplate
					  INTEGER,
				 fwSXLHostDropsDecryptionFailed
					  INTEGER,
				 fwSXLHostDropsOutboundConnNotFound
					  INTEGER,
				 fwSXLHostDropsInterfaceDown
					  INTEGER,
				 fwSXLHostDropsClusterError
					  INTEGER,
				 fwSXLHostDropsXmlError
					  INTEGER,
				 fwSXLHostDropsAntiSpoofing
					  INTEGER,
				 fwSXLHostDropsSanityError
					  INTEGER,
				 fwSXLHostDropsQxlDecision
					  INTEGER,
				 fwSXLHostDropsLoopPrevention
					  INTEGER
				}

	fwSXLHostDropsIndex OBJECT-TYPE
	SYNTAX Unsigned32
	MAX-ACCESS not-accessible
	STATUS current
	DESCRIPTION
                "Dummy index. "
        ::= { fwSXLStatHostDropsEntry 1 }

	fwSXLHostDropsTotPackets OBJECT-TYPE
	SYNTAX Counter64
	MAX-ACCESS read-only
	STATUS current
	DESCRIPTION
                "Total dropped packets number. "
        ::= { fwSXLStatHostDropsEntry 2 }

	fwSXLHostDropsPxlDecision OBJECT-TYPE
	SYNTAX  Integer32
	MAX-ACCESS read-only
	STATUS current
	DESCRIPTION
                "Packets dropped due to PXL decision. "
        ::= { fwSXLStatHostDropsEntry 3 }

	fwSXLHostDropsFragmentationError OBJECT-TYPE
	SYNTAX  Integer32
	MAX-ACCESS read-only
	STATUS current
	DESCRIPTION
                "Packets dropped due to fragmentation error. "
        ::= { fwSXLStatHostDropsEntry 4 }

	fwSXLHostDropsF2FNotAllowed OBJECT-TYPE
	SYNTAX  Integer32
	MAX-ACCESS read-only
	STATUS current
	DESCRIPTION
                "Packets dropped due to F2F not being allowed. "
        ::= { fwSXLStatHostDropsEntry 5 }

	fwSXLHostDropsHeavyLoadTcpViolation OBJECT-TYPE
	SYNTAX  Integer32
	MAX-ACCESS read-only
	STATUS current
	DESCRIPTION
                "Packets dropped due to TCP violation during heavy load. "
        ::= { fwSXLStatHostDropsEntry 6 }

	fwSXLHostDropsCorruptPacket OBJECT-TYPE
	SYNTAX  Integer32
	MAX-ACCESS read-only
	STATUS current
	DESCRIPTION
                "Packets dropped due to being corrupt. "
        ::= { fwSXLStatHostDropsEntry 7 }

	fwSXLHostDropsHeavyLoadNewConnection OBJECT-TYPE
	SYNTAX  Integer32
	MAX-ACCESS read-only
	STATUS current
	DESCRIPTION
                "Packets dropped due to being new connections during heavy load. "
        ::= { fwSXLStatHostDropsEntry 8 }

	fwSXLHostDropsClearPacketOnVPN OBJECT-TYPE
	SYNTAX  Integer32
	MAX-ACCESS read-only
	STATUS current
	DESCRIPTION
                "VPN packets dropped due to being sent unencrypted. "
        ::= { fwSXLStatHostDropsEntry 9 }

	fwSXLHostDropsEncryptionFailed OBJECT-TYPE
	SYNTAX  Integer32
	MAX-ACCESS read-only
	STATUS current
	DESCRIPTION
                "Packets dropped due to encryption failure. "
        ::= { fwSXLStatHostDropsEntry 10 }

	fwSXLHostDropsDropTemplate OBJECT-TYPE
	SYNTAX  Integer32
	MAX-ACCESS read-only
	STATUS current
	DESCRIPTION
                "Packets dropped due to drop template. "
        ::= { fwSXLStatHostDropsEntry 11 }

	fwSXLHostDropsDecryptionFailed OBJECT-TYPE
	SYNTAX  Integer32
	MAX-ACCESS read-only
	STATUS current
	DESCRIPTION
                "Packets dropped due to decryption failure. "
        ::= { fwSXLStatHostDropsEntry 12 }

	fwSXLHostDropsOutboundConnNotFound OBJECT-TYPE
	SYNTAX  Integer32
	MAX-ACCESS read-only
	STATUS current
	DESCRIPTION
                "Packets dropped due to missing outbound connection. "
        ::= { fwSXLStatHostDropsEntry 13 }

	fwSXLHostDropsInterfaceDown OBJECT-TYPE
	SYNTAX  Integer32
	MAX-ACCESS read-only
	STATUS current
	DESCRIPTION
                "Packets dropped due to interface being down. "
        ::= { fwSXLStatHostDropsEntry 14 }

	fwSXLHostDropsClusterError OBJECT-TYPE
	SYNTAX  Integer32
	MAX-ACCESS read-only
	STATUS current
	DESCRIPTION
                "Packets dropped due to cluster error. "
        ::= { fwSXLStatHostDropsEntry 15 }

	fwSXLHostDropsXmlError OBJECT-TYPE
	SYNTAX  Integer32
	MAX-ACCESS read-only
	STATUS current
	DESCRIPTION
                "Packets dropped due to XML error. "
        ::= { fwSXLStatHostDropsEntry 16 }

	fwSXLHostDropsAntiSpoofing OBJECT-TYPE
	SYNTAX  Integer32
	MAX-ACCESS read-only
	STATUS current
	DESCRIPTION
                "Packets dropped due to anti spoofing. "
        ::= { fwSXLStatHostDropsEntry 17 }

	fwSXLHostDropsSanityError OBJECT-TYPE
	SYNTAX  Integer32
	MAX-ACCESS read-only
	STATUS current
	DESCRIPTION
                "Packets dropped due to sanity error. "
        ::= { fwSXLStatHostDropsEntry 18 }

	fwSXLHostDropsQxlDecision OBJECT-TYPE
	SYNTAX  Integer32
	MAX-ACCESS read-only
	STATUS current
	DESCRIPTION
                "Packets dropped due to QXL decision. "
        ::= { fwSXLStatHostDropsEntry 19 }

	fwSXLHostDropsLoopPrevention OBJECT-TYPE
	SYNTAX  Integer32
	MAX-ACCESS read-only
	STATUS current
	DESCRIPTION
                "Packets dropped due to loop prevention. "
        ::= { fwSXLStatHostDropsEntry 20 }

	fwSXLStatHostInterfacesTable OBJECT-TYPE
	          SYNTAX  SEQUENCE OF  FwSXLStatHostInterfacesEntry
			  MAX-ACCESS  not-accessible
			  STATUS  current
			  DESCRIPTION "No description available"
			   ::= { fwSXLStatisticsHost 4 }

	fwSXLStatHostInterfacesEntry OBJECT-TYPE
	          SYNTAX  FwSXLStatHostInterfacesEntry
	          MAX-ACCESS  not-accessible
	          STATUS  current
	          DESCRIPTION "No description available"
	          INDEX   { fwSXLHostInterfacesIndex }
	          ::= { fwSXLStatHostInterfacesTable 1 }

      FwSXLStatHostInterfacesEntry ::=
              SEQUENCE {
                 fwSXLHostInterfacesIndex
                      Unsigned32,
				 fwSXLHostInterface0Name
					  DisplayString,
				 fwSXLHostInterface1Name
					  DisplayString,
				 fwSXLHostInterface2Name
					  DisplayString,
				 fwSXLHostInterface3Name
					  DisplayString,
				 fwSXLHostInterface4Name
					  DisplayString,
				 fwSXLHostInterface5Name
					  DisplayString,
				 fwSXLHostInterface6Name
					  DisplayString,
				 fwSXLHostInterface7Name
					  DisplayString,
				 fwSXLHostInterface0Speed
					  DisplayString,
				 fwSXLHostInterface1Speed
					  DisplayString,
				 fwSXLHostInterface2Speed
					  DisplayString,
				 fwSXLHostInterface3Speed
					  DisplayString,
				 fwSXLHostInterface4Speed
					  DisplayString,
				 fwSXLHostInterface5Speed
					  DisplayString,
				 fwSXLHostInterface6Speed
					  DisplayString,
				 fwSXLHostInterface7Speed
					  DisplayString,
				 fwSXLHostInterface0State
					  DisplayString,
				 fwSXLHostInterface1State
					  DisplayString,
				 fwSXLHostInterface2State
					  DisplayString,
				 fwSXLHostInterface3State
					  DisplayString,
				 fwSXLHostInterface4State
					  DisplayString,
				 fwSXLHostInterface5State
					  DisplayString,
				 fwSXLHostInterface6State
					  DisplayString,
				 fwSXLHostInterface7State
					  DisplayString
				}

	fwSXLHostInterfacesIndex OBJECT-TYPE
	SYNTAX Unsigned32
	MAX-ACCESS not-accessible
	STATUS current
	DESCRIPTION
                "Dummy index. "
        ::= { fwSXLStatHostInterfacesEntry 1 }

	fwSXLHostInterface0Name OBJECT-TYPE
	SYNTAX DisplayString
	MAX-ACCESS read-only
	STATUS current
	DESCRIPTION
                "Name of SXL's interface 0. "
        ::= { fwSXLStatHostInterfacesEntry 2 }

	fwSXLHostInterface1Name OBJECT-TYPE
	SYNTAX DisplayString
	MAX-ACCESS read-only
	STATUS current
	DESCRIPTION
                "Name of SXL's interface 1. "
        ::= { fwSXLStatHostInterfacesEntry 3 }

	fwSXLHostInterface2Name OBJECT-TYPE
	SYNTAX DisplayString
	MAX-ACCESS read-only
	STATUS current
	DESCRIPTION
                "Name of SXL's interface 2. "
        ::= { fwSXLStatHostInterfacesEntry 4 }

	fwSXLHostInterface3Name OBJECT-TYPE
	SYNTAX DisplayString
	MAX-ACCESS read-only
	STATUS current
	DESCRIPTION
                "Name of SXL's interface 3. "
        ::= { fwSXLStatHostInterfacesEntry 5 }

	fwSXLHostInterface4Name OBJECT-TYPE
	SYNTAX DisplayString
	MAX-ACCESS read-only
	STATUS current
	DESCRIPTION
                "Name of SXL's interface 4. "
        ::= { fwSXLStatHostInterfacesEntry 6 }

	fwSXLHostInterface5Name OBJECT-TYPE
	SYNTAX DisplayString
	MAX-ACCESS read-only
	STATUS current
	DESCRIPTION
                "Name of SXL's interface 5. "
        ::= { fwSXLStatHostInterfacesEntry 7 }

	fwSXLHostInterface6Name OBJECT-TYPE
	SYNTAX DisplayString
	MAX-ACCESS read-only
	STATUS current
	DESCRIPTION
                "Name of SXL's interface 6. "
        ::= { fwSXLStatHostInterfacesEntry 8 }

	fwSXLHostInterface7Name OBJECT-TYPE
	SYNTAX DisplayString
	MAX-ACCESS read-only
	STATUS current
	DESCRIPTION
                "Name of SXL's interface 7. "
        ::= { fwSXLStatHostInterfacesEntry 9 }

	fwSXLHostInterface0Speed OBJECT-TYPE
	SYNTAX DisplayString
	MAX-ACCESS read-only
	STATUS current
	DESCRIPTION
                "Speed of SXL's interface 0. "
        ::= { fwSXLStatHostInterfacesEntry 10 }

	fwSXLHostInterface1Speed OBJECT-TYPE
	SYNTAX DisplayString
	MAX-ACCESS read-only
	STATUS current
	DESCRIPTION
                "Speed of SXL's interface 1. "
        ::= { fwSXLStatHostInterfacesEntry 11 }

	fwSXLHostInterface2Speed OBJECT-TYPE
	SYNTAX DisplayString
	MAX-ACCESS read-only
	STATUS current
	DESCRIPTION
                "Speed of SXL's interface 2. "
        ::= { fwSXLStatHostInterfacesEntry 12 }

	fwSXLHostInterface3Speed OBJECT-TYPE
	SYNTAX DisplayString
	MAX-ACCESS read-only
	STATUS current
	DESCRIPTION
                "Speed of SXL's interface 3. "
        ::= { fwSXLStatHostInterfacesEntry 13 }

	fwSXLHostInterface4Speed OBJECT-TYPE
	SYNTAX DisplayString
	MAX-ACCESS read-only
	STATUS current
	DESCRIPTION
                "Speed of SXL's interface 4. "
        ::= { fwSXLStatHostInterfacesEntry 14 }

	fwSXLHostInterface5Speed OBJECT-TYPE
	SYNTAX DisplayString
	MAX-ACCESS read-only
	STATUS current
	DESCRIPTION
                "Speed of SXL's interface 5. "
        ::= { fwSXLStatHostInterfacesEntry 15 }

	fwSXLHostInterface6Speed OBJECT-TYPE
	SYNTAX DisplayString
	MAX-ACCESS read-only
	STATUS current
	DESCRIPTION
                "Speed of SXL's interface 6. "
        ::= { fwSXLStatHostInterfacesEntry 16 }

	fwSXLHostInterface7Speed OBJECT-TYPE
	SYNTAX DisplayString
	MAX-ACCESS read-only
	STATUS current
	DESCRIPTION
                "Speed of SXL's interface 7. "
        ::= { fwSXLStatHostInterfacesEntry 17 }

	fwSXLHostInterface0State OBJECT-TYPE
	SYNTAX DisplayString
	MAX-ACCESS read-only
	STATUS current
	DESCRIPTION
                "State of SXL's interface 0. "
        ::= { fwSXLStatHostInterfacesEntry 18 }

	fwSXLHostInterface1State OBJECT-TYPE
	SYNTAX DisplayString
	MAX-ACCESS read-only
	STATUS current
	DESCRIPTION
                "State of SXL's interface 1. "
        ::= { fwSXLStatHostInterfacesEntry 19 }

	fwSXLHostInterface2State OBJECT-TYPE
	SYNTAX DisplayString
	MAX-ACCESS read-only
	STATUS current
	DESCRIPTION
                "State of SXL's interface 2. "
        ::= { fwSXLStatHostInterfacesEntry 20 }

	fwSXLHostInterface3State OBJECT-TYPE
	SYNTAX DisplayString
	MAX-ACCESS read-only
	STATUS current
	DESCRIPTION
                "State of SXL's interface 3. "
        ::= { fwSXLStatHostInterfacesEntry 21 }

	fwSXLHostInterface4State OBJECT-TYPE
	SYNTAX DisplayString
	MAX-ACCESS read-only
	STATUS current
	DESCRIPTION
                "State of SXL's interface 4. "
        ::= { fwSXLStatHostInterfacesEntry 22 }

	fwSXLHostInterface5State OBJECT-TYPE
	SYNTAX DisplayString
	MAX-ACCESS read-only
	STATUS current
	DESCRIPTION
                "State of SXL's interface 5. "
        ::= { fwSXLStatHostInterfacesEntry 23 }

	fwSXLHostInterface6State OBJECT-TYPE
	SYNTAX DisplayString
	MAX-ACCESS read-only
	STATUS current
	DESCRIPTION
                "State of SXL's interface 6. "
        ::= { fwSXLStatHostInterfacesEntry 24 }

	fwSXLHostInterface7State OBJECT-TYPE
	SYNTAX DisplayString
	MAX-ACCESS read-only
	STATUS current
	DESCRIPTION
                "State of SXL's interface 7. "
        ::= { fwSXLStatHostInterfacesEntry 25 }

	fwSXLStatHostGeneralTable OBJECT-TYPE
	          SYNTAX  SEQUENCE OF  FwSXLStatHostGeneralEntry
			  MAX-ACCESS  not-accessible
			  STATUS  current
			  DESCRIPTION "No description available"
			   ::= { fwSXLStatisticsHost 5 }

	fwSXLStatHostGeneralEntry OBJECT-TYPE
	          SYNTAX  FwSXLStatHostGeneralEntry
	          MAX-ACCESS  not-accessible
	          STATUS  current
	          DESCRIPTION "No description available"
	          INDEX   { fwSXLHostGeneralIndex }
	          ::= { fwSXLStatHostGeneralTable 1 }

      FwSXLStatHostGeneralEntry ::=
              SEQUENCE {
                 fwSXLHostGeneralIndex
                      Unsigned32,
				 fwSXLHostState
					  DisplayString
				}

	fwSXLHostGeneralIndex OBJECT-TYPE
	SYNTAX Unsigned32
	MAX-ACCESS not-accessible
	STATUS current
	DESCRIPTION
                "Dummy index. "
        ::= { fwSXLStatHostGeneralEntry 1 }

	fwSXLHostState OBJECT-TYPE
	SYNTAX DisplayString
	MAX-ACCESS read-only
	STATUS current
	DESCRIPTION
                "The SXL's status. "
        ::= { fwSXLStatHostGeneralEntry 2 }

	fwSXLStatisticsFalcons OBJECT IDENTIFIER ::= { fwSXLStatistics 3 }

	fwSXLStatFalconsThroughputTable OBJECT-TYPE
	          SYNTAX  SEQUENCE OF  FwSXLStatFalconsThroughputEntry
			  MAX-ACCESS  not-accessible
			  STATUS  current
			  DESCRIPTION "No description available"
			   ::= { fwSXLStatisticsFalcons 1 }

	fwSXLStatFalconsThroughputEntry OBJECT-TYPE
	          SYNTAX  FwSXLStatFalconsThroughputEntry
	          MAX-ACCESS  not-accessible
	          STATUS  current
	          DESCRIPTION "No description available"
	          INDEX   { fwSXLFalconsThroughputIndex }
	          ::= { fwSXLStatFalconsThroughputTable 1 }

      FwSXLStatFalconsThroughputEntry ::=
              SEQUENCE {
                 fwSXLFalconsThroughputIndex
                      Unsigned32,
                 fwSXLFalconsRxMbits
					  INTEGER,
				 fwSXLFalconsTxMbits
					  INTEGER,
				 fwSXLFalconsInboundKbitsPerSecond
        		      DisplayString,
				 fwSXLFalconsOutboundKbitsPerSecond
					  DisplayString,
				 fwSXLFalconsInboundpacketsPerSecond
					  DisplayString,
				 fwSXLFalconsOutboundpacketsPerSecond
					  DisplayString,
				 fwSXLFalconsConnectionsPerSecond
					  DisplayString,
				 fwSXLFalconsConcurrentConnections
					  DisplayString
				}

	fwSXLFalconsThroughputIndex OBJECT-TYPE
	SYNTAX Unsigned32
	MAX-ACCESS not-accessible
	STATUS current
	DESCRIPTION
                "Dummy index. "
        ::= { fwSXLStatFalconsThroughputEntry 1 }

	fwSXLFalconsRxMbits OBJECT-TYPE
	SYNTAX  Integer32
	MAX-ACCESS read-only
	STATUS current
	DESCRIPTION
                "Number of RX bytes. "
        ::= { fwSXLStatFalconsThroughputEntry 2 }

	fwSXLFalconsTxMbits OBJECT-TYPE
	SYNTAX  Integer32
	MAX-ACCESS read-only
	STATUS current
	DESCRIPTION
                "Number of TX bytes. "
        ::= { fwSXLStatFalconsThroughputEntry 3 }

	fwSXLFalconsInboundKbitsPerSecond OBJECT-TYPE
	SYNTAX DisplayString (SIZE (0..255))
	MAX-ACCESS read-only
	STATUS current
	DESCRIPTION
                "Inbound Kbits per second. "
        ::= { fwSXLStatFalconsThroughputEntry 4 }

	fwSXLFalconsOutboundKbitsPerSecond OBJECT-TYPE
	SYNTAX DisplayString (SIZE (0..255))
	MAX-ACCESS read-only
	STATUS current
	DESCRIPTION
                "Outbound Kbits per second. "
        ::= { fwSXLStatFalconsThroughputEntry 5 }

	fwSXLFalconsInboundpacketsPerSecond OBJECT-TYPE
	SYNTAX DisplayString (SIZE (0..255))
	MAX-ACCESS read-only
	STATUS current
	DESCRIPTION
                "Inbound packets per second. "
        ::= { fwSXLStatFalconsThroughputEntry 6 }

	fwSXLFalconsOutboundpacketsPerSecond OBJECT-TYPE
	SYNTAX DisplayString (SIZE (0..255))
	MAX-ACCESS read-only
	STATUS current
	DESCRIPTION
                "Outbound packets per second. "
        ::= { fwSXLStatFalconsThroughputEntry 7 }

	fwSXLFalconsConnectionsPerSecond OBJECT-TYPE
	SYNTAX DisplayString (SIZE (0..255))
	MAX-ACCESS read-only
	STATUS current
	DESCRIPTION
                "Connection rate per second. "
        ::= { fwSXLStatFalconsThroughputEntry 8 }

	fwSXLFalconsConcurrentConnections OBJECT-TYPE
	SYNTAX DisplayString (SIZE (0..255))
	MAX-ACCESS read-only
	STATUS current
	DESCRIPTION
                "Concurrent connections number. "
        ::= { fwSXLStatFalconsThroughputEntry 9 }

	fwSXLStatFalconsNotificationsTable OBJECT-TYPE
	          SYNTAX  SEQUENCE OF  FwSXLStatFalconsNotificationsEntry
			  MAX-ACCESS  not-accessible
			  STATUS  current
			  DESCRIPTION "No description available"
			   ::= { fwSXLStatisticsFalcons 2 }

	fwSXLStatFalconsNotificationsEntry OBJECT-TYPE
	          SYNTAX  FwSXLStatFalconsNotificationsEntry
	          MAX-ACCESS  not-accessible
	          STATUS  current
	          DESCRIPTION "No description available"
	          INDEX   { fwSXLFalconsNotificationsIndex }
	          ::= { fwSXLStatFalconsNotificationsTable 1 }

      FwSXLStatFalconsNotificationsEntry ::=
              SEQUENCE {
                 fwSXLFalconsNotificationsIndex
                      Unsigned32,
				 fwSXLFalconsPpak2FwNotificationsSuccessful
					  DisplayString,
				 fwSXLFalconsPpak2FwNotificationsFailure
					  DisplayString,
				 fwSXLFalconsFw2PpakNotificationsSuccessful
					  DisplayString,
				 fwSXLFalconsFw2PpakNotificationsFailure
					  DisplayString
				}

	fwSXLFalconsNotificationsIndex OBJECT-TYPE
	SYNTAX Unsigned32
	MAX-ACCESS not-accessible
	STATUS current
	DESCRIPTION
                "Dummy index. "
        ::= { fwSXLStatFalconsNotificationsEntry 1 }

	fwSXLFalconsPpak2FwNotificationsSuccessful OBJECT-TYPE
	SYNTAX DisplayString (SIZE (0..255))
	MAX-ACCESS read-only
	STATUS current
	DESCRIPTION
                "Number of successful notifications from ppak to firewall. "
        ::= { fwSXLStatFalconsNotificationsEntry 2 }

	fwSXLFalconsPpak2FwNotificationsFailure OBJECT-TYPE
	SYNTAX DisplayString (SIZE (0..255))
	MAX-ACCESS read-only
	STATUS current
	DESCRIPTION
                "Number of failed notifications from ppak to firewall. "
        ::= { fwSXLStatFalconsNotificationsEntry 3 }

	fwSXLFalconsFw2PpakNotificationsSuccessful OBJECT-TYPE
	SYNTAX DisplayString (SIZE (0..255))
	MAX-ACCESS read-only
	STATUS current
	DESCRIPTION
                "Number of successful notifications from firewall to ppak. "
        ::= { fwSXLStatFalconsNotificationsEntry 4 }

	fwSXLFalconsFw2PpakNotificationsFailure OBJECT-TYPE
	SYNTAX DisplayString (SIZE (0..255))
	MAX-ACCESS read-only
	STATUS current
	DESCRIPTION
                "Number of failed notifications from firewall to ppak. "
        ::= { fwSXLStatFalconsNotificationsEntry 5 }

	fwSXLStatFalconsDropsTable OBJECT-TYPE
	          SYNTAX  SEQUENCE OF  FwSXLStatFalconsDropsEntry
			  MAX-ACCESS  not-accessible
			  STATUS  current
			  DESCRIPTION "No description available"
			   ::= { fwSXLStatisticsFalcons 3 }

	fwSXLStatFalconsDropsEntry OBJECT-TYPE
	          SYNTAX  FwSXLStatFalconsDropsEntry
	          MAX-ACCESS  not-accessible
	          STATUS  current
	          DESCRIPTION "No description available"
	          INDEX   { fwSXLFalconsDropsIndex }
	          ::= { fwSXLStatFalconsDropsTable 1 }

      FwSXLStatFalconsDropsEntry ::=
              SEQUENCE {
                 fwSXLFalconsDropsIndex
                      Unsigned32,
				 fwSXLFalconsDropsTotPackets
					  DisplayString,
				 fwSXLFalconsDropsPxlDecision
					  DisplayString,
				 fwSXLFalconsDropsFragmentationError
					  DisplayString,
				 fwSXLFalconsDropsF2FNotAllowed
					  DisplayString,
				 fwSXLFalconsDropsHeavyLoadTcpViolation
					  DisplayString,
				 fwSXLFalconsDropsCorruptPacket
					  DisplayString,
				 fwSXLFalconsDropsHeavyLoadNewConnection
					  DisplayString,
				 fwSXLFalconsDropsClearPacketOnVPN
					  DisplayString,
				 fwSXLFalconsDropsEncryptionFailed
					  DisplayString,
				 fwSXLFalconsDropsDropTemplate
					  DisplayString,
				 fwSXLFalconsDropsDecryptionFailed
					  DisplayString,
				 fwSXLFalconsDropsOutboundConnNotFound
					  DisplayString,
				 fwSXLFalconsDropsInterfaceDown
					  DisplayString,
				 fwSXLFalconsDropsClusterError
					  DisplayString,
				 fwSXLFalconsDropsXmlError
					  DisplayString,
				 fwSXLFalconsDropsAntiSpoofing
					  DisplayString,
				 fwSXLFalconsDropsSanityError
					  DisplayString,
				 fwSXLFalconsDropsQxlDecision
					  DisplayString,
				 fwSXLFalconsDropsLoopPrevention
					  DisplayString
				}

	fwSXLFalconsDropsIndex OBJECT-TYPE
	SYNTAX Unsigned32
	MAX-ACCESS not-accessible
	STATUS current
	DESCRIPTION
                "Dummy index. "
        ::= { fwSXLStatFalconsDropsEntry 1 }

	fwSXLFalconsDropsTotPackets OBJECT-TYPE
	SYNTAX DisplayString (SIZE (0..255))
	MAX-ACCESS read-only
	STATUS current
	DESCRIPTION
                "Total dropped packets number. "
        ::= { fwSXLStatFalconsDropsEntry 2 }

	fwSXLFalconsDropsPxlDecision OBJECT-TYPE
	SYNTAX DisplayString (SIZE (0..255))
	MAX-ACCESS read-only
	STATUS current
	DESCRIPTION
                "Packets dropped due to PXL decision. "
        ::= { fwSXLStatFalconsDropsEntry 3 }

	fwSXLFalconsDropsFragmentationError OBJECT-TYPE
	SYNTAX DisplayString (SIZE (0..255))
	MAX-ACCESS read-only
	STATUS current
	DESCRIPTION
                "Packets dropped due to fragmentation error. "
        ::= { fwSXLStatFalconsDropsEntry 4 }

	fwSXLFalconsDropsF2FNotAllowed OBJECT-TYPE
	SYNTAX DisplayString (SIZE (0..255))
	MAX-ACCESS read-only
	STATUS current
	DESCRIPTION
                "Packets dropped due to F2F not being allowed. "
        ::= { fwSXLStatFalconsDropsEntry 5 }

	fwSXLFalconsDropsHeavyLoadTcpViolation OBJECT-TYPE
	SYNTAX DisplayString (SIZE (0..255))
	MAX-ACCESS read-only
	STATUS current
	DESCRIPTION
                "Packets dropped due to TCP violation during heavy load. "
        ::= { fwSXLStatFalconsDropsEntry 6 }

	fwSXLFalconsDropsCorruptPacket OBJECT-TYPE
	SYNTAX DisplayString (SIZE (0..255))
	MAX-ACCESS read-only
	STATUS current
	DESCRIPTION
                "Packets dropped due to being corrupt. "
        ::= { fwSXLStatFalconsDropsEntry 7 }

	fwSXLFalconsDropsHeavyLoadNewConnection OBJECT-TYPE
	SYNTAX DisplayString (SIZE (0..255))
	MAX-ACCESS read-only
	STATUS current
	DESCRIPTION
                "Packets dropped due to being new connections during heavy load. "
        ::= { fwSXLStatFalconsDropsEntry 8 }

	fwSXLFalconsDropsClearPacketOnVPN OBJECT-TYPE
	SYNTAX DisplayString (SIZE (0..255))
	MAX-ACCESS read-only
	STATUS current
	DESCRIPTION
                "VPN packets dropped due to being sent unencrypted. "
        ::= { fwSXLStatFalconsDropsEntry 9 }

	fwSXLFalconsDropsEncryptionFailed OBJECT-TYPE
	SYNTAX DisplayString (SIZE (0..255))
	MAX-ACCESS read-only
	STATUS current
	DESCRIPTION
                "Packets dropped due to encryption failure. "
        ::= { fwSXLStatFalconsDropsEntry 10 }

	fwSXLFalconsDropsDropTemplate OBJECT-TYPE
	SYNTAX DisplayString (SIZE (0..255))
	MAX-ACCESS read-only
	STATUS current
	DESCRIPTION
                "Packets dropped due to drop template. "
        ::= { fwSXLStatFalconsDropsEntry 11 }

	fwSXLFalconsDropsDecryptionFailed OBJECT-TYPE
	SYNTAX DisplayString (SIZE (0..255))
	MAX-ACCESS read-only
	STATUS current
	DESCRIPTION
                "Packets dropped due to decryption failure. "
        ::= { fwSXLStatFalconsDropsEntry 12 }

	fwSXLFalconsDropsOutboundConnNotFound OBJECT-TYPE
	SYNTAX DisplayString (SIZE (0..255))
	MAX-ACCESS read-only
	STATUS current
	DESCRIPTION
                "Packets dropped due to missing outbound connection. "
        ::= { fwSXLStatFalconsDropsEntry 13 }

	fwSXLFalconsDropsInterfaceDown OBJECT-TYPE
	SYNTAX DisplayString (SIZE (0..255))
	MAX-ACCESS read-only
	STATUS current
	DESCRIPTION
                "Packets dropped due to interface being down. "
        ::= { fwSXLStatFalconsDropsEntry 14 }

	fwSXLFalconsDropsClusterError OBJECT-TYPE
	SYNTAX DisplayString (SIZE (0..255))
	MAX-ACCESS read-only
	STATUS current
	DESCRIPTION
                "Packets dropped due to cluster error. "
        ::= { fwSXLStatFalconsDropsEntry 15 }

	fwSXLFalconsDropsXmlError OBJECT-TYPE
	SYNTAX DisplayString (SIZE (0..255))
	MAX-ACCESS read-only
	STATUS current
	DESCRIPTION
                "Packets dropped due to XML error. "
        ::= { fwSXLStatFalconsDropsEntry 16 }

	fwSXLFalconsDropsAntiSpoofing OBJECT-TYPE
	SYNTAX DisplayString (SIZE (0..255))
	MAX-ACCESS read-only
	STATUS current
	DESCRIPTION
                "Packets dropped due to anti spoofing. "
        ::= { fwSXLStatFalconsDropsEntry 17 }

	fwSXLFalconsDropsSanityError OBJECT-TYPE
	SYNTAX DisplayString (SIZE (0..255))
	MAX-ACCESS read-only
	STATUS current
	DESCRIPTION
                "Packets dropped due to sanity error. "
        ::= { fwSXLStatFalconsDropsEntry 18 }

	fwSXLFalconsDropsQxlDecision OBJECT-TYPE
	SYNTAX DisplayString (SIZE (0..255))
	MAX-ACCESS read-only
	STATUS current
	DESCRIPTION
                "Packets dropped due to QXL decision. "
        ::= { fwSXLStatFalconsDropsEntry 19 }

	fwSXLFalconsDropsLoopPrevention OBJECT-TYPE
	SYNTAX DisplayString (SIZE (0..255))
	MAX-ACCESS read-only
	STATUS current
	DESCRIPTION
                "Packets dropped due to loop prevention. "
        ::= { fwSXLStatFalconsDropsEntry 20 }

	fwSXLStatFalconsInterfacesTable OBJECT-TYPE
	          SYNTAX  SEQUENCE OF  FwSXLStatFalconsInterfacesEntry
			  MAX-ACCESS  not-accessible
			  STATUS  current
			  DESCRIPTION "No description available"
			   ::= { fwSXLStatisticsFalcons 4 }

	fwSXLStatFalconsInterfacesEntry OBJECT-TYPE
	          SYNTAX  FwSXLStatFalconsInterfacesEntry
	          MAX-ACCESS  not-accessible
	          STATUS  current
	          DESCRIPTION "No description available"
	          INDEX   { fwSXLFalconsInterfacesIndex }
	          ::= { fwSXLStatFalconsInterfacesTable 1 }

      FwSXLStatFalconsInterfacesEntry ::=
              SEQUENCE {
                 fwSXLFalconsInterfacesIndex
                      Unsigned32,
				 fwSXLFalconsInterface0Name
					  DisplayString,
				 fwSXLFalconsInterface1Name
					  DisplayString,
				 fwSXLFalconsInterface2Name
					  DisplayString,
				 fwSXLFalconsInterface3Name
					  DisplayString,
				 fwSXLFalconsInterface4Name
					  DisplayString,
				 fwSXLFalconsInterface5Name
					  DisplayString,
				 fwSXLFalconsInterface6Name
					  DisplayString,
				 fwSXLFalconsInterface7Name
					  DisplayString,
				 fwSXLFalconsInterface0Speed
					  DisplayString,
				 fwSXLFalconsInterface1Speed
					  DisplayString,
				 fwSXLFalconsInterface2Speed
					  DisplayString,
				 fwSXLFalconsInterface3Speed
					  DisplayString,
				 fwSXLFalconsInterface4Speed
					  DisplayString,
				 fwSXLFalconsInterface5Speed
					  DisplayString,
				 fwSXLFalconsInterface6Speed
					  DisplayString,
				 fwSXLFalconsInterface7Speed
					  DisplayString,
				 fwSXLFalconsInterface0State
					  DisplayString,
				 fwSXLFalconsInterface1State
					  DisplayString,
				 fwSXLFalconsInterface2State
					  DisplayString,
				 fwSXLFalconsInterface3State
					  DisplayString,
				 fwSXLFalconsInterface4State
					  DisplayString,
				 fwSXLFalconsInterface5State
					  DisplayString,
				 fwSXLFalconsInterface6State
					  DisplayString,
				 fwSXLFalconsInterface7State
					  DisplayString
				}

	fwSXLFalconsInterfacesIndex OBJECT-TYPE
	SYNTAX Unsigned32
	MAX-ACCESS not-accessible
	STATUS current
	DESCRIPTION
                "Dummy index. "
        ::= { fwSXLStatFalconsInterfacesEntry 1 }

	fwSXLFalconsInterface0Name OBJECT-TYPE
	SYNTAX DisplayString
	MAX-ACCESS read-only
	STATUS current
	DESCRIPTION
                "Name of SXL's interface 0. "
        ::= { fwSXLStatFalconsInterfacesEntry 2 }

	fwSXLFalconsInterface1Name OBJECT-TYPE
	SYNTAX DisplayString
	MAX-ACCESS read-only
	STATUS current
	DESCRIPTION
                "Name of SXL's interface 1. "
        ::= { fwSXLStatFalconsInterfacesEntry 3 }

	fwSXLFalconsInterface2Name OBJECT-TYPE
	SYNTAX DisplayString
	MAX-ACCESS read-only
	STATUS current
	DESCRIPTION
                "Name of SXL's interface 2. "
        ::= { fwSXLStatFalconsInterfacesEntry 4 }

	fwSXLFalconsInterface3Name OBJECT-TYPE
	SYNTAX DisplayString
	MAX-ACCESS read-only
	STATUS current
	DESCRIPTION
                "Name of SXL's interface 3. "
        ::= { fwSXLStatFalconsInterfacesEntry 5 }

	fwSXLFalconsInterface4Name OBJECT-TYPE
	SYNTAX DisplayString
	MAX-ACCESS read-only
	STATUS current
	DESCRIPTION
                "Name of SXL's interface 4. "
        ::= { fwSXLStatFalconsInterfacesEntry 6 }

	fwSXLFalconsInterface5Name OBJECT-TYPE
	SYNTAX DisplayString
	MAX-ACCESS read-only
	STATUS current
	DESCRIPTION
                "Name of SXL's interface 5. "
        ::= { fwSXLStatFalconsInterfacesEntry 7 }

	fwSXLFalconsInterface6Name OBJECT-TYPE
	SYNTAX DisplayString
	MAX-ACCESS read-only
	STATUS current
	DESCRIPTION
                "Name of SXL's interface 6. "
        ::= { fwSXLStatFalconsInterfacesEntry 8 }

	fwSXLFalconsInterface7Name OBJECT-TYPE
	SYNTAX DisplayString
	MAX-ACCESS read-only
	STATUS current
	DESCRIPTION
                "Name of SXL's interface 7. "
        ::= { fwSXLStatFalconsInterfacesEntry 9 }

	fwSXLFalconsInterface0Speed OBJECT-TYPE
	SYNTAX DisplayString
	MAX-ACCESS read-only
	STATUS current
	DESCRIPTION
                "Speed of SXL's interface 0. "
        ::= { fwSXLStatFalconsInterfacesEntry 10 }

	fwSXLFalconsInterface1Speed OBJECT-TYPE
	SYNTAX DisplayString
	MAX-ACCESS read-only
	STATUS current
	DESCRIPTION
                "Speed of SXL's interface 1. "
        ::= { fwSXLStatFalconsInterfacesEntry 11 }

	fwSXLFalconsInterface2Speed OBJECT-TYPE
	SYNTAX DisplayString
	MAX-ACCESS read-only
	STATUS current
	DESCRIPTION
                "Speed of SXL's interface 2. "
        ::= { fwSXLStatFalconsInterfacesEntry 12 }

	fwSXLFalconsInterface3Speed OBJECT-TYPE
	SYNTAX DisplayString
	MAX-ACCESS read-only
	STATUS current
	DESCRIPTION
                "Speed of SXL's interface 3. "
        ::= { fwSXLStatFalconsInterfacesEntry 13 }

	fwSXLFalconsInterface4Speed OBJECT-TYPE
	SYNTAX DisplayString
	MAX-ACCESS read-only
	STATUS current
	DESCRIPTION
                "Speed of SXL's interface 4. "
        ::= { fwSXLStatFalconsInterfacesEntry 14 }

	fwSXLFalconsInterface5Speed OBJECT-TYPE
	SYNTAX DisplayString
	MAX-ACCESS read-only
	STATUS current
	DESCRIPTION
                "Speed of SXL's interface 5. "
        ::= { fwSXLStatFalconsInterfacesEntry 15 }

	fwSXLFalconsInterface6Speed OBJECT-TYPE
	SYNTAX DisplayString
	MAX-ACCESS read-only
	STATUS current
	DESCRIPTION
                "Speed of SXL's interface 6. "
        ::= { fwSXLStatFalconsInterfacesEntry 16 }

	fwSXLFalconsInterface7Speed OBJECT-TYPE
	SYNTAX DisplayString
	MAX-ACCESS read-only
	STATUS current
	DESCRIPTION
                "Speed of SXL's interface 7. "
        ::= { fwSXLStatFalconsInterfacesEntry 17 }

	fwSXLFalconsInterface0State OBJECT-TYPE
	SYNTAX DisplayString
	MAX-ACCESS read-only
	STATUS current
	DESCRIPTION
                "State of SXL's interface 0. "
        ::= { fwSXLStatFalconsInterfacesEntry 18 }

	fwSXLFalconsInterface1State OBJECT-TYPE
	SYNTAX DisplayString
	MAX-ACCESS read-only
	STATUS current
	DESCRIPTION
                "State of SXL's interface 1. "
        ::= { fwSXLStatFalconsInterfacesEntry 19 }

	fwSXLFalconsInterface2State OBJECT-TYPE
	SYNTAX DisplayString
	MAX-ACCESS read-only
	STATUS current
	DESCRIPTION
                "State of SXL's interface 2. "
        ::= { fwSXLStatFalconsInterfacesEntry 20 }

	fwSXLFalconsInterface3State OBJECT-TYPE
	SYNTAX DisplayString
	MAX-ACCESS read-only
	STATUS current
	DESCRIPTION
                "State of SXL's interface 3. "
        ::= { fwSXLStatFalconsInterfacesEntry 21 }

	fwSXLFalconsInterface4State OBJECT-TYPE
	SYNTAX DisplayString
	MAX-ACCESS read-only
	STATUS current
	DESCRIPTION
                "State of SXL's interface 4. "
        ::= { fwSXLStatFalconsInterfacesEntry 22 }

	fwSXLFalconsInterface5State OBJECT-TYPE
	SYNTAX DisplayString
	MAX-ACCESS read-only
	STATUS current
	DESCRIPTION
                "State of SXL's interface 5. "
        ::= { fwSXLStatFalconsInterfacesEntry 23 }

	fwSXLFalconsInterface6State OBJECT-TYPE
	SYNTAX DisplayString
	MAX-ACCESS read-only
	STATUS current
	DESCRIPTION
                "State of SXL's interface 6. "
        ::= { fwSXLStatFalconsInterfacesEntry 24 }

	fwSXLFalconsInterface7State OBJECT-TYPE
	SYNTAX DisplayString
	MAX-ACCESS read-only
	STATUS current
	DESCRIPTION
                "State of SXL's interface 7. "
        ::= { fwSXLStatFalconsInterfacesEntry 25 }

	fwSXLStatFalconsMemoryTable OBJECT-TYPE
	          SYNTAX  SEQUENCE OF  FwSXLStatFalconsMemoryEntry
			  MAX-ACCESS  not-accessible
			  STATUS  current
			  DESCRIPTION "No description available"
			   ::= { fwSXLStatisticsFalcons 5 }

	fwSXLStatFalconsMemoryEntry OBJECT-TYPE
	          SYNTAX  FwSXLStatFalconsMemoryEntry
	          MAX-ACCESS  not-accessible
	          STATUS  current
	          DESCRIPTION "No description available"
	          INDEX   { fwSXLFalconsMemoryIndex }
	          ::= { fwSXLStatFalconsMemoryTable 1 }

      FwSXLStatFalconsMemoryEntry ::=
              SEQUENCE {
                 fwSXLFalconsMemoryIndex
                      Unsigned32,
				 fwSXLFalconsSxlTotMemory
					  DisplayString,
				 fwSXLFalconsSxlUsedMemory
					  DisplayString,
				 fwSXLFalconsSxlFreeMemory
					  DisplayString,
				 fwSXLFalconsPacketPoolTotMemory
					  DisplayString,
				 fwSXLFalconsPacketPoolUsedMemory
					  DisplayString,
				 fwSXLFalconsPacketPoolFreeMemory
					  DisplayString
				}

	fwSXLFalconsMemoryIndex OBJECT-TYPE
	SYNTAX Unsigned32
	MAX-ACCESS not-accessible
	STATUS current
	DESCRIPTION
                "Dummy index. "
        ::= { fwSXLStatFalconsMemoryEntry 1 }

	fwSXLFalconsSxlTotMemory OBJECT-TYPE
	SYNTAX DisplayString (SIZE (0..255))
	MAX-ACCESS read-only
	STATUS current
	DESCRIPTION
                "Total sxl memory. "
        ::= { fwSXLStatFalconsMemoryEntry 2 }

	fwSXLFalconsSxlUsedMemory OBJECT-TYPE
	SYNTAX DisplayString (SIZE (0..255))
	MAX-ACCESS read-only
	STATUS current
	DESCRIPTION
                "Used sxl memory. "
        ::= { fwSXLStatFalconsMemoryEntry 3 }

	fwSXLFalconsSxlFreeMemory OBJECT-TYPE
	SYNTAX DisplayString (SIZE (0..255))
	MAX-ACCESS read-only
	STATUS current
	DESCRIPTION
                "Free sxl memory. "
        ::= { fwSXLStatFalconsMemoryEntry 4 }

	fwSXLFalconsPacketPoolTotMemory OBJECT-TYPE
	SYNTAX DisplayString (SIZE (0..255))
	MAX-ACCESS read-only
	STATUS current
	DESCRIPTION
                "Total packet pool memory. "
        ::= { fwSXLStatFalconsMemoryEntry 5 }

	fwSXLFalconsPacketPoolUsedMemory OBJECT-TYPE
	SYNTAX DisplayString (SIZE (0..255))
	MAX-ACCESS read-only
	STATUS current
	DESCRIPTION
                "Used packet pool memory. "
        ::= { fwSXLStatFalconsMemoryEntry 6 }

	fwSXLFalconsPacketPoolFreeMemory OBJECT-TYPE
	SYNTAX DisplayString (SIZE (0..255))
	MAX-ACCESS read-only
	STATUS current
	DESCRIPTION
                "Free packet pool memory. "
        ::= { fwSXLStatFalconsMemoryEntry 7 }

	fwSXLStatFalconsCpuTable OBJECT-TYPE
	          SYNTAX  SEQUENCE OF  FwSXLStatFalconsCpuEntry
			  MAX-ACCESS  not-accessible
			  STATUS  current
			  DESCRIPTION "No description available"
			   ::= { fwSXLStatisticsFalcons 6 }

	fwSXLStatFalconsCpuEntry OBJECT-TYPE
	          SYNTAX  FwSXLStatFalconsCpuEntry
	          MAX-ACCESS  not-accessible
	          STATUS  current
	          DESCRIPTION "No description available"
	          INDEX   { fwSXLFalconsCpuIndex }
	          ::= { fwSXLStatFalconsCpuTable 1 }

      FwSXLStatFalconsCpuEntry ::=
              SEQUENCE {
                 fwSXLFalconsCpuIndex
                      Unsigned32,
				 fwSXLFalconsCpu0Usage
					  DisplayString,
				 fwSXLFalconsCpu1Usage
					  DisplayString,
				 fwSXLFalconsCpu2Usage
					  DisplayString,
				 fwSXLFalconsCpu3Usage
					  DisplayString,
				 fwSXLFalconsCpu4Usage
					  DisplayString,
				 fwSXLFalconsCpu5Usage
					  DisplayString,
				 fwSXLFalconsCpu6Usage
					  DisplayString,
				 fwSXLFalconsCpu7Usage
					  DisplayString,
				 fwSXLFalconsCpu8Usage
					  DisplayString,
				 fwSXLFalconsCpu9Usage
					  DisplayString,
				 fwSXLFalconsCpu10Usage
					  DisplayString,
				 fwSXLFalconsCpu11Usage
					  DisplayString,
				 fwSXLFalconsCpu12Usage
					  DisplayString,
				 fwSXLFalconsCpu13Usage
					  DisplayString,
				 fwSXLFalconsCpu14Usage
					  DisplayString,
				 fwSXLFalconsCpu15Usage
					  DisplayString,
				 fwSXLFalconsCpu16Usage
					  DisplayString,
				 fwSXLFalconsCpu17Usage
					  DisplayString,
				 fwSXLFalconsCpu18Usage
					  DisplayString,
				 fwSXLFalconsCpu19Usage
					  DisplayString,
				 fwSXLFalconsCpu20Usage
					  DisplayString,
				 fwSXLFalconsCpu21Usage
					  DisplayString,
				 fwSXLFalconsCpu22Usage
					  DisplayString,
				 fwSXLFalconsCpu23Usage
					  DisplayString,
				 fwSXLFalconsCpu24Usage
					  DisplayString,
				 fwSXLFalconsCpu25Usage
					  DisplayString,
				 fwSXLFalconsCpu26Usage
					  DisplayString,
				 fwSXLFalconsCpu27Usage
					  DisplayString,
				 fwSXLFalconsCpu28Usage
					  DisplayString,
				 fwSXLFalconsCpu29Usage
					  DisplayString,
				 fwSXLFalconsCpu30Usage
					  DisplayString,
				 fwSXLFalconsCpu31Usage
					  DisplayString
				}

	fwSXLFalconsCpuIndex OBJECT-TYPE
	SYNTAX Unsigned32
	MAX-ACCESS not-accessible
	STATUS current
	DESCRIPTION
                "Dummy index. "
        ::= { fwSXLStatFalconsCpuEntry 1 }

	fwSXLFalconsCpu0Usage OBJECT-TYPE
	SYNTAX DisplayString (SIZE (0..255))
	MAX-ACCESS read-only
	STATUS current
	DESCRIPTION
                "Usage percentage of SXL CPU0. "
        ::= { fwSXLStatFalconsCpuEntry 2 }

	fwSXLFalconsCpu1Usage OBJECT-TYPE
	SYNTAX DisplayString (SIZE (0..255))
	MAX-ACCESS read-only
	STATUS current
	DESCRIPTION
                "Usage percentage of SXL CPU1. "
        ::= { fwSXLStatFalconsCpuEntry 3 }

	fwSXLFalconsCpu2Usage OBJECT-TYPE
	SYNTAX DisplayString (SIZE (0..255))
	MAX-ACCESS read-only
	STATUS current
	DESCRIPTION
                "Usage percentage of SXL CPU2. "
        ::= { fwSXLStatFalconsCpuEntry 4 }

	fwSXLFalconsCpu3Usage OBJECT-TYPE
	SYNTAX DisplayString (SIZE (0..255))
	MAX-ACCESS read-only
	STATUS current
	DESCRIPTION
                "Usage percentage of SXL CPU3. "
        ::= { fwSXLStatFalconsCpuEntry 5 }

	fwSXLFalconsCpu4Usage OBJECT-TYPE
	SYNTAX DisplayString (SIZE (0..255))
	MAX-ACCESS read-only
	STATUS current
	DESCRIPTION
                "Usage percentage of SXL CPU4. "
        ::= { fwSXLStatFalconsCpuEntry 6 }

	fwSXLFalconsCpu5Usage OBJECT-TYPE
	SYNTAX DisplayString (SIZE (0..255))
	MAX-ACCESS read-only
	STATUS current
	DESCRIPTION
                "Usage percentage of SXL CPU5. "
        ::= { fwSXLStatFalconsCpuEntry 7 }

	fwSXLFalconsCpu6Usage OBJECT-TYPE
	SYNTAX DisplayString (SIZE (0..255))
	MAX-ACCESS read-only
	STATUS current
	DESCRIPTION
                "Usage percentage of SXL CPU6. "
        ::= { fwSXLStatFalconsCpuEntry 8 }

	fwSXLFalconsCpu7Usage OBJECT-TYPE
	SYNTAX DisplayString (SIZE (0..255))
	MAX-ACCESS read-only
	STATUS current
	DESCRIPTION
                "Usage percentage of SXL CPU7. "
        ::= { fwSXLStatFalconsCpuEntry 9 }

	fwSXLFalconsCpu8Usage OBJECT-TYPE
	SYNTAX DisplayString (SIZE (0..255))
	MAX-ACCESS read-only
	STATUS current
	DESCRIPTION
                "Usage percentage of SXL CPU8. "
        ::= { fwSXLStatFalconsCpuEntry 10 }

	fwSXLFalconsCpu9Usage OBJECT-TYPE
	SYNTAX DisplayString (SIZE (0..255))
	MAX-ACCESS read-only
	STATUS current
	DESCRIPTION
                "Usage percentage of SXL CPU9. "
        ::= { fwSXLStatFalconsCpuEntry 11 }

	fwSXLFalconsCpu10Usage OBJECT-TYPE
	SYNTAX DisplayString (SIZE (0..255))
	MAX-ACCESS read-only
	STATUS current
	DESCRIPTION
                "Usage percentage of SXL CPU10. "
        ::= { fwSXLStatFalconsCpuEntry 12 }

	fwSXLFalconsCpu11Usage OBJECT-TYPE
	SYNTAX DisplayString (SIZE (0..255))
	MAX-ACCESS read-only
	STATUS current
	DESCRIPTION
                "Usage percentage of SXL CPU11. "
        ::= { fwSXLStatFalconsCpuEntry 13 }

	fwSXLFalconsCpu12Usage OBJECT-TYPE
	SYNTAX DisplayString (SIZE (0..255))
	MAX-ACCESS read-only
	STATUS current
	DESCRIPTION
                "Usage percentage of SXL CPU12. "
        ::= { fwSXLStatFalconsCpuEntry 14 }

	fwSXLFalconsCpu13Usage OBJECT-TYPE
	SYNTAX DisplayString (SIZE (0..255))
	MAX-ACCESS read-only
	STATUS current
	DESCRIPTION
                "Usage percentage of SXL CPU13. "
        ::= { fwSXLStatFalconsCpuEntry 15 }

	fwSXLFalconsCpu14Usage OBJECT-TYPE
	SYNTAX DisplayString (SIZE (0..255))
	MAX-ACCESS read-only
	STATUS current
	DESCRIPTION
                "Usage percentage of SXL CPU14. "
        ::= { fwSXLStatFalconsCpuEntry 16 }

	fwSXLFalconsCpu15Usage OBJECT-TYPE
	SYNTAX DisplayString (SIZE (0..255))
	MAX-ACCESS read-only
	STATUS current
	DESCRIPTION
                "Usage percentage of SXL CPU15. "
        ::= { fwSXLStatFalconsCpuEntry 17 }

	fwSXLFalconsCpu16Usage OBJECT-TYPE
	SYNTAX DisplayString (SIZE (0..255))
	MAX-ACCESS read-only
	STATUS current
	DESCRIPTION
                "Usage percentage of SXL CPU16. "
        ::= { fwSXLStatFalconsCpuEntry 18 }

	fwSXLFalconsCpu17Usage OBJECT-TYPE
	SYNTAX DisplayString (SIZE (0..255))
	MAX-ACCESS read-only
	STATUS current
	DESCRIPTION
                "Usage percentage of SXL CPU17. "
        ::= { fwSXLStatFalconsCpuEntry 19 }

	fwSXLFalconsCpu18Usage OBJECT-TYPE
	SYNTAX DisplayString (SIZE (0..255))
	MAX-ACCESS read-only
	STATUS current
	DESCRIPTION
                "Usage percentage of SXL CPU18. "
        ::= { fwSXLStatFalconsCpuEntry 20 }

	fwSXLFalconsCpu19Usage OBJECT-TYPE
	SYNTAX DisplayString (SIZE (0..255))
	MAX-ACCESS read-only
	STATUS current
	DESCRIPTION
                "Usage percentage of SXL CPU19. "
        ::= { fwSXLStatFalconsCpuEntry 21 }

	fwSXLFalconsCpu20Usage OBJECT-TYPE
	SYNTAX DisplayString (SIZE (0..255))
	MAX-ACCESS read-only
	STATUS current
	DESCRIPTION
                "Usage percentage of SXL CPU20. "
        ::= { fwSXLStatFalconsCpuEntry 22 }

	fwSXLFalconsCpu21Usage OBJECT-TYPE
	SYNTAX DisplayString (SIZE (0..255))
	MAX-ACCESS read-only
	STATUS current
	DESCRIPTION
                "Usage percentage of SXL CPU21. "
        ::= { fwSXLStatFalconsCpuEntry 23 }

	fwSXLFalconsCpu22Usage OBJECT-TYPE
	SYNTAX DisplayString (SIZE (0..255))
	MAX-ACCESS read-only
	STATUS current
	DESCRIPTION
                "Usage percentage of SXL CPU22. "
        ::= { fwSXLStatFalconsCpuEntry 24 }

	fwSXLFalconsCpu23Usage OBJECT-TYPE
	SYNTAX DisplayString (SIZE (0..255))
	MAX-ACCESS read-only
	STATUS current
	DESCRIPTION
                "Usage percentage of SXL CPU23. "
        ::= { fwSXLStatFalconsCpuEntry 25 }

	fwSXLFalconsCpu24Usage OBJECT-TYPE
	SYNTAX DisplayString (SIZE (0..255))
	MAX-ACCESS read-only
	STATUS current
	DESCRIPTION
                "Usage percentage of SXL CPU24. "
        ::= { fwSXLStatFalconsCpuEntry 26 }

	fwSXLFalconsCpu25Usage OBJECT-TYPE
	SYNTAX DisplayString (SIZE (0..255))
	MAX-ACCESS read-only
	STATUS current
	DESCRIPTION
                "Usage percentage of SXL CPU25. "
        ::= { fwSXLStatFalconsCpuEntry 27 }

	fwSXLFalconsCpu26Usage OBJECT-TYPE
	SYNTAX DisplayString (SIZE (0..255))
	MAX-ACCESS read-only
	STATUS current
	DESCRIPTION
                "Usage percentage of SXL CPU26. "
        ::= { fwSXLStatFalconsCpuEntry 28 }

	fwSXLFalconsCpu27Usage OBJECT-TYPE
	SYNTAX DisplayString (SIZE (0..255))
	MAX-ACCESS read-only
	STATUS current
	DESCRIPTION
                "Usage percentage of SXL CPU27. "
        ::= { fwSXLStatFalconsCpuEntry 29 }

	fwSXLFalconsCpu28Usage OBJECT-TYPE
	SYNTAX DisplayString (SIZE (0..255))
	MAX-ACCESS read-only
	STATUS current
	DESCRIPTION
                "Usage percentage of SXL CPU28. "
        ::= { fwSXLStatFalconsCpuEntry 30 }

	fwSXLFalconsCpu29Usage OBJECT-TYPE
	SYNTAX DisplayString (SIZE (0..255))
	MAX-ACCESS read-only
	STATUS current
	DESCRIPTION
                "Usage percentage of SXL CPU29. "
        ::= { fwSXLStatFalconsCpuEntry 31 }

	fwSXLFalconsCpu30Usage OBJECT-TYPE
	SYNTAX DisplayString (SIZE (0..255))
	MAX-ACCESS read-only
	STATUS current
	DESCRIPTION
                "Usage percentage of SXL CPU30. "
        ::= { fwSXLStatFalconsCpuEntry 32 }

	fwSXLFalconsCpu31Usage OBJECT-TYPE
	SYNTAX DisplayString (SIZE (0..255))
	MAX-ACCESS read-only
	STATUS current
	DESCRIPTION
                "Usage percentage of SXL CPU31. "
        ::= { fwSXLStatFalconsCpuEntry 33 }

	fwSXLStatFalconsGeneralTable OBJECT-TYPE
	          SYNTAX  SEQUENCE OF  FwSXLStatFalconsGeneralEntry
			  MAX-ACCESS  not-accessible
			  STATUS  current
			  DESCRIPTION "No description available"
			   ::= { fwSXLStatisticsFalcons 7 }

	fwSXLStatFalconsGeneralEntry OBJECT-TYPE
	          SYNTAX  FwSXLStatFalconsGeneralEntry
	          MAX-ACCESS  not-accessible
	          STATUS  current
	          DESCRIPTION "No description available"
	          INDEX   { fwSXLHostGeneralIndex }
	          ::= { fwSXLStatFalconsGeneralTable 1 }

      FwSXLStatFalconsGeneralEntry ::=
              SEQUENCE {
                 fwSXLFalconsGeneralIndex
                      Unsigned32,
				 fwSXLFalconsState
					  DisplayString,
				 fwSXLFalconsType
					  DisplayString,
				 fwSXLFalconsSerialNumber
					  DisplayString,
                 fwSXLFalconsSlotNumber
                      INTEGER
				}

	fwSXLFalconsGeneralIndex OBJECT-TYPE
	SYNTAX Unsigned32
	MAX-ACCESS read-only
	STATUS current
	DESCRIPTION
                "Dummy index. "
        ::= { fwSXLStatFalconsGeneralEntry 1 }

	fwSXLFalconsState OBJECT-TYPE
	SYNTAX DisplayString
	MAX-ACCESS read-only
	STATUS current
	DESCRIPTION
                "The SXL's status. "
        ::= { fwSXLStatFalconsGeneralEntry 2 }

	fwSXLFalconsType OBJECT-TYPE
	SYNTAX DisplayString
	MAX-ACCESS read-only
	STATUS current
	DESCRIPTION
                "The SXL's type. "
        ::= { fwSXLStatFalconsGeneralEntry 3 }

	fwSXLFalconsSerialNumber OBJECT-TYPE
	SYNTAX DisplayString
	MAX-ACCESS read-only
	STATUS current
	DESCRIPTION
                "The SXL's serial number. "
        ::= { fwSXLStatFalconsGeneralEntry 4 }

	fwSXLFalconsSlotNumber OBJECT-TYPE
	SYNTAX  Integer32
	MAX-ACCESS read-only
	STATUS current
	DESCRIPTION
                "The SXL's physical slot number. "
        ::= { fwSXLStatFalconsGeneralEntry 5 }

      -- the VPN status
	  -- Overall statistics and state

     cpvGeneral		    	OBJECT IDENTIFIER ::= { vpn 4 }
     cpvIpsec               OBJECT IDENTIFIER ::= { vpn 5 }
     cpvFwz                 OBJECT IDENTIFIER ::= { vpn 6 }
     cpvAccelerator         OBJECT IDENTIFIER ::= { vpn 8 }
     cpvIKE                 OBJECT IDENTIFIER ::= { vpn 9 }
     cpvIPsec               OBJECT IDENTIFIER ::= { vpn 10 }
     cpvStatistics          OBJECT IDENTIFIER ::= { cpvGeneral 1 }
     cpvErrors              OBJECT IDENTIFIER ::= { cpvGeneral 2 }
     cpvSaStatistics        OBJECT IDENTIFIER ::= { cpvIpsec 2 }
     cpvSaErrors            OBJECT IDENTIFIER ::= { cpvIpsec 3 }
     cpvIpsecStatistics     OBJECT IDENTIFIER ::= { cpvIpsec 4 }
     cpvFwzStatistics       OBJECT IDENTIFIER ::= { cpvFwz 1 }
     cpvFwzErrors           OBJECT IDENTIFIER ::= { cpvFwz 2 }
     cpvHwAccelGeneral      OBJECT IDENTIFIER ::= { cpvAccelerator 1 }
     cpvHwAccelStatistics   OBJECT IDENTIFIER ::= { cpvAccelerator 2 }
     cpvIKEglobals          OBJECT IDENTIFIER ::= { cpvIKE 1 }
     cpvIKEerrors           OBJECT IDENTIFIER ::= { cpvIKE 2 }
     cpvIPsecNIC            OBJECT IDENTIFIER ::= { cpvIPsec 1 }

     cpvProdName OBJECT-TYPE
	        SYNTAX  DisplayString (SIZE (0..255))
	        MAX-ACCESS read-only
	        STATUS  current
	        DESCRIPTION
	        	   "Product name"
	        ::= { vpn 1 }

     cpvVerMajor OBJECT-TYPE
	        SYNTAX  Gauge32
	        MAX-ACCESS read-only
	        STATUS  current
	        DESCRIPTION
	        	   "Major version"
	        ::= { vpn 2 }

	 cpvVerMinor OBJECT-TYPE
	        SYNTAX  Gauge32
	        MAX-ACCESS read-only
	        STATUS  current
	        DESCRIPTION
	        	   "Minor version"
	        ::= { vpn 3 }

     cpvEncPackets OBJECT-TYPE
	        SYNTAX  Counter64
	        MAX-ACCESS read-only
	        STATUS  current
	        DESCRIPTION
	        	   "Encrypted packets"
	        ::= { cpvStatistics 1 }

     cpvDecPackets OBJECT-TYPE
	        SYNTAX  Counter64
	        MAX-ACCESS read-only
	        STATUS  current
	        DESCRIPTION
	        	   "Decrypted packets"
	        ::= { cpvStatistics 2 }

     cpvErrOut OBJECT-TYPE
	        SYNTAX  Counter64
	        MAX-ACCESS read-only
	        STATUS  current
	        DESCRIPTION
	        	   "Encryption errors"
	        ::= { cpvErrors 1 }

     cpvErrIn OBJECT-TYPE
	        SYNTAX  Counter64
	        MAX-ACCESS read-only
	        STATUS  current
	        DESCRIPTION
	        	   "Decryption errors"
	        ::= { cpvErrors 2 }

	 cpvErrIke OBJECT-TYPE
	        SYNTAX  Counter64
	        MAX-ACCESS read-only
	        STATUS  current
	        DESCRIPTION
	        	   "IKE errors"
	        ::= { cpvErrors 3 }

     cpvErrPolicy OBJECT-TYPE
	        SYNTAX  Counter64
	        MAX-ACCESS read-only
	        STATUS  current
	        DESCRIPTION
	        	   "Policy errors"
	        ::= { cpvErrors 4 }


	 cpvCurrEspSAsIn OBJECT-TYPE
	        SYNTAX  Counter64
	        MAX-ACCESS read-only
	        STATUS  current
	        DESCRIPTION
	        	   "IPsec current Inbound ESP SAs"
	        ::= { cpvSaStatistics 1 }

	 cpvTotalEspSAsIn OBJECT-TYPE
	        SYNTAX  Counter64
	        MAX-ACCESS read-only
	        STATUS  current
	        DESCRIPTION
	        	   "IPsec total Inbound ESP SAs"
	        ::= { cpvSaStatistics 2 }

	 cpvCurrEspSAsOut OBJECT-TYPE
	        SYNTAX  Counter64
	        MAX-ACCESS read-only
	        STATUS  current
	        DESCRIPTION
	        	   "IPsec current Outbound ESP SAs"
	        ::= { cpvSaStatistics 3 }

	 cpvTotalEspSAsOut OBJECT-TYPE
	        SYNTAX  Counter64
	        MAX-ACCESS read-only
	        STATUS  current
	        DESCRIPTION
	        	   "IPsec total Outbound ESP SAs"
	        ::= { cpvSaStatistics 4 }

	 cpvCurrAhSAsIn OBJECT-TYPE
	        SYNTAX  Counter64
	        MAX-ACCESS read-only
	        STATUS  current
	        DESCRIPTION
	        	   "IPsec current Inbound AH SAs"
	        ::= { cpvSaStatistics 5 }

	 cpvTotalAhSAsIn OBJECT-TYPE
	        SYNTAX  Counter64
	        MAX-ACCESS read-only
	        STATUS  current
	        DESCRIPTION
	        	   "IPsec total Inbound AH SAs"
	        ::= { cpvSaStatistics 6 }

	 cpvCurrAhSAsOut OBJECT-TYPE
	        SYNTAX  Counter64
	        MAX-ACCESS read-only
	        STATUS  current
	        DESCRIPTION
	        	   "IPsec current Outbound AH SAs"
	        ::= { cpvSaStatistics 7 }

	 cpvTotalAhSAsOut OBJECT-TYPE
	        SYNTAX  Counter64
	        MAX-ACCESS read-only
	        STATUS  current
	        DESCRIPTION
	        	   "IPsec total Outbound AH SAs"
	        ::= { cpvSaStatistics 8 }

	 cpvMaxConncurEspSAsIn OBJECT-TYPE
	        SYNTAX  Counter64
	        MAX-ACCESS read-only
	        STATUS  current
	        DESCRIPTION
	        	   "IPsec max concurrent Inbound ESP SAs"
	        ::= { cpvSaStatistics 9 }

	 cpvMaxConncurEspSAsOut OBJECT-TYPE
	        SYNTAX  Counter64
	        MAX-ACCESS read-only
	        STATUS  current
	        DESCRIPTION
	        	   "IPsec max concurrent Outbound ESP SAs"
	        ::= { cpvSaStatistics 10 }

	 cpvMaxConncurAhSAsIn OBJECT-TYPE
	        SYNTAX  Counter64
	        MAX-ACCESS read-only
	        STATUS  current
	        DESCRIPTION
	        	   "IPsec max concurrent Inbound AH SAs"
	        ::= { cpvSaStatistics 11 }

	 cpvMaxConncurAhSAsOut OBJECT-TYPE
	        SYNTAX  Counter64
	        MAX-ACCESS read-only
	        STATUS  current
	        DESCRIPTION
	        	   "IPsec max concurrent Outbound AH SAs"
	        ::= { cpvSaStatistics 12 }

	 cpvSaDecrErr OBJECT-TYPE
	        SYNTAX  Counter64
	        MAX-ACCESS read-only
	        STATUS  current
	        DESCRIPTION
	        	   "IPsec decryption errors"
	        ::= { cpvSaErrors 1 }

	 cpvSaAuthErr OBJECT-TYPE
	        SYNTAX  Counter64
	        MAX-ACCESS read-only
	        STATUS  current
	        DESCRIPTION
	        	   "IPsec authentication errors"
	        ::= { cpvSaErrors 2 }

	 cpvSaReplayErr OBJECT-TYPE
	        SYNTAX  Counter64
	        MAX-ACCESS read-only
	        STATUS  current
	        DESCRIPTION
	        	   "IPsec replay errors"
	        ::= { cpvSaErrors 3 }

	 cpvSaPolicyErr OBJECT-TYPE
	        SYNTAX  Counter64
	        MAX-ACCESS read-only
	        STATUS  current
	        DESCRIPTION
	        	   "IPsec policy errors"
	        ::= { cpvSaErrors 4 }

	 cpvSaOtherErrIn OBJECT-TYPE
	        SYNTAX  Counter64
	        MAX-ACCESS read-only
	        STATUS  current
	        DESCRIPTION
	        	   "IPsec other inbound errors"
	        ::= { cpvSaErrors 5 }

	 cpvSaOtherErrOut OBJECT-TYPE
	        SYNTAX  Counter64
	        MAX-ACCESS read-only
	        STATUS  current
	        DESCRIPTION
	        	   "IPsec other outbound errors"
	        ::= { cpvSaErrors 6 }

	 cpvSaUnknownSpiErr OBJECT-TYPE
	        SYNTAX  Counter64
	        MAX-ACCESS read-only
	        STATUS  current
	        DESCRIPTION
	        	   "IPsec unknown SPI errors"
	        ::= { cpvSaErrors 7 }


	 cpvIpsecUdpEspEncPkts OBJECT-TYPE
	        SYNTAX  Counter64
	        MAX-ACCESS read-only
	        STATUS  current
	        DESCRIPTION
	        	   "IPsec UDP ESP encrypted packets"
	        ::= { cpvIpsecStatistics 1 }

	 cpvIpsecUdpEspDecPkts OBJECT-TYPE
	        SYNTAX  Counter64
	        MAX-ACCESS read-only
	        STATUS  current
	        DESCRIPTION
	        	   "IPsec UDP ESP decrypted packets"
	        ::= { cpvIpsecStatistics 2 }

	 cpvIpsecAhEncPkts OBJECT-TYPE
	        SYNTAX  Counter64
	        MAX-ACCESS read-only
	        STATUS  current
	        DESCRIPTION
	        	   "IPsec AH encrypted packets"
	        ::= { cpvIpsecStatistics 3 }

	 cpvIpsecAhDecPkts OBJECT-TYPE
	        SYNTAX  Counter64
	        MAX-ACCESS read-only
	        STATUS  current
	        DESCRIPTION
	        	   "IPsec AH decrypted packets"
	        ::= { cpvIpsecStatistics 4 }

	 cpvIpsecEspEncPkts OBJECT-TYPE
	        SYNTAX  Counter64
	        MAX-ACCESS read-only
	        STATUS  current
	        DESCRIPTION
	        	   "IPsec ESP encrypted packets"
	        ::= { cpvIpsecStatistics 5 }

	 cpvIpsecEspDecPkts OBJECT-TYPE
	        SYNTAX  Counter64
	        MAX-ACCESS read-only
	        STATUS  current
	        DESCRIPTION
	        	   "IPsec ESP decrypted packets"
	        ::= { cpvIpsecStatistics 6 }

     cpvIpsecDecomprBytesBefore OBJECT-TYPE
	        SYNTAX  Counter64
	        MAX-ACCESS read-only
	        STATUS  current
	        DESCRIPTION
	        	   "IPsec bytes before decompression"
	        ::= { cpvIpsecStatistics 7 }


	 cpvIpsecDecomprBytesAfter OBJECT-TYPE
	        SYNTAX  Counter64
	        MAX-ACCESS read-only
	        STATUS  current
	        DESCRIPTION
	        	   "IPsec bytes after decompression"
	        ::= { cpvIpsecStatistics 8 }

	 cpvIpsecDecomprOverhead OBJECT-TYPE
	        SYNTAX  Counter64
	        MAX-ACCESS read-only
	        STATUS  current
	        DESCRIPTION
	        	   "IPsec bytes decompression overhead"
	        ::= { cpvIpsecStatistics 9 }

	 cpvIpsecDecomprPkts OBJECT-TYPE
	        SYNTAX  Counter64
	        MAX-ACCESS read-only
	        STATUS  current
	        DESCRIPTION
	        	   "IPsec packets decompressed"
	        ::= { cpvIpsecStatistics 10 }

	 cpvIpsecDecomprErr OBJECT-TYPE
	        SYNTAX  Counter64
	        MAX-ACCESS read-only
	        STATUS  current
	        DESCRIPTION
	        	   "IPsec decompression errors"
	        ::= { cpvIpsecStatistics 11 }

	 cpvIpsecComprBytesBefore OBJECT-TYPE
	        SYNTAX  Counter64
	        MAX-ACCESS read-only
	        STATUS  current
	        DESCRIPTION
	        	   "IPsec bytes before compression"
	        ::= { cpvIpsecStatistics 12 }

     cpvIpsecComprBytesAfter OBJECT-TYPE
	        SYNTAX  Counter64
	        MAX-ACCESS read-only
	        STATUS  current
	        DESCRIPTION
	        	   "IPsec bytes after compression"
	        ::= { cpvIpsecStatistics 13 }

 	 cpvIpsecComprOverhead OBJECT-TYPE
	        SYNTAX  Counter64
	        MAX-ACCESS read-only
	        STATUS  current
	        DESCRIPTION
	        	   "IPsec bytes compression overhead"
	        ::= { cpvIpsecStatistics 14 }

	 cpvIpsecNonCompressibleBytes OBJECT-TYPE
	        SYNTAX  Counter64
	        MAX-ACCESS read-only
	        STATUS  current
	        DESCRIPTION
	        	   "IPsec bytes non compressible"
	        ::= { cpvIpsecStatistics 15 }

     cpvIpsecCompressiblePkts OBJECT-TYPE
	        SYNTAX  Counter64
	        MAX-ACCESS read-only
	        STATUS  current
	        DESCRIPTION
	        	   "IPsec packets compressed"
	        ::= { cpvIpsecStatistics 16 }

     cpvIpsecNonCompressiblePkts OBJECT-TYPE
	        SYNTAX  Counter64
	        MAX-ACCESS read-only
	        STATUS  current
	        DESCRIPTION
	        	   "IPsec packets non compressible"
	        ::= { cpvIpsecStatistics 17 }

	 cpvIpsecComprErrors OBJECT-TYPE
	        SYNTAX  Counter64
	        MAX-ACCESS read-only
	        STATUS  current
	        DESCRIPTION
	        	   "IPsec compression errors"
	        ::= { cpvIpsecStatistics 18 }

	 cpvIpsecEspEncBytes OBJECT-TYPE
	        SYNTAX  Counter64
	        MAX-ACCESS read-only
	        STATUS  current
	        DESCRIPTION
	        	   "IPsec ESP encrypted bytes"
	        ::= { cpvIpsecStatistics 19 }

	 cpvIpsecEspDecBytes OBJECT-TYPE
	        SYNTAX  Counter64
	        MAX-ACCESS read-only
	        STATUS  current
	        DESCRIPTION
	        	   "IPsec ESP decrypted bytes"
	        ::= { cpvIpsecStatistics 20 }

     cpvFwzEncapsEncPkts OBJECT-TYPE
	        SYNTAX  Counter64
	        MAX-ACCESS read-only
	        STATUS  current
	        DESCRIPTION
	        	   "Fwz encapsulated encrypted packets"
	        ::= { cpvFwzStatistics 1 }

     cpvFwzEncapsDecPkts OBJECT-TYPE
	        SYNTAX  Counter64
	        MAX-ACCESS read-only
	        STATUS  current
	        DESCRIPTION
	        	   "Fwz encapsulated decrypted packets"
	        ::= { cpvFwzStatistics 2 }

     cpvFwzEncPkts OBJECT-TYPE
	        SYNTAX  Integer32
	        MAX-ACCESS read-only
	        STATUS  current
	        DESCRIPTION
	        	   "Fwz encrypted packets"
	        ::= { cpvFwzStatistics 3 }

	 cpvFwzDecPkts OBJECT-TYPE
	        SYNTAX  Integer32
	        MAX-ACCESS read-only
	        STATUS  current
	        DESCRIPTION
	        	   "Fwz decrypted packets"
	        ::= { cpvFwzStatistics 4 }


	 cpvFwzEncapsEncErrs OBJECT-TYPE
	        SYNTAX Counter64
	        MAX-ACCESS read-only
	        STATUS  current
	        DESCRIPTION
	        	   "Fwz encapsulated encryption errors"
	        ::= { cpvFwzErrors 1 }

     cpvFwzEncapsDecErrs OBJECT-TYPE
	        SYNTAX  Counter64
	        MAX-ACCESS read-only
	        STATUS  current
	        DESCRIPTION
	        	   "Fwz encapsulated decryption errors"
	        ::= { cpvFwzErrors 2 }

     cpvFwzEncErrs OBJECT-TYPE
	        SYNTAX  Integer32
	        MAX-ACCESS read-only
	        STATUS  current
	        DESCRIPTION
	        	   "Fwz encryption errors"
	        ::= { cpvFwzErrors 3 }

	 cpvFwzDecErrs OBJECT-TYPE
	        SYNTAX  Integer32
	        MAX-ACCESS read-only
	        STATUS  current
	        DESCRIPTION
	        	   "Fwz decryption errors"
	        ::= { cpvFwzErrors 4 }

     cpvHwAccelVendor OBJECT-TYPE
	        SYNTAX  DisplayString
	        MAX-ACCESS read-only
	        STATUS  current
	        DESCRIPTION
	        	   "HW accel. vendor"
	        ::= { cpvHwAccelGeneral 1 }

     cpvHwAccelStatus OBJECT-TYPE
	        SYNTAX  DisplayString
	        MAX-ACCESS read-only
	        STATUS  current
	        DESCRIPTION
	        	   "HW accel. status"
	        ::= { cpvHwAccelGeneral 2 }

     cpvHwAccelDriverMajorVer OBJECT-TYPE
	        SYNTAX  Unsigned32
	        MAX-ACCESS read-only
	        STATUS  current
	        DESCRIPTION
	        	   "HW accel. driver major version"
	        ::= { cpvHwAccelGeneral 3 }

     cpvHwAccelDriverMinorVer OBJECT-TYPE
	        SYNTAX  Unsigned32
	        MAX-ACCESS read-only
	        STATUS  current
	        DESCRIPTION
	        	   "HW accel. driver minor version"
	        ::= { cpvHwAccelGeneral 4 }

     cpvHwAccelEspEncPkts OBJECT-TYPE
	        SYNTAX  Counter64
	        MAX-ACCESS read-only
	        STATUS  current
	        DESCRIPTION
	        	   "HW accel. encrypted IPsec ESP packets"
	        ::= { cpvHwAccelStatistics 1 }


     cpvHwAccelEspDecPkts OBJECT-TYPE
	        SYNTAX  Counter64
	        MAX-ACCESS read-only
	        STATUS  current
	        DESCRIPTION
	        	   "HW accel. decrypted IPsec ESP packets"
	        ::= { cpvHwAccelStatistics 2 }

	cpvHwAccelEspEncBytes OBJECT-TYPE
	        SYNTAX  Counter64
	        MAX-ACCESS read-only
	        STATUS  current
	        DESCRIPTION
	        	   "HW accel. encrypted IPsec ESP bytes"
	        ::= { cpvHwAccelStatistics 3 }

	cpvHwAccelEspDecBytes OBJECT-TYPE
	        SYNTAX  Counter64
	        MAX-ACCESS read-only
	        STATUS  current
	        DESCRIPTION
	        	   "HW accel. decrypted IPsec ESP bytes"
	        ::= { cpvHwAccelStatistics 4 }

	cpvHwAccelAhEncPkts OBJECT-TYPE
	        SYNTAX  Counter64
	        MAX-ACCESS read-only
	        STATUS  current
	        DESCRIPTION
	        	   "HW accel. encrypted IPsec AH packets"
	        ::= { cpvHwAccelStatistics 5 }

	cpvHwAccelAhDecPkts OBJECT-TYPE
	        SYNTAX  Counter64
	        MAX-ACCESS read-only
	        STATUS  current
	        DESCRIPTION
	        	   "HW accel. decrypted IPsec AH packets"
	        ::= { cpvHwAccelStatistics 6 }

	cpvHwAccelAhEncBytes OBJECT-TYPE
	        SYNTAX  Counter64
	        MAX-ACCESS read-only
	        STATUS  current
	        DESCRIPTION
	        	   "HW accel. encrypted IPsec AH bytes"
	        ::= { cpvHwAccelStatistics 7 }


     cpvHwAccelAhDecBytes OBJECT-TYPE
	        SYNTAX  Counter64
	        MAX-ACCESS read-only
	        STATUS  current
	        DESCRIPTION
	        	   "HW accel. decrypted IPsec AH bytes"
	        ::= { cpvHwAccelStatistics 8 }


     cpvIKECurrSAs OBJECT-TYPE
	        SYNTAX  Counter64
	        MAX-ACCESS read-only
	        STATUS  current
	        DESCRIPTION
	        	   "IKE current SAs"
	        ::= { cpvIKEglobals 1 }

     cpvIKECurrInitSAs OBJECT-TYPE
	        SYNTAX  Counter64
	        MAX-ACCESS read-only
	        STATUS  current
	        DESCRIPTION
	        	   "IKE current initiated SAs"
	        ::= { cpvIKEglobals 2 }

     cpvIKECurrRespSAs OBJECT-TYPE
	        SYNTAX  Counter64
	        MAX-ACCESS read-only
	        STATUS  current
	        DESCRIPTION
	        	   "IKE current responded SAs"
	        ::= { cpvIKEglobals 3 }

     cpvIKETotalSAs OBJECT-TYPE
	        SYNTAX  Counter64
	        MAX-ACCESS read-only
	        STATUS  current
	        DESCRIPTION
	        	   "IKE total SAs"
	        ::= { cpvIKEglobals 4 }

     cpvIKETotalInitSAs OBJECT-TYPE
	        SYNTAX  Counter64
	        MAX-ACCESS read-only
	        STATUS  current
	        DESCRIPTION
	        	   "IKE total initiated SAs"
	        ::= { cpvIKEglobals 5 }

     cpvIKETotalRespSAs OBJECT-TYPE
	        SYNTAX  Counter64
	        MAX-ACCESS read-only
	        STATUS  current
	        DESCRIPTION
	        	   "IKE total responded SAs"
	        ::= { cpvIKEglobals 6 }

     cpvIKETotalSAsAttempts OBJECT-TYPE
	        SYNTAX  Counter64
	        MAX-ACCESS read-only
	        STATUS  current
	        DESCRIPTION
	        	   "IKE total SAs attempts"
	        ::= { cpvIKEglobals 7 }

     cpvIKETotalSAsInitAttempts OBJECT-TYPE
	        SYNTAX  Counter64
	        MAX-ACCESS read-only
	        STATUS  current
	        DESCRIPTION
	        	   "IKE total SAs initiated attempts"
	        ::= { cpvIKEglobals 8 }

     cpvIKETotalSAsRespAttempts OBJECT-TYPE
	        SYNTAX  Counter64
	        MAX-ACCESS read-only
	        STATUS  current
	        DESCRIPTION
	        	   "IKE total SAs responded attempts"
	        ::= { cpvIKEglobals 9 }

     cpvIKEMaxConncurSAs OBJECT-TYPE
	        SYNTAX  Counter64
	        MAX-ACCESS read-only
	        STATUS  current
	        DESCRIPTION
	        	   "IKE max concurrent SAs"
	        ::= { cpvIKEglobals 10 }

     cpvIKEMaxConncurInitSAs OBJECT-TYPE
	        SYNTAX  Counter64
	        MAX-ACCESS read-only
	        STATUS  current
	        DESCRIPTION
	        	   "IKE max concurrent initiated SAs"
	        ::= { cpvIKEglobals 11 }

     cpvIKEMaxConncurRespSAs OBJECT-TYPE
	        SYNTAX  Counter64
	        MAX-ACCESS read-only
	        STATUS  current
	        DESCRIPTION
	        	   "IKE max concurrent responded SAs"
	        ::= { cpvIKEglobals 12 }

     cpvIKETotalFailuresInit OBJECT-TYPE
	        SYNTAX  Counter64
	        MAX-ACCESS read-only
	        STATUS  current
	        DESCRIPTION
	        	   "IKE total failures (initiator errors)"
	        ::= { cpvIKEerrors 1 }

     cpvIKENoResp OBJECT-TYPE
	        SYNTAX  Counter64
	        MAX-ACCESS read-only
	        STATUS  current
	        DESCRIPTION
	        	   "IKE no response from peer (initiator errors)"
	        ::= { cpvIKEerrors 2 }

     cpvIKETotalFailuresResp OBJECT-TYPE
	        SYNTAX  Counter64
	        MAX-ACCESS read-only
	        STATUS  current
	        DESCRIPTION
	        	   "IKE total failures (responder errors)"
	        ::= { cpvIKEerrors 3 }

     cpvIPsecNICsNum OBJECT-TYPE
	        SYNTAX  Unsigned32
	        MAX-ACCESS read-only
	        STATUS  current
	        DESCRIPTION
	        	   "IPsec NIC: Number of IPsec NIC's"
	        ::= { cpvIPsecNIC 1 }

     cpvIPsecNICTotalDownLoadedSAs OBJECT-TYPE
	        SYNTAX  Counter64
	        MAX-ACCESS read-only
	        STATUS  current
	        DESCRIPTION
	        	   "IPsec NIC: Total downloaded SA's"
	        ::= { cpvIPsecNIC 2 }

     cpvIPsecNICCurrDownLoadedSAs OBJECT-TYPE
	        SYNTAX  Counter64
	        MAX-ACCESS read-only
	        STATUS  current
	        DESCRIPTION
	        	   "IPsec NIC: Current downloaded SA's"
	        ::= { cpvIPsecNIC 3 }

     cpvIPsecNICDecrBytes OBJECT-TYPE
	        SYNTAX  Counter64
	        MAX-ACCESS read-only
	        STATUS  current
	        DESCRIPTION
	        	   "IPsec NIC: Decrypted bytes by NIC"
	        ::= { cpvIPsecNIC 4 }

     cpvIPsecNICEncrBytes OBJECT-TYPE
	        SYNTAX  Counter64
	        MAX-ACCESS read-only
	        STATUS  current
	        DESCRIPTION
	        	   "IPsec NIC: Encrypted bytes by NIC"
	        ::= { cpvIPsecNIC 5 }

     cpvIPsecNICDecrPackets OBJECT-TYPE
	        SYNTAX  Counter64
	        MAX-ACCESS read-only
	        STATUS  current
	        DESCRIPTION
	        	   "IPsec NIC: Decrypted packets by NIC"
	        ::= { cpvIPsecNIC 6 }

     cpvIPsecNICEncrPackets OBJECT-TYPE
	        SYNTAX  Counter64
	        MAX-ACCESS read-only
	        STATUS  current
	        DESCRIPTION
	        	   "IPsec NIC: Encrypted packets by NIC"
	        ::= { cpvIPsecNIC 7 }

--     cpvTnlMon OBJECT-TYPE
--	        SYNTAX  SEQUENCE OF cpvTnlMonEntry
--	        MAX-ACCESS read-only
--	        STATUS  current
--	        DESCRIPTION
--	        	   "The table of monitored tunnels"
--	        ::= { vpn 11 }
--
--    cpvTnlMonEntry OBJECT-TYPE
--	        SYNTAX  CpvTnlMonEntry
--	        MAX-ACCESS read-only
--	        STATUS  current
--			INDEX	{ cpvTnlMonAddr }
--	        ::= { cpvTnlMon 1 }
--
--      CpvTnlMonEntry ::=
--           SEQUENCE {
--              cpvTnlMonAddr
--                    IpAddress,
--               cpvTnlMonStatus
--                    INTEGER,
--               cpvTNlMonCurrAddr
--                    IpAddress
--            }
--
--    cpvTnlMonAddr OBJECT-TYPE
--	        SYNTAX  IpAddress
--	        MAX-ACCESS read-only
--	        STATUS  current
--	        DESCRIPTION
--	        	   "The main IP address of the peer (bogus IP for DAIP)"
--	        ::= { cpvTnlMonEntry 1 }
--
--     cpvTnlMonStatus OBJECT-TYPE
--	        SYNTAX  INTEGER {
--				INITIAL	(0),
--				UP		(1)
--			}
--	        MAX-ACCESS read-only
--	        STATUS  current
--	        DESCRIPTION
--	        	   "The status of the peer"
--	        ::= { cpvTnlMonEntry 2 }
--
--     cpvTnlMonCurrAddr OBJECT-TYPE
--	        SYNTAX  IpAddress
--	        MAX-ACCESS read-only
--	        STATUS  current
--	        DESCRIPTION
--	        	   "The current IP address of the peer (for DAIPs)"
--	        ::= { cpvTnlMonEntry 3 }

	  -- the FG status
	  -- Overall statistics and state

	 fgProdName OBJECT-TYPE
	        SYNTAX  DisplayString (SIZE (0..255))
	        MAX-ACCESS read-only
	        STATUS  current
	        DESCRIPTION
	        	   "Product name"
	        ::= { fg 1 }

	 fgVerMajor OBJECT-TYPE
	        SYNTAX  Integer32
	        MAX-ACCESS read-only
	        STATUS  current
	        DESCRIPTION
	        	   "Major version"
	        ::= { fg 2 }

	 fgVerMinor OBJECT-TYPE
	        SYNTAX  Integer32
	        MAX-ACCESS read-only
	        STATUS  current
	        DESCRIPTION
	        	   "Minor version"
	        ::= { fg 3 }

	 fgVersionString OBJECT-TYPE
	        SYNTAX  DisplayString (SIZE (0..255))
	        MAX-ACCESS read-only
	        STATUS  current
	        DESCRIPTION
	        	   "Version string"
	        ::= { fg 4 }

	 fgModuleKernelBuild OBJECT-TYPE
	        SYNTAX  Integer32
	        MAX-ACCESS read-only
	        STATUS  current
	        DESCRIPTION
	        	   "Kernel build"
	        ::= { fg 5 }

	 fgStrPolicyName OBJECT-TYPE
	        SYNTAX  DisplayString (SIZE (0..255))
	        MAX-ACCESS read-only
	        STATUS  current
	        DESCRIPTION
	        	   "Policy name"
	        ::= { fg 6 }

	 fgInstallTime OBJECT-TYPE
	        SYNTAX  DisplayString (SIZE (0..255))
	        MAX-ACCESS read-only
	        STATUS  current
	        DESCRIPTION
	        	   "Install time"
	        ::= { fg 7 }

	 fgNumInterfaces OBJECT-TYPE
	        SYNTAX  DisplayString (SIZE (0..255))
	        MAX-ACCESS read-only
	        STATUS  current
	        DESCRIPTION
	        	   "Interfaces num"
	        ::= { fg 8 }

	  fgIfTable OBJECT-TYPE
	        SYNTAX  SEQUENCE OF FgIfEntry
	        MAX-ACCESS  not-accessible
	        STATUS  current
	        DESCRIPTION "No description available"
	         ::= { fg 9 }

	  fgIfEntry OBJECT-TYPE
	  		SYNTAX  FgIfEntry
	  		MAX-ACCESS  not-accessible
	  		STATUS  current
	  		DESCRIPTION "No description available"
	  		INDEX   { fgIfIndex }
	  		::= { fgIfTable 1 }

      FgIfEntry ::=
      		SEQUENCE {
      			fgIfIndex
		          	Unsigned32,
		        fgIfName
		        	DisplayString,
		        fgPolicyName
		        	DisplayString,
		        fgRateLimitIn
		          	INTEGER,
		        fgRateLimitOut
		          	INTEGER,
		        fgAvrRateIn
		          	INTEGER,
                fgAvrRateOut
                  	INTEGER,
                fgRetransPcktsIn
         		  	INTEGER,
	            fgRetransPcktsOut
	              	INTEGER,
	            fgPendPcktsIn
	              	INTEGER,
	            fgPendPcktsOut
	              	INTEGER,
	            fgPendBytesIn
	              	INTEGER,
	            fgPendBytesOut
	              	INTEGER,
	            fgNumConnIn
	              	INTEGER,
	            fgNumConnOut
	              	INTEGER
	         }

	 fgIfIndex OBJECT-TYPE
              SYNTAX  Unsigned32
              MAX-ACCESS not-accessible
              STATUS  current
              DESCRIPTION "No description available"
              ::= { fgIfEntry 1 }

     fgIfName OBJECT-TYPE
              SYNTAX  DisplayString
              MAX-ACCESS read-only
              STATUS  current
              DESCRIPTION "No description available"
              ::= { fgIfEntry 2 }

     fgPolicyName OBJECT-TYPE
              SYNTAX  DisplayString
              MAX-ACCESS read-only
              STATUS  current
              DESCRIPTION "No description available"
              ::= { fgIfEntry 3 }


     fgRateLimitIn OBJECT-TYPE
              SYNTAX  Integer32
              MAX-ACCESS read-only
              STATUS  current
              DESCRIPTION "No description available"
              ::= { fgIfEntry 4 }

     fgRateLimitOut OBJECT-TYPE
              SYNTAX  Integer32
              MAX-ACCESS read-only
              STATUS  current
              DESCRIPTION "No description available"
              ::= { fgIfEntry 5 }

     fgAvrRateIn OBJECT-TYPE
              SYNTAX  Integer32
              MAX-ACCESS read-only
              STATUS  current
              DESCRIPTION "No description available"
              ::= { fgIfEntry 6 }

     fgAvrRateOut OBJECT-TYPE
              SYNTAX  Integer32
              MAX-ACCESS read-only
              STATUS  current
              DESCRIPTION "No description available"
              ::= { fgIfEntry 7 }

     fgRetransPcktsIn OBJECT-TYPE
              SYNTAX  Integer32
              MAX-ACCESS read-only
              STATUS  current
              DESCRIPTION "No description available"
              ::= { fgIfEntry 8 }

     fgRetransPcktsOut OBJECT-TYPE
              SYNTAX  Integer32
              MAX-ACCESS read-only
              STATUS  current
              DESCRIPTION "No description available"
              ::= { fgIfEntry 9 }

     fgPendPcktsIn OBJECT-TYPE
              SYNTAX  Integer32
              MAX-ACCESS read-only
              STATUS  current
              DESCRIPTION "No description available"
              ::= { fgIfEntry 10 }

     fgPendPcktsOut OBJECT-TYPE
              SYNTAX  Integer32
              MAX-ACCESS read-only
              STATUS  current
              DESCRIPTION "No description available"
              ::= { fgIfEntry 11 }

     fgPendBytesIn OBJECT-TYPE
              SYNTAX  Integer32
              MAX-ACCESS read-only
              STATUS  current
              DESCRIPTION "No description available"
              ::= { fgIfEntry 12 }

     fgPendBytesOut OBJECT-TYPE
              SYNTAX  Integer32
              MAX-ACCESS read-only
              STATUS  current
              DESCRIPTION "No description available"
              ::= { fgIfEntry 13 }

     fgNumConnIn OBJECT-TYPE
              SYNTAX  Integer32
              MAX-ACCESS read-only
              STATUS  current
              DESCRIPTION "No description available"
              ::= { fgIfEntry 14 }

     fgNumConnOut OBJECT-TYPE
              SYNTAX  Integer32
              MAX-ACCESS read-only
              STATUS  current
              DESCRIPTION "No description available"
              ::= { fgIfEntry 15 }

	  -- the HA status
	  -- Overall statistics and state

	 haProdName OBJECT-TYPE
	  		  SYNTAX  DisplayString (SIZE (0..255))
			  MAX-ACCESS read-only
			  STATUS  current
			  DESCRIPTION
					 "Product name"
			  ::= { ha 1 }

	 haInstalled OBJECT-TYPE
	  		  SYNTAX  Integer32
			  MAX-ACCESS read-only
			  STATUS  current
			  DESCRIPTION
					 "HA installed"
			  ::= { ha 2 }

     haVerMajor OBJECT-TYPE
	  		  SYNTAX  Integer32
			  MAX-ACCESS read-only
			  STATUS  current
			  DESCRIPTION
					 "Major version"
			  ::= { ha 3 }

	 haVerMinor OBJECT-TYPE
	  		  SYNTAX  Integer32
			  MAX-ACCESS read-only
			  STATUS  current
			  DESCRIPTION
					 "Minor version"
			  ::= { ha 4 }

	 haStarted OBJECT-TYPE
	  		  SYNTAX  DisplayString (SIZE (0..255))
			  MAX-ACCESS read-only
			  STATUS  current
			  DESCRIPTION
					 "HA started"
			  ::= { ha 5 }

	 haState OBJECT-TYPE
	  		  SYNTAX  DisplayString (SIZE (0..255))
			  MAX-ACCESS read-only
			  STATUS  current
			  DESCRIPTION
					 "HA state"
			  ::= { ha 6 }

	 haBlockState OBJECT-TYPE
	  		  SYNTAX  DisplayString (SIZE (0..255))
			  MAX-ACCESS read-only
			  STATUS  current
			  DESCRIPTION
					 "HA blocking state"
			  ::= { ha 7 }

	 haIdentifier OBJECT-TYPE
	  		  SYNTAX  Integer32
			  MAX-ACCESS read-only
			  STATUS  current
			  DESCRIPTION
					 "HA identifier"
			  ::= { ha 8 }

	 haProtoVersion OBJECT-TYPE
	  		  SYNTAX  Integer32
			  MAX-ACCESS read-only
			  STATUS  current
			  DESCRIPTION
					 "HA protocol version"
			  ::= { ha 10 }

	 haWorkMode OBJECT-TYPE
	  		  SYNTAX  DisplayString (SIZE (0..255))
			  MAX-ACCESS read-only
			  STATUS  current
			  DESCRIPTION
					 "Working mode"
			  ::= { ha 11 }

	 haVersionSting OBJECT-TYPE
	  		  SYNTAX  DisplayString (SIZE (0..255))
			  MAX-ACCESS read-only
			  STATUS  current
			  DESCRIPTION
					 "Version string"
			  ::= { ha 14 }

	 haClusterXLFailover OBJECT-TYPE
	  		  SYNTAX  Integer32
			  MAX-ACCESS read-only
			  STATUS  current
			  DESCRIPTION
					 "ClusterXL Failover"
			  ::= { ha 17 }

	 haStatCode OBJECT-TYPE
	  		  SYNTAX  Integer32
			  MAX-ACCESS read-only
			  STATUS  current
			  DESCRIPTION
					 "Status code"
			  ::= { ha 101 }

	 haStatShort OBJECT-TYPE
	  		  SYNTAX  DisplayString (SIZE (0..255))
			  MAX-ACCESS read-only
			  STATUS  current
			  DESCRIPTION
					 "Status short"
			  ::= { ha 102 }

	 haStatLong OBJECT-TYPE
	  		  SYNTAX  DisplayString (SIZE (0..255))
			  MAX-ACCESS read-only
			  STATUS  current
			  DESCRIPTION
					 "Status long"
			  ::= { ha 103 }

	 haServicePack OBJECT-TYPE
	  		  SYNTAX  Integer32
			  MAX-ACCESS read-only
			  STATUS  current
			  DESCRIPTION
					 "Service pack"
			  ::= { ha 999 }

	  haIfTable OBJECT-TYPE
	        SYNTAX  SEQUENCE OF HaIfEntry
	        MAX-ACCESS  not-accessible
	        STATUS  current
	        DESCRIPTION "No description available"
	         ::= { ha 12 }

	  haIfEntry OBJECT-TYPE
	  		SYNTAX  HaIfEntry
	  		MAX-ACCESS  not-accessible
	  		STATUS  current
	  		DESCRIPTION "No description available"
	  		INDEX   { haIfIndex }
	  		::= { haIfTable 1 }

      HaIfEntry ::=
      		SEQUENCE {
      			haIfIndex
		          	Unsigned32,
		        haIfName
		        	DisplayString,
		        haIP
		          	IpAddress,
		        haStatus
		          	DisplayString,
		        haVerified
		          	Unsigned32,
                haTrusted
                  	INTEGER,
                haShared
         		  	INTEGER
	         }

	 haIfIndex OBJECT-TYPE
              SYNTAX  Unsigned32
              MAX-ACCESS not-accessible
              STATUS  current
              DESCRIPTION "No description available"
              ::= { haIfEntry 1 }

     haIfName OBJECT-TYPE
              SYNTAX  DisplayString
              MAX-ACCESS read-only
              STATUS  current
              DESCRIPTION "No description available"
              ::= { haIfEntry 2 }

     haIP OBJECT-TYPE
              SYNTAX  IpAddress
              MAX-ACCESS read-only
              STATUS  current
              DESCRIPTION "No description available"
              ::= { haIfEntry 3 }

     haStatus OBJECT-TYPE
              SYNTAX  DisplayString
              MAX-ACCESS read-only
              STATUS  current
              DESCRIPTION "No description available"
              ::= { haIfEntry 4 }

     haVerified OBJECT-TYPE
              SYNTAX  Unsigned32
              MAX-ACCESS read-only
              STATUS  current
              DESCRIPTION "No description available"
              ::= { haIfEntry 5 }

     haTrusted OBJECT-TYPE
              SYNTAX  Integer32
              MAX-ACCESS read-only
              STATUS  current
              DESCRIPTION "No description available"
              ::= { haIfEntry 6 }

     haShared OBJECT-TYPE
              SYNTAX  Integer32
              MAX-ACCESS read-only
              STATUS  current
              DESCRIPTION "No description available"
              ::= { haIfEntry 7 }


	  haProblemTable OBJECT-TYPE
	        SYNTAX  SEQUENCE OF HaProblemEntry
	        MAX-ACCESS  not-accessible
	        STATUS  current
	        DESCRIPTION "No description available"
	         ::= { ha 13 }

	  haProblemEntry OBJECT-TYPE
	  		SYNTAX  HaProblemEntry
	  		MAX-ACCESS  not-accessible
	  		STATUS  current
	  		DESCRIPTION "No description available"
	  		INDEX   { haIfIndex }
	  		::= { haProblemTable 1 }

      HaProblemEntry ::=
      		SEQUENCE {
      			haProblemIndex
		          	Unsigned32,
		        haProblemName
		        	DisplayString,
		        haProblemStatus
		          	DisplayString,
		        haProblemPriority
		          	INTEGER,
                haProblemVerified
                  	Unsigned32,
                haProblemDescr
         		  	DisplayString
	         }

	 haProblemIndex OBJECT-TYPE
              SYNTAX  Unsigned32
              MAX-ACCESS read-only
              STATUS  current
              DESCRIPTION "No description available"
              ::= { haProblemEntry 1 }

     haProblemName OBJECT-TYPE
              SYNTAX  DisplayString
              MAX-ACCESS read-only
              STATUS  current
              DESCRIPTION "No description available"
              ::= { haProblemEntry 2 }

     haProblemStatus OBJECT-TYPE
              SYNTAX  DisplayString
              MAX-ACCESS read-only
              STATUS  current
              DESCRIPTION "No description available"
              ::= { haProblemEntry 3 }

     haProblemPriority OBJECT-TYPE
              SYNTAX  Integer32
              MAX-ACCESS read-only
              STATUS  current
              DESCRIPTION "No description available"
              ::= { haProblemEntry 4 }

     haProblemVerified OBJECT-TYPE
              SYNTAX  Unsigned32
              MAX-ACCESS read-only
              STATUS  current
              DESCRIPTION "No description available"
              ::= { haProblemEntry 5 }

     haProblemDescr OBJECT-TYPE
              SYNTAX  DisplayString
              MAX-ACCESS read-only
              STATUS  current
              DESCRIPTION "No description available"
              ::= { haProblemEntry 6 }

     haClusterIpTable OBJECT-TYPE
	      SYNTAX  SEQUENCE OF HaClusterIpEntry
	      MAX-ACCESS  not-accessible
	      STATUS  current
	      DESCRIPTION "No description available"
	      ::= { ha 15 }

     haClusterIpEntry OBJECT-TYPE
	      SYNTAX  HaClusterIpEntry
	      MAX-ACCESS  not-accessible
	      STATUS  current
	      DESCRIPTION "No description available"
	      INDEX   { haClusterIpIndex }
	      ::= { haClusterIpTable 1 }

     HaClusterIpEntry ::=
      	      SEQUENCE {
      	            haClusterIpIndex Unsigned32,
      	            haClusterIpIfName DisplayString,
      	            haClusterIpAddr IpAddress,
      	            haClusterIpNetMask IpAddress,
                    haClusterIpMemberNet IpAddress,
                    haClusterIpMemberNetMask IpAddress
              }

     haClusterIpIndex OBJECT-TYPE
              SYNTAX  Unsigned32
              MAX-ACCESS not-accessible
              STATUS  current
	      DESCRIPTION
	      	"Cluster IP index"
              ::= { haClusterIpEntry 1 }

     haClusterIpIfName OBJECT-TYPE
              SYNTAX  DisplayString
	      MAX-ACCESS read-only
	      STATUS  current
	      DESCRIPTION
	        "Cluster IP interface name"
	      ::= { haClusterIpEntry 2 }


     haClusterIpAddr OBJECT-TYPE
              SYNTAX  IpAddress
              MAX-ACCESS read-only
              STATUS  current
	      DESCRIPTION
	      	"Cluster IP address"
              ::= { haClusterIpEntry 3 }

     haClusterIpNetMask OBJECT-TYPE
              SYNTAX  IpAddress
              MAX-ACCESS read-only
              STATUS  current
	      DESCRIPTION
	      	"Cluster network mask"
              ::= { haClusterIpEntry 4 }

     haClusterIpMemberNet OBJECT-TYPE
              SYNTAX  IpAddress
              MAX-ACCESS read-only
              STATUS  current
	      DESCRIPTION
	      	"Cluster member network"
              ::= { haClusterIpEntry 5 }

     haClusterIpMemberNetMask OBJECT-TYPE
              SYNTAX  IpAddress
              MAX-ACCESS read-only
              STATUS  current
	      DESCRIPTION
	      	"Cluster member network mask"
              ::= { haClusterIpEntry 6 }


     haClusterSyncTable OBJECT-TYPE
	      SYNTAX  SEQUENCE OF HaClusterSyncEntry
	      MAX-ACCESS  not-accessible
	      STATUS  current
	      DESCRIPTION "No description available"
	      ::= { ha 16 }

     haClusterSyncEntry OBJECT-TYPE
	      SYNTAX  HaClusterSyncEntry
	      MAX-ACCESS  not-accessible
	      STATUS  current
	      DESCRIPTION "No description available"
	      INDEX   { haClusterSyncIndex }
	      ::= { haClusterSyncTable 1 }

     HaClusterSyncEntry ::=
      	      SEQUENCE {
      	            haClusterSyncIndex Unsigned32,
		    haClusterSyncName DisplayString,
		    haClusterSyncAddr INTEGER,
		    		haClusterSyncNetMask INTEGER
              }

     haClusterSyncIndex OBJECT-TYPE
              SYNTAX  Unsigned32
              MAX-ACCESS not-accessible
              STATUS  current
	      DESCRIPTION
	      	"Cluster sync index"
              ::= { haClusterSyncEntry 1 }

     haClusterSyncName OBJECT-TYPE
              SYNTAX  DisplayString
	      MAX-ACCESS read-only
	      STATUS  current
	      DESCRIPTION
	        "Cluster sync name"
	      ::= { haClusterSyncEntry 2 }


     haClusterSyncAddr OBJECT-TYPE
              SYNTAX  Integer32
              MAX-ACCESS read-only
              STATUS  current
	      DESCRIPTION
	      	"Cluster sync address"
              ::= { haClusterSyncEntry 3 }

     haClusterSyncNetMask OBJECT-TYPE
              SYNTAX  Integer32
              MAX-ACCESS read-only
              STATUS  current
	      DESCRIPTION
	      	"Cluster sync network mask"
              ::= { haClusterSyncEntry 4 }

	  -- the SVN status
	  -- Overall statistics and state

      svnInfo        OBJECT IDENTIFIER ::= { svn 4 }
	  svnOSInfo      OBJECT IDENTIFIER ::= { svn 5 }
	  svnPerf        OBJECT IDENTIFIER ::= { svn 7 }
	  svnApplianceInfo	        OBJECT IDENTIFIER ::= { svn 16 }
	  svnMem         OBJECT IDENTIFIER ::= { svnPerf 1 }
	  svnProc        OBJECT IDENTIFIER ::= { svnPerf 2 }
	  svnDisk        OBJECT IDENTIFIER ::= { svnPerf 3 }
	  svnMem64       OBJECT IDENTIFIER ::= { svnPerf 4 }
	  svnRoutingModify OBJECT IDENTIFIER ::= { svn 9 }
          svnLogDaemon	 OBJECT IDENTIFIER ::= { svn 11 }

	  svnUpdatesInfo OBJECT IDENTIFIER ::= { svn 20 }
	  svnVsxInfo OBJECT IDENTIFIER ::= { svn 21 }
	  arpTableInfo OBJECT IDENTIFIER ::= { svn 22 }

     svnProdName OBJECT-TYPE
	  		  SYNTAX  DisplayString (SIZE (0..255))
			  MAX-ACCESS read-only
			  STATUS  current
			  DESCRIPTION
	        	   "Product name"
	        ::= { svn 1 }

     svnProdVerMajor OBJECT-TYPE
	  		  SYNTAX  Gauge32
			  MAX-ACCESS read-only
			  STATUS  current
			  DESCRIPTION
	        	   "Major version"
	        ::= { svn 2 }

	 svnProdVerMinor OBJECT-TYPE
	        SYNTAX  Gauge32
	        MAX-ACCESS read-only
	        STATUS  current
	        DESCRIPTION
	        	   "Minor version"
	        ::= { svn 3 }

	 svnUpdatesInfoBuild OBJECT-TYPE
	  		  SYNTAX  Unsigned32
			  MAX-ACCESS read-only
			  STATUS  current
			  DESCRIPTION
					 "Deployment agent build number"
			  ::= { svnUpdatesInfo 1 }

	 svnUpdatesInfoStatus OBJECT-TYPE
	  		  SYNTAX  DisplayString (SIZE (0..255))
			  MAX-ACCESS read-only
			  STATUS  current
			  DESCRIPTION
					 "Deployment agent status"
			  ::= { svnUpdatesInfo 2 }

	 svnUpdatesInfoConnection OBJECT-TYPE
	  		  SYNTAX  DisplayString (SIZE (0..255))
			  MAX-ACCESS read-only
			  STATUS  current
			  DESCRIPTION
					 "Cloud connection"
			  ::= { svnUpdatesInfo 3 }

	 svnUpdatesInfoAvailablePackages OBJECT-TYPE
	  		  SYNTAX  Unsigned32
			  MAX-ACCESS read-only
			  STATUS  current
			  DESCRIPTION
					 "Available packages count"
			  ::= { svnUpdatesInfo 4 }

	 svnUpdatesInfoAvailableRecommended OBJECT-TYPE
	  		  SYNTAX  Unsigned32
			  MAX-ACCESS read-only
			  STATUS  current
			  DESCRIPTION
					 "Available recommended packages count"
			  ::= { svnUpdatesInfo 5 }

	 svnUpdatesInfoAvailableHotfixes OBJECT-TYPE
	  		  SYNTAX  Unsigned32
			  MAX-ACCESS read-only
			  STATUS  current
			  DESCRIPTION
					 "Available hotfixes count"
			  ::= { svnUpdatesInfo 6 }


	   updatesInstalledTable OBJECT-TYPE
	          SYNTAX  SEQUENCE OF  UpdatesInstalledEntry
			  MAX-ACCESS  not-accessible
			  STATUS  current
  			  DESCRIPTION "Installed updates table. This feature is supported only on gaia"
			  ::= { svnUpdatesInfo 7 }

	  updatesInstalledEntry OBJECT-TYPE
	          SYNTAX UpdatesInstalledEntry
			  MAX-ACCESS  not-accessible
			  STATUS  current
			  DESCRIPTION "No description available"
			  INDEX   { updatesInstalledIndex }
			  ::= { updatesInstalledTable 1 }

	  UpdatesInstalledEntry ::=
	          SEQUENCE {
				updatesInstalledIndex
				      Unsigned32,
				updatesInstalledName
				      DisplayString,
				updatesInstalledType
					  DisplayString
			  }

	  updatesInstalledIndex OBJECT-TYPE
	  		 SYNTAX  Unsigned32
			 MAX-ACCESS not-accessible
			 STATUS  current
			 DESCRIPTION "No description available"
    	     ::= { updatesInstalledEntry 1 }

	  updatesInstalledName OBJECT-TYPE
	  		 SYNTAX  DisplayString (SIZE (0..255))
			 MAX-ACCESS read-only
			 STATUS  current
			 DESCRIPTION
	       	   "Installed package name"
	       ::= { updatesInstalledEntry 2 }

	  updatesInstalledType OBJECT-TYPE
	  		 SYNTAX  DisplayString (SIZE (0..255))
			 MAX-ACCESS read-only
			 STATUS  current
			 DESCRIPTION
	       	   "Installed package type"
	       ::= { updatesInstalledEntry 3 }

	updatesRecommendedTable OBJECT-TYPE
	          SYNTAX  SEQUENCE OF  UpdatesRecommendedEntry
			  MAX-ACCESS  not-accessible
			  STATUS  current
  			  DESCRIPTION "Recommended updates table. This feature is supported only on gaia"
			  ::= { svnUpdatesInfo 8 }

	  updatesRecommendedEntry OBJECT-TYPE
	          SYNTAX UpdatesRecommendedEntry
			  MAX-ACCESS  not-accessible
			  STATUS  current
			  DESCRIPTION "No description available"
			  INDEX   { updatesRecommendedIndex }
			  ::= { updatesRecommendedTable 1 }

	  UpdatesRecommendedEntry ::=
	          SEQUENCE {
				updatesRecommendedIndex
				      Unsigned32,
				updatesRecommendedName
				      DisplayString,
				updatesRecommendedType
					  DisplayString,
				updatesRecommendedStatus
					  DisplayString
			  }

	  updatesRecommendedIndex OBJECT-TYPE
	  		 SYNTAX  Unsigned32
			 MAX-ACCESS not-accessible
			 STATUS  current
			 DESCRIPTION "No description available"
    	     ::= { updatesRecommendedEntry 1 }

	  updatesRecommendedName OBJECT-TYPE
	  		 SYNTAX  DisplayString (SIZE (0..255))
			 MAX-ACCESS read-only
			 STATUS  current
			 DESCRIPTION
	       	   "Recommended package name"
	       ::= { updatesRecommendedEntry 2 }

	  updatesRecommendedType OBJECT-TYPE
	  		 SYNTAX  DisplayString (SIZE (0..255))
			 MAX-ACCESS read-only
			 STATUS  current
			 DESCRIPTION
	       	   "Recommended package type"
	       ::= { updatesRecommendedEntry 3 }

	  updatesRecommendedStatus OBJECT-TYPE
	  		 SYNTAX  DisplayString (SIZE (0..255))
			 MAX-ACCESS read-only
			 STATUS  current
			 DESCRIPTION
	       	   "Recommended package status"
	       ::= { updatesRecommendedEntry 4 }


	  svnVersion OBJECT-TYPE
	  		  SYNTAX  DisplayString (SIZE (0..255))
			  MAX-ACCESS read-only
			  STATUS  current
			  DESCRIPTION
					 "SVN version"
			  ::= { svnInfo 1 }

	  svnBuild OBJECT-TYPE
	  		  SYNTAX  Unsigned32
			  MAX-ACCESS read-only
			  STATUS  current
			  DESCRIPTION
					 "SVN build number"
			  ::= { svnInfo 2 }

	  osName OBJECT-TYPE
	  		  SYNTAX  DisplayString (SIZE (0..255))
			  MAX-ACCESS read-only
			  STATUS  current
			  DESCRIPTION
					 "OS name"
			  ::= { svnOSInfo 1 }

	  osMajorVer OBJECT-TYPE
	  		  SYNTAX  Integer32
			  MAX-ACCESS read-only
			  STATUS  current
			  DESCRIPTION
					 "OS Major version"
			  ::= { svnOSInfo 2 }

	  osMinorVer OBJECT-TYPE
	  		  SYNTAX  Integer32
			  MAX-ACCESS read-only
			  STATUS  current
			  DESCRIPTION
					 "OS minor version"
			  ::= { svnOSInfo 3 }

	  osBuildNum OBJECT-TYPE
	  		  SYNTAX  Integer32
			  MAX-ACCESS read-only
			  STATUS  current
			  DESCRIPTION
					 "OS build number"
			  ::= { svnOSInfo 4 }

	  osSPmajor OBJECT-TYPE
	  		  SYNTAX  Integer32
			  MAX-ACCESS read-only
			  STATUS  current
			  DESCRIPTION
					 "OS SP major"
			  ::= { svnOSInfo 5 }

	  osSPminor OBJECT-TYPE
	  		  SYNTAX  Integer32
			  MAX-ACCESS read-only
			  STATUS  current
			  DESCRIPTION
					 "OS SP minor"
			  ::= { svnOSInfo 6 }

	  osVersionLevel OBJECT-TYPE
	  		  SYNTAX  DisplayString (SIZE (0..255))
			  MAX-ACCESS read-only
			  STATUS  current
			  DESCRIPTION
					 "OS version level"
			  ::= { svnOSInfo 7 }

	  svnApplianceSerialNumber OBJECT-TYPE
	  		  SYNTAX DisplayString (SIZE (0..255))
			  MAX-ACCESS read-only
			  STATUS  current
			  DESCRIPTION
					 "Appliance Serial Number"
			  ::= { svnApplianceInfo 3 }

	  svnApplianceManufacturer OBJECT-TYPE
	  		  SYNTAX DisplayString (SIZE (0..255))
			  MAX-ACCESS read-only
			  STATUS  current
			  DESCRIPTION
					 "Appliance Manufacturer"
			  ::= { svnApplianceInfo 9 }

	  svnApplianceProductName OBJECT-TYPE
	  		  SYNTAX  DisplayString (SIZE (0..255))
			  MAX-ACCESS read-only
			  STATUS  current
			  DESCRIPTION
					 "Appliance Product Name"
			  ::= { svnApplianceInfo 7 }

	  svnApplianceSeriesString OBJECT-TYPE
	  		  SYNTAX  DisplayString (SIZE (0..255))
			  MAX-ACCESS read-only
			  STATUS  current
			  DESCRIPTION
					 "Appliance Series String"
			  ::= { svnApplianceInfo 10 }

	  memTotalVirtual OBJECT-TYPE
			  SYNTAX  Unsigned32
			  MAX-ACCESS read-only
			  STATUS  current
			  DESCRIPTION
					 "Total virtual memory (32 bit)
					  NOTE: This 32 bit object has been superseded by a 64 bit object -
					  memTotalVirtual64, which is supported by Check Point SVN FP3 and above. The
					  32 bit object is still supported, but it is recommended to work with the new
					  64 bit object (avoid receiving erroneous values from 64 bit machines)."
			  ::= { svnMem 1 }

	  memActiveVirtual OBJECT-TYPE
			  SYNTAX  Unsigned32
			  MAX-ACCESS read-only
			  STATUS  current
			  DESCRIPTION
					 "Active virtual memory (32 bit)
					  NOTE: This 32 bit object has been superseded by a 64 bit object -
					  memActiveVirtual64, which is supported by Check Point SVN FP3 and above. The
					  32 bit object is still supported, but it is recommended to work with the new
					  64 bit object (avoid receiving erroneous values from 64 bit machines)."
			  ::= { svnMem 2 }

	  memTotalReal OBJECT-TYPE
			  SYNTAX  Unsigned32
			  MAX-ACCESS read-only
			  STATUS  current
			  DESCRIPTION
					 "Total real memory (32 bit)
					  NOTE: This 32 bit object has been superseded by a 64 bit object -
					  memTotalReal64, which is supported by Check Point SVN FP3 and above. The
					  32 bit object is still supported, but it is recommended to work with the new
					  64 bit object (avoid receiving erroneous values from 64 bit machines)."
			  ::= { svnMem 3 }

	  memActiveReal OBJECT-TYPE
			  SYNTAX  Unsigned32
			  MAX-ACCESS read-only
			  STATUS  current
			  DESCRIPTION
					 "Active real memory (32 bit)
					  NOTE: This 32 bit object has been superseded by a 64 bit object -
					  memActiveReal64, which is supported by Check Point SVN FP3 and above. The
					  32 bit object is still supported, but it is recommended to work with the new
					  64 bit object (avoid receiving erroneous values from 64 bit machines)."
			  ::= { svnMem 4 }

	  memFreeReal OBJECT-TYPE
			  SYNTAX  Unsigned32
			  MAX-ACCESS read-only
			  STATUS  current
			  DESCRIPTION
					 "Free real memory (32 bit)
					  NOTE: This 32 bit object has been superseded by a 64 bit object -
					  memFreeReal64, which is supported by Check Point SVN FP3 and above. The
					  32 bit object is still supported, but it is recommended to work with the new
					  64 bit object (avoid receiving erroneous values from 64 bit machines)."
			  ::= { svnMem 5 }

	  memSwapsSec OBJECT-TYPE
			  SYNTAX  Integer32
			  MAX-ACCESS read-only
			  STATUS  current
			  DESCRIPTION
					 "Memory swaped pages/sec (32 bit)
					  NOTE: This 32 bit object has been superseded by a 64 bit object -
					  memSwapsSec64, which is supported by Check Point SVN FP3 and above. The
					  32 bit object is still supported, but it is recommended to work with the new
					  64 bit object (avoid receiving erroneous values from 64 bit machines)."
			  ::= { svnMem 6 }

	  memDiskTransfers OBJECT-TYPE
			  SYNTAX  Integer32
			  MAX-ACCESS read-only
			  STATUS  current
			  DESCRIPTION
					 "Memory to Disk transfers/sec (32 bit)
					  NOTE: This 32 bit object has been superseded by a 64 bit object -
					  memDiskTransfers64, which is supported by Check Point SVN FP3 and above. The
					  32 bit object is still supported, but it is recommended to work with the new
					  64 bit object (avoid receiving erroneous values from 64 bit machines)."
			  ::= { svnMem 7 }

	  procUsrTime OBJECT-TYPE
			  SYNTAX  Unsigned32
			  MAX-ACCESS read-only
			  STATUS  current
			  DESCRIPTION
					 "Processor user time"
			  ::= { svnProc 1 }

	  procSysTime OBJECT-TYPE
			  SYNTAX  Unsigned32
			  MAX-ACCESS read-only
			  STATUS  current
			  DESCRIPTION
					 "Processor system time"
			  ::= { svnProc 2 }

	  procIdleTime OBJECT-TYPE
			  SYNTAX  Unsigned32
			  MAX-ACCESS read-only
			  STATUS  current
			  DESCRIPTION
					 "Processor idle time"
			  ::= { svnProc 3 }

	  procUsage OBJECT-TYPE
			  SYNTAX  Gauge32
			  MAX-ACCESS read-only
			  STATUS  current
			  DESCRIPTION
					 "Processor usage"
			  ::= { svnProc 4 }

	  procQueue OBJECT-TYPE
			  SYNTAX  Integer32
			  MAX-ACCESS read-only
			  STATUS  current
			  DESCRIPTION
					 "Processor queue length"
			  ::= { svnProc 5 }

	  procInterrupts OBJECT-TYPE
			  SYNTAX  Unsigned32
			  MAX-ACCESS read-only
			  STATUS  current
			  DESCRIPTION
					 "Processor interrupts/sec"
			  ::= { svnProc 6 }

	  procNum OBJECT-TYPE
			  SYNTAX  Unsigned32
			  MAX-ACCESS read-only
			  STATUS  current
			  DESCRIPTION
					 "Number of processors"
			  ::= { svnProc 7 }

	  diskTime OBJECT-TYPE
              SYNTAX  Integer32
			  MAX-ACCESS read-only
			  STATUS  current
			  DESCRIPTION
					 "Time the disk is performing io requests"
			  ::= { svnDisk 1 }

	  diskQueue OBJECT-TYPE
              SYNTAX  Integer32
			  MAX-ACCESS read-only
			  STATUS  current
			  DESCRIPTION
					 "Disk requests queue length"
			  ::= { svnDisk 2 }

	  diskPercent OBJECT-TYPE
              SYNTAX  Gauge32
			  MAX-ACCESS read-only
			  STATUS  current
			  DESCRIPTION
					 "Percent of free space"
			  ::= { svnDisk 3 }

	  diskFreeTotal OBJECT-TYPE
              SYNTAX  Counter64
			  MAX-ACCESS read-only
			  STATUS  current
			  DESCRIPTION
					 "Disk total free space"
			  ::= { svnDisk 4 }

	  diskFreeAvail OBJECT-TYPE
              SYNTAX  Counter64
			  MAX-ACCESS read-only
			  STATUS  current
			  DESCRIPTION
					 "Disk available free space"
			  ::= { svnDisk 5 }

	  diskTotal OBJECT-TYPE
              SYNTAX  Counter64
			  MAX-ACCESS read-only
			  STATUS  current
			  DESCRIPTION
					 "Disk total space"
			  ::= { svnDisk 6 }

	  memTotalVirtual64 OBJECT-TYPE
			  SYNTAX  Counter64
			  MAX-ACCESS read-only
			  STATUS  current
			  DESCRIPTION
					 "Total virtual memory"
			  ::= { svnMem64 1 }

	  memActiveVirtual64 OBJECT-TYPE
			  SYNTAX  Counter64
			  MAX-ACCESS read-only
			  STATUS  current
			  DESCRIPTION
					 "Active virtual memory"
			  ::= { svnMem64 2 }

	  memTotalReal64 OBJECT-TYPE
			  SYNTAX  Counter64
			  MAX-ACCESS read-only
			  STATUS  current
			  DESCRIPTION
					 "Total real memory"
			  ::= { svnMem64 3 }

	  memActiveReal64 OBJECT-TYPE
			  SYNTAX  Counter64
			  MAX-ACCESS read-only
			  STATUS  current
			  DESCRIPTION
					 "Active real memory"
			  ::= { svnMem64 4 }

	  memFreeReal64 OBJECT-TYPE
			  SYNTAX  Counter64
			  MAX-ACCESS read-only
			  STATUS  current
			  DESCRIPTION
					 "Free real memory"
			  ::= { svnMem64 5 }

	  memSwapsSec64 OBJECT-TYPE
			  SYNTAX  Integer32
			  MAX-ACCESS read-only
			  STATUS  current
			  DESCRIPTION
					 "Memory swaped pages/sec"
			  ::= { svnMem64 6 }

	  memDiskTransfers64 OBJECT-TYPE
			  SYNTAX  Integer32
			  MAX-ACCESS read-only
			  STATUS  current
			  DESCRIPTION
					 "Memory to Disk transfers/sec"
			  ::= { svnMem64 7 }

	  multiProcTable OBJECT-TYPE
			  SYNTAX  SEQUENCE OF  MultiProcEntry
			  MAX-ACCESS  not-accessible
			  STATUS  current
			  DESCRIPTION "No description available"
			  ::= { svnPerf 5 }

	  vdName OBJECT-TYPE
	  		  SYNTAX  DisplayString (SIZE (0..255))
			  MAX-ACCESS read-only
			  STATUS  current
			  DESCRIPTION
					 "Virtual-Device name"
			  ::= { svnVsxInfo 1 }

	  vdType OBJECT-TYPE
	  		  SYNTAX  DisplayString (SIZE (0..255))
			  MAX-ACCESS read-only
			  STATUS  current
			  DESCRIPTION
					 "Virtual-Device type"
			  ::= { svnVsxInfo 2 }

	  ctxId OBJECT-TYPE
	  		  SYNTAX  Integer32
			  MAX-ACCESS read-only
			  STATUS  current
			  DESCRIPTION
					 "Virtual-Device Context ID"
			  ::= { svnVsxInfo 3 }

	  multiProcEntry OBJECT-TYPE
			  SYNTAX MultiProcEntry
			  MAX-ACCESS  not-accessible
			  STATUS  current
			  DESCRIPTION "No description available"
			  INDEX   { multiProcIndex }
			  ::= { multiProcTable 1 }

	  MultiProcEntry ::=
			  SEQUENCE {
				multiProcIndex		Unsigned32,
				multiProcUserTime	Unsigned32,
				multiProcSystemTime	Unsigned32,
				multiProcIdleTime	Unsigned32,
				multiProcUsage		Unsigned32,
				multiProcRunQueue	INTEGER,
				multiProcInterrupts	Unsigned32
			  }

	  multiProcIndex OBJECT-TYPE
			  SYNTAX  Unsigned32
			  MAX-ACCESS not-accessible
			  STATUS  current
			  DESCRIPTION "No description available"
			  ::= { multiProcEntry 1 }

	  multiProcUserTime OBJECT-TYPE
			  SYNTAX  Unsigned32
			  MAX-ACCESS read-only
			  STATUS  current
			  DESCRIPTION "No description available"
			  ::= { multiProcEntry 2 }

	  multiProcSystemTime OBJECT-TYPE
			  SYNTAX  Unsigned32
			  MAX-ACCESS read-only
			  STATUS  current
			  DESCRIPTION "No description available"
			  ::= { multiProcEntry 3 }

	  multiProcIdleTime OBJECT-TYPE
			  SYNTAX  Unsigned32
			  MAX-ACCESS read-only
			  STATUS  current
			  DESCRIPTION "No description available"
			  ::= { multiProcEntry 4 }

	  multiProcUsage OBJECT-TYPE
			  SYNTAX  Unsigned32
			  MAX-ACCESS read-only
			  STATUS  current
			  DESCRIPTION "No description available"
			  ::= { multiProcEntry 5 }

	  multiProcRunQueue OBJECT-TYPE
			  SYNTAX  Integer32
			  MAX-ACCESS read-only
			  STATUS  current
			  DESCRIPTION "No description available"
			  ::= { multiProcEntry 6 }

	  multiProcInterrupts OBJECT-TYPE
			  SYNTAX  Unsigned32
			  MAX-ACCESS read-only
			  STATUS  current
			  DESCRIPTION "No description available"
			  ::= { multiProcEntry 7 }

	  multiDiskTable OBJECT-TYPE
			  SYNTAX  SEQUENCE OF  MultiDiskEntry
			  MAX-ACCESS  not-accessible
			  STATUS  current
			  DESCRIPTION "No description available"
			  ::= { svnPerf 6 }

	  multiDiskEntry OBJECT-TYPE
			  SYNTAX MultiDiskEntry
			  MAX-ACCESS  not-accessible
			  STATUS  current
			  DESCRIPTION "No description available"
			  INDEX   { multiDiskIndex }
			  ::= { multiDiskTable 1 }

	  MultiDiskEntry ::=
			  SEQUENCE {
				multiDiskIndex		Unsigned32,
				multiDiskName		DisplayString,
				multiDiskSize		Counter64,
				multiDiskUsed		Counter64,
				multiDiskFreeTotalBytes			Counter64,
				multiDiskFreeTotalPercent		Gauge32,
				multiDiskFreeAvailableBytes		Counter64,
				multiDiskFreeAvailablePercent	Gauge32
			  }

	  multiDiskIndex OBJECT-TYPE
			  SYNTAX  Unsigned32
			  MAX-ACCESS not-accessible
			  STATUS  current
			  DESCRIPTION "No description available"
			  ::= { multiDiskEntry 1 }

	  multiDiskName OBJECT-TYPE
			  SYNTAX  DisplayString
			  MAX-ACCESS read-only
			  STATUS  current
			  DESCRIPTION "No description available"
			  ::= { multiDiskEntry 2 }

	  multiDiskSize OBJECT-TYPE
			  SYNTAX  Counter64
			  MAX-ACCESS read-only
			  STATUS  current
			  DESCRIPTION "No description available"
			  ::= { multiDiskEntry 3 }

	  multiDiskUsed OBJECT-TYPE
			  SYNTAX  Counter64
			  MAX-ACCESS read-only
			  STATUS  current
			  DESCRIPTION "No description available"
			  ::= { multiDiskEntry 4 }

	  multiDiskFreeTotalBytes OBJECT-TYPE
			  SYNTAX  Counter64
			  MAX-ACCESS read-only
			  STATUS  current
			  DESCRIPTION "No description available"
			  ::= { multiDiskEntry 5 }

	  multiDiskFreeTotalPercent OBJECT-TYPE
			  SYNTAX  Gauge32
			  MAX-ACCESS read-only
			  STATUS  current
			  DESCRIPTION "No description available"
			  ::= { multiDiskEntry 6 }

	  multiDiskFreeAvailableBytes OBJECT-TYPE
			  SYNTAX  Counter64
			  MAX-ACCESS read-only
			  STATUS  current
			  DESCRIPTION "No description available"
			  ::= { multiDiskEntry 7 }

	  multiDiskFreeAvailablePercent OBJECT-TYPE
			  SYNTAX  Gauge32
			  MAX-ACCESS read-only
			  STATUS  current
			  DESCRIPTION "No description available"
			  ::= { multiDiskEntry 8 }

	  raidInfo       OBJECT IDENTIFIER ::= { svnPerf 7 }
	  sensorInfo       OBJECT IDENTIFIER ::= { svnPerf 8 }
	  powerSupplyInfo       OBJECT IDENTIFIER ::= { svnPerf 9 }

	  raidVolumeTable OBJECT-TYPE
	          SYNTAX  SEQUENCE OF  RaidVolumeEntry
			  MAX-ACCESS  not-accessible
			  STATUS  current
			  DESCRIPTION "No description available"
			  ::= { raidInfo 1 }

	  raidVolumeEntry OBJECT-TYPE
	          SYNTAX RaidVolumeEntry
			  MAX-ACCESS  not-accessible
			  STATUS  current
			  DESCRIPTION "No description available"
			  INDEX   { raidVolumeIndex }
			  ::= { raidVolumeTable 1 }

	  RaidVolumeEntry ::=
	          SEQUENCE {
	            raidVolumeIndex
	                  INTEGER,
	          	raidVolumeID
	          		  INTEGER,
	          	raidVolumeType
	          		  INTEGER,
				numOfDisksOnRaid
				      INTEGER,
				raidVolumeMaxLBA
				      INTEGER,
				raidVolumeState
					  INTEGER,
				raidVolumeFlags
				      INTEGER,
				raidVolumeSize
				      Unsigned32
			  }

	 raidVolumeIndex OBJECT-TYPE
	  		  SYNTAX  Integer32 (0..100)
			  MAX-ACCESS not-accessible
			  STATUS  current
			  DESCRIPTION "No description available"
	        ::= { raidVolumeEntry 1 }


	  raidVolumeID OBJECT-TYPE
	  		  SYNTAX  Integer32
			  MAX-ACCESS read-only
			  STATUS  current
			  DESCRIPTION
	        	   "Raid volume identification number"
	        ::= { raidVolumeEntry 2 }

	  raidVolumeType OBJECT-TYPE
	  		 SYNTAX  Integer32
			 MAX-ACCESS read-only
			 STATUS  current
			 DESCRIPTION
	       	   "Raid volume type, RAID-0, RAID-1E, RAID-1, RAID_10, RAID-4, RAID-5, RAID-6, RAID-60, RAID-50 (value 0-8 respectively)"
	       ::= { raidVolumeEntry 3 }

	 numOfDisksOnRaid OBJECT-TYPE
	  		 SYNTAX  Integer32
			 MAX-ACCESS read-only
			 STATUS  current
			 DESCRIPTION
	       	   "Number of disks on the raid"
	       ::= { raidVolumeEntry 4 }

     raidVolumeMaxLBA OBJECT-TYPE
	  		 SYNTAX  Integer32
			 MAX-ACCESS read-only
			 STATUS  current
			 DESCRIPTION
	       	   "Raid maximum number of Logical Block Addressing"
	       ::= { raidVolumeEntry 5 }

	  raidVolumeState OBJECT-TYPE
	  		 SYNTAX  Integer32
			 MAX-ACCESS read-only
			 STATUS  current
			 DESCRIPTION
	       	   "Raid state: OPTIMAL(0), DEGRADED (1), FAILED(2) or UNKNOWN(other))"
	       ::= { raidVolumeEntry 6 }

	  raidVolumeFlags OBJECT-TYPE
	  		 SYNTAX  Integer32
			 MAX-ACCESS read-only
			 STATUS  current
			 DESCRIPTION
	       	   "Raid status flags (can get more then one): ENABLED(0x01), QUIESCED(0x02), RESYNC_IN_PROGRESS(0x04),
                    VOLUME_INACTIVE(0x08), NOT_CONFIGURED(0x10), USING_INTERIM_RECOVERY_MODE(0x20),
		    READY_FOR_RECOVERY_OPERATION(0x40), WRONG_PHYSICAL_DRIVE_WAS_REPLACED(0x80),
		    A_PHYSICAL_DRIVE_IS_NOT_PROPERLY_CONNECTED(0x100), HARDWARE_IS_OVER_HEATING(0x200),
		    HARDWARE_WAS_OVERHEATED(0x400), CURRENTLY_EXPENDING(0x800), NOT_YET_AVAILABLE(0x1000),
		    QUEUED_FOR_EXPENSION(0x2000), MIGRATING(0x4000), IMPACTED(0x8000),OFFLINE(0x10000) and CLEARING(0x20000) or NONE(0x00)"
	       ::= { raidVolumeEntry 7 }

	  raidVolumeSize OBJECT-TYPE
	  		 SYNTAX  Unsigned32
			 MAX-ACCESS read-only
			 STATUS  current
			 DESCRIPTION
	       	   "Raid Volume Size (GB)"
	       ::= { raidVolumeEntry 8 }

	  raidDiskTable OBJECT-TYPE
	          SYNTAX  SEQUENCE OF  RaidDiskEntry
			  MAX-ACCESS  not-accessible
			  STATUS  current
			  DESCRIPTION "No description available"
			  ::= { raidInfo 2 }

	  raidDiskEntry OBJECT-TYPE
	          SYNTAX RaidDiskEntry
			  MAX-ACCESS  not-accessible
			  STATUS  current
			  DESCRIPTION "No description available"
			  INDEX   { raidDiskIndex }
			  ::= { raidDiskTable 1 }

	  RaidDiskEntry ::=
	          SEQUENCE {
	          	raidDiskIndex
	          		  INTEGER,
	          	raidDiskVolumeID
	          		  INTEGER,
				raidDiskID
				      INTEGER,
				raidDiskNumber
				      INTEGER,
				raidDiskVendor
					  DisplayString,
				raidDiskProductID
				      DisplayString,
				raidDiskRevision
				      DisplayString,
				raidDiskMaxLBA
				      INTEGER,
			    raidDiskState
				      INTEGER,
				raidDiskFlags
				      INTEGER,
				raidDiskSyncState
				      INTEGER,
				raidDiskSize
				      Unsigned32
			  }

	  raidDiskIndex OBJECT-TYPE
	  		 SYNTAX  Integer32 (0..100)
			 MAX-ACCESS not-accessible
			 STATUS  current
			 DESCRIPTION "No description available"
	       ::= { raidDiskEntry 1 }

	  raidDiskVolumeID OBJECT-TYPE
	  		 SYNTAX  Integer32
			 MAX-ACCESS read-only
			 STATUS  current
			 DESCRIPTION
	       	   "Raid volume identification"
	       ::= { raidDiskEntry 2 }

	  raidDiskID OBJECT-TYPE
	  		 SYNTAX  Integer32
			 MAX-ACCESS read-only
			 STATUS  current
			 DESCRIPTION
	       	   "Raid disk SCSI identification number"
	       ::= { raidDiskEntry 3 }

	  raidDiskNumber OBJECT-TYPE
	  		 SYNTAX  Integer32
			 MAX-ACCESS read-only
			 STATUS  current
			 DESCRIPTION
	       	   "Raid disk number: on Appliance 0 - upper disc, 1 - lower disc"
	       ::= { raidDiskEntry 4 }

	  raidDiskVendor OBJECT-TYPE
	  		 SYNTAX  DisplayString (SIZE (0..255))
			 MAX-ACCESS read-only
			 STATUS  current
			 DESCRIPTION
	       	   "Raid disk vendor"
	       ::= { raidDiskEntry 5 }

	  raidDiskProductID OBJECT-TYPE
	  		 SYNTAX  DisplayString (SIZE (0..255))
			 MAX-ACCESS read-only
			 STATUS  current
			 DESCRIPTION
	       	   "Raid disk product identification"
	       ::= { raidDiskEntry 6 }

      raidDiskRevision OBJECT-TYPE
	  		 SYNTAX  DisplayString (SIZE (0..255))
			 MAX-ACCESS read-only
			 STATUS  current
			 DESCRIPTION
	       	   "Raid disk revision level"
	       ::= { raidDiskEntry 7 }

	  raidDiskMaxLBA OBJECT-TYPE
	  		 SYNTAX  Integer32
			 MAX-ACCESS read-only
			 STATUS  current
			 DESCRIPTION
	       	   "Raid disk maximum number of Logical Block Addressing"
	       ::= { raidDiskEntry 8 }

	  raidDiskState OBJECT-TYPE
	  		 SYNTAX  Integer32
			 MAX-ACCESS read-only
			 STATUS  current
			 DESCRIPTION
	       	   "Raid disk state (can get more then one): ONLINE(0x00), MISSING(0x01), NOT_COMPATIBLE(0x02), DISC_FAILED(0x03),
				INITIALIZING(0x04), OFFLINE_REQUESTED(0x05), FAILED_REQUESTED(0x06), UNCONFIGURED_GOOD_SPUN_UP(0x07), UNCONFIGURED_GOOD_SPUN_DOWN (0x08),
				UNCONFIGURED_BAD(0x09), HOTSPARE(0x0A), DRIVE_OFFLINE(0x0B), REBUILD(0x0C), FAILED(0x0D), COPYBACK(0x0F),
                OTHER_OFFLINE(0xFF) or UNKNOWN (other)"
	       ::= { raidDiskEntry 9 }

	  raidDiskFlags OBJECT-TYPE
	  		 SYNTAX  Integer32
			 MAX-ACCESS read-only
			 STATUS  current
			 DESCRIPTION
	       	   "Raid disk flags: OUT_OF_SYNC(0x01),QUIESCED(0x02),VERIFYING(0x04),READY(0x08) or NONE(other)"
	       ::= { raidDiskEntry 10 }

	 raidDiskSyncState OBJECT-TYPE
	  		 SYNTAX  Integer32
			 MAX-ACCESS read-only
			 STATUS  current
			 DESCRIPTION
	       	   "Raid disk synchronized percent completed during the synchronization process, relevant only when
                RESYNC_IN_PROGRESS flag is on"
	       ::= { raidDiskEntry 11 }

	  raidDiskSize OBJECT-TYPE
	  		 SYNTAX  Unsigned32
			 MAX-ACCESS read-only
			 STATUS  current
			 DESCRIPTION
	       	   "Raid disk size (GB)"
	       ::= { raidDiskEntry 12 }

	       tempertureSensorTable OBJECT-TYPE
	          SYNTAX  SEQUENCE OF  TempertureSensorEntry
			  MAX-ACCESS  not-accessible
			  STATUS  current
  			  DESCRIPTION "No description available"
			  ::= { sensorInfo 1 }

	  tempertureSensorEntry OBJECT-TYPE
	          SYNTAX TempertureSensorEntry
			  MAX-ACCESS  not-accessible
			  STATUS  current
			  DESCRIPTION "No description available"
			  INDEX   { tempertureSensorIndex }
			  ::= { tempertureSensorTable 1 }

	  TempertureSensorEntry ::=
	          SEQUENCE {
				tempertureSensorIndex
				      INTEGER,
				tempertureSensorName
				      DisplayString,
				tempertureSensorValue
					  DisplayString,
				tempertureSensorUnit
				      DisplayString,
				tempertureSensorType
				      DisplayString,
				tempertureSensorStatus
				      INTEGER
			  }

	  tempertureSensorIndex OBJECT-TYPE
	  		 SYNTAX  Integer32 (0..100)
			 MAX-ACCESS not-accessible
			 STATUS  current
			 DESCRIPTION "No description available"
    	     ::= { tempertureSensorEntry 1 }

	  tempertureSensorName OBJECT-TYPE
	  		 SYNTAX  DisplayString (SIZE (0..255))
			 MAX-ACCESS read-only
			 STATUS  current
			 DESCRIPTION
	       	   "Sensor name"
	       ::= { tempertureSensorEntry 2 }

	  tempertureSensorValue OBJECT-TYPE
	  		 SYNTAX  DisplayString (SIZE (0..255))
			 MAX-ACCESS read-only
			 STATUS  current
			 DESCRIPTION
	       	   "Sensor value"
	       ::= { tempertureSensorEntry 3 }

	  tempertureSensorUnit OBJECT-TYPE
	  		 SYNTAX  DisplayString (SIZE (0..255))
			 MAX-ACCESS read-only
			 STATUS  current
			 DESCRIPTION
	       	   "Sensor unit"
	       ::= { tempertureSensorEntry 4 }

	  tempertureSensorType OBJECT-TYPE
	  		 SYNTAX  DisplayString (SIZE (0..255))
			 MAX-ACCESS read-only
			 STATUS  current
			 DESCRIPTION
	       	   "Sensor type"
	       ::= { tempertureSensorEntry 5 }

	  tempertureSensorStatus OBJECT-TYPE
	  		 SYNTAX  Integer32
	  		 MAX-ACCESS read-only
			 STATUS  current
			 DESCRIPTION
	       	   "Sensor is out of range TRUE(1), FALSE(0), READING ERROR(2)"
	       ::= { tempertureSensorEntry 6 }

	  fanSpeedSensorTable OBJECT-TYPE
	          SYNTAX  SEQUENCE OF  FanSpeedSensorEntry
			  MAX-ACCESS  not-accessible
			  STATUS  current
			  DESCRIPTION "No description available"
			  ::= { sensorInfo 2 }

	  fanSpeedSensorEntry OBJECT-TYPE
	          SYNTAX FanSpeedSensorEntry
			  MAX-ACCESS  not-accessible
			  STATUS  current
			  DESCRIPTION "No description available"
			  INDEX   { fanSpeedSensorIndex }
			  ::= { fanSpeedSensorTable 1 }

	  FanSpeedSensorEntry ::=
	          SEQUENCE {
				fanSpeedSensorIndex
				      INTEGER,
				fanSpeedSensorName
				      DisplayString,
				fanSpeedSensorValue
					  DisplayString,
				fanSpeedSensorUnit
				      DisplayString,
				fanSpeedSensorType
				      DisplayString,
				fanSpeedSensorStatus
				      INTEGER
			  }

	  fanSpeedSensorIndex OBJECT-TYPE
	  		 SYNTAX  Integer32 (0..100)
			 MAX-ACCESS not-accessible
			 STATUS  current
			 DESCRIPTION "No description available"
    	     ::= { fanSpeedSensorEntry 1 }

	  fanSpeedSensorName OBJECT-TYPE
	  		 SYNTAX  DisplayString (SIZE (0..255))
			 MAX-ACCESS read-only
			 STATUS  current
			 DESCRIPTION
	       	   "Sensor name"
	       ::= { fanSpeedSensorEntry 2 }

	  fanSpeedSensorValue OBJECT-TYPE
	  		 SYNTAX  DisplayString (SIZE (0..255))
			 MAX-ACCESS read-only
			 STATUS  current
			 DESCRIPTION
	       	   "Sensor value"
	       ::= { fanSpeedSensorEntry 3 }

	  fanSpeedSensorUnit OBJECT-TYPE
	  		 SYNTAX  DisplayString (SIZE (0..255))
			 MAX-ACCESS read-only
			 STATUS  current
			 DESCRIPTION
	       	   "Sensor unit"
	       ::= { fanSpeedSensorEntry 4 }

	  fanSpeedSensorType OBJECT-TYPE
	  		 SYNTAX  DisplayString (SIZE (0..255))
			 MAX-ACCESS read-only
			 STATUS  current
			 DESCRIPTION
	       	   "Sensor type"
	       ::= { fanSpeedSensorEntry 5 }

	  fanSpeedSensorStatus OBJECT-TYPE
	  		 SYNTAX  Integer32
	  		 MAX-ACCESS read-only
			 STATUS  current
			 DESCRIPTION
	       	   "Sensor is out of range TRUE(1), FALSE(0), READING ERROR(2)"
	       ::= { fanSpeedSensorEntry 6 }

	  voltageSensorTable OBJECT-TYPE
	          SYNTAX  SEQUENCE OF  VoltageSensorEntry
			  MAX-ACCESS  not-accessible
			  STATUS  current
			  DESCRIPTION "No description available"
			  ::= { sensorInfo 3 }

	  voltageSensorEntry OBJECT-TYPE
	          SYNTAX VoltageSensorEntry
			  MAX-ACCESS  not-accessible
			  STATUS  current
			  DESCRIPTION "No description available"
			  INDEX   { voltageSensorIndex }
			  ::= { voltageSensorTable 1 }

	  VoltageSensorEntry ::=
	          SEQUENCE {
				voltageSensorIndex
				      INTEGER,
				voltageSensorName
				      DisplayString,
				voltageSensorValue
					  DisplayString,
				voltageSensorUnit
				      DisplayString,
				voltageSensorType
				      DisplayString,
				voltageSensorStatus
				      INTEGER
			  }

	  voltageSensorIndex OBJECT-TYPE
	  		 SYNTAX  Integer32 (0..100)
			 MAX-ACCESS not-accessible
			 STATUS  current
			 DESCRIPTION "No description available"
    	     ::= { voltageSensorEntry 1 }

	  voltageSensorName OBJECT-TYPE
	  		 SYNTAX  DisplayString (SIZE (0..255))
			 MAX-ACCESS read-only
			 STATUS  current
			 DESCRIPTION
	       	   "Sensor name"
	       ::= { voltageSensorEntry 2 }

	  voltageSensorValue OBJECT-TYPE
	  		 SYNTAX  DisplayString (SIZE (0..255))
			 MAX-ACCESS read-only
			 STATUS  current
			 DESCRIPTION
	       	   "Sensor value"
	       ::= { voltageSensorEntry 3 }

	  voltageSensorUnit OBJECT-TYPE
	  		 SYNTAX  DisplayString (SIZE (0..255))
			 MAX-ACCESS read-only
			 STATUS  current
			 DESCRIPTION
	       	   "Sensor unit"
	       ::= { voltageSensorEntry 4 }

	  voltageSensorType OBJECT-TYPE
	  		 SYNTAX  DisplayString (SIZE (0..255))
			 MAX-ACCESS read-only
			 STATUS  current
			 DESCRIPTION
	       	   "Sensor type"
	       ::= { voltageSensorEntry 5 }

	  voltageSensorStatus OBJECT-TYPE
	  		 SYNTAX  Integer32
	  		 MAX-ACCESS read-only
			 STATUS  current
			 DESCRIPTION
	       	   "Sensor is out of range TRUE(1), FALSE(0), READING ERROR(2)"
	       ::= { voltageSensorEntry 6 }

	  powerSupplyTable OBJECT-TYPE
	          SYNTAX  SEQUENCE OF  PowerSupplyEntry
			  MAX-ACCESS  not-accessible
			  STATUS  current
			  DESCRIPTION "No description available"
			  ::= { powerSupplyInfo 1 }

	  powerSupplyEntry OBJECT-TYPE
	          SYNTAX PowerSupplyEntry
			  MAX-ACCESS  not-accessible
			  STATUS  current
			  DESCRIPTION "No description available"
			  INDEX   { powerSupplyIndex }
			  ::= { powerSupplyTable 1 }

	  PowerSupplyEntry ::=
	          SEQUENCE {
				powerSupplyIndex
				      INTEGER,
				powerSupplyStatus
				      DisplayString
			  }

	  powerSupplyIndex OBJECT-TYPE
	  		 SYNTAX  Integer32 (0..100)
			 MAX-ACCESS not-accessible
			 STATUS  current
			 DESCRIPTION "No description available"
    	     ::= { powerSupplyEntry 1 }

	  powerSupplyStatus OBJECT-TYPE
	  		 SYNTAX  DisplayString
			 MAX-ACCESS read-only
			 STATUS  current
			 DESCRIPTION
	       	   "Power supply status"
	       ::= { powerSupplyEntry 2 }

	  routingTable OBJECT-TYPE
	          SYNTAX  SEQUENCE OF  RoutingEntry
			  MAX-ACCESS  not-accessible
			  STATUS  current
			  DESCRIPTION "No description available"
			  ::= { svn 6 }

	  routingEntry OBJECT-TYPE
	          SYNTAX RoutingEntry
			  MAX-ACCESS  not-accessible
			  STATUS  current
			  DESCRIPTION "No description available"
			  INDEX   { routingIndex }
			  ::= { routingTable 1 }

	  RoutingEntry ::=
	          SEQUENCE {
				routingIndex
				     Unsigned32,
				routingDest
				      IpAddress,
				routingMask
					  IpAddress,
				routingGatweway
				      IpAddress,
				routingIntrfName
				      DisplayString
			  }

      routingIndex OBJECT-TYPE
              SYNTAX  Unsigned32
              MAX-ACCESS not-accessible
              STATUS  current
              DESCRIPTION "No description available"
              ::= { routingEntry 1 }

      routingDest OBJECT-TYPE
      		  SYNTAX  IpAddress
              MAX-ACCESS read-only
              STATUS  current
              DESCRIPTION "No description available"
              ::= { routingEntry 2 }

      routingMask OBJECT-TYPE
      		  SYNTAX  IpAddress
              MAX-ACCESS read-only
              STATUS  current
              DESCRIPTION "No description available"
              ::= { routingEntry 3 }

      routingGatweway OBJECT-TYPE
      		  SYNTAX  IpAddress
              MAX-ACCESS read-only
              STATUS  current
              DESCRIPTION "No description available"
              ::= { routingEntry 4 }

      routingIntrfName OBJECT-TYPE
      		  SYNTAX  DisplayString
              MAX-ACCESS read-only
              STATUS  current
              DESCRIPTION "No description available"
              ::= { routingEntry 5 }

      svnSysTime OBJECT-TYPE
      		  SYNTAX  Unsigned32
      		  MAX-ACCESS read-only
      		  STATUS  current
	          DESCRIPTION
	        	   "System time"
      		  ::= { svn 8 }

      svnRouteModDest OBJECT-TYPE
      		  SYNTAX  IpAddress
		  MAX-ACCESS read-only
		  STATUS  current
		  DESCRIPTION
		  	   "Destination routing modification"
		  ::= { svnRoutingModify 2 }

      svnRouteModMask OBJECT-TYPE
      		  SYNTAX  IpAddress
		  MAX-ACCESS read-only
		  STATUS  current
		  DESCRIPTION
		  	   "Subnet mask routing modification"
		  ::= { svnRoutingModify 3 }

      svnRouteModGateway OBJECT-TYPE
      		  SYNTAX  IpAddress
		  MAX-ACCESS read-only
		  STATUS  current
		  DESCRIPTION
		  	   "Gateway routing modification"
		  ::= { svnRoutingModify 4 }

      svnRouteModIfIndex OBJECT-TYPE
      		  SYNTAX  Integer32
		  MAX-ACCESS read-only
		  STATUS  current
		  DESCRIPTION
		  	   "Interface index routing modification"
		  ::= { svnRoutingModify 5 }

      svnRouteModIfName OBJECT-TYPE
      		  SYNTAX  DisplayString (SIZE (0..255))
		  MAX-ACCESS read-only
		  STATUS  current
		  DESCRIPTION
		  	   "Interface name routing modification"
		  ::= { svnRoutingModify 6 }

      svnRouteModAction OBJECT-TYPE
      		  SYNTAX  Integer32
		  MAX-ACCESS read-only
		  STATUS  current
		  DESCRIPTION
		  	   "Routing modification action"
		  ::= { svnRoutingModify 10 }

      svnUTCTimeOffset OBJECT-TYPE
      		  SYNTAX  Integer32
		  MAX-ACCESS read-only
		  STATUS  current
		  DESCRIPTION
		  	   "UTC time offset"
	          ::= { svn 10 }

      svnLogDStat OBJECT-TYPE
      		  SYNTAX  DisplayString (SIZE (0..255))
		  MAX-ACCESS read-only
		  STATUS  current
		  DESCRIPTION
		  	   "Log Daemon Status"
	          ::= { svnLogDaemon 1 }

      svnSysStartTime OBJECT-TYPE
      		  SYNTAX  Unsigned32
		  MAX-ACCESS read-only
		  STATUS  current
		  DESCRIPTION
		           "System start time"
		  ::= { svn 12 }

      svnSysUniqId OBJECT-TYPE
      		  SYNTAX  DisplayString
		  MAX-ACCESS read-only
		  STATUS  current
		  DESCRIPTION
		  	   "System unique ID"
	          ::= { svn 13 }

      svnWebUIPort OBJECT-TYPE
	        SYNTAX  Integer32
	        MAX-ACCESS read-only
	        STATUS  current
	        DESCRIPTION
	        	   "Web UI port (0 - Not supported)"
	        ::= { svn 15 }

    arpTableSize OBJECT-TYPE
      		SYNTAX  Counter32
      		MAX-ACCESS read-only
      		STATUS  current
      		DESCRIPTION
	        	   "count of arp table entries"
	        ::= { arpTableInfo 1 }

		-- Platforms

	svnPlatformInfo	  OBJECT IDENTIFIER ::= { svn 123 }

	supportedPlatforms   OBJECT IDENTIFIER ::= { svnPlatformInfo 1 }

	checkPointUTM-1450 OBJECT-TYPE
		SYNTAX  DisplayString (SIZE (0..255))
		MAX-ACCESS  read-only
		STATUS  current
		DESCRIPTION
			"UTM-1 450"
		::= { supportedPlatforms 1 }

	checkPointUTM-11050 OBJECT-TYPE
		SYNTAX  DisplayString (SIZE (0..255))
		MAX-ACCESS  read-only
		STATUS  current
		DESCRIPTION
			"UTM-1 1050"
		::= { supportedPlatforms 2 }

	checkPointUTM-12050 OBJECT-TYPE
		SYNTAX  DisplayString (SIZE (0..255))
		MAX-ACCESS  read-only
		STATUS  current
		DESCRIPTION
			"UTM-1 2050"
		::= { supportedPlatforms 3 }

	checkPointUTM-1130 OBJECT-TYPE
		SYNTAX  DisplayString (SIZE (0..255))
		MAX-ACCESS  read-only
		STATUS  current
		DESCRIPTION
			"UTM-1 130"
		::= { supportedPlatforms 4 }

	checkPointUTM-1270 OBJECT-TYPE
		SYNTAX  DisplayString (SIZE (0..255))
		MAX-ACCESS  read-only
		STATUS  current
		DESCRIPTION
			"UTM-1 270"
		::= { supportedPlatforms 5 }

	checkPointUTM-1570 OBJECT-TYPE
		SYNTAX  DisplayString (SIZE (0..255))
		MAX-ACCESS  read-only
		STATUS  current
		DESCRIPTION
			"UTM-1 570"
		::= { supportedPlatforms 6 }

	checkPointUTM-11070 OBJECT-TYPE
		SYNTAX  DisplayString (SIZE (0..255))
		MAX-ACCESS  read-only
		STATUS  current
		DESCRIPTION
			"UTM-1 1070"
		::= { supportedPlatforms 7 }

	checkPointUTM-12070 OBJECT-TYPE
		SYNTAX  DisplayString (SIZE (0..255))
		MAX-ACCESS  read-only
		STATUS  current
		DESCRIPTION
			"UTM-1 2070"
		::= { supportedPlatforms 8 }

	checkPointUTM-13070 OBJECT-TYPE
		SYNTAX  DisplayString (SIZE (0..255))
		MAX-ACCESS  read-only
		STATUS  current
		DESCRIPTION
			"UTM-1 3070"
		::= { supportedPlatforms 9 }

	checkPointPower-15070 OBJECT-TYPE
		SYNTAX  DisplayString (SIZE (0..255))
		MAX-ACCESS  read-only
		STATUS  current
		DESCRIPTION
			"Power-1 5070"
		::= { supportedPlatforms 10 }

	checkPointPower-19070 OBJECT-TYPE
		SYNTAX  DisplayString (SIZE (0..255))
		MAX-ACCESS  read-only
		STATUS  current
		DESCRIPTION
			"Power-1 9070"
		::= { supportedPlatforms 11 }

	checkPointPower-111000 OBJECT-TYPE
		SYNTAX  DisplayString (SIZE (0..255))
		MAX-ACCESS  read-only
		STATUS  current
		DESCRIPTION
			"Power-1 11000"
		::= { supportedPlatforms 12 }

	checkPointSmart-15 OBJECT-TYPE
		SYNTAX  DisplayString (SIZE (0..255))
		MAX-ACCESS  read-only
		STATUS  current
		DESCRIPTION
			"Smart-1 5"
		::= { supportedPlatforms 13 }

	checkPointSmart-125 OBJECT-TYPE
		SYNTAX  DisplayString (SIZE (0..255))
		MAX-ACCESS  read-only
		STATUS  current
		DESCRIPTION
			"Smart-1 25"
		::= { supportedPlatforms 14 }

	checkPointSmart-150 OBJECT-TYPE
		SYNTAX  DisplayString (SIZE (0..255))
		MAX-ACCESS  read-only
		STATUS  current
		DESCRIPTION
			"Smart-1 50"
		::= { supportedPlatforms 15 }

	checkPointSmart-1150 OBJECT-TYPE
		SYNTAX  DisplayString (SIZE (0..255))
		MAX-ACCESS  read-only
		STATUS  current
		DESCRIPTION
			"Smart-1 150"
		::= { supportedPlatforms 16 }

	checkPointIP150 OBJECT-TYPE
		SYNTAX  DisplayString (SIZE (0..255))
		MAX-ACCESS  read-only
		STATUS  current
		DESCRIPTION
			"IP150"
		::= { supportedPlatforms 17 }

	checkPointIP280 OBJECT-TYPE
		SYNTAX  DisplayString (SIZE (0..255))
		MAX-ACCESS  read-only
		STATUS  current
		DESCRIPTION
			"IP280"
		::= { supportedPlatforms 18 }

	checkPointIP290 OBJECT-TYPE
		SYNTAX  DisplayString (SIZE (0..255))
		MAX-ACCESS  read-only
		STATUS  current
		DESCRIPTION
			"IP290"
		::= { supportedPlatforms 19 }

	checkPointIP390 OBJECT-TYPE
		SYNTAX  DisplayString (SIZE (0..255))
		MAX-ACCESS  read-only
		STATUS  current
		DESCRIPTION
			"IP390"
		::= { supportedPlatforms 20 }

	checkPointIP560 OBJECT-TYPE
		SYNTAX  DisplayString (SIZE (0..255))
		MAX-ACCESS  read-only
		STATUS  current
		DESCRIPTION
			"IP560"
		::= { supportedPlatforms 21 }

	checkPointIP690 OBJECT-TYPE
		SYNTAX  DisplayString (SIZE (0..255))
		MAX-ACCESS  read-only
		STATUS  current
		DESCRIPTION
			"IP690"
		::= { supportedPlatforms 22 }

	checkPointIP1280 OBJECT-TYPE
		SYNTAX  DisplayString (SIZE (0..255))
		MAX-ACCESS  read-only
		STATUS  current
		DESCRIPTION
			"IP1280"
		::= { supportedPlatforms 23 }

	checkPointIP2450 OBJECT-TYPE
		SYNTAX  DisplayString (SIZE (0..255))
		MAX-ACCESS  read-only
		STATUS  current
		DESCRIPTION
			"IP2450"
		::= { supportedPlatforms 24 }

	checkPointUNIVERGEUnifiedWall1000 OBJECT-TYPE
		SYNTAX  DisplayString (SIZE (0..255))
		MAX-ACCESS  read-only
		STATUS  current
		DESCRIPTION
			"UNIVERGE UnifiedWall 1000"
		::= { supportedPlatforms 25 }

	checkPointUNIVERGEUnifiedWall2000 OBJECT-TYPE
		SYNTAX  DisplayString (SIZE (0..255))
		MAX-ACCESS  read-only
		STATUS  current
		DESCRIPTION
			"UNIVERGE UnifiedWall 2000"
		::= { supportedPlatforms 26 }

	checkPointUNIVERGEUnifiedWall4000 OBJECT-TYPE
		SYNTAX  DisplayString (SIZE (0..255))
		MAX-ACCESS  read-only
		STATUS  current
		DESCRIPTION
			"UNIVERGE UnifiedWall 4000"
		::= { supportedPlatforms 27 }

	checkPointUNIVERGEUnifiedWall100 OBJECT-TYPE
		SYNTAX  DisplayString (SIZE (0..255))
		MAX-ACCESS  read-only
		STATUS  current
		DESCRIPTION
			"UNIVERGE UnifiedWall 100"
		::= { supportedPlatforms 28 }

	checkPointDLP-19571 OBJECT-TYPE
		SYNTAX  DisplayString (SIZE (0..255))
		MAX-ACCESS  read-only
		STATUS  current
		DESCRIPTION
			"DLP-1 9571"
		::= { supportedPlatforms 29 }

	checkPointDLP-12571 OBJECT-TYPE
		SYNTAX  DisplayString (SIZE (0..255))
		MAX-ACCESS  read-only
		STATUS  current
		DESCRIPTION
			"DLP-1 2571"
		::= { supportedPlatforms 30 }

	checkPointIPS-12076 OBJECT-TYPE
		SYNTAX  DisplayString (SIZE (0..255))
		MAX-ACCESS  read-only
		STATUS  current
		DESCRIPTION
			"IPS-1 2076"
		::= { supportedPlatforms 31 }

	checkPointIPS-15076 OBJECT-TYPE
		SYNTAX  DisplayString (SIZE (0..255))
		MAX-ACCESS  read-only
		STATUS  current
		DESCRIPTION
			"IPS-1 5076"
		::= { supportedPlatforms 32 }

	checkPointIPS-19076 OBJECT-TYPE
		SYNTAX  DisplayString (SIZE (0..255))
		MAX-ACCESS  read-only
		STATUS  current
		DESCRIPTION
			"IPS-1 9076"
		::= { supportedPlatforms 33 }

	checkPoint2200 OBJECT-TYPE
		SYNTAX  DisplayString (SIZE (0..255))
		MAX-ACCESS  read-only
		STATUS  current
		DESCRIPTION
			"Check Point 2200"
		::= { supportedPlatforms 34 }

	checkPoint4200 OBJECT-TYPE
		SYNTAX  DisplayString (SIZE (0..255))
		MAX-ACCESS  read-only
		STATUS  current
		DESCRIPTION
			"Check Point 4200"
		::= { supportedPlatforms 35 }

	checkPoint4400 OBJECT-TYPE
		SYNTAX  DisplayString (SIZE (0..255))
		MAX-ACCESS  read-only
		STATUS  current
		DESCRIPTION
			"Check Point 4400"
		::= { supportedPlatforms 36 }

	checkPoint4600 OBJECT-TYPE
		SYNTAX  DisplayString (SIZE (0..255))
		MAX-ACCESS  read-only
		STATUS  current
		DESCRIPTION
			"Check Point 4600"
		::= { supportedPlatforms 37 }

	checkPoint4800 OBJECT-TYPE
		SYNTAX  DisplayString (SIZE (0..255))
		MAX-ACCESS  read-only
		STATUS  current
		DESCRIPTION
			"Check Point 4800"
		::= { supportedPlatforms 38 }

	checkPointTE250 OBJECT-TYPE
		SYNTAX  DisplayString (SIZE (0..255))
		MAX-ACCESS  read-only
		STATUS  current
		DESCRIPTION
			"Check Point TE250"
		::= { supportedPlatforms 39 }

	checkPoint12200 OBJECT-TYPE
		SYNTAX  DisplayString (SIZE (0..255))
		MAX-ACCESS  read-only
		STATUS  current
		DESCRIPTION
			"Check Point 12200"
		::= { supportedPlatforms 40 }

	checkPoint12400 OBJECT-TYPE
		SYNTAX  DisplayString (SIZE (0..255))
		MAX-ACCESS  read-only
		STATUS  current
		DESCRIPTION
			"Check Point 12400"
		::= { supportedPlatforms 41 }

	checkPoint12600 OBJECT-TYPE
		SYNTAX  DisplayString (SIZE (0..255))
		MAX-ACCESS  read-only
		STATUS  current
		DESCRIPTION
			"Check Point 12600"
		::= { supportedPlatforms 42 }

	checkPointTE1000 OBJECT-TYPE
		SYNTAX  DisplayString (SIZE (0..255))
		MAX-ACCESS  read-only
		STATUS  current
		DESCRIPTION
			"Check Point TE1000"
		::= { supportedPlatforms 43 }

	checkPoint13500 OBJECT-TYPE
		SYNTAX  DisplayString (SIZE (0..255))
		MAX-ACCESS  read-only
		STATUS  current
		DESCRIPTION
			"Check Point 13500"
		::= { supportedPlatforms 44 }

	checkPoint21400 OBJECT-TYPE
		SYNTAX  DisplayString (SIZE (0..255))
		MAX-ACCESS  read-only
		STATUS  current
		DESCRIPTION
			"Check Point 21400"
		::= { supportedPlatforms 45 }

	checkPoint21600 OBJECT-TYPE
		SYNTAX  DisplayString (SIZE (0..255))
		MAX-ACCESS  read-only
		STATUS  current
		DESCRIPTION
			"Check Point 21600"
		::= { supportedPlatforms 46 }

	checkPoint21700 OBJECT-TYPE
		SYNTAX  DisplayString (SIZE (0..255))
		MAX-ACCESS  read-only
		STATUS  current
		DESCRIPTION
			"Check Point 21700"
		::= { supportedPlatforms 47 }

	checkPointVMware OBJECT-TYPE
		SYNTAX  DisplayString (SIZE (0..255))
		MAX-ACCESS  read-only
		STATUS  current
		DESCRIPTION
			"VMware"
		::= { supportedPlatforms 48 }

	checkPointOpenServer OBJECT-TYPE
		SYNTAX  DisplayString (SIZE (0..255))
		MAX-ACCESS  read-only
		STATUS  current
		DESCRIPTION
			"Open Server"
		::= { supportedPlatforms 49 }

	checkPointSmart-1205 OBJECT-TYPE
		SYNTAX  DisplayString (SIZE (0..255))
		MAX-ACCESS  read-only
		STATUS  current
		DESCRIPTION
			"Smart-1 205"
		::= { supportedPlatforms 50 }

	checkPointSmart-1210 OBJECT-TYPE
		SYNTAX  DisplayString (SIZE (0..255))
		MAX-ACCESS  read-only
		STATUS  current
		DESCRIPTION
			"Smart-1 210"
		::= { supportedPlatforms 51 }

	checkPointSmart-1225 OBJECT-TYPE
		SYNTAX  DisplayString (SIZE (0..255))
		MAX-ACCESS  read-only
		STATUS  current
		DESCRIPTION
			"Smart-1 225"
		::= { supportedPlatforms 52 }

	checkPointSmart-13050 OBJECT-TYPE
		SYNTAX  DisplayString (SIZE (0..255))
		MAX-ACCESS  read-only
		STATUS  current
		DESCRIPTION
			"Smart-1 3050"
		::= { supportedPlatforms 53 }

	checkPointSmart-13150 OBJECT-TYPE
		SYNTAX  DisplayString (SIZE (0..255))
		MAX-ACCESS  read-only
		STATUS  current
		DESCRIPTION
			"Smart-1 3150"
		::= { supportedPlatforms 54 }

	checkPoint13800 OBJECT-TYPE
		SYNTAX  DisplayString (SIZE (0..255))
		MAX-ACCESS  read-only
		STATUS  current
		DESCRIPTION
			"Check Point 13800"
		::= { supportedPlatforms 55 }

	checkPoint21800 OBJECT-TYPE
		SYNTAX  DisplayString (SIZE (0..255))
		MAX-ACCESS  read-only
		STATUS  current
		DESCRIPTION
			"Check Point 21800"
		::= { supportedPlatforms 56 }

	checkPointTE250X OBJECT-TYPE
		SYNTAX  DisplayString (SIZE (0..255))
		MAX-ACCESS  read-only
		STATUS  current
		DESCRIPTION
			"Check Point TE250X"
		::= { supportedPlatforms 57 }

	checkPointTE1000X OBJECT-TYPE
		SYNTAX  DisplayString (SIZE (0..255))
		MAX-ACCESS  read-only
		STATUS  current
		DESCRIPTION
			"Check Point TE1000X"
		::= { supportedPlatforms 58 }

	checkPointTE2000X OBJECT-TYPE
		SYNTAX  DisplayString (SIZE (0..255))
		MAX-ACCESS  read-only
		STATUS  current
		DESCRIPTION
			"Check Point TE2000X"
		::= { supportedPlatforms 59 }

	checkPointTE100X OBJECT-TYPE
		SYNTAX  DisplayString (SIZE (0..255))
		MAX-ACCESS  read-only
		STATUS  current
		DESCRIPTION
			"Check Point TE100X"
		::= { supportedPlatforms 60 }

	checkPoint23500 OBJECT-TYPE
		SYNTAX  DisplayString (SIZE (0..255))
		MAX-ACCESS  read-only
		STATUS  current
		DESCRIPTION
			"Check Point 23500"
		::= { supportedPlatforms 61 }


	checkPoint23800 OBJECT-TYPE
		SYNTAX  DisplayString (SIZE (0..255))
		MAX-ACCESS  read-only
		STATUS  current
		DESCRIPTION
			"Check Point 23800"
		::= { supportedPlatforms 62 }


	checkPoint15400 OBJECT-TYPE
		SYNTAX  DisplayString (SIZE (0..255))
		MAX-ACCESS  read-only
		STATUS  current
		DESCRIPTION
			"Check Point 15400"
		::= { supportedPlatforms 63 }

	checkPoint15600 OBJECT-TYPE
		SYNTAX  DisplayString (SIZE (0..255))
		MAX-ACCESS  read-only
		STATUS  current
		DESCRIPTION
			"Check Point 15600"
		::= { supportedPlatforms 64 }

	checkPoint3200 OBJECT-TYPE
		SYNTAX  DisplayString (SIZE (0..255))
		MAX-ACCESS  read-only
		STATUS  current
		DESCRIPTION
			"Check Point 3200"
		::= { supportedPlatforms 65 }

	checkPoint5200 OBJECT-TYPE
		SYNTAX  DisplayString (SIZE (0..255))
		MAX-ACCESS  read-only
		STATUS  current
		DESCRIPTION
			"Check Point 5200"
		::= { supportedPlatforms 66 }

	checkPoint5400 OBJECT-TYPE
		SYNTAX  DisplayString (SIZE (0..255))
		MAX-ACCESS  read-only
		STATUS  current
		DESCRIPTION
			"Check Point 5400"
		::= { supportedPlatforms 67 }

	checkPoint5600 OBJECT-TYPE
		SYNTAX  DisplayString (SIZE (0..255))
		MAX-ACCESS  read-only
		STATUS  current
		DESCRIPTION
			"Check Point 5600"
		::= { supportedPlatforms 68 }

	checkPoint5800 OBJECT-TYPE
		SYNTAX  DisplayString (SIZE (0..255))
		MAX-ACCESS  read-only
		STATUS  current
		DESCRIPTION
			"Check Point 5800"
		::= { supportedPlatforms 69 }

	checkPoint5900 OBJECT-TYPE
		SYNTAX  DisplayString (SIZE (0..255))
		MAX-ACCESS  read-only
		STATUS  current
		DESCRIPTION
			"Check Point 5900"
		::= { supportedPlatforms 70 }

	checkPoint3100 OBJECT-TYPE
		SYNTAX  DisplayString (SIZE (0..255))
		MAX-ACCESS  read-only
		STATUS  current
		DESCRIPTION
			"Check Point 3100"
		::= { supportedPlatforms 71 }

	checkPoint5100 OBJECT-TYPE
		SYNTAX  DisplayString (SIZE (0..255))
		MAX-ACCESS  read-only
		STATUS  current
		DESCRIPTION
			"Check Point 5100"
		::= { supportedPlatforms 72 }

	checkPointSmart-1405 OBJECT-TYPE
		SYNTAX  DisplayString (SIZE (0..255))
		MAX-ACCESS  read-only
		STATUS  current
		DESCRIPTION
			"Smart-1 405"
		::= { supportedPlatforms 73 }

	checkPointSmart-1410 OBJECT-TYPE
		SYNTAX  DisplayString (SIZE (0..255))
		MAX-ACCESS  read-only
		STATUS  current
		DESCRIPTION
			"Smart-1 410"
		::= { supportedPlatforms 74 }

	checkPointSmart-5050 OBJECT-TYPE
               SYNTAX  DisplayString (SIZE (0..255))
               MAX-ACCESS  read-only
               STATUS  current
               DESCRIPTION
                       "Smart-1 5050"
               ::= { supportedPlatforms 75 }

	checkPointSmart-525 OBJECT-TYPE
               SYNTAX  DisplayString (SIZE (0..255))
               MAX-ACCESS  read-only
               STATUS  current
               DESCRIPTION
                       "Smart-1 525"
               ::= { supportedPlatforms 76 }

	checkPointSmart-5150 OBJECT-TYPE
               SYNTAX  DisplayString (SIZE (0..255))
               MAX-ACCESS  read-only
               STATUS  current
               DESCRIPTION
                       "Smart-1 5150"
               ::= { supportedPlatforms 77 }

	checkPoint23900 OBJECT-TYPE
               SYNTAX  DisplayString (SIZE (0..255))
               MAX-ACCESS  read-only
               STATUS  current
               DESCRIPTION
                       "Check Point 23900"
               ::= { supportedPlatforms 78 }

	checkPoint6500 OBJECT-TYPE
               SYNTAX  DisplayString (SIZE (0..255))
               MAX-ACCESS  read-only
               STATUS  current
               DESCRIPTION
                       "Check Point 6500"
               ::= { supportedPlatforms 79 }

	checkPoint6800 OBJECT-TYPE
               SYNTAX  DisplayString (SIZE (0..255))
               MAX-ACCESS  read-only
               STATUS  current
               DESCRIPTION
                       "Check Point 6800"
               ::= { supportedPlatforms 80 }

	checkPoint16000T OBJECT-TYPE
               SYNTAX  DisplayString (SIZE (0..255))
               MAX-ACCESS  read-only
               STATUS  current
               DESCRIPTION
                       "Check Point 16000T"
               ::= { supportedPlatforms 81 }

	checkPoint26000 OBJECT-TYPE
               SYNTAX  DisplayString (SIZE (0..255))
               MAX-ACCESS  read-only
               STATUS  current
               DESCRIPTION
                       "Check Point 26000"
               ::= { supportedPlatforms 82 }

	checkPointSmart-625 OBJECT-TYPE
               SYNTAX  DisplayString (SIZE (0..255))
               MAX-ACCESS  read-only
               STATUS  current
               DESCRIPTION
                       "Smart-1 625"
               ::= { supportedPlatforms 83 }

	checkPoint16000 OBJECT-TYPE
               SYNTAX  DisplayString (SIZE (0..255))
               MAX-ACCESS  read-only
               STATUS  current
               DESCRIPTION
                       "Check Point 16000"
               ::= { supportedPlatforms 84 }

	checkPoint26000T OBJECT-TYPE
               SYNTAX  DisplayString (SIZE (0..255))
               MAX-ACCESS  read-only
               STATUS  current
               DESCRIPTION
                       "Check Point 26000T"
               ::= { supportedPlatforms 85 }

	checkPoint3600 OBJECT-TYPE
               SYNTAX  DisplayString (SIZE (0..255))
               MAX-ACCESS  read-only
               STATUS  current
               DESCRIPTION
                       "Check Point 3600"
               ::= { supportedPlatforms 86 }

	checkPoint3600T OBJECT-TYPE
               SYNTAX  DisplayString (SIZE (0..255))
               MAX-ACCESS  read-only
               STATUS  current
               DESCRIPTION
                       "Check Point 3600T"
               ::= { supportedPlatforms 87 }

	checkPoint6200B OBJECT-TYPE
               SYNTAX  DisplayString (SIZE (0..255))
               MAX-ACCESS  read-only
               STATUS  current
               DESCRIPTION
                       "Check Point 6200B"
               ::= { supportedPlatforms 88 }

	checkPoint6200P OBJECT-TYPE
               SYNTAX  DisplayString (SIZE (0..255))
               MAX-ACCESS  read-only
               STATUS  current
               DESCRIPTION
                       "Check Point 6200P"
               ::= { supportedPlatforms 89 }

	checkPoint6200T OBJECT-TYPE
               SYNTAX  DisplayString (SIZE (0..255))
               MAX-ACCESS  read-only
               STATUS  current
               DESCRIPTION
                       "Check Point 6200T"
               ::= { supportedPlatforms 90 }

	checkPoint6600 OBJECT-TYPE
               SYNTAX  DisplayString (SIZE (0..255))
               MAX-ACCESS  read-only
               STATUS  current
               DESCRIPTION
                       "Check Point 6600"
               ::= { supportedPlatforms 91 }

	checkPoint6900 OBJECT-TYPE
               SYNTAX  DisplayString (SIZE (0..255))
               MAX-ACCESS  read-only
               STATUS  current
               DESCRIPTION
                       "Check Point 6900"
               ::= { supportedPlatforms 92 }

	checkPoint16600HS OBJECT-TYPE
               SYNTAX  DisplayString (SIZE (0..255))
               MAX-ACCESS  read-only
               STATUS  current
               DESCRIPTION
                       "Check Point 16600HS"
               ::= { supportedPlatforms 93 }

           checkPoint28600HS OBJECT-TYPE
               SYNTAX  DisplayString (SIZE (0..255))
               MAX-ACCESS  read-only
               STATUS  current
               DESCRIPTION
                       "Check Point 28600HS"
               ::= { supportedPlatforms 94 }

	checkPoint6700 OBJECT-TYPE
               SYNTAX  DisplayString (SIZE (0..255))
               MAX-ACCESS  read-only
               STATUS  current
               DESCRIPTION
                       "Check Point 6700"
               ::= { supportedPlatforms 95 }

	checkPoint7000 OBJECT-TYPE
               SYNTAX  DisplayString (SIZE (0..255))
               MAX-ACCESS  read-only
               STATUS  current
               DESCRIPTION
                       "Check Point 7000"
               ::= { supportedPlatforms 96 }

	checkPoint16200 OBJECT-TYPE
               SYNTAX  DisplayString (SIZE (0..255))
               MAX-ACCESS  read-only
               STATUS  current
               DESCRIPTION
                       "Check Point 16200"
               ::= { supportedPlatforms 97 }

	checkPoint28000 OBJECT-TYPE
               SYNTAX  DisplayString (SIZE (0..255))
               MAX-ACCESS  read-only
               STATUS  current
               DESCRIPTION
                       "Check Point 28000"
               ::= { supportedPlatforms 98 }

	checkPoint6400 OBJECT-TYPE
           SYNTAX  DisplayString (SIZE (0..255))
           MAX-ACCESS  read-only
           STATUS  current
           DESCRIPTION
                   "Check Point 6400"
           ::= { supportedPlatforms 99 }

	checkPoint3800 OBJECT-TYPE
               SYNTAX  DisplayString (SIZE (0..255))
               MAX-ACCESS  read-only
               STATUS  current
               DESCRIPTION
                       "Check Point 3800"
               ::= { supportedPlatforms 100 }

	checkPointSmart-6000-L OBJECT-TYPE
               SYNTAX  DisplayString (SIZE (0..255))
               MAX-ACCESS  read-only
               STATUS  current
               DESCRIPTION
                       "Smart-1 6000-L"
               ::= { supportedPlatforms 101 }

	checkPointSmart-6000-XL OBJECT-TYPE
               SYNTAX  DisplayString (SIZE (0..255))
               MAX-ACCESS  read-only
               STATUS  current
               DESCRIPTION
                       "Smart-1 6000-XL"
               ::= { supportedPlatforms 102 }

	checkPointSmart-600-S OBJECT-TYPE
	           SYNTAX  DisplayString (SIZE (0..255))
	           MAX-ACCESS  read-only
	           STATUS  current
	           DESCRIPTION
	                   "Smart-1 600-S"
	           ::= { supportedPlatforms 103 }

	checkPointSmart-600-M OBJECT-TYPE
	           SYNTAX  DisplayString (SIZE (0..255))
	           MAX-ACCESS  read-only
	           STATUS  current
	           DESCRIPTION
	                   "Smart-1 600-M"
	           ::= { supportedPlatforms 104 }

	checkPointSMB-1530 OBJECT-TYPE
               SYNTAX  DisplayString (SIZE (0..255))
               MAX-ACCESS  read-only
               STATUS  current
               DESCRIPTION
                       "Check Point SMB 1530"
               ::= { supportedPlatforms 2000 }

	checkPointSMB-1550 OBJECT-TYPE
               SYNTAX  DisplayString (SIZE (0..255))
               MAX-ACCESS  read-only
               STATUS  current
               DESCRIPTION
                       "Check Point SMB 1550"
               ::= { supportedPlatforms 2001 }

	checkPointSMB-1570 OBJECT-TYPE
               SYNTAX  DisplayString (SIZE (0..255))
               MAX-ACCESS  read-only
               STATUS  current
               DESCRIPTION
                       "Check Point SMB 1570"
               ::= { supportedPlatforms 2002 }

	checkPointSMB-1570R OBJECT-TYPE
               SYNTAX  DisplayString (SIZE (0..255))
               MAX-ACCESS  read-only
               STATUS  current
               DESCRIPTION
                       "Check Point SMB 1570R"
               ::= { supportedPlatforms 2003 }

	checkPointSMB-1590 OBJECT-TYPE
               SYNTAX  DisplayString (SIZE (0..255))
               MAX-ACCESS  read-only
               STATUS  current
               DESCRIPTION
                       "Check Point SMB 1590"
               ::= { supportedPlatforms 2004 }

	checkPointSMB-1600 OBJECT-TYPE
               SYNTAX  DisplayString (SIZE (0..255))
               MAX-ACCESS  read-only
               STATUS  current
               DESCRIPTION
                       "Check Point SMB 1600"
               ::= { supportedPlatforms 2005 }

	checkPointSMB-1800 OBJECT-TYPE
               SYNTAX  DisplayString (SIZE (0..255))
               MAX-ACCESS  read-only
               STATUS  current
               DESCRIPTION
                       "Check Point SMB 1800"
               ::= { supportedPlatforms 2006 }

	checkPoint61000 OBJECT-TYPE
               SYNTAX  DisplayString (SIZE (0..255))
               MAX-ACCESS  read-only
               STATUS  current
               DESCRIPTION
                       "Check Point 61000 Scalable Platforms"
               ::= { supportedPlatforms 3001 }

	checkPoint64000 OBJECT-TYPE
               SYNTAX  DisplayString (SIZE (0..255))
               MAX-ACCESS  read-only
               STATUS  current
               DESCRIPTION
                       "Check Point 64000 Scalable Platforms"
               ::= { supportedPlatforms 3002 }

	checkPoint41000 OBJECT-TYPE
               SYNTAX  DisplayString (SIZE (0..255))
               MAX-ACCESS  read-only
               STATUS  current
               DESCRIPTION
                       "Check Point 41000 Scalable Platforms"
               ::= { supportedPlatforms 3003 }

	checkPoint44000 OBJECT-TYPE
               SYNTAX  DisplayString (SIZE (0..255))
               MAX-ACCESS  read-only
               STATUS  current
               DESCRIPTION
                       "Check Point 44000 Scalable Platforms"
               ::= { supportedPlatforms 3004 }

	checkPointMHO140 OBJECT-TYPE
               SYNTAX  DisplayString (SIZE (0..255))
               MAX-ACCESS  read-only
               STATUS  current
               DESCRIPTION
                       "Check Point Maestro Hyperscale Orchestrator 140"
               ::= { supportedPlatforms 4000 }

	checkPointMHO170 OBJECT-TYPE
               SYNTAX  DisplayString (SIZE (0..255))
               MAX-ACCESS  read-only
               STATUS  current
               DESCRIPTION
                       "Check Point Maestro Hyperscale Orchestrator 170"
               ::= { supportedPlatforms 4001 }

	checkPointMHO175 OBJECT-TYPE
               SYNTAX  DisplayString (SIZE (0..255))
               MAX-ACCESS  read-only
               STATUS  current
               DESCRIPTION
                       "Check Point Maestro Hyperscale Orchestrator 175"
               ::= { supportedPlatforms 4002 }

      svnLicensing OBJECT IDENTIFIER ::= { svn 18 }

      licensingTable OBJECT-TYPE
			  SYNTAX  SEQUENCE OF  LicensingEntry
			  MAX-ACCESS  not-accessible
			  STATUS  current
			  DESCRIPTION "No description available"
			  ::= { svnLicensing 1 }

	  licensingEntry OBJECT-TYPE
			  SYNTAX LicensingEntry
			  MAX-ACCESS  not-accessible
			  STATUS  current
			  DESCRIPTION "No description available"
			  INDEX   { licensingIndex }
			  ::= { licensingTable 1 }

	  LicensingEntry ::=
			  SEQUENCE {
				licensingIndex			Unsigned32,
				licensingID			Unsigned32,
				licensingBladeGUIOrder		Unsigned32,
				licensingBladeName		DisplayString,
				licensingState			DisplayString,
				licensingExpirationDate		Unsigned32,
				licensingImpact			DisplayString,
				licensingBladeActive		INTEGER,
				licensingTotalQuota		INTEGER,
				licensingUsedQuota		INTEGER
			  }

	  licensingIndex OBJECT-TYPE
			  SYNTAX  Unsigned32
			  MAX-ACCESS not-accessible
			  STATUS  current
			  DESCRIPTION "No description available"
			  ::= { licensingEntry 1 }

	  licensingID OBJECT-TYPE
			  SYNTAX  Unsigned32
			  MAX-ACCESS read-only
			  STATUS  current
			  DESCRIPTION "No description available"
			  ::= { licensingEntry 2 }

	  licensingBladeGUIOrder OBJECT-TYPE
		  	  SYNTAX  Unsigned32
			  MAX-ACCESS read-only
			  STATUS  current
			  DESCRIPTION "No description available"
			  ::= { licensingEntry 3 }

	  licensingBladeName OBJECT-TYPE
			  SYNTAX  DisplayString
			  MAX-ACCESS read-only
			  STATUS  current
			  DESCRIPTION "No description available"
			  ::= { licensingEntry 4 }

	  licensingState OBJECT-TYPE
			  SYNTAX  DisplayString
			  MAX-ACCESS read-only
			  STATUS  current
			  DESCRIPTION "No description available"
			  ::= { licensingEntry 5 }

	  licensingExpirationDate OBJECT-TYPE
			  SYNTAX  Unsigned32
			  MAX-ACCESS read-only
			  STATUS  current
			  DESCRIPTION "No description available"
			  ::= { licensingEntry 6 }

	  licensingImpact OBJECT-TYPE
			  SYNTAX  DisplayString
			  MAX-ACCESS read-only
			  STATUS  current
			  DESCRIPTION "No description available"
			  ::= { licensingEntry 7 }

	  licensingBladeActive OBJECT-TYPE
			  SYNTAX  Integer32
			  MAX-ACCESS read-only
			  STATUS  current
			  DESCRIPTION "No description available"
			  ::= { licensingEntry 8 }

	  licensingTotalQuota OBJECT-TYPE
			  SYNTAX  Integer32
			  MAX-ACCESS read-only
			  STATUS  current
			  DESCRIPTION "No description available"
			  ::= { licensingEntry 9 }

	  licensingUsedQuota OBJECT-TYPE
			  SYNTAX  Integer32
			  MAX-ACCESS read-only
			  STATUS  current
			  DESCRIPTION "No description available"
			  ::= { licensingEntry 10 }

	  licensingAssetInfo        OBJECT IDENTIFIER ::= { svnLicensing 2 }

	  licensingAssetAccountId OBJECT-TYPE
			  SYNTAX  DisplayString
			  MAX-ACCESS read-only
			  STATUS  current
			  DESCRIPTION "No description available"
			  ::= { licensingAssetInfo 1 }

	  licensingAssetPackageDescription OBJECT-TYPE
			  SYNTAX  DisplayString
			  MAX-ACCESS read-only
			  STATUS  current
			  DESCRIPTION "No description available"
			  ::= { licensingAssetInfo 2 }

	  licensingAssetContainerCK OBJECT-TYPE
			  SYNTAX  DisplayString
			  MAX-ACCESS read-only
			  STATUS  current
			  DESCRIPTION "No description available"
			  ::= { licensingAssetInfo 3 }

	  licensingAssetCKSignature OBJECT-TYPE
			  SYNTAX  DisplayString
			  MAX-ACCESS read-only
			  STATUS  current
			  DESCRIPTION "No description available"
			  ::= { licensingAssetInfo 4 }

	  licensingAssetContainerSKU OBJECT-TYPE
			  SYNTAX  DisplayString
			  MAX-ACCESS read-only
			  STATUS  current
			  DESCRIPTION "No description available"
			  ::= { licensingAssetInfo 5 }

	  licensingAssetSupportLevel OBJECT-TYPE
		 	  SYNTAX  DisplayString
			  MAX-ACCESS read-only
			  STATUS  current
			  DESCRIPTION "No description available"
			  ::= { licensingAssetInfo 6 }

	  licensingAssetSupportExpiration OBJECT-TYPE
			  SYNTAX  DisplayString
			  MAX-ACCESS read-only
			  STATUS  current
			  DESCRIPTION "No description available"
			  ::= { licensingAssetInfo 7 }

	  licensingAssetActivationStatus OBJECT-TYPE
			  SYNTAX  DisplayString
			  MAX-ACCESS read-only
			  STATUS  current
			  DESCRIPTION "No description available"
			  ::= { licensingAssetInfo 8 }

	  svnConnectivity OBJECT-TYPE
	  		  SYNTAX  Integer32
			  MAX-ACCESS read-only
			  STATUS  current
			  DESCRIPTION
	        	   "User Center connectivity"
			  ::= { svn 19 }

       -- the svn interface table and stats

      svnNetStat	  OBJECT IDENTIFIER ::= { svn 50 }

	  svnNetIfTable OBJECT-TYPE
	          SYNTAX  SEQUENCE OF  SvnNetIfTableEntry
			  MAX-ACCESS  not-accessible
			  STATUS  current
			  DESCRIPTION "No description available"
			  ::= { svnNetStat 1 }

	  svnNetIfTableEntry OBJECT-TYPE
	          SYNTAX SvnNetIfTableEntry
			  MAX-ACCESS  not-accessible
			  STATUS  current
			  DESCRIPTION "No description available"
			  INDEX   { svnNetIfIndex }
			  ::= { svnNetIfTable 1 }

	  SvnNetIfTableEntry ::=
	          SEQUENCE {
				svnNetIfIndex
				      Unsigned32,
				svnNetIfVsid
				      Unsigned32,
				svnNetIfName
					  DisplayString,
				svnNetIfAddress
				      IpAddress,
				svnNetIfMask
				      IpAddress,
				svnNetIfMTU
				      Unsigned32,
				svnNetIfState
				      INTEGER,
				svnNetIfMAC
				      DisplayString,
				svnNetIfDescription
				      DisplayString,
				svnNetIfOperState
				      INTEGER,
				svnNetIfRXBytes
				      Counter64,
				svnNetIfRXDrops
				      Counter64,
				svnNetIfRXErrors
				      Counter64,
				svnNetIfRXPackets
				      Counter64,
				svnNetIfTXBytes
				      Counter64,
				svnNetIfTXDrops
				      Counter64,
				svnNetIfTXErrors
				      Counter64,
				svnNetIfTXPackets
				      Counter64
			  }

      svnNetIfIndex OBJECT-TYPE
              SYNTAX  Unsigned32
              MAX-ACCESS not-accessible
              STATUS  current
              DESCRIPTION "No description available"
              ::= { svnNetIfTableEntry 1 }

      svnNetIfVsid OBJECT-TYPE
      		  SYNTAX  Unsigned32
              MAX-ACCESS read-only
              STATUS  current
              DESCRIPTION "No description available"
              ::= { svnNetIfTableEntry 2 }

      svnNetIfName OBJECT-TYPE
      		  SYNTAX  DisplayString
              MAX-ACCESS read-only
              STATUS  current
              DESCRIPTION "No description available"
              ::= { svnNetIfTableEntry 3 }

      svnNetIfAddress OBJECT-TYPE
      		  SYNTAX  IpAddress
              MAX-ACCESS read-only
              STATUS  current
              DESCRIPTION "No description available"
              ::= { svnNetIfTableEntry 4 }

      svnNetIfMask OBJECT-TYPE
      		  SYNTAX  IpAddress
              MAX-ACCESS read-only
              STATUS  current
              DESCRIPTION "No description available"
              ::= { svnNetIfTableEntry 5 }

       svnNetIfMTU OBJECT-TYPE
      		  SYNTAX  Unsigned32
              MAX-ACCESS read-only
              STATUS  current
              DESCRIPTION "No description available"
              ::= { svnNetIfTableEntry 6 }

       svnNetIfState OBJECT-TYPE
      		  SYNTAX  Integer32
              MAX-ACCESS read-only
              STATUS  current
              DESCRIPTION "No description available"
              ::= { svnNetIfTableEntry 7 }

       svnNetIfMAC OBJECT-TYPE
      		  SYNTAX  DisplayString
              MAX-ACCESS read-only
              STATUS  current
              DESCRIPTION "No description available"
              ::= { svnNetIfTableEntry 8 }

        svnNetIfDescription OBJECT-TYPE
      		  SYNTAX  DisplayString
              MAX-ACCESS read-only
              STATUS  current
              DESCRIPTION "No description available"
              ::= { svnNetIfTableEntry 9 }

       svnNetIfOperState OBJECT-TYPE
      		  SYNTAX  Integer32
              MAX-ACCESS read-only
              STATUS  current
              DESCRIPTION "No description available"
              ::= { svnNetIfTableEntry 10 }

		svnNetIfRXBytes OBJECT-TYPE
			SYNTAX  Counter64
			MAX-ACCESS read-only
			STATUS  current
			DESCRIPTION "No description available"
			::= { svnNetIfTableEntry 13 }

		svnNetIfRXDrops OBJECT-TYPE
			SYNTAX  Counter64
			MAX-ACCESS read-only
			STATUS  current
			DESCRIPTION "No description available"
			::= { svnNetIfTableEntry 14 }

		svnNetIfRXErrors OBJECT-TYPE
			SYNTAX  Counter64
			MAX-ACCESS read-only
			STATUS  current
			DESCRIPTION "No description available"
			::= { svnNetIfTableEntry 15 }

		svnNetIfRXPackets OBJECT-TYPE
			SYNTAX  Counter64
			MAX-ACCESS read-only
			STATUS  current
			DESCRIPTION "No description available"
			::= { svnNetIfTableEntry 16 }

		svnNetIfTXBytes OBJECT-TYPE
			SYNTAX  Counter64
			MAX-ACCESS read-only
			STATUS  current
			DESCRIPTION "No description available"
			::= { svnNetIfTableEntry 17 }

		svnNetIfTXDrops OBJECT-TYPE
			SYNTAX  Counter64
			MAX-ACCESS read-only
			STATUS  current
			DESCRIPTION "No description available"
			::= { svnNetIfTableEntry 18 }

		svnNetIfTXErrors OBJECT-TYPE
			SYNTAX  Counter64
			MAX-ACCESS read-only
			STATUS  current
			DESCRIPTION "No description available"
			::= { svnNetIfTableEntry 19 }

		svnNetIfTXPackets OBJECT-TYPE
			SYNTAX  Counter64
			MAX-ACCESS read-only
			STATUS  current
			DESCRIPTION "No description available"
			::= { svnNetIfTableEntry 20 }

      vsRoutingTable OBJECT-TYPE
	          SYNTAX  SEQUENCE OF  VSRoutingEntry
			  MAX-ACCESS  not-accessible
			  STATUS  current
			  DESCRIPTION "No description available"
			  ::= { svn 51 }

      vsRoutingEntry OBJECT-TYPE
	          SYNTAX VSRoutingEntry
			  MAX-ACCESS  not-accessible
			  STATUS  current
			  DESCRIPTION "No description available"
			  INDEX   { vsRoutingIndex }
			  ::= { vsRoutingTable 1 }

      VSRoutingEntry ::=
	          SEQUENCE {
				vsRoutingIndex
				      Unsigned32,
				vsRoutingDest
				      IpAddress,
				vsRoutingMask
				      IpAddress,
				vsRoutingGateway
				      IpAddress,
				vsRoutingIntrfName
				      DisplayString,
				vsRoutingVsId
				      Unsigned32
			  }

      vsRoutingIndex OBJECT-TYPE
              SYNTAX  Unsigned32
              MAX-ACCESS not-accessible
              STATUS  current
              DESCRIPTION "No description available"
              ::= { vsRoutingEntry 1 }

      vsRoutingDest OBJECT-TYPE
      	      SYNTAX  IpAddress
              MAX-ACCESS read-only
              STATUS  current
              DESCRIPTION "No description available"
              ::= { vsRoutingEntry 2 }

      vsRoutingMask OBJECT-TYPE
      	      SYNTAX  IpAddress
              MAX-ACCESS read-only
              STATUS  current
              DESCRIPTION "No description available"
              ::= { vsRoutingEntry 3 }

      vsRoutingGateway OBJECT-TYPE
      	      SYNTAX  IpAddress
              MAX-ACCESS read-only
              STATUS  current
              DESCRIPTION "No description available"
              ::= { vsRoutingEntry 4 }

      vsRoutingIntrfName OBJECT-TYPE
      	      SYNTAX  DisplayString
              MAX-ACCESS read-only
              STATUS  current
              DESCRIPTION "No description available"
              ::= { vsRoutingEntry 5 }

      vsRoutingVsId OBJECT-TYPE
      	      SYNTAX  Unsigned32
              MAX-ACCESS read-only
              STATUS  current
              DESCRIPTION "No description available"
              ::= { vsRoutingEntry 6 }

      svnStatCode OBJECT-TYPE
      		  SYNTAX  Unsigned32
      		  MAX-ACCESS read-only
      		  STATUS  current
	          DESCRIPTION
	        	   "Status code"
      		  ::= { svn 101 }

      svnStatShortDescr OBJECT-TYPE
      		  SYNTAX  DisplayString (SIZE (0..255))
      		  MAX-ACCESS read-only
      		  STATUS  current
	          DESCRIPTION
	        	   "Status short description"
      		  ::= { svn 102 }

      svnStatLongDescr OBJECT-TYPE
      		  SYNTAX  DisplayString (SIZE (0..255))
      		  MAX-ACCESS read-only
      		  STATUS  current
	          DESCRIPTION
	        	   "Status long description"
      		  ::= { svn 103 }

      svnServicePack OBJECT-TYPE
      		  SYNTAX  Gauge32
      		  MAX-ACCESS read-only
      		  STATUS  current
	          DESCRIPTION
	        	   "SVN service pack"
      		  ::= { svn 999 }

      -- the Managment status
	  -- Overall statistics and state

      mgProdName OBJECT-TYPE
      		  SYNTAX  DisplayString (SIZE (0..255))
      		  MAX-ACCESS read-only
      		  STATUS  current
	          DESCRIPTION
	        	   "Product name"
      		  ::= { mngmt 1 }

      mgVerMajor OBJECT-TYPE
      		  SYNTAX  Integer32
      		  MAX-ACCESS read-only
      		  STATUS  current
	          DESCRIPTION
	        	   "Major version"
      		  ::= { mngmt 2 }

      mgVerMinor OBJECT-TYPE
      		  SYNTAX  Integer32
      		  MAX-ACCESS read-only
      		  STATUS  current
	          DESCRIPTION
	        	   "Minor version"
      		  ::= { mngmt 3 }

      mgBuildNumber OBJECT-TYPE
      		  SYNTAX  Integer32
      		  MAX-ACCESS read-only
      		  STATUS  current
	          DESCRIPTION
	        	   "Build number"
      		  ::= { mngmt 4 }

      mgActiveStatus OBJECT-TYPE
      		  SYNTAX  DisplayString
      		  MAX-ACCESS read-only
      		  STATUS  current
	          DESCRIPTION
	        	   "Active status"
      		  ::= { mngmt 5 }

      mgFwmIsAlive OBJECT-TYPE
      		  SYNTAX  Integer32
      		  MAX-ACCESS read-only
      		  STATUS  current
	          DESCRIPTION
	        	   "Managment is alive"
      		  ::= { mngmt 6 }

	  mgConnectedClientsTable OBJECT-TYPE
              SYNTAX  SEQUENCE OF  MgConnectedClientsEntry
			  MAX-ACCESS  not-accessible
			  STATUS  current
			  DESCRIPTION "No description available"
			  ::= { mngmt 7 }

      mgMgmtHAJournals OBJECT-TYPE
      		  SYNTAX  DisplayString
      		  MAX-ACCESS read-only
			  STATUS  current
      		  DESCRIPTION
	        	   "Management HA synchronization journals"
      		  ::= { mngmt 9 }

      mgIsLicenseViolation OBJECT-TYPE
      		  SYNTAX  Integer32
      		  MAX-ACCESS read-only
			  STATUS  current
	          DESCRIPTION
	        	   "License violation detected"
      		  ::= { mngmt 10 }

      mgLicenseViolationMsg OBJECT-TYPE
      		  SYNTAX  DisplayString
      		  MAX-ACCESS read-only
			  STATUS  current
	          DESCRIPTION
	        	   "License violation detected"
      		  ::= { mngmt 11 }

	  mgConnectedClientsEntry OBJECT-TYPE
	          SYNTAX MgConnectedClientsEntry
			  MAX-ACCESS  not-accessible
			  STATUS  current
			  DESCRIPTION "No description available"
			  INDEX   { mgIndex }
			  ::= { mgConnectedClientsTable 1 }

	  MgConnectedClientsEntry ::=
	          SEQUENCE {
				mgIndex
				      Unsigned32,
				mgClientName
				      DisplayString,
				mgClientHost
					  DisplayString,
				mgClientDbLock
				      DisplayString,
				mgApplicationType
				      DisplayString
			  }

      mgIndex OBJECT-TYPE
              SYNTAX  Unsigned32
              MAX-ACCESS not-accessible
              STATUS  current
              DESCRIPTION "No description available"
              ::= { mgConnectedClientsEntry 1 }

      mgClientName OBJECT-TYPE
              SYNTAX  DisplayString
              MAX-ACCESS read-only
              STATUS  current
              DESCRIPTION "No description available"
              ::= { mgConnectedClientsEntry 2 }

      mgClientHost OBJECT-TYPE
              SYNTAX  DisplayString
              MAX-ACCESS read-only
              STATUS  current
              DESCRIPTION "No description available"
              ::= { mgConnectedClientsEntry 3 }

      mgClientDbLock OBJECT-TYPE
              SYNTAX  DisplayString
              MAX-ACCESS read-only
              STATUS  current
              DESCRIPTION "No description available"
              ::= { mgConnectedClientsEntry 4 }

      mgApplicationType OBJECT-TYPE
              SYNTAX  DisplayString
              MAX-ACCESS read-only
              STATUS  current
              DESCRIPTION "No description available"
              ::= { mgConnectedClientsEntry 5 }

	  mgLogServerInfo  OBJECT IDENTIFIER ::= { mngmt 14 }

	  mgLSLogReceiveRate OBJECT-TYPE
              SYNTAX  Unsigned32
			  MAX-ACCESS  not-accessible
			  STATUS  current
			  DESCRIPTION "MGMT Log Server Log Receive Rate"
			  ::= { mgLogServerInfo 1 }

	  mgLSLogReceiveRatePeak OBJECT-TYPE
              SYNTAX  Unsigned32
			  MAX-ACCESS  not-accessible
			  STATUS  current
			  DESCRIPTION "MGMT Log Server Log Receive Rate Peak"
			  ::= { mgLogServerInfo 2 }

	  mgLSLogReceiveRate10Min OBJECT-TYPE
              SYNTAX  Unsigned32
			  MAX-ACCESS  not-accessible
			  STATUS  current
			  DESCRIPTION "MGMT Log Server Log Receive Rate (Last 10 Minutes)"
			  ::= { mgLogServerInfo 3 }

	  mgConnectedGatewaysTable OBJECT-TYPE
              SYNTAX  SEQUENCE OF  MgLsConnectedGatewaysEntry
			  MAX-ACCESS  not-accessible
			  STATUS  current
			  DESCRIPTION "Connected Gateways Table"
			  ::= { mgLogServerInfo 4 }

	  mgConnectedGatewaysEntry OBJECT-TYPE
	          SYNTAX MgLsConnectedGatewaysEntry
			  MAX-ACCESS  not-accessible
			  STATUS  current
			  DESCRIPTION "No description available"
			  INDEX   { mglsGWIndex }
			  ::= { mgConnectedGatewaysTable 1 }

	  MgLsConnectedGatewaysEntry ::=
	          SEQUENCE {
				mglsGWIndex
				      Unsigned32,
				mglsGWIP
				      DisplayString,
				mglsGWState
					  DisplayString,
				mglsGWLastLoginTime
				      DisplayString,
				mglsGWLogReceiveRate
				      Unsigned32
			  }

      mglsGWIndex OBJECT-TYPE
              SYNTAX  Unsigned32
              MAX-ACCESS not-accessible
              STATUS  current
              DESCRIPTION "No description available"
              ::= { mgConnectedGatewaysEntry 1 }

      mglsGWIP OBJECT-TYPE
              SYNTAX  DisplayString
              MAX-ACCESS read-only
              STATUS  current
              DESCRIPTION "No description available"
              ::= { mgConnectedGatewaysEntry 2 }

      mglsGWState OBJECT-TYPE
              SYNTAX  DisplayString
              MAX-ACCESS read-only
              STATUS  current
              DESCRIPTION "No description available"
              ::= { mgConnectedGatewaysEntry 3 }

      mglsGWLastLoginTime OBJECT-TYPE
              SYNTAX  DisplayString
              MAX-ACCESS read-only
              STATUS  current
              DESCRIPTION "No description available"
              ::= { mgConnectedGatewaysEntry 4 }

      mglsGWLogReceiveRate OBJECT-TYPE
              SYNTAX  Unsigned32
              MAX-ACCESS read-only
              STATUS  current
              DESCRIPTION "No description available"
              ::= { mgConnectedGatewaysEntry 5 }

	  mgIndexerInfo  OBJECT IDENTIFIER ::= { mgLogServerInfo 5 }

	  mgIndexerInfoTotalReadLogs OBJECT-TYPE
              SYNTAX  DisplayString
			  MAX-ACCESS  not-accessible
			  STATUS  current
			  DESCRIPTION "Total Read Logs"
			  ::= { mgIndexerInfo 1 }

	  mgIndexerInfoTotalUpdatesAndLogsIndexed OBJECT-TYPE
              SYNTAX  DisplayString
			  MAX-ACCESS  not-accessible
			  STATUS  current
			  DESCRIPTION "Total Updates and Logs Indexed"
			  ::= { mgIndexerInfo 2 }

	  mgIndexerInfoTotalReadLogsErrors OBJECT-TYPE
              SYNTAX  DisplayString
			  MAX-ACCESS  not-accessible
			  STATUS  current
			  DESCRIPTION "Total Read Logs Errors"
			  ::= { mgIndexerInfo 3 }

	  mgIndexerInfoTotalUpdatesAndLogsIndexedErrors OBJECT-TYPE
              SYNTAX  DisplayString
			  MAX-ACCESS  not-accessible
			  STATUS  current
			  DESCRIPTION "Total Updates and Logs Indexed Errors"
			  ::= { mgIndexerInfo 4 }

	  mgIndexerInfoUpdatesAndLogsIndexedRate OBJECT-TYPE
              SYNTAX  Unsigned32
			  MAX-ACCESS  not-accessible
			  STATUS  current
			  DESCRIPTION "Updates and Logs Indexed Rate"
			  ::= { mgIndexerInfo 5 }

	  mgIndexerInfoReadLogsRate OBJECT-TYPE
              SYNTAX  Unsigned32
			  MAX-ACCESS  not-accessible
			  STATUS  current
			  DESCRIPTION "Read Logs Rate"
			  ::= { mgIndexerInfo 6 }

	  mgIndexerInfoUpdatesAndLogsIndexedRate10min OBJECT-TYPE
              SYNTAX  Unsigned32
			  MAX-ACCESS  not-accessible
			  STATUS  current
			  DESCRIPTION "Updates and Logs Indexed Rate (10 min)"
			  ::= { mgIndexerInfo 7 }

	  mgIndexerInfoReadLogsRate10min OBJECT-TYPE
              SYNTAX  Unsigned32
			  MAX-ACCESS  not-accessible
			  STATUS  current
			  DESCRIPTION "Read Logs Rate  (10 min)"
			  ::= { mgIndexerInfo 8 }

	  mgIndexerInfoUpdatesAndLogsIndexedRate60min OBJECT-TYPE
              SYNTAX  Unsigned32
			  MAX-ACCESS  not-accessible
			  STATUS  current
			  DESCRIPTION "Updates and Logs Indexed Rate (60 min)"
			  ::= { mgIndexerInfo 9 }

	  mgIndexerInfoReadLogsRate60min OBJECT-TYPE
              SYNTAX  Unsigned32
			  MAX-ACCESS  not-accessible
			  STATUS  current
			  DESCRIPTION "Read Logs Rate (60 min)"
			  ::= { mgIndexerInfo 10 }


	  mgIndexerInfoUpdatesAndLogsIndexedRatePeak OBJECT-TYPE
              SYNTAX  Unsigned32
			  MAX-ACCESS  not-accessible
			  STATUS  current
			  DESCRIPTION "Updates and Logs Indexed Rate Peak"
			  ::= { mgIndexerInfo 11 }

	  mgIndexerInfoReadLogsRatePeak OBJECT-TYPE
              SYNTAX  Unsigned32
			  MAX-ACCESS  not-accessible
			  STATUS  current
			  DESCRIPTION "Read Logs Rate Peak"
			  ::= { mgIndexerInfo 12 }

	  mgIndexerInfoReadLogsDelay OBJECT-TYPE
              SYNTAX  Unsigned32
			  MAX-ACCESS  not-accessible
			  STATUS  current
			  DESCRIPTION "Read Logs Delay"
			  ::= { mgIndexerInfo 13 }

      mgStatCode OBJECT-TYPE
      		  SYNTAX  Integer32
      		  MAX-ACCESS read-only
      		  STATUS  current
	          DESCRIPTION
	        	   "Status code"
      		  ::= { mngmt 101 }

      mgStatShortDescr OBJECT-TYPE
      		  SYNTAX  DisplayString (SIZE (0..255))
      		  MAX-ACCESS read-only
      		  STATUS  current
	          DESCRIPTION
	        	   "Status short description"
      		  ::= { mngmt 102 }

      mgStatLongDescr OBJECT-TYPE
      		  SYNTAX  DisplayString (SIZE (0..255))
      		  MAX-ACCESS read-only
      		  STATUS  current
	          DESCRIPTION
	        	   "Status long description"
      		  ::= { mngmt 103 }

	  mgLSLogReceiveRate1Hour OBJECT-TYPE
		  SYNTAX  Unsigned32
		  MAX-ACCESS  not-accessible
		  STATUS  current
		  DESCRIPTION "MGMT Log Server Log Receive Rate (Last Hour)"
		  ::= { mgLogServerInfo 6 }

      -- the WAM Status
	  -- Overall statistics and state

      wamPluginPerformance   OBJECT IDENTIFIER ::= { wam 6 }
	  wamPolicy              OBJECT IDENTIFIER ::= { wam 7 }
	  wamUagQueries          OBJECT IDENTIFIER ::= { wam 8 }
	  wamGlobalPerformance   OBJECT IDENTIFIER ::= { wam 9 }

      wamProdName OBJECT-TYPE
      		  SYNTAX  DisplayString (SIZE (0..255))
      		  MAX-ACCESS read-only
      		  STATUS  current
	          DESCRIPTION
	        	   "Product name"
      		  ::= { wam 1 }

      wamVerMajor OBJECT-TYPE
      		  SYNTAX  Integer32
      		  MAX-ACCESS read-only
      		  STATUS  current
	          DESCRIPTION
	        	   "Major version"
      		  ::= { wam 2 }

      wamVerMinor OBJECT-TYPE
      		  SYNTAX  Integer32
      		  MAX-ACCESS read-only
      		  STATUS  current
	          DESCRIPTION
	        	   "Minor version"
      		  ::= { wam 3 }

      wamState OBJECT-TYPE
      		  SYNTAX  DisplayString (SIZE (0..255))
      		  MAX-ACCESS read-only
      		  STATUS  current
	          DESCRIPTION
	        	   "WAM state"
      		  ::= { wam 4 }

      wamName OBJECT-TYPE
      		  SYNTAX  DisplayString (SIZE (0..255))
      		  MAX-ACCESS read-only
      		  STATUS  current
	          DESCRIPTION
	        	   "WAM name"
      		  ::= { wam 5 }

      wamStatCode OBJECT-TYPE
      		  SYNTAX  Integer32
      		  MAX-ACCESS read-only
      		  STATUS  current
	          DESCRIPTION
	        	   "WAM status code"
      		  ::= { wam 101 }

      wamStatShortDescr OBJECT-TYPE
      		  SYNTAX  DisplayString (SIZE (0..255))
      		  MAX-ACCESS read-only
      		  STATUS  current
	          DESCRIPTION
	        	   "WAM status short description"
      		  ::= { wam 102 }

      wamStatLongDescr OBJECT-TYPE
      		  SYNTAX  DisplayString (SIZE (0..255))
      		  MAX-ACCESS read-only
      		  STATUS  current
	          DESCRIPTION
	        	   "WAM status full description"
      		  ::= { wam 103 }

      wamAcceptReq OBJECT-TYPE
      		  SYNTAX  Integer32
      		  MAX-ACCESS read-only
      		  STATUS  current
	          DESCRIPTION
	        	   "Plugin accepted requests"
      		  ::= { wamPluginPerformance 1 }

      wamRejectReq OBJECT-TYPE
      		  SYNTAX  Integer32
      		  MAX-ACCESS read-only
      		  STATUS  current
	          DESCRIPTION
	        	   "Plugin rejected requests"
      		  ::= { wamPluginPerformance 2 }

      wamPolicyName OBJECT-TYPE
      		  SYNTAX  DisplayString (SIZE (0..255))
      		  MAX-ACCESS read-only
      		  STATUS  current
	          DESCRIPTION
	        	   "Policy name"
      		  ::= { wamPolicy 1 }

      wamPolicyUpdate OBJECT-TYPE
      		  SYNTAX  DisplayString (SIZE (0..255))
      		  MAX-ACCESS read-only
      		  STATUS  current
	          DESCRIPTION
	        	   "Last update time"
      		  ::= { wamPolicy 2 }

      wamUagHost OBJECT-TYPE
      		  SYNTAX  DisplayString (SIZE (0..255))
      		  MAX-ACCESS read-only
      		  STATUS  current
	          DESCRIPTION
	        	   "UAG host name"
      		  ::= { wamUagQueries 1 }

      wamUagIp OBJECT-TYPE
      		  SYNTAX  Integer32
      		  MAX-ACCESS read-only
      		  STATUS  current
	          DESCRIPTION
	        	   "UAG IP address"
      		  ::= { wamUagQueries 2 }

      wamUagPort OBJECT-TYPE
      		  SYNTAX  Integer32
      		  MAX-ACCESS read-only
      		  STATUS  current
	          DESCRIPTION
	        	   "UAG port"
      		  ::= { wamUagQueries 3 }

      wamUagNoQueries OBJECT-TYPE
      		  SYNTAX  Integer32
      		  MAX-ACCESS read-only
      		  STATUS  current
	          DESCRIPTION
	        	   "UAG no. of queries"
      		  ::= { wamUagQueries 4 }

      wamUagLastQuery OBJECT-TYPE
      		  SYNTAX  DisplayString (SIZE (0..255))
      		  MAX-ACCESS read-only
      		  STATUS  current
	          DESCRIPTION
	        	   "UAG last query time"
      		  ::= { wamUagQueries 5 }

      wamOpenSessions OBJECT-TYPE
      		  SYNTAX  Integer32
      		  MAX-ACCESS read-only
      		  STATUS  current
	          DESCRIPTION
	        	   "Open sessions"
      		  ::= { wamGlobalPerformance 1 }

      wamLastSession OBJECT-TYPE
      		  SYNTAX  DisplayString (SIZE (0..255))
      		  MAX-ACCESS read-only
      		  STATUS  current
	          DESCRIPTION
	        	   "Last open session time"
      		  ::= { wamGlobalPerformance 2 }


      -- the Desktop Policy Server Status
	  -- Overall statistics and state

      dtpsProdName OBJECT-TYPE
      		  SYNTAX  DisplayString (SIZE (0..255))
      		  MAX-ACCESS read-only
      		  STATUS  current
	          DESCRIPTION
	        	   "Product name"
      		  ::= { dtps 1 }

      dtpsVerMajor OBJECT-TYPE
      		  SYNTAX  Gauge32
      		  MAX-ACCESS read-only
      		  STATUS  current
	          DESCRIPTION
	        	   "Major version"
      		  ::= { dtps 2 }

      dtpsVerMinor OBJECT-TYPE
      		  SYNTAX  Gauge32
      		  MAX-ACCESS read-only
      		  STATUS  current
	          DESCRIPTION
	        	   "Minor version"
      		  ::= { dtps 3 }

      dtpsLicensedUsers OBJECT-TYPE
      		  SYNTAX  Unsigned32
      		  MAX-ACCESS read-only
      		  STATUS  current
	          DESCRIPTION
	        	   "Licensed users"
      		  ::= { dtps 4 }

      dtpsConnectedUsers OBJECT-TYPE
      		  SYNTAX  Unsigned32
      		  MAX-ACCESS read-only
      		  STATUS  current
	          DESCRIPTION
	        	   "Connected users"
      		  ::= { dtps 5 }

      dtpsStatCode OBJECT-TYPE
      		  SYNTAX  Gauge32
      		  MAX-ACCESS read-only
      		  STATUS  current
	          DESCRIPTION
	        	   "Status code"
      		  ::= { dtps 101 }

      dtpsStatShortDescr OBJECT-TYPE
      		  SYNTAX  DisplayString (SIZE (0..255))
      		  MAX-ACCESS read-only
      		  STATUS  current
	          DESCRIPTION
	        	   "Status short description"
      		  ::= { dtps 102 }

      dtpsStatLongDescr OBJECT-TYPE
      		  SYNTAX  DisplayString (SIZE (0..255))
      		  MAX-ACCESS read-only
      		  STATUS  current
	          DESCRIPTION
	        	   "Status long description"
      		  ::= { dtps 103 }

      -- the Log Server Status
	  -- Overall statistics and state

      lsProdName OBJECT-TYPE
      		  SYNTAX  DisplayString (SIZE (0..255))
      		  MAX-ACCESS read-only
      		  STATUS  current
	          DESCRIPTION
	        	   "Product name"
      		  ::= { ls 1 }

      lsVerMajor OBJECT-TYPE
      		  SYNTAX  Integer32
      		  MAX-ACCESS read-only
      		  STATUS  current
	          DESCRIPTION
	        	   "Major version"
      		  ::= { ls 2 }

      lsVerMinor OBJECT-TYPE
      		  SYNTAX  Integer32
      		  MAX-ACCESS read-only
      		  STATUS  current
	          DESCRIPTION
	        	   "Minor version"
      		  ::= { ls 3 }

      lsBuildNumber OBJECT-TYPE
      		  SYNTAX  Integer32
      		  MAX-ACCESS read-only
      		  STATUS  current
	          DESCRIPTION
	        	   "Build number"
      		  ::= { ls 4 }

      lsFwmIsAlive OBJECT-TYPE
      		  SYNTAX  Integer32
      		  MAX-ACCESS read-only
      		  STATUS  current
	          DESCRIPTION
	        	   "Log Server is alive"
      		  ::= { ls 5 }

	  lsLoggingInfo  OBJECT IDENTIFIER ::= { ls 14 }

	  lsLogReceiveRate OBJECT-TYPE
              SYNTAX  Unsigned32
			  MAX-ACCESS  not-accessible
			  STATUS  current
			  DESCRIPTION "Log Server Log Receive Rate"
			  ::= { lsLoggingInfo 1 }

	  lsLogReceiveRatePeak OBJECT-TYPE
              SYNTAX  Unsigned32
			  MAX-ACCESS  not-accessible
			  STATUS  current
			  DESCRIPTION "Log Server Log Receive Rate Peak"
			  ::= { lsLoggingInfo 2 }

	  lsLogReceiveRate10Min OBJECT-TYPE
              SYNTAX  Unsigned32
			  MAX-ACCESS  not-accessible
			  STATUS  current
			  DESCRIPTION "Log Server Log Receive Rate (Last 10 Minutes)"
			  ::= { lsLoggingInfo 3 }

	  lsConnectedGatewaysTable OBJECT-TYPE
              SYNTAX  SEQUENCE OF  LsConnectedGatewaysEntry
			  MAX-ACCESS  not-accessible
			  STATUS  current
			  DESCRIPTION "Connected Gateways Table"
			  ::= { lsLoggingInfo 4 }

	  lsConnectedGatewaysEntry OBJECT-TYPE
	          SYNTAX LsConnectedGatewaysEntry
			  MAX-ACCESS  not-accessible
			  STATUS  current
			  DESCRIPTION "No description available"
			  INDEX   { lsGWIndex }
			  ::= { lsConnectedGatewaysTable 1 }

	  LsConnectedGatewaysEntry ::=
	          SEQUENCE {
				lsGWIndex
				      Unsigned32,
				lsGWIP
				      DisplayString,
				lsGWState
					  DisplayString,
				lsGWLastLoginTime
				      DisplayString,
				lsGWLogReceiveRate
				      Unsigned32
			  }

      lsGWIndex OBJECT-TYPE
              SYNTAX  Unsigned32
              MAX-ACCESS not-accessible
              STATUS  current
              DESCRIPTION "No description available"
              ::= { lsConnectedGatewaysEntry 1 }

      lsGWIP OBJECT-TYPE
              SYNTAX  DisplayString
              MAX-ACCESS read-only
              STATUS  current
              DESCRIPTION "No description available"
              ::= { lsConnectedGatewaysEntry 2 }

      lsGWState OBJECT-TYPE
              SYNTAX  DisplayString
              MAX-ACCESS read-only
              STATUS  current
              DESCRIPTION "No description available"
              ::= { lsConnectedGatewaysEntry 3 }

      lsGWLastLoginTime OBJECT-TYPE
              SYNTAX  DisplayString
              MAX-ACCESS read-only
              STATUS  current
              DESCRIPTION "No description available"
              ::= { lsConnectedGatewaysEntry 4 }

      lsGWLogReceiveRate OBJECT-TYPE
              SYNTAX  Unsigned32
              MAX-ACCESS read-only
              STATUS  current
              DESCRIPTION "No description available"
              ::= { lsConnectedGatewaysEntry 5 }

	  lsIndexerInfo  OBJECT IDENTIFIER ::= { lsLoggingInfo 5 }

	  lsIndexerInfoTotalReadLogs OBJECT-TYPE
              SYNTAX  Unsigned32
			  MAX-ACCESS  not-accessible
			  STATUS  current
			  DESCRIPTION "Total Read Logs"
			  ::= { lsIndexerInfo 1 }

	  lsIndexerInfoTotalUpdatesAndLogsIndexed OBJECT-TYPE
              SYNTAX  Unsigned32
			  MAX-ACCESS  not-accessible
			  STATUS  current
			  DESCRIPTION "Total Updates and Logs Indexed"
			  ::= { lsIndexerInfo 2 }

	  lsIndexerInfoTotalReadLogsErrors OBJECT-TYPE
              SYNTAX  Unsigned32
			  MAX-ACCESS  not-accessible
			  STATUS  current
			  DESCRIPTION "Total Read Logs Errors"
			  ::= { lsIndexerInfo 3 }

	  lsIndexerInfoTotalUpdatesAndLogsIndexedErrors OBJECT-TYPE
              SYNTAX  Unsigned32
			  MAX-ACCESS  not-accessible
			  STATUS  current
			  DESCRIPTION "Total Updates and Logs Indexed Errors"
			  ::= { lsIndexerInfo 4 }

	  lsIndexerInfoUpdatesAndLogsIndexedRate OBJECT-TYPE
              SYNTAX  Unsigned32
			  MAX-ACCESS  not-accessible
			  STATUS  current
			  DESCRIPTION "Updates and Logs Indexed Rate"
			  ::= { lsIndexerInfo 5 }

	  lsIndexerInfoReadLogsRate OBJECT-TYPE
              SYNTAX  Unsigned32
			  MAX-ACCESS  not-accessible
			  STATUS  current
			  DESCRIPTION "Read Logs Rate"
			  ::= { lsIndexerInfo 6 }

	  lsIndexerInfoUpdatesAndLogsIndexedRatePeak OBJECT-TYPE
              SYNTAX  Unsigned32
			  MAX-ACCESS  not-accessible
			  STATUS  current
			  DESCRIPTION "Updates and Logs Indexed Rate Peak"
			  ::= { lsIndexerInfo 7 }

	  lsIndexerInfoReadLogsRatePeak OBJECT-TYPE
              SYNTAX  Unsigned32
			  MAX-ACCESS  not-accessible
			  STATUS  current
			  DESCRIPTION "Read Logs Rate Peak"
			  ::= { lsIndexerInfo 8 }

	  lsLogReceiveRate1Hour OBJECT-TYPE
              SYNTAX  Unsigned32
			  MAX-ACCESS  not-accessible
			  STATUS  current
			  DESCRIPTION "Log Server Log Receive Rate (Last Hour)"
			  ::= { lsLoggingInfo 6 }

      lsStatCode OBJECT-TYPE
      		  SYNTAX  Integer32
      		  MAX-ACCESS read-only
      		  STATUS  current
	          DESCRIPTION
	        	   "Status code"
      		  ::= { ls 101 }

      lsStatShortDescr OBJECT-TYPE
      		  SYNTAX  DisplayString (SIZE (0..255))
      		  MAX-ACCESS read-only
      		  STATUS  current
	          DESCRIPTION
	        	   "Status short description"
      		  ::= { ls 102 }

      lsStatLongDescr OBJECT-TYPE
      		  SYNTAX  DisplayString (SIZE (0..255))
      		  MAX-ACCESS read-only
      		  STATUS  current
	          DESCRIPTION
	        	   "Status long description"
      		  ::= { ls 103 }

	  lsConnectedClientsTable OBJECT-TYPE
              SYNTAX  SEQUENCE OF  LSConnectedClientsEntry
			  MAX-ACCESS  not-accessible
			  STATUS  current
			  DESCRIPTION "No description available"
			  ::= { ls 7 }

	  lsConnectedClientsEntry OBJECT-TYPE
	          SYNTAX LSConnectedClientsEntry
			  MAX-ACCESS  not-accessible
			  STATUS  current
			  DESCRIPTION "No description available"
			  INDEX   { lsIndex }
			  ::= { lsConnectedClientsTable 1 }

	  LSConnectedClientsEntry ::=
	          SEQUENCE {
				lsIndex
				      Unsigned32,
				lsClientName
				      DisplayString,
				lsClientHost
					  DisplayString,
				lsClientDbLock
				      DisplayString,
				lsApplicationType
				      DisplayString
			  }

      lsIndex OBJECT-TYPE
              SYNTAX  Unsigned32
              MAX-ACCESS not-accessible
              STATUS  current
              DESCRIPTION "No description available"
              ::= { lsConnectedClientsEntry 1 }

      lsClientName OBJECT-TYPE
              SYNTAX  DisplayString
              MAX-ACCESS read-only
              STATUS  current
              DESCRIPTION "No description available"
              ::= { lsConnectedClientsEntry 2 }

      lsClientHost OBJECT-TYPE
              SYNTAX  DisplayString
              MAX-ACCESS read-only
              STATUS  current
              DESCRIPTION "No description available"
              ::= { lsConnectedClientsEntry 3 }

      lsClientDbLock OBJECT-TYPE
              SYNTAX  DisplayString
              MAX-ACCESS read-only
              STATUS  current
              DESCRIPTION "No description available"
              ::= { lsConnectedClientsEntry 4 }

      lsApplicationType OBJECT-TYPE
              SYNTAX  DisplayString
              MAX-ACCESS read-only
              STATUS  current
              DESCRIPTION "No description available"
              ::= { lsConnectedClientsEntry 5 }
--
			  -- the GX status
	  -- Overall statistics and state

      gxInfo            OBJECT IDENTIFIER ::= { gx 1 }
	  gxCreateInfo      OBJECT IDENTIFIER ::= { gx 5 }
	  gxDeleteInfo      OBJECT IDENTIFIER ::= { gx 6 }
	  gxUpdateInfo      OBJECT IDENTIFIER ::= { gx 7 }
	  gxPathMngInfo     OBJECT IDENTIFIER ::= { gx 8 }
	  gxGpduInfo        OBJECT IDENTIFIER ::= { gx 9 }
	  gxInitiateInfo    OBJECT IDENTIFIER ::= { gx 10 }
	  gxGTPv2CreateInfo OBJECT IDENTIFIER ::= { gx 11 }
	  gxGTPv2DeleteInfo OBJECT IDENTIFIER ::= { gx 12 }
	  gxGTPv2UpdateInfo OBJECT IDENTIFIER ::= { gx 13 }
	  gxGTPv2PathMngInfo OBJECT IDENTIFIER ::= { gx 14 }
	  gxGTPv2CmdInfo OBJECT IDENTIFIER ::= { gx 15 }


	  gxProdName OBJECT-TYPE
	        SYNTAX  DisplayString (SIZE (0..255))
	        MAX-ACCESS  read-only
	        STATUS  current
	        DESCRIPTION
	        	   "Product name"
	        ::= { gxInfo 1 }

	  gxProdVersion OBJECT-TYPE
	        SYNTAX  DisplayString (SIZE (0..255))
	        MAX-ACCESS  read-only
	        STATUS  current
	        DESCRIPTION
	        	   "Product Version"
	        ::= { gxInfo 2 }

	  gxProdVerMajor OBJECT-TYPE
	        SYNTAX  Integer32
	        MAX-ACCESS  read-only
	        STATUS  current
	        DESCRIPTION
	        	   "Major version"
	        ::= { gx 2 }

	  gxProdVerMinor OBJECT-TYPE
	        SYNTAX  Integer32
	        MAX-ACCESS  read-only
	        STATUS  current
	        DESCRIPTION
	        	   "Minor version"
	        ::= { gx 3 }

	  gxBuild OBJECT-TYPE
	        SYNTAX  Integer32
	        MAX-ACCESS  read-only
	        STATUS  current
	        DESCRIPTION
	        	   "GX build number"
	        ::= { gx 4 }

	  gxCreateSinceInstall OBJECT-TYPE
	        SYNTAX  Integer32
	        MAX-ACCESS  read-only
	        STATUS  current
	        DESCRIPTION
	        	   "Total success create contexts since install policy"
	        ::= { gxCreateInfo 1 }

	  gxActContxt OBJECT-TYPE
	  		  SYNTAX  Integer32
			  MAX-ACCESS  read-only
			  STATUS  current
			  DESCRIPTION
					 "Total active contexts"
			  ::= { gxCreateInfo 2 }

	  gxDropPlicyCreate OBJECT-TYPE
	  		  SYNTAX  Integer32
			  MAX-ACCESS  read-only
			  STATUS  current
			  DESCRIPTION
					 "Total dropped create messages due to policy violation"
			  ::= { gxCreateInfo 3 }

	  gxDropMalformedReqCreate OBJECT-TYPE
	  		  SYNTAX  Integer32
			  MAX-ACCESS  read-only
			  STATUS  current
			  DESCRIPTION
					 "Total dropped create messages due to malformed create-request"
			  ::= { gxCreateInfo 4 }

	  gxDropMalformedRespCreate OBJECT-TYPE
	  		  SYNTAX  Integer32
			  MAX-ACCESS  read-only
			  STATUS  current
			  DESCRIPTION
					 "Total dropped create messages due to malformed create-response"
			  ::= { gxCreateInfo 5 }

	  gxExpiredCreate OBJECT-TYPE
	  		  SYNTAX  Integer32
			  MAX-ACCESS  read-only
			  STATUS  current
			  DESCRIPTION
					 "Total time-out expired create messages "
			  ::= { gxCreateInfo 6 }

	  gxBadCauseCreate OBJECT-TYPE
	  		  SYNTAX  Integer32
			  MAX-ACCESS  read-only
			  STATUS  current
			  DESCRIPTION
					 "Total bad cause create messages"
			  ::= { gxCreateInfo 7	 }

	  gxSecondaryNsapiEntries OBJECT-TYPE

	  		  SYNTAX  Integer32
			  MAX-ACCESS  read-only
			  STATUS  current
			  DESCRIPTION
					 "Total entries in gtp_secondary_nsapi"
			  ::= { gxCreateInfo 8	 }

	  gxActv0v1PdnConns OBJECT-TYPE
	  		  SYNTAX  Integer32
			  MAX-ACCESS  read-only
			  STATUS  current
			  DESCRIPTION
					 "Total active v0 v1 PDN connections"
			  ::= { gxCreateInfo 11 }

	  gxTunnelApnsEntries OBJECT-TYPE

	  		  SYNTAX  Integer32
			  MAX-ACCESS  read-only
			  STATUS  current
			  DESCRIPTION
					 "Total entries in gtp_tunnel_apns"
			  ::= { gxCreateInfo 12	 }

	  gxTunnelsEntries OBJECT-TYPE

	  		  SYNTAX  Integer32
			  MAX-ACCESS  read-only
			  STATUS  current
			  DESCRIPTION
					 "Total entries in gtp_tunnels"
			  ::= { gxCreateInfo 13	 }

	  gxDeleteSinceInstall OBJECT-TYPE
	        SYNTAX  Integer32
	        MAX-ACCESS  read-only
	        STATUS  current
	        DESCRIPTION
	        	   "Total success delete messages since install policy"
	        ::= { gxDeleteInfo 1 }

	  gxDropOutOfContxtDelete OBJECT-TYPE
	  		  SYNTAX  Integer32
			  MAX-ACCESS  read-only
			  STATUS  current
			  DESCRIPTION
					 "Total dropped out of context delete messages"
			  ::= { gxDeleteInfo 2 }


	  gxDropMalformedReqDelete OBJECT-TYPE
	  		  SYNTAX  Integer32
			  MAX-ACCESS  read-only
			  STATUS  current
			  DESCRIPTION
					 "Total dropped delete messages due to malformed delete-request"
			  ::= { gxDeleteInfo 3 }

	  gxDropMalformedRespDelete OBJECT-TYPE
	  		  SYNTAX  Integer32
			  MAX-ACCESS  read-only
			  STATUS  current
			  DESCRIPTION
					 "Total dropped delete messages due to malformed delete-response"
			  ::= { gxDeleteInfo 4 }

	  gxExpiredDelete OBJECT-TYPE
	  		  SYNTAX  Integer32
			  MAX-ACCESS  read-only
			  STATUS  current
			  DESCRIPTION
					 "Total time-out expired delete messages "
			  ::= { gxDeleteInfo 5 }

	  gxBadCauseDelete OBJECT-TYPE
	  		  SYNTAX  Integer32
			  MAX-ACCESS  read-only
			  STATUS  current
			  DESCRIPTION
					 "Total bad cause delete messages"
			  ::= { gxDeleteInfo 6	 }

	  gxUpdateSinceInstall OBJECT-TYPE
	        SYNTAX  Integer32
	        MAX-ACCESS  read-only
	        STATUS  current
	        DESCRIPTION
	        	   "Total success update messages since install policy"
	        ::= { gxUpdateInfo 1 }

	  gxDropOutOfContxtUpdate OBJECT-TYPE
	  		  SYNTAX  Integer32
			  MAX-ACCESS  read-only
			  STATUS  current
			  DESCRIPTION
					 "Total dropped out of context update messages"
			  ::= { gxUpdateInfo 2 }


	  gxDropMalformedReqUpdate OBJECT-TYPE
	  		  SYNTAX  Integer32
			  MAX-ACCESS  read-only
			  STATUS  current
			  DESCRIPTION
					 "Total dropped update messages due to malformed update-request"
			  ::= { gxUpdateInfo 3 }

	  gxDropMalformedRespUpdate OBJECT-TYPE
	  		  SYNTAX  Integer32
			  MAX-ACCESS  read-only
			  STATUS  current
			  DESCRIPTION
					 "Total dropped update messages due to malformed update-response"
			  ::= { gxUpdateInfo 4 }

	  gxExpiredUpdate OBJECT-TYPE
	  		  SYNTAX  Integer32
			  MAX-ACCESS  read-only
			  STATUS  current
			  DESCRIPTION
					 "Total time-out expired update messages "
			  ::= { gxUpdateInfo 5 }

	  gxBadCauseUpdate OBJECT-TYPE
	  		  SYNTAX  Integer32
			  MAX-ACCESS  read-only
			  STATUS  current
			  DESCRIPTION
					 "Total bad cause update messages"
			  ::= { gxUpdateInfo 6	 }

	  gxEchoSinceInstall OBJECT-TYPE
	        SYNTAX  Integer32
	        MAX-ACCESS  read-only
	        STATUS  current
	        DESCRIPTION
	        	   "Total success echo messages since install policy"
	        ::= { gxPathMngInfo 1 }

	  gxVnspSinceInstall OBJECT-TYPE
	  		  SYNTAX  Integer32
			  MAX-ACCESS  read-only
			  STATUS  current
			  DESCRIPTION
					 "Total success vnsp messages since install policy"
			  ::= { gxPathMngInfo 2 }


	  gxDropPolicyEcho OBJECT-TYPE
	  		  SYNTAX  Integer32
			  MAX-ACCESS  read-only
			  STATUS  current
			  DESCRIPTION
					 "Total dropped echo messages due to policy violation"
			  ::= { gxPathMngInfo 3 }

	  gxDropMalformedReqEcho OBJECT-TYPE
	  		  SYNTAX  Integer32
			  MAX-ACCESS  read-only
			  STATUS  current
			  DESCRIPTION
					 "Total dropped echo messages due to malformed echo-request"
			  ::= { gxPathMngInfo 4 }

	  gxDropMalformedRespEcho OBJECT-TYPE
	  		  SYNTAX  Integer32
			  MAX-ACCESS  read-only
			  STATUS  current
			  DESCRIPTION
					 "Total dropped echo messages due to malformed echo-response"
			  ::= { gxPathMngInfo 5 }

	  gxExpiredEcho OBJECT-TYPE
	  		  SYNTAX  Integer32
			  MAX-ACCESS  read-only
			  STATUS  current
			  DESCRIPTION
					 "Total time-out expired echo messages "
			  ::= { gxPathMngInfo 6}

	  gxDropVnsp OBJECT-TYPE
	  		  SYNTAX  Integer32
			  MAX-ACCESS  read-only
			  STATUS  current
			  DESCRIPTION
					 "Total dropped vnsp messages"
			  ::= { gxPathMngInfo 7	 }

  	  gxGtpPathEntries OBJECT-TYPE
	  		   SYNTAX  Integer32
			   MAX-ACCESS  read-only
			   STATUS  current
			   DESCRIPTION
			  		 "Total gtp path entries"
			   ::= { gxPathMngInfo 8 }


	  gxGpdu1MinAvgRate OBJECT-TYPE
	        SYNTAX  Integer32
	        MAX-ACCESS  read-only
	        STATUS  current
	        DESCRIPTION
	        	   "GPDU 1 minute average packet rate"
	        ::= { gxGpduInfo 1 }

	  gxDropOutOfContxtGpdu OBJECT-TYPE
	  		  SYNTAX  Integer32
			  MAX-ACCESS  read-only
			  STATUS  current
			  DESCRIPTION
					 "Total dropped out of context GPDU's "
			  ::= { gxGpduInfo 2 }


	  gxDropAnti-spoofingGpdu OBJECT-TYPE
	  		  SYNTAX  Integer32
			  MAX-ACCESS  read-only
			  STATUS  current
			  DESCRIPTION
					 "Total dropped GPDU's due to anti-spoofing"
			  ::= { gxGpduInfo 3 }

	  gxDropMs-MsGpdu OBJECT-TYPE
	  		  SYNTAX  Integer32
			  MAX-ACCESS  read-only
			  STATUS  current
			  DESCRIPTION
					 "Total dropped GPDU's due to ms-ms violation "
			  ::= { gxGpduInfo 4 }

	  gxDropBadSeqGpdu OBJECT-TYPE
	  		  SYNTAX  Integer32
			  MAX-ACCESS  read-only
			  STATUS  current
			  DESCRIPTION
					 "Total dropped GPDU's due bad sequence"
			  ::= { gxGpduInfo 5 }

	  gxDropBadGpdu OBJECT-TYPE
	  		  SYNTAX  Integer32
			  MAX-ACCESS  read-only
			  STATUS  current
			  DESCRIPTION
					 "Total dropped bad GPDU's"
			  ::= { gxGpduInfo 6}

	gxGpduExpiredTunnel OBJECT-TYPE
	  		  SYNTAX  Integer32
			  MAX-ACCESS  read-only
			  STATUS  current
			  DESCRIPTION
					 "Total expired GTP tunnels"
			  ::= { gxGpduInfo 7}

	gxInitiateSinceInstall OBJECT-TYPE
	  		   SYNTAX  Integer32
			   MAX-ACCESS  read-only
			   STATUS  current
			   DESCRIPTION
			  		 "Total successive initate activations since last install policy"
			   ::= { gxInitiateInfo 1}

	gxDropInitiationReq	  OBJECT-TYPE
	  		  SYNTAX  Integer32
			  MAX-ACCESS  read-only
			  STATUS  current
			  DESCRIPTION
					 "Total initate activation request messages droped "
			  ::= { gxInitiateInfo 2}

	  gxDropInitiationResp OBJECT-TYPE
	  		  SYNTAX  Integer32
			  MAX-ACCESS  read-only
			  STATUS  current
			  DESCRIPTION
					 "Total initate activation response messages droped"
			  ::= { gxInitiateInfo 3}

  	  gxExpiredInitiateAct OBJECT-TYPE
	  		   SYNTAX  Integer32
			   MAX-ACCESS  read-only
			   STATUS  current
			   DESCRIPTION
			  		 "Total time-out expired initate activations messages"
			   ::= { gxInitiateInfo 4}

	gxGTPv2CreateSessionSinceInstall OBJECT-TYPE
			SYNTAX  Integer32
			MAX-ACCESS  read-only
			STATUS  current
			DESCRIPTION
				   "Total success create session messages since install policy"
			::= { gxGTPv2CreateInfo 1 }

	gxGTPv2CreateBearerSinceInstall OBJECT-TYPE
			SYNTAX  Integer32
			MAX-ACCESS  read-only
			STATUS  current
			DESCRIPTION
				   "Total success create bearer messages since install policy"
			::= { gxGTPv2CreateInfo 2 }

	  gxGTPv2ExpiredCreateSession OBJECT-TYPE
	  		  SYNTAX  Integer32
			  MAX-ACCESS  read-only
			  STATUS  current
			  DESCRIPTION
					 "Total time-out expired create session messages "
			  ::= { gxGTPv2CreateInfo 3 }

	  gxGTPv2ExpiredCreateBearer OBJECT-TYPE
	  		  SYNTAX  Integer32
			  MAX-ACCESS  read-only
			  STATUS  current
			  DESCRIPTION
					 "Total time-out expired create bearer messages "
			  ::= { gxGTPv2CreateInfo 4 }

	  gxGTPv2DropMalformedCreateSessionReq OBJECT-TYPE
		  SYNTAX  Integer32
		  MAX-ACCESS  read-only
		  STATUS  current
		  DESCRIPTION
				 "Total dropped create session request messages due to malformed create-request"
		  ::= { gxGTPv2CreateInfo 5 }

	  gxGTPv2DropMalformedCreateSessionResp OBJECT-TYPE
		  SYNTAX  Integer32
		  MAX-ACCESS  read-only
		  STATUS  current
		  DESCRIPTION
				 "Total dropped create session response messages due to malformed create-response"
		  ::= { gxGTPv2CreateInfo 6 }

	  gxGTPv2DropMalformedCreateBearerReq OBJECT-TYPE
		  SYNTAX  Integer32
		  MAX-ACCESS  read-only
		  STATUS  current
		  DESCRIPTION
				 "Total dropped create bearer request messages due to malformed create-request"
		  ::= { gxGTPv2CreateInfo 7 }

	  gxGTPv2DropMalformedCreateBearerResp OBJECT-TYPE
		  SYNTAX  Integer32
		  MAX-ACCESS  read-only
		  STATUS  current
		  DESCRIPTION
				 "Total dropped create bearer response messages due to malformed create-response"
		  ::= { gxGTPv2CreateInfo 8 }

	  gxGTPv2DropPolicyCreateSession OBJECT-TYPE
		  SYNTAX  Integer32
		  MAX-ACCESS  read-only
		  STATUS  current
		  DESCRIPTION
				 "Total dropped create session messages due to policy violation"
		  ::= { gxGTPv2CreateInfo 9 }

	  gxGTPv2DropPolicyCreateBearer OBJECT-TYPE
		  SYNTAX  Integer32
		  MAX-ACCESS  read-only
		  STATUS  current
		  DESCRIPTION
				 "Total dropped create bearer messages due to policy violation"
		  ::= { gxGTPv2CreateInfo 10 }

	gxGTPv2ActPDN OBJECT-TYPE
			SYNTAX  Integer32
			MAX-ACCESS  read-only
			STATUS  current
			DESCRIPTION
				   "Total active GTPv2 PDN connections"
			::= { gxGTPv2CreateInfo 11 }

	gxGTPv2ActDataBearers OBJECT-TYPE
			SYNTAX  Integer32
			MAX-ACCESS  read-only
			STATUS  current
			DESCRIPTION
				   "Total active data bearers"
			::= { gxGTPv2CreateInfo 12 }

	gxGTPv2DeleteSessionSinceInstall OBJECT-TYPE
			SYNTAX  Integer32
			MAX-ACCESS  read-only
			STATUS  current
			DESCRIPTION
				   "Total success delete session messages since install policy"
			::= { gxGTPv2DeleteInfo 1 }

	gxGTPv2DeleteBearerSinceInstall OBJECT-TYPE
			SYNTAX  Integer32
			MAX-ACCESS  read-only
			STATUS  current
			DESCRIPTION
				   "Total success delete bearer messages since install policy"
			::= { gxGTPv2DeleteInfo 2 }

	  gxGTPv2ExpiredDeleteSession OBJECT-TYPE
		  SYNTAX  Integer32
		  MAX-ACCESS  read-only
		  STATUS  current
		  DESCRIPTION
				 "Total time-out expired delete session messages "
		  ::= { gxGTPv2DeleteInfo 3 }

	  gxGTPv2ExpiredDeleteBearer OBJECT-TYPE
		  SYNTAX  Integer32
		  MAX-ACCESS  read-only
		  STATUS  current
		  DESCRIPTION
				 "Total time-out expired delete bearer messages "
		  ::= { gxGTPv2DeleteInfo 4 }

	  gxGTPv2DropMalformedDeleteSessionReq OBJECT-TYPE
		  SYNTAX  Integer32
		  MAX-ACCESS  read-only
		  STATUS  current
		  DESCRIPTION
				 "Total dropped delete session request messages due to malformed delete-request"
		  ::= { gxGTPv2DeleteInfo 5 }

	  gxGTPv2DropMalformedDeleteSessionResp OBJECT-TYPE
		  SYNTAX  Integer32
		  MAX-ACCESS  read-only
		  STATUS  current
		  DESCRIPTION
				 "Total dropped delete session response messages due to malformed delete-response"
		  ::= { gxGTPv2DeleteInfo 6 }

	  gxGTPv2DropMalformedDeleteBearerReq OBJECT-TYPE
		  SYNTAX  Integer32
		  MAX-ACCESS  read-only
		  STATUS  current
		  DESCRIPTION
				 "Total dropped delete bearer request messages due to malformed delete-request"
		  ::= { gxGTPv2DeleteInfo 7 }

	  gxGTPv2DropMalformedDeleteBearerResp OBJECT-TYPE
		  SYNTAX  Integer32
		  MAX-ACCESS  read-only
		  STATUS  current
		  DESCRIPTION
				 "Total dropped delete bearer response messages due to malformed delete-response"
		  ::= { gxGTPv2DeleteInfo 8 }

	  gxGTPv2DropPolicyDeleteSession OBJECT-TYPE
		  SYNTAX  Integer32
		  MAX-ACCESS  read-only
		  STATUS  current
		  DESCRIPTION
				 "Total dropped delete session messages due to policy violation"
		  ::= { gxGTPv2DeleteInfo 9 }

	  gxGTPv2DropPolicyDeleteBearer OBJECT-TYPE
		  SYNTAX  Integer32
		  MAX-ACCESS  read-only
		  STATUS  current
		  DESCRIPTION
				 "Total dropped delete bearer messages due to policy violation"
		  ::= { gxGTPv2DeleteInfo 10 }

	gxGTPv2UpdateBearerSinceInstall OBJECT-TYPE
			SYNTAX  Integer32
			MAX-ACCESS  read-only
			STATUS  current
			DESCRIPTION
				   "Total success update bearer messages since install policy"
			::= { gxGTPv2UpdateInfo 1 }

	 gxGTPv2ExpiredUpdateBearer OBJECT-TYPE
	  		  SYNTAX  Integer32
			  MAX-ACCESS  read-only
			  STATUS  current
			  DESCRIPTION
					 "Total time-out expired update bearer messages "
			  ::= { gxGTPv2UpdateInfo 2 }

	gxGTPv2ModifyBearerSinceInstall OBJECT-TYPE
			SYNTAX  Integer32
			MAX-ACCESS  read-only
			STATUS  current
			DESCRIPTION
				   "Total success modify bearer messages since install policy"
			::= { gxGTPv2UpdateInfo 3 }

	 gxGTPv2ExpiredModifyBearer OBJECT-TYPE
	  		  SYNTAX  Integer32
			  MAX-ACCESS  read-only
			  STATUS  current
			  DESCRIPTION
					 "Total time-out expired modify bearer messages "
			  ::= { gxGTPv2UpdateInfo 4 }

	  gxGTPv2DropMalformedUpdateBearerReq OBJECT-TYPE
		  SYNTAX  Integer32
		  MAX-ACCESS  read-only
		  STATUS  current
		  DESCRIPTION
				 "Total dropped update bearer request messages due to malformed update-request"
		  ::= { gxGTPv2UpdateInfo 5 }

	  gxGTPv2DropMalformedUpdateBearerResp OBJECT-TYPE
		  SYNTAX  Integer32
		  MAX-ACCESS  read-only
		  STATUS  current
		  DESCRIPTION
				 "Total dropped update bearer response messages due to malformed update-response"
		  ::= { gxGTPv2UpdateInfo 6 }

	  gxGTPv2DropMalformedModifyBearerReq OBJECT-TYPE
		  SYNTAX  Integer32
		  MAX-ACCESS  read-only
		  STATUS  current
		  DESCRIPTION
				 "Total dropped modify bearer request messages due to malformed modify-request"
		  ::= { gxGTPv2UpdateInfo 7 }

	  gxGTPv2DropMalformedModifyBearerResp OBJECT-TYPE
		  SYNTAX  Integer32
		  MAX-ACCESS  read-only
		  STATUS  current
		  DESCRIPTION
				 "Total dropped modify bearer response messages due to malformed modify-response"
		  ::= { gxGTPv2UpdateInfo 8 }

	  gxGTPv2DropPolicyUpdateBearer OBJECT-TYPE
		  SYNTAX  Integer32
		  MAX-ACCESS  read-only
		  STATUS  current
		  DESCRIPTION
				 "Total dropped update bearer messages due to policy violation"
		  ::= { gxGTPv2UpdateInfo 9 }

	  gxGTPv2DropPolicyModifyBearer OBJECT-TYPE
		  SYNTAX  Integer32
		  MAX-ACCESS  read-only
		  STATUS  current
		  DESCRIPTION
				 "Total dropped modify bearer messages due to policy violation"
		  ::= { gxGTPv2UpdateInfo 10 }

	  gxGTPv2EchoSinceInstall OBJECT-TYPE
	        SYNTAX  Integer32
	        MAX-ACCESS  read-only
	        STATUS  current
	        DESCRIPTION
	        	   "Total success gtpv2 echo messages since install policy"
	        ::= { gxGTPv2PathMngInfo 1 }

	  gxGTPv2VnspSinceInstall OBJECT-TYPE
			  SYNTAX  Integer32
			  MAX-ACCESS  read-only
			  STATUS  current
			  DESCRIPTION
					 "Total success gtpv2 vnsp messages since install policy"
			  ::= { gxGTPv2PathMngInfo 2 }

	  gxGTPv2ExpiredEcho OBJECT-TYPE
		  SYNTAX  Integer32
		  MAX-ACCESS  read-only
		  STATUS  current
		  DESCRIPTION
				 "Total time-out expired gtpv2 echo messages "
		  ::= { gxGTPv2PathMngInfo 3 }

	  gxGTPv2DropMalformedEchoReq OBJECT-TYPE
		  SYNTAX  Integer32
		  MAX-ACCESS  read-only
		  STATUS  current
		  DESCRIPTION
				 "Total dropped echo request messages due to malformed echo-request"
		  ::= { gxGTPv2PathMngInfo 4 }

	  gxGTPv2DropMalformedEchoResp OBJECT-TYPE
		  SYNTAX  Integer32
		  MAX-ACCESS  read-only
		  STATUS  current
		  DESCRIPTION
				 "Total dropped echo response messages due to malformed echo-response"
		  ::= { gxGTPv2PathMngInfo 5 }

	  gxGTPv2DropPolicyEcho OBJECT-TYPE
		  SYNTAX  Integer32
		  MAX-ACCESS  read-only
		  STATUS  current
		  DESCRIPTION
				 "Total dropped echo messages due to policy violation"
		  ::= { gxGTPv2PathMngInfo 6 }

	  gxGTPv2ModifyBearerCmdSinceInstall OBJECT-TYPE
		  SYNTAX  Integer32
		  MAX-ACCESS  read-only
		  STATUS  current
		  DESCRIPTION
				 "Total success gtpv2 modify bearer command messages since install policy"
		  ::= { gxGTPv2CmdInfo 1 }

	  gxGTPv2ModifyBearerFailIndSinceInstall OBJECT-TYPE
		  SYNTAX  Integer32
		  MAX-ACCESS  read-only
		  STATUS  current
		  DESCRIPTION
				 "Total success gtpv2 modify bearer failure indication messages since install policy"
		  ::= { gxGTPv2CmdInfo 2 }

	  gxGTPv2DeleteBearerCmdSinceInstall OBJECT-TYPE
		  SYNTAX  Integer32
		  MAX-ACCESS  read-only
		  STATUS  current
		  DESCRIPTION
				 "Total success gtpv2 delete bearer command messages since install policy"
		  ::= { gxGTPv2CmdInfo 3 }

	  gxGTPv2DeleteBearerFailIndSinceInstall OBJECT-TYPE
		  SYNTAX  Integer32
		  MAX-ACCESS  read-only
		  STATUS  current
		  DESCRIPTION
				 "Total success gtpv2 delete bearer failure indication messages since install policy"
		  ::= { gxGTPv2CmdInfo 4 }

	  gxGTPv2BearerResourceCmdSinceInstall OBJECT-TYPE
		  SYNTAX  Integer32
		  MAX-ACCESS  read-only
		  STATUS  current
		  DESCRIPTION
				 "Total success gtpv2 bearer resource command messages since install policy"
		  ::= { gxGTPv2CmdInfo 5 }

	  gxGTPv2BearerResourceFailIndSinceInstall OBJECT-TYPE
		  SYNTAX  Integer32
		  MAX-ACCESS  read-only
		  STATUS  current
		  DESCRIPTION
				 "Total success gtpv2 bearer resource failure indication messages since install policy"
		  ::= { gxGTPv2CmdInfo 6 }

 		-- the Smart Defense Status

      asmAttacks     OBJECT IDENTIFIER ::= { smartDefense 1 }
	  asmLayer3      OBJECT IDENTIFIER ::= { asmAttacks 1 }

	  asmLayer4      OBJECT IDENTIFIER ::= { asmAttacks 2 }
	  	asmTCP       	OBJECT IDENTIFIER ::= { asmLayer4 1 }
	  		asmSynatk        OBJECT IDENTIFIER ::= { asmTCP 1 }
	  		asmSmallPmtu     OBJECT IDENTIFIER ::= { asmTCP 2 }
	  		asmSeqval        OBJECT IDENTIFIER ::= { asmTCP 3 }
	  	asmUDP        OBJECT IDENTIFIER ::= { asmLayer4 2 }
	  	asmScans      OBJECT IDENTIFIER ::= { asmLayer4 3 }
	  		asmHostPortScan     OBJECT IDENTIFIER ::= { asmScans 1 }
	  		asmIPSweep  	    OBJECT IDENTIFIER ::= { asmScans 2 }

	  asmLayer5      OBJECT IDENTIFIER ::= { asmAttacks 3 }
		  asmHTTP        OBJECT IDENTIFIER ::= { asmLayer5 1 }
		  	asmHttpWorms              OBJECT IDENTIFIER ::= { asmHTTP 1 }
		  	asmHttpFormatViolatoin    OBJECT IDENTIFIER ::= { asmHTTP 2 }
		  	asmHttpAsciiViolation     OBJECT IDENTIFIER ::= { asmHTTP 3 }
		  	asmHttpP2PHeaderFilter    OBJECT IDENTIFIER ::= { asmHTTP 4 }
		  asmCIFS        OBJECT IDENTIFIER ::= { asmLayer5 2 }
			asmCIFSWorms                OBJECT IDENTIFIER ::= { asmCIFS 1 }
			asmCIFSNullSession          OBJECT IDENTIFIER ::= { asmCIFS 2 }
			asmCIFSBlockedPopUps        OBJECT IDENTIFIER ::= { asmCIFS 3 }
			asmCIFSBlockedCommands      OBJECT IDENTIFIER ::= { asmCIFS 4 }
			asmCIFSPasswordLengthViolations     OBJECT IDENTIFIER ::= { asmCIFS 5 }
		  asmP2P        OBJECT IDENTIFIER ::= { asmLayer5 3 }
			asmP2POtherConAttempts      OBJECT IDENTIFIER ::= { asmP2P 1 }
			asmP2PKazaaConAttempts      OBJECT IDENTIFIER ::= { asmP2P 2 }
			asmP2PeMuleConAttempts      OBJECT IDENTIFIER ::= { asmP2P 3 }
			asmP2PGnutellaConAttempts   OBJECT IDENTIFIER ::= { asmP2P 4 }
			asmP2PSkypeCon              OBJECT IDENTIFIER ::= { asmP2P 5 }
			asmP2PBitTorrentCon         OBJECT IDENTIFIER ::= { asmP2P 6 }




	  asmSynatkSynAckTimeout  OBJECT-TYPE
            SYNTAX  Integer32
            MAX-ACCESS read-only
            STATUS  current
            DESCRIPTION
	  		        "SYN attack - Syn-Ack Timeout"
            ::= { asmSynatk 1 }

	  asmSynatkSynAckReset  OBJECT-TYPE
            SYNTAX  Integer32
            MAX-ACCESS read-only
            STATUS  current
            DESCRIPTION
	  		        "SYN attack - Syn-Ack Reset"
            ::= { asmSynatk 2 }

	  asmSynatkModeChange  OBJECT-TYPE
            SYNTAX  Integer32
            MAX-ACCESS read-only
            STATUS  current
            DESCRIPTION
	  		        "SYN attack  - Mode Change"
            ::= { asmSynatk 3 }

	  asmSynatkCurrentMode  OBJECT-TYPE
            SYNTAX  Integer32
            MAX-ACCESS read-only
            STATUS  current
            DESCRIPTION
	  		        "SYN attack  - Current Mode"
            ::= { asmSynatk 4 }

	  asmSynatkNumberofunAckedSyns OBJECT-TYPE
            SYNTAX  Integer32
            MAX-ACCESS read-only
            STATUS  current
            DESCRIPTION
	  		        "SYN attack  - Number of un-Acked Syns"
            ::= { asmSynatk 5 }

	  smallPMTUNumberOfAttacks OBJECT-TYPE
            SYNTAX  Integer32
            MAX-ACCESS read-only
            STATUS  current
            DESCRIPTION
	  		        "Small PMTU - Number of attacks"
            ::= { asmSmallPmtu 1 }

	  smallPMTUValueOfMinimalMTUsize OBJECT-TYPE
            SYNTAX  Integer32
            MAX-ACCESS read-only
            STATUS  current
            DESCRIPTION
	  		        "Small PMTU - Value of Minimal MTU size"
            ::= { asmSmallPmtu 2 }

	  sequenceVerifierInvalidAck OBJECT-TYPE
            SYNTAX  Integer32
            MAX-ACCESS read-only
            STATUS  current
            DESCRIPTION
	  		        "Sequence Verifier - Invalid Ack"
            ::= { asmSeqval 1 }

	  sequenceVerifierInvalidSequence OBJECT-TYPE
            SYNTAX  Integer32
            MAX-ACCESS read-only
            STATUS  current
            DESCRIPTION
	  		        "Sequence Verifier - Invalid Sequence"
            ::= { asmSeqval 2 }

	  sequenceVerifierInvalidretransmit OBJECT-TYPE
            SYNTAX  Integer32
            MAX-ACCESS read-only
            STATUS  current
            DESCRIPTION
	  		        "Sequence Verifier - Invalid retransmit"
            ::= { asmSeqval 3 }

	  httpWorms OBJECT-TYPE
            SYNTAX  Integer32
            MAX-ACCESS read-only
            STATUS  current
            DESCRIPTION
	  		        "HTTP worms"
            ::= { asmHttpWorms 1 }

	  numOfhostPortScan OBJECT-TYPE
            SYNTAX  Integer32
            MAX-ACCESS read-only
            STATUS  current
            DESCRIPTION
	  		        "host port scan"
            ::= { asmHostPortScan 1 }

	  numOfIpSweep OBJECT-TYPE
            SYNTAX  Integer32
            MAX-ACCESS read-only
            STATUS  current
            DESCRIPTION
	  		        "host port scan"
            ::= { asmIPSweep 1 }

	  httpURLLengthViolation OBJECT-TYPE
            SYNTAX  Integer32
            MAX-ACCESS read-only
            STATUS  current
            DESCRIPTION
	  		        "HTTP - URL Length Violations"
            ::= { asmHttpFormatViolatoin 1 }

	  httpHeaderLengthViolations OBJECT-TYPE
            SYNTAX  Integer32
            MAX-ACCESS read-only
            STATUS  current
            DESCRIPTION
	  		        "HTTP - Header Length Violations"
            ::= { asmHttpFormatViolatoin 2 }

	  httpMaxHeaderReached OBJECT-TYPE
            SYNTAX  Integer32
            MAX-ACCESS read-only
            STATUS  current
            DESCRIPTION
	  		        "HTTP - Maximum Headers Reached"
            ::= { asmHttpFormatViolatoin 3 }

	numOfHttpASCIIViolations OBJECT-TYPE
            SYNTAX  Integer32
            MAX-ACCESS read-only
            STATUS  current
            DESCRIPTION
	  		        "HTTP - ASCII Violations"
            ::= { asmHttpAsciiViolation 1 }

	numOfHttpP2PHeaders OBJECT-TYPE
            SYNTAX  Integer32
            MAX-ACCESS read-only
            STATUS  current
            DESCRIPTION
	  		        "HTTP - Peer To Peer Headers"
            ::= { asmHttpP2PHeaderFilter 1 }

	numOfCIFSworms OBJECT-TYPE
            SYNTAX  Integer32
            MAX-ACCESS read-only
            STATUS  current
            DESCRIPTION
	  		        "num of CIFS worms"
            ::= { asmCIFSWorms 1 }

	numOfCIFSNullSessions OBJECT-TYPE
            SYNTAX  Integer32
            MAX-ACCESS read-only
            STATUS  current
            DESCRIPTION
	  		        "num of CIFS Null Sessions"
            ::= { asmCIFSNullSession 1 }


	numOfCIFSBlockedPopUps OBJECT-TYPE
            SYNTAX  Integer32
            MAX-ACCESS read-only
            STATUS  current
            DESCRIPTION
	  		        "num of CIFS Blocked Pop-Ups"
            ::= { asmCIFSBlockedPopUps 1 }

	numOfCIFSBlockedCommands OBJECT-TYPE
            SYNTAX  Integer32
            MAX-ACCESS read-only
            STATUS  current
            DESCRIPTION
	  		        "num of CIFS Blocked Commands"
            ::= { asmCIFSBlockedCommands 1 }

	numOfCIFSPasswordLengthViolations OBJECT-TYPE
            SYNTAX  Integer32
            MAX-ACCESS read-only
            STATUS  current
            DESCRIPTION
	  		        "num of CIFS PasswordLength Violations"
            ::= { asmCIFSPasswordLengthViolations 1 }

	numOfP2POtherConAttempts OBJECT-TYPE
            SYNTAX  Integer32
            MAX-ACCESS read-only
            STATUS  current
            DESCRIPTION
	  		        "num of P2P Other Con Attempts"
            ::= { asmP2POtherConAttempts 1 }

	numOfP2PKazaaConAttempts OBJECT-TYPE
            SYNTAX  Integer32
            MAX-ACCESS read-only
            STATUS  current
            DESCRIPTION
	  		        "num of P2P Kazaa Con Attempts"
            ::= { asmP2PKazaaConAttempts 1 }

	numOfP2PeMuleConAttempts OBJECT-TYPE
            SYNTAX  Integer32
            MAX-ACCESS read-only
            STATUS  current
            DESCRIPTION
	  		        "num of P2P eMule Con Attempts"
            ::= { asmP2PeMuleConAttempts 1 }

	numOfGnutellaConAttempts OBJECT-TYPE
            SYNTAX  Integer32
            MAX-ACCESS read-only
            STATUS  current
            DESCRIPTION
	  		        "num of P2P Gnutella Con Attempts"
            ::= { asmP2PGnutellaConAttempts 1 }

	numOfP2PSkypeCon OBJECT-TYPE
            SYNTAX  Integer32
            MAX-ACCESS read-only
            STATUS  current
            DESCRIPTION
	  		        "num of P2P Skype Con"
            ::= { asmP2PSkypeCon 1 }

	numOfBitTorrentCon OBJECT-TYPE
            SYNTAX  Integer32
            MAX-ACCESS read-only
            STATUS  current
            DESCRIPTION
	  		        "num of P2P Bit Torrent Con"
            ::= { asmP2PBitTorrentCon 1 }


         --the AntiVirus ( avi ) status

	aviEngines    		OBJECT IDENTIFIER ::= { avi 1 }
    	aviTopViruses 		OBJECT IDENTIFIER ::= { avi 2 }
    	aviTopEverViruses	OBJECT IDENTIFIER ::= { avi 3 }
    	aviServices		OBJECT IDENTIFIER ::= { avi 4 }

    		aviServicesHTTP		OBJECT IDENTIFIER ::= { aviServices 1 }
    		aviServicesFTP		OBJECT IDENTIFIER ::= { aviServices 2 }
    		aviServicesSMTP		OBJECT IDENTIFIER ::= { aviServices 3 }
    		aviServicesPOP3		OBJECT IDENTIFIER ::= { aviServices 4 }

	aviStatCode OBJECT-TYPE
      		SYNTAX  Integer32
			MAX-ACCESS read-only
			STATUS  current
			DESCRIPTION
				"Status code"
			::= {avi 101 }

	aviStatShortDescr OBJECT-TYPE
      		SYNTAX  DisplayString
			MAX-ACCESS read-only
			STATUS  current
			DESCRIPTION
				"Status short description"
			::= {avi 102 }

	aviStatLongDescr OBJECT-TYPE
      		SYNTAX  DisplayString
			MAX-ACCESS read-only
			STATUS  current
			DESCRIPTION
				"Status long description"
			::= {avi 103 }


	aviEngineTable OBJECT-TYPE
      		SYNTAX  SEQUENCE OF AviEngineEntry
			MAX-ACCESS  not-accessible
			STATUS  current
			DESCRIPTION
				"Table of Anti Virus engines installed. Each engine entry contains information about this engine."
			::= {aviEngines 1 }


	aviEngineEntry OBJECT-TYPE
	  		SYNTAX  AviEngineEntry
	  		MAX-ACCESS  not-accessible
	  		STATUS  current
	  		DESCRIPTION "No description available"
	  		INDEX   { aviEngineIndex }
	  		::= { aviEngineTable 1 }

	AviEngineEntry ::=
      		SEQUENCE {
      			aviEngineIndex
		          			Unsigned32,
		        aviEngineName
		        			DisplayString,
        	        aviEngineVer
         		  			DisplayString,
         		aviEngineDate
         					INTEGER,
         		aviSignatureName
         					DisplayString,
         		aviSignatureVer
         					DisplayString,
         		aviSignatureDate
         					INTEGER,
         		aviLastSigCheckTime
         					INTEGER,
         		aviLastSigLocation
         					DisplayString,
         		aviLastLicExp
         					DisplayString
	        }

		aviEngineIndex OBJECT-TYPE
		              SYNTAX  Unsigned32
		              MAX-ACCESS not-accessible
		              STATUS  current
		              DESCRIPTION "No description available"
		              ::= { aviEngineEntry 1 }

		aviEngineName OBJECT-TYPE
		              SYNTAX  DisplayString
		              MAX-ACCESS read-only
		              STATUS  current
		              DESCRIPTION "No description available"
		              ::= { aviEngineEntry 2 }

		aviEngineVer OBJECT-TYPE
		              SYNTAX  DisplayString
		              MAX-ACCESS read-only
		              STATUS  current
		              DESCRIPTION "No description available"
		              ::= { aviEngineEntry 3 }

		aviEngineDate OBJECT-TYPE
		              SYNTAX  Integer32
		              MAX-ACCESS read-only
		              STATUS  current
		              DESCRIPTION "No description available"
		              ::= { aviEngineEntry 4 }

		aviSignatureName OBJECT-TYPE
		              SYNTAX  DisplayString
		              MAX-ACCESS read-only
		              STATUS  current
		              DESCRIPTION "No description available"
		              ::= { aviEngineEntry 5 }

		aviSignatureVer OBJECT-TYPE
		              SYNTAX  DisplayString
		              MAX-ACCESS read-only
		              STATUS  current
		              DESCRIPTION "No description available"
		              ::= { aviEngineEntry 6 }

		aviSignatureDate OBJECT-TYPE
		              SYNTAX  Integer32
		              MAX-ACCESS read-only
		              STATUS  current
		              DESCRIPTION "No description available"
		              ::= { aviEngineEntry 7 }

		aviLastSigCheckTime OBJECT-TYPE
		              SYNTAX  Integer32
		              MAX-ACCESS read-only
		              STATUS  current
		              DESCRIPTION "No description available"
		              ::= { aviEngineEntry 8 }

		aviLastSigLocation OBJECT-TYPE
		              SYNTAX  DisplayString
		              MAX-ACCESS read-only
		              STATUS  current
		              DESCRIPTION "No description available"
		              ::= { aviEngineEntry 9 }

		aviLastLicExp OBJECT-TYPE
			      SYNTAX  DisplayString
		              MAX-ACCESS read-only
		              STATUS  current
		              DESCRIPTION "No description available"
		              ::= { aviEngineEntry 10 }


	aviTopVirusesTable OBJECT-TYPE
      		SYNTAX  SEQUENCE OF AviTopVirusesEntry
			MAX-ACCESS  not-accessible
			STATUS  current
			DESCRIPTION
				"Table for virus count of the most frequent viruses found in the last hour"
			::= {aviTopViruses 1 }


	aviTopVirusesEntry OBJECT-TYPE
	  		SYNTAX  AviTopVirusesEntry
	  		MAX-ACCESS  not-accessible
	  		STATUS  current
	  		DESCRIPTION "No description available"
	  		INDEX   { aviTopVirusesIndex }
	  		::= { aviTopVirusesTable 1 }

	AviTopVirusesEntry ::=
      		SEQUENCE {
      			aviTopVirusesIndex
		          			Unsigned32,
		        aviTopVirusesName
		        			DisplayString,
		        aviTopVirusesCnt
		          			INTEGER

	         }

		aviTopVirusesIndex OBJECT-TYPE
				SYNTAX  Unsigned32
		              	MAX-ACCESS not-accessible
		              	STATUS  current
		              	DESCRIPTION
		              	  	"Virus index"
		              	::= { aviTopVirusesEntry 1 }

		aviTopVirusesName OBJECT-TYPE
				SYNTAX  DisplayString
		              	MAX-ACCESS read-only
		              	STATUS  current
		              	DESCRIPTION
		              	  	"Virus Name"
		              	::= { aviTopVirusesEntry 2 }

		aviTopVirusesCnt OBJECT-TYPE
				SYNTAX  Integer32
				MAX-ACCESS read-only
				STATUS  current
				DESCRIPTION
					"Virus hit count"
				::= { aviTopVirusesEntry 3 }


		aviTopEverVirusesTable OBJECT-TYPE
	    		SYNTAX  SEQUENCE OF AviTopEverVirusesEntry
				MAX-ACCESS  not-accessible
				STATUS  current
				DESCRIPTION
					"Table for virus count of the most frequent viruses found from last system restart"
				::= {aviTopEverViruses 1 }


		aviTopEverVirusesEntry OBJECT-TYPE
	  		SYNTAX  AviTopEverVirusesEntry
	  		MAX-ACCESS  not-accessible
	  		STATUS  current
	  		DESCRIPTION "No description available"
	  		INDEX   { aviTopEverVirusesIndex }
	  		::= { aviTopEverVirusesTable 1 }

    	AviTopEverVirusesEntry ::=
      		SEQUENCE {
      			aviTopEverVirusesIndex
		          			Unsigned32,
		        aviTopEverVirusesName
		        			DisplayString,
		        aviTopEverVirusesCnt
		          			INTEGER
	         }

		aviTopEverVirusesIndex OBJECT-TYPE
		              SYNTAX  Unsigned32
		              MAX-ACCESS not-accessible
		              STATUS  current
		              DESCRIPTION "No description available"
		              ::= { aviTopEverVirusesEntry 1 }

		aviTopEverVirusesName OBJECT-TYPE
		              SYNTAX  DisplayString
		              MAX-ACCESS read-only
		              STATUS  current
		              DESCRIPTION "No description available"
		              ::= { aviTopEverVirusesEntry 2 }

		aviTopEverVirusesCnt OBJECT-TYPE
		              SYNTAX  Integer32
		              MAX-ACCESS read-only
		              STATUS  current
		              DESCRIPTION "No description available"
		              ::= { aviTopEverVirusesEntry 3 }


	aviHTTPState OBJECT-TYPE
      			SYNTAX  Integer32
			MAX-ACCESS read-only
			STATUS  current
			DESCRIPTION
				"State of the Anti Virus engine that inspects HTTP"
			::= { aviServicesHTTP 1 }

	aviHTTPLastVirusName OBJECT-TYPE
      			SYNTAX  DisplayString
			MAX-ACCESS read-only
			STATUS  current
			DESCRIPTION
				"Last virus found over HTTP"
			::= { aviServicesHTTP 2 }

	aviHTTPLastVirusTime OBJECT-TYPE
      			SYNTAX  Integer32
			MAX-ACCESS read-only
			STATUS  current
			DESCRIPTION "No description available"
			::= { aviServicesHTTP 3 }

	aviHTTPTopVirusesTable OBJECT-TYPE
      			SYNTAX  SEQUENCE OF AviHTTPTopVirusesEntry
			MAX-ACCESS  not-accessible
			STATUS  current
			DESCRIPTION
				"Table for virus count of the most frequent viruses found over HTTP in the last day
				 or from last system restart (the latest of the two)"
			::= {aviServicesHTTP 4 }

	aviHTTPTopVirusesEntry OBJECT-TYPE
	  		SYNTAX  AviHTTPTopVirusesEntry
	  		MAX-ACCESS  not-accessible
	  		STATUS  current
	  		DESCRIPTION "No description available"
	  		INDEX   { aviHTTPTopVirusesIndex }
	  		::= { aviHTTPTopVirusesTable 1 }

	AviHTTPTopVirusesEntry ::=
      		SEQUENCE {
      			aviHTTPTopVirusesIndex
		          			Unsigned32,
		        aviHTTPTopVirusesName
		        			DisplayString,
		        aviHTTPTopVirusesCnt
		          			INTEGER

	         }

		aviHTTPTopVirusesIndex OBJECT-TYPE
			SYNTAX  Unsigned32
			MAX-ACCESS not-accessible
			STATUS  current
			DESCRIPTION "No description available"
		        ::= { aviHTTPTopVirusesEntry 1 }

		aviHTTPTopVirusesName OBJECT-TYPE
			SYNTAX  DisplayString
			MAX-ACCESS read-only
			STATUS  current
			DESCRIPTION "No description available"
			::= { aviHTTPTopVirusesEntry 2 }

		aviHTTPTopVirusesCnt OBJECT-TYPE
			SYNTAX  Integer32
			MAX-ACCESS read-only
			STATUS  current
			DESCRIPTION "No description available"
			::= { aviHTTPTopVirusesEntry 3 }



	aviFTPState OBJECT-TYPE
		SYNTAX  Integer32
		MAX-ACCESS read-only
		STATUS  current
		DESCRIPTION
			"State of the Anti Virus engine that inspects FTP"
		::= { aviServicesFTP 1 }

	aviFTPLastVirusName OBJECT-TYPE
      		SYNTAX  DisplayString
		MAX-ACCESS read-only
		STATUS  current
		DESCRIPTION
			"Last virus found over FTP"
		::= { aviServicesFTP 2 }

	aviFTPLastVirusTime OBJECT-TYPE
      		SYNTAX  Integer32
		MAX-ACCESS read-only
		STATUS  current
		DESCRIPTION "No description available"
		::= { aviServicesFTP 3 }

	aviFTPTopVirusesTable OBJECT-TYPE
      		SYNTAX  SEQUENCE OF AviFTPTopVirusesEntry
		MAX-ACCESS  not-accessible
		STATUS  current
		DESCRIPTION
			"Table for virus count of the most frequent viruses found over FTP in the last day
			 or from last system restart (the latest of the two)"
		::= {aviServicesFTP 4 }

	aviFTPTopVirusesEntry OBJECT-TYPE
	  	SYNTAX  AviFTPTopVirusesEntry
	  	MAX-ACCESS  not-accessible
	  	STATUS  current
	  	DESCRIPTION "No description available"
	  	INDEX   { aviFTPTopVirusesIndex }
	  	::= { aviFTPTopVirusesTable 1 }

	AviFTPTopVirusesEntry ::=
      		SEQUENCE {
      			aviFTPTopVirusesIndex
		          			Unsigned32,
		        aviFTPTopVirusesName
		        			DisplayString,
		        aviFTPTopVirusesCnt
		          			INTEGER

	         }

		aviFTPTopVirusesIndex OBJECT-TYPE
			SYNTAX  Unsigned32
			MAX-ACCESS not-accessible
			STATUS  current
			DESCRIPTION "No description available"
			::= { aviFTPTopVirusesEntry 1 }

		aviFTPTopVirusesName OBJECT-TYPE
			SYNTAX  DisplayString
			MAX-ACCESS read-only
			STATUS  current
			DESCRIPTION "No description available"
			::= { aviFTPTopVirusesEntry 2 }

		aviFTPTopVirusesCnt OBJECT-TYPE
			SYNTAX  Integer32
			MAX-ACCESS read-only
			STATUS  current
			DESCRIPTION "No description available"
			::= { aviFTPTopVirusesEntry 3 }


	aviSMTPState OBJECT-TYPE
      		SYNTAX  Integer32
		MAX-ACCESS read-only
		STATUS  current
		DESCRIPTION
			"State of the Anti Virus engine that inspects SMTP"
		::= { aviServicesSMTP 1 }

	aviSMTPLastVirusName OBJECT-TYPE
      		SYNTAX  DisplayString
		MAX-ACCESS read-only
		STATUS  current
		DESCRIPTION
			"Last virus found over SMTP"
		::= { aviServicesSMTP 2 }

	aviSMTPLastVirusTime OBJECT-TYPE
      		SYNTAX  Integer32
		MAX-ACCESS read-only
		STATUS  current
		DESCRIPTION "No description available"
		::= { aviServicesSMTP 3 }

	aviSMTPTopVirusesTable OBJECT-TYPE
      		SYNTAX  SEQUENCE OF AviSMTPTopVirusesEntry
		MAX-ACCESS  not-accessible
		STATUS  current
		DESCRIPTION
			"Table for virus count of the most frequent viruses found over SMTP in the last day
			 or from last system restart (the latest of the two)"
		::= {aviServicesSMTP 4 }

	aviSMTPTopVirusesEntry OBJECT-TYPE
	  	SYNTAX  AviSMTPTopVirusesEntry
	  	MAX-ACCESS  not-accessible
	  	STATUS  current
	  	DESCRIPTION "No description available"
	  	INDEX   { aviSMTPTopVirusesIndex }
	  	::= { aviSMTPTopVirusesTable 1 }

	AviSMTPTopVirusesEntry ::=
      		SEQUENCE {
      			aviSMTPTopVirusesIndex
		          			Unsigned32,
		        aviSMTPTopVirusesName
		        			DisplayString,
		        aviSMTPTopVirusesCnt
		          			INTEGER

	         }

		aviSMTPTopVirusesIndex OBJECT-TYPE
			SYNTAX  Unsigned32
			MAX-ACCESS not-accessible
			STATUS  current
			DESCRIPTION "No description available"
			::= { aviSMTPTopVirusesEntry 1 }

		aviSMTPTopVirusesName OBJECT-TYPE
			SYNTAX  DisplayString
			MAX-ACCESS read-only
			STATUS  current
			DESCRIPTION "No description available"
			::= { aviSMTPTopVirusesEntry 2 }

		aviSMTPTopVirusesCnt OBJECT-TYPE
			SYNTAX  Integer32
			MAX-ACCESS read-only
			STATUS  current
			DESCRIPTION "No description available"
			::= { aviSMTPTopVirusesEntry 3 }


	aviPOP3State OBJECT-TYPE
      		SYNTAX  Integer32
		MAX-ACCESS read-only
		STATUS  current
		DESCRIPTION
			"State of the Anti Virus engine that inspects POP3"
		::= { aviServicesPOP3 1 }

	aviPOP3LastVirusName OBJECT-TYPE
      		SYNTAX  DisplayString
		MAX-ACCESS read-only
		STATUS  current
		DESCRIPTION
			"Last virus found over POP3"
		::= { aviServicesPOP3 2 }

	aviPOP3LastVirusTime OBJECT-TYPE
      		SYNTAX  Integer32
		MAX-ACCESS read-only
		STATUS  current
		DESCRIPTION "No description available"
		::= { aviServicesPOP3 3 }

	aviPOP3TopVirusesTable OBJECT-TYPE
      		SYNTAX  SEQUENCE OF AviPOP3TopVirusesEntry
		MAX-ACCESS  not-accessible
		STATUS  current
		DESCRIPTION
			"Table for virus count of the most frequent viruses found over POP3 in the last day
			 or from last system restart (the latest of the two)"
		::= {aviServicesPOP3 4 }

	aviPOP3TopVirusesEntry OBJECT-TYPE
		SYNTAX  AviPOP3TopVirusesEntry
		MAX-ACCESS  not-accessible
		STATUS  current
		DESCRIPTION "No description available"
		INDEX   { aviPOP3TopVirusesIndex }
	  	::= { aviPOP3TopVirusesTable 1 }

	AviPOP3TopVirusesEntry ::=
      		SEQUENCE {
      			aviPOP3TopVirusesIndex
		          			Unsigned32,
		        aviPOP3TopVirusesName
		        			DisplayString,
		        aviPOP3TopVirusesCnt
		          			INTEGER
	         }

		aviPOP3TopVirusesIndex OBJECT-TYPE
			SYNTAX  Unsigned32
			MAX-ACCESS not-accessible
			STATUS  current
			DESCRIPTION "No description available"
			::= { aviPOP3TopVirusesEntry 1 }

		aviPOP3TopVirusesName OBJECT-TYPE
			SYNTAX  DisplayString
			MAX-ACCESS read-only
			STATUS  current
			DESCRIPTION "No description available"
			::= { aviPOP3TopVirusesEntry 2 }

		aviPOP3TopVirusesCnt OBJECT-TYPE
			SYNTAX  Integer32
			MAX-ACCESS read-only
			STATUS  current
			DESCRIPTION "No description available"
			::= { aviPOP3TopVirusesEntry 3 }



    --Eventia statuses: both Eventia Analyzer and Correlation Unit
    --cpsemd is the Analyzer Server, and cpsead is the Correlation Unit

        cpsemd    		OBJECT IDENTIFIER ::= { eventiaAnalyzer 1 }
    	cpsead	 		OBJECT IDENTIFIER ::= { eventiaAnalyzer 2 }


	--cpsemd statuses:

	cpsemdStatCode OBJECT-TYPE
      		SYNTAX  Integer32
			MAX-ACCESS read-only
			STATUS  current
			DESCRIPTION
				"Status code"
			::= {cpsemd 101 }

	cpsemdStatShortDescr OBJECT-TYPE
      		SYNTAX  DisplayString
			MAX-ACCESS read-only
			STATUS  current
			DESCRIPTION
				"Status short description"
			::= {cpsemd 102 }

	cpsemdStatLongDescr OBJECT-TYPE
      		SYNTAX  DisplayString
			MAX-ACCESS read-only
			STATUS  current
			DESCRIPTION
				"Status long description"
			::= {cpsemd 103 }

	cpsemdProcAlive OBJECT-TYPE
      		SYNTAX  Integer32
			MAX-ACCESS read-only
			STATUS  current
			DESCRIPTION
				"cpsemd Process is alive"
			::= {cpsemd 1 }

	cpsemdNewEventsHandled OBJECT-TYPE
      		SYNTAX  Integer32
			MAX-ACCESS read-only
			STATUS  current
			DESCRIPTION
				"New events handled"
			::= {cpsemd 2 }

	cpsemdUpdatesHandled OBJECT-TYPE
      		SYNTAX  Integer32
			MAX-ACCESS read-only
			STATUS  current
			DESCRIPTION
				"Number of updates handled"
			::= {cpsemd 3 }

	cpsemdLastEventTime OBJECT-TYPE
      		SYNTAX  DisplayString
			MAX-ACCESS read-only
			STATUS  current
			DESCRIPTION
				"Last processed event time"
			::= {cpsemd 4 }

	cpsemdCurrentDBSize OBJECT-TYPE
      		SYNTAX  DisplayString
			MAX-ACCESS read-only
			STATUS  current
			DESCRIPTION
				"Current database size"
			::= {cpsemd 5 }

	cpsemdDBCapacity OBJECT-TYPE
      		SYNTAX  DisplayString
			MAX-ACCESS read-only
			STATUS  current
			DESCRIPTION
				"Database capacity"
			::= {cpsemd 6 }

	cpsemdNumEvents OBJECT-TYPE
      		SYNTAX  Integer32
			MAX-ACCESS read-only
			STATUS  current
			DESCRIPTION
				"Number of events in database"
			::= {cpsemd 7 }

	cpsemdDBDiskSpace OBJECT-TYPE
      		SYNTAX  DisplayString
			MAX-ACCESS read-only
			STATUS  current
			DESCRIPTION
				"Available database disk space"
			::= {cpsemd 8 }


	cpsemdCorrelationUnitTable OBJECT-TYPE
      		SYNTAX  SEQUENCE OF CpsemdCorrelationUnitEntry
    		MAX-ACCESS  not-accessible
			STATUS  current
			DESCRIPTION
				"Table for Correlation Units details"
			::= {cpsemd 9 }

	cpsemdDBIsFull OBJECT-TYPE
      		SYNTAX  Integer32
			MAX-ACCESS read-only
			STATUS  current
			DESCRIPTION
				"1 - Database is full; 0 - Database is not full"
			::= {cpsemd 10 }

	cpsemdCorrelationUnitEntry OBJECT-TYPE
		SYNTAX  CpsemdCorrelationUnitEntry
		MAX-ACCESS  not-accessible
		STATUS  current
		DESCRIPTION "No description available"
		INDEX   { cpsemdCorrelationUnitIndex }
	  	::= { cpsemdCorrelationUnitTable 1 }

	CpsemdCorrelationUnitEntry ::=
      		SEQUENCE {
      			cpsemdCorrelationUnitIndex
		          			Unsigned32,
		        cpsemdCorrelationUnitIP
		        			DisplayString,
		        cpsemdCorrelationUnitLastRcvdTime
		          			DisplayString,
		        cpsemdCorrelationUnitNumEventsRcvd
		         			INTEGER,
		        cpsemdConnectionDuration
		        			INTEGER
	         }

		cpsemdCorrelationUnitIndex OBJECT-TYPE
			SYNTAX  Unsigned32
			MAX-ACCESS not-accessible
			STATUS  current
			DESCRIPTION "No description available"
			::= { cpsemdCorrelationUnitEntry 1 }

		cpsemdCorrelationUnitIP OBJECT-TYPE
			SYNTAX  DisplayString
			MAX-ACCESS read-only
			STATUS  current
			DESCRIPTION
				"Correlation Unit IP"
			::= { cpsemdCorrelationUnitEntry 2 }

		cpsemdCorrelationUnitLastRcvdTime OBJECT-TYPE
			SYNTAX  DisplayString
			MAX-ACCESS read-only
			STATUS  current
			DESCRIPTION
				"Time of last received event"
			::= { cpsemdCorrelationUnitEntry 3 }

		cpsemdCorrelationUnitNumEventsRcvd OBJECT-TYPE
			SYNTAX  Integer32
			MAX-ACCESS read-only
			STATUS  current
			DESCRIPTION
				"Number of events received"
			::= { cpsemdCorrelationUnitEntry 4 }

		cpsemdConnectionDuration OBJECT-TYPE
			SYNTAX  Integer32
			MAX-ACCESS read-only
			STATUS  current
			DESCRIPTION
				"Connection duration (to the Correlation Unit)"
			::= { cpsemdCorrelationUnitEntry 5 }

	--cpsead statuses:

	cpseadStatCode OBJECT-TYPE
      		SYNTAX  Integer32
			MAX-ACCESS read-only
			STATUS  current
			DESCRIPTION
				"Status code"
			::= {cpsead 101 }

	cpseadStatShortDescr OBJECT-TYPE
      		SYNTAX  DisplayString
			MAX-ACCESS read-only
			STATUS  current
			DESCRIPTION
				"Status short description"
			::= {cpsead 102 }

	cpseadStatLongDescr OBJECT-TYPE
      		SYNTAX  DisplayString
			MAX-ACCESS read-only
			STATUS  current
			DESCRIPTION
				"Status long description"
			::= {cpsead 103 }


	cpseadProcAlive OBJECT-TYPE
      		SYNTAX  Integer32
			MAX-ACCESS read-only
			STATUS  current
			DESCRIPTION
				"cpsead Process is alive"
			::= {cpsead 1 }

	cpseadConnectedToSem OBJECT-TYPE
      		SYNTAX  Integer32
			MAX-ACCESS read-only
			STATUS  current
			DESCRIPTION
				"Connected to SEM (is the Correlation Unit connected to the Analyzer Server)"
			::= {cpsead 2 }

	cpseadNumProcessedLogs OBJECT-TYPE
      		SYNTAX  DisplayString
			MAX-ACCESS read-only
			STATUS  current
			DESCRIPTION
				"Number of logs processed"
			::= {cpsead 3 }


	cpseadJobsTable OBJECT-TYPE
      		SYNTAX  SEQUENCE OF CpseadJobsEntry
			MAX-ACCESS  not-accessible
			STATUS  current
			DESCRIPTION
				"Jobs Table"
			::= {cpsead 4 }

	cpseadJobsEntry OBJECT-TYPE
		SYNTAX  CpseadJobsEntry
			MAX-ACCESS  not-accessible
			STATUS  current
			DESCRIPTION "No description available"
			INDEX   { cpseadJobIndex }
		  	::= { cpseadJobsTable 1 }

	CpseadJobsEntry ::=
      		SEQUENCE {
      			cpseadJobIndex
		          			Unsigned32,
		        cpseadJobID
		        			DisplayString,
		        cpseadJobName
		          			DisplayString,
		        cpseadJobState
		         			DisplayString,
		        cpseadJobIsOnline
		        			INTEGER,
		        cpseadJobLogServer
		        			DisplayString,
		       	cpseadJobDataType
		          			DisplayString,
		        cpseadConnectedToLogServer
		        			INTEGER,
		        cpseadNumAnalyzedLogs
		          			DisplayString,
		        cpseadFileName
		         			DisplayString,
		        cpseadFileCurrentPosition
		        			DisplayString,
		        cpseadStateDescriptionCode
		        			DisplayString,
		        cpseadStateDescription
		        			DisplayString
	         }

		cpseadJobIndex OBJECT-TYPE
			SYNTAX  Unsigned32
			MAX-ACCESS not-accessible
			STATUS  current
			DESCRIPTION "No description available"
			::= { cpseadJobsEntry 1 }

		cpseadJobID OBJECT-TYPE
			SYNTAX  DisplayString
			MAX-ACCESS read-only
			STATUS  current
			DESCRIPTION
				"Job ID"
			::= { cpseadJobsEntry 2 }

		cpseadJobName OBJECT-TYPE
			SYNTAX  DisplayString
			MAX-ACCESS read-only
			STATUS  current
			DESCRIPTION
				"Job name"
			::= { cpseadJobsEntry 3 }

		cpseadJobState OBJECT-TYPE
			SYNTAX  DisplayString
			MAX-ACCESS read-only
			STATUS  current
			DESCRIPTION
				"Job state"
			::= { cpseadJobsEntry 4 }

		cpseadJobIsOnline OBJECT-TYPE
			SYNTAX  Integer32
			MAX-ACCESS read-only
			STATUS  current
			DESCRIPTION
				"Is job online"
			::= { cpseadJobsEntry 5 }

		cpseadJobLogServer OBJECT-TYPE
			SYNTAX  DisplayString
			MAX-ACCESS read-only
			STATUS  current
			DESCRIPTION
				" Log Server (the IP of the log server from which the job is reading logs)"
			::= { cpseadJobsEntry 6 }

		cpseadJobDataType OBJECT-TYPE
			SYNTAX  DisplayString
			MAX-ACCESS read-only
			STATUS  current
			DESCRIPTION
				"Data type (the type of date being read: log or audit)"
			::= { cpseadJobsEntry 7 }

		cpseadConnectedToLogServer OBJECT-TYPE
			SYNTAX  Integer32
			MAX-ACCESS read-only
			STATUS  current
			DESCRIPTION
				"Connected to Log Server (is the Correlation Unit connected to the Log Server)"
			::= { cpseadJobsEntry 8 }

		cpseadNumAnalyzedLogs OBJECT-TYPE
			SYNTAX  DisplayString
			MAX-ACCESS read-only
			STATUS  current
			DESCRIPTION
				"Number of logs analyzed"
			::= { cpseadJobsEntry 9 }

		cpseadFileName OBJECT-TYPE
			SYNTAX  DisplayString
			MAX-ACCESS read-only
			STATUS  current
			DESCRIPTION
				"File Name (the name of the file from which the job is reading logs)"
			::= { cpseadJobsEntry 10 }

		cpseadFileCurrentPosition OBJECT-TYPE
			SYNTAX  DisplayString
			MAX-ACCESS read-only
			STATUS  current
			DESCRIPTION
				"current position in the file"
			::= { cpseadJobsEntry 11 }

		cpseadStateDescriptionCode OBJECT-TYPE
			SYNTAX  DisplayString
			MAX-ACCESS read-only
			STATUS  current
			DESCRIPTION
				"state description code (code for the state description in the next OID)"
			::= { cpseadJobsEntry 12 }

		cpseadStateDescription OBJECT-TYPE
			SYNTAX  DisplayString
			MAX-ACCESS read-only
			STATUS  current
			DESCRIPTION
				"state description (provides more info regarding the job's state (OID 4), for instance details errors.)"
			::= { cpseadJobsEntry 13 }

	cpseadNoFreeDiskSpace OBJECT-TYPE
      		SYNTAX  Integer32
			MAX-ACCESS read-only
			STATUS  current
			DESCRIPTION
				"no free disk space (is there not enough free disk space on the Correlation Unit)"
			::= {cpsead 5 }



        --the Url Filtering ( uf ) status

	ufEngine		OBJECT IDENTIFIER ::= { uf 1 }
	ufSS			OBJECT IDENTIFIER ::= { uf 2 }

	ufStatCode OBJECT-TYPE
      		SYNTAX  Integer32
			MAX-ACCESS read-only
			STATUS  current
			DESCRIPTION
				"Status code"
			::= {uf 101 }

	ufStatShortDescr OBJECT-TYPE
      		SYNTAX  DisplayString
			MAX-ACCESS read-only
			STATUS  current
			DESCRIPTION
				"Status short description"
			::= {uf 102 }

	ufStatLongDescr OBJECT-TYPE
      		SYNTAX  DisplayString
			MAX-ACCESS read-only
			STATUS  current
			DESCRIPTION
				"Status long description"
			::= {uf 103 }


    	ufEngineName OBJECT-TYPE
      		SYNTAX  DisplayString
			MAX-ACCESS read-only
			STATUS  current
			DESCRIPTION
				"Engine name"
			::= {ufEngine 1 }

    	ufEngineVer OBJECT-TYPE
      		SYNTAX  DisplayString
			MAX-ACCESS read-only
			STATUS  current
			DESCRIPTION
				"Engine version"
			::= {ufEngine 2 }

	ufEngineDate OBJECT-TYPE
      		SYNTAX  Integer32
			MAX-ACCESS read-only
			STATUS  current
			DESCRIPTION
				"Engine build date"
			::= {ufEngine 3 }

	ufSignatureDate OBJECT-TYPE
      		SYNTAX  Integer32
			MAX-ACCESS read-only
			STATUS  current
			DESCRIPTION
				"Creation date of the signature-set used by the engine"
			::= {ufEngine 4 }

	ufSignatureVer OBJECT-TYPE
      		SYNTAX  DisplayString
			MAX-ACCESS read-only
			STATUS  current
			DESCRIPTION
				"Version of the signature"
			::= {ufEngine 5 }

	ufLastSigCheckTime OBJECT-TYPE
      		SYNTAX  Integer32
			MAX-ACCESS read-only
			STATUS  current
			DESCRIPTION
				"Last time there was a check for new signature "
			::= {ufEngine 6 }

	ufLastSigLocation OBJECT-TYPE
      		SYNTAX  DisplayString
			MAX-ACCESS read-only
			STATUS  current
			DESCRIPTION
				"Last signature origine (either from Remote site or from SmartCenter)"
			::= {ufEngine 7 }

	ufLastLicExp OBJECT-TYPE
      		SYNTAX  DisplayString
			MAX-ACCESS read-only
			STATUS  current
			DESCRIPTION
				"Expiration date of the subscription for Web Filtering updates"
			::= {ufEngine 8 }



	ufIsMonitor OBJECT-TYPE
      		SYNTAX  DisplayString
			MAX-ACCESS read-only
			STATUS  current
			DESCRIPTION
				"Monitor-Only Running mode (ON or OFF)"
			::= {ufSS 1 }

	ufScannedCnt OBJECT-TYPE
      		SYNTAX  Integer32
			MAX-ACCESS read-only
			STATUS  current
			DESCRIPTION
				"Total number of scanned URLs"
			::= {ufSS 2 }

	ufBlockedCnt OBJECT-TYPE
      		SYNTAX  Integer32
			MAX-ACCESS read-only
			STATUS  current
			DESCRIPTION
				"Number of blocked URLs"
			::= {ufSS 3 }

	ufTopBlockedCatTable OBJECT-TYPE
      		SYNTAX  SEQUENCE OF UfTopBlockedCatEntry
			MAX-ACCESS  not-accessible
			STATUS  current
			DESCRIPTION
				"Table for counting of the most frequent categories blocked in the last day"
			::= {ufSS 4 }


     	ufTopBlockedCatEntry OBJECT-TYPE
	  		SYNTAX  UfTopBlockedCatEntry
	  		MAX-ACCESS  not-accessible
	  		STATUS  current
	  		DESCRIPTION "No description available"
	  		INDEX   { ufTopBlockedCatIndex }
	  		::= { ufTopBlockedCatTable 1 }

	UfTopBlockedCatEntry ::=
      		SEQUENCE {
      			ufTopBlockedCatIndex
		          			Unsigned32,
		        ufTopBlockedCatName
		        			DisplayString,
        		ufTopBlockedCatCnt
         		  			INTEGER
	         }

		 ufTopBlockedCatIndex OBJECT-TYPE
		              SYNTAX  Unsigned32
		              MAX-ACCESS not-accessible
		              STATUS  current
		              DESCRIPTION
		              		  "Blocked Category index"
		              ::= { ufTopBlockedCatEntry 1 }

		ufTopBlockedCatName OBJECT-TYPE
		              SYNTAX  DisplayString
		              MAX-ACCESS read-only
		              STATUS  current
		              DESCRIPTION
		              		  "Blocked Category name"
		              ::= { ufTopBlockedCatEntry 2 }

		ufTopBlockedCatCnt OBJECT-TYPE
		              SYNTAX  Integer32
		              MAX-ACCESS read-only
		              STATUS  current
		              DESCRIPTION
		              		  "Blocked Category count"
		              ::= { ufTopBlockedCatEntry 3 }


	ufTopBlockedSiteTable OBJECT-TYPE
      		SYNTAX  SEQUENCE OF UfTopBlockedSiteEntry
			MAX-ACCESS  not-accessible
			STATUS  current
			DESCRIPTION
				"Table for counting of the most frequent sites blocked in the last day"
			::= {ufSS 5 }


	ufTopBlockedSiteEntry OBJECT-TYPE
	  		SYNTAX  UfTopBlockedSiteEntry
	  		MAX-ACCESS  not-accessible
	  		STATUS  current
	  		DESCRIPTION "No description available"
	  		INDEX   { ufTopBlockedSiteIndex }
	  		::= { ufTopBlockedSiteTable 1 }

	UfTopBlockedSiteEntry ::=
      		SEQUENCE {
      			ufTopBlockedSiteIndex
		          			Unsigned32,
		        ufTopBlockedSiteName
		        			DisplayString,
        		ufTopBlockedSiteCnt
         		  			INTEGER
	         }

		ufTopBlockedSiteIndex OBJECT-TYPE
		              SYNTAX  Unsigned32
		              MAX-ACCESS not-accessible
		              STATUS  current
		              DESCRIPTION
		              		  "Blocked URL index"
		              ::= { ufTopBlockedSiteEntry 1 }

		ufTopBlockedSiteName OBJECT-TYPE
		              SYNTAX  DisplayString
		              MAX-ACCESS read-only
		              STATUS  current
		              DESCRIPTION
		              		  "Blocked URL name"
		              ::= { ufTopBlockedSiteEntry 2 }

		ufTopBlockedSiteCnt OBJECT-TYPE
		              SYNTAX  Integer32
		              MAX-ACCESS read-only
		              STATUS  current
		              DESCRIPTION
		              		  "Blocked URL count"
		              ::= { ufTopBlockedSiteEntry 3 }


	ufTopBlockedUserTable OBJECT-TYPE
      		SYNTAX  SEQUENCE OF UfTopBlockedUserEntry
			MAX-ACCESS  not-accessible
			STATUS  current
			DESCRIPTION
				"Table for counting blocked URLs of the most frequent blocked users in the last day"
			::= {ufSS 6 }


	ufTopBlockedUserEntry OBJECT-TYPE
	  		SYNTAX  UfTopBlockedUserEntry
	  		MAX-ACCESS  not-accessible
	  		STATUS  current
	  		DESCRIPTION "No description available"
	  		INDEX   { ufTopBlockedUserIndex }
	  		::= { ufTopBlockedUserTable 1 }

	UfTopBlockedUserEntry ::=
      		SEQUENCE {
      			ufTopBlockedUserIndex
		          			Unsigned32,
		        ufTopBlockedUserName
		        			DisplayString,
        	        ufTopBlockedUserCnt
         		  			INTEGER
	         }

		ufTopBlockedUserIndex OBJECT-TYPE
		              SYNTAX  Unsigned32
		              MAX-ACCESS not-accessible
		              STATUS  current
		              DESCRIPTION
		              		  "Blocked User index"
		              ::= { ufTopBlockedUserEntry 1 }

		ufTopBlockedUserName OBJECT-TYPE
		              SYNTAX  DisplayString
		              MAX-ACCESS read-only
		              STATUS  current
		              DESCRIPTION
		              		  "Blocked User name"
		              ::= { ufTopBlockedUserEntry 2 }

		ufTopBlockedUserCnt OBJECT-TYPE
		              SYNTAX  Integer32
		              MAX-ACCESS read-only
		              STATUS  current
		              DESCRIPTION
		              		  "Blocked User count"
		              ::= { ufTopBlockedUserEntry 3 }

    --Anti Spam (mail security) statuses:

	msProductName OBJECT-TYPE
      		SYNTAX  DisplayString
			MAX-ACCESS read-only
			STATUS  current
			DESCRIPTION
				"Product Name"
			::= { ms 1 }

	msMajorVersion OBJECT-TYPE
      		SYNTAX  Integer32
			MAX-ACCESS read-only
			STATUS  current
			DESCRIPTION
				"Major Version"
			::= { ms 2 }

 	msMinorVersion OBJECT-TYPE
      		SYNTAX  Integer32
			MAX-ACCESS read-only
			STATUS  current
			DESCRIPTION
				"Minor Version"
			::= { ms 3 }

	msBuildNumber OBJECT-TYPE
      		SYNTAX  Integer32
			MAX-ACCESS read-only
			STATUS  current
			DESCRIPTION
				"Build Number"
			::= { ms 4 }

 	msVersionStr OBJECT-TYPE
      		SYNTAX  DisplayString
			MAX-ACCESS read-only
			STATUS  current
			DESCRIPTION
				"Version String"
			::= { ms 5 }

	--Spam Statuses subtree
	msSpam	OBJECT IDENTIFIER ::= { ms 6 }

	msSpamNumScannedEmails	OBJECT-TYPE
      		SYNTAX  Integer32
			MAX-ACCESS read-only
			STATUS  current
			DESCRIPTION
				"Number of scanned emails"
			::= { msSpam 1 }

 	msSpamNumSpamEmails	OBJECT-TYPE
      		SYNTAX  Integer32
			MAX-ACCESS read-only
			STATUS  current
			DESCRIPTION
				"Number of spam emails"
			::= { msSpam 2 }

	msSpamNumHandledSpamEmails	OBJECT-TYPE
      		SYNTAX  Integer32
			MAX-ACCESS read-only
			STATUS  current
			DESCRIPTION
				"Number of handled spam emails"
			::= { msSpam 3 }

	    --spam controls subtree
	    msSpamControls  OBJECT IDENTIFIER ::= { msSpam 4 }

		msSpamControlsSpamEngine	OBJECT-TYPE
	      		SYNTAX  Integer32
				MAX-ACCESS read-only
				STATUS  current
				DESCRIPTION
					"Number of spam emails by Anti Spam engine"
				::= { msSpamControls 1 }

		msSpamControlsIpRepuatation	OBJECT-TYPE
	      		SYNTAX  Integer32
				MAX-ACCESS read-only
				STATUS  current
				DESCRIPTION
					"Number of spam emails by IP reputation service"
				::= { msSpamControls 2 }

		msSpamControlsSPF OBJECT-TYPE
	      		SYNTAX  Integer32
				MAX-ACCESS read-only
				STATUS  current
				DESCRIPTION
					"Number of spam emails by SPF"
				::= { msSpamControls 3 }

		msSpamControlsDomainKeys OBJECT-TYPE
	      		SYNTAX  Integer32
				MAX-ACCESS read-only
				STATUS  current
				DESCRIPTION
					"Number of spam emails by Domain Keys"
				::= { msSpamControls 4 }

		msSpamControlsRDNS OBJECT-TYPE
	      		SYNTAX  Integer32
				MAX-ACCESS read-only
				STATUS  current
				DESCRIPTION
					"Number of spam emails by Reverse DNS"
				::= { msSpamControls 5 }

		msSpamControlsRBL OBJECT-TYPE
	      		SYNTAX  Integer32
				MAX-ACCESS read-only
				STATUS  current
				DESCRIPTION
					"Number of spam emails by RBLs (Including Received headers and URLs)"
				::= { msSpamControls 6 }

	msExpirationDate OBJECT-TYPE
      		SYNTAX  DisplayString
			MAX-ACCESS read-only
			STATUS  current
			DESCRIPTION
				"Subscription expiration date"
			::= { ms 7 }

    msEngineVer OBJECT-TYPE
      		SYNTAX  DisplayString
			MAX-ACCESS read-only
			STATUS  current
			DESCRIPTION
				"Anti Spam Engine Version"
			::= { ms 8 }

     msEngineDate OBJECT-TYPE
      		SYNTAX  Integer32
			MAX-ACCESS read-only
			STATUS  current
			DESCRIPTION
				"Anti Spam Engine Build Date"
			::= { ms 9 }

 	msStatCode OBJECT-TYPE
      		SYNTAX  Integer32
			MAX-ACCESS read-only
			STATUS  current
			DESCRIPTION
				"Status code"
			::= { ms 101 }

	msStatShortDescr OBJECT-TYPE
      		SYNTAX  DisplayString
			MAX-ACCESS read-only
			STATUS  current
			DESCRIPTION
				"Status short description"
			::= { ms 102 }

	msStatLongDescr OBJECT-TYPE
      		SYNTAX  DisplayString
			MAX-ACCESS read-only
			STATUS  current
			DESCRIPTION
				"Status long description"
			::= { ms 103 }

	msServicePack OBJECT-TYPE
      		SYNTAX  DisplayString
			MAX-ACCESS read-only
			STATUS  current
			DESCRIPTION
				"Service Pack"
			::= { ms 999 }



	--voip statuses:

 	voipProductName OBJECT-TYPE
      		SYNTAX  DisplayString
			MAX-ACCESS read-only
			STATUS  current
			DESCRIPTION
				"Product Name"
			::= {voip 1 }


 	voipMajorVersion OBJECT-TYPE
      		SYNTAX  Integer32
			MAX-ACCESS read-only
			STATUS  current
			DESCRIPTION
				"Major Version"
			::= {voip 2 }

 	voipMinorVersion OBJECT-TYPE
      		SYNTAX  Integer32
			MAX-ACCESS read-only
			STATUS  current
			DESCRIPTION
				"Minor Version"
			::= {voip 3 }

 	voipBuildNumber OBJECT-TYPE
      		SYNTAX  Integer32
			MAX-ACCESS read-only
			STATUS  current
			DESCRIPTION
				"Build Number"
			::= {voip 4 }

 	voipVersionStr OBJECT-TYPE
      		SYNTAX  DisplayString
			MAX-ACCESS read-only
			STATUS  current
			DESCRIPTION
				"Version String"
			::= {voip 5 }

    -- Denial Of Service Statuses Subtree
 	voipDOS		OBJECT IDENTIFIER ::= { voip 6 }
	voipDOSSip		OBJECT IDENTIFIER ::= { voipDOS 1 }
	voipDOSSipNetwork		OBJECT IDENTIFIER ::= { voipDOSSip 1 }

    voipDOSSipNetworkReqInterval OBJECT-TYPE
      		SYNTAX  Integer32
			MAX-ACCESS read-only
			STATUS  current
			DESCRIPTION
				"Total Number of SIP Requests to The Internal Network per Interval: Interval (seconds)"
			::= {voipDOSSipNetwork 1 }

    voipDOSSipNetworkReqConfThreshold OBJECT-TYPE
      		SYNTAX  Integer32
			MAX-ACCESS read-only
			STATUS  current
			DESCRIPTION
				"Total Number of SIP Requests to The Internal Network per Interval: Configured Threshold"
			::= {voipDOSSipNetwork 2 }

    voipDOSSipNetworkReqCurrentVal OBJECT-TYPE
      		SYNTAX  Integer32
			MAX-ACCESS read-only
			STATUS  current
			DESCRIPTION
				"Total Number of SIP Requests to The Internal Network per Interval: Current Value"
			::= {voipDOSSipNetwork 3 }

    voipDOSSipNetworkRegInterval OBJECT-TYPE
      		SYNTAX  Integer32
			MAX-ACCESS read-only
			STATUS  current
			DESCRIPTION
				"Total number of 'REGISTER' Requests to The Internal Network per Interval: Interval (seconds)"
			::= {voipDOSSipNetwork 4 }

    voipDOSSipNetworkRegConfThreshold OBJECT-TYPE
      		SYNTAX  Integer32
			MAX-ACCESS read-only
			STATUS  current
			DESCRIPTION
				"Total number of 'REGISTER' Requests to The Internal Network per Interval: Configured Threshold"
			::= {voipDOSSipNetwork 5 }

	voipDOSSipNetworkRegCurrentVal OBJECT-TYPE
      		SYNTAX  Integer32
			MAX-ACCESS read-only
			STATUS  current
			DESCRIPTION
				"Total number of 'REGISTER' Requests to The Internal Network per Interval: Current Value"
			::= {voipDOSSipNetwork 6 }

	voipDOSSipNetworkCallInitInterval OBJECT-TYPE
      		SYNTAX  Integer32
			MAX-ACCESS read-only
			STATUS  current
			DESCRIPTION
				"Total Number of SIP Call Initiations to The Internal Network per Interval: Interval (seconds)"
			::= {voipDOSSipNetwork 7 }

	voipDOSSipNetworkCallInitConfThreshold OBJECT-TYPE
      		SYNTAX  Integer32
			MAX-ACCESS read-only
			STATUS  current
			DESCRIPTION
				"Total Number of SIP Call Initiations to The Internal Network per Interval: Configured Threshold"
			::= {voipDOSSipNetwork 8 }

	voipDOSSipNetworkCallInitICurrentVal OBJECT-TYPE
      		SYNTAX  Integer32
			MAX-ACCESS read-only
			STATUS  current
			DESCRIPTION
				"Total Number of SIP Call Initiations to The Internal Network per Interval: Current Value"
			::= {voipDOSSipNetwork 9 }


	voipDOSSipRateLimitingTable OBJECT-TYPE
      		SYNTAX  SEQUENCE OF VoipDOSSipRateLimitingEntry
			MAX-ACCESS  not-accessible
			STATUS  current
			DESCRIPTION
				"Table for counting blocked URLs of the most frequent blocked users in the last day"
			::= {voipDOSSip 2 }


	voipDOSSipRateLimitingEntry OBJECT-TYPE
	  		SYNTAX  VoipDOSSipRateLimitingEntry
	  		MAX-ACCESS  not-accessible
	  		STATUS  current
	  		DESCRIPTION "No description available"
	  		INDEX   { voipDOSSipRateLimitingTableIndex }
	  		::= { voipDOSSipRateLimitingTable 1 }

	VoipDOSSipRateLimitingEntry ::=
      		SEQUENCE {
      			voipDOSSipRateLimitingTableIndex
		          			Unsigned32,
				voipDOSSipRateLimitingTableIpAddress
		          			INTEGER,
 				voipDOSSipRateLimitingTableInterval
		          			INTEGER,
 				voipDOSSipRateLimitingTableConfThreshold
		          			INTEGER,
				voipDOSSipRateLimitingTableNumDOSSipRequests
		          			INTEGER,
				voipDOSSipRateLimitingTableNumTrustedRequests
		          			INTEGER,
				voipDOSSipRateLimitingTableNumNonTrustedRequests
		          			INTEGER,
				voipDOSSipRateLimitingTableNumRequestsfromServers
		          			INTEGER
	         }

		voipDOSSipRateLimitingTableIndex OBJECT-TYPE
		              SYNTAX  Unsigned32
		              MAX-ACCESS not-accessible
		              STATUS  current
		              DESCRIPTION
		              		  "Rate Limiting Defense for Internal SIP Servers: Table Index"
		              ::= { voipDOSSipRateLimitingEntry 1 }

		voipDOSSipRateLimitingTableIpAddress OBJECT-TYPE
		              SYNTAX  Integer32
		              MAX-ACCESS read-only
		              STATUS  current
		              DESCRIPTION
		              		  "Rate Limiting Defense for Internal SIP Servers: Ip Address"
		              ::= { voipDOSSipRateLimitingEntry 2 }

		voipDOSSipRateLimitingTableInterval OBJECT-TYPE
		              SYNTAX  Integer32
		              MAX-ACCESS read-only
		              STATUS  current
		              DESCRIPTION
		              		  "Rate Limiting Defense for Internal SIP Servers: Interval (Seconds)"
		              ::= { voipDOSSipRateLimitingEntry 3 }

		voipDOSSipRateLimitingTableConfThreshold OBJECT-TYPE
		              SYNTAX  Integer32
		              MAX-ACCESS read-only
		              STATUS  current
		              DESCRIPTION
		              		  "Rate Limiting Defense for Internal SIP Servers: Configured Threshold for Number of SIP Requests"
		              ::= { voipDOSSipRateLimitingEntry 4 }

 		voipDOSSipRateLimitingTableNumDOSSipRequests OBJECT-TYPE
		              SYNTAX  Integer32
		              MAX-ACCESS read-only
		              STATUS  current
		              DESCRIPTION
		              		  "Rate Limiting Defense for Internal SIP Servers: Number of SIP Requests"
		              ::= { voipDOSSipRateLimitingEntry 5 }

		voipDOSSipRateLimitingTableNumTrustedRequests OBJECT-TYPE
		              SYNTAX  Integer32
		              MAX-ACCESS read-only
		              STATUS  current
		              DESCRIPTION
		              		  "Rate Limiting Defense for Internal SIP Servers: Number of SIP Requests from Trusted Users"
		              ::= { voipDOSSipRateLimitingEntry 6 }

		voipDOSSipRateLimitingTableNumNonTrustedRequests OBJECT-TYPE
		              SYNTAX  Integer32
		              MAX-ACCESS read-only
		              STATUS  current
		              DESCRIPTION
		              		  "Rate Limiting Defense for Internal SIP Servers: Number of SIP Requests from Non-Trusted Users"
		              ::= { voipDOSSipRateLimitingEntry 7 }

		voipDOSSipRateLimitingTableNumRequestsfromServers OBJECT-TYPE
		              SYNTAX  Integer32
		              MAX-ACCESS read-only
		              STATUS  current
		              DESCRIPTION
		              		  "Rate Limiting Defense for Internal SIP Servers: Number of SIP Requests from Non-Trusted Users"
		              ::= { voipDOSSipRateLimitingEntry 8 }


	-- Call Admission Control Subtree
 	voipCAC		OBJECT IDENTIFIER ::= { voip 7 }
	voipCACConcurrentCalls		OBJECT IDENTIFIER ::= { voipCAC 1 }

	voipCACConcurrentCallsConfThreshold OBJECT-TYPE
      		SYNTAX  Integer32
			MAX-ACCESS read-only
			STATUS  current
			DESCRIPTION
				"Number of Concurrent Calls: Configured Threshold"
			::= {voipCACConcurrentCalls 1 }

	voipCACConcurrentCallsCurrentVal OBJECT-TYPE
      		SYNTAX  Integer32
			MAX-ACCESS read-only
			STATUS  current
			DESCRIPTION
				"Number of Concurrent Calls: Configured Threshold"
			::= {voipCACConcurrentCalls 2 }

	voipStatCode OBJECT-TYPE
      		SYNTAX  Integer32
			MAX-ACCESS read-only
			STATUS  current
			DESCRIPTION
				"Status code"
			::= {voip 101 }

	voipStatShortDescr OBJECT-TYPE
      		SYNTAX  DisplayString
			MAX-ACCESS read-only
			STATUS  current
			DESCRIPTION
				"Status short description"
			::= {voip 102 }

	voipStatLongDescr OBJECT-TYPE
      		SYNTAX  DisplayString
			MAX-ACCESS read-only
			STATUS  current
			DESCRIPTION
				"Status long description"
			::= {voip 103 }

	voipServicePack OBJECT-TYPE
      		SYNTAX  DisplayString
			MAX-ACCESS read-only
			STATUS  current
			DESCRIPTION
				"Service Pack"
			::= {voip 999 }

		--identityAwareness statuses:

 	identityAwarenessProductName OBJECT-TYPE
      		SYNTAX  DisplayString
			MAX-ACCESS read-only
			STATUS  current
			DESCRIPTION
				"Product Name"
			::= {identityAwareness 1 }


 	identityAwarenessAuthUsers OBJECT-TYPE
      		SYNTAX  Integer32
			MAX-ACCESS read-only
			STATUS  current
			DESCRIPTION
				"Number of users authenticated to the gateway"
			::= {identityAwareness 2 }

 	identityAwarenessUnAuthUsers OBJECT-TYPE
      		SYNTAX  Integer32
			MAX-ACCESS read-only
			STATUS  current
			DESCRIPTION
				"Number of unauthenticated guests"
			::= {identityAwareness 3 }

 	identityAwarenessAuthUsersKerberos OBJECT-TYPE
      		SYNTAX  Integer32
			MAX-ACCESS read-only
			STATUS  current
			DESCRIPTION
				"Number of authenticated users by Kerberos method"
			::= {identityAwareness 4 }

 	identityAwarenessAuthMachKerberos OBJECT-TYPE
      		SYNTAX  Integer32
			MAX-ACCESS read-only
			STATUS  current
			DESCRIPTION
				"Number of authenticated machines by Kerberos method"
			::= {identityAwareness 5 }

	identityAwarenessAuthUsersPass OBJECT-TYPE
      		SYNTAX  Integer32
			MAX-ACCESS read-only
			STATUS  current
			DESCRIPTION
				"Number of authenticated users by User name and password method"
			::= {identityAwareness 6 }

	identityAwarenessAuthUsersADQuery OBJECT-TYPE
      		SYNTAX  Integer32
			MAX-ACCESS read-only
			STATUS  current
			DESCRIPTION
				"Number of authenticated users by ADQuery method"
			::= {identityAwareness 7 }

    identityAwarenessAuthMachADQuery OBJECT-TYPE
      		SYNTAX  Integer32
			MAX-ACCESS read-only
			STATUS  current
			DESCRIPTION
				"Number of authenticated machines by ADQuery method"
			::= {identityAwareness 8 }

    identityAwarenessLoggedInAgent OBJECT-TYPE
      		SYNTAX  Integer32
			MAX-ACCESS read-only
			STATUS  current
			DESCRIPTION
				"Number of users that are logged in with agents"
			::= {identityAwareness 9 }

	identityAwarenessLoggedInCaptivePortal OBJECT-TYPE
      		SYNTAX  Integer32
			MAX-ACCESS read-only
			STATUS  current
			DESCRIPTION
				"Number of users that are logged in with Captive Portal"
			::= {identityAwareness 10 }

	identityAwarenessLoggedInADQuery OBJECT-TYPE
      		SYNTAX  Integer32
			MAX-ACCESS read-only
			STATUS  current
			DESCRIPTION
				"Number of users that are logged in with ADQuery"
			::= {identityAwareness 11 }

	identityAwarenessAntiSpoffProtection OBJECT-TYPE
      		SYNTAX  Integer32
			MAX-ACCESS read-only
			STATUS  current
			DESCRIPTION
				"Number of users with an active Traffic Anti-Spoffing protection"
			::= {identityAwareness 12 }

	identityAwarenessSuccUserLoginKerberos OBJECT-TYPE
      		SYNTAX  Integer32
			MAX-ACCESS read-only
			STATUS  current
			DESCRIPTION
				"Number of successfull Kerberos user login attempts"
			::= {identityAwareness 13 }

	identityAwarenessSuccMachLoginKerberos OBJECT-TYPE
      		SYNTAX  Integer32
			MAX-ACCESS read-only
			STATUS  current
			DESCRIPTION
				"Number of successfull Kerberos machine login attempts"
			::= {identityAwareness 14 }

	identityAwarenessSuccUserLoginPass OBJECT-TYPE
      		SYNTAX  Integer32
			MAX-ACCESS read-only
			STATUS  current
			DESCRIPTION
				"Number of successfull User Name And Password login attempts"
			::= {identityAwareness 15 }

	identityAwarenessSuccUserLoginADQuery OBJECT-TYPE
      		SYNTAX  Integer32
			MAX-ACCESS read-only
			STATUS  current
			DESCRIPTION
				"Number of successfull ADQuery user login attempts"
			::= {identityAwareness 16 }

	identityAwarenessSuccMachLoginADQuery OBJECT-TYPE
      		SYNTAX  Integer32
			MAX-ACCESS read-only
			STATUS  current
			DESCRIPTION
				"Number of successfull ADQuery machine login attempts"
			::= {identityAwareness 17 }

	identityAwarenessUnSuccUserLoginKerberos OBJECT-TYPE
      		SYNTAX  Integer32
			MAX-ACCESS read-only
			STATUS  current
			DESCRIPTION
				"Number of unsuccessfull Kerberos user login attempts"
			::= {identityAwareness 18 }

    identityAwarenessUnSuccMachLoginKerberos OBJECT-TYPE
      		SYNTAX  Integer32
			MAX-ACCESS read-only
			STATUS  current
			DESCRIPTION
				"Number of unsuccessfull Kerberos machine login attempts"
			::= {identityAwareness 19 }

	identityAwarenessUnSuccUserLoginPass OBJECT-TYPE
      		SYNTAX  Integer32
			MAX-ACCESS read-only
			STATUS  current
			DESCRIPTION
				"Number of unsuccessfull User Name And Password login attempts"
			::= {identityAwareness 20 }

	identityAwarenessSuccUserLDAP OBJECT-TYPE
      		SYNTAX  Integer32
			MAX-ACCESS read-only
			STATUS  current
			DESCRIPTION
				"Number of successful LDAP queries"
			::= {identityAwareness 21 }

	identityAwarenessUnSuccUserLDAP OBJECT-TYPE
      		SYNTAX  Integer32
			MAX-ACCESS read-only
			STATUS  current
			DESCRIPTION
				"Number of unsuccessful LDAP queries"
			::= {identityAwareness 22 }

	identityAwarenessDataTrans OBJECT-TYPE
      		SYNTAX  Integer32
			MAX-ACCESS read-only
			STATUS  current
			DESCRIPTION
				"How much data did  gateway transmitted"
			::= {identityAwareness 23 }

   	identityAwarenessDistributedEnvTable OBJECT-TYPE
     		SYNTAX  SEQUENCE OF IdentityAwarenessDistributedEnvEntry
		MAX-ACCESS  not-accessible
		STATUS  current
		DESCRIPTION
			"Table for distributed environments"
		::= {identityAwareness 24 }


	identityAwarenessDistributedEnvEntry OBJECT-TYPE
	  		SYNTAX  IdentityAwarenessDistributedEnvEntry
	  		MAX-ACCESS  not-accessible
	  		STATUS  current
	  		DESCRIPTION "No description available"
	  		INDEX   { identityAwarenessDistributedEnvTableIndex }
	  		::= { identityAwarenessDistributedEnvTable 1 }

	IdentityAwarenessDistributedEnvEntry ::=
      		SEQUENCE {
      			identityAwarenessDistributedEnvTableIndex
		          			Unsigned32,
				identityAwarenessDistributedEnvTableGwName
		          			DisplayString,
 				identityAwarenessDistributedEnvTableDisconnections
		          			INTEGER,
 				identityAwarenessDistributedEnvTableBruteForceAtt
		          			INTEGER,
				identityAwarenessDistributedEnvTableStatus
		          			INTEGER,
				identityAwarenessDistributedEnvTableIsLocal
		          			INTEGER
		        }

		identityAwarenessDistributedEnvTableIndex OBJECT-TYPE
		              SYNTAX  Unsigned32
		              MAX-ACCESS not-accessible
		              STATUS  current
		              DESCRIPTION
		              		  "Distributed Environments: Table Index"
		              ::= { identityAwarenessDistributedEnvEntry 1 }

		identityAwarenessDistributedEnvTableGwName OBJECT-TYPE
		              SYNTAX  DisplayString
		              MAX-ACCESS read-only
		              STATUS  current
		              DESCRIPTION
		              		  "Distributed Environments: GW Name"
		              ::= { identityAwarenessDistributedEnvEntry 2 }

		identityAwarenessDistributedEnvTableDisconnections OBJECT-TYPE
		              SYNTAX  Integer32
		              MAX-ACCESS read-only
		              STATUS  current
		              DESCRIPTION
		              		  "Distributed Environments: Number of disconnections"
		              ::= { identityAwarenessDistributedEnvEntry 3 }

		identityAwarenessDistributedEnvTableBruteForceAtt OBJECT-TYPE
		              SYNTAX  Integer32
		              MAX-ACCESS read-only
		              STATUS  current
		              DESCRIPTION
		              		  "Distributed Environments: Number of brute force attack detected"
		              ::= { identityAwarenessDistributedEnvEntry 4 }

 		identityAwarenessDistributedEnvTableStatus OBJECT-TYPE
		              SYNTAX  Integer32
		              MAX-ACCESS read-only
		              STATUS  current
		              DESCRIPTION
		              		  "Distributed Environments: Status
		              		   Possible values include:
			  		           Ok		0
							   Error	2"
		              ::= { identityAwarenessDistributedEnvEntry 5 }

		identityAwarenessDistributedEnvTableIsLocal OBJECT-TYPE
		              SYNTAX  Integer32
		              MAX-ACCESS read-only
		              STATUS  current
		              DESCRIPTION
		              		  "Distributed Environments: Is local
		              		   Possible values include:
			  		           False	0
			  		           True		1"
		              ::= { identityAwarenessDistributedEnvEntry 6 }

		identityAwarenessADQueryStatusTable OBJECT-TYPE
     		SYNTAX  SEQUENCE OF IdentityAwarenessADQueryStatusEntry
		MAX-ACCESS  not-accessible
		STATUS  current
		DESCRIPTION
			"Table for AD Query status"
		::= {identityAwareness 25 }


	identityAwarenessADQueryStatusEntry OBJECT-TYPE
	  		SYNTAX  IdentityAwarenessADQueryStatusEntry
	  		MAX-ACCESS  not-accessible
	  		STATUS  current
	  		DESCRIPTION "No description available"
	  		INDEX   { identityAwarenessADQueryStatusTableIndex }
	  		::= { identityAwarenessADQueryStatusTable 1 }

	IdentityAwarenessADQueryStatusEntry ::=
      		SEQUENCE {
      			identityAwarenessADQueryStatusTableIndex
		          			Unsigned32,
				identityAwarenessADQueryStatusCurrStatus
		          			INTEGER,
 				identityAwarenessADQueryStatusDomainName
		          			DisplayString,
 				identityAwarenessADQueryStatusDomainIP
		          			IpAddress,
				identityAwarenessADQueryStatusEvents
		          			INTEGER
		        }

		identityAwarenessADQueryStatusTableIndex OBJECT-TYPE
		              SYNTAX  Unsigned32
		              MAX-ACCESS not-accessible
		              STATUS  current
		              DESCRIPTION
		              		  "AD Query Status: Table Index"
		              ::= { identityAwarenessADQueryStatusEntry 1 }

		identityAwarenessADQueryStatusCurrStatus OBJECT-TYPE
		              SYNTAX  Integer32
		              MAX-ACCESS read-only
		              STATUS  current
		              DESCRIPTION
		              		  "AD Query Status: Current status
		              		   Possible values include:
			  		           Ok					0
						   Ok 1
			  		           Bad Credentials 2
			  		           Connectivity Error 3
			  		           Domain Controller Internal Error 4
			  		           Connection Time Out 5
						   WMI permission denied 7
					  	   Domain Controller unreachable 8
						   Domain Controller RPC Internal Error 9
						   Connection refused 10"
		              ::= { identityAwarenessADQueryStatusEntry 2 }

		identityAwarenessADQueryStatusDomainName OBJECT-TYPE
		              SYNTAX  DisplayString
		              MAX-ACCESS read-only
		              STATUS  current
		              DESCRIPTION
		              		  "AD Query Status: Domain name"
		              ::= { identityAwarenessADQueryStatusEntry 3 }

		identityAwarenessADQueryStatusDomainIP OBJECT-TYPE
		              SYNTAX  IpAddress
		              MAX-ACCESS read-only
		              STATUS  current
		              DESCRIPTION
		              		  "AD Query Status: Domain IP"
		              ::= { identityAwarenessADQueryStatusEntry 4 }

 		identityAwarenessADQueryStatusEvents OBJECT-TYPE
		              SYNTAX  Integer32
		              MAX-ACCESS read-only
		              STATUS  current
		              DESCRIPTION
		              		  "AD Query Status: Number of events"
		              ::= { identityAwarenessADQueryStatusEntry 5 }

       	identityAwarenessRADIUSAccounting OBJECT-TYPE
      		SYNTAX  Unsigned32
			MAX-ACCESS read-only
			STATUS  current
			DESCRIPTION
				"Number of identities logged in with RADIUS Accounting"
			::= {identityAwareness 39 }

		identityAwarenessIdentityCollectorActiveDirectory OBJECT-TYPE
      		SYNTAX  Unsigned32
			MAX-ACCESS read-only
			STATUS  current
			DESCRIPTION
				"Number of identities logged in with Identity Collector Active Directory"
			::= {identityAwareness 40 }

		identityAwarenessIdentityCollectorCiscoISE OBJECT-TYPE
      		SYNTAX  Unsigned32
			MAX-ACCESS read-only
			STATUS  current
			DESCRIPTION
				"Number of identities logged in with Identity Collector Cisco ISE"
			::= {identityAwareness 41 }

		identityAwarenessTerminalServer OBJECT-TYPE
      		SYNTAX  Unsigned32
			MAX-ACCESS read-only
			STATUS  current
			DESCRIPTION
				"Number of identities logged in with terminal server"
			::= {identityAwareness 42 }

		identityAwarenessRemoteAccess OBJECT-TYPE
      		SYNTAX  Unsigned32
			MAX-ACCESS read-only
			STATUS  current
			DESCRIPTION
				"Number of identities logged in with Remote Access"
			::= {identityAwareness 43 }

		identityAwarenessIdentityWebAPI OBJECT-TYPE
      		SYNTAX  Unsigned32
			MAX-ACCESS read-only
			STATUS  current
			DESCRIPTION
				"Number of identities logged in with Identity Web API"
			::= {identityAwareness 44 }

	   identityAwarenessStatus OBJECT-TYPE
      		SYNTAX  Integer32
			MAX-ACCESS read-only
			STATUS  current
			DESCRIPTION
				"Identity Awarness Status code"
			::= {identityAwareness 101 }

	   identityAwarenessStatusShortDesc OBJECT-TYPE
      		SYNTAX  DisplayString
			MAX-ACCESS read-only
			STATUS  current
			DESCRIPTION
				"Identity Awarness Status - Short Description"
			::= {identityAwareness 102 }

	   identityAwarenessStatusLongDesc OBJECT-TYPE
      		SYNTAX  DisplayString
			MAX-ACCESS read-only
			STATUS  current
			DESCRIPTION
				"Identity Awarness Status  - Long Description"
			::= {identityAwareness 103 }

       	--applicationControl statuses:

    applicationControlSubscription OBJECT IDENTIFIER ::= { applicationControl 1 }

	applicationControlSubscriptionStatus OBJECT-TYPE
      		SYNTAX  DisplayString
			MAX-ACCESS read-only
			STATUS  current
			DESCRIPTION
				"Subscription status
				 Possible values include:
	           	 valid, expired, about-to-expire, not-associated, unknown"
			::= {applicationControlSubscription 1 }

	applicationControlSubscriptionExpDate OBJECT-TYPE
      		SYNTAX  DisplayString
			MAX-ACCESS read-only
			STATUS  current
			DESCRIPTION
				"Application Control subscription expiration date"
			::= {applicationControlSubscription 2 }

    applicationControlSubscriptionDesc OBJECT-TYPE
      		SYNTAX  DisplayString
			MAX-ACCESS read-only
			STATUS  current
			DESCRIPTION
				"Subscription description"
			::= {applicationControlSubscription 3 }

	applicationControlUpdate OBJECT IDENTIFIER ::= { applicationControl 2 }

	applicationControlUpdateStatus OBJECT-TYPE
      		SYNTAX  DisplayString
			MAX-ACCESS read-only
			STATUS  current
			DESCRIPTION
				"Update status
				 Possible values include:
	           	 failed, up-to-date, new, degrade, unknown"
			::= {applicationControlUpdate 1 }

	applicationControlUpdateDesc OBJECT-TYPE
      		SYNTAX  DisplayString
			MAX-ACCESS read-only
			STATUS  current
			DESCRIPTION
				"Update description"
			::= {applicationControlUpdate 2 }

    applicationControlNextUpdate OBJECT-TYPE
      		SYNTAX  DisplayString
			MAX-ACCESS read-only
			STATUS  current
			DESCRIPTION
				"Next update description"
			::= {applicationControlUpdate 3 }

	applicationControlVersion OBJECT-TYPE
      		SYNTAX  DisplayString
			MAX-ACCESS read-only
			STATUS  current
			DESCRIPTION
				"Application Control database version"
			::= {applicationControlUpdate 4 }

	applicationControlStatusCode OBJECT-TYPE
      		SYNTAX  Integer32
			MAX-ACCESS read-only
			STATUS  current
			DESCRIPTION
				"Application Control Status code"
			::= {applicationControl 101 }

   applicationControlStatusShortDesc OBJECT-TYPE
     		SYNTAX  DisplayString
		MAX-ACCESS read-only
		STATUS  current
		DESCRIPTION
			"Application Control Status - Short Description"
		::= {applicationControl 102 }

   applicationControlStatusLongDesc OBJECT-TYPE
     		SYNTAX  DisplayString
		MAX-ACCESS read-only
		STATUS  current
		DESCRIPTION
			"Application Control Status  - Long Description"
		::= {applicationControl 103 }

--DLP statuses:

    exchangeAgentsStatus OBJECT IDENTIFIER ::= { dlp 1 }

    exchangeAgentsStatusTable OBJECT-TYPE
     		SYNTAX  SEQUENCE OF ExchangeAgentsStatusEntry
		MAX-ACCESS  not-accessible
		STATUS  current
		DESCRIPTION
			"Table for exchange agents status"
		::= {exchangeAgentsStatus 1 }


	exchangeAgentsStatusEntry OBJECT-TYPE
	  		SYNTAX  ExchangeAgentsStatusEntry
	  		MAX-ACCESS  not-accessible
	  		STATUS  current
	  		DESCRIPTION "No description available"
	  		INDEX   { exchangeAgentsStatusTableIndex }
	  		::= { exchangeAgentsStatusTable 1 }

	ExchangeAgentsStatusEntry ::=
      		SEQUENCE {
      			exchangeAgentsStatusTableIndex
		          			Unsigned32,
				exchangeAgentName
		          			DisplayString,
 				exchangeAgentStatus
		          			DisplayString,
		        exchangeAgentTotalMsg
		          			INTEGER,
		        exchangeAgentTotalScannedMsg
		          			INTEGER,
                exchangeAgentDroppedMsg
		          			INTEGER,
                exchangeAgentUpTime
		          			INTEGER,
                exchangeAgentTimeSinceLastMsg
		          			INTEGER,
                exchangeAgentQueueLen
		          			INTEGER,
                exchangeQueueLen
		          			INTEGER,
                exchangeAgentAvgTimePerMsg
		          			DisplayString,
                exchangeAgentAvgTimePerScannedMsg
		          			DisplayString,
		        exchangeAgentVersion
		          			DisplayString,
		        exchangeCPUUsage
		          			DisplayString,
		        exchangeMemoryUsage
		          			DisplayString,
		        exchangeAgentPolicyTimeStamp
		          			INTEGER
		        }

		exchangeAgentsStatusTableIndex OBJECT-TYPE
		              SYNTAX  Unsigned32
		              MAX-ACCESS not-accessible
		              STATUS  current
		              DESCRIPTION
		              		  "Exchange agents: Table Index"
		              ::= { exchangeAgentsStatusEntry 1 }

		exchangeAgentName OBJECT-TYPE
		              SYNTAX  DisplayString
		              MAX-ACCESS read-only
		              STATUS  current
		              DESCRIPTION
		              		  "Exchange agent name"
		              ::= { exchangeAgentsStatusEntry 2 }

		exchangeAgentStatus OBJECT-TYPE
		              SYNTAX  DisplayString
		              MAX-ACCESS read-only
		              STATUS  current
		              DESCRIPTION
		              		  "Exchange agent status"
		              ::= { exchangeAgentsStatusEntry 3 }

		exchangeAgentTotalMsg OBJECT-TYPE
		              SYNTAX  Integer32
		              MAX-ACCESS read-only
		              STATUS  current
		              DESCRIPTION
		              		  "Exchange agent total messages"
		              ::= { exchangeAgentsStatusEntry 4 }

		exchangeAgentTotalScannedMsg OBJECT-TYPE
		              SYNTAX  Integer32
		              MAX-ACCESS read-only
		              STATUS  current
		              DESCRIPTION
		              		  "Exchange agent total scanned messages"
		              ::= { exchangeAgentsStatusEntry 5 }

		exchangeAgentDroppedMsg OBJECT-TYPE
		              SYNTAX  Integer32
		              MAX-ACCESS read-only
		              STATUS  current
		              DESCRIPTION
		              		  "Exchange agent dropped messages"
		              ::= { exchangeAgentsStatusEntry 6 }

		exchangeAgentUpTime OBJECT-TYPE
		              SYNTAX  Integer32
		              MAX-ACCESS read-only
		              STATUS  current
		              DESCRIPTION
		              		  "Number of seconds that the exchange agent is up"
		              ::= { exchangeAgentsStatusEntry 7 }

		exchangeAgentTimeSinceLastMsg OBJECT-TYPE
		              SYNTAX  Integer32
		              MAX-ACCESS read-only
		              STATUS  current
		              DESCRIPTION
		              		  "Number of seconds since the last message passed through the exchange agent"
		              ::= { exchangeAgentsStatusEntry 8 }

		exchangeAgentQueueLen OBJECT-TYPE
		              SYNTAX  Integer32
		              MAX-ACCESS read-only
		              STATUS  current
		              DESCRIPTION
		              		  "The current exchange agent message queue length"
		              ::= { exchangeAgentsStatusEntry 9 }

        exchangeQueueLen OBJECT-TYPE
		              SYNTAX  Integer32
		              MAX-ACCESS read-only
		              STATUS  current
		              DESCRIPTION
		              		  "The cumulative exchange server queue length"
		              ::= { exchangeAgentsStatusEntry 10 }


		exchangeAgentAvgTimePerMsg OBJECT-TYPE
		              SYNTAX  DisplayString
		              MAX-ACCESS read-only
		              STATUS  current
		              DESCRIPTION
		              		  "The average (for all messages) latency added by the exchange agent"
		              ::= { exchangeAgentsStatusEntry 11 }

		exchangeAgentAvgTimePerScannedMsg OBJECT-TYPE
		              SYNTAX  DisplayString
		              MAX-ACCESS read-only
		              STATUS  current
		              DESCRIPTION
		              		  "The average (for scanned messages only) latency added by the exchange agent"
		              ::= { exchangeAgentsStatusEntry 12 }

		exchangeAgentVersion OBJECT-TYPE
		              SYNTAX  DisplayString
		              MAX-ACCESS read-only
		              STATUS  current
		              DESCRIPTION
		              		  "The version of the exchange agent"
		              ::= { exchangeAgentsStatusEntry 13 }

		exchangeCPUUsage OBJECT-TYPE
		              SYNTAX  DisplayString
		              MAX-ACCESS read-only
		              STATUS  current
		              DESCRIPTION
		              		  "The exchange server CPU usage in percentage"
		              ::= { exchangeAgentsStatusEntry 14 }

		exchangeMemoryUsage OBJECT-TYPE
		              SYNTAX  DisplayString
		              MAX-ACCESS read-only
		              STATUS  current
		              DESCRIPTION
		              		  "The exchange server memory usage in percentage"
		              ::= { exchangeAgentsStatusEntry 15 }

		exchangeAgentPolicyTimeStamp OBJECT-TYPE
		              SYNTAX  Integer32
		              MAX-ACCESS read-only
		              STATUS  current
		              DESCRIPTION
		              		  "The time of the last policy retrieved by the exchange agent from the gateway"
		              ::= { exchangeAgentsStatusEntry 16 }

	dlpVersionString OBJECT-TYPE
      		SYNTAX  DisplayString
			MAX-ACCESS read-only
			STATUS  current
			DESCRIPTION
				"Version"
			::= {dlp 11 }

	dlpLicenseStatus OBJECT-TYPE
      		SYNTAX  DisplayString
			MAX-ACCESS read-only
			STATUS  current
			DESCRIPTION
				"License status"
			::= {dlp 12 }

	dlpLdapStatus OBJECT-TYPE
      		SYNTAX  DisplayString
			MAX-ACCESS read-only
			STATUS  current
			DESCRIPTION
				"LDAP Status"
			::= {dlp 13 }

	dlpTotalScans OBJECT-TYPE
      		SYNTAX  DisplayString
			MAX-ACCESS read-only
			STATUS  current
			DESCRIPTION
				"Traffic scans"
			::= {dlp 14 }

	dlpSMTPScans OBJECT-TYPE
      		SYNTAX  DisplayString
			MAX-ACCESS read-only
			STATUS  current
			DESCRIPTION
				"Scanned e-mails"
			::= {dlp 15 }

	dlpSMTPIncidents OBJECT-TYPE
      		SYNTAX  DisplayString
			MAX-ACCESS read-only
			STATUS  current
			DESCRIPTION
				"E-mail incidents"
			::= {dlp 16 }

	dlpLastSMTPScan OBJECT-TYPE
      		SYNTAX  DisplayString
			MAX-ACCESS read-only
			STATUS  current
			DESCRIPTION
				"Last E-mail scan"
			::= {dlp 17 }

	dlpNumQuarantined OBJECT-TYPE
      		SYNTAX  Integer32
			MAX-ACCESS read-only
			STATUS  current
			DESCRIPTION
				"Quarantined messages"
			::= {dlp 18 }

	dlpQrntMsgsSize OBJECT-TYPE
      		SYNTAX  Integer32
			MAX-ACCESS read-only
			STATUS  current
			DESCRIPTION
				"Size of quarantined messages"
			::= {dlp 19 }

	dlpSentEMails OBJECT-TYPE
      		SYNTAX  DisplayString
			MAX-ACCESS read-only
			STATUS  current
			DESCRIPTION
				"Sent e-mails"
			::= {dlp 20 }

	dlpExpiredEMails OBJECT-TYPE
      		SYNTAX  DisplayString
			MAX-ACCESS read-only
			STATUS  current
			DESCRIPTION
				"Expired e-mails"
			::= {dlp 21 }

	dlpDiscardEMails OBJECT-TYPE
      		SYNTAX  DisplayString
			MAX-ACCESS read-only
			STATUS  current
			DESCRIPTION
				"Discarded e-mails"
			::= {dlp 22 }

	dlpPostfixQLen OBJECT-TYPE
      		SYNTAX  Integer32
			MAX-ACCESS read-only
			STATUS  current
			DESCRIPTION
				"Postfix queue length"
			::= {dlp 23 }

	dlpPostfixErrors OBJECT-TYPE
      		SYNTAX  Integer32
			MAX-ACCESS read-only
			STATUS  current
			DESCRIPTION
				"Postfix errors"
			::= {dlp 24 }

	dlpPostfixQOldMsg OBJECT-TYPE
      		SYNTAX  Integer32
			MAX-ACCESS read-only
			STATUS  current
			DESCRIPTION
				"E-mails in queue older than 1 hour"
			::= {dlp 25 }

	dlpPostfixQMsgsSz OBJECT-TYPE
      		SYNTAX  Integer32
			MAX-ACCESS read-only
			STATUS  current
			DESCRIPTION
				"Size of messages in queue"
			::= {dlp 26 }

	dlpPostfixQFreeSp OBJECT-TYPE
      		SYNTAX  Integer32
			MAX-ACCESS read-only
			STATUS  current
			DESCRIPTION
				"Free space in queue"
			::= {dlp 27 }

	dlpQrntFreeSpace OBJECT-TYPE
      		SYNTAX  DisplayString
			MAX-ACCESS read-only
			STATUS  current
			DESCRIPTION
				"Free space for quarantine"
			::= {dlp 28 }

	dlpQrntStatus OBJECT-TYPE
      		SYNTAX  DisplayString
			MAX-ACCESS read-only
			STATUS  current
			DESCRIPTION
				"Quarantine status"
			::= {dlp 29 }

	dlpHttpScans OBJECT-TYPE
      		SYNTAX  DisplayString
			MAX-ACCESS read-only
			STATUS  current
			DESCRIPTION
				"HTTP scans"
			::= {dlp 30 }

	dlpHttpIncidents OBJECT-TYPE
      		SYNTAX  DisplayString
			MAX-ACCESS read-only
			STATUS  current
			DESCRIPTION
				"HTTP incidents"
			::= {dlp 31 }

	dlpHttpLastScan OBJECT-TYPE
      		SYNTAX  DisplayString
			MAX-ACCESS read-only
			STATUS  current
			DESCRIPTION
				"HTTP last scan"
			::= {dlp 32 }

	dlpFtpScans OBJECT-TYPE
      		SYNTAX  DisplayString
			MAX-ACCESS read-only
			STATUS  current
			DESCRIPTION
				"FTP scans"
			::= {dlp 33 }

	dlpFtpIncidents OBJECT-TYPE
      		SYNTAX  DisplayString
			MAX-ACCESS read-only
			STATUS  current
			DESCRIPTION
				"FTP incidents"
			::= {dlp 34 }

	dlpFtpLastScan OBJECT-TYPE
     		SYNTAX  DisplayString
		MAX-ACCESS read-only
		STATUS  current
		DESCRIPTION
			"FTP last scan"
		::= {dlp 35 }

	dlpBypassStatus OBJECT-TYPE
      		SYNTAX  DisplayString
			MAX-ACCESS read-only
			STATUS  current
			DESCRIPTION
				"Bypass status"
			::= {dlp 36 }

	dlpUserCheckClnts OBJECT-TYPE
      		SYNTAX  Integer32
			MAX-ACCESS read-only
			STATUS  current
			DESCRIPTION
				"UserCheck clients"
			::= {dlp 37 }

	dlpLastPolStatus OBJECT-TYPE
      		SYNTAX  DisplayString
			MAX-ACCESS read-only
			STATUS  current
			DESCRIPTION
				"Last policy install status"
			::= {dlp 38 }

	dlpStatusCode OBJECT-TYPE
      		SYNTAX  Integer32
			MAX-ACCESS read-only
			STATUS  current
			DESCRIPTION
				"DLP Status code"
			::= {dlp 101 }

   dlpStatusShortDesc OBJECT-TYPE
     		SYNTAX  DisplayString
		MAX-ACCESS read-only
		STATUS  current
		DESCRIPTION
			"DLP Status - Short Description"
		::= {dlp 102 }

   dlpStatusLongDesc OBJECT-TYPE
     		SYNTAX  DisplayString
		MAX-ACCESS read-only
		STATUS  current
		DESCRIPTION
			"DLP Status  - Long Description"
		::= {dlp 103 }


	--thresholds statuses:

	  thresholdPolicy  OBJECT-TYPE
            SYNTAX  DisplayString
            MAX-ACCESS read-only
            STATUS  current
            DESCRIPTION
	  		        "The name of the policy"
            ::= { thresholds 1 }


      thresholdState  OBJECT-TYPE
            SYNTAX  Integer32
            MAX-ACCESS read-only
            STATUS  current
            DESCRIPTION
	  		        "State of the thresholds engine: Ok (1), Error (0)"
            ::= { thresholds 2 }

      thresholdStateDesc  OBJECT-TYPE
            SYNTAX  DisplayString
            MAX-ACCESS read-only
            STATUS  current
            DESCRIPTION
	  		        "Description for the state"
            ::= { thresholds 3 }

      thresholdEnabled  OBJECT-TYPE
            SYNTAX  Integer32
            MAX-ACCESS read-only
            STATUS  current
            DESCRIPTION
	  		        "Number of enabled thresholds (Monitoring statuses)"
            ::= { thresholds 4 }

       thresholdActive  OBJECT-TYPE
            SYNTAX  Integer32
            MAX-ACCESS read-only
            STATUS  current
            DESCRIPTION
	  		        "Number of active thresholds (Generating alerts)"
            ::= { thresholds 5 }

       thresholdEventsSinceStartup  OBJECT-TYPE
            SYNTAX  Integer32
            MAX-ACCESS read-only
            STATUS  current
            DESCRIPTION
	  		        "Number of activated thresholds since startup"
            ::= { thresholds 6 }



	  thresholdActiveEventsTable OBJECT-TYPE
	          SYNTAX  SEQUENCE OF  ThresholdActiveEventsEntry
			  MAX-ACCESS  not-accessible
			  STATUS  current
			  DESCRIPTION "No description available"
			   ::= { thresholds 7 }


	  thresholdActiveEventsEntry OBJECT-TYPE
	          SYNTAX  ThresholdActiveEventsEntry
	          MAX-ACCESS  not-accessible
	          STATUS  current
	          DESCRIPTION "No description available"
	          INDEX   { thresholdActiveEventsIndex }
	          ::= { thresholdActiveEventsTable 1 }

      ThresholdActiveEventsEntry ::=
              SEQUENCE {
                 thresholdActiveEventsIndex
                      Unsigned32,
                 thresholdActiveEventName
                      DisplayString,
                 thresholdActiveEventCategory
					  DisplayString,
				 thresholdActiveEventSeverity
					  INTEGER,
				 thresholdActiveEventSubject
					  DisplayString,
				 thresholdActiveEventSubjectValue
					  DisplayString,
				 thresholdActiveEventActivationTime
					  DisplayString,
				 thresholdActiveEventState
					  DisplayString
              }

      thresholdActiveEventsIndex OBJECT-TYPE
            SYNTAX  Unsigned32
            MAX-ACCESS not-accessible
            STATUS  current
            DESCRIPTION "No description available"
            ::= { thresholdActiveEventsEntry 1 }

      thresholdActiveEventName OBJECT-TYPE
            SYNTAX  DisplayString
            MAX-ACCESS read-only
            STATUS  current
			DESCRIPTION
	  		        "Name of the threshold"
            ::= { thresholdActiveEventsEntry 2 }

      thresholdActiveEventCategory OBJECT-TYPE
            SYNTAX  DisplayString
            MAX-ACCESS read-only
            STATUS  current
            DESCRIPTION
	  		        "The category of the threshold"
            ::= { thresholdActiveEventsEntry 3 }

      thresholdActiveEventSeverity OBJECT-TYPE
            SYNTAX  Integer32
            MAX-ACCESS read-only
            STATUS  current
            DESCRIPTION
	  		        "Severity of the threshold: Cleared (0), Low (1), Medium (2), High (3), Critical (4)"
            ::= { thresholdActiveEventsEntry 4 }

       thresholdActiveEventSubject OBJECT-TYPE
            SYNTAX  DisplayString
            MAX-ACCESS read-only
            STATUS  current
            DESCRIPTION
	  		        "The name of the status been checked by the threshold"
            ::= { thresholdActiveEventsEntry 5 }

       thresholdActiveEventSubjectValue OBJECT-TYPE
            SYNTAX  DisplayString
            MAX-ACCESS read-only
            STATUS  current
            DESCRIPTION
	  		        "The value of the status been checked by the threshold"
            ::= { thresholdActiveEventsEntry 6 }

       thresholdActiveEventActivationTime OBJECT-TYPE
            SYNTAX  DisplayString
            MAX-ACCESS read-only
            STATUS  current
            DESCRIPTION
	  		        "The activation time of the event"
            ::= { thresholdActiveEventsEntry 7 }

       thresholdActiveEventState OBJECT-TYPE
            SYNTAX  DisplayString
            MAX-ACCESS read-only
            STATUS  current
            DESCRIPTION
	  		        "The state of the event [Active\Clearing]"
            ::= { thresholdActiveEventsEntry 8 }

       thresholdDestinationsTable OBJECT-TYPE
	          SYNTAX  SEQUENCE OF  ThresholdDestinationsEntry
			  MAX-ACCESS  not-accessible
			  STATUS  current
			  DESCRIPTION "No description available"
			   ::= { thresholds 8 }


	  thresholdDestinationsEntry OBJECT-TYPE
	          SYNTAX  ThresholdDestinationsEntry
	          MAX-ACCESS  not-accessible
	          STATUS  current
	          DESCRIPTION "No description available"
	          INDEX   { thresholdDestinationIndex }
	          ::= { thresholdDestinationsTable 1 }

      ThresholdDestinationsEntry ::=
              SEQUENCE {
                 thresholdDestinationIndex
                      Unsigned32,
                 thresholdDestinationName
                      DisplayString,
                 thresholdDestinationType
					  DisplayString,
				 thresholdSendingState
					  INTEGER,
				 thresholdSendingStateDesc
					  DisplayString,
				 thresholdAlertCount
					  INTEGER
              }

      thresholdDestinationIndex OBJECT-TYPE
            SYNTAX  Unsigned32
            MAX-ACCESS not-accessible
            STATUS  current
            DESCRIPTION "No description available"
            ::= { thresholdDestinationsEntry 1 }

      thresholdDestinationName OBJECT-TYPE
            SYNTAX  DisplayString
            MAX-ACCESS read-only
            STATUS  current
			DESCRIPTION
	  		        "Name of the destination"
            ::= { thresholdDestinationsEntry 2 }

      thresholdDestinationType OBJECT-TYPE
            SYNTAX  DisplayString
            MAX-ACCESS read-only
            STATUS  current
            DESCRIPTION
	  		        "The type of the destination"
            ::= { thresholdDestinationsEntry 3 }

      thresholdSendingState OBJECT-TYPE
            SYNTAX  Integer32
            MAX-ACCESS read-only
            STATUS  current
            DESCRIPTION
	  		        "Alerts transmission status: Ok (0), Error (1)"
            ::= { thresholdDestinationsEntry 4 }

       thresholdSendingStateDesc OBJECT-TYPE
            SYNTAX  DisplayString
            MAX-ACCESS read-only
            STATUS  current
            DESCRIPTION
	  		        "Description for the alert transmission state"
            ::= { thresholdDestinationsEntry 5 }

       thresholdAlertCount OBJECT-TYPE
            SYNTAX  Integer32
            MAX-ACCESS read-only
            STATUS  current
            DESCRIPTION
	  		        "Number of alerts transmitted to the destination"
            ::= { thresholdDestinationsEntry 6 }

       thresholdErrorsTable OBJECT-TYPE
	          SYNTAX  SEQUENCE OF  ThresholdErrorsEntry
			  MAX-ACCESS  not-accessible
			  STATUS  current
			  DESCRIPTION "No description available"
			   ::= { thresholds 9 }


	  thresholdErrorsEntry OBJECT-TYPE
	          SYNTAX  ThresholdErrorsEntry
	          MAX-ACCESS  not-accessible
	          STATUS  current
	          DESCRIPTION "No description available"
	          INDEX   { thresholdErrorIndex }
	          ::= { thresholdErrorsTable 1 }

      ThresholdErrorsEntry ::=
              SEQUENCE {
                 thresholdErrorIndex
                      Unsigned32,
                 thresholdName
                      DisplayString,
                 thresholdThresholdOID
					  DisplayString,
				 thresholdErrorDesc
					  DisplayString,
				 thresholdErrorTime
					  DisplayString
			}

      thresholdErrorIndex OBJECT-TYPE
            SYNTAX  Unsigned32
            MAX-ACCESS not-accessible
            STATUS  current
            DESCRIPTION "No description available"
            ::= { thresholdErrorsEntry 1 }

      thresholdName OBJECT-TYPE
            SYNTAX  DisplayString
            MAX-ACCESS read-only
            STATUS  current
			DESCRIPTION
	  		        "Name of the threshold"
            ::= { thresholdErrorsEntry 2 }

      thresholdThresholdOID OBJECT-TYPE
            SYNTAX  DisplayString
            MAX-ACCESS read-only
            STATUS  current
            DESCRIPTION
	  		        "OID of the thresholds alert"
            ::= { thresholdErrorsEntry 3 }

      thresholdErrorDesc OBJECT-TYPE
            SYNTAX  DisplayString
            MAX-ACCESS read-only
            STATUS  current
            DESCRIPTION
	  		        "Description of the error"
            ::= { thresholdErrorsEntry 4 }

       thresholdErrorTime OBJECT-TYPE
            SYNTAX  DisplayString
            MAX-ACCESS read-only
            STATUS  current
            DESCRIPTION
	  		        "The occurrence time of the error"
            ::= { thresholdErrorsEntry 5 }


	--advanced urlf statuses:

    advancedUrlFilteringSubscription OBJECT IDENTIFIER ::= { advancedUrlFiltering 1 }

	advancedUrlFilteringSubscriptionStatus OBJECT-TYPE
      		SYNTAX  DisplayString
			MAX-ACCESS read-only
			STATUS  current
			DESCRIPTION
				"Subscription status
				 Possible values include:
	           	 valid, expired, about-to-expire, not-associated, unknown"
			::= {advancedUrlFilteringSubscription 1 }

	advancedUrlFilteringSubscriptionExpDate OBJECT-TYPE
      		SYNTAX  DisplayString
			MAX-ACCESS read-only
			STATUS  current
			DESCRIPTION
				"Application Control subscription expiration date"
			::= {advancedUrlFilteringSubscription 2 }

    advancedUrlFilteringSubscriptionDesc OBJECT-TYPE
      		SYNTAX  DisplayString
			MAX-ACCESS read-only
			STATUS  current
			DESCRIPTION
				"Subscription description"
			::= {advancedUrlFilteringSubscription 3 }

	advancedUrlFilteringUpdate OBJECT IDENTIFIER ::= { advancedUrlFiltering 2 }

	advancedUrlFilteringUpdateStatus OBJECT-TYPE
      		SYNTAX  DisplayString
			MAX-ACCESS read-only
			STATUS  current
			DESCRIPTION
				"Update status
				 Possible values include:
	           	 failed, up-to-date, new, degrade, unknown"
			::= {advancedUrlFilteringUpdate 1 }

	advancedUrlFilteringUpdateDesc OBJECT-TYPE
      		SYNTAX  DisplayString
			MAX-ACCESS read-only
			STATUS  current
			DESCRIPTION
				"Update description"
			::= {advancedUrlFilteringUpdate 2 }

    advancedUrlFilteringNextUpdate OBJECT-TYPE
      		SYNTAX  DisplayString
			MAX-ACCESS read-only
			STATUS  current
			DESCRIPTION
				"Next update description"
			::= {advancedUrlFilteringUpdate 3 }

	advancedUrlFilteringVersion OBJECT-TYPE
      		SYNTAX  DisplayString
			MAX-ACCESS read-only
			STATUS  current
			DESCRIPTION
				"Url Filtering database version"
			::= {advancedUrlFilteringUpdate 4 }

	advancedUrlFilteringRADStatus OBJECT IDENTIFIER ::= { advancedUrlFiltering 3 }

	advancedUrlFilteringRADStatusCode OBJECT-TYPE
      		SYNTAX  Integer32
			MAX-ACCESS read-only
			STATUS  current
			DESCRIPTION
				"RAD Status code"
			::= {advancedUrlFilteringRADStatus 1 }


	advancedUrlFilteringRADStatusDesc OBJECT-TYPE
      		SYNTAX  DisplayString
			MAX-ACCESS read-only
			STATUS  current
			DESCRIPTION
				"RAD status description"
			::= {advancedUrlFilteringRADStatus 2 }

	advancedUrlFilteringStatusCode OBJECT-TYPE
      		SYNTAX  Integer32
			MAX-ACCESS read-only
			STATUS  current
			DESCRIPTION
				"Application Control Status code"
			::= {advancedUrlFiltering 101 }

   advancedUrlFilteringStatusShortDesc OBJECT-TYPE
     		SYNTAX  DisplayString
		MAX-ACCESS read-only
		STATUS  current
		DESCRIPTION
			"Application Control Status - Short Description"
		::= {advancedUrlFiltering 102 }

   advancedUrlFilteringStatusLongDesc OBJECT-TYPE
     		SYNTAX  DisplayString
		MAX-ACCESS read-only
		STATUS  current
		DESCRIPTION
			"Application Control Status  - Long Description"
		::= {advancedUrlFiltering 103 }

  	--AMW statuses:

    antiBotSubscription OBJECT IDENTIFIER ::= { amw 2 }

	antiBotSubscriptionStatus OBJECT-TYPE
      		SYNTAX  DisplayString
			MAX-ACCESS read-only
			STATUS  current
			DESCRIPTION
				"Anti-Bot subscription status
				 Possible values include:
	           	 valid, expired, about-to-expire, not-associated, unknown"
			::= {antiBotSubscription 1 }

	antiBotSubscriptionExpDate OBJECT-TYPE
      		SYNTAX  DisplayString
			MAX-ACCESS read-only
			STATUS  current
			DESCRIPTION
				"Anti-Bot subscription expiration date"
			::= {antiBotSubscription 2 }

    antiBotSubscriptionDesc OBJECT-TYPE
      		SYNTAX  DisplayString
			MAX-ACCESS read-only
			STATUS  current
			DESCRIPTION
				"Anti-Bot subscription description"
			::= {antiBotSubscription 3 }

	antiVirusSubscription OBJECT IDENTIFIER ::= { amw 3 }

	antiVirusSubscriptionStatus OBJECT-TYPE
      		SYNTAX  DisplayString
			MAX-ACCESS read-only
			STATUS  current
			DESCRIPTION
				"Anti-Virus subscription status
				 Possible values include:
	           	 valid, expired, about-to-expire, not-associated, unknown"
			::= {antiVirusSubscription 1 }

	antiVirusSubscriptionExpDate OBJECT-TYPE
      		SYNTAX  DisplayString
			MAX-ACCESS read-only
			STATUS  current
			DESCRIPTION
				"Anti-Virus subscription expiration date"
			::= {antiVirusSubscription 2 }

    antiVirusSubscriptionDesc OBJECT-TYPE
      		SYNTAX  DisplayString
			MAX-ACCESS read-only
			STATUS  current
			DESCRIPTION
				"Anti-Virus subscription description"
			::= {antiVirusSubscription 3 }

	antiSpamSubscription OBJECT IDENTIFIER ::= { amw 4 }

	antiSpamSubscriptionStatus OBJECT-TYPE
      		SYNTAX  DisplayString
			MAX-ACCESS read-only
			STATUS  current
			DESCRIPTION
				"Anti-Spam subscription status
				 Possible values include:
	           	 valid, expired, about-to-expire, not-associated, unknown"
			::= {antiSpamSubscription 1 }

	antiSpamSubscriptionExpDate OBJECT-TYPE
      		SYNTAX  DisplayString
			MAX-ACCESS read-only
			STATUS  current
			DESCRIPTION
				"Anti-Spam subscription expiration date"
			::= {antiSpamSubscription 2 }

    antiSpamSubscriptionDesc OBJECT-TYPE
      		SYNTAX  DisplayString
			MAX-ACCESS read-only
			STATUS  current
			DESCRIPTION
				"Anti-Spam subscription description"
			::= {antiSpamSubscription 3 }

	amwABUpdate OBJECT IDENTIFIER ::= { amw 1 }

	amwABUpdateStatus OBJECT-TYPE
      		SYNTAX  DisplayString
			MAX-ACCESS read-only
			STATUS  current
			DESCRIPTION
				"Anti-Malware update status
				 Possible values include:
	           	 failed, up-to-date, new, degrade, unknown"
			::= {amwABUpdate 1 }

	amwABUpdateDesc OBJECT-TYPE
      		SYNTAX  DisplayString
			MAX-ACCESS read-only
			STATUS  current
			DESCRIPTION
				"Anti-Malware update description"
			::= {amwABUpdate 2 }

    amwABNextUpdate OBJECT-TYPE
      		SYNTAX  DisplayString
			MAX-ACCESS read-only
			STATUS  current
			DESCRIPTION
				"Anti-Malware next update description"
			::= {amwABUpdate 3 }

	amwABVersion OBJECT-TYPE
      		SYNTAX  DisplayString
			MAX-ACCESS read-only
			STATUS  current
			DESCRIPTION
				"Anti-Malware database version"
			::= {amwABUpdate 4 }

	amwAVUpdate OBJECT IDENTIFIER ::= { amw 5 }

	amwAVUpdateStatus OBJECT-TYPE
      		SYNTAX  DisplayString
			MAX-ACCESS read-only
			STATUS  current
			DESCRIPTION
				"Anti-Virus update status
				 Possible values include:
	           	 failed, up-to-date, new, degrade, unknown"
			::= {amwAVUpdate 1 }

	amwAVUpdateDesc OBJECT-TYPE
      		SYNTAX  DisplayString
			MAX-ACCESS read-only
			STATUS  current
			DESCRIPTION
				"Anti-Virus update description"
			::= {amwAVUpdate 2 }

    amwAVNextUpdate OBJECT-TYPE
      		SYNTAX  DisplayString
			MAX-ACCESS read-only
			STATUS  current
			DESCRIPTION
				"Anti-Virus next update description"
			::= {amwAVUpdate 3 }

	amwAVVersion OBJECT-TYPE
      		SYNTAX  DisplayString
			MAX-ACCESS read-only
			STATUS  current
			DESCRIPTION
				"Anti-Virus database version"
			::= {amwAVUpdate 4 }

	amwStatusCode OBJECT-TYPE
      		SYNTAX  Integer32
			MAX-ACCESS read-only
			STATUS  current
			DESCRIPTION
				"Anti-Bot & Anti-Virus Status code"
			::= {amw 101 }

   amwStatusShortDesc OBJECT-TYPE
     		SYNTAX  DisplayString
		MAX-ACCESS read-only
		STATUS  current
		DESCRIPTION
			"Anti-Bot & Anti-Virus Status - Short Description"
		::= {amw 102 }

   amwStatusLongDesc OBJECT-TYPE
     		SYNTAX  DisplayString
		MAX-ACCESS read-only
		STATUS  current
		DESCRIPTION
			"Anti-Bot & Anti-Virus Status  - Long Description"
		::= {amw 103 }


	--asg statuses:

 	asgProductName OBJECT-TYPE
      		SYNTAX  DisplayString (SIZE (0..255))
			MAX-ACCESS  read-only
			STATUS  current
			DESCRIPTION
				"Product name"
			::= {asg 1 }

	asgVer OBJECT-TYPE
            SYNTAX  DisplayString (SIZE (0..255))
            MAX-ACCESS  read-only
            STATUS  current
            DESCRIPTION
                "ASG build version"
              ::= { asg 2 }

	asgKernelVer OBJECT-TYPE
            SYNTAX  DisplayString
            MAX-ACCESS  read-only
            STATUS  current
            DESCRIPTION
                "Kernel version"
              ::= { asg 3 }

	asgBuildNum OBJECT-TYPE
	  		SYNTAX  Unsigned32
			MAX-ACCESS  read-only
			STATUS  current
			DESCRIPTION
			   "ASG build number"
			  ::= { asg 4 }

 	asgMaximumBladesPerChassis OBJECT-TYPE
      		SYNTAX  Unsigned32
			MAX-ACCESS  read-only
			STATUS  current
			DESCRIPTION
				"Maximum blades per chassis"
			::= {asg 7 }

	asgActiveBladesBitmask OBJECT-TYPE
      		SYNTAX  DisplayString
			MAX-ACCESS  read-only
			STATUS  current
			DESCRIPTION
				"Bitmask of active blades:
				 Chassis 1 - 16 Least Significant Bits
				 Chassis 2 - 16 Most Significant Bits
				 E.g. asgActiveBladesBitmask = 00030002
				 It means blade 2 is active in chassis 1 and
				 blade 1 and blade 2 are active in chassis 2"
			::= {asg 8 }

 	asgInstalledBladesBitmask OBJECT-TYPE
      		SYNTAX  DisplayString
			MAX-ACCESS  read-only
			STATUS  current
			DESCRIPTION
				"Bitmask of installed blades:
				 Chassis 1 - 16 Least Significant Bits
				 Chassis 2 - 16 Most Significant Bits
				 E.g. asgInstalledBladesBitmask = 00030002
				 It means blade 2 is installed in chassis 1 and
				 blade 1 and blade 2 are installed in chassis 2"
			::= {asg 9 }

	asgInstalled OBJECT-TYPE
		    SYNTAX  DisplayString
			MAX-ACCESS  read-only
			STATUS  current
			DESCRIPTION
				 "Date and time of ASG installation"
			::= { asg 10 }

	asgSystemUp OBJECT-TYPE
		    SYNTAX  DisplayString
			MAX-ACCESS  read-only
			STATUS  current
			DESCRIPTION
			    "Time elapsed since the last system startup"
			::= { asg 11 }

	asgEvent OBJECT-TYPE
            SYNTAX  DisplayString (SIZE (0..255))
            MAX-ACCESS  read-only
            STATUS  current
            DESCRIPTION
                "A string containing the last snmp trap sent from ASG"
              ::= { asg 12 }

	asgStatusCode OBJECT-TYPE
            SYNTAX  DisplayString (SIZE (0..255))
            MAX-ACCESS  read-only
            STATUS  current
            DESCRIPTION
                "No description available"
              ::= { asg 13 }

	asgStatShort OBJECT-TYPE
            SYNTAX  DisplayString (SIZE (0..255))
            MAX-ACCESS  read-only
            STATUS  current
            DESCRIPTION
                "Status short description"
              ::= { asg 14 }

	asgStatLong OBJECT-TYPE
            SYNTAX  DisplayString (SIZE (0..255))
            MAX-ACCESS  read-only
            STATUS  current
            DESCRIPTION
                "Status long description"
              ::= { asg 15 }

	asgSecureXLStatusBitmask OBJECT-TYPE
            SYNTAX  DisplayString (SIZE (0..255))
            MAX-ACCESS  read-only
            STATUS  current
            DESCRIPTION
                "Bitmask of SecureXL status:
				 Chassis 1 - 16 Least Significant Bits
				 Chassis 2 - 16 Most Significant Bits
				 E.g. asgSecureXLStatusBitmask = 00030002
				 It means SecureXL is enabled on blade 2 in chassis 1 and
				 on blade 1 and blade 2 in chassis 2"
              ::= { asg 16 }

	asgAttachedBladesBitmask OBJECT-TYPE
      		SYNTAX  DisplayString
			MAX-ACCESS  read-only
			STATUS  current
			DESCRIPTION
				"Bitmask of attached blades:
				 Chassis 1 - 16 Least Significant Bits
				 Chassis 2 - 16 Most Significant Bits
				 E.g. asgAttachedBladesBitmask = 00030002
				 It means blade 2 is attached in chassis 1 and
				 blade 1 and blade 2 are attached in chassis 2"
			::= {asg 17 }

	asgIPv4PerformanceCounters OBJECT IDENTIFIER ::= { asg 20 }

   	asgThroughput OBJECT-TYPE
            SYNTAX  DisplayString
            MAX-ACCESS  read-only
            STATUS  current
            DESCRIPTION
	  		        "Throughput"
            ::= { asgIPv4PerformanceCounters 1 }

	asgConnectionRate OBJECT-TYPE
            SYNTAX  DisplayString
            MAX-ACCESS  read-only
            STATUS  current
            DESCRIPTION
	  		        "Connection rate"
            ::= { asgIPv4PerformanceCounters 2 }

	asgPacketRate OBJECT-TYPE
            SYNTAX  DisplayString
            MAX-ACCESS  read-only
            STATUS  current
            DESCRIPTION
	  		        "Packet rate"
            ::= { asgIPv4PerformanceCounters 3 }

    asgConcurrConn OBJECT-TYPE
            SYNTAX  DisplayString
            MAX-ACCESS  read-only
            STATUS  current
            DESCRIPTION
	  		        "Concurrent connections"
            ::= { asgIPv4PerformanceCounters 4 }

	asgAccelConnectionRate OBJECT-TYPE
            SYNTAX  DisplayString
            MAX-ACCESS  read-only
            STATUS  current
            DESCRIPTION
	  		        "Accelerated connections rate"
            ::= { asgIPv4PerformanceCounters 6 }

	asgNonAccelConnectionRate OBJECT-TYPE
            SYNTAX  DisplayString
            MAX-ACCESS  read-only
            STATUS  current
            DESCRIPTION
	  		        "Non-accelerated connections rate"
            ::= { asgIPv4PerformanceCounters 7 }

	asgAccelConcurrConn OBJECT-TYPE
            SYNTAX  DisplayString
            MAX-ACCESS  read-only
            STATUS  current
            DESCRIPTION
	  		        "Accelerated concurrent connections"
            ::= { asgIPv4PerformanceCounters 8 }

	asgNonAccelConcurrConn OBJECT-TYPE
            SYNTAX  DisplayString
            MAX-ACCESS  read-only
            STATUS  current
            DESCRIPTION
	  		        "Non-accelerated concurrent connections"
            ::= { asgIPv4PerformanceCounters 9 }

	asgLoad OBJECT-TYPE
            SYNTAX  DisplayString
            MAX-ACCESS  read-only
            STATUS  current
            DESCRIPTION
	  		        "Load (average), in %"
            ::= { asgIPv4PerformanceCounters 10 }

	asgAccelLoadAvg OBJECT-TYPE
            SYNTAX  DisplayString
            MAX-ACCESS  read-only
            STATUS  current
            DESCRIPTION
	  		        "Accelerated load (average), in %"
            ::= { asgIPv4PerformanceCounters 11 }

	asgAccelLoadMin OBJECT-TYPE
            SYNTAX  DisplayString
            MAX-ACCESS  read-only
            STATUS  current
            DESCRIPTION
	  		        "Accelerated load (minumum), in %"
            ::= { asgIPv4PerformanceCounters 12 }

	asgAccelLoadMax OBJECT-TYPE
            SYNTAX  DisplayString
            MAX-ACCESS  read-only
            STATUS  current
            DESCRIPTION
	  		        "Accelerated load (maximum), in %"
            ::= { asgIPv4PerformanceCounters 13 }

	asgInstancesLoadAvg OBJECT-TYPE
            SYNTAX  DisplayString
            MAX-ACCESS  read-only
            STATUS  current
            DESCRIPTION
	  		        "Instances load (average), in %"
            ::= { asgIPv4PerformanceCounters 14 }

	asgInstancesLoadMin OBJECT-TYPE
            SYNTAX  DisplayString
            MAX-ACCESS  read-only
            STATUS  current
            DESCRIPTION
	  		        "Instances load (minimum), in %"
            ::= { asgIPv4PerformanceCounters 15 }

	asgInstancesLoadMax OBJECT-TYPE
            SYNTAX  DisplayString
            MAX-ACCESS  read-only
            STATUS  current
            DESCRIPTION
	  		        "Instances load (maximum), in %"
            ::= { asgIPv4PerformanceCounters 16 }

	asgVpnThroughput OBJECT-TYPE
            SYNTAX  DisplayString
            MAX-ACCESS  read-only
            STATUS  current
            DESCRIPTION
	  		        "VPN throughput"
            ::= { asgIPv4PerformanceCounters 17 }

	asgVpnConn OBJECT-TYPE
            SYNTAX  DisplayString
            MAX-ACCESS  read-only
            STATUS  current
            DESCRIPTION
	  		        "VPN connections"
            ::= { asgIPv4PerformanceCounters 18 }

	asgNatConnRate OBJECT-TYPE
            SYNTAX  DisplayString
            MAX-ACCESS  read-only
            STATUS  current
            DESCRIPTION
	  		        "NAT connection rate"
            ::= { asgIPv4PerformanceCounters 19 }

	asgNatConn OBJECT-TYPE
            SYNTAX  DisplayString
            MAX-ACCESS  read-only
            STATUS  current
            DESCRIPTION
	  		        "NAT connections"
            ::= { asgIPv4PerformanceCounters 20 }

	asgVsxCpu1MinAvg OBJECT-TYPE
            SYNTAX  DisplayString
            MAX-ACCESS  read-only
            STATUS  current
            DESCRIPTION
	  		        "Average CPU usage of 1min per VS"
            ::= { asgIPv4PerformanceCounters 21 }

	asgPathDistTable OBJECT-TYPE
			SYNTAX  SEQUENCE OF  AsgPathDistEntry
			MAX-ACCESS  not-accessible
			STATUS  current
			DESCRIPTION
       	  		        "NAT connections"
			::= { asgIPv4PerformanceCounters 24 }

	asgPathDistEntry OBJECT-TYPE
			SYNTAX  AsgPathDistEntry
	        MAX-ACCESS  not-accessible
	        STATUS  current
	        DESCRIPTION "No description available"
	        INDEX   { asgPathDistIndex }
	        ::= { asgPathDistTable 1 }

    AsgPathDistEntry ::=
            SEQUENCE {
				asgPathDistIndex
                    Unsigned32,
			    asgStatName
					DisplayString,
				asgAccelPath
                    DisplayString,
				asgMediumPath
                    DisplayString,
				asgFirewallPath
                    DisplayString,
				asgDropped
                    DisplayString
	        }

	 asgPathDistIndex OBJECT-TYPE
			SYNTAX  Unsigned32
            MAX-ACCESS  not-accessible
            STATUS  current
            DESCRIPTION "No description available"
            ::= { asgPathDistEntry 1 }

    asgStatName OBJECT-TYPE
            SYNTAX  DisplayString
            MAX-ACCESS  read-only
            STATUS  current
			DESCRIPTION
					"Statistic's name"
            ::= { asgPathDistEntry 2 }

    asgAccelPath OBJECT-TYPE
			SYNTAX  DisplayString
            MAX-ACCESS  read-only
            STATUS  current
			DESCRIPTION
					"Accelerated traffic"
            ::= { asgPathDistEntry 3 }

    asgMediumPath OBJECT-TYPE
			SYNTAX  DisplayString
            MAX-ACCESS  read-only
            STATUS  current
			DESCRIPTION
					"PXL accelerated traffic"
            ::= { asgPathDistEntry 4 }

	asgFirewallPath OBJECT-TYPE
			SYNTAX  DisplayString
            MAX-ACCESS  read-only
            STATUS  current
			DESCRIPTION
					"Firewall traffic"
            ::= { asgPathDistEntry 5 }

	asgDropped OBJECT-TYPE
			SYNTAX  DisplayString
            MAX-ACCESS  read-only
            STATUS  current
			DESCRIPTION
					"Dropped traffic"
            ::= { asgPathDistEntry 6 }

	-- Counters Table

	asgCountersTable OBJECT-TYPE
			SYNTAX SEQUENCE OF  AsgCountersEntry
			MAX-ACCESS  not-accessible
			STATUS  current
			DESCRIPTION "No description available"
			::= { asgIPv4PerformanceCounters 25 }

	asgCountersEntry OBJECT-TYPE
			SYNTAX  AsgCountersEntry
	        MAX-ACCESS  not-accessible
	        STATUS  current
	        DESCRIPTION "No description available"
	        INDEX   { asgCountersIndex }
	        ::= { asgCountersTable 1 }

    AsgCountersEntry ::=
            SEQUENCE {
				asgCountersIndex
                    Unsigned32,
                asgCountersBladeId
                    DisplayString,
				asgCountersThroughput
					DisplayString,
				asgCountersConnRate
					DisplayString,
				asgCountersPacketRate
					DisplayString,
				asgCountersConcurrConnNum
				    DisplayString,
				asgCountersAccelLoadAverage
				    DisplayString,
				asgCountersAccelLoadMin
				    DisplayString,
				asgCountersAccelLoadMax
				    DisplayString,
				asgCountersInstanceLoadAverage
				    DisplayString,
				asgCountersInstanceLoadMin
				    DisplayString,
				asgCountersInstanceLoadMax
				    DisplayString
	        }

    asgCountersIndex OBJECT-TYPE
			SYNTAX  Unsigned32
            MAX-ACCESS  not-accessible
            STATUS  current
            DESCRIPTION "No description available"
            ::= { asgCountersEntry 1 }

    asgCountersBladeId OBJECT-TYPE
            SYNTAX  DisplayString
            MAX-ACCESS  read-only
            STATUS  current
			DESCRIPTION
					"Blade Identifier"
            ::= { asgCountersEntry 2 }

	asgCountersThroughput OBJECT-TYPE
            SYNTAX  DisplayString
            MAX-ACCESS  read-only
            STATUS  current
			DESCRIPTION
					"Throughput"
            ::= { asgCountersEntry 3 }

	asgCountersConnRate OBJECT-TYPE
            SYNTAX  DisplayString
            MAX-ACCESS  read-only
            STATUS  current
			DESCRIPTION
					"Connection rate"
            ::= { asgCountersEntry 4 }

	asgCountersPacketRate OBJECT-TYPE
            SYNTAX  DisplayString
            MAX-ACCESS  read-only
            STATUS  current
			DESCRIPTION
					"Packet rate"
            ::= { asgCountersEntry 5 }

    asgCountersConcurrConnNum OBJECT-TYPE
			SYNTAX  DisplayString
            MAX-ACCESS  read-only
            STATUS  current
			DESCRIPTION
					"Number of concurrent connections"
            ::= { asgCountersEntry 6 }

        asgCountersAccelLoadAverage OBJECT-TYPE
			SYNTAX  DisplayString
            MAX-ACCESS  read-only
            STATUS  current
			DESCRIPTION
					"Acceleration load (average), in %"
            ::= { asgCountersEntry 7 }

	asgCountersAccelLoadMin OBJECT-TYPE
			SYNTAX  DisplayString
            MAX-ACCESS  read-only
            STATUS  current
			DESCRIPTION
					"Acceleration load (minimum), in %"
            ::= { asgCountersEntry 8 }

	asgCountersAccelLoadMax OBJECT-TYPE
			SYNTAX  DisplayString
            MAX-ACCESS  read-only
            STATUS  current
			DESCRIPTION
					"Acceleration load (maximum), in %"
            ::= { asgCountersEntry 9 }

    asgCountersInstanceLoadAverage OBJECT-TYPE
			SYNTAX  DisplayString
            MAX-ACCESS  read-only
            STATUS  current
			DESCRIPTION
					"Instances load (average), in %"
            ::= { asgCountersEntry 10 }

	asgCountersInstanceLoadMin OBJECT-TYPE
			SYNTAX  DisplayString
            MAX-ACCESS  read-only
            STATUS  current
			DESCRIPTION
					"Instances load (minimum), in %"
            ::= { asgCountersEntry 11 }

	asgCountersInstanceLoadMax OBJECT-TYPE
			SYNTAX  DisplayString
            MAX-ACCESS  read-only
            STATUS  current
			DESCRIPTION
					"Instances load (maximum), in %"
            ::= { asgCountersEntry 12 }

	-- Peaks Table

	asgPeaksTable OBJECT-TYPE
			SYNTAX  SEQUENCE OF  AsgPeaksEntry
			MAX-ACCESS  not-accessible
			STATUS  current
			DESCRIPTION "No description available"
			::= { asgIPv4PerformanceCounters 26 }

	asgPeaksEntry OBJECT-TYPE
			SYNTAX  AsgPeaksEntry
	        MAX-ACCESS  not-accessible
	        STATUS  current
	        DESCRIPTION "No description available"
	        INDEX   { asgPeakIndex }
	        ::= { asgPeaksTable 1 }

    AsgPeaksEntry ::=
            SEQUENCE {
				asgPeakIndex
                    Unsigned32,
                asgPeakCriteria
                    DisplayString,
				asgPeakName
                    DisplayString,
				asgPeakValue
					DisplayString,
				asgPeakTimeStamp
					DisplayString,
				asgPeakUnits
					DisplayString
	        }

    asgPeakIndex OBJECT-TYPE
			SYNTAX  Unsigned32
            MAX-ACCESS  not-accessible
            STATUS  current
            DESCRIPTION "No description available"
            ::= { asgPeaksEntry 1 }

	asgPeakCriteria OBJECT-TYPE
			SYNTAX  DisplayString
            MAX-ACCESS  read-only
            STATUS  current
            DESCRIPTION "No description available"
            ::= { asgPeaksEntry 2 }

    asgPeakName OBJECT-TYPE
            SYNTAX  DisplayString
            MAX-ACCESS  read-only
            STATUS  current
			DESCRIPTION
					"Name of the peak statistics"
            ::= { asgPeaksEntry 3 }

	asgPeakValue OBJECT-TYPE
            SYNTAX  DisplayString
            MAX-ACCESS  read-only
            STATUS  current
			DESCRIPTION
					"Peak value"
            ::= { asgPeaksEntry 4 }

	asgPeakTimeStamp OBJECT-TYPE
            SYNTAX  DisplayString
            MAX-ACCESS  read-only
            STATUS  current
			DESCRIPTION
					"Peak timestamp"
            ::= { asgPeaksEntry 5 }

	asgPeakUnits OBJECT-TYPE
            SYNTAX  DisplayString
            MAX-ACCESS  read-only
            STATUS  current
			DESCRIPTION
					"Units"
            ::= { asgPeaksEntry 6 }

	asgRulebase OBJECT IDENTIFIER ::= { asgIPv4PerformanceCounters 27 }

    asgAcceptedBytesTotal OBJECT-TYPE
            SYNTAX  Integer32
            MAX-ACCESS  read-only
            STATUS  current
            DESCRIPTION
	  		        "Total number of accepted bytes"
            ::= { asgRulebase 1 }

    asgDroppedBytesTotal OBJECT-TYPE
            SYNTAX  Integer32
            MAX-ACCESS  read-only
            STATUS  current
            DESCRIPTION
	  		        "Total number of dropped bytes"
            ::= { asgRulebase 2 }

    asgRejectedTotal OBJECT-TYPE
            SYNTAX  Integer32
            MAX-ACCESS  read-only
            STATUS  current
            DESCRIPTION
	  		        "Total number of rejected bytes"
            ::= { asgRulebase 3 }

	-- Rulebase Table

	--asgRulebaseTable OBJECT-TYPE
	--		SYNTAX  SEQUENCE OF  AsgRulebaseEntry
	--		MAX-ACCESS  not-accessible
	--		STATUS  current
	--		DESCRIPTION "No description available"
	--		::= { asgRulebase 4 }

	--asgRulebaseEntry OBJECT-TYPE
	--		SYNTAX  AsgRulebaseEntry
	--        MAX-ACCESS  not-accessible
	--        STATUS  current
	--        DESCRIPTION "No description available"
	--        INDEX   { asgRulebaseIndex }
	--        ::= { asgRulebaseTable 1 }

    -- AsgRulebaseEntry ::=
    --        SEQUENCE {
	--			asgRulebaseIndex
    --                Unsigned32,
    --            asgRulebaseBladeId
	--			    DisplayString,
    --           asgRulebaseDroppedTotal
	--			    INTEGER,
	--			asgRulebaseAcceptedTotal
	--			    INTEGER,
	--			asgRulebaseRejectedTotal
	--			    INTEGER,
	--			asgRulebaseBytesDroppedTotal
	--			    INTEGER,
	--			asgRulebaseBytesAcceptedTotal
	--			    INTEGER,
	--			asgRulebaseBytesRejectedTotal
	--			    INTEGER
	 --       }

    --asgRulebaseIndex OBJECT-TYPE
	--		SYNTAX  Unsigned32
    --       MAX-ACCESS  read-only
    --        STATUS  current
    --        DESCRIPTION "No description available"
    --        ::= { asgRulebaseEntry 1 }

	-- asgRulebaseBladeId OBJECT-TYPE
    --        SYNTAX  DisplayString
    --        MAX-ACCESS  read-only
    --        STATUS  current
	--		DESCRIPTION
	--		"Blade identifier"
    --        ::= { asgRulebaseEntry 2 }

    --asgRulebaseDroppedTotal OBJECT-TYPE
    --        SYNTAX  Integer32
    --        MAX-ACCESS  read-only
    --        STATUS  current
	--		DESCRIPTION
	--		"Number of dropped packets"
    --        ::= { asgRulebaseEntry 3 }

	--asgRulebaseAcceptedTotal OBJECT-TYPE
    --        SYNTAX  Integer32
    --        MAX-ACCESS  read-only
    --        STATUS  current
	--		DESCRIPTION
	--		"Number of accepted packets"
    --        ::= { asgRulebaseEntry 4 }

	--asgRulebaseRejectedTotal OBJECT-TYPE
    --        SYNTAX  Integer32
    --        MAX-ACCESS  read-only
    --        STATUS  current
	--		DESCRIPTION
	--		"Number of rejected packets"
    --        ::= { asgRulebaseEntry 5 }

	--asgRulebaseBytesDroppedTotal OBJECT-TYPE
    --        SYNTAX  Integer32
    --        MAX-ACCESS  read-only
    --        STATUS  current
	--		DESCRIPTION
	--		"Number of dropped bytes"
    --        ::= { asgRulebaseEntry 6 }

	--asgRulebaseBytesAcceptedTotal OBJECT-TYPE
    --        SYNTAX  Integer32
    --        MAX-ACCESS  read-only
    --        STATUS  current
	--		DESCRIPTION
	--		"Number of accepted bytes"
    --        ::= { asgRulebaseEntry 7 }

	--asgRulebaseBytesRejectedTotal OBJECT-TYPE
    --        SYNTAX  Integer32
    --        MAX-ACCESS  read-only
    --        STATUS  current
	--		DESCRIPTION
	--		"Number of rejected bytes"
    --        ::= { asgRulebaseEntry 8 }

	-- IPv6 statistics
	asgIPv6PerformanceCounters OBJECT IDENTIFIER ::= { asg 21 }

   	asgIPv6Throughput OBJECT-TYPE
            SYNTAX  DisplayString
            MAX-ACCESS  read-only
            STATUS  current
            DESCRIPTION
	  		        "Throughput"
            ::= { asgIPv6PerformanceCounters 1 }

	asgIPv6ConnectionRate OBJECT-TYPE
            SYNTAX  DisplayString
            MAX-ACCESS  read-only
            STATUS  current
            DESCRIPTION
	  		        "Connection rate"
            ::= { asgIPv6PerformanceCounters 2 }

	asgIPv6PacketRate OBJECT-TYPE
            SYNTAX  DisplayString
            MAX-ACCESS  read-only
            STATUS  current
            DESCRIPTION
	  		        "Packet rate"
            ::= { asgIPv6PerformanceCounters 3 }

    asgIPv6ConcurrConn OBJECT-TYPE
            SYNTAX  DisplayString
            MAX-ACCESS  read-only
            STATUS  current
            DESCRIPTION
	  		        "Concurrent connections"
            ::= { asgIPv6PerformanceCounters 4 }

	asgIPv6AccelConnectionRate OBJECT-TYPE
            SYNTAX  DisplayString
            MAX-ACCESS  read-only
            STATUS  current
            DESCRIPTION
	  		        "Accelerated connections rate"
            ::= { asgIPv6PerformanceCounters 6 }

	asgIPv6NonAccelConnectionRate OBJECT-TYPE
            SYNTAX  DisplayString
            MAX-ACCESS  read-only
            STATUS  current
            DESCRIPTION
	  		        "Non-accelerated connections rate"
            ::= { asgIPv6PerformanceCounters 7 }

	asgIPv6AccelConcurrConn OBJECT-TYPE
            SYNTAX  DisplayString
            MAX-ACCESS  read-only
            STATUS  current
            DESCRIPTION
	  		        "Accelerated concurrent connections"
            ::= { asgIPv6PerformanceCounters 8 }

	asgIPv6NonAccelConcurrConn OBJECT-TYPE
            SYNTAX  DisplayString
            MAX-ACCESS  read-only
            STATUS  current
            DESCRIPTION
	  		        "Non-accelerated concurrent connections"
            ::= { asgIPv6PerformanceCounters 9 }

	asgIPv6Load OBJECT-TYPE
            SYNTAX  DisplayString
            MAX-ACCESS  read-only
            STATUS  current
            DESCRIPTION
	  		        "Load (average), in %"
            ::= { asgIPv6PerformanceCounters 10 }

	asgIPv6AccelLoadAvg OBJECT-TYPE
            SYNTAX  DisplayString
            MAX-ACCESS  read-only
            STATUS  current
            DESCRIPTION
	  		        "Accelerated load (average), in %"
            ::= { asgIPv6PerformanceCounters 11 }

	asgIPv6AccelLoadMin OBJECT-TYPE
            SYNTAX  DisplayString
            MAX-ACCESS  read-only
            STATUS  current
            DESCRIPTION
	  		        "Accelerated load (minumum), in %"
            ::= { asgIPv6PerformanceCounters 12 }

	asgIPv6AccelLoadMax OBJECT-TYPE
            SYNTAX  DisplayString
            MAX-ACCESS  read-only
            STATUS  current
            DESCRIPTION
	  		        "Accelerated load (maximum), in %"
            ::= { asgIPv6PerformanceCounters 13 }

	asgIPv6InstancesLoadAvg OBJECT-TYPE
            SYNTAX  DisplayString
            MAX-ACCESS  read-only
            STATUS  current
            DESCRIPTION
	  		        "Instances load (average), in %"
            ::= { asgIPv6PerformanceCounters 14 }

	asgIPv6InstancesLoadMin OBJECT-TYPE
            SYNTAX  DisplayString
            MAX-ACCESS  read-only
            STATUS  current
            DESCRIPTION
	  		        "Instances load (minimum), in %"
            ::= { asgIPv6PerformanceCounters 15 }

	asgIPv6InstancesLoadMax OBJECT-TYPE
            SYNTAX  DisplayString
            MAX-ACCESS  read-only
            STATUS  current
            DESCRIPTION
	  		        "Instances load (maximum), in %"
            ::= { asgIPv6PerformanceCounters 16 }

	asgIPv6VpnThroughput OBJECT-TYPE
            SYNTAX  DisplayString
            MAX-ACCESS  read-only
            STATUS  current
            DESCRIPTION
	  		        "VPN throughput"
            ::= { asgIPv6PerformanceCounters 17 }

	asgIPv6VpnConn OBJECT-TYPE
            SYNTAX  DisplayString
            MAX-ACCESS  read-only
            STATUS  current
            DESCRIPTION
	  		        "VPN connections"
            ::= { asgIPv6PerformanceCounters 18 }

	asgIPv6NatConnRate OBJECT-TYPE
            SYNTAX  DisplayString
            MAX-ACCESS  read-only
            STATUS  current
            DESCRIPTION
	  		        "NAT connection rate"
            ::= { asgIPv6PerformanceCounters 19 }

	asgIPv6NatConn OBJECT-TYPE
            SYNTAX  DisplayString
            MAX-ACCESS  read-only
            STATUS  current
            DESCRIPTION
	  		        "NAT connections"
            ::= { asgIPv6PerformanceCounters 20 }

	asgIPv6VsxCpu1MinAvg OBJECT-TYPE
            SYNTAX  DisplayString
            MAX-ACCESS  read-only
            STATUS  current
            DESCRIPTION
	  		        "Average CPU usage of 1min per VS"
            ::= { asgIPv6PerformanceCounters 21 }

	asgIPv6PathDistTable OBJECT-TYPE
			SYNTAX  SEQUENCE OF  AsgIPv6PathDistEntry
	        MAX-ACCESS  not-accessible
	        STATUS  current
	        DESCRIPTION "No description available"
			::= { asgIPv6PerformanceCounters 24 }

	asgIPv6PathDistEntry OBJECT-TYPE
			SYNTAX  AsgIPv6PathDistEntry
	  		MAX-ACCESS  not-accessible
	  		STATUS  current
	  		DESCRIPTION "No description available"
	        INDEX   { asgIPv6PathDistIndex }
	        ::= { asgIPv6PathDistTable 1 }

    AsgIPv6PathDistEntry ::=
      		SEQUENCE {
				asgIPv6PathDistIndex
		          	Unsigned32,
			    asgIPv6StatName
		        	DisplayString,
				asgIPv6AccelPath
		          	DisplayString,
				asgIPv6MediumPath
                    DisplayString,
				asgIPv6FirewallPath
                    DisplayString,
				asgIPv6Dropped
                    DisplayString
	        }

	 asgIPv6PathDistIndex OBJECT-TYPE
			SYNTAX  Unsigned32
            MAX-ACCESS  not-accessible
            STATUS  current
            DESCRIPTION "No description available"
            ::= { asgIPv6PathDistEntry 1 }

    asgIPv6StatName OBJECT-TYPE
            SYNTAX  DisplayString
            MAX-ACCESS  read-only
            STATUS  current
			DESCRIPTION
					"Statistic's name"
            ::= { asgIPv6PathDistEntry 2 }

    asgIPv6AccelPath OBJECT-TYPE
			SYNTAX  DisplayString
            MAX-ACCESS  read-only
            STATUS  current
			DESCRIPTION
					"Accelerated traffic"
            ::= { asgIPv6PathDistEntry 3 }

    asgIPv6MediumPath OBJECT-TYPE
			SYNTAX  DisplayString
            MAX-ACCESS  read-only
            STATUS  current
			DESCRIPTION
					"PXL accelerated traffic"
            ::= { asgIPv6PathDistEntry 4 }

	asgIPv6FirewallPath OBJECT-TYPE
			SYNTAX  DisplayString
            MAX-ACCESS  read-only
            STATUS  current
			DESCRIPTION
					"Firewall traffic"
            ::= { asgIPv6PathDistEntry 5 }

	asgIPv6Dropped OBJECT-TYPE
			SYNTAX  DisplayString
            MAX-ACCESS  read-only
	        STATUS  current
			DESCRIPTION
					"Dropped traffic"
            ::= { asgIPv6PathDistEntry 6 }

	-- Counters Table

	asgIPv6CountersTable OBJECT-TYPE
			SYNTAX  SEQUENCE OF  AsgIPv6CountersEntry
			MAX-ACCESS  not-accessible
			STATUS  current
			DESCRIPTION "No description available"
			::= { asgIPv6PerformanceCounters 25 }

	asgIPv6CountersEntry OBJECT-TYPE
			SYNTAX  AsgIPv6CountersEntry
	        MAX-ACCESS  not-accessible
	        STATUS  current
	        DESCRIPTION "No description available"
	        INDEX   { asgIPv6CountersIndex }
	        ::= { asgIPv6CountersTable 1 }

    AsgIPv6CountersEntry ::=
            SEQUENCE {
				asgIPv6CountersIndex
		          	Unsigned32,
                asgIPv6CountersBladeId
                    DisplayString,
				asgIPv6CountersThroughput
                  	DisplayString,
				asgIPv6CountersConnRate
					DisplayString,
				asgIPv6CountersPacketRate
					DisplayString,
				asgIPv6CountersConcurrConnNum
				    DisplayString,
				asgIPv6CountersAccelLoadAverage
				    DisplayString,
				asgIPv6CountersAccelLoadMin
				    DisplayString,
				asgIPv6CountersAccelLoadMax
				    DisplayString,
				asgIPv6CountersInstanceLoadAverage
				    DisplayString,
				asgIPv6CountersInstanceLoadMin
				    DisplayString,
				asgIPv6CountersInstanceLoadMax
				    DisplayString
	        }

    asgIPv6CountersIndex OBJECT-TYPE
			SYNTAX  Unsigned32
            MAX-ACCESS  not-accessible
            STATUS  current
            DESCRIPTION "No description available"
            ::= { asgIPv6CountersEntry 1 }

    asgIPv6CountersBladeId OBJECT-TYPE
            SYNTAX  DisplayString
            MAX-ACCESS  read-only
            STATUS  current
			DESCRIPTION
					"Blade Identifier"
            ::= { asgIPv6CountersEntry 2 }

	asgIPv6CountersThroughput OBJECT-TYPE
            SYNTAX  DisplayString
            MAX-ACCESS  read-only
            STATUS  current
			DESCRIPTION
					"Throughput"
            ::= { asgIPv6CountersEntry 3 }

	asgIPv6CountersConnRate OBJECT-TYPE
            SYNTAX  DisplayString
            MAX-ACCESS  read-only
            STATUS  current
			DESCRIPTION
					"Connection rate"
            ::= { asgIPv6CountersEntry 4 }

	asgIPv6CountersPacketRate OBJECT-TYPE
            SYNTAX  DisplayString
            MAX-ACCESS  read-only
            STATUS  current
			DESCRIPTION
					"Packet rate"
            ::= { asgIPv6CountersEntry 5 }

    asgIPv6CountersConcurrConnNum OBJECT-TYPE
			SYNTAX  DisplayString
            MAX-ACCESS  read-only
            STATUS  current
			DESCRIPTION
					"Number of concurrent connections"
            ::= { asgIPv6CountersEntry 6 }

        asgIPv6CountersAccelLoadAverage OBJECT-TYPE
			SYNTAX  DisplayString
            MAX-ACCESS  read-only
            STATUS  current
			DESCRIPTION
					"Acceleration load (average), in %"
            ::= { asgIPv6CountersEntry 7 }

	asgIPv6CountersAccelLoadMin OBJECT-TYPE
			SYNTAX  DisplayString
            MAX-ACCESS  read-only
            STATUS  current
			DESCRIPTION
					"Acceleration load (minimum), in %"
            ::= { asgIPv6CountersEntry 8 }

	asgIPv6CountersAccelLoadMax OBJECT-TYPE
			SYNTAX  DisplayString
            MAX-ACCESS  read-only
            STATUS  current
			DESCRIPTION
					"Acceleration load (maximum), in %"
            ::= { asgIPv6CountersEntry 9 }

    asgIPv6CountersInstanceLoadAverage OBJECT-TYPE
			SYNTAX  DisplayString
            MAX-ACCESS  read-only
            STATUS  current
			DESCRIPTION
					"Instances load (average), in %"
            ::= { asgIPv6CountersEntry 10 }

	asgIPv6CountersInstanceLoadMin OBJECT-TYPE
			SYNTAX  DisplayString
            MAX-ACCESS  read-only
            STATUS  current
			DESCRIPTION
					"Instances load (minimum), in %"
            ::= { asgIPv6CountersEntry 11 }

	asgIPv6CountersInstanceLoadMax OBJECT-TYPE
			SYNTAX  DisplayString
            MAX-ACCESS  read-only
            STATUS  current
			DESCRIPTION
					"Instances load (maximum), in %"
            ::= { asgIPv6CountersEntry 12 }

	-- Peaks Table

	asgIPv6PeaksTable OBJECT-TYPE
			SYNTAX  SEQUENCE OF  AsgIPv6PeaksEntry
			MAX-ACCESS  not-accessible
			STATUS  current
			DESCRIPTION "No description available"
			::= { asgIPv6PerformanceCounters 26 }

	asgIPv6PeaksEntry OBJECT-TYPE
			SYNTAX  AsgIPv6PeaksEntry
	        MAX-ACCESS  not-accessible
	        STATUS  current
	        DESCRIPTION "No description available"
	        INDEX   { asgIPv6PeakIndex }
	        ::= { asgIPv6PeaksTable 1 }

    AsgIPv6PeaksEntry ::=
            SEQUENCE {
				asgIPv6PeakIndex
                    Unsigned32,
                asgIPv6PeakCriteria
                    DisplayString,
				asgIPv6PeakName
					DisplayString,
				asgIPv6PeakValue
					DisplayString,
				asgIPv6PeakTimeStamp
					DisplayString,
				asgIPv6PeakUnits
         		  	DisplayString
			}

    asgIPv6PeakIndex OBJECT-TYPE
            SYNTAX  Unsigned32
            MAX-ACCESS  not-accessible
            STATUS  current
            DESCRIPTION "No description available"
            ::= { asgIPv6PeaksEntry 1 }

	asgIPv6PeakCriteria OBJECT-TYPE
            SYNTAX  DisplayString
            MAX-ACCESS  read-only
            STATUS  current
			DESCRIPTION
					"Name of the peak statistics"
            ::= { asgIPv6PeaksEntry 2 }

    asgIPv6PeakName OBJECT-TYPE
            SYNTAX  DisplayString
            MAX-ACCESS  read-only
            STATUS  current
			DESCRIPTION
					"Name of the peak statistics"
            ::= { asgIPv6PeaksEntry 3 }

	asgIPv6PeakValue OBJECT-TYPE
            SYNTAX  DisplayString
            MAX-ACCESS  read-only
            STATUS  current
			DESCRIPTION
					"Peak value"
            ::= { asgIPv6PeaksEntry 4 }

	asgIPv6PeakTimeStamp OBJECT-TYPE
            SYNTAX  DisplayString
            MAX-ACCESS  read-only
            STATUS  current
			DESCRIPTION
					"Peak timestamp"
            ::= { asgIPv6PeaksEntry 5 }

	asgIPv6PeakUnits OBJECT-TYPE
            SYNTAX  DisplayString
            MAX-ACCESS  read-only
            STATUS  current
			DESCRIPTION
					"Units"
            ::= { asgIPv6PeaksEntry 6 }

	asgIPv6Rulebase OBJECT IDENTIFIER ::= { asgIPv6PerformanceCounters 27 }

    asgIPv6AcceptedBytesTotalRate OBJECT-TYPE
            SYNTAX  Integer32
            MAX-ACCESS  read-only
            STATUS  current
			DESCRIPTION
	  		        "Rate of accepted bytes"
            ::= { asgIPv6Rulebase 1 }

    asgIPv6DroppedBytesTotalRate OBJECT-TYPE
            SYNTAX  Integer32
            MAX-ACCESS  read-only
            STATUS  current
			DESCRIPTION
	  		        "Rate of dropped bytes"
            ::= { asgIPv6Rulebase 2 }

    asgIPv6DroppedTotalRate OBJECT-TYPE
            SYNTAX  Integer32
            MAX-ACCESS  read-only
            STATUS  current
            DESCRIPTION
	  		        "Rate of dropped packets"
            ::= { asgIPv6Rulebase 3 }

	-- Rulebase Table

	asgIPv6RulebaseTable OBJECT-TYPE
			SYNTAX  SEQUENCE OF  AsgIPv6RulebaseEntry
			MAX-ACCESS  not-accessible
			STATUS  current
			DESCRIPTION "No description available"
			::= { asgIPv6Rulebase 4 }

	asgIPv6RulebaseEntry OBJECT-TYPE
			SYNTAX  AsgIPv6RulebaseEntry
	        MAX-ACCESS  not-accessible
	        STATUS  current
	        DESCRIPTION "No description available"
	        INDEX   { asgIPv6RulebaseIndex }
	        ::= { asgIPv6RulebaseTable 1 }

    AsgIPv6RulebaseEntry ::=
            SEQUENCE {
				asgIPv6RulebaseIndex
                    Unsigned32,
                asgIPv6RulebaseBladeId
				    DisplayString,
                asgIPv6RulebaseDroppedTotal
				    INTEGER,
				asgIPv6RulebaseAcceptedTotal
				    INTEGER,
				asgIPv6RulebaseRejectedTotal
				    INTEGER,
				asgIPv6RulebaseBytesDroppedTotal
				    INTEGER,
				asgIPv6RulebaseBytesAcceptedTotal
				    INTEGER,
				asgIPv6RulebaseBytesRejectedTotal
				    INTEGER
	        }

    asgIPv6RulebaseIndex OBJECT-TYPE
			SYNTAX  Unsigned32
            MAX-ACCESS  not-accessible
            STATUS  current
            DESCRIPTION "No description available"
            ::= { asgIPv6RulebaseEntry 1 }

	asgIPv6RulebaseBladeId OBJECT-TYPE
            SYNTAX  DisplayString
            MAX-ACCESS  read-only
            STATUS  current
			DESCRIPTION
			"Blade identifier"
            ::= { asgIPv6RulebaseEntry 2 }

    asgIPv6RulebaseDroppedTotal OBJECT-TYPE
            SYNTAX  Integer32
            MAX-ACCESS  read-only
            STATUS  current
			DESCRIPTION
			"Number of dropped packets"
            ::= { asgIPv6RulebaseEntry 3 }

	asgIPv6RulebaseAcceptedTotal OBJECT-TYPE
            SYNTAX  Integer32
            MAX-ACCESS  read-only
            STATUS  current
			DESCRIPTION
			"Number of accepted packets"
            ::= { asgIPv6RulebaseEntry 4 }

	asgIPv6RulebaseRejectedTotal OBJECT-TYPE
            SYNTAX  Integer32
            MAX-ACCESS  read-only
            STATUS  current
			DESCRIPTION
			"Number of rejected packets"
            ::= { asgIPv6RulebaseEntry 5 }

	asgIPv6RulebaseBytesDroppedTotal OBJECT-TYPE
            SYNTAX  Integer32
            MAX-ACCESS  read-only
            STATUS  current
			DESCRIPTION
			"Number of dropped bytes"
            ::= { asgIPv6RulebaseEntry 6 }

	asgIPv6RulebaseBytesAcceptedTotal OBJECT-TYPE
            SYNTAX  Integer32
            MAX-ACCESS  read-only
            STATUS  current
			DESCRIPTION
			"Number of accepted bytes"
            ::= { asgIPv6RulebaseEntry 7 }

	asgIPv6RulebaseBytesRejectedTotal OBJECT-TYPE
            SYNTAX  Integer32
            MAX-ACCESS  read-only
            STATUS  current
			DESCRIPTION
			"Number of rejected bytes"
            ::= { asgIPv6RulebaseEntry 8 }

	-- HW Monitoring

	asgHwMonitoring OBJECT IDENTIFIER ::= { asg 22 }
    asgSensors OBJECT IDENTIFIER ::= { asgHwMonitoring 1}

	-- Sensors Table

	asgSensorTable OBJECT-TYPE
	          SYNTAX  SEQUENCE OF  AsgSensorEntry
			  MAX-ACCESS  not-accessible
			  STATUS  current
			  DESCRIPTION "No description available"
			  ::= { asgSensors 1 }

	asgSensorEntry OBJECT-TYPE
	          SYNTAX AsgSensorEntry
			  MAX-ACCESS  not-accessible
			  STATUS  current
			  DESCRIPTION "No description available"
			  INDEX   { asgSensorIndex }
			  ::= { asgSensorTable 1 }

	AsgSensorEntry ::=
	          SEQUENCE {
				asgSensorIndex
				      Unsigned32,
				asgSensorName
				      DisplayString,
				asgSensorLocation
				      DisplayString,
				asgSensorCurrValue
					  DisplayString,
				asgSensorMinValue
					  DisplayString,
				asgSensorMaxValue
					  DisplayString,
				asgSensorThreshold
					  DisplayString,
				asgSensorUnit
				      DisplayString,
				asgSensorIdentity
				      DisplayString,
				asgSensorStatus
				      DisplayString
			  }

	asgSensorIndex OBJECT-TYPE
	  		 SYNTAX  Unsigned32
			 MAX-ACCESS  not-accessible
			 STATUS  current
			 DESCRIPTION "No description available"
    	     ::= { asgSensorEntry 1 }

	asgSensorName OBJECT-TYPE
	  		 SYNTAX  DisplayString (SIZE (0..255))
			 MAX-ACCESS  read-only
			 STATUS  current
			 DESCRIPTION
	       	   "Sensor name"
	       ::= { asgSensorEntry 2 }

	asgSensorLocation OBJECT-TYPE
	  		 SYNTAX  DisplayString (SIZE (0..255))
			 MAX-ACCESS  read-only
			 STATUS  current
			 DESCRIPTION
	       	   "Sensor location"
	       ::= { asgSensorEntry 3 }

	asgSensorCurrValue OBJECT-TYPE
	  		 SYNTAX  DisplayString (SIZE (0..255))
			 MAX-ACCESS  read-only
			 STATUS  current
			 DESCRIPTION
	       	   "Sensor value"
	       ::= { asgSensorEntry 4 }

	asgSensorMinValue OBJECT-TYPE
	  		 SYNTAX  DisplayString (SIZE (0..255))
			 MAX-ACCESS  read-only
			 STATUS  current
			 DESCRIPTION
	       	   "Sensor minimum value"
	       ::= { asgSensorEntry 5 }

	asgSensorMaxValue OBJECT-TYPE
	  		 SYNTAX  DisplayString (SIZE (0..255))
	  		 MAX-ACCESS  read-only
			 STATUS  current
			 DESCRIPTION
	       	   "Sensor maximum value"
	       ::= { asgSensorEntry 6 }

	asgSensorThreshold OBJECT-TYPE
	  		 SYNTAX  DisplayString (SIZE (0..255))
	  		 MAX-ACCESS  read-only
			 STATUS  current
			 DESCRIPTION
	       	   "Sensor threshold"
	       ::= { asgSensorEntry 7 }

	asgSensorUnit OBJECT-TYPE
	  		 SYNTAX  DisplayString (SIZE (0..255))
	  		 MAX-ACCESS  read-only
			 STATUS  current
			 DESCRIPTION
	       	   "Sensor units"
	       ::= { asgSensorEntry 8 }

	asgSensorIdentity OBJECT-TYPE
	  		 SYNTAX  DisplayString (SIZE (0..255))
	  		 MAX-ACCESS  read-only
			 STATUS  current
			 DESCRIPTION
	       	   "Sensor identity"
	       ::= { asgSensorEntry 9 }

	asgSensorStatus OBJECT-TYPE
	  		 SYNTAX  DisplayString (SIZE (0..255))
	  		 MAX-ACCESS  read-only
			 STATUS  current
			 DESCRIPTION
	       	   "Sensor status"
	       ::= { asgSensorEntry 10 }

	-- Resource Table

	asgResourceTable OBJECT-TYPE
	          SYNTAX  SEQUENCE OF  AsgResourceEntry
			  MAX-ACCESS  not-accessible
			  STATUS  current
			  DESCRIPTION "No description available"
			  ::= { asg 23 }

	asgResourceEntry OBJECT-TYPE
	          SYNTAX AsgResourceEntry
			  MAX-ACCESS  not-accessible
			  STATUS  current
			  DESCRIPTION "No description available"
			  INDEX   { asgResourceIndex }
			  ::= { asgResourceTable 1 }

	AsgResourceEntry ::=
	          SEQUENCE {
				asgResourceIndex
					Unsigned32,
				asgResourceName
					DisplayString,
				asgResourceLocation
					DisplayString,
				asgResourceCurrValue
					DisplayString,
				asgResourceThreshold
					DisplayString,
				asgResourceUnit
					DisplayString,
				asgResourceTotalVal
					DisplayString,
				asgResourceTitle
					DisplayString
			  }

	asgResourceIndex OBJECT-TYPE
	  		 SYNTAX  Unsigned32
			 MAX-ACCESS  not-accessible
			 STATUS  current
			 DESCRIPTION "No description available"
    	     ::= { asgResourceEntry 1 }

	asgResourceName OBJECT-TYPE
	  		 SYNTAX  DisplayString (SIZE (0..255))
			 MAX-ACCESS  read-only
			 STATUS  current
			 DESCRIPTION
	       	   "Resource name"
	       ::= { asgResourceEntry 2 }

	asgResourceLocation OBJECT-TYPE
	  		 SYNTAX  DisplayString (SIZE (0..255))
			 MAX-ACCESS  read-only
			 STATUS  current
			 DESCRIPTION
	       	   "Resource location"
	       ::= { asgResourceEntry 3 }

	asgResourceCurrValue OBJECT-TYPE
	  		 SYNTAX  DisplayString (SIZE (0..255))
			 MAX-ACCESS  read-only
			 STATUS  current
			 DESCRIPTION
	       	   "Resource current value"
	       ::= { asgResourceEntry 4 }

	asgResourceThreshold OBJECT-TYPE
	  		 SYNTAX  DisplayString (SIZE (0..255))
	  		 MAX-ACCESS  read-only
			 STATUS  current
			 DESCRIPTION
	       	   "Threshold for resource value"
	       ::= { asgResourceEntry 5 }

	asgResourceUnit OBJECT-TYPE
	  		 SYNTAX  DisplayString (SIZE (0..255))
	  		 MAX-ACCESS  read-only
			 STATUS  current
			 DESCRIPTION
	       	   "Resource units"
	       ::= { asgResourceEntry 6 }

	asgResourceTotalVal OBJECT-TYPE
	  		 SYNTAX  DisplayString (SIZE (0..255))
	  		 MAX-ACCESS  read-only
			 STATUS  current
			 DESCRIPTION
	       	   "Resource total value (bytes)"
	       ::= { asgResourceEntry 7 }

	asgResourceTitle OBJECT-TYPE
	  		 SYNTAX  DisplayString (SIZE (0..255))
	  		 MAX-ACCESS  read-only
	  		 STATUS  current
	  		 DESCRIPTION
	       	   "Record title."
	       ::= { asgResourceEntry 8 }

	asgProtocolTraffic OBJECT IDENTIFIER ::= { asg 24 }
	asgServicesTraffic OBJECT IDENTIFIER ::= { asg 25 }

	asgProtocolTrafficTable OBJECT-TYPE
	        SYNTAX  SEQUENCE OF  AsgProtocolTrafficEntry
			MAX-ACCESS  not-accessible
			STATUS  current
			DESCRIPTION "No description available"
			::= { asgProtocolTraffic 1 }

	asgProtocolTrafficEntry OBJECT-TYPE
	        SYNTAX  AsgProtocolTrafficEntry
	        MAX-ACCESS  not-accessible
			STATUS  current
			DESCRIPTION "No description available"
	        INDEX   { asgProtocolIndex }
	        ::= { asgProtocolTrafficTable 1 }

    AsgProtocolTrafficEntry ::=
            SEQUENCE {
                asgProtocolIndex
                      Unsigned32,
                asgProtocolName
                      DisplayString,
                asgProtocolConns
					  INTEGER,
				asgProtocolTotalPkts
					  INTEGER,
				asgProtocolTotalBytes
					  INTEGER
            }

    asgProtocolIndex OBJECT-TYPE
      		SYNTAX  Unsigned32
			MAX-ACCESS  not-accessible
                        STATUS  current
			DESCRIPTION "No description available"
            ::= { asgProtocolTrafficEntry 1 }

    asgProtocolName OBJECT-TYPE
            SYNTAX  DisplayString
			MAX-ACCESS  read-only
			STATUS  current
			DESCRIPTION
	  		        "Protocol Name"
            ::= { asgProtocolTrafficEntry 2 }

	asgProtocolConns OBJECT-TYPE
      		SYNTAX  Integer32
			MAX-ACCESS  read-only
			STATUS  current
			DESCRIPTION
				"Current number of protocol connections"
			::= {asgProtocolTrafficEntry 3 }

	asgProtocolTotalPkts OBJECT-TYPE
      		SYNTAX  Integer32
			MAX-ACCESS  read-only
			STATUS  current
			DESCRIPTION
				"Total number of protocol packets"
			::= {asgProtocolTrafficEntry 4 }

	asgProtocolTotalBytes OBJECT-TYPE
      		SYNTAX  Integer32
			MAX-ACCESS  read-only
			STATUS  current
			DESCRIPTION
				"Total number of protocol bytes"
			::= {asgProtocolTrafficEntry 5 }

	asgServiceTrafficTable OBJECT-TYPE
	        SYNTAX  SEQUENCE OF  AsgServiceTrafficEntry
			MAX-ACCESS  not-accessible
			STATUS  current
			DESCRIPTION "No description available"
			::= { asgServicesTraffic 1 }

	asgServiceTrafficEntry OBJECT-TYPE
	        SYNTAX  AsgServiceTrafficEntry
	        MAX-ACCESS  not-accessible
			STATUS  current
			DESCRIPTION "No description available"
	        INDEX   { asgServiceIndex }
	        ::= { asgServiceTrafficTable 1 }

    AsgServiceTrafficEntry ::=
            SEQUENCE {
                asgServiceIndex
                      Unsigned32,
                asgServiceName
                      DisplayString,
                asgServiceConns
					  INTEGER,
				asgServiceTotalPkts
					  INTEGER,
				asgServiceTotalBytes
					  INTEGER
            }

    asgServiceIndex OBJECT-TYPE
      		SYNTAX  Unsigned32
			MAX-ACCESS  not-accessible
			STATUS  current
			DESCRIPTION "No description available"
            ::= { asgServiceTrafficEntry 1 }

    asgServiceName OBJECT-TYPE
            SYNTAX  DisplayString
			MAX-ACCESS  read-only
			STATUS  current
			DESCRIPTION
	  		        "Service/Port"
            ::= { asgServiceTrafficEntry 2 }

	asgServiceConns OBJECT-TYPE
      		SYNTAX  Integer32
			MAX-ACCESS  read-only
			STATUS  current
			DESCRIPTION
				"Current number of service connections"
			::= {asgServiceTrafficEntry 3 }

	asgServiceTotalPkts OBJECT-TYPE
      		SYNTAX  Integer32
			MAX-ACCESS  read-only
			STATUS  current
			DESCRIPTION
				"Total number of service packets"
			::= {asgServiceTrafficEntry 4 }

	asgServiceTotalBytes OBJECT-TYPE
      		SYNTAX  Integer32
			MAX-ACCESS  read-only
			STATUS  current
			DESCRIPTION
				"Total number of service bytes"
			::= {asgServiceTrafficEntry 5 }

	asgSetup OBJECT IDENTIFIER ::= { asg 26 }

	-- Interfaces Table

	asgNetIfTable OBJECT-TYPE
	        SYNTAX  SEQUENCE OF  AsgNetIfEntry
			MAX-ACCESS  not-accessible
			STATUS  current
			DESCRIPTION "No description available"
			::= { asgSetup 1 }

	asgNetIfEntry OBJECT-TYPE
	        SYNTAX  AsgNetIfEntry
	        MAX-ACCESS  not-accessible
	        STATUS  current
	        DESCRIPTION "No description available"
	        INDEX   { asgNetIfIndex }
	        ::= { asgNetIfTable 1 }

    AsgNetIfEntry ::=
            SEQUENCE {
                asgNetIfIndex
                      Unsigned32,
                 asgNetIfName
                      DisplayString,
                 asgNetIfIPv4Addr
					  DisplayString,
				 asgNetIfIPv6Addr
					  DisplayString,
				 asgNetIfMACAddr
					  DisplayString,
     			 asgNetIfInfo
					  DisplayString,
     			 asgNetIfState
					  DisplayString,
     			 asgNetIfSpeed
					  DisplayString,
     			 asgNetIfMTU
					  DisplayString,
     			 asgNetIfDuplex
					  DisplayString,
				asgNetIfRx
					  DisplayString,
				asgNetIfTx
					  DisplayString
           }

    asgNetIfIndex OBJECT-TYPE
            SYNTAX  Unsigned32
            MAX-ACCESS  not-accessible
            STATUS  current
            DESCRIPTION "No description available"
            ::= { asgNetIfEntry 1 }

    asgNetIfName OBJECT-TYPE
            SYNTAX  DisplayString
            MAX-ACCESS  read-only
            STATUS  current
			DESCRIPTION
	  		        "Interface Name"
            ::= { asgNetIfEntry 2 }

    asgNetIfIPv4Addr OBJECT-TYPE
            SYNTAX  DisplayString (SIZE (0..255))
            MAX-ACCESS  read-only
            STATUS  current
            DESCRIPTION
	 		        "IPv4 Address and Netmask"
            ::= { asgNetIfEntry 3 }

    asgNetIfIPv6Addr OBJECT-TYPE
            SYNTAX  DisplayString (SIZE (0..255))
            MAX-ACCESS  read-only
            STATUS  current
            DESCRIPTION
	  		        "IPv6 (global) Address and Netmask"
            ::= { asgNetIfEntry 4 }

    asgNetIfMACAddr OBJECT-TYPE
            SYNTAX  DisplayString (SIZE (0..255))
            MAX-ACCESS  read-only
            STATUS  current
            DESCRIPTION
	 		        "MAC Address"
            ::= { asgNetIfEntry 5 }

    asgNetIfInfo OBJECT-TYPE
            SYNTAX  DisplayString (SIZE (0..255))
            MAX-ACCESS  read-only
            STATUS  current
            DESCRIPTION
	  		        "Info"
            ::= { asgNetIfEntry 6 }

    asgNetIfState OBJECT-TYPE
            SYNTAX  DisplayString (SIZE (0..255))
            MAX-ACCESS  read-only
            STATUS  current
            DESCRIPTION
	  		        "State"
            ::= { asgNetIfEntry 7 }

    asgNetIfSpeed OBJECT-TYPE
            SYNTAX  DisplayString (SIZE (0..255))
            MAX-ACCESS  read-only
            STATUS  current
            DESCRIPTION
	  		        "Speed"
            ::= { asgNetIfEntry 8 }

    asgNetIfMTU OBJECT-TYPE
            SYNTAX  DisplayString (SIZE (0..255))
            MAX-ACCESS  read-only
            STATUS  current
            DESCRIPTION
	  		        "MTU"
            ::= { asgNetIfEntry 9 }

    asgNetIfDuplex OBJECT-TYPE
            SYNTAX  DisplayString (SIZE (0..255))
            MAX-ACCESS  read-only
            STATUS  current
            DESCRIPTION
	  		        "Duplex"
            ::= { asgNetIfEntry 10 }

	asgNetIfRx OBJECT-TYPE
            SYNTAX  DisplayString (SIZE (0..255))
            MAX-ACCESS  read-only
            STATUS  current
            DESCRIPTION
	  		        "RX"
            ::= { asgNetIfEntry 11 }

	asgNetIfTx OBJECT-TYPE
            SYNTAX  DisplayString (SIZE (0..255))
            MAX-ACCESS  read-only
            STATUS  current
            DESCRIPTION
	  		        "TX"
            ::= { asgNetIfEntry 12 }

	-- Problem Table

   	asgProblemTable OBJECT-TYPE
	        SYNTAX  SEQUENCE OF AsgProblemEntry
	        MAX-ACCESS  not-accessible
	        STATUS  current
	        DESCRIPTION "No description available"
	         ::= { asg 27}

	asgProblemEntry OBJECT-TYPE
	  		SYNTAX  AsgProblemEntry
	  		MAX-ACCESS  not-accessible
	  		STATUS  current
	  		DESCRIPTION "No description available"
	  		INDEX   { asgProblemIndex }
	  		::= { asgProblemTable 1 }

    AsgProblemEntry ::=
      		SEQUENCE {
      			asgProblemIndex
		          	Unsigned32,
		        asgProblemName
		        	DisplayString,
		        asgProblemStatus
		          	DisplayString,
		        asgProblemPriority
		          	INTEGER,
                asgProblemVerified
                  	INTEGER,
                asgProblemDescr
         		  	DisplayString
			}

	asgProblemIndex OBJECT-TYPE
            SYNTAX  Unsigned32
            MAX-ACCESS  not-accessible
            STATUS  current
            DESCRIPTION "No description available"
            ::= { asgProblemEntry 1 }

    asgProblemName OBJECT-TYPE
            SYNTAX  DisplayString
            MAX-ACCESS  read-only
            STATUS  current
			DESCRIPTION
					"Problem name"
            ::= { asgProblemEntry 2 }

    asgProblemStatus OBJECT-TYPE
            SYNTAX  DisplayString
            MAX-ACCESS  read-only
            STATUS  current
			DESCRIPTION
					"Problem status"
	        ::= { asgProblemEntry 3 }

    asgProblemPriority OBJECT-TYPE
            SYNTAX  Integer32
            MAX-ACCESS  read-only
            STATUS  current
			DESCRIPTION
					"Problem priority"
            ::= { asgProblemEntry 4 }

    asgProblemVerified OBJECT-TYPE
            SYNTAX  Integer32
            MAX-ACCESS  read-only
            STATUS  current
			DESCRIPTION
					"No description available"
            ::= { asgProblemEntry 5 }

    asgProblemDescr OBJECT-TYPE
            SYNTAX  DisplayString
            MAX-ACCESS  read-only
            STATUS  current
			DESCRIPTION
					"Problem description"
            ::= { asgProblemEntry 6 }

	asgChassisInfo OBJECT IDENTIFIER ::= { asg 28 }

	asgChassisMode OBJECT-TYPE
            SYNTAX  DisplayString (SIZE (0..255))
            MAX-ACCESS  read-only
            STATUS  current
            DESCRIPTION
                "Single or Dual Chassis"
              ::= { asgChassisInfo 1 }

	asgChassisHAMode OBJECT-TYPE
            SYNTAX  DisplayString (SIZE (0..255))
            MAX-ACCESS  read-only
            STATUS  current
            DESCRIPTION
                "Chassis HA Mode:
				Primary UP or Active UP"
              ::= { asgChassisInfo 2 }

	asgSynchronization     	OBJECT IDENTIFIER ::= { asgChassisInfo 3 }

	asgSyncToActive OBJECT-TYPE
            SYNTAX  DisplayString (SIZE (0..255))
            MAX-ACCESS  read-only
            STATUS  current
            DESCRIPTION
                "Synchronization to active chassis:
			(Enabled / Disabled)"
              ::= { asgSynchronization 1 }

	asgSyncToStandby OBJECT-TYPE
            SYNTAX  DisplayString (SIZE (0..255))
            MAX-ACCESS  read-only
            STATUS  current
            DESCRIPTION
                "Synchronization to standby chassis
			(Enabled / Disabled)"
              ::= { asgSynchronization 2 }

	asgSyncExceptionsTable OBJECT-TYPE
	        SYNTAX  SEQUENCE OF  AsgSyncExceptionsEntry
			MAX-ACCESS  not-accessible
			STATUS  current
			DESCRIPTION "No description available"
			::= { asgSynchronization 3 }

	asgSyncExceptionsEntry OBJECT-TYPE
	        SYNTAX  AsgSyncExceptionsEntry
	        MAX-ACCESS  not-accessible
	        STATUS  current
	        DESCRIPTION "No description available"
	        INDEX   { asgSyncExceptionsIndex }
	        ::= { asgSyncExceptionsTable 1 }

    AsgSyncExceptionsEntry ::=
            SEQUENCE {
                asgSyncExceptionsIndex
                      Unsigned32,
                 asgSyncExceptionsID
                      INTEGER,
                 asgSyncExceptionsSource
					  DisplayString,
				 asgSyncExceptionsSourceMask
					  DisplayString,
				 asgSyncExceptionsDestination
					  DisplayString,
				 asgSyncExceptionsDestinationMask
					  DisplayString,
				 asgSyncExceptionsIpProtocol
					  DisplayString,
				 asgSyncExceptionsSync
					  DisplayString,
				 asgSyncExceptionsDelay
					  DisplayString
            }

    asgSyncExceptionsIndex OBJECT-TYPE
            SYNTAX  Unsigned32
            MAX-ACCESS  not-accessible
            STATUS  current
            DESCRIPTION "No description available"
            ::= { asgSyncExceptionsEntry 1 }

	asgSyncExceptionsID OBJECT-TYPE
            SYNTAX  Integer32
			MAX-ACCESS  read-only
			STATUS  current
			DESCRIPTION
	  		        "Exception ID"
            ::= { asgSyncExceptionsEntry 2 }

	asgSyncExceptionsSource OBJECT-TYPE
            SYNTAX  DisplayString
			MAX-ACCESS  read-only
			STATUS  current
			DESCRIPTION
	  		        "Source IP Address"
            ::= { asgSyncExceptionsEntry 3 }

	asgSyncExceptionsSourceMask OBJECT-TYPE
            SYNTAX  DisplayString
			MAX-ACCESS  read-only
			STATUS  current
			DESCRIPTION
	  		        "Source IP Mask"
            ::= { asgSyncExceptionsEntry 4 }

	asgSyncExceptionsDestination OBJECT-TYPE
            SYNTAX  DisplayString
			MAX-ACCESS  read-only
			STATUS  current
			DESCRIPTION
	  		        "Destination IP Address"
            ::= { asgSyncExceptionsEntry 5 }

	asgSyncExceptionsDestinationMask OBJECT-TYPE
            SYNTAX  DisplayString
			MAX-ACCESS  read-only
			STATUS  current
			DESCRIPTION
	  		        "Destination IP Mask"
            ::= { asgSyncExceptionsEntry 6 }

	asgSyncExceptionsIpProtocol OBJECT-TYPE
            SYNTAX  DisplayString
			MAX-ACCESS  read-only
			STATUS  current
			DESCRIPTION
	  		        "Exception IP Protocol"
            ::= { asgSyncExceptionsEntry 7 }

	asgSyncExceptionsSync OBJECT-TYPE
            SYNTAX  DisplayString
			MAX-ACCESS  read-only
			STATUS  current
			DESCRIPTION
	  		        "Exception Syncronization Type:
						0 = no sync
						1 = sync only to local chassis
						2 = sync only to other chassis
						3 = sync to all chassis"
            ::= { asgSyncExceptionsEntry 8 }

	asgSyncExceptionsDelay OBJECT-TYPE
            SYNTAX  DisplayString
			MAX-ACCESS  read-only
			STATUS  current
			DESCRIPTION
	  		        "Exception Delay Time:
					Default delays: http - 30, other - 5"
            ::= { asgSyncExceptionsEntry 9 }

	asgChassisParamsTable OBJECT-TYPE
	        SYNTAX  SEQUENCE OF  AsgChassisParamsEntry
			MAX-ACCESS  not-accessible
			STATUS  current
			DESCRIPTION "No description available"
			::= { asgChassisInfo 4 }

	asgChassisParamsEntry OBJECT-TYPE
	        SYNTAX  AsgChassisParamsEntry
	        MAX-ACCESS  not-accessible
	        STATUS  current
	        DESCRIPTION "No description available"
	        INDEX   { asgChassisParamsIndex }
	        ::= { asgChassisParamsTable 1 }

    AsgChassisParamsEntry ::=
            SEQUENCE {
                 asgChassisParamsIndex
                      Unsigned32,
                 asgChassisParamsID
                      DisplayString,
                 asgChassisParamsStatus
					  DisplayString,
				 asgChassisParamsGrade
					  DisplayString,
				 asgChassisParamsMaxGrade
					  DisplayString,
				 asgChassisParamsUniqueIP
					  DisplayString
            }

    asgChassisParamsIndex OBJECT-TYPE
            SYNTAX  Unsigned32
            MAX-ACCESS  not-accessible
            STATUS  current
            DESCRIPTION "No description available"
            ::= { asgChassisParamsEntry 1 }

	asgChassisParamsID OBJECT-TYPE
		SYNTAX  DisplayString (SIZE (0..255))
		MAX-ACCESS  read-only
		STATUS  current
		DESCRIPTION
			"Chassis ID: (1 / 2)"
		  ::= { asgChassisParamsEntry 2 }

	asgChassisParamsStatus OBJECT-TYPE
		SYNTAX  DisplayString (SIZE (0..255))
		MAX-ACCESS  read-only
		STATUS  current
		DESCRIPTION
			"Chassis Status:
			ACTIVE / STANDBY / INIT / DOWN / DOWN (Admin)"
		  ::= { asgChassisParamsEntry 3 }

	asgChassisParamsGrade OBJECT-TYPE
		SYNTAX  DisplayString (SIZE (0..255))
		MAX-ACCESS  read-only
		STATUS  current
		DESCRIPTION
			"Chassis Grade"
		  ::= { asgChassisParamsEntry 4 }

	asgChassisParamsMaxGrade OBJECT-TYPE
		SYNTAX  DisplayString (SIZE (0..255))
		MAX-ACCESS  read-only
		STATUS  current
		DESCRIPTION
			"Chassis Maximum Grade"
		  ::= { asgChassisParamsEntry 5 }

	asgChassisParamsUniqueIP OBJECT-TYPE
            SYNTAX  DisplayString (SIZE (0..255))
            MAX-ACCESS  read-only
            STATUS  current
            DESCRIPTION
                "Chassis Unique IP"
              ::= { asgChassisParamsEntry 6 }

	asgSGMTable OBJECT-TYPE
	        SYNTAX  SEQUENCE OF  AsgSGMEntry
			MAX-ACCESS  not-accessible
			STATUS  current
			DESCRIPTION "No description available"
			::= { asgChassisInfo 5 }

	asgSGMEntry OBJECT-TYPE
	        SYNTAX  AsgSGMEntry
	        MAX-ACCESS  not-accessible
	        STATUS  current
	        DESCRIPTION "No description available"
	        INDEX   { asgSGMIndex }
	        ::= { asgSGMTable 1 }

    AsgSGMEntry ::=
            SEQUENCE {
                asgSGMIndex
                      Unsigned32,
                 asgSGMID
                      INTEGER,
                 asgSGMStatus
					  DisplayString,
				 asgSGMProcess
					  DisplayString,
				 asgSGMPolicyTime
					  DisplayString
				}

    asgSGMIndex OBJECT-TYPE
            SYNTAX  Unsigned32
            MAX-ACCESS  not-accessible
            STATUS  current
            DESCRIPTION "No description available"
            ::= { asgSGMEntry 1 }

    asgSGMID OBJECT-TYPE
            SYNTAX  Integer32
            MAX-ACCESS  read-only
            STATUS  current
			DESCRIPTION
                "SGM ID"
            ::= { asgSGMEntry 2 }

    asgSGMStatus OBJECT-TYPE
            SYNTAX  DisplayString
            MAX-ACCESS  read-only
            STATUS  current
			DESCRIPTION
                "SGM Status"
            ::= { asgSGMEntry 3 }

    asgSGMProcess OBJECT-TYPE
            SYNTAX  DisplayString
            MAX-ACCESS  read-only
            STATUS  current
			DESCRIPTION
                "SGM Process state
				for example:
				(Enforcing Security, Inactive, Policy Started)"
            ::= { asgSGMEntry 4 }

    asgSGMPolicyTime OBJECT-TYPE
            SYNTAX  DisplayString
            MAX-ACCESS  read-only
            STATUS  current
			DESCRIPTION
                "SGM Policy Time"
            ::= { asgSGMEntry 5 }

	asgFactorTable OBJECT-TYPE
	        SYNTAX  SEQUENCE OF  AsgFactorEntry
			MAX-ACCESS  not-accessible
			STATUS  current
			DESCRIPTION "No description available"
			::= { asgChassisInfo 6 }

	asgFactorEntry OBJECT-TYPE
	        SYNTAX  AsgFactorEntry
	        MAX-ACCESS  not-accessible
	        STATUS  current
	        DESCRIPTION "No description available"
	        INDEX   { asgFactorIndex }
	        ::= { asgFactorTable 1 }

    AsgFactorEntry ::=
            SEQUENCE {
                asgFactorIndex
					Unsigned32,
				asgFactorName
                     DisplayString,
                asgFactorValue
                     DisplayString
            }

    asgFactorIndex OBJECT-TYPE
            SYNTAX  Unsigned32
            MAX-ACCESS  not-accessible
            STATUS  current
            DESCRIPTION "No description available"
            ::= { asgFactorEntry 1 }

    asgFactorName OBJECT-TYPE
            SYNTAX  DisplayString
            MAX-ACCESS  read-only
            STATUS  current
			DESCRIPTION
                "Factor Name"
            ::= { asgFactorEntry 2 }

    asgFactorValue OBJECT-TYPE
            SYNTAX  DisplayString
            MAX-ACCESS  read-only
            STATUS  current
			DESCRIPTION
                "Factor Value"
            ::= { asgFactorEntry 3 }

	asgPortPriorityTable OBJECT-TYPE
	        SYNTAX  SEQUENCE OF  AsgPortPriorityEntry
			MAX-ACCESS  not-accessible
			STATUS  current
			DESCRIPTION "No description available"
			::= { asgChassisInfo 7 }

	asgPortPriorityEntry OBJECT-TYPE
	        SYNTAX  AsgPortPriorityEntry
	        MAX-ACCESS  not-accessible
	        STATUS  current
	        DESCRIPTION "No description available"
	        INDEX   { asgPortPriorityIndex }
	        ::= { asgPortPriorityTable 1 }

    AsgPortPriorityEntry ::=
            SEQUENCE {
                asgPortPriorityIndex
					Unsigned32,
				asgPriorityPortName
                     DisplayString,
                asgPortPriority
                     DisplayString
            }

    asgPortPriorityIndex OBJECT-TYPE
            SYNTAX  Unsigned32
            MAX-ACCESS  not-accessible
            STATUS  current
            DESCRIPTION "No description available"
            ::= { asgPortPriorityEntry 1 }

    asgPriorityPortName OBJECT-TYPE
            SYNTAX  DisplayString
            MAX-ACCESS  read-only
            STATUS  current
			DESCRIPTION
                "Port Name"
            ::= { asgPortPriorityEntry 2 }

    asgPortPriority OBJECT-TYPE
            SYNTAX  DisplayString
            MAX-ACCESS  read-only
            STATUS  current
			DESCRIPTION
                "Port Priority:
				(Standard / High)"
            ::= { asgPortPriorityEntry 3 }

	-- Cores Utilization Table

	asgCoresUtilTable OBJECT-TYPE
			SYNTAX  SEQUENCE OF  AsgCoresUtilEntry
			MAX-ACCESS  not-accessible
			STATUS  current
			DESCRIPTION "No description available"
			::= { asg 29 }

	asgCoresUtilEntry OBJECT-TYPE
			SYNTAX  AsgCoresUtilEntry
	        MAX-ACCESS  not-accessible
	        STATUS  current
	        DESCRIPTION "No description available"
	        INDEX   { asgCoreIndex }
	        ::= { asgCoresUtilTable 1 }

    AsgCoresUtilEntry ::=
            SEQUENCE {
				asgCoreIndex
					Unsigned32,
				asgCoreRowTitle
                    DisplayString,
                blade1
                    DisplayString,
                blade2
                    DisplayString,
                blade3
                    DisplayString,
                blade4
                    DisplayString,
                blade5
                    DisplayString,
                blade6
                    DisplayString,
                blade7
                    DisplayString,
                blade8
                    DisplayString,
                blade9
                    DisplayString,
                blade10
                    DisplayString,
                blade11
                    DisplayString,
                blade12
                    DisplayString,
                blade13
                    DisplayString,
                blade14
                    DisplayString,
                blade15
                    DisplayString,
                blade16
                    DisplayString,
                blade17
                    DisplayString,
                blade18
                    DisplayString,
                blade19
                    DisplayString,
                blade20
                    DisplayString,
                blade21
                    DisplayString,
                blade22
                    DisplayString,
                blade23
                    DisplayString,
                blade24
                    DisplayString,
                blade25
                    DisplayString,
                blade26
                    DisplayString,
                blade27
                    DisplayString,
                blade28
                    DisplayString,
                blade29
                    DisplayString,
                blade30
                    DisplayString,
                blade31
                    DisplayString,
                blade32
                    DisplayString,
                blade33
                    DisplayString,
                blade34
                    DisplayString,
                blade35
                    DisplayString,
                blade36
                    DisplayString,
                blade37
                    DisplayString,
                blade38
                    DisplayString,
                blade39
                    DisplayString,
                blade40
                    DisplayString,
                blade41
                    DisplayString,
                blade42
                    DisplayString,
                blade43
                    DisplayString,
                blade44
                    DisplayString,
                blade45
                    DisplayString,
                blade46
                    DisplayString,
                blade47
                    DisplayString,
                blade48
                    DisplayString
	        }

    asgCoreIndex OBJECT-TYPE
			SYNTAX  Unsigned32
            MAX-ACCESS  not-accessible
            STATUS  current
            DESCRIPTION "No description available"
            ::= { asgCoresUtilEntry 1 }

	asgCoreRowTitle	OBJECT-TYPE
			SYNTAX  DisplayString
            MAX-ACCESS  read-only
            STATUS  current
            DESCRIPTION "No description available"
            ::= { asgCoresUtilEntry 2 }

	blade1 OBJECT-TYPE
            SYNTAX  DisplayString
            MAX-ACCESS  read-only
            STATUS  current
			DESCRIPTION
					"1st blade"
            ::= { asgCoresUtilEntry 3 }

	blade2 OBJECT-TYPE
            SYNTAX  DisplayString
            MAX-ACCESS  read-only
            STATUS  current
			DESCRIPTION
					"2nd blade"
            ::= { asgCoresUtilEntry 4 }

	blade3 OBJECT-TYPE
            SYNTAX  DisplayString
            MAX-ACCESS  read-only
            STATUS  current
			DESCRIPTION
					"3rd blade"
            ::= { asgCoresUtilEntry 5 }

	blade4 OBJECT-TYPE
            SYNTAX  DisplayString
            MAX-ACCESS  read-only
            STATUS  current
			DESCRIPTION
					"4th blade"
            ::= { asgCoresUtilEntry 6 }

	blade5 OBJECT-TYPE
            SYNTAX  DisplayString
            MAX-ACCESS  read-only
            STATUS  current
			DESCRIPTION
					"5th blade"
            ::= { asgCoresUtilEntry 7 }

	blade6 OBJECT-TYPE
            SYNTAX  DisplayString
            MAX-ACCESS  read-only
            STATUS  current
			DESCRIPTION
					"6th blade"
            ::= { asgCoresUtilEntry 8 }

	blade7 OBJECT-TYPE
            SYNTAX  DisplayString
            MAX-ACCESS  read-only
            STATUS  current
			DESCRIPTION
					"7th blade"
            ::= { asgCoresUtilEntry 9 }

	blade8 OBJECT-TYPE
            SYNTAX  DisplayString
            MAX-ACCESS  read-only
            STATUS  current
			DESCRIPTION
					"8th blade"
            ::= { asgCoresUtilEntry 10 }

	blade9 OBJECT-TYPE
            SYNTAX  DisplayString
            MAX-ACCESS  read-only
            STATUS  current
			DESCRIPTION
					"9th blade"
            ::= { asgCoresUtilEntry 11 }

	blade10 OBJECT-TYPE
            SYNTAX  DisplayString
            MAX-ACCESS  read-only
            STATUS  current
			DESCRIPTION
					"10th blade"
            ::= { asgCoresUtilEntry 12 }

	blade11 OBJECT-TYPE
            SYNTAX  DisplayString
            MAX-ACCESS  read-only
            STATUS  current
			DESCRIPTION
					"11th blade"
            ::= { asgCoresUtilEntry 13 }

	blade12 OBJECT-TYPE
            SYNTAX  DisplayString
            MAX-ACCESS  read-only
            STATUS  current
			DESCRIPTION
					"12ve blade"
            ::= { asgCoresUtilEntry 14 }

	blade13 OBJECT-TYPE
            SYNTAX  DisplayString
            MAX-ACCESS  read-only
            STATUS  current
			DESCRIPTION
					"13th blade"
            ::= { asgCoresUtilEntry 15 }

	blade14 OBJECT-TYPE
            SYNTAX  DisplayString
            MAX-ACCESS  read-only
            STATUS  current
			DESCRIPTION
					"14th blade"
            ::= { asgCoresUtilEntry 16 }

	blade15 OBJECT-TYPE
            SYNTAX  DisplayString
            MAX-ACCESS  read-only
            STATUS  current
			DESCRIPTION
					"15th blade"
            ::= { asgCoresUtilEntry 17 }

	blade16 OBJECT-TYPE
            SYNTAX  DisplayString
            MAX-ACCESS  read-only
            STATUS  current
			DESCRIPTION
					"16th blade"
            ::= { asgCoresUtilEntry 18 }

	blade17 OBJECT-TYPE
            SYNTAX  DisplayString
            MAX-ACCESS  read-only
            STATUS  current
			DESCRIPTION
					"17th blade"
            ::= { asgCoresUtilEntry 19 }

	blade18 OBJECT-TYPE
            SYNTAX  DisplayString
            MAX-ACCESS  read-only
            STATUS  current
			DESCRIPTION
					"18th blade"
            ::= { asgCoresUtilEntry 20 }

	blade19 OBJECT-TYPE
            SYNTAX  DisplayString
            MAX-ACCESS  read-only
            STATUS  current
			DESCRIPTION
					"19th blade"
            ::= { asgCoresUtilEntry 21 }

	blade20 OBJECT-TYPE
            SYNTAX  DisplayString
            MAX-ACCESS  read-only
            STATUS  current
			DESCRIPTION
					"20th blade"
            ::= { asgCoresUtilEntry 22 }

	blade21 OBJECT-TYPE
            SYNTAX  DisplayString
            MAX-ACCESS  read-only
            STATUS  current
			DESCRIPTION
					"21st blade"
            ::= { asgCoresUtilEntry 23 }

	blade22 OBJECT-TYPE
            SYNTAX  DisplayString
            MAX-ACCESS  read-only
            STATUS  current
			DESCRIPTION
					"22nd blade"
            ::= { asgCoresUtilEntry 24 }

	blade23 OBJECT-TYPE
            SYNTAX  DisplayString
            MAX-ACCESS  read-only
            STATUS  current
			DESCRIPTION
					"23rd blade"
            ::= { asgCoresUtilEntry 25 }

	blade24 OBJECT-TYPE
            SYNTAX  DisplayString
            MAX-ACCESS  read-only
            STATUS  current
			DESCRIPTION
					"24th blade"
            ::= { asgCoresUtilEntry 26 }

	blade25 OBJECT-TYPE
            SYNTAX  DisplayString
            MAX-ACCESS  read-only
            STATUS  current
			DESCRIPTION
					"25th blade"
            ::= { asgCoresUtilEntry 27 }

	blade26 OBJECT-TYPE
            SYNTAX  DisplayString
            MAX-ACCESS  read-only
            STATUS  current
			DESCRIPTION
					"26th blade"
            ::= { asgCoresUtilEntry 28 }

	blade27 OBJECT-TYPE
            SYNTAX  DisplayString
            MAX-ACCESS  read-only
            STATUS  current
			DESCRIPTION
					"27th blade"
            ::= { asgCoresUtilEntry 29 }

	blade28 OBJECT-TYPE
            SYNTAX  DisplayString
            MAX-ACCESS  read-only
            STATUS  current
			DESCRIPTION
					"28th blade"
            ::= { asgCoresUtilEntry 30 }

	blade29 OBJECT-TYPE
            SYNTAX  DisplayString
            MAX-ACCESS  read-only
            STATUS  current
			DESCRIPTION
					"29th blade"
            ::= { asgCoresUtilEntry 31 }

	blade30 OBJECT-TYPE
            SYNTAX  DisplayString
            MAX-ACCESS  read-only
            STATUS  current
			DESCRIPTION
					"30th blade"
            ::= { asgCoresUtilEntry 32 }

	blade31 OBJECT-TYPE
            SYNTAX  DisplayString
            MAX-ACCESS  read-only
            STATUS  current
			DESCRIPTION
					"31th blade"
            ::= { asgCoresUtilEntry 33 }

	blade32 OBJECT-TYPE
            SYNTAX  DisplayString
            MAX-ACCESS  read-only
            STATUS  current
			DESCRIPTION
					"32th blade"
            ::= { asgCoresUtilEntry 34 }

	blade33 OBJECT-TYPE
            SYNTAX  DisplayString
            MAX-ACCESS  read-only
            STATUS  current
			DESCRIPTION
					"33th blade"
            ::= { asgCoresUtilEntry 35 }

	blade34 OBJECT-TYPE
            SYNTAX  DisplayString
            MAX-ACCESS  read-only
            STATUS  current
			DESCRIPTION
					"34th blade"
            ::= { asgCoresUtilEntry 36 }

	blade35 OBJECT-TYPE
            SYNTAX  DisplayString
            MAX-ACCESS  read-only
            STATUS  current
			DESCRIPTION
					"35th blade"
            ::= { asgCoresUtilEntry 37 }

	blade36 OBJECT-TYPE
            SYNTAX  DisplayString
            MAX-ACCESS  read-only
            STATUS  current
			DESCRIPTION
					"36th blade"
            ::= { asgCoresUtilEntry 38 }

	blade37 OBJECT-TYPE
            SYNTAX  DisplayString
            MAX-ACCESS  read-only
            STATUS  current
			DESCRIPTION
					"37th blade"
            ::= { asgCoresUtilEntry 39 }

	blade38 OBJECT-TYPE
            SYNTAX  DisplayString
            MAX-ACCESS  read-only
            STATUS  current
			DESCRIPTION
					"38th blade"
            ::= { asgCoresUtilEntry 40 }

	blade39 OBJECT-TYPE
            SYNTAX  DisplayString
            MAX-ACCESS  read-only
            STATUS  current
			DESCRIPTION
					"39th blade"
            ::= { asgCoresUtilEntry 41 }

	blade40 OBJECT-TYPE
            SYNTAX  DisplayString
            MAX-ACCESS  read-only
            STATUS  current
			DESCRIPTION
					"40th blade"
            ::= { asgCoresUtilEntry 42 }

	blade41 OBJECT-TYPE
            SYNTAX  DisplayString
            MAX-ACCESS  read-only
            STATUS  current
			DESCRIPTION
					"41th blade"
            ::= { asgCoresUtilEntry 43 }

	blade42 OBJECT-TYPE
            SYNTAX  DisplayString
            MAX-ACCESS  read-only
            STATUS  current
			DESCRIPTION
					"42th blade"
            ::= { asgCoresUtilEntry 44 }

	blade43 OBJECT-TYPE
            SYNTAX  DisplayString
            MAX-ACCESS  read-only
            STATUS  current
			DESCRIPTION
					"43th blade"
            ::= { asgCoresUtilEntry 45 }

	blade44 OBJECT-TYPE
            SYNTAX  DisplayString
            MAX-ACCESS  read-only
            STATUS  current
			DESCRIPTION
					"44th blade"
            ::= { asgCoresUtilEntry 46 }

	blade45 OBJECT-TYPE
            SYNTAX  DisplayString
            MAX-ACCESS  read-only
            STATUS  current
			DESCRIPTION
					"45th blade"
            ::= { asgCoresUtilEntry 47 }

	blade46 OBJECT-TYPE
            SYNTAX  DisplayString
            MAX-ACCESS  read-only
            STATUS  current
			DESCRIPTION
					"46th blade"
            ::= { asgCoresUtilEntry 48 }

	blade47 OBJECT-TYPE
            SYNTAX  DisplayString
            MAX-ACCESS  read-only
            STATUS  current
			DESCRIPTION
					"47th blade"
            ::= { asgCoresUtilEntry 49 }

	blade48 OBJECT-TYPE
            SYNTAX  DisplayString
            MAX-ACCESS  read-only
            STATUS  current
			DESCRIPTION
					"48th blade"
            ::= { asgCoresUtilEntry 50 }

	--VSLS statuses:

	asgVSX OBJECT IDENTIFIER ::= { asg 30 }

	asgVslsInfo OBJECT IDENTIFIER ::= { asgVSX 20 }

	asgVslsSgmRatio OBJECT-TYPE
                        SYNTAX  Unsigned32
                        MAX-ACCESS  read-only
                        STATUS  current
                        DESCRIPTION
                           "Threshold ratio for failover. Ratio is calculated by number of SGMS between Chassis"
                          ::= { asgVslsInfo 1 }

	asgVslsSystemPrimaryChassis OBJECT-TYPE
                        SYNTAX  DisplayString
                        MAX-ACCESS  read-only
                        STATUS  current
                        DESCRIPTION
                           "Method for defaulting Chassis per each VS.
								0 - Automatic. System decides automatically on primary Chassis, based on VS ID.
								1 - defaulting Chassis 1 for all VSs
								2 - defaulting Chassis 2 for all VSs"
                          ::= { asgVslsInfo 2 }

	asgVslsStateTable OBJECT-TYPE
                SYNTAX  SEQUENCE OF  AsgVslsStateEntry
                        MAX-ACCESS  not-accessible
                        STATUS  current
                        DESCRIPTION "No description available"
                        ::= { asgVslsInfo 10 }

	asgVslsStateEntry OBJECT-TYPE
                SYNTAX  AsgVslsStateEntry
                MAX-ACCESS  not-accessible
                STATUS  current
                DESCRIPTION "No description available"
                INDEX   { asgVslsVsid }
                ::= { asgVslsStateTable 1 }

	AsgVslsStateEntry ::=
            SEQUENCE {
                 asgVslsVsid
			Unsigned32,
                 asgVslsVsName
			DisplayString,
                 asgVslsVsPrimaryChassis
			Unsigned32,
                 asgVslsVsActiveChassis
			Unsigned32,
                 asgVslsVsHealth
			DisplayString,
		asgVslsVsReason
			DisplayString,
		asgVslsVsChassis1InterfacesUp
			Unsigned32,
		asgVslsVsChassis1InterfacesTotal
			Unsigned32,
		 asgVslsVsChassis1FwksUp
			  Unsigned32,
		 asgVslsVsChassis1FwksTotal
			  Unsigned32,
		 asgVslsVsChassis2InterfacesUp
			  Unsigned32,
		 asgVslsVsChassis2InterfacesTotal
			  Unsigned32,
		 asgVslsVsChassis2FwksUp
			  Unsigned32,
		 asgVslsVsChassis2FwksTotal
			  Unsigned32,
		 asgVslsVsChassis3InterfacesUp
			  Unsigned32,
		 asgVslsVsChassis3InterfacesTotal
			  Unsigned32,
		 asgVslsVsChassis3FwksUp
			  Unsigned32,
		 asgVslsVsChassis3FwksTotal
			  Unsigned32,
		 asgVslsVsChassis4InterfacesUp
			  Unsigned32,
		 asgVslsVsChassis4InterfacesTotal
			  Unsigned32,
		 asgVslsVsChassis4FwksUp
			  Unsigned32,
		 asgVslsVsChassis4FwksTotal
			  Unsigned32
            }

	asgVslsVsid OBJECT-TYPE
            SYNTAX  Unsigned32
            MAX-ACCESS  not-accessible
            STATUS  current
            DESCRIPTION "VS index"
            ::= { asgVslsStateEntry 1 }

	asgVslsVsName OBJECT-TYPE
                SYNTAX  DisplayString (SIZE (0..255))
                MAX-ACCESS  read-only
                STATUS  current
                DESCRIPTION
                        "VS name"
                  ::= { asgVslsStateEntry 2 }

	asgVslsVsPrimaryChassis OBJECT-TYPE
            SYNTAX  Unsigned32
            MAX-ACCESS  read-only
            STATUS  current
            DESCRIPTION "VS primary Chassis"
            ::= { asgVslsStateEntry 3 }

	asgVslsVsActiveChassis OBJECT-TYPE
            SYNTAX  Unsigned32
            MAX-ACCESS  read-only
            STATUS  current
            DESCRIPTION "VS Active Chassis"
            ::= { asgVslsStateEntry 4 }

	asgVslsVsHealth OBJECT-TYPE
            SYNTAX  DisplayString (SIZE (0..255))
            MAX-ACCESS  read-only
            STATUS  current
            DESCRIPTION
                    "VS status string"
            ::= { asgVslsStateEntry 5 }

	asgVslsVsReason OBJECT-TYPE
            SYNTAX  DisplayString (SIZE (0..255))
            MAX-ACCESS  read-only
            STATUS  current
            DESCRIPTION
                    "Reason for prefaring Active Chassis"
            ::= { asgVslsStateEntry 6 }

	asgVslsVsChassis1InterfacesUp OBJECT-TYPE
            SYNTAX  Unsigned32
            MAX-ACCESS  read-only
            STATUS  current
            DESCRIPTION "Number of UP interfaces on Chassis 1"
            ::= { asgVslsStateEntry 7 }

	asgVslsVsChassis1InterfacesTotal OBJECT-TYPE
            SYNTAX  Unsigned32
            MAX-ACCESS  read-only
            STATUS  current
            DESCRIPTION "Number of configured interfaces on Chassis 1"
            ::= { asgVslsStateEntry 8 }

	asgVslsVsChassis1FwksUp OBJECT-TYPE
            SYNTAX  Unsigned32
            MAX-ACCESS  read-only
            STATUS  current
            DESCRIPTION "Number of FWKs on Chassis 1"
            ::= { asgVslsStateEntry 9 }

	asgVslsVsChassis1FwksTotal OBJECT-TYPE
            SYNTAX  Unsigned32
            MAX-ACCESS  read-only
            STATUS  current
            DESCRIPTION "Optimum number of FWKs for Chassis 1"
            ::= { asgVslsStateEntry 10 }

	asgVslsVsChassis2InterfacesUp OBJECT-TYPE
            SYNTAX  Unsigned32
            MAX-ACCESS  read-only
            STATUS  current
            DESCRIPTION "Number of UP interfaces on Chassis 2"
            ::= { asgVslsStateEntry 21 }

	asgVslsVsChassis2InterfacesTotal OBJECT-TYPE
            SYNTAX  Unsigned32
            MAX-ACCESS  read-only
            STATUS  current
            DESCRIPTION "Number of configured interfaces on Chassis 2"
            ::= { asgVslsStateEntry 22 }

	asgVslsVsChassis2FwksUp OBJECT-TYPE
            SYNTAX  Unsigned32
            MAX-ACCESS  read-only
            STATUS  current
            DESCRIPTION "Number of FWKs on Chassis 2"
            ::= { asgVslsStateEntry 23 }

	asgVslsVsChassis2FwksTotal OBJECT-TYPE
            SYNTAX  Unsigned32
            MAX-ACCESS  read-only
            STATUS  current
            DESCRIPTION "Optimum number of FWKs on Chassis 2"
            ::= { asgVslsStateEntry 24 }

  asgVslsVsChassis3InterfacesUp OBJECT-TYPE
            SYNTAX  Unsigned32
            MAX-ACCESS  read-only
            STATUS  current
            DESCRIPTION "Number of UP interfaces on Chassis 3"
            ::= { asgVslsStateEntry 31 }

  asgVslsVsChassis3InterfacesTotal OBJECT-TYPE
            SYNTAX  Unsigned32
            MAX-ACCESS  read-only
            STATUS  current
            DESCRIPTION "Number of configured interfaces on Chassis 3"
            ::= { asgVslsStateEntry 32 }

  asgVslsVsChassis3FwksUp OBJECT-TYPE
            SYNTAX  Unsigned32
            MAX-ACCESS  read-only
            STATUS  current
            DESCRIPTION "Number of FWKs on Chassis 3"
            ::= { asgVslsStateEntry 33 }

  asgVslsVsChassis3FwksTotal OBJECT-TYPE
            SYNTAX  Unsigned32
            MAX-ACCESS  read-only
            STATUS  current
            DESCRIPTION "Optimum number of FWKs on Chassis 3"
            ::= { asgVslsStateEntry 34 }

  asgVslsVsChassis4InterfacesUp OBJECT-TYPE
            SYNTAX  Unsigned32
            MAX-ACCESS  read-only
            STATUS  current
            DESCRIPTION "Number of UP interfaces on Chassis 4"
            ::= { asgVslsStateEntry 41 }

  asgVslsVsChassis4InterfacesTotal OBJECT-TYPE
            SYNTAX  Unsigned32
            MAX-ACCESS  read-only
            STATUS  current
            DESCRIPTION "Number of configured interfaces on Chassis 4"
            ::= { asgVslsStateEntry 42 }

  asgVslsVsChassis4FwksUp OBJECT-TYPE
            SYNTAX  Unsigned32
            MAX-ACCESS  read-only
            STATUS  current
            DESCRIPTION "Number of FWKs on Chassis 4"
            ::= { asgVslsStateEntry 43 }

  asgVslsVsChassis4FwksTotal OBJECT-TYPE
            SYNTAX  Unsigned32
            MAX-ACCESS  read-only
            STATUS  current
            DESCRIPTION "Optimum number of FWKs on Chassis 4"
            ::= { asgVslsStateEntry 44 }

	-- VSX Conn info
	asgVSXConnInfo OBJECT IDENTIFIER ::= { asgVSX 30 }

	asgVSXConnInfoTable OBJECT-TYPE
			SYNTAX  SEQUENCE OF  AsgVSXConnInfoEntry
			MAX-ACCESS  not-accessible
			STATUS  current
			DESCRIPTION "Table with connection information per VS per Member"
			::= { asgVSXConnInfo 10 }

	asgVSXConnInfoEntry OBJECT-TYPE
                SYNTAX  AsgVSXConnInfoEntry
                MAX-ACCESS  not-accessible
                STATUS  current
                DESCRIPTION "No description available"
				INDEX   { asgVSXConnInfoIndex }
                ::= { asgVSXConnInfoTable 1 }

	AsgVSXConnInfoEntry ::=
            SEQUENCE {
						asgVSXConnInfoIndex
								Unsigned32,
                        asgVSXConnBladeID
                                DisplayString,
                        asgVSXIPver
                                DisplayString,
                        asgVSXConcurrentConns
                                Counter64,
                        asgVSXPeakConns
                                Counter64,
                        asgVSXConnLimit
                                DisplayString
            }

	asgVSXConnInfoIndex OBJECT-TYPE
		SYNTAX  Unsigned32
		MAX-ACCESS  not-accessible
		STATUS  current
		DESCRIPTION "Record index"
		::= { asgVSXConnInfoEntry 1 }

	asgVSXConnBladeID OBJECT-TYPE
		SYNTAX  DisplayString
		MAX-ACCESS  read-only
		STATUS  current
		DESCRIPTION
				"Member ID"
		::= { asgVSXConnInfoEntry 2 }

	asgVSXIPver OBJECT-TYPE
		SYNTAX  DisplayString
		MAX-ACCESS  read-only
		STATUS  current
		DESCRIPTION
				"IP Version"
		::= { asgVSXConnInfoEntry 3 }

	asgVSXConcurrentConns OBJECT-TYPE
			SYNTAX  Counter64
			MAX-ACCESS  read-only
			STATUS  current
			DESCRIPTION
					"Concurrent connections number on this VS"
			::= { asgVSXConnInfoEntry 4 }

	asgVSXPeakConns OBJECT-TYPE
			SYNTAX  Counter64
			MAX-ACCESS  read-only
			STATUS  current
			DESCRIPTION
					"Peak connection number on this VS"
			::= { asgVSXConnInfoEntry 5 }

	asgVSXConnLimit OBJECT-TYPE
			SYNTAX  DisplayString
			MAX-ACCESS  read-only
			STATUS  current
			DESCRIPTION
					"Total connections limit on this VS"
			::= { asgVSXConnInfoEntry 6 }

	--Connections Number per system:
 	asgVSXConnectionsNumberPerSystem OBJECT-TYPE
      		SYNTAX  Counter64
			MAX-ACCESS  read-only
			STATUS  current
			DESCRIPTION
				"Total connections number on this VS (across all Members)"
			::= {asgVSXConnInfo 20 }

        -- VSX cross sys Mem info
	asgVSXMemInfo OBJECT IDENTIFIER ::= { asgVSX 40 }

	asgVSXMemInfoTable OBJECT-TYPE
			SYNTAX  SEQUENCE OF  AsgVSXMemInfoEntry
			MAX-ACCESS  not-accessible
			STATUS  current
			DESCRIPTION "Physical memory usage per VS per Member"
			::= { asgVSXMemInfo 10 }

	asgVSXMemInfoEntry OBJECT-TYPE
                SYNTAX  AsgVSXMemInfoEntry
                MAX-ACCESS  not-accessible
                STATUS  current
                DESCRIPTION "No description available"
				INDEX   { asgVSXMemInfoIndex }
                ::= { asgVSXMemInfoTable 1 }

	AsgVSXMemInfoEntry ::=
            SEQUENCE {
						asgVSXMemInfoIndex
								Unsigned32,
                        asgVSXMemBladeid
                                DisplayString,
                        asgVSXOverallMem
                                Counter64
            }

	asgVSXMemInfoIndex OBJECT-TYPE
		SYNTAX  Unsigned32
		MAX-ACCESS  not-accessible
		STATUS  current
		DESCRIPTION "Record index"
		::= { asgVSXMemInfoEntry 1 }

	asgVSXMemBladeid OBJECT-TYPE
			SYNTAX  DisplayString
			MAX-ACCESS  read-only
			STATUS  current
			DESCRIPTION
					"Member ID - defined as ChassisID_MemberID"
			::= { asgVSXMemInfoEntry 2 }

	asgVSXOverallMem OBJECT-TYPE
			SYNTAX  Counter64
			MAX-ACCESS  read-only
			STATUS  current
			DESCRIPTION
					"Overall physical memory
					of the virtual system in Member (Bytes)"
			::= { asgVSXMemInfoEntry 3 }

	--VSX Cross System CPU usage
	asgVSXCoreUtilInfo OBJECT IDENTIFIER ::= { asgVSX 50 }

	asgVSXCoreUtilTable OBJECT-TYPE
			SYNTAX  SEQUENCE OF  AsgVSXCoreUtilEntry
			MAX-ACCESS  not-accessible
			STATUS  current
			DESCRIPTION "CPU usage table per VS per Member per CPU"
			::= { asgVSXCoreUtilInfo 10 }

	asgVSXCoreUtilEntry OBJECT-TYPE
                SYNTAX  AsgVSXCoreUtilEntry
                MAX-ACCESS  not-accessible
                STATUS  current
                DESCRIPTION "No description available"
                INDEX   { asgVSXCoreUtilIndex }
                ::= { asgVSXCoreUtilTable 1 }

	AsgVSXCoreUtilEntry ::=
            SEQUENCE {
                        asgVSXCoreUtilIndex
                                Unsigned32,
                        asgVSXCoreUtilBladeid
                                DisplayString,
                        asgVSXCoreUtilCPUID
                                Integer32,
                        asgVSXCoreUtilUsage
                                DisplayString
            }

	asgVSXCoreUtilIndex OBJECT-TYPE
		SYNTAX  Unsigned32
		MAX-ACCESS  not-accessible
		STATUS  current
		DESCRIPTION "Record index"
		::= { asgVSXCoreUtilEntry 1 }

	asgVSXCoreUtilBladeid OBJECT-TYPE
			SYNTAX  DisplayString
			MAX-ACCESS  read-only
			STATUS  current
			DESCRIPTION
					"Member ID - defined as ChassisID_MemberID"
			::= { asgVSXCoreUtilEntry 2 }


	asgVSXCoreUtilCPUID OBJECT-TYPE
			SYNTAX  Integer32
			MAX-ACCESS  read-only
			STATUS  current
			DESCRIPTION
					"CPU Core ID"
			::= { asgVSXCoreUtilEntry 3 }

	asgVSXCoreUtilUsage OBJECT-TYPE
			SYNTAX  DisplayString
			MAX-ACCESS  read-only
			STATUS  current
			DESCRIPTION
					"CPU core utilization average over the last
                                        minute by this VS in percentage"
			::= { asgVSXCoreUtilEntry 4 }


    -- VSX cross packet rate info
	asgVSXPacketRateInfo OBJECT IDENTIFIER ::= { asgVSX 80 }

	asgVSXPacketRateTable OBJECT-TYPE
			SYNTAX  SEQUENCE OF  AsgVSXPacketRateEntry
			MAX-ACCESS  not-accessible
			STATUS  current
			DESCRIPTION "Packet rate per VS per Member"
			::= { asgVSXPacketRateInfo 10 }

	asgVSXPacketRateEntry OBJECT-TYPE
                SYNTAX  AsgVSXPacketRateEntry
                MAX-ACCESS  not-accessible
                STATUS  current
                DESCRIPTION "No description available"
				INDEX { asgVSXPacketRateIndex }
                ::= { asgVSXPacketRateTable 1 }

	AsgVSXPacketRateEntry ::=
            SEQUENCE {
						asgVSXPacketRateIndex
								Unsigned32,
                        asgVSXRateBladeid
                                DisplayString,
                        asgVSXRateValue
                                Counter64
            }

	asgVSXPacketRateIndex OBJECT-TYPE
		SYNTAX  Unsigned32
		MAX-ACCESS  not-accessible
		STATUS  current
		DESCRIPTION "Record index"
		::= { asgVSXPacketRateEntry 1 }

	asgVSXRateBladeid OBJECT-TYPE
			SYNTAX  DisplayString
			MAX-ACCESS  read-only
			STATUS  current
			DESCRIPTION
					"Member ID - defined as ChassisID_MemberID"
			::= { asgVSXPacketRateEntry 2 }

	asgVSXRateValue OBJECT-TYPE
			SYNTAX  Counter64
			MAX-ACCESS  read-only
			STATUS  current
			DESCRIPTION
					"Packet rate on this Member"
			::= { asgVSXPacketRateEntry 3 }

	--Packet rate per system:
 	asgVSXPacketRatePerSystem OBJECT-TYPE
      		SYNTAX  Counter64
			MAX-ACCESS  read-only
			STATUS  current
			DESCRIPTION
				"VS's total packet rate (on all Members)"
			::= {asgVSXPacketRateInfo 20 }

        -- VSX cross Throughput info
	asgVSXThroughputInfo OBJECT IDENTIFIER ::= { asgVSX 90 }

	asgVSXThroughputTable OBJECT-TYPE
			SYNTAX  SEQUENCE OF  AsgVSXThroughputEntry
			MAX-ACCESS  not-accessible
			STATUS  current
			DESCRIPTION "Throughput per VS per Member"
			::= { asgVSXThroughputInfo 10 }

	asgVSXThroughputEntry OBJECT-TYPE
                SYNTAX  AsgVSXThroughputEntry
                MAX-ACCESS  not-accessible
                STATUS  current
                DESCRIPTION "No description available"
				INDEX { asgVSXThroughputIndex }
                ::= { asgVSXThroughputTable 1 }

	AsgVSXThroughputEntry ::=
            SEQUENCE {
						asgVSXThroughputIndex
								Unsigned32,
                        asgVSXThroughputBladeid
                                DisplayString,
                        asgVSXThroughputValue
                                Counter64
            }

	asgVSXThroughputIndex OBJECT-TYPE
		SYNTAX  Unsigned32
		MAX-ACCESS  not-accessible
		STATUS  current
		DESCRIPTION "Record index"
		::= { asgVSXThroughputEntry 1 }

	asgVSXThroughputBladeid OBJECT-TYPE
			SYNTAX  DisplayString
			MAX-ACCESS  read-only
			STATUS  current
			DESCRIPTION
					"Member ID - defined as ChassisID_MemberID"
			::= { asgVSXThroughputEntry 2 }

	asgVSXThroughputValue OBJECT-TYPE
			SYNTAX  Counter64
			MAX-ACCESS  read-only
			STATUS  current
			DESCRIPTION
					"IPv4 + IPv6 Throughput on this Member for current VS (Bytes/Second)"
			::= { asgVSXThroughputEntry 3 }

	--Throughput per system:
 	asgVSXThroughputPerSystem OBJECT-TYPE
      		SYNTAX  Counter64
			MAX-ACCESS  read-only
			STATUS  current
			DESCRIPTION
				"VS's total IPv4 + IPv6 throughput(on all Members)"
			::= {asgVSXThroughputInfo 20 }

        -- VSX cross Throughput per interface info
	asgVSXThroughputPerInterfaceInfo OBJECT IDENTIFIER ::= { asgVSX 100 }

	asgVSXThroughputPerInterfaceTable OBJECT-TYPE
			SYNTAX  SEQUENCE OF  AsgVSXThroughputPerInterfaceEntry
			MAX-ACCESS  not-accessible
			STATUS  current
			DESCRIPTION "Throughput per Interface per VS per Member"
			::= { asgVSXThroughputPerInterfaceInfo 10 }

	asgVSXThroughputPerInterfaceEntry OBJECT-TYPE
                SYNTAX  AsgVSXThroughputPerInterfaceEntry
                MAX-ACCESS  not-accessible
                STATUS  current
                DESCRIPTION "No description available"
				INDEX { asgVSXThroughputPerInterfaceIndex }
                ::= { asgVSXThroughputPerInterfaceTable 1 }

	AsgVSXThroughputPerInterfaceEntry ::=
            SEQUENCE {
						asgVSXThroughputPerInterfaceIndex
								Unsigned32,
                        asgVSXThroughputPerInterfaceBladeid
                                DisplayString,
                        asgVSXThroughputPerInterfaceName
                                DisplayString,
                        asgVSXThroughputPerInterfaceValue
                                Counter64
            }

	asgVSXThroughputPerInterfaceIndex OBJECT-TYPE
		SYNTAX  Unsigned32
		MAX-ACCESS  not-accessible
		STATUS  current
		DESCRIPTION "Record index"
		::= { asgVSXThroughputPerInterfaceEntry 1 }

	asgVSXThroughputPerInterfaceBladeid OBJECT-TYPE
			SYNTAX  DisplayString
			MAX-ACCESS  read-only
			STATUS  current
			DESCRIPTION
					"Member ID - defined as ChassisID_MemberID"
			::= { asgVSXThroughputPerInterfaceEntry 2 }

	asgVSXThroughputPerInterfaceName OBJECT-TYPE
			SYNTAX  DisplayString
			MAX-ACCESS  read-only
			STATUS  current
			DESCRIPTION
					"Interface name"
			::= { asgVSXThroughputPerInterfaceEntry 3 }

	asgVSXThroughputPerInterfaceValue OBJECT-TYPE
			SYNTAX  Counter64
			MAX-ACCESS  read-only
			STATUS  current
			DESCRIPTION
					"Throughput on this Member (KB/Second) on current interface"
			::= { asgVSXThroughputPerInterfaceEntry 4 }

	-- VSX cross Throughput per interface per system info
	asgVSXPerSystemThroughputPerInterfaceTable OBJECT-TYPE
			SYNTAX  SEQUENCE OF  AsgVSXPerSystemThroughputPerInterfaceTableEntry
			MAX-ACCESS  not-accessible
			STATUS  current
			DESCRIPTION "Throughput per Interface per VS on System (across all Members)"
			::= { asgVSXThroughputPerInterfaceInfo 20 }

	asgVSXPerSystemThroughputPerInterfaceTableEntry OBJECT-TYPE
                SYNTAX  AsgVSXPerSystemThroughputPerInterfaceTableEntry
                MAX-ACCESS  not-accessible
                STATUS  current
                DESCRIPTION "No description available"
				INDEX { asgVSXPerSystemThroughputIndex }
                ::= { asgVSXPerSystemThroughputPerInterfaceTable 1 }

	AsgVSXPerSystemThroughputPerInterfaceTableEntry ::=
            SEQUENCE {
						asgVSXPerSystemThroughputIndex
								Unsigned32,
                        asgVSXPerSystemThroughputPerInterfaceName
                                DisplayString,
                        asgVSXPerSystemThroughputPerInterfaceValue
                                Counter64
            }

	asgVSXPerSystemThroughputIndex OBJECT-TYPE
		SYNTAX  Unsigned32
		MAX-ACCESS  not-accessible
		STATUS  current
		DESCRIPTION "Record index"
		::= { asgVSXPerSystemThroughputPerInterfaceTableEntry 1 }

	asgVSXPerSystemThroughputPerInterfaceName OBJECT-TYPE
			SYNTAX  DisplayString
			MAX-ACCESS  read-only
			STATUS  current
			DESCRIPTION
					"Interface name"
			::= { asgVSXPerSystemThroughputPerInterfaceTableEntry 2 }

	asgVSXPerSystemThroughputPerInterfaceValue OBJECT-TYPE
			SYNTAX  Counter64
			MAX-ACCESS  read-only
			STATUS  current
			DESCRIPTION
					"Throughput across all Members (KB/Second) over current interface"
			::= { asgVSXPerSystemThroughputPerInterfaceTableEntry 3 }

	-- VSX cross Connection Rate info
	asgVSXConnectionRateInfo OBJECT IDENTIFIER ::= { asgVSX 120 }

	asgVSXConnectionRateTable OBJECT-TYPE
			SYNTAX  SEQUENCE OF  AsgVSXConnectionRateEntry
			MAX-ACCESS  not-accessible
			STATUS  current
			DESCRIPTION "Connection rate table per VS per Member"
			::= { asgVSXConnectionRateInfo 10 }

	asgVSXConnectionRateEntry OBJECT-TYPE
                SYNTAX  AsgVSXConnectionRateEntry
                MAX-ACCESS  not-accessible
                STATUS  current
                DESCRIPTION "No description available"
				INDEX { asgVSXConnectionRateIndex }
                ::= { asgVSXConnectionRateTable 1 }

	AsgVSXConnectionRateEntry ::=
            SEQUENCE {
						asgVSXConnectionRateIndex
								Unsigned32,
                        asgVSXConnectionRateBladeid
                                DisplayString,
                        asgVSXConnectionRateValue
                                Counter64
            }

	asgVSXConnectionRateIndex OBJECT-TYPE
		SYNTAX  Unsigned32
		MAX-ACCESS  not-accessible
		STATUS  current
		DESCRIPTION "Record index"
		::= { asgVSXConnectionRateEntry 1 }

	asgVSXConnectionRateBladeid OBJECT-TYPE
			SYNTAX  DisplayString
			MAX-ACCESS  read-only
			STATUS  current
			DESCRIPTION
					"Member ID - defined as ChassisID_MemberID"
			::= { asgVSXConnectionRateEntry 2 }

	asgVSXConnectionRateValue OBJECT-TYPE
			SYNTAX  Counter64
			MAX-ACCESS  read-only
			STATUS  current
			DESCRIPTION
					"Connection Rate on this Member"
			::= { asgVSXConnectionRateEntry 3 }

	--Connection Rate per system:
 	asgVSXConnectionRatePerSystem OBJECT-TYPE
      		SYNTAX  Counter64
			MAX-ACCESS  read-only
			STATUS  current
			DESCRIPTION
				"VS's total connection rate (across all Members)"
			::= {asgVSXConnectionRateInfo 20 }

	-- VSX cross Virtual Memory info
	asgVSXVirtualMemoryInfo OBJECT IDENTIFIER ::= { asgVSX 130 }

	asgVSXVirtualMemoryTable OBJECT-TYPE
			SYNTAX  SEQUENCE OF  AsgVSXVirtualMemoryEntry
			MAX-ACCESS  not-accessible
			STATUS  current
			DESCRIPTION "Virtual Memory table per VS per Member"
			::= { asgVSXVirtualMemoryInfo 10 }

	asgVSXVirtualMemoryEntry OBJECT-TYPE
                SYNTAX  AsgVSXVirtualMemoryEntry
                MAX-ACCESS  not-accessible
                STATUS  current
                DESCRIPTION "No description available"
				INDEX { asgVSXVirtualMemoryIndex }
					::= { asgVSXVirtualMemoryTable 1 }

	AsgVSXVirtualMemoryEntry ::=
            SEQUENCE {
						asgVSXVirtualMemoryIndex
								Unsigned32,
                        asgVSXVirtualMemoryBladeid
                                DisplayString,
                        asgVSXVirtualMemoryValue
                                DisplayString
            }

	asgVSXVirtualMemoryIndex OBJECT-TYPE
		SYNTAX  Unsigned32
		MAX-ACCESS  not-accessible
		STATUS  current
		DESCRIPTION "Record index"
		::= { asgVSXVirtualMemoryEntry 1 }

	asgVSXVirtualMemoryBladeid OBJECT-TYPE
			SYNTAX  DisplayString
			MAX-ACCESS  read-only
			STATUS  current
			DESCRIPTION
					"Member ID - defined as ChassisID_MemberID"
			::= { asgVSXVirtualMemoryEntry 2 }

	asgVSXVirtualMemoryValue OBJECT-TYPE
			SYNTAX  DisplayString
			MAX-ACCESS  read-only
			STATUS  current
			DESCRIPTION
					"Virtual Memory usage percentage on this Member"
			::= { asgVSXVirtualMemoryEntry 3 }

	asgDiagnostic OBJECT IDENTIFIER ::= { asg 31 }

	-- Diagnostic Table

	asgDiagnosticTable OBJECT-TYPE
			SYNTAX  SEQUENCE OF  AsgDiagnosticEntry
			MAX-ACCESS  not-accessible
			STATUS  current
			DESCRIPTION "No description available"
			::= { asgDiagnostic 1 }

	asgDiagnosticEntry OBJECT-TYPE
			SYNTAX  AsgDiagnosticEntry
	        MAX-ACCESS  not-accessible
	        STATUS  current
	        DESCRIPTION "No description available"
	        INDEX   { asgDiagnosticIndex }
	        ::= { asgDiagnosticTable 1 }

    AsgDiagnosticEntry ::=
            SEQUENCE {
				asgDiagnosticIndex
                    Unsigned32,
                asgDiagnosticTestName
                    DisplayString,
                asgDiagnosticLastRun
                    DisplayString,
                asgDiagnosticResult
                    DisplayString,
                asgDiagnosticComment
                    DisplayString
	        }

    asgDiagnosticIndex OBJECT-TYPE
			SYNTAX  Unsigned32
            MAX-ACCESS  not-accessible
            STATUS  current
            DESCRIPTION "No description available"
            ::= { asgDiagnosticEntry 1 }

	asgDiagnosticTestName OBJECT-TYPE
            SYNTAX  DisplayString
            MAX-ACCESS  read-only
            STATUS  current
			DESCRIPTION
					"test name"
            ::= { asgDiagnosticEntry 2 }

	asgDiagnosticLastRun OBJECT-TYPE
            SYNTAX  DisplayString
            MAX-ACCESS  read-only
            STATUS  current
			DESCRIPTION
					"last run"
            ::= { asgDiagnosticEntry 3 }

	asgDiagnosticResult OBJECT-TYPE
            SYNTAX  DisplayString
            MAX-ACCESS  read-only
            STATUS  current
			DESCRIPTION
					"test result"
            ::= { asgDiagnosticEntry 4 }

	asgDiagnosticComment OBJECT-TYPE
            SYNTAX  DisplayString
            MAX-ACCESS  read-only
            STATUS  current
			DESCRIPTION
					"comment"
            ::= { asgDiagnosticEntry 5 }

	asgDiagSummary OBJECT-TYPE
            SYNTAX  DisplayString
            MAX-ACCESS  read-only
            STATUS  current
            DESCRIPTION
	  		        "summary"
            ::= { asgDiagnostic 2 }

  	--Threat-Emulation statuses:

	teSubscriptionStatus OBJECT-TYPE
      		SYNTAX  DisplayString
			MAX-ACCESS read-only
			STATUS  current
			DESCRIPTION
				"Subscription status
				 Possible values include:
	           	 up-to-date, expired, about-to-expire, not-associated, unknown"
			::= {te 25 }

	teCloudSubscriptionStatus OBJECT-TYPE
      		SYNTAX  DisplayString
			MAX-ACCESS read-only
			STATUS  current
			DESCRIPTION
				"Cloud subscription status
				 Possible values include:
	           	 up-to-date, expired, about-to-expire, not-associated, unknown"
			::= {te 26 }

	teSubscriptionExpDate OBJECT-TYPE
      		SYNTAX  DisplayString
			MAX-ACCESS read-only
			STATUS  current
			DESCRIPTION
				"Threat-Emulation subscription expiration date"
			::= {te 20 }

    teSubscriptionDesc OBJECT-TYPE
      		SYNTAX  DisplayString
			MAX-ACCESS read-only
			STATUS  current
			DESCRIPTION
				"Threat-Emulation Subscription description"
			::= {te 27 }

	teUpdateStatus OBJECT-TYPE
      		SYNTAX  DisplayString
			MAX-ACCESS read-only
			STATUS  current
			DESCRIPTION
				"Anti-Malware update status
				 Possible values include:
	           	 failed, up-to-date, new, degrade, downloading, unknown"
			::= {te 16 }

	teUpdateDesc OBJECT-TYPE
      		SYNTAX  DisplayString
			MAX-ACCESS read-only
			STATUS  current
			DESCRIPTION
				"Threat-Emulation update description"
			::= {te 17 }

	teStatusCode OBJECT-TYPE
      		SYNTAX  Integer32
			MAX-ACCESS read-only
			STATUS  current
			DESCRIPTION
				"Threat-Emulation Status code"
			::= {te 101 }

   teStatusShortDesc OBJECT-TYPE
     		SYNTAX  DisplayString
		MAX-ACCESS read-only
		STATUS  current
		DESCRIPTION
			"Threat-Emulation Status - Short Description"
		::= {te 102 }

   teStatusLongDesc OBJECT-TYPE
     		SYNTAX  DisplayString
		MAX-ACCESS read-only
		STATUS  current
		DESCRIPTION
			"Threat-Emulation Status  - Long Description"
		::= {te 103 }

	--threatExtraction statuses:

	threatExtractionSubscription OBJECT IDENTIFIER ::= { threatExtraction 1 }

	threatExtractionSubscriptionStatus OBJECT-TYPE
      		SYNTAX  DisplayString
		MAX-ACCESS  read-only
		STATUS  current
		DESCRIPTION
			"Threat Extraction subscription status
			Possible values include:
	           	 valid, expired, about-to-expire, not-associated, unknown"
		::= {threatExtractionSubscription 1 }

	threatExtractionSubscriptionExpDate OBJECT-TYPE
      		SYNTAX  DisplayString
		MAX-ACCESS  read-only
		STATUS  current
		DESCRIPTION
			"Threat Extraction subscription expiration date"
		::= {threatExtractionSubscription 2 }

    	threatExtractionSubscriptionDesc OBJECT-TYPE
      		SYNTAX  DisplayString
		MAX-ACCESS  read-only
		STATUS  current
		DESCRIPTION
			"Threat Extraction subscription description"
		::= {threatExtractionSubscription 3 }

	threatExtractionStatistics OBJECT IDENTIFIER ::= { threatExtraction 2 }

    	threatExtractionTotalScannedAttachments OBJECT-TYPE
      		SYNTAX  Integer32
		MAX-ACCESS  read-only
		STATUS  current
		DESCRIPTION
			"Total scanned attachments"
		::= {threatExtractionStatistics 1 }

    	threatExtractionCleanedAttachments OBJECT-TYPE
      		SYNTAX  Integer32
		MAX-ACCESS  read-only
		STATUS  current
		DESCRIPTION
			"Cleaned attachments"
		::= {threatExtractionStatistics 2 }

    	threatExtractionOriginalAttachmentsAccesses OBJECT-TYPE
      		SYNTAX  Integer32
		MAX-ACCESS  read-only
		STATUS  current
		DESCRIPTION
			"Original attachments accesses"
		::= {threatExtractionStatistics 3 }

	threatExtractionStatusCode OBJECT-TYPE
      		SYNTAX  Integer32
		MAX-ACCESS  read-only
		STATUS  current
		DESCRIPTION
			"Threat Extraction Status code"
		::= {threatExtraction 101 }

	threatExtractionStatusShortDesc OBJECT-TYPE
     		SYNTAX  DisplayString
		MAX-ACCESS  read-only
		STATUS  current
		DESCRIPTION
			"Threat Extraction Status - Short Description"
		::= {threatExtraction 102 }

   	threatExtractionStatusLongDesc OBJECT-TYPE
     		SYNTAX  DisplayString
		MAX-ACCESS  read-only
		STATUS  current
		DESCRIPTION
			"Threat Extraction Status - Long Description"
		::= {threatExtraction 103 }

   	threatExtractionEngineVersion OBJECT-TYPE
     		SYNTAX  DisplayString
		MAX-ACCESS  read-only
		STATUS  current
		DESCRIPTION
			"Threat Extraction Engine Version"
		::= {threatExtraction 104 }

END
