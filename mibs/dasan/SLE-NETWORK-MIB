--
-- sle-network-mib.mib
-- MIB generated by MG-SOFT Visual MIB Builder Version 6.0  Build 88
-- Monday, April 18, 2016 at 15:57:25
--

	SLE-NETWORK-MIB DEFINITIONS ::= BEGIN

		IMPORTS
			sleMgmt
				FROM DASAN-SMI
			IANAtunnelType
				FROM IANAifType-MIB
			InterfaceIndex
				FROM IF-MIB
			InetAddress, InetAddressType
				FROM INET-ADDRESS-MIB
			SleControlStatusType, SleControlRequestResultType
				FROM SLE-TC-MIB
			OBJECT-GROUP, NOTIFICATION-GROUP
				FROM SNMPv2-CONF
			TimeTicks, IpAddress, Integer32, Unsigned32, Gauge32,
			Counter64, BITS, OBJECT-TYPE, MODULE-IDENTITY, NOTIFICATION-TYPE
				FROM SNMPv2-SMI
			MacAddress
				FROM SNMPv2-TC;


		sleNetwork MODULE-IDENTITY
			LAST-UPDATED "200412291441Z"		-- December 29, 2004 at 14:41 GMT
			ORGANIZATION
				"HANASOFT"
			CONTACT-INFO
				" "
			DESCRIPTION
				"This MIB contains all needed informations about DHCP and
				all supported sle DHCP features."
			REVISION "200412101632Z"		-- December 10, 2004 at 16:32 GMT
			DESCRIPTION
				"Description"
			::= { sleMgmt 11 }




--
-- Node definitions
--

		sleNetInterface OBJECT IDENTIFIER ::= { sleNetwork 1 }


		sleNetIfTable OBJECT-TYPE
			SYNTAX SEQUENCE OF SleNetIfEntry
			MAX-ACCESS not-accessible
			STATUS current
			DESCRIPTION
				"Description."
			::= { sleNetInterface 1 }


		sleNetIfEntry OBJECT-TYPE
			SYNTAX SleNetIfEntry
			MAX-ACCESS not-accessible
			STATUS current
			DESCRIPTION
				"Description."
			INDEX { sleNetIfIndex }
			::= { sleNetIfTable 1 }


		SleNetIfEntry ::=
			SEQUENCE {
				sleNetIfIndex
					Integer32,
				sleNetIfName
					OCTET STRING,
				sleNetIfDescription
					OCTET STRING,
				sleNetIfTableIndex
					InterfaceIndex,
				sleNetIfRegState
					INTEGER,
				sleNetIfAdminState
					INTEGER,
				sleNetIfOperState
					INTEGER,
				sleNetIfMulticast
					INTEGER,
				sleNetIfMtu
					INTEGER,
				sleNetIfIpSetMode
					INTEGER,
				sleNetIfIpMartianFilter
					INTEGER,
				sleNetIfUpCnt
					Integer32,
				sleNetIfDownCnt
					Integer32,
				sleNetIfLinkUpTime
					Counter64,
				sleNetIfElapsedTimeAfterClearStats
					Counter64,
				sleNetIfBindingVRFName
					OCTET STRING,
				sleNetIfOnFailUseVRF
					INTEGER,
				sleNetIfIpUnreachability
					INTEGER,
				sleNetIfipRedirects
					INTEGER,
				sleNetIfIpForwarding
					INTEGER,
				sleNetIfAlias
					OCTET STRING,
				sleNetIfIpArpAlias
					INTEGER,
				sleNetIfIpArpAliasMac
					MacAddress,
				sleNetIfArpMCProbeCount
					Integer32,
				sleNetIfArpUCProbeCount
					Integer32,
				sleNetIfArpRetransTime
					Integer32,
				sleNetIfIpProxyArp
					INTEGER,
				sleNetIfIpRPFilter
					INTEGER,
				sleNetIfRPFilter
					INTEGER,
				sleNetIfRouteMap
					OCTET STRING
			 }

		sleNetIfIndex OBJECT-TYPE
			SYNTAX Integer32 (0..11023)
			MAX-ACCESS read-only
			STATUS current
			DESCRIPTION
				"Network interface index
				0           : any(all)
				1..4094     : VLAN
				4095        : management
				4096        : loopback
				4097        : NULL device
				10000..11023: Tunnel interface index
				"
			::= { sleNetIfEntry 1 }


		sleNetIfName OBJECT-TYPE
			SYNTAX OCTET STRING (SIZE (0..8))
			MAX-ACCESS read-only
			STATUS current
			DESCRIPTION
				"Device Name of this Interface."
			::= { sleNetIfEntry 2 }


		sleNetIfDescription OBJECT-TYPE
			SYNTAX OCTET STRING (SIZE (0..64))
			MAX-ACCESS read-only
			STATUS current
			DESCRIPTION
				"Description of this interface."
			::= { sleNetIfEntry 3 }


		sleNetIfTableIndex OBJECT-TYPE
			SYNTAX InterfaceIndex
			MAX-ACCESS read-only
			STATUS current
			DESCRIPTION
				"Same as ifIndex (for appropriated ifTable entries)."
			::= { sleNetIfEntry 4 }


		sleNetIfRegState OBJECT-TYPE
			SYNTAX INTEGER
				{
				unregistered(0),
				registered(1)
				}
			MAX-ACCESS read-only
			STATUS current
			DESCRIPTION
				"Registered state of Network device."
			::= { sleNetIfEntry 5 }


		sleNetIfAdminState OBJECT-TYPE
			SYNTAX INTEGER
				{
				down(0),
				up(1)
				}
			MAX-ACCESS read-only
			STATUS current
			DESCRIPTION
				"Administrative state.
				down - shutdown
				up - noshutdown"
			::= { sleNetIfEntry 6 }


		sleNetIfOperState OBJECT-TYPE
			SYNTAX INTEGER
				{
				down(0),
				up(1)
				}
			MAX-ACCESS read-only
			STATUS current
			DESCRIPTION
				"Operational state.
				down - shutdown or not running
				up - running"
			::= { sleNetIfEntry 7 }


		sleNetIfMulticast OBJECT-TYPE
			SYNTAX INTEGER
				{
				disable(0),
				enable(1)
				}
			MAX-ACCESS read-only
			STATUS current
			DESCRIPTION
				"Multicast enable/disable state."
			::= { sleNetIfEntry 8 }


		sleNetIfMtu OBJECT-TYPE
			SYNTAX INTEGER (64..17940)
			MAX-ACCESS read-only
			STATUS current
			DESCRIPTION
				"Maximum Transmission Unit."
			::= { sleNetIfEntry 9 }


		sleNetIfIpSetMode OBJECT-TYPE
			SYNTAX INTEGER
				{
				static(0),
				dynamic(1)
				}
			MAX-ACCESS read-only
			STATUS current
			DESCRIPTION
				"IP address setting mode.
				0 : static
				1 : dynamic (by DHCP client)
				"
			::= { sleNetIfEntry 10 }


		sleNetIfIpMartianFilter OBJECT-TYPE
			SYNTAX INTEGER
				{
				disable(0),
				enable(1)
				}
			MAX-ACCESS read-only
			STATUS current
			DESCRIPTION
				"Description."
			::= { sleNetIfEntry 11 }


		sleNetIfUpCnt OBJECT-TYPE
			SYNTAX Integer32
			MAX-ACCESS read-only
			STATUS current
			DESCRIPTION
				"The times of link-up event."
			::= { sleNetIfEntry 12 }


		sleNetIfDownCnt OBJECT-TYPE
			SYNTAX Integer32
			MAX-ACCESS read-only
			STATUS current
			DESCRIPTION
				"The times of link-down event."
			::= { sleNetIfEntry 13 }


		sleNetIfLinkUpTime OBJECT-TYPE
			SYNTAX Counter64
			UNITS "1 sec"
			MAX-ACCESS read-only
			STATUS current
			DESCRIPTION
				"The elapsed time after link is up."
			::= { sleNetIfEntry 14 }


		sleNetIfElapsedTimeAfterClearStats OBJECT-TYPE
			SYNTAX Counter64
			UNITS "1 sec"
			MAX-ACCESS read-only
			STATUS current
			DESCRIPTION
				"The elapsed time after clearing status."
			::= { sleNetIfEntry 15 }


		sleNetIfBindingVRFName OBJECT-TYPE
			SYNTAX OCTET STRING (SIZE (0..63))
			MAX-ACCESS read-only
			STATUS current
			DESCRIPTION
				"VRF name that this tunnel interface is binding."
			::= { sleNetIfEntry 16 }


		sleNetIfOnFailUseVRF OBJECT-TYPE
			SYNTAX INTEGER
				{
				enable(1),
				disable(2)
				}
			MAX-ACCESS read-only
			STATUS current
			DESCRIPTION
				"Lookup into a global routing table when the VRF routing table lookup was failed."
			::= { sleNetIfEntry 17 }


		sleNetIfIpUnreachability OBJECT-TYPE
			SYNTAX INTEGER
				{
				enable(1),
				disable(2)
				}
			MAX-ACCESS read-only
			STATUS current
			DESCRIPTION
				"IP unreachability ON/OFF
				"
			DEFVAL { 1 }
			::= { sleNetIfEntry 18 }


		sleNetIfipRedirects OBJECT-TYPE
			SYNTAX INTEGER
				{
				enable(1),
				disable(2)
				}
			MAX-ACCESS read-only
			STATUS current
			DESCRIPTION
				"Description."
			::= { sleNetIfEntry 19 }


		sleNetIfIpForwarding OBJECT-TYPE
			SYNTAX INTEGER
				{
				disable(0),
				enable(1)
				}
			MAX-ACCESS read-only
			STATUS current
			DESCRIPTION
				"The IP forwarding status"
			::= { sleNetIfEntry 20 }


		sleNetIfAlias OBJECT-TYPE
			SYNTAX OCTET STRING
			MAX-ACCESS read-only
			STATUS current
			DESCRIPTION
				"lias Name for the Interface"
			::= { sleNetIfEntry 21 }


		sleNetIfIpArpAlias OBJECT-TYPE
			SYNTAX INTEGER
				{
				disable(0),
				enable(1)
				}
			MAX-ACCESS read-only
			STATUS current
			DESCRIPTION
				"IP Arp Alias state"
			::= { sleNetIfEntry 22 }


		sleNetIfIpArpAliasMac OBJECT-TYPE
			SYNTAX MacAddress
			MAX-ACCESS read-only
			STATUS current
			DESCRIPTION
				"IP Arp Alias MAC"
			::= { sleNetIfEntry 23 }


		sleNetIfArpMCProbeCount OBJECT-TYPE
			SYNTAX Integer32 (2..10)
			MAX-ACCESS read-only
			STATUS current
			DESCRIPTION
				"ARP request Multicast probe count"
			::= { sleNetIfEntry 24 }


		sleNetIfArpUCProbeCount OBJECT-TYPE
			SYNTAX Integer32 (2..10)
			MAX-ACCESS read-only
			STATUS current
			DESCRIPTION
				"ARP request Unicast probe count"
			::= { sleNetIfEntry 25 }


		sleNetIfArpRetransTime OBJECT-TYPE
			SYNTAX Integer32 (1..300)
			MAX-ACCESS read-only
			STATUS current
			DESCRIPTION
				"Retrans time of ARP request (unit: 1s)"
			::= { sleNetIfEntry 26 }


		sleNetIfIpProxyArp OBJECT-TYPE
			SYNTAX INTEGER
				{
				disable(0),
				enable(1)
				}
			MAX-ACCESS read-only
			STATUS current
			DESCRIPTION
				"IP Proxy Arp state"
			::= { sleNetIfEntry 27 }


		sleNetIfIpRPFilter OBJECT-TYPE
			SYNTAX INTEGER
				{
				disable(0),
				loose(1),
				strict(2)
				}
			MAX-ACCESS read-only
			STATUS current
			DESCRIPTION
				"IP Reverse Path Filtering of CPU"
			::= { sleNetIfEntry 28 }


		sleNetIfRPFilter OBJECT-TYPE
			SYNTAX INTEGER
				{
				disable(0),
				loose(1),
				strict(2),
				looseAllow(3)
				}
			MAX-ACCESS read-only
			STATUS current
			DESCRIPTION
				"Reverse Path Filtering of CHIP (default : looseAllow)"
			::= { sleNetIfEntry 29 }


		sleNetIfRouteMap OBJECT-TYPE
			SYNTAX OCTET STRING
			MAX-ACCESS read-only
			STATUS current
			DESCRIPTION
				"IP Policy route-map name"
			::= { sleNetIfEntry 30 }


		sleNetIfControl OBJECT IDENTIFIER ::= { sleNetInterface 2 }


		sleNetIfControlRequest OBJECT-TYPE
			SYNTAX INTEGER
				{
				setNetIfRegState(1),
				setNetIfProfile(2),
				setNetIfIpMartianFilter(3),
				setNetIfBindingVRF(4),
				unsetNetIfBindingVRF(5),
				setNetIfOnFailUseVRF(6),
				setNetIfIpUnreachability(7),
				setNetIfIpRedirects(8),
				setNetIfIpForwarding(9),
				setAlias(10),
				setIpArpAlias(11),
				setArpMCProbeCount(12),
				setArpUCProbeCount(13),
				setArpRetransTime(14),
				setIpProxyArp(15),
				setIpRPFilter(16),
				setRPFilter(17),
				setRouteMap(18)
				}
			MAX-ACCESS read-write
			STATUS current
			DESCRIPTION
				"The request of a user command."
			DEFVAL { setNetIfProfile }
			::= { sleNetIfControl 1 }


		sleNetIfControlStatus OBJECT-TYPE
			SYNTAX SleControlStatusType
			MAX-ACCESS read-only
			STATUS current
			DESCRIPTION
				"The status of a user command."
			::= { sleNetIfControl 2 }


		sleNetIfControlTimer OBJECT-TYPE
			SYNTAX Gauge32
			MAX-ACCESS read-write
			STATUS current
			DESCRIPTION
				"The maximum wait time for the manager for a long running user command."
			DEFVAL { 0 }
			::= { sleNetIfControl 3 }


		sleNetIfControlTimeStamp OBJECT-TYPE
			SYNTAX SleControlRequestResultType
			MAX-ACCESS read-only
			STATUS current
			DESCRIPTION
				"The time stamp of the last command (end of command)."
			::= { sleNetIfControl 4 }


		sleNetIfControlReqResult OBJECT-TYPE
			SYNTAX TimeTicks
			MAX-ACCESS read-only
			STATUS current
			DESCRIPTION
				"The result of the last user command."
			::= { sleNetIfControl 5 }


		sleNetIfControlIndex OBJECT-TYPE
			SYNTAX Integer32 (0..11023)
			MAX-ACCESS read-write
			STATUS current
			DESCRIPTION
				"Network interface index
				0           : any(all)
				1..4094     : VLAN
				4095        : management
				4096        : loopback
				4097        : NULL device
				10000..11023: Tunnel interface index"
			::= { sleNetIfControl 6 }


		sleNetIfControlDescription OBJECT-TYPE
			SYNTAX OCTET STRING (SIZE (0..64))
			MAX-ACCESS read-write
			STATUS current
			DESCRIPTION
				"Description of this interface."
			DEFVAL { "" }
			::= { sleNetIfControl 7 }


		sleNetIfControlRegState OBJECT-TYPE
			SYNTAX INTEGER
				{
				unregister(0),
				register(1)
				}
			MAX-ACCESS read-write
			STATUS current
			DESCRIPTION
				"Description."
			::= { sleNetIfControl 8 }


		sleNetIfControlAdminState OBJECT-TYPE
			SYNTAX INTEGER
				{
				down(0),
				up(1)
				}
			MAX-ACCESS read-write
			STATUS current
			DESCRIPTION
				"Administrative state."
			DEFVAL { up }
			::= { sleNetIfControl 9 }


		sleNetIfControlMulticast OBJECT-TYPE
			SYNTAX INTEGER
				{
				disable(0),
				enable(1)
				}
			MAX-ACCESS read-write
			STATUS current
			DESCRIPTION
				"Multicast enable/disable state."
			DEFVAL { enable }
			::= { sleNetIfControl 10 }


		sleNetIfControlMtu OBJECT-TYPE
			SYNTAX INTEGER (64..17940)
			MAX-ACCESS read-write
			STATUS current
			DESCRIPTION
				"Maximum Transmission Unit."
			DEFVAL { 1500 }
			::= { sleNetIfControl 11 }


		sleNetIfControlIpMartianFilter OBJECT-TYPE
			SYNTAX INTEGER
				{
				disable(0),
				enable(1)
				}
			MAX-ACCESS read-write
			STATUS current
			DESCRIPTION
				"Description."
			::= { sleNetIfControl 12 }


		sleNetIfControlBindingVRFName OBJECT-TYPE
			SYNTAX OCTET STRING (SIZE (0..63))
			MAX-ACCESS read-write
			STATUS current
			DESCRIPTION
				"VRF name that this tunnel interface is binding."
			::= { sleNetIfControl 13 }


		sleNetIfControlOnFailUseVRF OBJECT-TYPE
			SYNTAX INTEGER
				{
				enable(1),
				disable(2)
				}
			MAX-ACCESS read-write
			STATUS current
			DESCRIPTION
				"Lookup into a global routing table when the VRF routing table lookup was failed."
			::= { sleNetIfControl 14 }


		sleNetIfControlIpUnreachability OBJECT-TYPE
			SYNTAX INTEGER
				{
				enable(1),
				disable(2)
				}
			MAX-ACCESS read-write
			STATUS current
			DESCRIPTION
				"IP unreachability ON/OFF"
			DEFVAL { 1 }
			::= { sleNetIfControl 15 }


		sleNetIfControlIpRedirects OBJECT-TYPE
			SYNTAX INTEGER
				{
				enable(1),
				disable(2)
				}
			MAX-ACCESS read-write
			STATUS current
			DESCRIPTION
				"Description."
			::= { sleNetIfControl 16 }


		sleNetIfControlIpForwarding OBJECT-TYPE
			SYNTAX INTEGER
				{
				disable(0),
				enable(1)
				}
			MAX-ACCESS read-write
			STATUS current
			DESCRIPTION
				"The IP forwarding status"
			::= { sleNetIfControl 17 }


		sleNetIfControlAlias OBJECT-TYPE
			SYNTAX OCTET STRING
			MAX-ACCESS read-write
			STATUS current
			DESCRIPTION
				"Alias Name for the Interface"
			::= { sleNetIfControl 18 }


		sleNetIfControlIpArpAlias OBJECT-TYPE
			SYNTAX INTEGER
				{
				disable(0),
				enable(1)
				}
			MAX-ACCESS read-write
			STATUS current
			DESCRIPTION
				"IP Arp Alias state"
			::= { sleNetIfControl 19 }


		sleNetIfControlIpArpAliasMac OBJECT-TYPE
			SYNTAX MacAddress
			MAX-ACCESS read-write
			STATUS current
			DESCRIPTION
				"IP Arp Alias MAC"
			::= { sleNetIfControl 20 }


		sleNetIfControlArpMCProbeCount OBJECT-TYPE
			SYNTAX Integer32 (2..10)
			MAX-ACCESS read-write
			STATUS current
			DESCRIPTION
				"ARP request Multicast probe count"
			::= { sleNetIfControl 21 }


		sleNetIfControlArpUCProbeCount OBJECT-TYPE
			SYNTAX Integer32 (2..10)
			MAX-ACCESS read-write
			STATUS current
			DESCRIPTION
				"ARP request Unicast probe count"
			::= { sleNetIfControl 22 }


		sleNetIfControlArpRetransTime OBJECT-TYPE
			SYNTAX Integer32 (1..300)
			MAX-ACCESS read-write
			STATUS current
			DESCRIPTION
				"Retrans time of ARP request (unit: 1s)"
			::= { sleNetIfControl 23 }


		sleNetIfControlIpProxyArp OBJECT-TYPE
			SYNTAX INTEGER
				{
				disable(0),
				enable(1)
				}
			MAX-ACCESS read-write
			STATUS current
			DESCRIPTION
				"IP Proxy Arp state"
			::= { sleNetIfControl 24 }


		sleNetIfControlIpRPFilter OBJECT-TYPE
			SYNTAX INTEGER
				{
				disable(0),
				loose(1),
				strict(2)
				}
			MAX-ACCESS read-write
			STATUS current
			DESCRIPTION
				"IP Reverse Path Filtering of CPU"
			::= { sleNetIfControl 25 }


		sleNetIfControlRPFilter OBJECT-TYPE
			SYNTAX INTEGER
				{
				disable(0),
				loose(1),
				strict(2),
				looseAllow(3)
				}
			MAX-ACCESS read-write
			STATUS current
			DESCRIPTION
				"Reverse Path Filtering of CHIP (default : looseAllow)"
			::= { sleNetIfControl 26 }


		sleNetIfControlRouteMap OBJECT-TYPE
			SYNTAX OCTET STRING
			MAX-ACCESS read-write
			STATUS current
			DESCRIPTION
				"IP Policy route-map name"
			::= { sleNetIfControl 27 }


		sleNetIfNotification OBJECT IDENTIFIER ::= { sleNetInterface 3 }


		sleNetIfRegStateChanged NOTIFICATION-TYPE
			OBJECTS { sleNetIfControlRequest, sleNetIfControlTimeStamp, sleNetIfControlReqResult, sleNetIfRegState }
			STATUS current
			DESCRIPTION
				"Description."
			::= { sleNetIfNotification 1 }


		sleNetIfProfileChanged NOTIFICATION-TYPE
			OBJECTS { sleNetIfControlRequest, sleNetIfControlTimeStamp, sleNetIfControlReqResult, sleNetIfDescription, sleNetIfAdminState,
				sleNetIfMulticast, sleNetIfMtu }
			STATUS current
			DESCRIPTION
				"setNetIfProfile."
			::= { sleNetIfNotification 2 }


		sleNetIfIpMartianFilterChanged NOTIFICATION-TYPE
			OBJECTS { sleNetIfControlRequest, sleNetIfControlIndex, sleNetIfControlTimeStamp, sleNetIfControlReqResult, sleNetIfControlIpMartianFilter
				 }
			STATUS current
			DESCRIPTION
				"Description."
			::= { sleNetIfNotification 3 }


		sleNetIfBindingVRFSet NOTIFICATION-TYPE
			OBJECTS { sleNetIfControlRequest, sleNetIfControlTimeStamp, sleNetIfControlReqResult, sleNetIfControlIndex, sleNetIfControlBindingVRFName
				 }
			STATUS current
			DESCRIPTION
				"Description."
			::= { sleNetIfNotification 4 }


		sleNetIfBindingVRFUnset NOTIFICATION-TYPE
			OBJECTS { sleNetIfControlRequest, sleNetIfControlTimeStamp, sleNetIfControlReqResult, sleNetIfControlIndex, sleNetIfControlBindingVRFName
				 }
			STATUS current
			DESCRIPTION
				"Description."
			::= { sleNetIfNotification 5 }


		sleNetIfIpOnFailUseVRFChanged NOTIFICATION-TYPE
			OBJECTS { sleNetIfControlRequest, sleNetIfControlTimeStamp, sleNetIfControlReqResult, sleNetIfControlIndex, sleNetIfControlOnFailUseVRF
				 }
			STATUS current
			DESCRIPTION
				"Description."
			::= { sleNetIfNotification 6 }


		sleNetIfIpUnreachabilityChanged NOTIFICATION-TYPE
			OBJECTS { sleNetIfControlRequest, sleNetIfControlTimeStamp, sleNetIfControlReqResult, sleNetIfControlIndex, sleNetIfControlIpUnreachability
				 }
			STATUS current
			DESCRIPTION
				"Description."
			::= { sleNetIfNotification 7 }


		sleNetIfIpRedirectsChanged NOTIFICATION-TYPE
			OBJECTS { sleNetIfControlRequest, sleNetIfControlTimeStamp, sleNetIfControlReqResult, sleNetIfControlIpRedirects }
			STATUS current
			DESCRIPTION
				"Description."
			::= { sleNetIfNotification 8 }


		sleNetIfIpForwardingChanged NOTIFICATION-TYPE
			OBJECTS { sleNetIfControlRequest, sleNetIfControlTimeStamp, sleNetIfControlReqResult, sleNetIfControlIndex, sleNetIfControlIpForwarding
				 }
			STATUS current
			DESCRIPTION
				"setNetIfIpForwarding"
			::= { sleNetIfNotification 9 }


		sleNetIfAliasChanged NOTIFICATION-TYPE
			OBJECTS { sleNetIfControlRequest, sleNetIfControlTimeStamp, sleNetIfControlReqResult, sleNetIfControlIndex, sleNetIfControlAlias
				 }
			STATUS current
			DESCRIPTION
				"setAlias"
			::= { sleNetIfNotification 10 }


		sleNetIfIpArpAliasChanged NOTIFICATION-TYPE
			OBJECTS { sleNetIfControlRequest, sleNetIfControlTimeStamp, sleNetIfControlReqResult, sleNetIfControlIndex, sleNetIfControlIpArpAlias,
				sleNetIfControlIpArpAliasMac }
			STATUS current
			DESCRIPTION
				"setIpArpAlias"
			::= { sleNetIfNotification 11 }


		sleNetIfArpMCProbeCountChanged NOTIFICATION-TYPE
			OBJECTS { sleNetIfControlRequest, sleNetIfControlTimeStamp, sleNetIfControlReqResult, sleNetIfControlIndex, sleNetIfControlArpMCProbeCount
				 }
			STATUS current
			DESCRIPTION
				"setArpMCProbeCount"
			::= { sleNetIfNotification 12 }


		sleNetIfArpUCProbeCountChanged NOTIFICATION-TYPE
			OBJECTS { sleNetIfControlRequest, sleNetIfControlTimeStamp, sleNetIfControlReqResult, sleNetIfControlIndex, sleNetIfControlArpUCProbeCount
				 }
			STATUS current
			DESCRIPTION
				"setArpUCProbeCount"
			::= { sleNetIfNotification 13 }


		sleNetIfArpRetransTimeChanged NOTIFICATION-TYPE
			OBJECTS { sleNetIfControlRequest, sleNetIfControlTimeStamp, sleNetIfControlReqResult, sleNetIfControlIndex, sleNetIfControlArpRetransTime
				 }
			STATUS current
			DESCRIPTION
				"setArpRetransTime"
			::= { sleNetIfNotification 14 }


		sleNetIfIpProxyArpChanged NOTIFICATION-TYPE
			OBJECTS { sleNetIfControlRequest, sleNetIfControlTimeStamp, sleNetIfControlReqResult, sleNetIfControlIndex, sleNetIfControlIpProxyArp
				 }
			STATUS current
			DESCRIPTION
				"setIpProxyArp"
			::= { sleNetIfNotification 15 }


		sleNetIfIpRPFilterChanged NOTIFICATION-TYPE
			OBJECTS { sleNetIfControlRequest, sleNetIfControlTimeStamp, sleNetIfControlReqResult, sleNetIfControlIndex, sleNetIfControlIpRPFilter
				 }
			STATUS current
			DESCRIPTION
				"setIpRPFilter"
			::= { sleNetIfNotification 16 }


		sleNetIfRPFilterChanged NOTIFICATION-TYPE
			OBJECTS { sleNetIfControlRequest, sleNetIfControlTimeStamp, sleNetIfControlReqResult, sleNetIfControlIndex, sleNetIfControlRPFilter
				 }
			STATUS current
			DESCRIPTION
				"setRPFilter"
			::= { sleNetIfNotification 17 }


		sleNetIfRouteMapChanged NOTIFICATION-TYPE
			OBJECTS { sleNetIfControlRequest, sleNetIfControlTimeStamp, sleNetIfControlReqResult, sleNetIfControlIndex, sleNetIfControlRouteMap
				 }
			STATUS current
			DESCRIPTION
				"setRouteMap"
			::= { sleNetIfNotification 18 }


		sleIpAddress OBJECT IDENTIFIER ::= { sleNetwork 2 }


		sleIpAddrTable OBJECT-TYPE
			SYNTAX SEQUENCE OF SleIpAddrEntry
			MAX-ACCESS not-accessible
			STATUS current
			DESCRIPTION
				"Description."
			::= { sleIpAddress 1 }


		sleIpAddrEntry OBJECT-TYPE
			SYNTAX SleIpAddrEntry
			MAX-ACCESS not-accessible
			STATUS current
			DESCRIPTION
				"Description."
			INDEX { sleNetIfIndex, sleIpAddrValue }
			::= { sleIpAddrTable 1 }


		SleIpAddrEntry ::=
			SEQUENCE {
				sleIpAddrValue
					IpAddress,
				sleIpAddrMask
					Integer32,
				sleIpAddrBcast
					IpAddress,
				sleIpAddrFlag
					BITS,
				sleIpAddrScope
					INTEGER,
				sleIpAddrIpIndex
					INTEGER,
				sleIpAddrUnnumUsedIp
					INTEGER
			 }

		sleIpAddrValue OBJECT-TYPE
			SYNTAX IpAddress
			MAX-ACCESS read-only
			STATUS current
			DESCRIPTION
				"The IP address to which this entry's addressing information pertains."
			::= { sleIpAddrEntry 1 }


		sleIpAddrMask OBJECT-TYPE
			SYNTAX Integer32 (1..32)
			MAX-ACCESS read-only
			STATUS current
			DESCRIPTION
				"The subnet mask associated with the IP address of this entry.
				The value of the mask is an IP address with all the network
				bits set to 1 and all the hosts bits set to 0."
			::= { sleIpAddrEntry 2 }


		sleIpAddrBcast OBJECT-TYPE
			SYNTAX IpAddress
			MAX-ACCESS read-only
			STATUS current
			DESCRIPTION
				"The value of the least-significant bit in the IP broadcast
				address used for sending datagrams on the (logical)
				interface associated with the IP address of this entry.
				For example, when the Internet standard all-ones broadcast
				address is used, the value will be 1.  This value applies
				to both the subnet and network broadcasts addresses used
				by the entity on this (logical) interface."
			::= { sleIpAddrEntry 3 }


		sleIpAddrFlag OBJECT-TYPE
			SYNTAX BITS
				{
				permanent(0),
				tentative(1),
				deprecated(2),
				reserved3(3),
				reserved4(4),
				reserved5(5),
				reserved6(6),
				secondary(7)
				}
			MAX-ACCESS read-only
			STATUS current
			DESCRIPTION
				"Description."
			::= { sleIpAddrEntry 4 }


		sleIpAddrScope OBJECT-TYPE
			SYNTAX INTEGER
				{
				global(0),
				site(200),
				link(253),
				host(254),
				nowhere(255)
				}
			MAX-ACCESS read-only
			STATUS current
			DESCRIPTION
				"Description."
			::= { sleIpAddrEntry 5 }


		sleIpAddrIpIndex OBJECT-TYPE
			SYNTAX INTEGER (0..1024)
			MAX-ACCESS read-only
			STATUS current
			DESCRIPTION
				"The Ip index for Interface Unnumbered feature enhanced.
				If Interface Unnumbered enhanced feature is enabled on a point-to-point interface. It will get a ip address of a specific interface.
				Interface unnumbered default setting - it get primary ip address.
				Interface unnumbered enhanced setting - it get secondary ip address with ip-index.
				(cf. primary ip address's ip-index : 1. no setting: 0. other setting: 2-1024)"
			::= { sleIpAddrEntry 6 }


		sleIpAddrUnnumUsedIp OBJECT-TYPE
			SYNTAX INTEGER
				{
				none(0),
				used(1)
				}
			MAX-ACCESS read-only
			STATUS current
			DESCRIPTION
				"The Check a specific IP address for using interface unnumbered feature."
			::= { sleIpAddrEntry 7 }


		sleIpAddrControl OBJECT IDENTIFIER ::= { sleIpAddress 2 }


		sleIpAddrControlRequest OBJECT-TYPE
			SYNTAX INTEGER
				{
				createIpAddress(1),
				destroyIpAddress(2),
				addIpIndex(3),
				delIpIndex(4)
				}
			MAX-ACCESS read-write
			STATUS current
			DESCRIPTION
				"The request of a user command."
			::= { sleIpAddrControl 1 }


		sleIpAddrControlStatus OBJECT-TYPE
			SYNTAX SleControlStatusType
			MAX-ACCESS read-only
			STATUS current
			DESCRIPTION
				"The status of a user command."
			::= { sleIpAddrControl 2 }


		sleIpAddrControlTimer OBJECT-TYPE
			SYNTAX Gauge32
			MAX-ACCESS read-write
			STATUS current
			DESCRIPTION
				"The maximum wait time for the manager for a long running user command."
			DEFVAL { 0 }
			::= { sleIpAddrControl 3 }


		sleIpAddrControlTimeStamp OBJECT-TYPE
			SYNTAX SleControlRequestResultType
			MAX-ACCESS read-only
			STATUS current
			DESCRIPTION
				"The time stamp of the last command (end of command)."
			::= { sleIpAddrControl 4 }


		sleIpAddrControlReqResult OBJECT-TYPE
			SYNTAX TimeTicks
			MAX-ACCESS read-only
			STATUS current
			DESCRIPTION
				"The result of the last user command."
			::= { sleIpAddrControl 5 }


		sleIpAddrControlNetIfIndex OBJECT-TYPE
			SYNTAX Integer32 (1..4094 | 10000..11023)
			MAX-ACCESS read-write
			STATUS current
			DESCRIPTION
				"Network interface index
				1..4094     : VLAN
				10000..11023: Tunnel interface index
				"
			DEFVAL { 1 }
			::= { sleIpAddrControl 6 }


		sleIpAddrControlValue OBJECT-TYPE
			SYNTAX IpAddress
			MAX-ACCESS read-write
			STATUS current
			DESCRIPTION
				"The IP address to which this entry's addressing information pertains."
			DEFVAL { 'ac106464'h }
			::= { sleIpAddrControl 7 }


		sleIpAddrControlMask OBJECT-TYPE
			SYNTAX Integer32 (1..32)
			MAX-ACCESS read-write
			STATUS current
			DESCRIPTION
				"The subnet mask associated with the IP address of this entry.  "
			DEFVAL { 24 }
			::= { sleIpAddrControl 8 }


		sleIpAddrControlFlag OBJECT-TYPE
			SYNTAX INTEGER
				{
				primary(0),
				secondary(1)
				}
			MAX-ACCESS read-write
			STATUS current
			DESCRIPTION
				"Description."
			DEFVAL { primary }
			::= { sleIpAddrControl 9 }


		sleIpAddrControlScope OBJECT-TYPE
			SYNTAX INTEGER
				{
				global(0),
				link(253),
				host(254)
				}
			MAX-ACCESS read-write
			STATUS current
			DESCRIPTION
				"Description."
			DEFVAL { global }
			::= { sleIpAddrControl 10 }


		sleIpAddrControlIpIndex OBJECT-TYPE
			SYNTAX INTEGER (1..1024)
			MAX-ACCESS read-write
			STATUS current
			DESCRIPTION
				"The Ip index for Interface Unnumbered feature enhanced.
				If Interface Unnumbered enhanced feature is enabled on a point-to-point interface. It will get a ip address of a specific interface.
				Interface unnumbered default setting - it get primary ip address.
				Interface unnumbered enhanced setting - it get secondary ip address with ip-index.
				(cf. primary ip address's ip-index : 1. no setting: 0. other setting: 2-1024)"
			::= { sleIpAddrControl 11 }


		sleIpAddrNotification OBJECT IDENTIFIER ::= { sleIpAddress 3 }


		sleIpAddressCreated NOTIFICATION-TYPE
			OBJECTS { sleIpAddrControlRequest, sleIpAddrControlTimeStamp, sleIpAddrControlReqResult, sleIpAddrMask, sleIpAddrFlag,
				sleIpAddrScope }
			STATUS current
			DESCRIPTION
				"createIpAddress."
			::= { sleIpAddrNotification 1 }


		sleIpAddressDestroyed NOTIFICATION-TYPE
			OBJECTS { sleIpAddrControlRequest, sleIpAddrControlTimeStamp, sleIpAddrControlReqResult, sleIpAddrMask }
			STATUS current
			DESCRIPTION
				"destroyIpAddress."
			::= { sleIpAddrNotification 2 }


		sleIpAddressIpIndexAdded NOTIFICATION-TYPE
			OBJECTS { sleIpAddrControlRequest, sleIpAddrControlTimeStamp, sleIpAddrControlReqResult, sleIpAddrControlNetIfIndex, sleIpAddrControlValue,
				sleIpAddrControlMask, sleIpAddrControlIpIndex }
			STATUS current
			DESCRIPTION
				"addIpIndex"
			::= { sleIpAddrNotification 3 }


		sleIpAddressIpIndexDeleted NOTIFICATION-TYPE
			OBJECTS { sleIpAddrControlRequest, sleIpAddrControlTimeStamp, sleIpAddrControlReqResult, sleIpAddrControlNetIfIndex, sleIpAddrControlIpIndex
				 }
			STATUS current
			DESCRIPTION
				"delIpIndex"
			::= { sleIpAddrNotification 4 }


		sleArp OBJECT IDENTIFIER ::= { sleNetwork 3 }


		sleArpTable OBJECT-TYPE
			SYNTAX SEQUENCE OF SleArpEntry
			MAX-ACCESS not-accessible
			STATUS current
			DESCRIPTION
				"Description."
			::= { sleArp 1 }


		sleArpEntry OBJECT-TYPE
			SYNTAX SleArpEntry
			MAX-ACCESS not-accessible
			STATUS current
			DESCRIPTION
				"Description."
			INDEX { sleNetIfIndex, sleArpIpAddress }
			::= { sleArpTable 1 }


		SleArpEntry ::=
			SEQUENCE {
				sleArpIpAddress
					IpAddress,
				sleArpPhyAddress
					MacAddress,
				sleArpPortIndex
					Integer32,
				sleArpState
					INTEGER,
				sleArpHwType
					INTEGER,
				sleArpHwUsed
					INTEGER,
				sleArpUsedTime
					INTEGER
			 }

		sleArpIpAddress OBJECT-TYPE
			SYNTAX IpAddress
			MAX-ACCESS read-only
			STATUS current
			DESCRIPTION
				"The NetworkAddress (e.g., the IP address) corresponding
				to the media-dependent `physical' address."
			::= { sleArpEntry 1 }


		sleArpPhyAddress OBJECT-TYPE
			SYNTAX MacAddress
			MAX-ACCESS read-only
			STATUS current
			DESCRIPTION
				"The media-dependent `physical' address."
			::= { sleArpEntry 2 }


		sleArpPortIndex OBJECT-TYPE
			SYNTAX Integer32 (0..255)
			MAX-ACCESS read-only
			STATUS current
			DESCRIPTION
				"The interface on which this entry's equivalence is effective.
				0: for any ports."
			::= { sleArpEntry 3 }


		sleArpState OBJECT-TYPE
			SYNTAX INTEGER
				{
				static(0),
				dynamic(1)
				}
			MAX-ACCESS read-only
			STATUS current
			DESCRIPTION
				"Arp entry's currently status."
			::= { sleArpEntry 4 }


		sleArpHwType OBJECT-TYPE
			SYNTAX INTEGER { ethernet(1) }
			MAX-ACCESS read-only
			STATUS current
			DESCRIPTION
				"Hardware Type of media."
			::= { sleArpEntry 5 }


		sleArpHwUsed OBJECT-TYPE
			SYNTAX INTEGER
				{
				nonused(0),
				used(1)
				}
			MAX-ACCESS read-only
			STATUS current
			DESCRIPTION
				"Arp entry's currently chip usage state."
			::= { sleArpEntry 6 }


		sleArpUsedTime OBJECT-TYPE
			SYNTAX INTEGER (1..10000000)
			MAX-ACCESS read-only
			STATUS current
			DESCRIPTION
				"Arp entry's chip used time.(if sleArpState is 0, always 0 and if sleArpHwUsed is 0, always 0.)"
			::= { sleArpEntry 7 }


		sleArpControl OBJECT IDENTIFIER ::= { sleArp 2 }


		sleArpControlRequest OBJECT-TYPE
			SYNTAX INTEGER
				{
				createArpEntry(1),
				destroyArpEntry(2),
				clearArpTable(3),
				clearArpTableByAddr(4)
				}
			MAX-ACCESS read-write
			STATUS current
			DESCRIPTION
				"The request of a user command."
			::= { sleArpControl 1 }


		sleArpControlStatus OBJECT-TYPE
			SYNTAX SleControlStatusType
			MAX-ACCESS read-only
			STATUS current
			DESCRIPTION
				"The status of a user command."
			::= { sleArpControl 2 }


		sleArpControlTimer OBJECT-TYPE
			SYNTAX Gauge32
			MAX-ACCESS read-write
			STATUS current
			DESCRIPTION
				"The maximum wait time for the manager for a long running user command."
			::= { sleArpControl 3 }


		sleArpControlTimeStamp OBJECT-TYPE
			SYNTAX SleControlRequestResultType
			MAX-ACCESS read-only
			STATUS current
			DESCRIPTION
				"The time stamp of the last command (end of command)."
			::= { sleArpControl 4 }


		sleArpControlReqResult OBJECT-TYPE
			SYNTAX TimeTicks
			MAX-ACCESS read-only
			STATUS current
			DESCRIPTION
				"The result of the last user command."
			::= { sleArpControl 5 }


		sleArpControlNetIfIndex OBJECT-TYPE
			SYNTAX Integer32 (0..4096)
			MAX-ACCESS read-write
			STATUS current
			DESCRIPTION
				"Network interface index."
			::= { sleArpControl 6 }


		sleArpControlIpAddress OBJECT-TYPE
			SYNTAX IpAddress
			MAX-ACCESS read-write
			STATUS current
			DESCRIPTION
				"The NetworkAddress (e.g., the IP address) corresponding
				to the media-dependent `physical' address."
			::= { sleArpControl 7 }


		sleArpControlPhyAddress OBJECT-TYPE
			SYNTAX MacAddress
			MAX-ACCESS read-write
			STATUS current
			DESCRIPTION
				"The media-dependent `physical' address."
			::= { sleArpControl 8 }


		sleArpControlState OBJECT-TYPE
			SYNTAX INTEGER
				{
				static(0),
				dynamic(1)
				}
			MAX-ACCESS read-write
			STATUS current
			DESCRIPTION
				"Arp entry's currently status."
			::= { sleArpControl 9 }


		sleArpControlMask OBJECT-TYPE
			SYNTAX INTEGER (0..32)
			MAX-ACCESS read-write
			STATUS current
			DESCRIPTION
				"Description."
			::= { sleArpControl 10 }


		sleArpNotification OBJECT IDENTIFIER ::= { sleArp 3 }


		sleArpEntryCreated NOTIFICATION-TYPE
			OBJECTS { sleArpControlRequest, sleArpControlTimeStamp, sleArpControlReqResult, sleArpPhyAddress }
			STATUS current
			DESCRIPTION
				"createArpEntry."
			::= { sleArpNotification 1 }


		sleArpEntryDestroyed NOTIFICATION-TYPE
			OBJECTS { sleArpControlRequest, sleArpControlTimeStamp, sleArpControlReqResult, sleArpPhyAddress }
			STATUS current
			DESCRIPTION
				"destroyArpEntry."
			::= { sleArpNotification 2 }


		sleArpTableCleared NOTIFICATION-TYPE
			OBJECTS { sleArpControlRequest, sleArpControlTimeStamp, sleArpControlReqResult, sleArpState }
			STATUS current
			DESCRIPTION
				"clearArpTable.
				In this notification PDU, key of sleArpState
				is ifindex.0.0.0.0."
			::= { sleArpNotification 3 }


		sleArpTableClearedByAddr NOTIFICATION-TYPE
			OBJECTS { sleArpControlRequest, sleArpControlTimeStamp, sleArpControlReqResult, sleArpControlIpAddress, sleArpControlMask,
				sleArpControlState }
			STATUS current
			DESCRIPTION
				"clearArpTableByAddr"
			::= { sleArpNotification 4 }


		sleRoute OBJECT IDENTIFIER ::= { sleNetwork 4 }


		sleRouteTable OBJECT-TYPE
			SYNTAX SEQUENCE OF SleRouteEntry
			MAX-ACCESS not-accessible
			STATUS current
			DESCRIPTION
				"Description."
			::= { sleRoute 1 }


		sleRouteEntry OBJECT-TYPE
			SYNTAX SleRouteEntry
			MAX-ACCESS not-accessible
			STATUS current
			DESCRIPTION
				"Description."
			INDEX { sleRouteDstAddress, sleRouteDstMask, sleRouteGateway, sleRouteInterface, sleRouteVRFIndex
				 }
			::= { sleRouteTable 1 }


		SleRouteEntry ::=
			SEQUENCE {
				sleRouteDstAddress
					IpAddress,
				sleRouteDstMask
					INTEGER,
				sleRouteGateway
					IpAddress,
				sleRouteInterface
					INTEGER,
				sleRouteType
					INTEGER,
				sleRouteProto
					INTEGER,
				sleRouteMetric
					INTEGER,
				sleRouteActive
					INTEGER,
				sleRouteBindingSrcAddr
					IpAddress,
				sleRouteDistance
					INTEGER,
				sleRouteSubtype
					INTEGER,
				sleRouteNexthopStatus
					BITS,
				sleRouteRibStatus
					BITS,
				sleRouteVRFIndex
					Integer32
			 }

		sleRouteDstAddress OBJECT-TYPE
			SYNTAX IpAddress
			MAX-ACCESS read-only
			STATUS current
			DESCRIPTION
				"The destination IP address of this route.
				An entry with a value of 0.0.0.0 is considered a default route.
				Multiple routes to a single destination can appear in the table,
				but access to such multiple entries is dependent on the table-access mechanisms defined by the network management protocol in use."
			::= { sleRouteEntry 1 }


		sleRouteDstMask OBJECT-TYPE
			SYNTAX INTEGER (0..32)
			MAX-ACCESS read-only
			STATUS current
			DESCRIPTION
				"Indicate the mask to be logical-ANDed with the destination address
				before being compared to the value in the sleRouteDstAddress field.
				For those systems that do not support arbitrary subnet masks,
				an agent constructs the value of the sleRouteDstMask
				by determining whether the value of the correspondent sleRouteDstAddress field
				belong to a class-A, B, or C network.
				If the value of the sleRouteDstAddress is 0.0.0.0 (a default route),
				then the mask value is also 0.0.0.0. It should be noted that all IP routing subsystems implicitly use this mechanism."
			::= { sleRouteEntry 2 }


		sleRouteGateway OBJECT-TYPE
			SYNTAX IpAddress
			MAX-ACCESS read-only
			STATUS current
			DESCRIPTION
				"The Gateway IP Address.
				0.0.0.0/0 : indicate default gateway or invalid"
			::= { sleRouteEntry 3 }


		sleRouteInterface OBJECT-TYPE
			SYNTAX INTEGER (0..11023)
			MAX-ACCESS read-only
			STATUS current
			DESCRIPTION
				"The index value which uniquely identifies
				the local interface through
				which the next hop of this route
				should be reached.
				The interface identified by a particular
				value of this index is the same interface
				as identified by the same value of
				sleNetIfIndex.

				Network interface index
				0: invalid
				1..4094: VLAN
				4095: management
				4096: loopback
				4097: NULL device
				10000..11023: Tunnel interface index"
			::= { sleRouteEntry 4 }


		sleRouteType OBJECT-TYPE
			SYNTAX INTEGER
				{
				other(1),
				invalid(2),
				direct(3),
				indirect(4)
				}
			MAX-ACCESS read-write
			STATUS current
			DESCRIPTION
				"The type of route.
				Note that the values direct and indirect refer to the notion of direct
				and indirect routing in the IP architecture.
				Setting this object to the value invalid has the effect of invalidating the corresponding entry
				in the sleRouteTable object.
				That is, it effectively dissasociates the destination identified
				with said entry from the route identified with said entry.
				It is an implementation-specific matter as to whether the agent removes an invalidated entry
				from the table. Accordingly,
				management stations must be prepared to receive tabular information
				from agents that corresponds to entries not currently in use.
				Proper interpretation of such entries requires examination of the relevant sleRouteType object."
			::= { sleRouteEntry 5 }


		sleRouteProto OBJECT-TYPE
			SYNTAX INTEGER
				{
				other(1),
				localDirect(2),
				netmgmtStatic(3),
				icmp(4),
				egp(5),
				ggp(6),
				hello(7),
				rip(8),
				isIs(9),
				esIs(10),
				ciscoIgrp(11),
				bbnSpfIgp(12),
				ospf(13),
				bgp(14),
				idpr(15),
				ciscoEigrp(16),
				dhcp(17)
				}
			MAX-ACCESS read-only
			STATUS current
			DESCRIPTION
				"The routing mechanism via which this route was learned.
				Inclusion of values for gateway routing protocols is not intended to imply
				that hosts should support those protocols."
			::= { sleRouteEntry 6 }


		sleRouteMetric OBJECT-TYPE
			SYNTAX INTEGER (-1..255)
			MAX-ACCESS read-write
			STATUS current
			DESCRIPTION
				"The primary routing metric for this route.
				The semantics of this metric are determined
				by the routing-protocol specified
				in the route's sleRouteProto value.
				If this metric is not used,
				its value should be set to -1."
			::= { sleRouteEntry 7 }


		sleRouteActive OBJECT-TYPE
			SYNTAX INTEGER
				{
				inactive(0),
				active(1)
				}
			MAX-ACCESS read-write
			STATUS current
			DESCRIPTION
				"The active status for this routing entry."
			::= { sleRouteEntry 8 }


		sleRouteBindingSrcAddr OBJECT-TYPE
			SYNTAX IpAddress
			MAX-ACCESS read-only
			STATUS current
			DESCRIPTION
				"The binding source IP Address for this route."
			::= { sleRouteEntry 9 }


		sleRouteDistance OBJECT-TYPE
			SYNTAX INTEGER (1..255)
			MAX-ACCESS read-write
			STATUS current
			DESCRIPTION
				"The Distance value for this route."
			::= { sleRouteEntry 10 }


		sleRouteSubtype OBJECT-TYPE
			SYNTAX INTEGER
				{
				unknown(0),
				ospfIa(1),
				ospfNssa1(2),
				ospfNssa2(3),
				ospfExternal1(4),
				ospfExternal2(5),
				isisL1(8),
				isisL2(9),
				isisIa(10),
				bgpMpls(11)
				}
			MAX-ACCESS read-only
			STATUS current
			DESCRIPTION
				"The subtype of this route."
			::= { sleRouteEntry 11 }


		sleRouteNexthopStatus OBJECT-TYPE
			SYNTAX BITS
				{
				active(0),
				fib(1),
				recursive(2)
				}
			MAX-ACCESS read-only
			STATUS current
			DESCRIPTION
				"The nexthop status of this route."
			::= { sleRouteEntry 12 }


		sleRouteRibStatus OBJECT-TYPE
			SYNTAX BITS
				{
				internal(0),
				selfroute(1),
				blackhole(2),
				nonfib(3),
				selected(4),
				changed(5),
				static(6),
				stale(7)
				}
			MAX-ACCESS read-only
			STATUS current
			DESCRIPTION
				"The rib status for this route."
			::= { sleRouteEntry 13 }


		sleRouteVRFIndex OBJECT-TYPE
			SYNTAX Integer32 (0..2147483647)
			MAX-ACCESS read-only
			STATUS current
			DESCRIPTION
				"VRF index in sleIpVRFTable."
			::= { sleRouteEntry 14 }


		sleRouteControl OBJECT IDENTIFIER ::= { sleRoute 2 }


		sleRouteControlRequest OBJECT-TYPE
			SYNTAX INTEGER
				{
				createStaticRoute(1),
				destroyStaticRoute(2),
				setStaticRouteProfile(3)
				}
			MAX-ACCESS read-write
			STATUS current
			DESCRIPTION
				"The request of a user command."
			::= { sleRouteControl 1 }


		sleRouteControlStatus OBJECT-TYPE
			SYNTAX SleControlStatusType
			MAX-ACCESS read-only
			STATUS current
			DESCRIPTION
				"The status of a user command."
			::= { sleRouteControl 2 }


		sleRouteControlTimer OBJECT-TYPE
			SYNTAX Gauge32
			MAX-ACCESS read-write
			STATUS current
			DESCRIPTION
				"The maximum wait time for the manager for a long running user command."
			::= { sleRouteControl 3 }


		sleRouteControlTimeStamp OBJECT-TYPE
			SYNTAX SleControlRequestResultType
			MAX-ACCESS read-only
			STATUS current
			DESCRIPTION
				"The result of the last user command."
			::= { sleRouteControl 4 }


		sleRouteControlReqResult OBJECT-TYPE
			SYNTAX TimeTicks
			MAX-ACCESS read-only
			STATUS current
			DESCRIPTION
				"The time stamp of the last command (end of command)."
			::= { sleRouteControl 5 }


		sleRouteControlDstAddress OBJECT-TYPE
			SYNTAX IpAddress
			MAX-ACCESS read-write
			STATUS current
			DESCRIPTION
				"The destination IP address of this route.
				An entry with a value of 0.0.0.0 is considered a default route.
				Multiple routes to a single destination can appear in the table,
				but access to such multiple entries is dependent on the table-access mechanisms defined by the network management protocol in use."
			::= { sleRouteControl 6 }


		sleRouteControlDstMask OBJECT-TYPE
			SYNTAX INTEGER (0..32)
			MAX-ACCESS read-write
			STATUS current
			DESCRIPTION
				"Indicate the mask to be logical-ANDed with the destination address
				before being compared to the value in the sleRouteDstAddress field.
				For those systems that do not support arbitrary subnet masks,
				an agent constructs the value of the sleRouteDstMask
				by determining whether the value of the correspondent sleRouteDstAddress field
				belong to a class-A, B, or C network.
				If the value of the sleRouteDstAddress is 0.0.0.0 (a default route),
				then the mask value is also 0.0.0.0. It should be noted that all IP routing subsystems implicitly use this mechanism."
			::= { sleRouteControl 7 }


		sleRouteControlGateway OBJECT-TYPE
			SYNTAX IpAddress
			MAX-ACCESS read-write
			STATUS current
			DESCRIPTION
				"The Gateway IP Address.
				0.0.0.0/0 : indicate default gateway or invalid"
			::= { sleRouteControl 8 }


		sleRouteControlInterface OBJECT-TYPE
			SYNTAX INTEGER (0..11023)
			MAX-ACCESS read-write
			STATUS current
			DESCRIPTION
				"Network interface index
				0: invalid
				1..4094: VLAN
				4095: management
				4096: loopback
				4097: NULL device
				10000..11023: Tunnel interface index
				To config interface, sleRouteControlGateway have to be removed."
			::= { sleRouteControl 9 }


		sleRouteControlBindingSrcAddr OBJECT-TYPE
			SYNTAX IpAddress
			MAX-ACCESS read-write
			STATUS current
			DESCRIPTION
				"The binding source IP Address for this route."
			::= { sleRouteControl 10 }


		sleRouteControlDistance OBJECT-TYPE
			SYNTAX INTEGER (1..255)
			MAX-ACCESS read-write
			STATUS current
			DESCRIPTION
				"The Distance value for this route."
			DEFVAL { 1 }
			::= { sleRouteControl 11 }


		sleRouteControlVRFIndex OBJECT-TYPE
			SYNTAX Integer32 (0..2147483647)
			MAX-ACCESS read-write
			STATUS current
			DESCRIPTION
				"VRF index in sleIpVRFTable."
			::= { sleRouteControl 12 }


		sleRouteNotification OBJECT IDENTIFIER ::= { sleRoute 3 }


		sleRouteStaticCreated NOTIFICATION-TYPE
			OBJECTS { sleRouteControlRequest, sleRouteControlTimeStamp, sleRouteControlReqResult, sleRouteControlDstAddress, sleRouteControlDstMask,
				sleRouteControlGateway, sleRouteControlInterface, sleRouteControlBindingSrcAddr, sleRouteControlDistance, sleRouteControlVRFIndex
				 }
			STATUS current
			DESCRIPTION
				"createStaticRoute"
			::= { sleRouteNotification 1 }


		sleRouteStaticDestroyed NOTIFICATION-TYPE
			OBJECTS { sleRouteControlRequest, sleRouteControlTimeStamp, sleRouteControlReqResult, sleRouteControlDstAddress, sleRouteControlDstMask,
				sleRouteControlGateway, sleRouteControlInterface, sleRouteControlVRFIndex }
			STATUS current
			DESCRIPTION
				"destroyStaticRoute"
			::= { sleRouteNotification 2 }


		sleRouteStaticProfileChanged NOTIFICATION-TYPE
			OBJECTS { sleRouteControlRequest, sleRouteControlTimeStamp, sleRouteControlReqResult, sleRouteControlDstAddress, sleRouteControlDstMask,
				sleRouteControlGateway, sleRouteControlInterface, sleRouteControlBindingSrcAddr, sleRouteControlDistance, sleRouteControlVRFIndex
				 }
			STATUS current
			DESCRIPTION
				"setStaticRouteProfile"
			::= { sleRouteNotification 3 }


		sleDhcpClient OBJECT IDENTIFIER ::= { sleNetwork 5 }


		sleDhcpClTable OBJECT-TYPE
			SYNTAX SEQUENCE OF SleDhcpClEntry
			MAX-ACCESS not-accessible
			STATUS current
			DESCRIPTION
				"Description."
			::= { sleDhcpClient 1 }


		sleDhcpClEntry OBJECT-TYPE
			SYNTAX SleDhcpClEntry
			MAX-ACCESS not-accessible
			STATUS current
			DESCRIPTION
				"Description."
			INDEX { sleNetIfIndex }
			::= { sleDhcpClTable 1 }


		SleDhcpClEntry ::=
			SEQUENCE {
				sleDhcpClMode
					INTEGER,
				sleDhcpClIpAddr
					IpAddress,
				sleDhcpClNetmask
					IpAddress,
				sleDhcpClGateway
					IpAddress,
				sleDhcpClDnsServer
					IpAddress,
				sleDhcpClServer
					IpAddress,
				sleDhcpClClientId
					OCTET STRING,
				sleDhcpClClientIdStyle
					INTEGER,
				sleDhcpClClassId
					OCTET STRING,
				sleDhcpClClassIdStyle
					INTEGER,
				sleDhcpClLeasetime
					Integer32,
				sleDhcpClState
					INTEGER
			 }

		sleDhcpClMode OBJECT-TYPE
			SYNTAX INTEGER
				{
				disable(0),
				enable(1)
				}
			MAX-ACCESS read-only
			STATUS current
			DESCRIPTION
				"DHCP Client activity state in this interface."
			DEFVAL { disable }
			::= { sleDhcpClEntry 1 }


		sleDhcpClIpAddr OBJECT-TYPE
			SYNTAX IpAddress
			MAX-ACCESS read-only
			STATUS current
			DESCRIPTION
				"The IP address acquired by DHCP Client active in this interface."
			::= { sleDhcpClEntry 2 }


		sleDhcpClNetmask OBJECT-TYPE
			SYNTAX IpAddress
			MAX-ACCESS read-only
			STATUS current
			DESCRIPTION
				"The subnet mask associated with the IP address acquired by DHCP Client.
				The value of the mask is an IP address with all the network
				bits set to 1 and all the hosts bits set to 0."
			::= { sleDhcpClEntry 3 }


		sleDhcpClGateway OBJECT-TYPE
			SYNTAX IpAddress
			MAX-ACCESS read-only
			STATUS current
			DESCRIPTION
				"The Gateway's IP address acquired by DHCP Client active in this interface."
			::= { sleDhcpClEntry 4 }


		sleDhcpClDnsServer OBJECT-TYPE
			SYNTAX IpAddress
			MAX-ACCESS read-only
			STATUS current
			DESCRIPTION
				"The DNS server's IP address acquired by DHCP Client active in this interface."
			::= { sleDhcpClEntry 5 }


		sleDhcpClServer OBJECT-TYPE
			SYNTAX IpAddress
			MAX-ACCESS read-only
			STATUS current
			DESCRIPTION
				"DHCP Server's IP address."
			::= { sleDhcpClEntry 6 }


		sleDhcpClClientId OBJECT-TYPE
			SYNTAX OCTET STRING (SIZE (0..255))
			MAX-ACCESS read-only
			STATUS current
			DESCRIPTION
				"DHCP Client-identifier value.
				This is used by DHCP clients to specify their unique identifier.
				DHCP servers use this value to index their database of address bindings.
				This value is expected to be unique for all clients in an administrative domain."
			::= { sleDhcpClEntry 7 }


		sleDhcpClClientIdStyle OBJECT-TYPE
			SYNTAX INTEGER
				{
				ascii(0),
				hex(1)
				}
			MAX-ACCESS read-only
			STATUS current
			DESCRIPTION
				"DHCP Client-identifier input style.
				0 : ascii string format
				1 : hexadecimal format"
			DEFVAL { ascii }
			::= { sleDhcpClEntry 8 }


		sleDhcpClClassId OBJECT-TYPE
			SYNTAX OCTET STRING (SIZE (0..256))
			MAX-ACCESS read-only
			STATUS current
			DESCRIPTION
				"DHCP Class identifier value.
				This is used by DHCP clients to optionally identify the vendor
				type and configuration of a DHCP client.
				The information is a string of n octets, interpreted by servers.
				Vendors may choose to define specific vendor class identifiers
				to convey particular configuration or other identification
				information about a client.
				For example, the identifier may encode the client's hardware configuration."
			::= { sleDhcpClEntry 9 }


		sleDhcpClClassIdStyle OBJECT-TYPE
			SYNTAX INTEGER
				{
				ascii(0),
				hex(1)
				}
			MAX-ACCESS read-only
			STATUS current
			DESCRIPTION
				"DHCP Class identifier input style.
				0 : ascii string format
				1 : hexadecimal format"
			DEFVAL { ascii }
			::= { sleDhcpClEntry 10 }


		sleDhcpClLeasetime OBJECT-TYPE
			SYNTAX Integer32 (120..2147483637)
			MAX-ACCESS read-only
			STATUS current
			DESCRIPTION
				"The leased time for IP address acquired by DHCP Client.
				Default lease-time: 3600s"
			DEFVAL { 3600 }
			::= { sleDhcpClEntry 11 }


		sleDhcpClState OBJECT-TYPE
			SYNTAX INTEGER
				{
				halt(0),
				init(1),
				request(3),
				bound(4),
				renew(5),
				rebind(6),
				nonactive(255)
				}
			MAX-ACCESS read-only
			STATUS current
			DESCRIPTION
				"The operating status of DHCP Client."
			DEFVAL { non-active }
			::= { sleDhcpClEntry 12 }


		sleDhcpClControl OBJECT IDENTIFIER ::= { sleDhcpClient 2 }


		sleDhcpClControlRequest OBJECT-TYPE
			SYNTAX INTEGER
				{
				setDhcpClMode(1),
				setDhcpClProfile(2),
				changeDhcpClState(3)
				}
			MAX-ACCESS read-write
			STATUS current
			DESCRIPTION
				"The request of a user command."
			::= { sleDhcpClControl 1 }


		sleDhcpClControlStatus OBJECT-TYPE
			SYNTAX SleControlStatusType
			MAX-ACCESS read-only
			STATUS current
			DESCRIPTION
				"The status of a user command."
			::= { sleDhcpClControl 2 }


		sleDhcpClControlTimer OBJECT-TYPE
			SYNTAX Gauge32
			MAX-ACCESS read-write
			STATUS current
			DESCRIPTION
				"The maximum wait time for the manager for a long running user command."
			::= { sleDhcpClControl 3 }


		sleDhcpClControlTimeStamp OBJECT-TYPE
			SYNTAX SleControlRequestResultType
			MAX-ACCESS read-only
			STATUS current
			DESCRIPTION
				"The time stamp of the last command (end of command)."
			::= { sleDhcpClControl 4 }


		sleDhcpClControlReqResult OBJECT-TYPE
			SYNTAX TimeTicks
			MAX-ACCESS read-only
			STATUS current
			DESCRIPTION
				"The result of the last user command."
			::= { sleDhcpClControl 5 }


		sleDhcpClControlNetIfIndex OBJECT-TYPE
			SYNTAX Integer32 (1..4094)
			MAX-ACCESS read-write
			STATUS current
			DESCRIPTION
				"Network Interface Index."
			DEFVAL { 1 }
			::= { sleDhcpClControl 6 }


		sleDhcpClControlMode OBJECT-TYPE
			SYNTAX INTEGER
				{
				disable(0),
				enable(1)
				}
			MAX-ACCESS read-write
			STATUS current
			DESCRIPTION
				"DHCP Client activity state in this interface."
			DEFVAL { disable }
			::= { sleDhcpClControl 7 }


		sleDhcpClControlClientId OBJECT-TYPE
			SYNTAX OCTET STRING (SIZE (0..255))
			MAX-ACCESS read-write
			STATUS current
			DESCRIPTION
				"DHCP Client-identifier value.
				This is used by DHCP clients to specify their unique identifier.
				DHCP servers use this value to index their database of address bindings.
				This value is expected to be unique for all clients in an administrative domain."
			::= { sleDhcpClControl 8 }


		sleDhcpClControlClientIdStyle OBJECT-TYPE
			SYNTAX INTEGER
				{
				ascii(0),
				hex(1)
				}
			MAX-ACCESS read-write
			STATUS current
			DESCRIPTION
				"DHCP Client-identifier input style.
				0 : ascii string format
				1 : hexadecimal format"
			DEFVAL { ascii }
			::= { sleDhcpClControl 9 }


		sleDhcpClControlClassId OBJECT-TYPE
			SYNTAX OCTET STRING (SIZE (0..255))
			MAX-ACCESS read-write
			STATUS current
			DESCRIPTION
				"DHCP Class identifier value.
				This is used by DHCP clients to optionally identify the vendor
				type and configuration of a DHCP client.
				The information is a string of n octets, interpreted by servers.
				Vendors may choose to define specific vendor class identifiers
				to convey particular configuration or other identification
				information about a client.
				For example, the identifier may encode the client's hardware configuration."
			::= { sleDhcpClControl 10 }


		sleDhcpClControlClassIdStyle OBJECT-TYPE
			SYNTAX INTEGER
				{
				ascii(0),
				hex(1)
				}
			MAX-ACCESS read-write
			STATUS current
			DESCRIPTION
				"DHCP Class identifier input style.
				0 : ascii string format
				1 : hexadecimal format"
			DEFVAL { ascii }
			::= { sleDhcpClControl 11 }


		sleDhcpClControlLeasetime OBJECT-TYPE
			SYNTAX Integer32 (120..2147483637)
			MAX-ACCESS read-write
			STATUS current
			DESCRIPTION
				"The leased time for IP address acquired by DHCP Client.
				Default lease-time: 3600s"
			DEFVAL { 3600 }
			::= { sleDhcpClControl 12 }


		sleDhcpClControlUpdateIP OBJECT-TYPE
			SYNTAX INTEGER
				{
				remain(0),
				renew(1),
				release(2)
				}
			MAX-ACCESS read-write
			STATUS current
			DESCRIPTION
				"Update DHCP client operating status.
				0 : default
				1 : renew
				2 : release
				"
			DEFVAL { remain }
			::= { sleDhcpClControl 13 }


		sleDhcpClNotification OBJECT IDENTIFIER ::= { sleDhcpClient 3 }


		sleDhcpClModeChanged NOTIFICATION-TYPE
			OBJECTS { sleDhcpClControlRequest, sleDhcpClControlTimeStamp, sleDhcpClControlReqResult, sleDhcpClMode }
			STATUS current
			DESCRIPTION
				"setDhcpClMode."
			::= { sleDhcpClNotification 1 }


		sleDhcpClProfileChanged NOTIFICATION-TYPE
			OBJECTS { sleDhcpClControlRequest, sleDhcpClControlTimeStamp, sleDhcpClControlReqResult, sleDhcpClClientId, sleDhcpClClientIdStyle,
				sleDhcpClClassId, sleDhcpClClassIdStyle, sleDhcpClLeasetime }
			STATUS current
			DESCRIPTION
				"setDhcpClProfile."
			::= { sleDhcpClNotification 2 }


		sleDhcpClStateChanged NOTIFICATION-TYPE
			OBJECTS { sleDhcpClControlRequest, sleDhcpClControlTimeStamp, sleDhcpClControlReqResult, sleDhcpClState }
			STATUS current
			DESCRIPTION
				"ChangeDhcpClState."
			::= { sleDhcpClNotification 3 }


		sleV2DhcpClient OBJECT IDENTIFIER ::= { sleNetwork 6 }


		sleNetworkBase OBJECT IDENTIFIER ::= { sleNetwork 7 }


		sleNetworkBaseInfo OBJECT IDENTIFIER ::= { sleNetworkBase 1 }


		sleNetworkArpAgingTime OBJECT-TYPE
			SYNTAX INTEGER (10..2147483637)
			MAX-ACCESS read-only
			STATUS current
			DESCRIPTION
				"System Arp Aging Time"
			::= { sleNetworkBaseInfo 1 }


		sleNetworkBaseVrfDynamicForwardBinding OBJECT-TYPE
			SYNTAX INTEGER
				{
				disable(0),
				vrrp(1)
				}
			MAX-ACCESS read-only
			STATUS current
			DESCRIPTION
				"Description."
			::= { sleNetworkBaseInfo 2 }


		sleNetworkBaseControl OBJECT IDENTIFIER ::= { sleNetworkBase 2 }


		sleNetworkControlRequest OBJECT-TYPE
			SYNTAX INTEGER
				{
				setArpProfile(1),
				setVrfForwdDynamicStatus(2)
				}
			MAX-ACCESS read-write
			STATUS current
			DESCRIPTION
				"Description."
			::= { sleNetworkBaseControl 1 }


		sleNetworkControlStatus OBJECT-TYPE
			SYNTAX SleControlStatusType
			MAX-ACCESS read-only
			STATUS current
			DESCRIPTION
				"Description."
			::= { sleNetworkBaseControl 2 }


		sleNetworkControlTimer OBJECT-TYPE
			SYNTAX Gauge32
			MAX-ACCESS read-write
			STATUS current
			DESCRIPTION
				"Description."
			::= { sleNetworkBaseControl 3 }


		sleNetworkControlTimeStamp OBJECT-TYPE
			SYNTAX TimeTicks
			MAX-ACCESS read-only
			STATUS current
			DESCRIPTION
				"Description."
			::= { sleNetworkBaseControl 4 }


		sleNetworkControlReqResult OBJECT-TYPE
			SYNTAX SleControlRequestResultType
			MAX-ACCESS read-only
			STATUS current
			DESCRIPTION
				"Description."
			::= { sleNetworkBaseControl 5 }


		sleNetworkControlArpAgingTime OBJECT-TYPE
			SYNTAX INTEGER (10..2147483637)
			MAX-ACCESS read-write
			STATUS current
			DESCRIPTION
				"Description."
			::= { sleNetworkBaseControl 6 }


		sleNetworkControlVrfDynamicForwardBinding OBJECT-TYPE
			SYNTAX INTEGER
				{
				disable(0),
				vrrp(1)
				}
			MAX-ACCESS read-write
			STATUS current
			DESCRIPTION
				"Description."
			::= { sleNetworkBaseControl 7 }


		sleNetworkBaseNotification OBJECT IDENTIFIER ::= { sleNetworkBase 3 }


		sleNetworkArpProfileChanged NOTIFICATION-TYPE
			OBJECTS { sleNetworkControlRequest, sleNetworkControlReqResult, sleNetworkControlTimeStamp, sleNetworkArpAgingTime }
			STATUS current
			DESCRIPTION
				"Description."
			::= { sleNetworkBaseNotification 1 }


		sleTunnel OBJECT IDENTIFIER ::= { sleNetwork 8 }


		sleTunnelIfTable OBJECT-TYPE
			SYNTAX SEQUENCE OF SleTunnelIfEntry
			MAX-ACCESS not-accessible
			STATUS current
			DESCRIPTION
				"Description."
			::= { sleTunnel 1 }


		sleTunnelIfEntry OBJECT-TYPE
			SYNTAX SleTunnelIfEntry
			MAX-ACCESS not-accessible
			STATUS current
			DESCRIPTION
				"Description."
			INDEX { sleTunnelIfIndex }
			::= { sleTunnelIfTable 1 }


		SleTunnelIfEntry ::=
			SEQUENCE {
				sleTunnelIfIndex
					Integer32,
				sleTunnelIfLocalAddress
					IpAddress,
				sleTunnelIfRemoteAddress
					IpAddress,
				sleTunnelIfMode
					IANAtunnelType,
				sleTunnelIfTTL
					Integer32,
				sleTunnelIfDscpMode
					INTEGER,
				sleTunnelIfDscp
					Integer32,
				sleTunnelIfKeepaliveInterval
					Integer32,
				sleTunnelIfKeepaliveRetry
					Integer32,
				sleTunnelIfPathMtuDiscovery
					INTEGER,
				sleTunnelIfVRFName
					OCTET STRING,
				sleTunnelIfBindingPorts
					OCTET STRING,
				sleTunnelIfLocalAddress6
					InetAddress,
				sleTunnelIfRemoteAddress6
					InetAddress,
				sleTunnelIfChecksum
					INTEGER,
				sleTunnelIfDmac
					MacAddress,
				sleTunnelIfTos
					INTEGER
			 }

		sleTunnelIfIndex OBJECT-TYPE
			SYNTAX Integer32 (10000..11023)
			MAX-ACCESS read-only
			STATUS current
			DESCRIPTION
				"Tunnel interface index"
			::= { sleTunnelIfEntry 1 }


		sleTunnelIfLocalAddress OBJECT-TYPE
			SYNTAX IpAddress
			MAX-ACCESS read-only
			STATUS current
			DESCRIPTION
				"The address of the local endpoint of the tunnel (i.e., the source address used in the outer IP header), or 0.0.0.0 if unknown."
			::= { sleTunnelIfEntry 2 }


		sleTunnelIfRemoteAddress OBJECT-TYPE
			SYNTAX IpAddress
			MAX-ACCESS read-only
			STATUS current
			DESCRIPTION
				"The address of the remote endpoint of the tunnel (i.e., the destination address used in the outer IP header), or 0.0.0.0 if unknown."
			::= { sleTunnelIfEntry 3 }


		sleTunnelIfMode OBJECT-TYPE
			SYNTAX IANAtunnelType
			MAX-ACCESS read-only
			STATUS current
			DESCRIPTION
				"The encapsulation method used by the tunnel.

				other(1) - none of the following
				direct(2) - intermediate header
				gre(3) - GRE encapsulation
				minimal(4) - Minimal encapsulation
				l2tp(5) - L2TP encapsulation
				pptp(6)  - PPTP encapsulation
				l2f(7) - L2F encapsulation
				udp(8) - UDP encapsulation
				atmp(9) - ATMP encapsulation
				msdp(10) - MSDP encapsulation
				sixToFour(11) - 6to4 encapsulation
				sixOverFour(12) - 6over4 encapsulation
				isatap(13) - ISATAP encapsulation
				teredo(14)  - Teredo encapsulation
				"
			::= { sleTunnelIfEntry 4 }


		sleTunnelIfTTL OBJECT-TYPE
			SYNTAX Integer32 (1..255)
			MAX-ACCESS read-only
			STATUS current
			DESCRIPTION
				"The TTL to use in the outer IP header."
			::= { sleTunnelIfEntry 5 }


		sleTunnelIfDscpMode OBJECT-TYPE
			SYNTAX INTEGER
				{
				dscpAssign(1),
				dscpCopyFromPacket(2),
				dscpMapFromPacket(3)
				}
			MAX-ACCESS read-only
			STATUS current
			DESCRIPTION
				"The DiffServ field mode to use in the outer IP header.
				A value of dscpCopyFromPacket indicates that the bits are copied from the payload's header. A value of dscpMapFromPacket indicates that the bit field is mapping dscp field of incoming packet.  A value of dscpAssign indicates that the bit field is static DiffServ field value.
				"
			::= { sleTunnelIfEntry 6 }


		sleTunnelIfDscp OBJECT-TYPE
			SYNTAX Integer32 (0..63)
			MAX-ACCESS read-only
			STATUS current
			DESCRIPTION
				"The static DiffServ field value to use in the outer IP header."
			::= { sleTunnelIfEntry 7 }


		sleTunnelIfKeepaliveInterval OBJECT-TYPE
			SYNTAX Integer32 (0..32767)
			MAX-ACCESS read-only
			STATUS current
			DESCRIPTION
				"Specifies the time interval, in seconds, at which keepalive packets are sent. (This object is available for a gre tunnel only.)"
			::= { sleTunnelIfEntry 8 }


		sleTunnelIfKeepaliveRetry OBJECT-TYPE
			SYNTAX Integer32 (1..255)
			MAX-ACCESS read-only
			STATUS current
			DESCRIPTION
				"Specifies the number times that the device will continue to send keepalive packets without response before bringing the tunnel interface protocol down. (This object is available for a gre tunnel only.)"
			::= { sleTunnelIfEntry 9 }


		sleTunnelIfPathMtuDiscovery OBJECT-TYPE
			SYNTAX INTEGER
				{
				enable(1),
				disable(2)
				}
			MAX-ACCESS read-only
			STATUS current
			DESCRIPTION
				"Path mtu discovery on tunnel."
			::= { sleTunnelIfEntry 10 }


		sleTunnelIfVRFName OBJECT-TYPE
			SYNTAX OCTET STRING (SIZE (0..63))
			MAX-ACCESS read-only
			STATUS current
			DESCRIPTION
				"VPN Routing/Forwarding instance name."
			::= { sleTunnelIfEntry 11 }


		sleTunnelIfBindingPorts OBJECT-TYPE
			SYNTAX OCTET STRING
			MAX-ACCESS read-only
			STATUS current
			DESCRIPTION
				"Tunnel binding ports map."
			::= { sleTunnelIfEntry 12 }


		sleTunnelIfLocalAddress6 OBJECT-TYPE
			SYNTAX InetAddress
			MAX-ACCESS read-only
			STATUS current
			DESCRIPTION
				"The address of the local endpoint of the tunnel for IPv6"
			::= { sleTunnelIfEntry 13 }


		sleTunnelIfRemoteAddress6 OBJECT-TYPE
			SYNTAX InetAddress
			MAX-ACCESS read-only
			STATUS current
			DESCRIPTION
				"The address of the remote endpoint of the tunnel for IPv6"
			::= { sleTunnelIfEntry 14 }


		sleTunnelIfChecksum OBJECT-TYPE
			SYNTAX INTEGER
				{
				disable(0),
				enable(1)
				}
			MAX-ACCESS read-only
			STATUS current
			DESCRIPTION
				"A checksum feature for the tunnel."
			::= { sleTunnelIfEntry 15 }


		sleTunnelIfDmac OBJECT-TYPE
			SYNTAX MacAddress
			MAX-ACCESS read-only
			STATUS current
			DESCRIPTION
				"A destination MAC address for tunneled packets. (IP-in-IP tunneling on Broadcom.)"
			::= { sleTunnelIfEntry 16 }


		sleTunnelIfTos OBJECT-TYPE
			SYNTAX INTEGER (0..255)
			MAX-ACCESS read-only
			STATUS current
			DESCRIPTION
				"A value of Type of Service (TOS) in the tunnel IPv4 encapsulation header."
			::= { sleTunnelIfEntry 17 }


		sleTunnelIfControl OBJECT IDENTIFIER ::= { sleTunnel 2 }


		sleTunnelIfControlRequest OBJECT-TYPE
			SYNTAX INTEGER
				{
				createTunnelInterface(1),
				deleteTunnelInterface(2),
				setTunnelIfLocalAddress(3),
				setTunnelIfRemoteAddress(4),
				setTunnelIfMode(5),
				setTunnelIfTTL(6),
				setTunnelIfDscp(7),
				setTunnelIfKeepalive(8),
				setTunnelIfPathMtuDiscovery(9),
				setTunnelIfVRFName(10),
				unsetTunnelIfVRFName(11),
				setTunnelLocalAddr6(12),
				setTunnelRemoteAddr6(13),
				setTunnelChecksum(14),
				setTunnelDmac(15),
				setTunnelTos(16)
				}
			MAX-ACCESS read-write
			STATUS current
			DESCRIPTION
				"The request of a user command."
			::= { sleTunnelIfControl 1 }


		sleTunnelIfControlStatus OBJECT-TYPE
			SYNTAX SleControlStatusType
			MAX-ACCESS read-only
			STATUS current
			DESCRIPTION
				"The status of a user command."
			::= { sleTunnelIfControl 2 }


		sleTunnelIfControlTimer OBJECT-TYPE
			SYNTAX Gauge32
			MAX-ACCESS read-write
			STATUS current
			DESCRIPTION
				"The maximum wait time for the manager for a long running user command."
			::= { sleTunnelIfControl 3 }


		sleTunnelIfControlTimeStamp OBJECT-TYPE
			SYNTAX SleControlRequestResultType
			MAX-ACCESS read-only
			STATUS current
			DESCRIPTION
				"The result of the last user command."
			::= { sleTunnelIfControl 4 }


		sleTunnelIfControlReqResult OBJECT-TYPE
			SYNTAX TimeTicks
			MAX-ACCESS read-only
			STATUS current
			DESCRIPTION
				"The time stamp of the last command (end of command)."
			::= { sleTunnelIfControl 5 }


		sleTunnelIfControlIndex OBJECT-TYPE
			SYNTAX Integer32 (10000..11023)
			MAX-ACCESS read-write
			STATUS current
			DESCRIPTION
				"Tunnel interface index"
			::= { sleTunnelIfControl 6 }


		sleTunnelIfControlLocalAddress OBJECT-TYPE
			SYNTAX IpAddress
			MAX-ACCESS read-write
			STATUS current
			DESCRIPTION
				"The address of the local endpoint of the tunnel (i.e., the source address used in the outer IP header), or 0.0.0.0 if unknown."
			::= { sleTunnelIfControl 7 }


		sleTunnelIfControlRemoteAddress OBJECT-TYPE
			SYNTAX IpAddress
			MAX-ACCESS read-write
			STATUS current
			DESCRIPTION
				"The address of the remote endpoint of the tunnel (i.e., the destination address used in the outer IP header), or 0.0.0.0 if unknown."
			::= { sleTunnelIfControl 8 }


		sleTunnelIfControlMode OBJECT-TYPE
			SYNTAX IANAtunnelType
			MAX-ACCESS read-write
			STATUS current
			DESCRIPTION
				"The encapsulation method used by the tunnel.

				other(1) - none of the following
				direct(2) - intermediate header
				gre(3) - GRE encapsulation
				minimal(4) - Minimal encapsulation
				l2tp(5) - L2TP encapsulation
				pptp(6)  - PPTP encapsulation
				l2f(7) - L2F encapsulation
				udp(8) - UDP encapsulation
				atmp(9) - ATMP encapsulation
				msdp(10) - MSDP encapsulation
				sixToFour(11) - 6to4 encapsulation
				sixOverFour(12) - 6over4 encapsulation
				isatap(13) - ISATAP encapsulation
				teredo(14)  - Teredo encapsulation
				"
			::= { sleTunnelIfControl 9 }


		sleTunnelIfControlTTL OBJECT-TYPE
			SYNTAX Integer32 (1..255)
			MAX-ACCESS read-write
			STATUS current
			DESCRIPTION
				"The TTL to use in the outer IP header."
			::= { sleTunnelIfControl 10 }


		sleTunneIflControlDscpMode OBJECT-TYPE
			SYNTAX INTEGER
				{
				dscpAssign(1),
				dscpCopyFromPacket(2),
				dscpMapFromPacket(3)
				}
			MAX-ACCESS read-write
			STATUS current
			DESCRIPTION
				"The DiffServ field mode to use in the outer IP header.
				A value of dscpCopyFromPacket indicates that the bits are copied from the payload's header. A value of dscpMapFromPacket indicates that the bit field is mapping dscp field of incoming packet.  A value of dscpAssign indicates that the bit field is static DiffServ field value.
				"
			DEFVAL { dscpCopyFromPacket }
			::= { sleTunnelIfControl 11 }


		sleTunneIflControlDscp OBJECT-TYPE
			SYNTAX Integer32 (0..63)
			MAX-ACCESS read-write
			STATUS current
			DESCRIPTION
				"The static DiffServ field value to use in the outer IP header."
			::= { sleTunnelIfControl 12 }


		sleTunnelIfControlKeepaliveInterval OBJECT-TYPE
			SYNTAX Integer32 (1..32767)
			MAX-ACCESS read-write
			STATUS current
			DESCRIPTION
				"Specifies the time interval, in seconds, at which keepalive packets are sent. (This object is available for a gre tunnel only.)"
			DEFVAL { 100 }
			::= { sleTunnelIfControl 13 }


		sleTunneIflControlKeepaliveRetry OBJECT-TYPE
			SYNTAX Integer32 (1..255)
			MAX-ACCESS read-write
			STATUS current
			DESCRIPTION
				"Specifies the number times that the device will continue to send keepalive packets without response before bringing the tunnel interface protocol down. (This object is available for a gre tunnel only.)"
			DEFVAL { 3 }
			::= { sleTunnelIfControl 14 }


		sleTunnelIfControlPathMtuDiscovery OBJECT-TYPE
			SYNTAX INTEGER
				{
				enable(1),
				disable(2)
				}
			MAX-ACCESS read-write
			STATUS current
			DESCRIPTION
				" Path mtu discovery on tunnel."
			::= { sleTunnelIfControl 15 }


		sleTunnelIfControlVRFName OBJECT-TYPE
			SYNTAX OCTET STRING (SIZE (0..63))
			MAX-ACCESS read-write
			STATUS current
			DESCRIPTION
				"VPN Routing/Forwarding instance name."
			::= { sleTunnelIfControl 16 }


		sleTunnelIfControlLocalAddress6 OBJECT-TYPE
			SYNTAX InetAddress
			MAX-ACCESS read-write
			STATUS current
			DESCRIPTION
				"The address of the local endpoint of the tunnel for IPv6"
			::= { sleTunnelIfControl 17 }


		sleTunnelIfControlRemoteAddress6 OBJECT-TYPE
			SYNTAX InetAddress
			MAX-ACCESS read-write
			STATUS current
			DESCRIPTION
				"The address of the remote endpoint of the tunnel for IPv6"
			::= { sleTunnelIfControl 18 }


		sleTunnelIfControlChecksum OBJECT-TYPE
			SYNTAX INTEGER
				{
				disable(0),
				enable(1)
				}
			MAX-ACCESS read-write
			STATUS current
			DESCRIPTION
				"A checksum feature for the tunnel."
			::= { sleTunnelIfControl 19 }


		sleTunnelIfControlDmac OBJECT-TYPE
			SYNTAX MacAddress
			MAX-ACCESS read-write
			STATUS current
			DESCRIPTION
				"A destination MAC address for tunneled packets. (IP-in-IP tunneling on Broadcom.)"
			::= { sleTunnelIfControl 20 }


		sleTunnelIfControlTos OBJECT-TYPE
			SYNTAX INTEGER (0..255)
			MAX-ACCESS read-write
			STATUS current
			DESCRIPTION
				"A value of Type of Service (TOS) in the tunnel IPv4 encapsulation header."
			::= { sleTunnelIfControl 21 }


		sleTunnelIfNotification OBJECT IDENTIFIER ::= { sleTunnel 3 }


		sleTunnelIfCreated NOTIFICATION-TYPE
			OBJECTS { sleTunnelIfControlRequest, sleTunnelIfControlTimeStamp, sleTunnelIfControlReqResult, sleTunnelIfControlIndex }
			STATUS current
			DESCRIPTION
				"Description."
			::= { sleTunnelIfNotification 1 }


		sleTunnelIfDeleted NOTIFICATION-TYPE
			OBJECTS { sleTunnelIfControlRequest, sleTunnelIfControlTimeStamp, sleTunnelIfControlReqResult, sleTunnelIfControlIndex }
			STATUS current
			DESCRIPTION
				"Description."
			::= { sleTunnelIfNotification 2 }


		sleTunnelIfLocalAddressChanged NOTIFICATION-TYPE
			OBJECTS { sleTunnelIfControlRequest, sleTunnelIfControlTimeStamp, sleTunnelIfControlReqResult, sleTunnelIfControlIndex, sleTunnelIfControlLocalAddress
				 }
			STATUS current
			DESCRIPTION
				"Description."
			::= { sleTunnelIfNotification 3 }


		sleTunnelIfRemoteAddressChanged NOTIFICATION-TYPE
			OBJECTS { sleTunnelIfControlRequest, sleTunnelIfControlTimeStamp, sleTunnelIfControlReqResult, sleTunnelIfControlIndex, sleTunnelIfControlRemoteAddress
				 }
			STATUS current
			DESCRIPTION
				"Description."
			::= { sleTunnelIfNotification 4 }


		sleTunnelIfModeChanged NOTIFICATION-TYPE
			OBJECTS { sleTunnelIfControlRequest, sleTunnelIfControlTimeStamp, sleTunnelIfControlReqResult, sleTunnelIfControlIndex, sleTunnelIfControlMode
				 }
			STATUS current
			DESCRIPTION
				"Description."
			::= { sleTunnelIfNotification 5 }


		sleTunnelIfTTLChanged NOTIFICATION-TYPE
			OBJECTS { sleTunnelIfControlRequest, sleTunnelIfControlTimeStamp, sleTunnelIfControlReqResult, sleTunnelIfControlIndex, sleTunnelIfControlTTL
				 }
			STATUS current
			DESCRIPTION
				"Description."
			::= { sleTunnelIfNotification 6 }


		sleTunnelIfDscpChanged NOTIFICATION-TYPE
			OBJECTS { sleTunnelIfControlRequest, sleTunnelIfControlTimeStamp, sleTunnelIfControlReqResult, sleTunnelIfControlIndex, sleTunneIflControlDscpMode,
				sleTunneIflControlDscp }
			STATUS current
			DESCRIPTION
				"Description."
			::= { sleTunnelIfNotification 7 }


		sleTunnelIfKeepaliveChanged NOTIFICATION-TYPE
			OBJECTS { sleTunnelIfControlRequest, sleTunnelIfControlTimeStamp, sleTunnelIfControlReqResult, sleTunnelIfControlIndex, sleTunnelIfControlKeepaliveInterval,
				sleTunneIflControlKeepaliveRetry }
			STATUS current
			DESCRIPTION
				"Description."
			::= { sleTunnelIfNotification 8 }


		sleTunnelIfPathMtuDiscoveryChanged NOTIFICATION-TYPE
			OBJECTS { sleTunnelIfControlRequest, sleTunnelIfControlTimeStamp, sleTunnelIfControlReqResult, sleTunnelIfControlIndex, sleTunnelIfControlPathMtuDiscovery
				 }
			STATUS current
			DESCRIPTION
				"Description."
			::= { sleTunnelIfNotification 9 }


		sleTunnelIfVRFNameSet NOTIFICATION-TYPE
			OBJECTS { sleTunnelIfControlRequest, sleTunnelIfControlTimeStamp, sleTunnelIfControlReqResult, sleTunnelIfControlIndex, sleTunnelIfControlVRFName
				 }
			STATUS current
			DESCRIPTION
				"Description."
			::= { sleTunnelIfNotification 10 }


		sleTunnelIfVRFNameUnset NOTIFICATION-TYPE
			OBJECTS { sleTunnelIfControlRequest, sleTunnelIfControlTimeStamp, sleTunnelIfControlReqResult, sleTunnelIfControlIndex }
			STATUS current
			DESCRIPTION
				"Description."
			::= { sleTunnelIfNotification 11 }


		sleTunnelIfLocalAddress6Changed NOTIFICATION-TYPE
			OBJECTS { sleTunnelIfControlRequest, sleTunnelIfControlTimeStamp, sleTunnelIfControlReqResult, sleTunnelIfControlIndex, sleTunnelIfControlLocalAddress6
				 }
			STATUS current
			DESCRIPTION
				"setTunnelLocalAddr6"
			::= { sleTunnelIfNotification 12 }


		sleTunnelIfRemoteAddress6Changed NOTIFICATION-TYPE
			OBJECTS { sleTunnelIfControlRequest, sleTunnelIfControlTimeStamp, sleTunnelIfControlReqResult, sleTunnelIfControlIndex, sleTunnelIfControlRemoteAddress6
				 }
			STATUS current
			DESCRIPTION
				"setTunnelRemoteAddr6"
			::= { sleTunnelIfNotification 13 }


		sleTunnelAddressTable OBJECT-TYPE
			SYNTAX SEQUENCE OF SleTunnelAddressEntry
			MAX-ACCESS not-accessible
			STATUS current
			DESCRIPTION
				"Description."
			::= { sleTunnel 4 }


		sleTunnelAddressEntry OBJECT-TYPE
			SYNTAX SleTunnelAddressEntry
			MAX-ACCESS not-accessible
			STATUS current
			DESCRIPTION
				"Description."
			INDEX { sleTunnelIfIndex, sleTunnelAddressValue }
			::= { sleTunnelAddressTable 1 }


		SleTunnelAddressEntry ::=
			SEQUENCE {
				sleTunnelAddressValue
					IpAddress,
				sleTunnelAddressMask
					Integer32,
				sleTunnelIpAddrBcast
					IpAddress,
				sleTunnelAddressFlag
					BITS,
				sleTunnelAddressScope
					Integer32,
				sleTunnelAddressUnnumIfIndex
					INTEGER,
				sleTunnelAddressUnnumIpIndex
					INTEGER
			 }

		sleTunnelAddressValue OBJECT-TYPE
			SYNTAX IpAddress
			MAX-ACCESS read-only
			STATUS current
			DESCRIPTION
				"The IP address to which this entry's addressing information pertains."
			::= { sleTunnelAddressEntry 1 }


		sleTunnelAddressMask OBJECT-TYPE
			SYNTAX Integer32 (1..128)
			MAX-ACCESS read-only
			STATUS current
			DESCRIPTION
				"The subnet mask associated with the IP address of this entry. The value of the mask is an IP address with all the network bits set to 1 and all the hosts bits set to 0."
			::= { sleTunnelAddressEntry 2 }


		sleTunnelIpAddrBcast OBJECT-TYPE
			SYNTAX IpAddress
			MAX-ACCESS read-only
			STATUS current
			DESCRIPTION
				"Description."
			::= { sleTunnelAddressEntry 3 }


		sleTunnelAddressFlag OBJECT-TYPE
			SYNTAX BITS
				{
				permanent(0),
				tentative(1),
				deprecated(2),
				anycast(3),
				reserved1(4),
				reserved2(5),
				reserved3(6),
				secondary(7)
				}
			MAX-ACCESS read-only
			STATUS current
			DESCRIPTION
				"dynamic: ~ permanent
				primary : ~ secondary
				anycast: this bit is available for ipv6 only.
				The others are available for ipv4 only.
				"
			::= { sleTunnelAddressEntry 4 }


		sleTunnelAddressScope OBJECT-TYPE
			SYNTAX Integer32 (0..255)
			MAX-ACCESS read-only
			STATUS current
			DESCRIPTION
				"default : global
				In linux, 200 - site
				0 - global
				1..252 - scopeNUM
				253 - link
				254 - host
				255 - nowhere
				"
			::= { sleTunnelAddressEntry 5 }


		sleTunnelAddressUnnumIfIndex OBJECT-TYPE
			SYNTAX INTEGER (1..4094)
			MAX-ACCESS read-only
			STATUS current
			DESCRIPTION
				"The unnumbered-source interface index (Before ip unnumbered feature is set, a tunnel interface must be created.)
				(ex. br100 -> 100, br200 -> 200)"
			::= { sleTunnelAddressEntry 6 }


		sleTunnelAddressUnnumIpIndex OBJECT-TYPE
			SYNTAX INTEGER (0 | 2..1024)
			MAX-ACCESS read-only
			STATUS current
			DESCRIPTION
				"The Ip index for Interface Unnumbered feature enhanced.
				If Interface Unnumbered enhanced feature is enabled on a point-to-point interface. It will get a ip address of a specific interface.
				Interface unnumbered default setting - it get primary ip address.
				Interface unnumbered enhanced setting - it get secondary ip address with ip-index.
				(cf. primary ip address's ip-index : 1. no setting: 0. other setting: 2-1024)"
			::= { sleTunnelAddressEntry 7 }


		sleTunnelAddressControl OBJECT IDENTIFIER ::= { sleTunnel 5 }


		sleTunnelAddressControlRequest OBJECT-TYPE
			SYNTAX INTEGER
				{
				createTunnelIpAddress(1),
				destroyTunnelIpAddress(2),
				setIfUnnumbered(3),
				delIfUnnumbered(4)
				}
			MAX-ACCESS read-write
			STATUS current
			DESCRIPTION
				"The request of a user command."
			::= { sleTunnelAddressControl 1 }


		sleTunnelAddressControlStatus OBJECT-TYPE
			SYNTAX SleControlStatusType
			MAX-ACCESS read-only
			STATUS current
			DESCRIPTION
				"The status of a user command."
			::= { sleTunnelAddressControl 2 }


		sleTunnelAddressControlTimer OBJECT-TYPE
			SYNTAX Gauge32
			MAX-ACCESS read-write
			STATUS current
			DESCRIPTION
				"The maximum wait time for the manager for a long running user command."
			::= { sleTunnelAddressControl 3 }


		sleTunnelAddressControlTimeStamp OBJECT-TYPE
			SYNTAX SleControlRequestResultType
			MAX-ACCESS read-only
			STATUS current
			DESCRIPTION
				"The result of the last user command."
			::= { sleTunnelAddressControl 4 }


		sleTunnelAddressControlReqResult OBJECT-TYPE
			SYNTAX TimeTicks
			MAX-ACCESS read-only
			STATUS current
			DESCRIPTION
				"The time stamp of the last command (end of command)."
			::= { sleTunnelAddressControl 5 }


		sleTunnelAddressControlTunnelIfIndex OBJECT-TYPE
			SYNTAX Integer32 (10000..11023)
			MAX-ACCESS read-write
			STATUS current
			DESCRIPTION
				"Tunnel interface index"
			::= { sleTunnelAddressControl 6 }


		sleTunnelAddressControlValue OBJECT-TYPE
			SYNTAX IpAddress
			MAX-ACCESS read-write
			STATUS current
			DESCRIPTION
				"The IP address to which this entry's addressing information pertains."
			::= { sleTunnelAddressControl 7 }


		sleTunnelAddressControlMask OBJECT-TYPE
			SYNTAX Integer32 (1..128)
			MAX-ACCESS read-write
			STATUS current
			DESCRIPTION
				"The subnet mask associated with the IP address of this entry. The value of the mask is an IP address with all the network bits set to 1 and all the hosts bits set to 0."
			::= { sleTunnelAddressControl 8 }


		sleTunnelAddressControlFlag OBJECT-TYPE
			SYNTAX INTEGER
				{
				primary(1),
				secondary(2),
				anycast(3),
				unicast(4)
				}
			MAX-ACCESS read-write
			STATUS current
			DESCRIPTION
				"default : primary"
			DEFVAL { primary }
			::= { sleTunnelAddressControl 9 }


		sleTunnelAddressControlScope OBJECT-TYPE
			SYNTAX INTEGER
				{
				global(0),
				link(253),
				host(254)
				}
			MAX-ACCESS read-write
			STATUS current
			DESCRIPTION
				"default : global
				not applicable : nowhere"
			DEFVAL { global }
			::= { sleTunnelAddressControl 10 }


		sleTunnelAddressControlUnnumIfIndex OBJECT-TYPE
			SYNTAX INTEGER (1..4094)
			MAX-ACCESS read-write
			STATUS current
			DESCRIPTION
				"The unnumbered-source interface index (Before ip unnumbered feature is set, a tunnel interface must be created.)
				(ex. br100 -> 100, br200 -> 200)"
			::= { sleTunnelAddressControl 11 }


		sleTunnelAddressControlUnnumIpIndex OBJECT-TYPE
			SYNTAX INTEGER (0 | 2..1024)
			MAX-ACCESS read-write
			STATUS current
			DESCRIPTION
				"The Ip index for Interface Unnumbered feature enhanced.
				If Interface Unnumbered enhanced feature is enabled on a point-to-point interface. It will get a ip address of a specific interface.
				Interface unnumbered default setting - it get primary ip address.
				Interface unnumbered enhanced setting - it get secondary ip address with ip-index.
				(cf. primary ip address's ip-index : 1. no setting: 0. other setting: 2-1024)"
			::= { sleTunnelAddressControl 12 }


		sleTunnelAddressNotification OBJECT IDENTIFIER ::= { sleTunnel 6 }


		sleTunnelAddressCreated NOTIFICATION-TYPE
			OBJECTS { sleTunnelAddressControlRequest, sleTunnelAddressControlTimeStamp, sleTunnelAddressControlReqResult, sleTunnelAddressControlTunnelIfIndex, sleTunnelAddressControlValue,
				sleTunnelAddressControlMask, sleTunnelAddressControlFlag, sleTunnelAddressControlScope }
			STATUS current
			DESCRIPTION
				"Description."
			::= { sleTunnelAddressNotification 1 }


		sleTunnelAddressDeleted NOTIFICATION-TYPE
			OBJECTS { sleTunnelAddressControlRequest, sleTunnelAddressControlTimeStamp, sleTunnelAddressControlReqResult, sleTunnelAddressControlTunnelIfIndex, sleTunnelAddressControlValue,
				sleTunnelAddressControlMask, sleTunnelAddressControlFlag }
			STATUS current
			DESCRIPTION
				"Description."
			::= { sleTunnelAddressNotification 2 }


		sleTunnelAddressUnnumChanged NOTIFICATION-TYPE
			OBJECTS { sleTunnelAddressControlRequest, sleTunnelAddressControlTimeStamp, sleTunnelAddressControlReqResult, sleTunnelAddressControlUnnumIfIndex, sleTunnelAddressControlUnnumIpIndex
				 }
			STATUS current
			DESCRIPTION
				"setIfUnnumbered"
			::= { sleTunnelAddressNotification 3 }


		sleTunnelAddressUnnumDeleted NOTIFICATION-TYPE
			OBJECTS { sleTunnelAddressControlRequest, sleTunnelAddressControlTimeStamp, sleTunnelAddressControlReqResult, sleTunnelAddressControlTunnelIfIndex }
			STATUS current
			DESCRIPTION
				"delIfUnnumbered"
			::= { sleTunnelAddressNotification 4 }


		sleIpVRF OBJECT IDENTIFIER ::= { sleNetwork 9 }


		sleIpVRFTable OBJECT-TYPE
			SYNTAX SEQUENCE OF SleIpVRFEntry
			MAX-ACCESS not-accessible
			STATUS current
			DESCRIPTION
				"Description."
			::= { sleIpVRF 1 }


		sleIpVRFEntry OBJECT-TYPE
			SYNTAX SleIpVRFEntry
			MAX-ACCESS not-accessible
			STATUS current
			DESCRIPTION
				"Description."
			INDEX { sleIpVRFIndex }
			::= { sleIpVRFTable 1 }


		SleIpVRFEntry ::=
			SEQUENCE {
				sleIpVRFIndex
					Integer32,
				sleIpVRFName
					OCTET STRING,
				sleIpVRFDesignatedPorts
					OCTET STRING,
				sleIpVRFRouterId
					IpAddress,
				sleIpVRFDescription
					OCTET STRING
			 }

		sleIpVRFIndex OBJECT-TYPE
			SYNTAX Integer32 (0..2147483647)
			MAX-ACCESS read-only
			STATUS current
			DESCRIPTION
				"VRF index."
			::= { sleIpVRFEntry 1 }


		sleIpVRFName OBJECT-TYPE
			SYNTAX OCTET STRING (SIZE (0..63))
			MAX-ACCESS read-only
			STATUS current
			DESCRIPTION
				"VRF name."
			::= { sleIpVRFEntry 2 }


		sleIpVRFDesignatedPorts OBJECT-TYPE
			SYNTAX OCTET STRING
			MAX-ACCESS read-only
			STATUS current
			DESCRIPTION
				"The port map of  VRF designated-port."
			::= { sleIpVRFEntry 3 }


		sleIpVRFRouterId OBJECT-TYPE
			SYNTAX IpAddress
			MAX-ACCESS read-only
			STATUS current
			DESCRIPTION
				"Router-Identifier
				"
			::= { sleIpVRFEntry 4 }


		sleIpVRFDescription OBJECT-TYPE
			SYNTAX OCTET STRING (SIZE (0..128))
			MAX-ACCESS read-only
			STATUS current
			DESCRIPTION
				"The description of VRF.
				"
			::= { sleIpVRFEntry 5 }


		sleIpVRFControl OBJECT IDENTIFIER ::= { sleIpVRF 2 }


		sleIpVRFControlRequest OBJECT-TYPE
			SYNTAX INTEGER
				{
				createIpVRF(1),
				deleteIpVRF(2),
				setIpVRFDesignatedPorts(3),
				unsetIpVRFDesignatedPorts(4),
				setVRFRouterId(5),
				setVRFDescription(6)
				}
			MAX-ACCESS read-write
			STATUS current
			DESCRIPTION
				"The request of a user command."
			::= { sleIpVRFControl 1 }


		sleIpVRFControlStatus OBJECT-TYPE
			SYNTAX SleControlStatusType
			MAX-ACCESS read-only
			STATUS current
			DESCRIPTION
				"The status of a user command."
			::= { sleIpVRFControl 2 }


		sleIpVRFControlTimer OBJECT-TYPE
			SYNTAX Gauge32
			MAX-ACCESS read-write
			STATUS current
			DESCRIPTION
				"The maximum wait time for the manager for a long running user command."
			::= { sleIpVRFControl 3 }


		sleIpVRFControlTimeStamp OBJECT-TYPE
			SYNTAX SleControlRequestResultType
			MAX-ACCESS read-only
			STATUS current
			DESCRIPTION
				"The result of the last user command."
			::= { sleIpVRFControl 4 }


		sleIpVRFControlReqResult OBJECT-TYPE
			SYNTAX TimeTicks
			MAX-ACCESS read-only
			STATUS current
			DESCRIPTION
				"The time stamp of the last command (end of command)."
			::= { sleIpVRFControl 5 }


		sleIpVRFControlName OBJECT-TYPE
			SYNTAX OCTET STRING (SIZE (0..63))
			MAX-ACCESS read-write
			STATUS current
			DESCRIPTION
				"VRF name"
			::= { sleIpVRFControl 6 }


		sleIpVRFControlDesignatedPorts OBJECT-TYPE
			SYNTAX OCTET STRING
			MAX-ACCESS read-write
			STATUS current
			DESCRIPTION
				"The port map of  VRF designated-port."
			::= { sleIpVRFControl 7 }


		sleIpVRFControlRouterId OBJECT-TYPE
			SYNTAX IpAddress
			MAX-ACCESS read-write
			STATUS current
			DESCRIPTION
				"Router-Identifier
				"
			::= { sleIpVRFControl 8 }


		sleIpVRFControlDescription OBJECT-TYPE
			SYNTAX OCTET STRING (SIZE (0..128))
			MAX-ACCESS read-write
			STATUS current
			DESCRIPTION
				"The description of VRF."
			::= { sleIpVRFControl 9 }


		sleIpVRFNotification OBJECT IDENTIFIER ::= { sleIpVRF 3 }


		sleIpVRFCreated NOTIFICATION-TYPE
			OBJECTS { sleIpVRFControlRequest, sleIpVRFControlTimeStamp, sleIpVRFControlName, sleIpVRFControlReqResult }
			STATUS current
			DESCRIPTION
				"Description."
			::= { sleIpVRFNotification 1 }


		sleIpVRFDeleted NOTIFICATION-TYPE
			OBJECTS { sleIpVRFControlRequest, sleIpVRFControlTimeStamp, sleIpVRFControlReqResult, sleIpVRFControlName }
			STATUS current
			DESCRIPTION
				"Description."
			::= { sleIpVRFNotification 2 }


		sleIpVRFDesignatedPortsSet NOTIFICATION-TYPE
			OBJECTS { sleIpVRFControlRequest, sleIpVRFControlTimeStamp, sleIpVRFControlReqResult, sleIpVRFControlName, sleIpVRFControlDesignatedPorts
				 }
			STATUS current
			DESCRIPTION
				"Description."
			::= { sleIpVRFNotification 3 }


		sleIpVRFDesignatedPortsUnset NOTIFICATION-TYPE
			OBJECTS { sleIpVRFControlRequest, sleIpVRFControlTimeStamp, sleIpVRFControlReqResult, sleIpVRFControlName, sleIpVRFControlDesignatedPorts
				 }
			STATUS current
			DESCRIPTION
				"Description."
			::= { sleIpVRFNotification 4 }


		sleIpVRFRouterIdChanged NOTIFICATION-TYPE
			OBJECTS { sleIpVRFControlRequest, sleIpVRFControlTimeStamp, sleIpVRFControlReqResult, sleIpVRFControlName, sleIpVRFControlRouterId
				 }
			STATUS current
			DESCRIPTION
				"Description."
			::= { sleIpVRFNotification 5 }


		sleIpVRFDescriptionChanged NOTIFICATION-TYPE
			OBJECTS { sleIpVRFControlRequest, sleIpVRFControlTimeStamp, sleIpVRFControlReqResult, sleIpVRFControlName, sleIpVRFControlDescription
				 }
			STATUS current
			DESCRIPTION
				"Description."
			::= { sleIpVRFNotification 6 }


		sleIpVRFSelectionSourceTable OBJECT-TYPE
			SYNTAX SEQUENCE OF SleIpVRFSelectionSourceEntry
			MAX-ACCESS not-accessible
			STATUS current
			DESCRIPTION
				"Description."
			::= { sleIpVRF 4 }


		sleIpVRFSelectionSourceEntry OBJECT-TYPE
			SYNTAX SleIpVRFSelectionSourceEntry
			MAX-ACCESS not-accessible
			STATUS current
			DESCRIPTION
				"Description."
			INDEX { sleIpVRFSelectionSrcIndex }
			::= { sleIpVRFSelectionSourceTable 1 }


		SleIpVRFSelectionSourceEntry ::=
			SEQUENCE {
				sleIpVRFSelectionSrcIndex
					INTEGER,
				sleIpVRFSelectionSrcAddr
					IpAddress,
				sleIpVRFSelectionSrcMask
					Integer32,
				sleIpVRFSelectionSrcVRFName
					OCTET STRING
			 }

		sleIpVRFSelectionSrcIndex OBJECT-TYPE
			SYNTAX INTEGER (1..1024)
			MAX-ACCESS read-only
			STATUS current
			DESCRIPTION
				"VRF selection source index."
			::= { sleIpVRFSelectionSourceEntry 1 }


		sleIpVRFSelectionSrcAddr OBJECT-TYPE
			SYNTAX IpAddress
			MAX-ACCESS read-only
			STATUS current
			DESCRIPTION
				"VRF selection by source IP address."
			::= { sleIpVRFSelectionSourceEntry 2 }


		sleIpVRFSelectionSrcMask OBJECT-TYPE
			SYNTAX Integer32 (1..32)
			MAX-ACCESS read-only
			STATUS current
			DESCRIPTION
				"The subnet mask associated with the IP address of this entry. The value of the mask is an IP address with all the network bits set to 1 and all the hosts bits set to 0."
			::= { sleIpVRFSelectionSourceEntry 3 }


		sleIpVRFSelectionSrcVRFName OBJECT-TYPE
			SYNTAX OCTET STRING (SIZE (0..63))
			MAX-ACCESS read-only
			STATUS current
			DESCRIPTION
				"VPN Routing/Forwarding instance name."
			::= { sleIpVRFSelectionSourceEntry 4 }


		sleIpVRFSelectionSourceControl OBJECT IDENTIFIER ::= { sleIpVRF 5 }


		sleIpVRFSelectionSrcControlRequest OBJECT-TYPE
			SYNTAX INTEGER
				{
				setVRFSelectionSource(1),
				unsetVRFSelectionSource(2)
				}
			MAX-ACCESS read-write
			STATUS current
			DESCRIPTION
				"The request of a user command."
			::= { sleIpVRFSelectionSourceControl 1 }


		sleIpVRFSelectionSrcControlStatus OBJECT-TYPE
			SYNTAX SleControlStatusType
			MAX-ACCESS read-only
			STATUS current
			DESCRIPTION
				"The status of a user command."
			::= { sleIpVRFSelectionSourceControl 2 }


		sleIpVRFSelectionSrcControlTimer OBJECT-TYPE
			SYNTAX Gauge32
			MAX-ACCESS read-write
			STATUS current
			DESCRIPTION
				"The maximum wait time for the manager for a long running user command."
			::= { sleIpVRFSelectionSourceControl 3 }


		sleIpVRFSelectionSrcControlTimeStamp OBJECT-TYPE
			SYNTAX SleControlRequestResultType
			MAX-ACCESS read-only
			STATUS current
			DESCRIPTION
				"The result of the last user command."
			::= { sleIpVRFSelectionSourceControl 4 }


		sleIpVRFSelectionSrcControlReqResult OBJECT-TYPE
			SYNTAX TimeTicks
			MAX-ACCESS read-only
			STATUS current
			DESCRIPTION
				"The time stamp of the last command (end of command)."
			::= { sleIpVRFSelectionSourceControl 5 }


		sleIpVRFSelectionSrcControlAddr OBJECT-TYPE
			SYNTAX IpAddress
			MAX-ACCESS read-write
			STATUS current
			DESCRIPTION
				"VRF selection by source IP address."
			::= { sleIpVRFSelectionSourceControl 6 }


		sleIpVRFSelectionSrcControlMask OBJECT-TYPE
			SYNTAX Integer32 (1..32)
			MAX-ACCESS read-write
			STATUS current
			DESCRIPTION
				"The subnet mask associated with the IP address of this entry. The value of the mask is an IP address with all the network bits set to 1 and all the hosts bits set to 0."
			::= { sleIpVRFSelectionSourceControl 7 }


		sleIpVRFSelectionSrcControlVRFName OBJECT-TYPE
			SYNTAX OCTET STRING (SIZE (0..63))
			MAX-ACCESS read-write
			STATUS current
			DESCRIPTION
				"VPN Routing/Forwarding instance name."
			::= { sleIpVRFSelectionSourceControl 8 }


		sleIpVRFSelectionSourceNotification OBJECT IDENTIFIER ::= { sleIpVRF 6 }


		sleIpVRFSelectionSrcSet NOTIFICATION-TYPE
			OBJECTS { sleIpVRFSelectionSrcControlRequest, sleIpVRFSelectionSrcControlTimeStamp, sleIpVRFSelectionSrcControlReqResult, sleIpVRFSelectionSrcControlAddr, sleIpVRFSelectionSrcControlMask,
				sleIpVRFSelectionSrcControlVRFName }
			STATUS current
			DESCRIPTION
				"Description."
			::= { sleIpVRFSelectionSourceNotification 1 }


		sleIpVRFSelectionSrcUnset NOTIFICATION-TYPE
			OBJECTS { sleIpVRFSelectionSrcControlRequest, sleIpVRFSelectionSrcControlTimeStamp, sleIpVRFSelectionSrcControlReqResult, sleIpVRFSelectionSrcControlAddr, sleIpVRFSelectionSrcControlMask,
				sleIpVRFSelectionSrcControlVRFName }
			STATUS current
			DESCRIPTION
				"Description."
			::= { sleIpVRFSelectionSourceNotification 2 }


		sleBFD OBJECT IDENTIFIER ::= { sleNetwork 10 }


		sleBFDBase OBJECT IDENTIFIER ::= { sleBFD 1 }


		sleBFDBaseInfo OBJECT IDENTIFIER ::= { sleBFDBase 1 }


		sleBFDEnable OBJECT-TYPE
			SYNTAX INTEGER
				{
				disable(0),
				enable(1)
				}
			MAX-ACCESS read-only
			STATUS current
			DESCRIPTION
				"BFD fast-detect is enabled or disabled."
			::= { sleBFDBaseInfo 1 }


		sleBFDEchoEnable OBJECT-TYPE
			SYNTAX INTEGER
				{
				disable(0),
				enable(1)
				}
			MAX-ACCESS read-only
			STATUS current
			DESCRIPTION
				"BFD Echo function is enabled or disabled."
			::= { sleBFDBaseInfo 2 }


		sleBFDSlowTimer OBJECT-TYPE
			SYNTAX INTEGER (1000..30000)
			MAX-ACCESS read-only
			STATUS current
			DESCRIPTION
				"BFD Slow Timer in unit of milliseconds
				default: 1000(ms)"
			::= { sleBFDBaseInfo 3 }


		sleBFDBaseControl OBJECT IDENTIFIER ::= { sleBFDBase 2 }


		sleBFDControlRequest OBJECT-TYPE
			SYNTAX INTEGER { setBFDBaseProfile(1) }
			MAX-ACCESS read-write
			STATUS current
			DESCRIPTION
				"The request of a user command"
			::= { sleBFDBaseControl 1 }


		sleBFDControlStatus OBJECT-TYPE
			SYNTAX SleControlStatusType
			MAX-ACCESS read-only
			STATUS current
			DESCRIPTION
				"The status of user command."
			::= { sleBFDBaseControl 2 }


		sleBFDControlTimer OBJECT-TYPE
			SYNTAX Gauge32
			MAX-ACCESS read-write
			STATUS current
			DESCRIPTION
				"The maximum time for the manager for a long running user command."
			::= { sleBFDBaseControl 3 }


		sleBFDControlTimeStamp OBJECT-TYPE
			SYNTAX TimeTicks
			MAX-ACCESS read-only
			STATUS current
			DESCRIPTION
				"The time stamp of the last command(end of command)."
			::= { sleBFDBaseControl 4 }


		sleBFDControlReqResult OBJECT-TYPE
			SYNTAX SleControlRequestResultType
			MAX-ACCESS read-only
			STATUS current
			DESCRIPTION
				"The result of the last user command."
			::= { sleBFDBaseControl 5 }


		sleBFDControlEnable OBJECT-TYPE
			SYNTAX INTEGER
				{
				disable(0),
				enable(1)
				}
			MAX-ACCESS read-write
			STATUS current
			DESCRIPTION
				"BFD fast-detect is enabled or disabled."
			::= { sleBFDBaseControl 6 }


		sleBFDControlEchoEnable OBJECT-TYPE
			SYNTAX INTEGER
				{
				disable(0),
				enable(1)
				}
			MAX-ACCESS read-write
			STATUS current
			DESCRIPTION
				"BFD Echo function is enabled or disabled."
			::= { sleBFDBaseControl 7 }


		sleBFDControlSlowTimer OBJECT-TYPE
			SYNTAX INTEGER (1000..30000)
			MAX-ACCESS read-write
			STATUS current
			DESCRIPTION
				"BFD Slow Timer in unit of milliseconds
				default: 1000(ms)"
			::= { sleBFDBaseControl 8 }


		sleBFDBaseNotification OBJECT IDENTIFIER ::= { sleBFDBase 3 }


		sleBFDBaseProfileChanged NOTIFICATION-TYPE
			OBJECTS { sleBFDControlRequest, sleBFDControlReqResult, sleBFDControlTimeStamp, sleBFDEnable, sleBFDEchoEnable,
				sleBFDSlowTimer }
			STATUS current
			DESCRIPTION
				"Description."
			::= { sleBFDBaseNotification 1 }


		sleBFDInterface OBJECT IDENTIFIER ::= { sleBFD 2 }


		sleBFDInterfaceTable OBJECT-TYPE
			SYNTAX SEQUENCE OF SleBFDInterfaceEntry
			MAX-ACCESS not-accessible
			STATUS current
			DESCRIPTION
				"Description."
			::= { sleBFDInterface 1 }


		sleBFDInterfaceEntry OBJECT-TYPE
			SYNTAX SleBFDInterfaceEntry
			MAX-ACCESS not-accessible
			STATUS current
			DESCRIPTION
				"Description."
			INDEX { sleNetIfIndex }
			::= { sleBFDInterfaceTable 1 }


		SleBFDInterfaceEntry ::=
			SEQUENCE {
				sleBFDIfRxInterval
					INTEGER,
				sleBFDIfTxInterval
					INTEGER,
				sleBFDIfDetectMulti
					INTEGER,
				sleBFDIfRxIntervalIPv6
					Integer32,
				sleBFDIfTxIntervalIJPv6
					Integer32,
				sleBFDIfDetectMultiIPv6
					Integer32
			 }

		sleBFDIfRxInterval OBJECT-TYPE
			SYNTAX INTEGER (50..10000)
			MAX-ACCESS read-only
			STATUS current
			DESCRIPTION
				"Required Min Rx Interval of BFD control packet in this interface.
				default: 50(ms)"
			::= { sleBFDInterfaceEntry 1 }


		sleBFDIfTxInterval OBJECT-TYPE
			SYNTAX INTEGER (50..10000)
			MAX-ACCESS read-only
			STATUS current
			DESCRIPTION
				"Required Min Tx Interval of BFD control packet in this interface.
				default: 50(ms)"
			::= { sleBFDInterfaceEntry 2 }


		sleBFDIfDetectMulti OBJECT-TYPE
			SYNTAX INTEGER (3..255)
			MAX-ACCESS read-only
			STATUS current
			DESCRIPTION
				"Detect Multi value of BFD control packet in this interface.
				default: 3"
			::= { sleBFDInterfaceEntry 3 }


		sleBFDIfRxIntervalIPv6 OBJECT-TYPE
			SYNTAX Integer32 (50..1000)
			MAX-ACCESS read-only
			STATUS current
			DESCRIPTION
				"Required Min Rx Interval of IPv6 BFD control packet in this interface.
				default: 50(ms)
				"
			::= { sleBFDInterfaceEntry 4 }


		sleBFDIfTxIntervalIJPv6 OBJECT-TYPE
			SYNTAX Integer32 (50..1000)
			MAX-ACCESS read-only
			STATUS current
			DESCRIPTION
				"Required Min Tx Interval of IPv6 BFD control packet in this interface.
				default: 50(ms)
				"
			::= { sleBFDInterfaceEntry 5 }


		sleBFDIfDetectMultiIPv6 OBJECT-TYPE
			SYNTAX Integer32 (3..50)
			MAX-ACCESS read-only
			STATUS current
			DESCRIPTION
				"Detect Multi value of IPv6 BFD control packet in this interface.
				default: 3
				"
			::= { sleBFDInterfaceEntry 6 }


		sleBFDInterfaceControl OBJECT IDENTIFIER ::= { sleBFDInterface 2 }


		sleBFDIfControlRequest OBJECT-TYPE
			SYNTAX INTEGER { setBFDIfProfile(1) }
			MAX-ACCESS read-write
			STATUS current
			DESCRIPTION
				"The request of a user command"
			::= { sleBFDInterfaceControl 1 }


		sleBFDIfControlStatus OBJECT-TYPE
			SYNTAX SleControlStatusType
			MAX-ACCESS read-only
			STATUS current
			DESCRIPTION
				"The status of user command."
			::= { sleBFDInterfaceControl 2 }


		sleBFDIfControlTimer OBJECT-TYPE
			SYNTAX Gauge32
			MAX-ACCESS read-write
			STATUS current
			DESCRIPTION
				"The maximum time for the manager for a long running user command."
			::= { sleBFDInterfaceControl 3 }


		sleBFDIfControlTimeStamp OBJECT-TYPE
			SYNTAX TimeTicks
			MAX-ACCESS read-only
			STATUS current
			DESCRIPTION
				"The time stamp of the last command(end of command)."
			::= { sleBFDInterfaceControl 4 }


		sleBFDIfControlReqResult OBJECT-TYPE
			SYNTAX SleControlRequestResultType
			MAX-ACCESS read-only
			STATUS current
			DESCRIPTION
				"The result of the last user command."
			::= { sleBFDInterfaceControl 5 }


		sleBFDIfControlNetIfIndex OBJECT-TYPE
			SYNTAX Integer32 (0..4097)
			MAX-ACCESS read-write
			STATUS current
			DESCRIPTION
				"BFD Interface Index."
			::= { sleBFDInterfaceControl 6 }


		sleBFDIfControlRxInterval OBJECT-TYPE
			SYNTAX INTEGER (50..10000)
			MAX-ACCESS read-write
			STATUS current
			DESCRIPTION
				"Required Min Rx Interval of BFD control packet in this interface.
				default: 50(ms)"
			::= { sleBFDInterfaceControl 7 }


		sleBFDIfControlTxInterval OBJECT-TYPE
			SYNTAX INTEGER (50..10000)
			MAX-ACCESS read-write
			STATUS current
			DESCRIPTION
				"Required Min Tx Interval of BFD control packet in this interface.
				default: 50(ms)"
			::= { sleBFDInterfaceControl 8 }


		sleBFDIfControlDetectMulti OBJECT-TYPE
			SYNTAX INTEGER (3..255)
			MAX-ACCESS read-write
			STATUS current
			DESCRIPTION
				"Detect Multi value of BFD control packet in this interface.
				default: 3"
			::= { sleBFDInterfaceControl 9 }


		sleBFDIfControlRxIntervalIPv6 OBJECT-TYPE
			SYNTAX Integer32 (50..1000)
			MAX-ACCESS read-write
			STATUS current
			DESCRIPTION
				"Required Min Rx Interval of IPv6 BFD control packet in this interface.
				default: 50(ms)
				"
			::= { sleBFDInterfaceControl 10 }


		sleBFDIfControlTxIntervalIPv6 OBJECT-TYPE
			SYNTAX Integer32 (50..1000)
			MAX-ACCESS read-write
			STATUS current
			DESCRIPTION
				"Required Min Tx Interval of IPv6 BFD control packet in this interface.
				default: 50(ms)
				"
			::= { sleBFDInterfaceControl 11 }


		sleBFDIfControlDetectMultiIPv6 OBJECT-TYPE
			SYNTAX Integer32 (3..50)
			MAX-ACCESS read-write
			STATUS current
			DESCRIPTION
				"Detect Multi value of IPv6 BFD control packet in this interface.
				default: 3
				"
			::= { sleBFDInterfaceControl 12 }


		sleBFDInterfaceNotification OBJECT IDENTIFIER ::= { sleBFDInterface 3 }


		sleBFDIfProfileChanged NOTIFICATION-TYPE
			OBJECTS { sleBFDIfControlRequest, sleBFDIfControlTimeStamp, sleBFDIfControlRxIntervalIPv6, sleBFDIfControlTxIntervalIPv6, sleBFDIfControlDetectMultiIPv6,
				sleBFDIfControlReqResult, sleBFDIfRxInterval, sleBFDIfTxInterval, sleBFDIfDetectMulti }
			STATUS current
			DESCRIPTION
				"Description."
			::= { sleBFDInterfaceNotification 1 }


		sleBFDSession OBJECT IDENTIFIER ::= { sleBFD 3 }


		sleBFDSessionInfo OBJECT IDENTIFIER ::= { sleBFDSession 1 }


		sleBFDSessionInfoTable OBJECT-TYPE
			SYNTAX SEQUENCE OF SleBFDSessionInfoEntry
			MAX-ACCESS not-accessible
			STATUS current
			DESCRIPTION
				"Description."
			::= { sleBFDSessionInfo 1 }


		sleBFDSessionInfoEntry OBJECT-TYPE
			SYNTAX SleBFDSessionInfoEntry
			MAX-ACCESS not-accessible
			STATUS current
			DESCRIPTION
				"Description."
			INDEX { sleNetIfIndex, sleBFDSessionNeighAddrType, sleBFDSessionNeighAddrValue }
			::= { sleBFDSessionInfoTable 1 }


		SleBFDSessionInfoEntry ::=
			SEQUENCE {
				sleBFDSessionNeighAddrType
					InetAddressType,
				sleBFDSessionNeighAddrValue
					InetAddress,
				sleBFDSessionRegProtocols
					BITS,
				sleBFDSessionLocalDiscr
					Unsigned32,
				sleBFDSessionRemoteDiscr
					Unsigned32,
				sleBFDSessionDetecMultiplier
					INTEGER,
				sleBFDSessionStatus
					INTEGER,
				sleBFDSessionEchoUsage
					INTEGER,
				sleBFDSessionUptime
					TimeTicks
			 }

		sleBFDSessionNeighAddrType OBJECT-TYPE
			SYNTAX InetAddressType
			MAX-ACCESS read-only
			STATUS current
			DESCRIPTION
				"Type of Neighbor Address referred to this session"
			::= { sleBFDSessionInfoEntry 1 }


		sleBFDSessionNeighAddrValue OBJECT-TYPE
			SYNTAX InetAddress
			MAX-ACCESS read-only
			STATUS current
			DESCRIPTION
				"Value of Neighbor Address referred to this session."
			::= { sleBFDSessionInfoEntry 2 }


		sleBFDSessionRegProtocols OBJECT-TYPE
			SYNTAX BITS
				{
				ospfv2(0),
				ospfv3(1),
				vrrp4(2),
				vrrp6(3),
				staticroute4(4),
				staticroute6(5),
				bgp(6)
				}
			MAX-ACCESS read-only
			STATUS current
			DESCRIPTION
				"Value of Neighbor Address referred to this session."
			::= { sleBFDSessionInfoEntry 3 }


		sleBFDSessionLocalDiscr OBJECT-TYPE
			SYNTAX Unsigned32
			MAX-ACCESS read-only
			STATUS current
			DESCRIPTION
				"Discriminator of this session."
			::= { sleBFDSessionInfoEntry 4 }


		sleBFDSessionRemoteDiscr OBJECT-TYPE
			SYNTAX Unsigned32
			MAX-ACCESS read-only
			STATUS current
			DESCRIPTION
				"Discriminator of remote session neighboring this session."
			::= { sleBFDSessionInfoEntry 5 }


		sleBFDSessionDetecMultiplier OBJECT-TYPE
			SYNTAX INTEGER (1..63)
			MAX-ACCESS read-only
			STATUS current
			DESCRIPTION
				"Detect Multiplier value which this session used.
				default: 3"
			::= { sleBFDSessionInfoEntry 6 }


		sleBFDSessionStatus OBJECT-TYPE
			SYNTAX INTEGER
				{
				adminDown(0),
				down(1),
				init(2),
				up(3),
				disabled(4)
				}
			MAX-ACCESS read-only
			STATUS current
			DESCRIPTION
				"Status of this session.
				AdminDown(0) is same as disabled(4)."
			::= { sleBFDSessionInfoEntry 7 }


		sleBFDSessionEchoUsage OBJECT-TYPE
			SYNTAX INTEGER
				{
				notUsing(0),
				using(1)
				}
			MAX-ACCESS read-only
			STATUS current
			DESCRIPTION
				"Determine whether this session use or not echo function."
			::= { sleBFDSessionInfoEntry 8 }


		sleBFDSessionUptime OBJECT-TYPE
			SYNTAX TimeTicks
			MAX-ACCESS read-only
			STATUS current
			DESCRIPTION
				"The time since this session’s status changed into ‘Up’."
			::= { sleBFDSessionInfoEntry 9 }


		sleBFDSessionStats OBJECT IDENTIFIER ::= { sleBFDSession 2 }


		sleBFDSessionStatsTable OBJECT-TYPE
			SYNTAX SEQUENCE OF SleBFDSessionStatsEntry
			MAX-ACCESS not-accessible
			STATUS current
			DESCRIPTION
				"Description."
			::= { sleBFDSessionStats 1 }


		sleBFDSessionStatsEntry OBJECT-TYPE
			SYNTAX SleBFDSessionStatsEntry
			MAX-ACCESS not-accessible
			STATUS current
			DESCRIPTION
				"Description."
			INDEX { sleNetIfIndex, sleBFDSessionNeighAddrType, sleBFDSessionNeighAddrValue }
			::= { sleBFDSessionStatsTable 1 }


		SleBFDSessionStatsEntry ::=
			SEQUENCE {
				sleBFDSessionStatsHolddownTime
					Unsigned32,
				sleBFDSessionStatsHolddownExpires
					Unsigned32,
				sleBFDSessionStatsHolddownHitCount
					Unsigned32,
				sleBFDSessionStatsHelloTime
					Unsigned32,
				sleBFDSessionStatsHelloHitCount
					Unsigned32,
				sleBFDSessionStatsRxCount
					Unsigned32,
				sleBFDSessionStatsRxAvgInterval
					Unsigned32,
				sleBFDSessionStatsRxMinInterval
					Unsigned32,
				sleBFDSessionStatsRxMaxInterval
					Unsigned32,
				sleBFDSessionStatsTxCount
					Unsigned32,
				sleBFDSessionStatsTxAvgInterval
					Unsigned32,
				sleBFDSessionStatsTxMinInterval
					Unsigned32,
				sleBFDSessionStatsTxMaxInterval
					Unsigned32,
				sleBFDSessionStatsEchoRxCount
					Unsigned32,
				sleBFDSessionStatsEchoRxAvgInterval
					Unsigned32,
				sleBFDSessionStatsEchoRxMinInterval
					Unsigned32,
				sleBFDSessionStatsEchoRxMaxInterval
					Unsigned32,
				sleBFDSessionStatsEchoTxCount
					Unsigned32,
				sleBFDSessionStatsEchoTxAvgInterval
					Unsigned32,
				sleBFDSessionStatsEchoTxMinInterva
					Unsigned32,
				sleBFDSessionStatsEchoTxMaxInterval
					Unsigned32
			 }

		sleBFDSessionStatsHolddownTime OBJECT-TYPE
			SYNTAX Unsigned32
			MAX-ACCESS read-only
			STATUS current
			DESCRIPTION
				"Type of Neighbor Address referred to this session."
			::= { sleBFDSessionStatsEntry 1 }


		sleBFDSessionStatsHolddownExpires OBJECT-TYPE
			SYNTAX Unsigned32
			MAX-ACCESS read-only
			STATUS current
			DESCRIPTION
				"The time remaining before this entry change into down status without receiving hello in unit of milliseconds."
			::= { sleBFDSessionStatsEntry 2 }


		sleBFDSessionStatsHolddownHitCount OBJECT-TYPE
			SYNTAX Unsigned32
			MAX-ACCESS read-only
			STATUS current
			DESCRIPTION
				"Hit Count whose this session status chang into down."
			::= { sleBFDSessionStatsEntry 3 }


		sleBFDSessionStatsHelloTime OBJECT-TYPE
			SYNTAX Unsigned32
			MAX-ACCESS read-only
			STATUS current
			DESCRIPTION
				"The time is when it expects next hello, after receiving that in unit of milliseconds."
			::= { sleBFDSessionStatsEntry 4 }


		sleBFDSessionStatsHelloHitCount OBJECT-TYPE
			SYNTAX Unsigned32
			MAX-ACCESS read-only
			STATUS current
			DESCRIPTION
				"Hit Count whose this session received."
			::= { sleBFDSessionStatsEntry 5 }


		sleBFDSessionStatsRxCount OBJECT-TYPE
			SYNTAX Unsigned32
			MAX-ACCESS read-only
			STATUS current
			DESCRIPTION
				"Hit Count whose this session received control packet."
			::= { sleBFDSessionStatsEntry 6 }


		sleBFDSessionStatsRxAvgInterval OBJECT-TYPE
			SYNTAX Unsigned32
			MAX-ACCESS read-only
			STATUS current
			DESCRIPTION
				"Average interval whose this session received control packet."
			::= { sleBFDSessionStatsEntry 7 }


		sleBFDSessionStatsRxMinInterval OBJECT-TYPE
			SYNTAX Unsigned32
			MAX-ACCESS read-only
			STATUS current
			DESCRIPTION
				"Minimum interval whose this session received control packet."
			::= { sleBFDSessionStatsEntry 8 }


		sleBFDSessionStatsRxMaxInterval OBJECT-TYPE
			SYNTAX Unsigned32
			MAX-ACCESS read-only
			STATUS current
			DESCRIPTION
				"Maximum interval whose this session received control packet."
			::= { sleBFDSessionStatsEntry 9 }


		sleBFDSessionStatsTxCount OBJECT-TYPE
			SYNTAX Unsigned32
			MAX-ACCESS read-only
			STATUS current
			DESCRIPTION
				"Hit Count whose this session send control packet."
			::= { sleBFDSessionStatsEntry 10 }


		sleBFDSessionStatsTxAvgInterval OBJECT-TYPE
			SYNTAX Unsigned32
			MAX-ACCESS read-only
			STATUS current
			DESCRIPTION
				"Average interval whose this session sent control packet."
			::= { sleBFDSessionStatsEntry 11 }


		sleBFDSessionStatsTxMinInterval OBJECT-TYPE
			SYNTAX Unsigned32
			MAX-ACCESS read-only
			STATUS current
			DESCRIPTION
				"Minimum interval whose this session sent control packet."
			::= { sleBFDSessionStatsEntry 12 }


		sleBFDSessionStatsTxMaxInterval OBJECT-TYPE
			SYNTAX Unsigned32
			MAX-ACCESS read-only
			STATUS current
			DESCRIPTION
				"Maximum interval whose this session received control packet."
			::= { sleBFDSessionStatsEntry 13 }


		sleBFDSessionStatsEchoRxCount OBJECT-TYPE
			SYNTAX Unsigned32
			MAX-ACCESS read-only
			STATUS current
			DESCRIPTION
				"Hit Count whose this session received echo packet"
			::= { sleBFDSessionStatsEntry 14 }


		sleBFDSessionStatsEchoRxAvgInterval OBJECT-TYPE
			SYNTAX Unsigned32
			MAX-ACCESS read-only
			STATUS current
			DESCRIPTION
				"Average interval whose this session received echo packet"
			::= { sleBFDSessionStatsEntry 15 }


		sleBFDSessionStatsEchoRxMinInterval OBJECT-TYPE
			SYNTAX Unsigned32
			MAX-ACCESS read-only
			STATUS current
			DESCRIPTION
				"Minimum interval whose this session received echo packet"
			::= { sleBFDSessionStatsEntry 16 }


		sleBFDSessionStatsEchoRxMaxInterval OBJECT-TYPE
			SYNTAX Unsigned32
			MAX-ACCESS read-only
			STATUS current
			DESCRIPTION
				"Maximum interval whose this session received echo packet"
			::= { sleBFDSessionStatsEntry 17 }


		sleBFDSessionStatsEchoTxCount OBJECT-TYPE
			SYNTAX Unsigned32
			MAX-ACCESS read-only
			STATUS current
			DESCRIPTION
				"Hit Count whose this session send echo packet
				"
			::= { sleBFDSessionStatsEntry 18 }


		sleBFDSessionStatsEchoTxAvgInterval OBJECT-TYPE
			SYNTAX Unsigned32
			MAX-ACCESS read-only
			STATUS current
			DESCRIPTION
				"Average interval whose this session sent echo packet."
			::= { sleBFDSessionStatsEntry 19 }


		sleBFDSessionStatsEchoTxMinInterva OBJECT-TYPE
			SYNTAX Unsigned32
			MAX-ACCESS read-only
			STATUS current
			DESCRIPTION
				"Minimum interval whose this session sent echo packet."
			::= { sleBFDSessionStatsEntry 20 }


		sleBFDSessionStatsEchoTxMaxInterval OBJECT-TYPE
			SYNTAX Unsigned32
			MAX-ACCESS read-only
			STATUS current
			DESCRIPTION
				"Maximum interval whose this session received echo packet."
			::= { sleBFDSessionStatsEntry 21 }


		sleBFDSessionLocal OBJECT IDENTIFIER ::= { sleBFDSession 3 }


		sleBFDSessionLocalTable OBJECT-TYPE
			SYNTAX SEQUENCE OF SleBFDSessionLocalEntry
			MAX-ACCESS not-accessible
			STATUS current
			DESCRIPTION
				"Description."
			::= { sleBFDSessionLocal 1 }


		sleBFDSessionLocalEntry OBJECT-TYPE
			SYNTAX SleBFDSessionLocalEntry
			MAX-ACCESS not-accessible
			STATUS current
			DESCRIPTION
				"Description."
			INDEX { sleNetIfIndex, sleBFDSessionNeighAddrType, sleBFDSessionNeighAddrValue }
			::= { sleBFDSessionLocalTable 1 }


		SleBFDSessionLocalEntry ::=
			SEQUENCE {
				sleBFDSessionLocalDiag
					INTEGER,
				sleBFDSessionLocalState
					INTEGER,
				sleBFDSessionLocalFlags
					BITS,
				sleBFDSessionLocalMultiplier
					INTEGER,
				sleBFDSessionLocalMinTxInterval
					Unsigned32,
				sleBFDSessionLocalMinRxInterval
					Unsigned32,
				sleBFDSessionLocalMinEchoInterval
					Unsigned32
			 }

		sleBFDSessionLocalDiag OBJECT-TYPE
			SYNTAX INTEGER
				{
				noDiag(0),
				detectExpired(1),
				echoFailed(2),
				neighDownAlarm(3),
				fwdPlaneReset(4),
				pathDown(5),
				concatPathDown(6),
				adminDown(7),
				reverseConcatDown(8),
				reserved(9)
				}
			MAX-ACCESS read-only
			STATUS current
			DESCRIPTION
				"Value of State field of this session’s control packet."
			::= { sleBFDSessionLocalEntry 1 }


		sleBFDSessionLocalState OBJECT-TYPE
			SYNTAX INTEGER
				{
				adminDown(0),
				donw(1),
				init(2),
				up(3)
				}
			MAX-ACCESS read-only
			STATUS current
			DESCRIPTION
				"Value of Diag field of this session’s control packet"
			::= { sleBFDSessionLocalEntry 2 }


		sleBFDSessionLocalFlags OBJECT-TYPE
			SYNTAX BITS
				{
				poll(0),
				final(1),
				controlIndependent(2),
				authPresent(3),
				demand(4),
				multipoint(5)
				}
			MAX-ACCESS read-only
			STATUS current
			DESCRIPTION
				"Value of Flags field of this session’s control packet."
			::= { sleBFDSessionLocalEntry 3 }


		sleBFDSessionLocalMultiplier OBJECT-TYPE
			SYNTAX INTEGER (1..63)
			MAX-ACCESS read-only
			STATUS current
			DESCRIPTION
				"Value of MinTxInterval field of this session’s control packet in unit of microseconds."
			::= { sleBFDSessionLocalEntry 4 }


		sleBFDSessionLocalMinTxInterval OBJECT-TYPE
			SYNTAX Unsigned32
			MAX-ACCESS read-only
			STATUS current
			DESCRIPTION
				"Value of MinTxInterval field of this session’s control packet in unit of microseconds."
			::= { sleBFDSessionLocalEntry 5 }


		sleBFDSessionLocalMinRxInterval OBJECT-TYPE
			SYNTAX Unsigned32
			MAX-ACCESS read-only
			STATUS current
			DESCRIPTION
				"Value of MinRxInterval field of this session’s control packet in unit of microseconds."
			::= { sleBFDSessionLocalEntry 6 }


		sleBFDSessionLocalMinEchoInterval OBJECT-TYPE
			SYNTAX Unsigned32
			MAX-ACCESS read-only
			STATUS current
			DESCRIPTION
				"Value of MinEchoInterval field of this session’s control packet in unit of microseconds."
			::= { sleBFDSessionLocalEntry 7 }


		sleBFDSessionRemote OBJECT IDENTIFIER ::= { sleBFDSession 4 }


		sleBFDSessionRemoteTable OBJECT-TYPE
			SYNTAX SEQUENCE OF SleBFDSessionRemoteEntry
			MAX-ACCESS not-accessible
			STATUS current
			DESCRIPTION
				"Description."
			::= { sleBFDSessionRemote 1 }


		sleBFDSessionRemoteEntry OBJECT-TYPE
			SYNTAX SleBFDSessionRemoteEntry
			MAX-ACCESS not-accessible
			STATUS current
			DESCRIPTION
				"Description."
			INDEX { sleNetIfIndex, sleBFDSessionNeighAddrType, sleBFDSessionNeighAddrValue }
			::= { sleBFDSessionRemoteTable 1 }


		SleBFDSessionRemoteEntry ::=
			SEQUENCE {
				sleBFDSessionRemoteDiag
					INTEGER,
				sleBFDSessionRemoteState
					INTEGER,
				sleBFDSessionremoteFlags
					BITS,
				sleBFDSessionRemoteMultiplier
					INTEGER,
				sleBFDSessionRemoteMinTxInterval
					Unsigned32,
				sleBFDSessionRemoteMinRxInterval
					Unsigned32,
				sleBFDSessionRemoteMinEchoInterval
					Unsigned32
			 }

		sleBFDSessionRemoteDiag OBJECT-TYPE
			SYNTAX INTEGER
				{
				noDiag(0),
				detectExpired(1),
				echoFailed(2),
				neighDownAlarm(3),
				fwdPlaneReset(4),
				pathDown(5),
				concatPathDown(6),
				adminDown(7),
				reverseConcatDown(8),
				reserved(9)
				}
			MAX-ACCESS read-only
			STATUS current
			DESCRIPTION
				"Value of State field of remote session’s control packet."
			::= { sleBFDSessionRemoteEntry 1 }


		sleBFDSessionRemoteState OBJECT-TYPE
			SYNTAX INTEGER
				{
				adminDown(0),
				donw(1),
				init(2),
				up(3)
				}
			MAX-ACCESS read-only
			STATUS current
			DESCRIPTION
				"Value of Diag field of remote session’s control packet"
			::= { sleBFDSessionRemoteEntry 2 }


		sleBFDSessionremoteFlags OBJECT-TYPE
			SYNTAX BITS
				{
				poll(0),
				final(1),
				controlIndependent(2),
				authPresent(3),
				demand(4),
				multipoint(5)
				}
			MAX-ACCESS read-only
			STATUS current
			DESCRIPTION
				"Value of Flags field of remote session’s control packet."
			::= { sleBFDSessionRemoteEntry 3 }


		sleBFDSessionRemoteMultiplier OBJECT-TYPE
			SYNTAX INTEGER (1..63)
			MAX-ACCESS read-only
			STATUS current
			DESCRIPTION
				"Value of MinTxInterval field of this session’s control packet in unit of microseconds."
			::= { sleBFDSessionRemoteEntry 4 }


		sleBFDSessionRemoteMinTxInterval OBJECT-TYPE
			SYNTAX Unsigned32
			MAX-ACCESS read-only
			STATUS current
			DESCRIPTION
				"Value of MinTxInterval field of remote session’s control packet in unit of microseconds."
			::= { sleBFDSessionRemoteEntry 5 }


		sleBFDSessionRemoteMinRxInterval OBJECT-TYPE
			SYNTAX Unsigned32
			MAX-ACCESS read-only
			STATUS current
			DESCRIPTION
				"Value of MinRxInterval field of remote session’s control packet in unit of microseconds."
			::= { sleBFDSessionRemoteEntry 6 }


		sleBFDSessionRemoteMinEchoInterval OBJECT-TYPE
			SYNTAX Unsigned32
			MAX-ACCESS read-only
			STATUS current
			DESCRIPTION
				"Value of MinEchoInterval field of remote session’s control packet in unit of microseconds."
			::= { sleBFDSessionRemoteEntry 7 }


		sleBFDStaticGw OBJECT IDENTIFIER ::= { sleBFD 4 }


		sleBFDStaticGwTable OBJECT-TYPE
			SYNTAX SEQUENCE OF SleBFDStaticGwEntry
			MAX-ACCESS not-accessible
			STATUS current
			DESCRIPTION
				"Description."
			::= { sleBFDStaticGw 1 }


		sleBFDStaticGwEntry OBJECT-TYPE
			SYNTAX SleBFDStaticGwEntry
			MAX-ACCESS not-accessible
			STATUS current
			DESCRIPTION
				"Description."
			INDEX { sleNetIfIndex, sleBFDStaticGwAddrType, sleBFDStaticGwAddr }
			::= { sleBFDStaticGwTable 1 }


		SleBFDStaticGwEntry ::=
			SEQUENCE {
				sleBFDStaticGwAddrType
					InetAddressType,
				sleBFDStaticGwAddr
					InetAddress
			 }

		sleBFDStaticGwAddrType OBJECT-TYPE
			SYNTAX InetAddressType
			MAX-ACCESS read-write
			STATUS current
			DESCRIPTION
				"The BFD static Gateway address type.  Only ipv4(1)."
			::= { sleBFDStaticGwEntry 1 }


		sleBFDStaticGwAddr OBJECT-TYPE
			SYNTAX InetAddress
			MAX-ACCESS read-write
			STATUS current
			DESCRIPTION
				"The BFD static Gateway address. 4bytes"
			::= { sleBFDStaticGwEntry 2 }


		sleBFDStaticGwControl OBJECT IDENTIFIER ::= { sleBFDStaticGw 2 }


		sleBFDStaticGwControlRequest OBJECT-TYPE
			SYNTAX INTEGER
				{
				addBfdStaticGw(1),
				delBfdStaticGw(2)
				}
			MAX-ACCESS read-write
			STATUS current
			DESCRIPTION
				"Description."
			::= { sleBFDStaticGwControl 1 }


		sleBFDStaticGwControlStatus OBJECT-TYPE
			SYNTAX SleControlStatusType
			MAX-ACCESS read-only
			STATUS current
			DESCRIPTION
				"Description."
			::= { sleBFDStaticGwControl 2 }


		sleBFDStaticGwControlTimer OBJECT-TYPE
			SYNTAX Gauge32
			MAX-ACCESS read-write
			STATUS current
			DESCRIPTION
				"Description."
			::= { sleBFDStaticGwControl 3 }


		sleBFDStaticGwControlTimeStamp OBJECT-TYPE
			SYNTAX TimeTicks
			MAX-ACCESS read-only
			STATUS current
			DESCRIPTION
				"Description."
			::= { sleBFDStaticGwControl 4 }


		sleBFDStaticGwControlReqResult OBJECT-TYPE
			SYNTAX SleControlRequestResultType
			MAX-ACCESS read-only
			STATUS current
			DESCRIPTION
				"Description."
			::= { sleBFDStaticGwControl 5 }


		sleBFDStaticGwControlNetIfIndex OBJECT-TYPE
			SYNTAX Integer32
			MAX-ACCESS read-write
			STATUS current
			DESCRIPTION
				"Description."
			::= { sleBFDStaticGwControl 6 }


		sleBFDStaticGwControlGwAddrType OBJECT-TYPE
			SYNTAX InetAddressType
			MAX-ACCESS read-write
			STATUS current
			DESCRIPTION
				"Description."
			::= { sleBFDStaticGwControl 7 }


		sleBFDStaticGwControlGwAddr OBJECT-TYPE
			SYNTAX InetAddress
			MAX-ACCESS read-write
			STATUS current
			DESCRIPTION
				"Description."
			::= { sleBFDStaticGwControl 8 }


		sleBFDStaticGwNotification OBJECT IDENTIFIER ::= { sleBFDStaticGw 3 }


		sleBFDStaticGwAdded NOTIFICATION-TYPE
			OBJECTS { sleBFDStaticGwControlRequest, sleBFDStaticGwControlTimer, sleBFDStaticGwControlReqResult, sleBFDStaticGwControlNetIfIndex, sleBFDStaticGwControlGwAddr,
				sleBFDStaticGwControlGwAddrType }
			STATUS current
			DESCRIPTION
				"Description."
			::= { sleBFDStaticGwNotification 1 }


		sleBFDStaticGwDeleted NOTIFICATION-TYPE
			OBJECTS { sleBFDStaticGwControlRequest, sleBFDStaticGwControlTimeStamp, sleBFDStaticGwControlReqResult, sleBFDStaticGwControlNetIfIndex, sleBFDStaticGwControlGwAddr,
				sleBFDStaticGwControlGwAddrType }
			STATUS current
			DESCRIPTION
				"Description."
			::= { sleBFDStaticGwNotification 2 }


		sleNetworkGroup OBJECT-GROUP
			OBJECTS { sleNetIfIndex, sleNetIfName, sleNetIfDescription, sleNetIfTableIndex, sleNetIfAdminState,
				sleNetIfOperState, sleNetIfMulticast, sleNetIfControlRequest, sleNetIfControlStatus, sleNetIfControlTimer,
				sleNetIfControlTimeStamp, sleNetIfControlReqResult, sleNetIfControlIndex, sleNetIfControlDescription, sleNetIfControlAdminState,
				sleNetIfControlMulticast, sleIpAddrValue, sleIpAddrMask, sleIpAddrBcast, sleIpAddrControlRequest,
				sleIpAddrControlStatus, sleIpAddrControlTimer, sleIpAddrControlTimeStamp, sleIpAddrControlReqResult, sleIpAddrControlNetIfIndex,
				sleIpAddrControlValue, sleIpAddrControlMask, sleArpIpAddress, sleArpPhyAddress, sleArpPortIndex,
				sleArpHwType, sleArpControlRequest, sleArpControlStatus, sleArpControlTimer, sleArpControlTimeStamp,
				sleArpControlReqResult, sleArpControlIpAddress, sleArpControlPhyAddress, sleRouteDstAddress, sleRouteDstMask,
				sleRouteGateway, sleRouteInterface, sleRouteType, sleRouteProto, sleRouteMetric,
				sleRouteActive, sleRouteBindingSrcAddr, sleRouteDistance, sleRouteControlRequest, sleRouteControlStatus,
				sleRouteControlTimer, sleRouteControlTimeStamp, sleRouteControlReqResult, sleRouteControlDstAddress, sleRouteControlDstMask,
				sleRouteControlGateway, sleRouteControlInterface, sleRouteControlBindingSrcAddr, sleRouteControlDistance, sleDhcpClIpAddr,
				sleDhcpClState, sleDhcpClControlRequest, sleDhcpClControlStatus, sleDhcpClControlTimer, sleDhcpClControlTimeStamp,
				sleDhcpClControlReqResult, sleDhcpClControlUpdateIP, sleNetIfRegState, sleNetIfMtu, sleNetIfIpSetMode,
				sleNetIfIpMartianFilter, sleNetIfControlRegState, sleNetIfControlMtu, sleNetIfControlIpMartianFilter, sleIpAddrFlag,
				sleIpAddrScope, sleIpAddrControlFlag, sleIpAddrControlScope, sleArpState, sleArpHwUsed,
				sleArpUsedTime, sleArpControlNetIfIndex, sleArpControlState, sleArpControlMask, sleRouteSubtype,
				sleRouteNexthopStatus, sleRouteRibStatus, sleNetworkArpAgingTime, sleNetworkControlRequest, sleNetworkControlStatus,
				sleNetworkControlTimer, sleNetworkControlReqResult, sleNetworkControlTimeStamp, sleNetworkControlArpAgingTime, sleNetIfUpCnt,
				sleNetIfDownCnt, sleNetIfLinkUpTime, sleNetIfElapsedTimeAfterClearStats, sleNetIfBindingVRFName, sleNetIfControlBindingVRFName,
				sleRouteVRFIndex, sleRouteControlVRFIndex, sleTunnelIfIndex, sleTunnelIfLocalAddress, sleTunnelIfRemoteAddress,
				sleTunnelIfMode, sleTunnelIfTTL, sleTunnelIfDscpMode, sleTunnelIfDscp, sleTunnelIfKeepaliveInterval,
				sleTunnelIfKeepaliveRetry, sleTunnelIfControlRequest, sleTunnelIfControlStatus, sleTunnelIfControlTimer, sleTunnelIfControlTimeStamp,
				sleTunnelIfControlReqResult, sleTunnelIfControlIndex, sleTunnelIfControlLocalAddress, sleTunnelIfControlRemoteAddress, sleTunnelIfControlMode,
				sleTunnelIfControlTTL, sleTunneIflControlDscpMode, sleTunneIflControlDscp, sleTunnelIfControlKeepaliveInterval, sleTunneIflControlKeepaliveRetry,
				sleTunnelAddressValue, sleTunnelAddressMask, sleTunnelIpAddrBcast, sleTunnelAddressFlag, sleTunnelAddressScope,
				sleTunnelAddressControlRequest, sleTunnelAddressControlStatus, sleTunnelAddressControlTimer, sleTunnelAddressControlTimeStamp, sleTunnelAddressControlReqResult,
				sleTunnelAddressControlTunnelIfIndex, sleTunnelAddressControlValue, sleTunnelAddressControlMask, sleTunnelAddressControlFlag, sleTunnelAddressControlScope,
				sleIpVRFIndex, sleIpVRFName, sleIpVRFControlRequest, sleIpVRFControlStatus, sleIpVRFControlTimer,
				sleIpVRFControlTimeStamp, sleIpVRFControlReqResult, sleIpVRFControlName, sleNetIfOnFailUseVRF, sleNetIfControlOnFailUseVRF,
				sleTunnelIfPathMtuDiscovery, sleTunnelIfVRFName, sleTunnelIfBindingPorts, sleTunnelIfControlPathMtuDiscovery, sleTunnelIfControlVRFName,
				sleIpVRFDesignatedPorts, sleIpVRFControlDesignatedPorts, sleIpVRFSelectionSrcIndex, sleIpVRFSelectionSrcAddr, sleIpVRFSelectionSrcMask,
				sleIpVRFSelectionSrcVRFName, sleIpVRFSelectionSrcControlRequest, sleIpVRFSelectionSrcControlStatus, sleIpVRFSelectionSrcControlTimer, sleIpVRFSelectionSrcControlTimeStamp,
				sleIpVRFSelectionSrcControlReqResult, sleIpVRFSelectionSrcControlAddr, sleIpVRFSelectionSrcControlMask, sleIpVRFSelectionSrcControlVRFName, sleNetIfIpUnreachability,
				sleNetIfControlIpUnreachability, sleIpVRFRouterId, sleIpVRFDescription, sleIpVRFControlRouterId, sleIpVRFControlDescription,
				sleBFDEnable, sleBFDEchoEnable, sleBFDSlowTimer, sleBFDControlRequest, sleBFDControlStatus,
				sleBFDControlTimer, sleBFDControlTimeStamp, sleBFDControlReqResult, sleBFDControlEnable, sleBFDControlEchoEnable,
				sleBFDControlSlowTimer, sleBFDIfRxInterval, sleBFDIfTxInterval, sleBFDIfDetectMulti, sleBFDIfControlRequest,
				sleBFDIfControlStatus, sleBFDIfControlTimer, sleBFDIfControlTimeStamp, sleBFDIfControlReqResult, sleBFDIfControlNetIfIndex,
				sleBFDIfControlRxInterval, sleBFDIfControlTxInterval, sleBFDIfControlDetectMulti, sleBFDSessionNeighAddrType, sleBFDSessionNeighAddrValue,
				sleBFDSessionRegProtocols, sleBFDSessionLocalDiscr, sleBFDSessionRemoteDiscr, sleBFDSessionDetecMultiplier, sleBFDSessionStatus,
				sleBFDSessionEchoUsage, sleBFDSessionUptime, sleBFDSessionStatsHolddownTime, sleBFDSessionStatsHolddownExpires, sleBFDSessionStatsHolddownHitCount,
				sleBFDSessionStatsHelloTime, sleBFDSessionStatsHelloHitCount, sleBFDSessionStatsRxCount, sleBFDSessionStatsRxAvgInterval, sleBFDSessionStatsRxMinInterval,
				sleBFDSessionStatsRxMaxInterval, sleBFDSessionStatsTxCount, sleBFDSessionStatsTxAvgInterval, sleBFDSessionStatsTxMinInterval, sleBFDSessionStatsTxMaxInterval,
				sleBFDSessionLocalDiag, sleBFDSessionLocalState, sleBFDSessionLocalFlags, sleBFDSessionLocalMultiplier, sleBFDSessionLocalMinTxInterval,
				sleBFDSessionLocalMinRxInterval, sleBFDSessionLocalMinEchoInterval, sleBFDSessionRemoteDiag, sleBFDSessionRemoteState, sleBFDSessionremoteFlags,
				sleBFDSessionRemoteMultiplier, sleBFDSessionRemoteMinTxInterval, sleBFDSessionRemoteMinRxInterval, sleBFDSessionRemoteMinEchoInterval, sleBFDStaticGwAddrType,
				sleBFDStaticGwAddr, sleBFDStaticGwControlRequest, sleBFDStaticGwControlStatus, sleBFDStaticGwControlTimer, sleBFDStaticGwControlTimeStamp,
				sleBFDStaticGwControlReqResult, sleBFDStaticGwControlNetIfIndex, sleBFDStaticGwControlGwAddrType, sleBFDStaticGwControlGwAddr, sleBFDSessionStatsEchoRxCount,
				sleBFDSessionStatsEchoRxAvgInterval, sleBFDSessionStatsEchoRxMinInterval, sleBFDSessionStatsEchoRxMaxInterval, sleBFDSessionStatsEchoTxCount, sleBFDSessionStatsEchoTxAvgInterval,
				sleBFDSessionStatsEchoTxMinInterva, sleBFDSessionStatsEchoTxMaxInterval, sleNetIfipRedirects, sleNetIfControlIpRedirects, sleIpAddrIpIndex,
				sleIpAddrUnnumUsedIp, sleIpAddrControlIpIndex, sleTunnelAddressUnnumIpIndex, sleTunnelAddressControlUnnumIpIndex, sleNetIfIpForwarding,
				sleNetIfControlIpForwarding, sleTunnelIfLocalAddress6, sleTunnelIfRemoteAddress6, sleTunnelIfControlLocalAddress6, sleTunnelIfControlRemoteAddress6,
				sleNetIfAlias, sleNetIfIpArpAlias, sleNetIfIpArpAliasMac, sleNetIfArpMCProbeCount, sleNetIfArpUCProbeCount,
				sleNetIfArpRetransTime, sleNetIfIpProxyArp, sleNetIfIpRPFilter, sleNetIfRPFilter, sleNetIfRouteMap,
				sleNetIfControlAlias, sleNetIfControlIpArpAlias, sleNetIfControlIpArpAliasMac, sleNetIfControlArpMCProbeCount, sleNetIfControlArpUCProbeCount,
				sleNetIfControlArpRetransTime, sleNetIfControlIpProxyArp, sleNetIfControlIpRPFilter, sleNetIfControlRPFilter, sleNetIfControlRouteMap,
				sleBFDIfRxIntervalIPv6, sleBFDIfTxIntervalIJPv6, sleBFDIfDetectMultiIPv6, sleBFDIfControlRxIntervalIPv6, sleBFDIfControlTxIntervalIPv6,
				sleBFDIfControlDetectMultiIPv6, sleTunnelIfControlTos, sleTunnelIfControlDmac, sleTunnelIfControlChecksum, sleTunnelIfTos,
				sleTunnelIfDmac, sleTunnelIfChecksum, sleNetworkBaseVrfDynamicForwardBinding, sleNetworkControlVrfDynamicForwardBinding, sleDhcpClControlNetIfIndex,
				sleDhcpClMode, sleDhcpClNetmask, sleDhcpClGateway, sleDhcpClDnsServer, sleDhcpClServer,
				sleDhcpClClientId, sleDhcpClClientIdStyle, sleDhcpClClassId, sleDhcpClClassIdStyle, sleDhcpClLeasetime,
				sleDhcpClControlMode, sleDhcpClControlClientId, sleDhcpClControlClientIdStyle, sleDhcpClControlClassId, sleDhcpClControlClassIdStyle,
				sleDhcpClControlLeasetime, sleTunnelAddressUnnumIfIndex, sleTunnelAddressControlUnnumIfIndex }
			STATUS current
			DESCRIPTION
				"Description."
			::= { sleNetwork 14 }


		sleNetworkNotificationGroup NOTIFICATION-GROUP
			NOTIFICATIONS { sleNetIfProfileChanged, sleIpAddressCreated, sleIpAddressDestroyed, sleArpEntryCreated, sleArpEntryDestroyed,
				sleArpTableCleared, sleRouteStaticCreated, sleRouteStaticDestroyed, sleRouteStaticProfileChanged, sleDhcpClModeChanged,
				sleDhcpClProfileChanged, sleTunnelIfCreated, sleTunnelIfDeleted, sleTunnelIfLocalAddressChanged, sleTunnelIfRemoteAddressChanged,
				sleTunnelIfModeChanged, sleTunnelIfTTLChanged, sleTunnelIfDscpChanged, sleTunnelIfKeepaliveChanged, sleTunnelAddressCreated,
				sleTunnelAddressDeleted, sleIpVRFCreated, sleIpVRFDeleted, sleDhcpClStateChanged, sleNetIfRegStateChanged,
				sleNetIfIpMartianFilterChanged, sleArpTableClearedByAddr, sleNetworkArpProfileChanged, sleNetIfBindingVRFSet, sleNetIfBindingVRFUnset,
				sleNetIfIpOnFailUseVRFChanged, sleTunnelIfPathMtuDiscoveryChanged, sleIpVRFDesignatedPortsSet, sleIpVRFDesignatedPortsUnset, sleIpVRFSelectionSrcSet,
				sleNetIfIpUnreachabilityChanged, sleIpVRFRouterIdChanged, sleIpVRFDescriptionChanged, sleBFDBaseProfileChanged, sleBFDIfProfileChanged,
				sleBFDStaticGwAdded, sleBFDStaticGwDeleted, sleNetIfIpRedirectsChanged, sleIpAddressIpIndexAdded, sleIpAddressIpIndexDeleted,
				sleTunnelAddressUnnumChanged, sleTunnelAddressUnnumDeleted, sleNetIfIpForwardingChanged, sleTunnelIfLocalAddress6Changed, sleTunnelIfRemoteAddress6Changed,
				sleNetIfAliasChanged, sleNetIfIpArpAliasChanged, sleNetIfArpMCProbeCountChanged, sleNetIfArpUCProbeCountChanged, sleNetIfArpRetransTimeChanged,
				sleNetIfIpProxyArpChanged, sleNetIfIpRPFilterChanged, sleNetIfRPFilterChanged, sleNetIfRouteMapChanged, sleIpVRFSelectionSrcUnset,
				sleTunnelIfVRFNameSet, sleTunnelIfVRFNameUnset }
			STATUS current
			DESCRIPTION
				"Description."
			::= { sleNetwork 15 }



	END

--
-- sle-network-mib.mib
--
