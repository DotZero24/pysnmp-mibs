--
-- sle-bgp-mib.mib
-- MIB generated by MG-SOFT Visual MIB Builder Version 6.0  Build 88
-- Monday, March 23, 2015 at 14:50:25
--

	SLE-BGP-MIB DEFINITIONS ::= BEGIN

		IMPORTS
			sleMgmt
				FROM DASAN-SMI
			SleControlStatusType, SleControlRequestResultType
				FROM SLE-TC-MIB
			OBJECT-GROUP, NOTIFICATION-GROUP
				FROM SNMPv2-CONF
			TimeTicks, IpAddress, Gauge32, OBJECT-TYPE, MODULE-IDENTITY,
			NOTIFICATION-TYPE
				FROM SNMPv2-SMI;


		-- 1.3.6.1.4.1.6296.101.53
		sleBGP MODULE-IDENTITY
			LAST-UPDATED "200412291441Z"		-- December 29, 2004 at 14:41 GMT
			ORGANIZATION
				"HANASOFT"
			CONTACT-INFO
				" "
			DESCRIPTION
				"This MIB contains information about BGP version 2."
			REVISION "201003211954Z"		-- March 21, 2010 at 19:54 GMT
			DESCRIPTION
				"OSFPv2"
			::= { sleMgmt 53 }




--
-- Node definitions
--

		-- 1.3.6.1.4.1.6296.101.53.1
		sleBGPBase OBJECT IDENTIFIER ::= { sleBGP 1 }


		-- 1.3.6.1.4.1.6296.101.53.1.1
		sleBGPBaseInfo OBJECT IDENTIFIER ::= { sleBGPBase 1 }


		-- 1.3.6.1.4.1.6296.101.53.1.1.1
		sleBGPBaseAsNumber OBJECT-TYPE
			SYNTAX Gauge32 (0..4294967295)
			MAX-ACCESS read-only
			STATUS current
			DESCRIPTION
				"Description."
			::= { sleBGPBaseInfo 1 }


		-- 1.3.6.1.4.1.6296.101.53.1.1.2
		sleBGPBaseConfigType OBJECT-TYPE
			SYNTAX INTEGER
				{
				zebos(0),
				standard(1)
				}
			MAX-ACCESS read-only
			STATUS current
			DESCRIPTION
				"Description."
			DEFVAL { 0 }
			::= { sleBGPBaseInfo 2 }


		-- 1.3.6.1.4.1.6296.101.53.1.1.3
		sleBGPBaseRfc1771PathSelect OBJECT-TYPE
			SYNTAX INTEGER
				{
				disable(0),
				enable(1)
				}
			MAX-ACCESS read-only
			STATUS current
			DESCRIPTION
				"Description."
			::= { sleBGPBaseInfo 3 }


		-- 1.3.6.1.4.1.6296.101.53.1.1.4
		sleBGPBaseRfc1771Strict OBJECT-TYPE
			SYNTAX INTEGER
				{
				disable(0),
				enable(1)
				}
			MAX-ACCESS read-only
			STATUS current
			DESCRIPTION
				"Description."
			::= { sleBGPBaseInfo 4 }


		-- 1.3.6.1.4.1.6296.101.53.1.1.5
		sleBGPBaseAggregateNextHop OBJECT-TYPE
			SYNTAX INTEGER
				{
				disable(0),
				enable(1)
				}
			MAX-ACCESS read-only
			STATUS current
			DESCRIPTION
				"Description."
			::= { sleBGPBaseInfo 5 }


		-- 1.3.6.1.4.1.6296.101.53.1.1.6
		sleBGPBaseExtendAsnCap OBJECT-TYPE
			SYNTAX INTEGER
				{
				disable(0),
				enable(1)
				}
			MAX-ACCESS read-only
			STATUS current
			DESCRIPTION
				"Description."
			::= { sleBGPBaseInfo 6 }


		-- 1.3.6.1.4.1.6296.101.53.1.2
		sleBGPBaseControl OBJECT IDENTIFIER ::= { sleBGPBase 2 }


		-- 1.3.6.1.4.1.6296.101.53.1.2.1
		sleBGPBaseControlRequest OBJECT-TYPE
			SYNTAX INTEGER
				{
				createBGPAsNumber(1),
				deleteBGPAsNumber(2),
				setBGPConfigType(3),
				setBGPRfc1771PathSelect(4),
				setBGPRfc1771Strict(5),
				setAggregateNextHop(6),
				setBGPExtendAsnCap(7),
				clearBGPAll(8),
				clearBGPAsNumber(9),
				clearBGPPeer(10),
				clearBGPDamp(11),
				clearBGPExternal(12),
				clearBGPView(13)
				}
			MAX-ACCESS read-write
			STATUS current
			DESCRIPTION
				"Description."
			::= { sleBGPBaseControl 1 }


		-- 1.3.6.1.4.1.6296.101.53.1.2.2
		sleBGPBaseControlStatus OBJECT-TYPE
			SYNTAX SleControlStatusType
			MAX-ACCESS read-only
			STATUS current
			DESCRIPTION
				"1.3.6.1.4.1.6296.101.61.1.2.2"
			::= { sleBGPBaseControl 2 }


		-- 1.3.6.1.4.1.6296.101.53.1.2.3
		sleBGPBaseControlTimer OBJECT-TYPE
			SYNTAX Gauge32
			MAX-ACCESS read-write
			STATUS current
			DESCRIPTION
				"1.3.6.1.4.1.6296.101.61.1.2.3"
			::= { sleBGPBaseControl 3 }


		-- 1.3.6.1.4.1.6296.101.53.1.2.4
		sleBGPBaseControlTimeStamp OBJECT-TYPE
			SYNTAX TimeTicks
			MAX-ACCESS read-only
			STATUS current
			DESCRIPTION
				"1.3.6.1.4.1.6296.101.61.1.2.4"
			::= { sleBGPBaseControl 4 }


		-- 1.3.6.1.4.1.6296.101.53.1.2.5
		sleBGPBaseControlReqResult OBJECT-TYPE
			SYNTAX SleControlRequestResultType
			MAX-ACCESS read-only
			STATUS current
			DESCRIPTION
				"1.3.6.1.4.1.6296.101.61.1.2.5"
			::= { sleBGPBaseControl 5 }


		-- 1.3.6.1.4.1.6296.101.53.1.2.6
		sleBGPBaseControlAsNumber OBJECT-TYPE
			SYNTAX Gauge32 (1..4294967295)
			MAX-ACCESS read-only
			STATUS current
			DESCRIPTION
				"1.3.6.1.4.1.6296.101.61.1.2.7"
			::= { sleBGPBaseControl 6 }


		-- 1.3.6.1.4.1.6296.101.53.1.2.7
		sleBGPBaseControlConfigType OBJECT-TYPE
			SYNTAX INTEGER
				{
				zebos(0),
				standard(1)
				}
			MAX-ACCESS read-only
			STATUS current
			DESCRIPTION
				"1.3.6.1.4.1.6296.101.61.1.2.8"
			DEFVAL { 0 }
			::= { sleBGPBaseControl 7 }


		-- 1.3.6.1.4.1.6296.101.53.1.2.8
		sleBGPBaseControlRfc1771PathSelect OBJECT-TYPE
			SYNTAX INTEGER
				{
				disable(0),
				enable(1)
				}
			MAX-ACCESS read-only
			STATUS current
			DESCRIPTION
				"1.3.6.1.4.1.6296.101.61.1.2.9"
			::= { sleBGPBaseControl 8 }


		-- 1.3.6.1.4.1.6296.101.53.1.2.9
		sleBGPBaseControlRfc1771Strict OBJECT-TYPE
			SYNTAX INTEGER
				{
				disable(0),
				enable(1)
				}
			MAX-ACCESS read-only
			STATUS current
			DESCRIPTION
				"1.3.6.1.4.1.6296.101.61.1.2.9"
			::= { sleBGPBaseControl 9 }


		-- 1.3.6.1.4.1.6296.101.53.1.2.10
		sleBGPBaseControlAggregateNextHop OBJECT-TYPE
			SYNTAX INTEGER
				{
				disable(0),
				enable(1)
				}
			MAX-ACCESS read-only
			STATUS current
			DESCRIPTION
				"1.3.6.1.4.1.6296.101.61.1.2.9"
			::= { sleBGPBaseControl 10 }


		-- 1.3.6.1.4.1.6296.101.53.1.2.11
		sleBGPBaseControlExtendAsnCap OBJECT-TYPE
			SYNTAX INTEGER
				{
				disable(0),
				enable(1)
				}
			MAX-ACCESS read-only
			STATUS current
			DESCRIPTION
				"1.3.6.1.4.1.6296.101.61.1.2.9"
			::= { sleBGPBaseControl 11 }


		-- 1.3.6.1.4.1.6296.101.53.1.2.12
		sleBGPBaseControlClearFamilyMode OBJECT-TYPE
			SYNTAX INTEGER
				{
				ipv4(1),
				ipv6(2)
				}
			MAX-ACCESS read-only
			STATUS current
			DESCRIPTION
				"1.3.6.1.4.1.6296.101.61.1.2.9"
			::= { sleBGPBaseControl 12 }


		-- 1.3.6.1.4.1.6296.101.53.1.2.13
		sleBGPBaseControlClearFamilyType OBJECT-TYPE
			SYNTAX INTEGER
				{
				unicast(1),
				multicast(2),
				vpnv4(3)
				}
			MAX-ACCESS read-only
			STATUS current
			DESCRIPTION
				"1.3.6.1.4.1.6296.101.61.1.2.9"
			::= { sleBGPBaseControl 13 }


		-- 1.3.6.1.4.1.6296.101.53.1.2.14
		sleBGPBaseControlClearDirection OBJECT-TYPE
			SYNTAX INTEGER
				{
				all(0),
				in(1),
				out(2)
				}
			MAX-ACCESS read-only
			STATUS current
			DESCRIPTION
				"1.3.6.1.4.1.6296.101.61.1.2.9"
			::= { sleBGPBaseControl 14 }


		-- 1.3.6.1.4.1.6296.101.53.1.2.15
		sleBGPBaseControlClearSoft OBJECT-TYPE
			SYNTAX INTEGER
				{
				disable(0),
				enable(1)
				}
			MAX-ACCESS read-only
			STATUS current
			DESCRIPTION
				"1.3.6.1.4.1.6296.101.61.1.2.9"
			::= { sleBGPBaseControl 15 }


		-- 1.3.6.1.4.1.6296.101.53.1.2.16
		sleBGPBaseControlClearPrefixFilter OBJECT-TYPE
			SYNTAX INTEGER
				{
				disable(0),
				enable(1)
				}
			MAX-ACCESS read-only
			STATUS current
			DESCRIPTION
				"1.3.6.1.4.1.6296.101.61.1.2.9"
			::= { sleBGPBaseControl 16 }


		-- 1.3.6.1.4.1.6296.101.53.1.2.17
		sleBGPBaseControlClearPeerName OBJECT-TYPE
			SYNTAX OCTET STRING
			MAX-ACCESS read-only
			STATUS current
			DESCRIPTION
				"1.3.6.1.4.1.6296.101.61.1.2.9"
			::= { sleBGPBaseControl 17 }


		-- 1.3.6.1.4.1.6296.101.53.1.2.18
		sleBGPBaseControlClearAddr OBJECT-TYPE
			SYNTAX OCTET STRING
			MAX-ACCESS read-only
			STATUS current
			DESCRIPTION
				"1.3.6.1.4.1.6296.101.61.1.2.9"
			::= { sleBGPBaseControl 18 }


		-- 1.3.6.1.4.1.6296.101.53.1.2.19
		sleBGPBaseControlClearViewName OBJECT-TYPE
			SYNTAX OCTET STRING
			MAX-ACCESS read-only
			STATUS current
			DESCRIPTION
				"1.3.6.1.4.1.6296.101.61.1.2.9"
			::= { sleBGPBaseControl 19 }


		-- 1.3.6.1.4.1.6296.101.53.1.2.20
		sleBGPBaseControlClearDampFlag OBJECT-TYPE
			SYNTAX INTEGER
				{
				damp(1),
				flap(2)
				}
			MAX-ACCESS read-only
			STATUS current
			DESCRIPTION
				"1.3.6.1.4.1.6296.101.61.1.2.9"
			::= { sleBGPBaseControl 20 }


		-- 1.3.6.1.4.1.6296.101.53.1.3
		sleBGPBaseNotification OBJECT IDENTIFIER ::= { sleBGPBase 3 }


		-- 1.3.6.1.4.1.6296.101.53.1.3.1
		sleBGPBaseAsModeCreated NOTIFICATION-TYPE
			OBJECTS { sleBGPBaseControlRequest, sleBGPBaseControlTimeStamp, sleBGPBaseControlReqResult, sleBGPBaseAsNumber }
			STATUS current
			DESCRIPTION
				"Description."
			::= { sleBGPBaseNotification 1 }


		-- 1.3.6.1.4.1.6296.101.53.1.3.2
		sleBGPBaseAsModeDeleted NOTIFICATION-TYPE
			OBJECTS { sleBGPBaseControlRequest, sleBGPBaseControlTimeStamp, sleBGPBaseControlReqResult, sleBGPBaseControlAsNumber }
			STATUS current
			DESCRIPTION
				"Description."
			::= { sleBGPBaseNotification 2 }


		-- 1.3.6.1.4.1.6296.101.53.1.3.3
		sleBGPBaseConfigTypeChanged NOTIFICATION-TYPE
			OBJECTS { sleBGPBaseControlRequest, sleBGPBaseControlTimeStamp, sleBGPBaseControlReqResult, sleBGPBaseConfigType }
			STATUS current
			DESCRIPTION
				"Description."
			::= { sleBGPBaseNotification 3 }


		-- 1.3.6.1.4.1.6296.101.53.1.3.4
		sleBGPBaseRfc1771PathSelectChanged NOTIFICATION-TYPE
			OBJECTS { sleBGPBaseControlRequest, sleBGPBaseControlTimeStamp, sleBGPBaseControlReqResult, sleBGPBaseRfc1771PathSelect }
			STATUS current
			DESCRIPTION
				"Description."
			::= { sleBGPBaseNotification 4 }


		-- 1.3.6.1.4.1.6296.101.53.1.3.5
		sleBGPBaseRfc1771StrictChanged NOTIFICATION-TYPE
			OBJECTS { sleBGPBaseControlRequest, sleBGPBaseControlTimeStamp, sleBGPBaseControlReqResult, sleBGPBaseRfc1771Strict }
			STATUS current
			DESCRIPTION
				"Description."
			::= { sleBGPBaseNotification 5 }


		-- 1.3.6.1.4.1.6296.101.53.1.3.6
		sleBGPBaseAggregateNextHopChanged NOTIFICATION-TYPE
			OBJECTS { sleBGPBaseControlRequest, sleBGPBaseControlTimeStamp, sleBGPBaseControlReqResult, sleBGPBaseAggregateNextHop }
			STATUS current
			DESCRIPTION
				"Description."
			::= { sleBGPBaseNotification 6 }


		-- 1.3.6.1.4.1.6296.101.53.1.3.7
		sleBGPBaseExtendAsnCapChanged NOTIFICATION-TYPE
			OBJECTS { sleBGPBaseControlRequest, sleBGPBaseControlTimeStamp, sleBGPBaseControlReqResult, sleBGPBaseExtendAsnCap }
			STATUS current
			DESCRIPTION
				"Description."
			::= { sleBGPBaseNotification 7 }


		-- 1.3.6.1.4.1.6296.101.53.1.3.8
		sleBGPBaseAllCleared NOTIFICATION-TYPE
			OBJECTS { sleBGPBaseControlRequest, sleBGPBaseControlTimeStamp, sleBGPBaseControlReqResult, sleBGPBaseControlClearFamilyMode, sleBGPBaseControlClearFamilyType,
				sleBGPBaseControlClearDirection, sleBGPBaseControlClearSoft, sleBGPBaseControlClearPrefixFilter }
			STATUS current
			DESCRIPTION
				"Description."
			::= { sleBGPBaseNotification 8 }


		-- 1.3.6.1.4.1.6296.101.53.1.3.9
		sleBGPBaseAsNumberCleared NOTIFICATION-TYPE
			OBJECTS { sleBGPBaseControlRequest, sleBGPBaseControlTimeStamp, sleBGPBaseControlReqResult, sleBGPBaseControlAsNumber, sleBGPBaseControlClearFamilyMode,
				sleBGPBaseControlClearFamilyType, sleBGPBaseControlClearDirection, sleBGPBaseControlClearSoft, sleBGPBaseControlClearPrefixFilter }
			STATUS current
			DESCRIPTION
				"Description."
			::= { sleBGPBaseNotification 9 }


		-- 1.3.6.1.4.1.6296.101.53.1.3.10
		sleBGPBasePeerCleared NOTIFICATION-TYPE
			OBJECTS { sleBGPBaseControlRequest, sleBGPBaseControlTimeStamp, sleBGPBaseControlReqResult, sleBGPBaseControlClearPeerName, sleBGPBaseControlClearFamilyMode,
				sleBGPBaseControlClearFamilyType, sleBGPBaseControlClearDirection, sleBGPBaseControlClearSoft, sleBGPBaseControlClearPrefixFilter }
			STATUS current
			DESCRIPTION
				"Description."
			::= { sleBGPBaseNotification 10 }


		-- 1.3.6.1.4.1.6296.101.53.1.3.11
		sleBGPBaseDampCleared NOTIFICATION-TYPE
			OBJECTS { sleBGPBaseControlRequest, sleBGPBaseControlTimeStamp, sleBGPBaseControlReqResult, sleBGPBaseControlClearFamilyType, sleBGPBaseControlClearAddr,
				sleBGPBaseControlClearDampFlag }
			STATUS current
			DESCRIPTION
				"Description."
			::= { sleBGPBaseNotification 11 }


		-- 1.3.6.1.4.1.6296.101.53.1.3.12
		sleBGPBaseExternalCleared NOTIFICATION-TYPE
			OBJECTS { sleBGPBaseControlRequest, sleBGPBaseControlTimeStamp, sleBGPBaseControlReqResult, sleBGPBaseControlClearFamilyMode, sleBGPBaseControlClearFamilyType,
				sleBGPBaseControlClearDirection, sleBGPBaseControlClearSoft, sleBGPBaseControlClearPrefixFilter }
			STATUS current
			DESCRIPTION
				"Description."
			::= { sleBGPBaseNotification 12 }


		-- 1.3.6.1.4.1.6296.101.53.1.3.13
		sleBGPBaseViewCleared NOTIFICATION-TYPE
			OBJECTS { sleBGPBaseControlRequest, sleBGPBaseControlTimeStamp, sleBGPBaseControlReqResult, sleBGPBaseControlClearViewName, sleBGPBaseControlClearFamilyType,
				sleBGPBaseControlClearDirection, sleBGPBaseControlClearSoft, sleBGPBaseControlClearPrefixFilter }
			STATUS current
			DESCRIPTION
				"Description."
			::= { sleBGPBaseNotification 13 }


		-- 1.3.6.1.4.1.6296.101.53.2
		sleBGPInfo OBJECT IDENTIFIER ::= { sleBGP 2 }


		-- 1.3.6.1.4.1.6296.101.53.2.1
		sleBGPInfoValue OBJECT IDENTIFIER ::= { sleBGPInfo 1 }


		-- 1.3.6.1.4.1.6296.101.53.2.1.1
		sleBGPInfoRouterID OBJECT-TYPE
			SYNTAX IpAddress
			MAX-ACCESS read-only
			STATUS current
			DESCRIPTION
				"Description."
			::= { sleBGPInfoValue 1 }


		-- 1.3.6.1.4.1.6296.101.53.2.1.2
		sleBGPInfoLogNeighborChange OBJECT-TYPE
			SYNTAX INTEGER
				{
				disable(0),
				enable(1)
				}
			MAX-ACCESS read-only
			STATUS current
			DESCRIPTION
				"Description."
			DEFVAL { 0 }
			::= { sleBGPInfoValue 2 }


		-- 1.3.6.1.4.1.6296.101.53.2.1.3
		sleBGPInfoAlwaysCompareMed OBJECT-TYPE
			SYNTAX INTEGER
				{
				disable(0),
				enable(1)
				}
			MAX-ACCESS read-only
			STATUS current
			DESCRIPTION
				"Description."
			::= { sleBGPInfoValue 3 }


		-- 1.3.6.1.4.1.6296.101.53.2.1.4
		sleBGPInfoBestPathAsPathIgnore OBJECT-TYPE
			SYNTAX INTEGER
				{
				disable(0),
				enable(1)
				}
			MAX-ACCESS read-only
			STATUS current
			DESCRIPTION
				"Description."
			::= { sleBGPInfoValue 4 }


		-- 1.3.6.1.4.1.6296.101.53.2.1.5
		sleBGPInfoBestPathCompareConfedAsPath OBJECT-TYPE
			SYNTAX INTEGER
				{
				disable(0),
				enable(1)
				}
			MAX-ACCESS read-only
			STATUS current
			DESCRIPTION
				"Description."
			::= { sleBGPInfoValue 5 }


		-- 1.3.6.1.4.1.6296.101.53.2.1.6
		sleBGPInfoBestPathCompareRouterID OBJECT-TYPE
			SYNTAX INTEGER
				{
				disable(0),
				enable(1)
				}
			MAX-ACCESS read-only
			STATUS current
			DESCRIPTION
				"Description."
			::= { sleBGPInfoValue 6 }


		-- 1.3.6.1.4.1.6296.101.53.2.1.7
		sleBGPInfoBestPathCompareMedConfed OBJECT-TYPE
			SYNTAX INTEGER
				{
				disable(0),
				enable(1)
				}
			MAX-ACCESS read-only
			STATUS current
			DESCRIPTION
				"Description."
			::= { sleBGPInfoValue 7 }


		-- 1.3.6.1.4.1.6296.101.53.2.1.8
		sleBGPInfoBestPathCompareMedMisAsWorst OBJECT-TYPE
			SYNTAX INTEGER
				{
				disable(0),
				enable(1)
				}
			MAX-ACCESS read-only
			STATUS current
			DESCRIPTION
				"Description."
			::= { sleBGPInfoValue 8 }


		-- 1.3.6.1.4.1.6296.101.53.2.1.9
		sleBGPInfoClientToClient OBJECT-TYPE
			SYNTAX INTEGER
				{
				disable(0),
				enable(1)
				}
			MAX-ACCESS read-only
			STATUS current
			DESCRIPTION
				"Description."
			::= { sleBGPInfoValue 9 }


		-- 1.3.6.1.4.1.6296.101.53.2.1.10
		sleBGPInfoClusterID OBJECT-TYPE
			SYNTAX IpAddress
			MAX-ACCESS read-only
			STATUS current
			DESCRIPTION
				"Description."
			::= { sleBGPInfoValue 10 }


		-- 1.3.6.1.4.1.6296.101.53.2.1.11
		sleBGPInfoConfederationID OBJECT-TYPE
			SYNTAX INTEGER (0..65535)
			MAX-ACCESS read-only
			STATUS current
			DESCRIPTION
				"Description."
			::= { sleBGPInfoValue 11 }


		-- 1.3.6.1.4.1.6296.101.53.2.1.12
		sleBGPInfoDeterministicMed OBJECT-TYPE
			SYNTAX INTEGER
				{
				disable(0),
				enable(1)
				}
			MAX-ACCESS read-only
			STATUS current
			DESCRIPTION
				"Description."
			::= { sleBGPInfoValue 12 }


		-- 1.3.6.1.4.1.6296.101.53.2.1.13
		sleBGPInfoEnforceFirstAs OBJECT-TYPE
			SYNTAX INTEGER
				{
				disable(0),
				enable(1)
				}
			MAX-ACCESS read-only
			STATUS current
			DESCRIPTION
				"Description."
			::= { sleBGPInfoValue 13 }


		-- 1.3.6.1.4.1.6296.101.53.2.1.14
		sleBGPInfoFastExternalFailOver OBJECT-TYPE
			SYNTAX INTEGER
				{
				disable(0),
				enable(1)
				}
			MAX-ACCESS read-only
			STATUS current
			DESCRIPTION
				"Description."
			::= { sleBGPInfoValue 14 }


		-- 1.3.6.1.4.1.6296.101.53.2.1.15
		sleBGPInfoGracefulRestartTime OBJECT-TYPE
			SYNTAX INTEGER (0..3600)
			MAX-ACCESS read-only
			STATUS current
			DESCRIPTION
				"Description."
			::= { sleBGPInfoValue 15 }


		-- 1.3.6.1.4.1.6296.101.53.2.1.16
		sleBGPInfoGracefulStalepathTime OBJECT-TYPE
			SYNTAX INTEGER (0..3600)
			MAX-ACCESS read-only
			STATUS current
			DESCRIPTION
				"Description."
			::= { sleBGPInfoValue 16 }


		-- 1.3.6.1.4.1.6296.101.53.2.1.17
		sleBGPInfoScanTime OBJECT-TYPE
			SYNTAX INTEGER (0..60)
			MAX-ACCESS read-only
			STATUS current
			DESCRIPTION
				"Description."
			::= { sleBGPInfoValue 17 }


		-- 1.3.6.1.4.1.6296.101.53.2.1.18
		sleBGPInfoNexthopTriggerStatus OBJECT-TYPE
			SYNTAX INTEGER
				{
				disable(0),
				enable(1)
				}
			MAX-ACCESS read-only
			STATUS current
			DESCRIPTION
				"Description."
			::= { sleBGPInfoValue 18 }


		-- 1.3.6.1.4.1.6296.101.53.2.1.19
		sleBGPInfoNexthopTriggerDelay OBJECT-TYPE
			SYNTAX INTEGER (2..30)
			MAX-ACCESS read-only
			STATUS current
			DESCRIPTION
				"Description."
			::= { sleBGPInfoValue 19 }


		-- 1.3.6.1.4.1.6296.101.53.2.1.20
		sleBGPInfoSnmpNotification OBJECT-TYPE
			SYNTAX INTEGER
				{
				disable(0),
				enable(1)
				}
			MAX-ACCESS read-only
			STATUS current
			DESCRIPTION
				"Description."
			::= { sleBGPInfoValue 20 }


		-- 1.3.6.1.4.1.6296.101.53.2.1.21
		sleBGPInfoUpdateDelay OBJECT-TYPE
			SYNTAX INTEGER (0..60)
			MAX-ACCESS read-only
			STATUS current
			DESCRIPTION
				"Description."
			::= { sleBGPInfoValue 21 }


		-- 1.3.6.1.4.1.6296.101.53.2.1.22
		sleBGPInfoExternalRouteDistance OBJECT-TYPE
			SYNTAX INTEGER (0..255)
			MAX-ACCESS read-only
			STATUS current
			DESCRIPTION
				"Description."
			::= { sleBGPInfoValue 22 }


		-- 1.3.6.1.4.1.6296.101.53.2.1.23
		sleBGPInfoInternalRouteDistance OBJECT-TYPE
			SYNTAX INTEGER (0..255)
			MAX-ACCESS read-only
			STATUS current
			DESCRIPTION
				"Description."
			::= { sleBGPInfoValue 23 }


		-- 1.3.6.1.4.1.6296.101.53.2.1.24
		sleBGPInfoLocalRouteDistance OBJECT-TYPE
			SYNTAX INTEGER (0..255)
			MAX-ACCESS read-only
			STATUS current
			DESCRIPTION
				"Description."
			::= { sleBGPInfoValue 24 }


		-- 1.3.6.1.4.1.6296.101.53.2.1.25
		sleBGPInfoMaximumPath OBJECT-TYPE
			SYNTAX INTEGER (1..8)
			MAX-ACCESS read-only
			STATUS current
			DESCRIPTION
				"Description."
			::= { sleBGPInfoValue 25 }


		-- 1.3.6.1.4.1.6296.101.53.2.1.26
		sleBGPInfoMaximumPathIBGP OBJECT-TYPE
			SYNTAX INTEGER (1..8)
			MAX-ACCESS read-only
			STATUS current
			DESCRIPTION
				"Description."
			::= { sleBGPInfoValue 26 }


		-- 1.3.6.1.4.1.6296.101.53.2.1.27
		sleBGPInfoKeepAliveInterval OBJECT-TYPE
			SYNTAX INTEGER (0..65535)
			MAX-ACCESS read-only
			STATUS current
			DESCRIPTION
				"Description."
			::= { sleBGPInfoValue 27 }


		-- 1.3.6.1.4.1.6296.101.53.2.1.28
		sleBGPInfoHoldTime OBJECT-TYPE
			SYNTAX INTEGER (0..65535)
			MAX-ACCESS read-only
			STATUS current
			DESCRIPTION
				"Description."
			::= { sleBGPInfoValue 28 }


		-- 1.3.6.1.4.1.6296.101.53.2.2
		sleBGPInfoControl OBJECT IDENTIFIER ::= { sleBGPInfo 2 }


		-- 1.3.6.1.4.1.6296.101.53.2.2.1
		sleBGPInfoControlRequest OBJECT-TYPE
			SYNTAX INTEGER
				{
				createBGPRouterID(1),
				deleteBGPRouterID(2),
				setBGPLogNeighbor(3),
				setBGPAlwaysCompareMed(4),
				setBGPBestPathAsPathIgnore(5),
				setBGPBestPathCompareConfedAsPath(6),
				setBGPBestPathCompareRouterID(7),
				setBGPBestPathCompareMedConfed(8),
				setBGPBestPathCompareMedMisAsWorst(9),
				setBGPClientToClient(10),
				createBGPClusterID(11),
				deleteBGPClusterID(12),
				setBGPConfederationID(13),
				setBGPDeterministicMed(14),
				setBGPEnforceFirstAs(15),
				setBGPFastExternalFailOver(16),
				setBGPGracefulRestartProfile(17),
				setBGPScanTime(18),
				setBGPNexthopTriggerStatus(19),
				setBGPNexthopTriggerInterval(20),
				setBGPSnmpNotification(21),
				setBGPUpdateDelay(22),
				createBGPDistanceProfile(23),
				deleteBGPDistanceProfile(24),
				setBGPMaximumPath(25),
				setBGPMaximumPathIBGP(26),
				setBGPTimersProfile(27)
				}
			MAX-ACCESS read-write
			STATUS current
			DESCRIPTION
				"Description."
			::= { sleBGPInfoControl 1 }


		-- 1.3.6.1.4.1.6296.101.53.2.2.2
		sleBGPInfoControlStatus OBJECT-TYPE
			SYNTAX SleControlStatusType
			MAX-ACCESS read-only
			STATUS current
			DESCRIPTION
				"1.3.6.1.4.1.6296.101.61.1.2.2"
			::= { sleBGPInfoControl 2 }


		-- 1.3.6.1.4.1.6296.101.53.2.2.3
		sleBGPInfoControlTimer OBJECT-TYPE
			SYNTAX Gauge32
			MAX-ACCESS read-write
			STATUS current
			DESCRIPTION
				"1.3.6.1.4.1.6296.101.61.1.2.3"
			::= { sleBGPInfoControl 3 }


		-- 1.3.6.1.4.1.6296.101.53.2.2.4
		sleBGPInfoControlTimeStamp OBJECT-TYPE
			SYNTAX TimeTicks
			MAX-ACCESS read-only
			STATUS current
			DESCRIPTION
				"1.3.6.1.4.1.6296.101.61.1.2.4"
			::= { sleBGPInfoControl 4 }


		-- 1.3.6.1.4.1.6296.101.53.2.2.5
		sleBGPInfoControlReqResult OBJECT-TYPE
			SYNTAX SleControlRequestResultType
			MAX-ACCESS read-only
			STATUS current
			DESCRIPTION
				"1.3.6.1.4.1.6296.101.61.1.2.5"
			::= { sleBGPInfoControl 5 }


		-- 1.3.6.1.4.1.6296.101.53.2.2.6
		sleBGPInfoControlRouterID OBJECT-TYPE
			SYNTAX IpAddress
			MAX-ACCESS read-only
			STATUS current
			DESCRIPTION
				"Description."
			::= { sleBGPInfoControl 6 }


		-- 1.3.6.1.4.1.6296.101.53.2.2.7
		sleBGPInfoControlLogNeighborChange OBJECT-TYPE
			SYNTAX INTEGER
				{
				disable(0),
				enable(1)
				}
			MAX-ACCESS read-only
			STATUS current
			DESCRIPTION
				"Description."
			DEFVAL { 0 }
			::= { sleBGPInfoControl 7 }


		-- 1.3.6.1.4.1.6296.101.53.2.2.8
		sleBGPInfoControlAlwaysCompareMed OBJECT-TYPE
			SYNTAX INTEGER
				{
				disable(0),
				enable(1)
				}
			MAX-ACCESS read-only
			STATUS current
			DESCRIPTION
				"Description."
			::= { sleBGPInfoControl 8 }


		-- 1.3.6.1.4.1.6296.101.53.2.2.9
		sleBGPInfoControlBestPathAsPathIgnore OBJECT-TYPE
			SYNTAX INTEGER
				{
				disable(0),
				enable(1)
				}
			MAX-ACCESS read-only
			STATUS current
			DESCRIPTION
				"Description."
			::= { sleBGPInfoControl 9 }


		-- 1.3.6.1.4.1.6296.101.53.2.2.10
		sleBGPInfoControlBestPathCompareConfedAsPath OBJECT-TYPE
			SYNTAX INTEGER
				{
				disable(0),
				enable(1)
				}
			MAX-ACCESS read-only
			STATUS current
			DESCRIPTION
				"Description."
			::= { sleBGPInfoControl 10 }


		-- 1.3.6.1.4.1.6296.101.53.2.2.11
		sleBGPInfoControlBestPathCompareRouterID OBJECT-TYPE
			SYNTAX INTEGER
				{
				disable(0),
				enable(1)
				}
			MAX-ACCESS read-only
			STATUS current
			DESCRIPTION
				"Description."
			::= { sleBGPInfoControl 11 }


		-- 1.3.6.1.4.1.6296.101.53.2.2.12
		sleBGPInfoControlBestPathCompareMedConfed OBJECT-TYPE
			SYNTAX INTEGER
				{
				disable(0),
				enable(1)
				}
			MAX-ACCESS read-only
			STATUS current
			DESCRIPTION
				"Description."
			::= { sleBGPInfoControl 12 }


		-- 1.3.6.1.4.1.6296.101.53.2.2.13
		sleBGPInfoControlBestPathCompareMedMisAsWorst OBJECT-TYPE
			SYNTAX INTEGER
				{
				disable(0),
				enable(1)
				}
			MAX-ACCESS read-only
			STATUS current
			DESCRIPTION
				"Description."
			::= { sleBGPInfoControl 13 }


		-- 1.3.6.1.4.1.6296.101.53.2.2.14
		sleBGPInfoControlClientToClient OBJECT-TYPE
			SYNTAX INTEGER
				{
				disable(0),
				enable(1)
				}
			MAX-ACCESS read-only
			STATUS current
			DESCRIPTION
				"Description."
			::= { sleBGPInfoControl 14 }


		-- 1.3.6.1.4.1.6296.101.53.2.2.15
		sleBGPInfoControlClusterID OBJECT-TYPE
			SYNTAX IpAddress
			MAX-ACCESS read-only
			STATUS current
			DESCRIPTION
				"Description."
			::= { sleBGPInfoControl 15 }


		-- 1.3.6.1.4.1.6296.101.53.2.2.16
		sleBGPInfoControlConfederationID OBJECT-TYPE
			SYNTAX INTEGER (0..65535)
			MAX-ACCESS read-only
			STATUS current
			DESCRIPTION
				"Description."
			::= { sleBGPInfoControl 16 }


		-- 1.3.6.1.4.1.6296.101.53.2.2.17
		sleBGPInfoControlDeterministicMed OBJECT-TYPE
			SYNTAX INTEGER
				{
				disable(0),
				enable(1)
				}
			MAX-ACCESS read-only
			STATUS current
			DESCRIPTION
				"Description."
			::= { sleBGPInfoControl 17 }


		-- 1.3.6.1.4.1.6296.101.53.2.2.18
		sleBGPInfoControlEnforceFirstAs OBJECT-TYPE
			SYNTAX INTEGER
				{
				disable(0),
				enable(1)
				}
			MAX-ACCESS read-only
			STATUS current
			DESCRIPTION
				"Description."
			::= { sleBGPInfoControl 18 }


		-- 1.3.6.1.4.1.6296.101.53.2.2.19
		sleBGPInfoControlFastExternalFailOver OBJECT-TYPE
			SYNTAX INTEGER
				{
				disable(0),
				enable(1)
				}
			MAX-ACCESS read-only
			STATUS current
			DESCRIPTION
				"Description."
			::= { sleBGPInfoControl 19 }


		-- 1.3.6.1.4.1.6296.101.53.2.2.20
		sleBGPInfoControlGracefulRestartTime OBJECT-TYPE
			SYNTAX INTEGER (0..3600)
			MAX-ACCESS read-only
			STATUS current
			DESCRIPTION
				"Description."
			::= { sleBGPInfoControl 20 }


		-- 1.3.6.1.4.1.6296.101.53.2.2.21
		sleBGPInfoControlGracefulStalepathTime OBJECT-TYPE
			SYNTAX INTEGER (0..3600)
			MAX-ACCESS read-only
			STATUS current
			DESCRIPTION
				"Description."
			::= { sleBGPInfoControl 21 }


		-- 1.3.6.1.4.1.6296.101.53.2.2.22
		sleBGPInfoControlScanTime OBJECT-TYPE
			SYNTAX INTEGER (0..60)
			MAX-ACCESS read-only
			STATUS current
			DESCRIPTION
				"Description."
			::= { sleBGPInfoControl 22 }


		-- 1.3.6.1.4.1.6296.101.53.2.2.23
		sleBGPInfoControlNexthopTriggerStatus OBJECT-TYPE
			SYNTAX INTEGER
				{
				disable(0),
				enable(1)
				}
			MAX-ACCESS read-only
			STATUS current
			DESCRIPTION
				"Description."
			::= { sleBGPInfoControl 23 }


		-- 1.3.6.1.4.1.6296.101.53.2.2.24
		sleBGPInfoControlNexthopTriggerDelay OBJECT-TYPE
			SYNTAX INTEGER (2..30)
			MAX-ACCESS read-only
			STATUS current
			DESCRIPTION
				"Description."
			::= { sleBGPInfoControl 24 }


		-- 1.3.6.1.4.1.6296.101.53.2.2.25
		sleBGPInfoControlSnmpNotification OBJECT-TYPE
			SYNTAX INTEGER
				{
				disable(0),
				enable(1)
				}
			MAX-ACCESS read-only
			STATUS current
			DESCRIPTION
				"Description."
			::= { sleBGPInfoControl 25 }


		-- 1.3.6.1.4.1.6296.101.53.2.2.26
		sleBGPInfoControlUpdateDelay OBJECT-TYPE
			SYNTAX INTEGER (0..60)
			MAX-ACCESS read-only
			STATUS current
			DESCRIPTION
				"Description."
			::= { sleBGPInfoControl 26 }


		-- 1.3.6.1.4.1.6296.101.53.2.2.27
		sleBGPInfoControlExternalRouteDistance OBJECT-TYPE
			SYNTAX INTEGER (0..255)
			MAX-ACCESS read-only
			STATUS current
			DESCRIPTION
				"Description."
			::= { sleBGPInfoControl 27 }


		-- 1.3.6.1.4.1.6296.101.53.2.2.28
		sleBGPInfoControlInternalRouteDistance OBJECT-TYPE
			SYNTAX INTEGER (0..255)
			MAX-ACCESS read-only
			STATUS current
			DESCRIPTION
				"Description."
			::= { sleBGPInfoControl 28 }


		-- 1.3.6.1.4.1.6296.101.53.2.2.29
		sleBGPInfoControlLocalRouteDistance OBJECT-TYPE
			SYNTAX INTEGER (0..255)
			MAX-ACCESS read-only
			STATUS current
			DESCRIPTION
				"Description."
			::= { sleBGPInfoControl 29 }


		-- 1.3.6.1.4.1.6296.101.53.2.2.30
		sleBGPInfoControlMaximumPath OBJECT-TYPE
			SYNTAX INTEGER (1..8)
			MAX-ACCESS read-only
			STATUS current
			DESCRIPTION
				"Description."
			::= { sleBGPInfoControl 30 }


		-- 1.3.6.1.4.1.6296.101.53.2.2.31
		sleBGPInfoControlMaximumPathIBGP OBJECT-TYPE
			SYNTAX INTEGER (1..8)
			MAX-ACCESS read-only
			STATUS current
			DESCRIPTION
				"Description."
			::= { sleBGPInfoControl 31 }


		-- 1.3.6.1.4.1.6296.101.53.2.2.32
		sleBGPInfoControlKeepAliveInterval OBJECT-TYPE
			SYNTAX INTEGER (0..65535)
			MAX-ACCESS read-only
			STATUS current
			DESCRIPTION
				"Description."
			::= { sleBGPInfoControl 32 }


		-- 1.3.6.1.4.1.6296.101.53.2.2.33
		sleBGPInfoControlHoldTime OBJECT-TYPE
			SYNTAX INTEGER (0..65535)
			MAX-ACCESS read-only
			STATUS current
			DESCRIPTION
				"Description."
			::= { sleBGPInfoControl 33 }


		-- 1.3.6.1.4.1.6296.101.53.2.3
		sleBGPInfoNotification OBJECT IDENTIFIER ::= { sleBGPInfo 3 }


		-- 1.3.6.1.4.1.6296.101.53.2.3.1
		sleBGPInfoRouterIDCreated NOTIFICATION-TYPE
			OBJECTS { sleBGPInfoControlRequest, sleBGPInfoControlTimeStamp, sleBGPInfoControlReqResult, sleBGPInfoRouterID }
			STATUS current
			DESCRIPTION
				"Description."
			::= { sleBGPInfoNotification 1 }


		-- 1.3.6.1.4.1.6296.101.53.2.3.2
		sleBGPInfoRouterIDDeleted NOTIFICATION-TYPE
			OBJECTS { sleBGPInfoControlRequest, sleBGPInfoControlTimeStamp, sleBGPInfoControlReqResult, sleBGPInfoControlRouterID }
			STATUS current
			DESCRIPTION
				"Description."
			::= { sleBGPInfoNotification 2 }


		-- 1.3.6.1.4.1.6296.101.53.2.3.3
		sleBGPInfoLogNeighborChanged NOTIFICATION-TYPE
			OBJECTS { sleBGPInfoControlRequest, sleBGPInfoControlTimeStamp, sleBGPInfoControlReqResult, sleBGPInfoLogNeighborChange }
			STATUS current
			DESCRIPTION
				"Description."
			::= { sleBGPInfoNotification 3 }


		-- 1.3.6.1.4.1.6296.101.53.2.3.4
		sleBGPInfoAlwaysCompareMedChanged NOTIFICATION-TYPE
			OBJECTS { sleBGPInfoControlRequest, sleBGPInfoControlTimeStamp, sleBGPInfoControlReqResult, sleBGPInfoAlwaysCompareMed }
			STATUS current
			DESCRIPTION
				"Description."
			::= { sleBGPInfoNotification 4 }


		-- 1.3.6.1.4.1.6296.101.53.2.3.5
		sleBGPInfoBestPathAsPathIgnoreChanged NOTIFICATION-TYPE
			OBJECTS { sleBGPInfoControlRequest, sleBGPInfoControlTimeStamp, sleBGPInfoControlReqResult, sleBGPInfoBestPathAsPathIgnore }
			STATUS current
			DESCRIPTION
				"Description."
			::= { sleBGPInfoNotification 5 }


		-- 1.3.6.1.4.1.6296.101.53.2.3.6
		sleBGPInfoBestPathCompareConfedAsPathChanged NOTIFICATION-TYPE
			OBJECTS { sleBGPInfoControlRequest, sleBGPInfoControlTimeStamp, sleBGPInfoControlReqResult, sleBGPInfoBestPathCompareConfedAsPath }
			STATUS current
			DESCRIPTION
				"Description."
			::= { sleBGPInfoNotification 6 }


		-- 1.3.6.1.4.1.6296.101.53.2.3.7
		sleBGPInfoBestPathCompareRouterIDChanged NOTIFICATION-TYPE
			OBJECTS { sleBGPInfoControlRequest, sleBGPInfoControlTimeStamp, sleBGPInfoControlReqResult, sleBGPInfoBestPathCompareRouterID }
			STATUS current
			DESCRIPTION
				"Description."
			::= { sleBGPInfoNotification 7 }


		-- 1.3.6.1.4.1.6296.101.53.2.3.8
		sleBGPInfoBestPathCompareMedConfedChanged NOTIFICATION-TYPE
			OBJECTS { sleBGPInfoControlRequest, sleBGPInfoControlTimeStamp, sleBGPInfoControlReqResult, sleBGPInfoBestPathCompareMedConfed }
			STATUS current
			DESCRIPTION
				"Description."
			::= { sleBGPInfoNotification 8 }


		-- 1.3.6.1.4.1.6296.101.53.2.3.9
		sleBGPInfoBestPathCompareMedMisAsWorstChanged NOTIFICATION-TYPE
			OBJECTS { sleBGPInfoControlRequest, sleBGPInfoControlTimeStamp, sleBGPInfoControlReqResult, sleBGPInfoBestPathCompareMedMisAsWorst }
			STATUS current
			DESCRIPTION
				"Description."
			::= { sleBGPInfoNotification 9 }


		-- 1.3.6.1.4.1.6296.101.53.2.3.10
		sleBGPInfoClientToClientChanged NOTIFICATION-TYPE
			OBJECTS { sleBGPInfoControlRequest, sleBGPInfoControlTimeStamp, sleBGPInfoControlReqResult, sleBGPInfoClientToClient }
			STATUS current
			DESCRIPTION
				"Description."
			::= { sleBGPInfoNotification 10 }


		-- 1.3.6.1.4.1.6296.101.53.2.3.11
		sleBGPInfoClusterIDCreated NOTIFICATION-TYPE
			OBJECTS { sleBGPInfoControlRequest, sleBGPInfoControlTimeStamp, sleBGPInfoControlReqResult, sleBGPInfoClusterID }
			STATUS current
			DESCRIPTION
				"Description."
			::= { sleBGPInfoNotification 11 }


		-- 1.3.6.1.4.1.6296.101.53.2.3.12
		sleBGPInfoClusterIDDeleted NOTIFICATION-TYPE
			OBJECTS { sleBGPInfoControlRequest, sleBGPInfoControlTimeStamp, sleBGPInfoControlReqResult, sleBGPInfoControlClusterID }
			STATUS current
			DESCRIPTION
				"Description."
			::= { sleBGPInfoNotification 12 }


		-- 1.3.6.1.4.1.6296.101.53.2.3.13
		sleBGPInfoConfederationIDChanged NOTIFICATION-TYPE
			OBJECTS { sleBGPInfoControlRequest, sleBGPInfoControlTimeStamp, sleBGPInfoControlReqResult, sleBGPInfoConfederationID }
			STATUS current
			DESCRIPTION
				"Description."
			::= { sleBGPInfoNotification 13 }


		-- 1.3.6.1.4.1.6296.101.53.2.3.14
		sleBGPInfoDeterministicMedChanged NOTIFICATION-TYPE
			OBJECTS { sleBGPInfoControlRequest, sleBGPInfoControlTimeStamp, sleBGPInfoControlReqResult, sleBGPInfoDeterministicMed }
			STATUS current
			DESCRIPTION
				"Description."
			::= { sleBGPInfoNotification 14 }


		-- 1.3.6.1.4.1.6296.101.53.2.3.15
		sleBGPInfoEnforceFirstAsChanged NOTIFICATION-TYPE
			OBJECTS { sleBGPInfoControlRequest, sleBGPInfoControlTimeStamp, sleBGPInfoControlReqResult, sleBGPInfoEnforceFirstAs }
			STATUS current
			DESCRIPTION
				"Description."
			::= { sleBGPInfoNotification 15 }


		-- 1.3.6.1.4.1.6296.101.53.2.3.16
		sleBGPInfoFastExternalFailOverChanged NOTIFICATION-TYPE
			OBJECTS { sleBGPInfoControlRequest, sleBGPInfoControlTimeStamp, sleBGPInfoControlReqResult, sleBGPInfoFastExternalFailOver }
			STATUS current
			DESCRIPTION
				"Description."
			::= { sleBGPInfoNotification 16 }


		-- 1.3.6.1.4.1.6296.101.53.2.3.17
		sleBGPInfoGracefulRestartProfileChanged NOTIFICATION-TYPE
			OBJECTS { sleBGPInfoControlRequest, sleBGPInfoControlTimeStamp, sleBGPInfoControlReqResult, sleBGPInfoGracefulRestartTime, sleBGPInfoGracefulStalepathTime
				 }
			STATUS current
			DESCRIPTION
				"Description."
			::= { sleBGPInfoNotification 17 }


		-- 1.3.6.1.4.1.6296.101.53.2.3.18
		sleBGPInfoScanTimeChanged NOTIFICATION-TYPE
			OBJECTS { sleBGPInfoControlRequest, sleBGPInfoControlTimeStamp, sleBGPInfoControlReqResult, sleBGPInfoScanTime }
			STATUS current
			DESCRIPTION
				"Description."
			::= { sleBGPInfoNotification 18 }


		-- 1.3.6.1.4.1.6296.101.53.2.3.19
		sleBGPInfoNexthopTriggerStatusChanged NOTIFICATION-TYPE
			OBJECTS { sleBGPInfoControlRequest, sleBGPInfoControlTimeStamp, sleBGPInfoControlReqResult, sleBGPInfoNexthopTriggerStatus }
			STATUS current
			DESCRIPTION
				"Description."
			::= { sleBGPInfoNotification 19 }


		-- 1.3.6.1.4.1.6296.101.53.2.3.20
		sleBGPInfoNexthopTriggerDelayChanged NOTIFICATION-TYPE
			OBJECTS { sleBGPInfoControlRequest, sleBGPInfoControlTimeStamp, sleBGPInfoControlReqResult, sleBGPInfoNexthopTriggerDelay }
			STATUS current
			DESCRIPTION
				"Description."
			::= { sleBGPInfoNotification 20 }


		-- 1.3.6.1.4.1.6296.101.53.2.3.21
		sleBGPInfoSnmpNotificationChanged NOTIFICATION-TYPE
			OBJECTS { sleBGPInfoControlRequest, sleBGPInfoControlTimeStamp, sleBGPInfoControlReqResult, sleBGPInfoSnmpNotification }
			STATUS current
			DESCRIPTION
				"Description."
			::= { sleBGPInfoNotification 21 }


		-- 1.3.6.1.4.1.6296.101.53.2.3.22
		sleBGPInfoUpdateDelayChanged NOTIFICATION-TYPE
			OBJECTS { sleBGPInfoControlRequest, sleBGPInfoControlTimeStamp, sleBGPInfoControlReqResult, sleBGPInfoUpdateDelay }
			STATUS current
			DESCRIPTION
				"Description."
			::= { sleBGPInfoNotification 22 }


		-- 1.3.6.1.4.1.6296.101.53.2.3.23
		sleBGPInfoDistanceCreated NOTIFICATION-TYPE
			OBJECTS { sleBGPInfoControlRequest, sleBGPInfoControlTimeStamp, sleBGPInfoControlReqResult, sleBGPInfoExternalRouteDistance, sleBGPInfoInternalRouteDistance,
				sleBGPInfoLocalRouteDistance }
			STATUS current
			DESCRIPTION
				"Description."
			::= { sleBGPInfoNotification 23 }


		-- 1.3.6.1.4.1.6296.101.53.2.3.24
		sleBGPInfoDistanceDeleted NOTIFICATION-TYPE
			OBJECTS { sleBGPInfoControlRequest, sleBGPInfoControlTimeStamp, sleBGPInfoControlReqResult, sleBGPInfoControlExternalRouteDistance, sleBGPInfoControlInternalRouteDistance,
				sleBGPInfoControlLocalRouteDistance }
			STATUS current
			DESCRIPTION
				"Description."
			::= { sleBGPInfoNotification 24 }


		-- 1.3.6.1.4.1.6296.101.53.2.3.25
		sleBGPInfoMaximumPathChanged NOTIFICATION-TYPE
			OBJECTS { sleBGPInfoControlRequest, sleBGPInfoControlTimeStamp, sleBGPInfoControlReqResult, sleBGPInfoMaximumPath }
			STATUS current
			DESCRIPTION
				"Description."
			::= { sleBGPInfoNotification 25 }


		-- 1.3.6.1.4.1.6296.101.53.2.3.26
		sleBGPInfoMaximumPathIBGPChanged NOTIFICATION-TYPE
			OBJECTS { sleBGPInfoControlRequest, sleBGPInfoControlTimeStamp, sleBGPInfoControlReqResult, sleBGPInfoMaximumPathIBGP }
			STATUS current
			DESCRIPTION
				"Description."
			::= { sleBGPInfoNotification 26 }


		-- 1.3.6.1.4.1.6296.101.53.2.3.27
		sleBGPInfoTimersChanged NOTIFICATION-TYPE
			OBJECTS { sleBGPInfoControlRequest, sleBGPInfoControlTimeStamp, sleBGPInfoControlReqResult, sleBGPInfoKeepAliveInterval, sleBGPInfoHoldTime
				 }
			STATUS current
			DESCRIPTION
				"Description."
			::= { sleBGPInfoNotification 27 }


		-- 1.3.6.1.4.1.6296.101.53.3
		sleBGPAdminDistance OBJECT IDENTIFIER ::= { sleBGP 3 }


		-- 1.3.6.1.4.1.6296.101.53.3.1
		sleBGPAdminDistanceTable OBJECT-TYPE
			SYNTAX SEQUENCE OF SleBGPAdminDistanceEntry
			MAX-ACCESS not-accessible
			STATUS current
			DESCRIPTION
				"Description."
			::= { sleBGPAdminDistance 1 }


		-- 1.3.6.1.4.1.6296.101.53.3.1.1
		sleBGPAdminDistanceEntry OBJECT-TYPE
			SYNTAX SleBGPAdminDistanceEntry
			MAX-ACCESS not-accessible
			STATUS current
			DESCRIPTION
				"Description."
			INDEX { sleBGPAdminDistanceAddrPrefix }
			::= { sleBGPAdminDistanceTable 1 }


		SleBGPAdminDistanceEntry ::=
			SEQUENCE {
				sleBGPAdminDistanceAddrPrefix
					OCTET STRING,
				sleBGPAdminDistanceValue
					INTEGER,
				sleBGPAdminDistanceAccName
					OCTET STRING
			 }

		-- 1.3.6.1.4.1.6296.101.53.3.1.1.1
		sleBGPAdminDistanceAddrPrefix OBJECT-TYPE
			SYNTAX OCTET STRING
			MAX-ACCESS read-only
			STATUS current
			DESCRIPTION
				"Description."
			::= { sleBGPAdminDistanceEntry 1 }


		-- 1.3.6.1.4.1.6296.101.53.3.1.1.2
		sleBGPAdminDistanceValue OBJECT-TYPE
			SYNTAX INTEGER (1..255)
			MAX-ACCESS read-only
			STATUS current
			DESCRIPTION
				"Description."
			::= { sleBGPAdminDistanceEntry 2 }


		-- 1.3.6.1.4.1.6296.101.53.3.1.1.3
		sleBGPAdminDistanceAccName OBJECT-TYPE
			SYNTAX OCTET STRING (SIZE (0..512))
			MAX-ACCESS read-only
			STATUS current
			DESCRIPTION
				"Description."
			::= { sleBGPAdminDistanceEntry 3 }


		-- 1.3.6.1.4.1.6296.101.53.3.2
		sleBGPAdminDistanceControl OBJECT IDENTIFIER ::= { sleBGPAdminDistance 2 }


		-- 1.3.6.1.4.1.6296.101.53.3.2.1
		sleBGPAdminDistanceControlRequest OBJECT-TYPE
			SYNTAX INTEGER
				{
				createBGPAdminDistance(1),
				deleteBGPAdminDistance(2)
				}
			MAX-ACCESS read-write
			STATUS current
			DESCRIPTION
				"Description."
			::= { sleBGPAdminDistanceControl 1 }


		-- 1.3.6.1.4.1.6296.101.53.3.2.2
		sleBGPAdminDistanceControlStatus OBJECT-TYPE
			SYNTAX SleControlStatusType
			MAX-ACCESS read-only
			STATUS current
			DESCRIPTION
				"Description."
			::= { sleBGPAdminDistanceControl 2 }


		-- 1.3.6.1.4.1.6296.101.53.3.2.3
		sleBGPAdminDistanceControlTimer OBJECT-TYPE
			SYNTAX Gauge32
			MAX-ACCESS read-write
			STATUS current
			DESCRIPTION
				"Description."
			::= { sleBGPAdminDistanceControl 3 }


		-- 1.3.6.1.4.1.6296.101.53.3.2.4
		sleBGPAdminDistanceControlTimeStamp OBJECT-TYPE
			SYNTAX TimeTicks
			MAX-ACCESS read-only
			STATUS current
			DESCRIPTION
				"Description."
			::= { sleBGPAdminDistanceControl 4 }


		-- 1.3.6.1.4.1.6296.101.53.3.2.5
		sleBGPAdminDistanceControlReqResult OBJECT-TYPE
			SYNTAX SleControlRequestResultType
			MAX-ACCESS read-only
			STATUS current
			DESCRIPTION
				"Description."
			::= { sleBGPAdminDistanceControl 5 }


		-- 1.3.6.1.4.1.6296.101.53.3.2.6
		sleBGPAdminDistanceControlAddrPrefix OBJECT-TYPE
			SYNTAX OCTET STRING
			MAX-ACCESS read-write
			STATUS current
			DESCRIPTION
				"Description."
			::= { sleBGPAdminDistanceControl 6 }


		-- 1.3.6.1.4.1.6296.101.53.3.2.7
		sleBGPAdminDistanceControlValue OBJECT-TYPE
			SYNTAX INTEGER (1..255)
			MAX-ACCESS read-write
			STATUS current
			DESCRIPTION
				"Description."
			::= { sleBGPAdminDistanceControl 7 }


		-- 1.3.6.1.4.1.6296.101.53.3.2.8
		sleBGPAdminDistanceControlAccName OBJECT-TYPE
			SYNTAX OCTET STRING (SIZE (0..512))
			MAX-ACCESS read-write
			STATUS current
			DESCRIPTION
				"Description."
			::= { sleBGPAdminDistanceControl 8 }


		-- 1.3.6.1.4.1.6296.101.53.3.3
		sleBGPAdminDistanceNotification OBJECT IDENTIFIER ::= { sleBGPAdminDistance 3 }


		-- 1.3.6.1.4.1.6296.101.53.3.3.1
		sleBGPAdminDistanceCreated NOTIFICATION-TYPE
			OBJECTS { sleBGPAdminDistanceControlRequest, sleBGPAdminDistanceControlTimeStamp, sleBGPAdminDistanceControlReqResult, sleBGPAdminDistanceAddrPrefix, sleBGPAdminDistanceValue,
				sleBGPAdminDistanceAccName }
			STATUS current
			DESCRIPTION
				"Description."
			::= { sleBGPAdminDistanceNotification 1 }


		-- 1.3.6.1.4.1.6296.101.53.3.3.2
		sleBGPAdminDistanceDeleted NOTIFICATION-TYPE
			OBJECTS { sleBGPBaseAsNumber, sleBGPBaseConfigType, sleBGPBaseRfc1771PathSelect, sleBGPBaseRfc1771Strict, sleBGPBaseAggregateNextHop,
				sleBGPBaseExtendAsnCap, sleBGPBaseControlRequest, sleBGPBaseControlStatus, sleBGPBaseControlTimer, sleBGPBaseControlTimeStamp,
				sleBGPBaseControlReqResult, sleBGPBaseControlAsNumber, sleBGPBaseControlConfigType, sleBGPBaseControlRfc1771PathSelect, sleBGPBaseControlRfc1771Strict,
				sleBGPBaseControlAggregateNextHop, sleBGPBaseControlExtendAsnCap, sleBGPBaseControlClearFamilyMode, sleBGPBaseControlClearFamilyType, sleBGPBaseControlClearDirection,
				sleBGPBaseControlClearSoft, sleBGPBaseControlClearPrefixFilter, sleBGPBaseControlClearPeerName, sleBGPBaseControlClearIPv4Addr, sleBGPBaseControlClearIPv6Addr,
				sleBGPBaseControlClearViewName, sleBGPInfoRouterID, sleBGPInfoLogNeighborChange, sleBGPInfoAlwaysCompareMed, sleBGPInfoBestPathAsPathIgnore,
				sleBGPInfoBestPathCompareConfedAsPath, sleBGPInfoBestPathCompareRouterID, sleBGPInfoBestPathCompareMedConfed, sleBGPInfoBestPathCompareMedMisAsWorst, sleBGPInfoClientToClient,
				sleBGPInfoClusterID, sleBGPInfoConfederationID, sleBGPInfoDeterministicMed, sleBGPInfoEnforceFirstAs, sleBGPInfoFastExternalFailOver,
				sleBGPInfoGracefulRestartTime, sleBGPInfoGracefulStalepathTime, sleBGPInfoScanTime, sleBGPInfoNexthopTriggerStatus, sleBGPInfoNexthopTriggerDelay,
				sleBGPInfoSnmpNotification, sleBGPInfoUpdateDelay, sleBGPInfoExternalRouteDistance, sleBGPInfoInternalRouteDistance, sleBGPInfoLocalRouteDistance,
				sleBGPInfoMaximumPath, sleBGPInfoMaximumPathIBGP, sleBGPInfoKeepAliveInterval, sleBGPInfoHoldTime, sleBGPInfoControlRequest,
				sleBGPInfoControlStatus, sleBGPInfoControlTimer, sleBGPInfoControlTimeStamp, sleBGPInfoControlReqResult, sleBGPInfoControlRouterID,
				sleBGPInfoControlLogNeighborChange, sleBGPInfoControlAlwaysCompareMed, sleBGPInfoControlBestPathAsPathIgnore, sleBGPInfoControlBestPathCompareConfedAsPath, sleBGPInfoControlBestPathCompareRouterID,
				sleBGPInfoControlBestPathCompareMedConfed, sleBGPInfoControlBestPathCompareMedMisAsWorst, sleBGPInfoControlClientToClient, sleBGPInfoControlClusterID, sleBGPInfoControlConfederationID,
				sleBGPInfoControlDeterministicMed, sleBGPInfoControlEnforceFirstAs, sleBGPInfoControlFastExternalFailOver, sleBGPInfoControlGracefulRestartTime, sleBGPInfoControlGracefulStalepathTime,
				sleBGPInfoControlScanTime, sleBGPInfoControlNexthopTriggerStatus, sleBGPInfoControlNexthopTriggerDelay, sleBGPInfoControlSnmpNotification, sleBGPInfoControlUpdateDelay,
				sleBGPInfoControlExternalRouteDistance, sleBGPInfoControlInternalRouteDistance, sleBGPInfoControlLocalRouteDistance, sleBGPInfoControlMaximumPath, sleBGPInfoControlMaximumPathIBGP,
				sleBGPInfoControlKeepAliveInterval, sleBGPInfoControlHoldTime, sleBGPAdminDistanceAddrPrefix, sleBGPAdminDistanceValue, sleBGPAdminDistanceAccName,
				sleBGPAdminDistanceControlRequest, sleBGPAdminDistanceControlStatus, sleBGPAdminDistanceControlTimer, sleBGPAdminDistanceControlTimeStamp, sleBGPAdminDistanceControlReqResult,
				sleBGPAdminDistanceControlAddrPrefix, sleBGPAdminDistanceControlValue, sleBGPAdminDistanceControlAccName, sleBGPPeerName, sleBGPPeerAsNum,
				sleBGPPeerGroupName, sleBGPPeerAdvInterval, sleBGPPeerAsOriInterval, sleBGPPeerDesc, sleBGPPeerDontCapNego,
				sleBGPPeerWeight, sleBGPPeerEnforcMultiHop, sleBGPPeerPassive, sleBGPPeerUpSourceName, sleBGPPeerPort,
				sleBGPPeerRetstartTime, sleBGPPeerShutDown, sleBGPPeerKeepInterval, sleBGPPeerHoldInterval, sleBGPPeerConnInterval,
				sleBGPPeerOverCap, sleBGPPeerStrictCapMatch, sleBGPPeerIfname, sleBGPPeerCapRouteRefresh, sleBGPPeerCapDynamic,
				sleBGPPeerEBGPMulthopCount, sleBGPPeerPassword, sleBGPPeerControlRequest, sleBGPPeerControlStatus, sleBGPPeerControlTimer,
				sleBGPPeerControlTimeStamp, sleBGPPeerControlReqResult, sleBGPPeerControlName, sleBGPPeerControlAsNum, sleBGPPeerControlGroupName,
				sleBGPPeerControlAdvInterval, sleBGPPeerControlAsOriInterval, sleBGPPeerControlDesc, sleBGPPeerControlDontCapNego, sleBGPPeerControlWeight,
				sleBGPPeerControlEnforcMultiHop, sleBGPPeerControlPassive, sleBGPPeerControlUpSourceName, sleBGPPeerControlPort, sleBGPPeerControlRetstartTime,
				sleBGPPeerControlShutDown, sleBGPPeerControlKeepInterval, sleBGPPeerControlHoldInterval, sleBGPPeerControlConnInterval, sleBGPPeerControlOverCap,
				sleBGPPeerControlStrictCapMatch, sleBGPPeerControlIfname, sleBGPPeerControlCapRouteRefresh, sleBGPPeerControlCapDynamic, sleBGPPeerControlEBGPMulthopCount,
				sleBGPPeerControlPassword, sleBGPPeerGroupStr, sleBGPPeerGroupAsNum, sleBGPPeerGroupAdvInterval, sleBGPPeerGroupAsOriInterval,
				sleBGPPeerGroupDesc, sleBGPPeerGroupDontCapNego, sleBGPPeerGroupWeight, sleBGPPeerGroupEnforcMultiHop, sleBGPPeerGroupPassive,
				sleBGPPeerGroupUpSourceName, sleBGPPeerGroupPort, sleBGPPeerGroupRetstartTime, sleBGPPeerGroupShutDown, sleBGPPeerGroupKeepInterval,
				sleBGPPeerGroupHoldInterval, sleBGPPeerGroupConnInterval, sleBGPPeerGroupOverCap, sleBGPPeerGroupStrictCapMatch, sleBGPPeerGroupCapRouteRefresh,
				sleBGPPeerGroupCapDynamic, sleBGPPeerGroupEBGPMulthopCount, sleBGPPeerGroupPassword, sleBGPPeerGroupControlRequest, sleBGPPeerGroupControlStatus,
				sleBGPPeerGroupControlTimer, sleBGPPeerGroupControlTimeStamp, sleBGPPeerGroupControlReqResult, sleBGPPeerGroupControlStr, sleBGPPeerGroupControlAsNum,
				sleBGPPeerGroupControlAdvInterval, sleBGPPeerGroupControlAsOriInterval, sleBGPPeerGroupControlDesc, sleBGPPeerGroupControlDontCapNego, sleBGPPeerGroupControlWeight,
				sleBGPPeerGroupControlEnforcMultiHop, sleBGPPeerGroupControlPassive, sleBGPPeerGroupControlUpSourceName, sleBGPPeerGroupControlPort, sleBGPPeerGroupControlRetstartTime,
				sleBGPPeerGroupControlShutDown, sleBGPPeerGroupControlKeepInterval, sleBGPPeerGroupControlHoldInterval, sleBGPPeerGroupControlConnInterval, sleBGPPeerGroupControlOverCap,
				sleBGPPeerGroupControlStrictCapMatch, sleBGPPeerGroupControlCapRouteRefresh, sleBGPPeerGroupControlCapDynamic, sleBGPPeerGroupControlEBGPMulthopCount, sleBGPPeerGroupControlPassword,
				sleBGPAFBaseMode, sleBGPAFBaseType, sleBGPAFBaseNetworkCheck, sleBGPAFBaseSync, sleBGPAFBaseDefOrg,
				sleBGPAFBaseDampRoutemapName, sleBGPAFBaseDampReachHlife, sleBGPAFBaseDampReuse, sleBGPAFBaseDampSuppress, sleBGPAFBaseDampMaxSuppress,
				sleBGPAFBaseDampUnReachHlife, sleBGPAFBaseControlRequest, sleBGPAFBaseControlStatus, sleBGPAFBaseControlTimer, sleBGPAFBaseControlTimeStamp,
				sleBGPAFBaseControlReqResult, sleBGPAFBaseControlMode, sleBGPAFBaseControlType, sleBGPAFBaseControlNetworkCheck, sleBGPAFBaseControlSync,
				sleBGPAFBaseControlDefOrg, sleBGPAFBaseControlDampRoutemapName, sleBGPAFBaseControlDampReachHlife, sleBGPAFBaseControlDampReuse, sleBGPAFBaseControlDampSuppress,
				sleBGPAFBaseControlDampMaxSuppress, sleBGPAFBaseControlDampUnReachHlife, sleBGPAFRedistMode, sleBGPAFRedistType, sleBGPAFRedistProtoType,
				sleBGPAFRedistRoutemapName, sleBGPAFRedistControlRequest, sleBGPAFRedistControlStatus, sleBGPAFRedistControlTimer, sleBGPAFRedistControlTimeStamp,
				sleBGPAFRedistControlReqResult, sleBGPAFRedistControlMode, sleBGPAFRedistControlType, sleBGPAFRedistControlProtoType, sleBGPAFRedistControlRoutemapName,
				sleBGPAFAggreAddrMode, sleBGPAFAggreAddrType, sleBGPAFAggreAddrIPType, sleBGPAFAggreAddrIPPrefix, sleBGPAFAggreAddrIPMask,
				sleBGPAFAggreAddrAsSet, sleBGPAFAggreAddrSummOnly, sleBGPAFAggreAddrControlRequest, sleBGPAFAggreAddrControlStatus, sleBGPAFAggreAddrControlTimer,
				sleBGPAFAggreAddrControlTimeStamp, sleBGPAFAggreAddrControlReqResult, sleBGPAFAggreAddrControlMode, sleBGPAFAggreAddrControlType, sleBGPAFAggreAddrControlIPType,
				sleBGPAFAggreAddrControlIPPrefix, sleBGPAFAggreAddrControlIPMask, sleBGPAFAggreAddrControlAsSet, sleBGPAFAggreAddrControlSummOnly, sleBGPAFPeerMode,
				sleBGPAFPeerType, sleBGPAFPeerName, sleBGPAFPeerActviate, sleBGPAFPeerAllowAsIn, sleBGPAFPeerAllowAsInNum,
				sleBGPAFPeerAttrUnchangedAsPath, sleBGPAFPeerAttrUnchangedMed, sleBGPAFPeerAttrUnchangedNexthop, sleBGPAFPeerCapGracefulRestart, sleBGPAFPeerCapOrfMode,
				sleBGPAFPeerDefOriginate, sleBGPAFPeerDefOriginateRoutemap, sleBGPAFPeerFLInAccName, sleBGPAFPeerFLOutAccName, sleBGPAFPeerMaxPrefixNum,
				sleBGPAFPeerMaxPrefixThreshold, sleBGPAFPeerMaxPrefixWarnOnly, sleBGPAFPeerRemotePrivateAs, sleBGPAFPeerInRoutemap, sleBGPAFPeerOutRoutemap,
				sleBGPAFPeerRouteReflectClient, sleBGPAFPeerRouteServerClient, sleBGPAFPeerInDistListName, sleBGPAFPeerOutDistListName, sleBGPAFPeerInPrefixListName,
				sleBGPAFPeerOutPrefixListName, sleBGPAFPeerSendCommunity, sleBGPAFPeerNexthopSelf, sleBGPAFPeerSoftReconfig, sleBGPAFPeerUnsuppressMapName,
				sleBGPAFPeerControlRequest, sleBGPAFPeerControlStatus, sleBGPAFPeerControlTimer, sleBGPAFPeerControlTimeStamp, sleBGPAFPeerControlReqResult,
				sleBGPAFPeerControlMode, sleBGPAFPeerControlType, sleBGPAFPeerControlName, sleBGPAFPeerControlActviate, sleBGPAFPeerControlAllowAsIn,
				sleBGPAFPeerControlAllowAsInNum, sleBGPAFPeerControlAttrUnchangedAsPath, sleBGPAFPeerControlAttrUnchangedMed, sleBGPAFPeerControlAttrUnchangedNexthop, sleBGPAFPeerControlCapGracefulRestart,
				sleBGPAFPeerControlCapOrfMode, sleBGPAFPeerControlDefOriginate, sleBGPAFPeerControlDefOriginateRoutemap, sleBGPAFPeerControlFLInAccName, sleBGPAFPeerControlFLOutAccName,
				sleBGPAFPeerControlMaxPrefixNum, sleBGPAFPeerControlMaxPrefixThreshold, sleBGPAFPeerControlMaxPrefixWarnOnly, sleBGPAFPeerControlRemotePrivateAs, sleBGPAFPeerControlInRoutemap,
				sleBGPAFPeerControlOutRoutemap, sleBGPAFPeerControlRouteReflectClient, sleBGPAFPeerControlRouteServerClient, sleBGPAFPeerControlInDistListName, sleBGPAFPeerControlOutDistListName,
				sleBGPAFPeerControlInPrefixListName, sleBGPAFPeerControlOutPrefixListName, sleBGPAFPeerControlSendCommunity, sleBGPAFPeerControlNexthopSelf, sleBGPAFPeerControlSoftReconfig,
				sleBGPAFPeerControlUnsuppressMapName, sleBGPAFPeerGroupMode, sleBGPAFPeerGroupType, sleBGPAFPeerGroupName, sleBGPAFPeerGroupActviate,
				sleBGPAFPeerGroupAllowAsIn, sleBGPAFPeerGroupAllowAsInNum, sleBGPAFPeerGroupAttrUnchangedAsPath, sleBGPAFPeerGroupAttrUnchangedMed, sleBGPAFPeerGroupAttrUnchangedNexthop,
				sleBGPAFPeerGroupCapGracefulRestart, sleBGPAFPeerGroupCapOrfMode, sleBGPAFPeerGroupDefOriginate, sleBGPAFPeerGroupDefOriginateRoutemap, sleBGPAFPeerGroupFLInAccName,
				sleBGPAFPeerGroupFLOutAccName, sleBGPAFPeerGroupMaxPrefixNum, sleBGPAFPeerGroupMaxPrefixThreshold, sleBGPAFPeerGroupMaxPrefixWarnOnly, sleBGPAFPeerGroupRemotePrivateAs,
				sleBGPAFPeerGroupInRoutemap, sleBGPAFPeerGroupOutRoutemap, sleBGPAFPeerGroupRouteReflectClient, sleBGPAFPeerGroupRouteServerClient, sleBGPAFPeerGroupInDistListName,
				sleBGPAFPeerGroupOutDistListName, sleBGPAFPeerGroupInPrefixListName, sleBGPAFPeerGroupOutPrefixListName, sleBGPAFPeerGroupSendCommunity, sleBGPAFPeerGroupNexthopSelf,
				sleBGPAFPeerGroupSoftReconfig, sleBGPAFPeerGroupUnsuppressMapName, sleBGPAFPeerGroupControlRequest, sleBGPAFPeerGroupControlStatus, sleBGPAFPeerGroupControlTimer,
				sleBGPAFPeerGroupControlTimeStamp, sleBGPAFPeerGroupControlReqResult, sleBGPAFPeerGroupControlMode, sleBGPAFPeerGroupControlType, sleBGPAFPeerGroupControlName,
				sleBGPAFPeerGroupControlActviate, sleBGPAFPeerGroupControlAllowAsIn, sleBGPAFPeerGroupControlAllowAsInNum, sleBGPAFPeerGroupControlAttrUnchangedAsPath, sleBGPAFPeerGroupControlAttrUnchangedMed,
				sleBGPAFPeerGroupControlAttrUnchangedNexthop, sleBGPAFPeerGroupControlCapGracefulRestart, sleBGPAFPeerGroupControlCapOrfMode, sleBGPAFPeerGroupControlDefOriginate, sleBGPAFPeerGroupControlDefOriginateRoutemap,
				sleBGPAFPeerGroupControlFLInAccName, sleBGPAFPeerGroupControlFLOutAccName, sleBGPAFPeerGroupControlMaxPrefixNum, sleBGPAFPeerGroupControlMaxPrefixThreshold, sleBGPAFPeerGroupControlMaxPrefixWarnOnly,
				sleBGPAFPeerGroupControlRemotePrivateAs, sleBGPAFPeerGroupControlInRoutemap, sleBGPAFPeerGroupControlOutRoutemap, sleBGPAFPeerGroupControlRouteReflectClient, sleBGPAFPeerGroupControlRouteServerClient,
				sleBGPAFPeerGroupControlInDistListName, sleBGPAFPeerGroupControlOutDistListName, sleBGPAFPeerGroupControlInPrefixListName, sleBGPAFPeerGroupControlOutPrefixListName, sleBGPAFPeerGroupControlSendCommunity,
				sleBGPAFPeerGroupControlNexthopSelf, sleBGPAFPeerGroupControlSoftReconfig, sleBGPAFPeerGroupControlUnsuppressMapName, sleBGPAFNetworkMode, sleBGPAFNetworkType,
				sleBGPAFNetworkAddrType, sleBGPAFNetworkAddr, sleBGPAFNetworkAddrMask, sleBGPAFNetworkBackdoor, sleBGPAFNetworkRoutemap,
				sleBGPAFNetworkControlRequest, sleBGPAFNetworkControlStatus, sleBGPAFNetworkControlTimer, sleBGPAFNetworkControlTimeStamp, sleBGPAFNetworkControlReqResult,
				sleBGPAFNetworkControlMode, sleBGPAFNetworkControlType, sleBGPAFNetworkControlAddrType, sleBGPAFNetworkControlAddr, sleBGPAFNetworkControlAddrMask,
				sleBGPAFNetworkControlBackdoor, sleBGPAFNetworkControlRoutemap }
			STATUS current
			DESCRIPTION
				"Description."
			::= { sleBGPAdminDistanceNotification 2 }


		-- 1.3.6.1.4.1.6296.101.53.4
		sleBGPPeerInfo OBJECT IDENTIFIER ::= { sleBGP 4 }


		-- 1.3.6.1.4.1.6296.101.53.4.1
		sleBGPPeer OBJECT IDENTIFIER ::= { sleBGPPeerInfo 1 }


		-- 1.3.6.1.4.1.6296.101.53.4.1.1
		sleBGPPeerTable OBJECT-TYPE
			SYNTAX SEQUENCE OF SleBGPPeerEntry
			MAX-ACCESS not-accessible
			STATUS current
			DESCRIPTION
				"Description."
			::= { sleBGPPeer 1 }


		-- 1.3.6.1.4.1.6296.101.53.4.1.1.1
		sleBGPPeerEntry OBJECT-TYPE
			SYNTAX SleBGPPeerEntry
			MAX-ACCESS not-accessible
			STATUS current
			DESCRIPTION
				"Description."
			INDEX { sleBGPPeerName }
			::= { sleBGPPeerTable 1 }


		SleBGPPeerEntry ::=
			SEQUENCE {
				sleBGPPeerName
					OCTET STRING,
				sleBGPPeerAsNum
					Gauge32,
				sleBGPPeerGroupName
					OCTET STRING,
				sleBGPPeerAdvInterval
					INTEGER,
				sleBGPPeerAsOriInterval
					INTEGER,
				sleBGPPeerDesc
					OCTET STRING,
				sleBGPPeerDontCapNego
					INTEGER,
				sleBGPPeerWeight
					INTEGER,
				sleBGPPeerEnforcMultiHop
					INTEGER,
				sleBGPPeerPassive
					INTEGER,
				sleBGPPeerUpSourceName
					OCTET STRING,
				sleBGPPeerPort
					INTEGER,
				sleBGPPeerRetstartTime
					INTEGER,
				sleBGPPeerShutDown
					INTEGER,
				sleBGPPeerKeepInterval
					INTEGER,
				sleBGPPeerHoldInterval
					INTEGER,
				sleBGPPeerConnInterval
					INTEGER,
				sleBGPPeerOverCap
					INTEGER,
				sleBGPPeerStrictCapMatch
					INTEGER,
				sleBGPPeerIfname
					OCTET STRING,
				sleBGPPeerCapRouteRefresh
					INTEGER,
				sleBGPPeerCapDynamic
					INTEGER,
				sleBGPPeerEBGPMulthopCount
					INTEGER,
				sleBGPPeerPassword
					OCTET STRING
			 }

		-- 1.3.6.1.4.1.6296.101.53.4.1.1.1.1
		sleBGPPeerName OBJECT-TYPE
			SYNTAX OCTET STRING (SIZE (0..512))
			MAX-ACCESS read-only
			STATUS current
			DESCRIPTION
				"Description."
			::= { sleBGPPeerEntry 1 }


		-- 1.3.6.1.4.1.6296.101.53.4.1.1.1.2
		sleBGPPeerAsNum OBJECT-TYPE
			SYNTAX Gauge32 (1..4294967295)
			MAX-ACCESS read-only
			STATUS current
			DESCRIPTION
				"Description."
			::= { sleBGPPeerEntry 2 }


		-- 1.3.6.1.4.1.6296.101.53.4.1.1.1.3
		sleBGPPeerGroupName OBJECT-TYPE
			SYNTAX OCTET STRING (SIZE (0..80))
			MAX-ACCESS read-only
			STATUS current
			DESCRIPTION
				"Description."
			::= { sleBGPPeerEntry 3 }


		-- 1.3.6.1.4.1.6296.101.53.4.1.1.1.4
		sleBGPPeerAdvInterval OBJECT-TYPE
			SYNTAX INTEGER (0..600)
			MAX-ACCESS read-only
			STATUS current
			DESCRIPTION
				"Description."
			::= { sleBGPPeerEntry 4 }


		-- 1.3.6.1.4.1.6296.101.53.4.1.1.1.5
		sleBGPPeerAsOriInterval OBJECT-TYPE
			SYNTAX INTEGER (0..600)
			MAX-ACCESS read-only
			STATUS current
			DESCRIPTION
				"Description."
			::= { sleBGPPeerEntry 5 }


		-- 1.3.6.1.4.1.6296.101.53.4.1.1.1.6
		sleBGPPeerDesc OBJECT-TYPE
			SYNTAX OCTET STRING (SIZE (0..80))
			MAX-ACCESS read-only
			STATUS current
			DESCRIPTION
				"Description."
			::= { sleBGPPeerEntry 6 }


		-- 1.3.6.1.4.1.6296.101.53.4.1.1.1.7
		sleBGPPeerDontCapNego OBJECT-TYPE
			SYNTAX INTEGER
				{
				disable(0),
				enable(1)
				}
			MAX-ACCESS read-only
			STATUS current
			DESCRIPTION
				"Description."
			::= { sleBGPPeerEntry 7 }


		-- 1.3.6.1.4.1.6296.101.53.4.1.1.1.8
		sleBGPPeerWeight OBJECT-TYPE
			SYNTAX INTEGER (0..65535)
			MAX-ACCESS read-only
			STATUS current
			DESCRIPTION
				"Description."
			::= { sleBGPPeerEntry 8 }


		-- 1.3.6.1.4.1.6296.101.53.4.1.1.1.9
		sleBGPPeerEnforcMultiHop OBJECT-TYPE
			SYNTAX INTEGER
				{
				disable(0),
				enable(1)
				}
			MAX-ACCESS read-only
			STATUS current
			DESCRIPTION
				"Description."
			::= { sleBGPPeerEntry 9 }


		-- 1.3.6.1.4.1.6296.101.53.4.1.1.1.10
		sleBGPPeerPassive OBJECT-TYPE
			SYNTAX INTEGER
				{
				disable(0),
				enable(1)
				}
			MAX-ACCESS read-only
			STATUS current
			DESCRIPTION
				"Description."
			::= { sleBGPPeerEntry 10 }


		-- 1.3.6.1.4.1.6296.101.53.4.1.1.1.11
		sleBGPPeerUpSourceName OBJECT-TYPE
			SYNTAX OCTET STRING
			MAX-ACCESS read-only
			STATUS current
			DESCRIPTION
				"Description."
			::= { sleBGPPeerEntry 11 }


		-- 1.3.6.1.4.1.6296.101.53.4.1.1.1.12
		sleBGPPeerPort OBJECT-TYPE
			SYNTAX INTEGER (0..65535)
			MAX-ACCESS read-only
			STATUS current
			DESCRIPTION
				"Description."
			::= { sleBGPPeerEntry 12 }


		-- 1.3.6.1.4.1.6296.101.53.4.1.1.1.13
		sleBGPPeerRetstartTime OBJECT-TYPE
			SYNTAX INTEGER (1..65535)
			MAX-ACCESS read-only
			STATUS current
			DESCRIPTION
				"Description."
			::= { sleBGPPeerEntry 13 }


		-- 1.3.6.1.4.1.6296.101.53.4.1.1.1.14
		sleBGPPeerShutDown OBJECT-TYPE
			SYNTAX INTEGER
				{
				disable(0),
				enable(1)
				}
			MAX-ACCESS read-only
			STATUS current
			DESCRIPTION
				"Description."
			::= { sleBGPPeerEntry 14 }


		-- 1.3.6.1.4.1.6296.101.53.4.1.1.1.15
		sleBGPPeerKeepInterval OBJECT-TYPE
			SYNTAX INTEGER (0..65535)
			MAX-ACCESS read-only
			STATUS current
			DESCRIPTION
				"Description."
			::= { sleBGPPeerEntry 15 }


		-- 1.3.6.1.4.1.6296.101.53.4.1.1.1.16
		sleBGPPeerHoldInterval OBJECT-TYPE
			SYNTAX INTEGER (0..65535)
			MAX-ACCESS read-only
			STATUS current
			DESCRIPTION
				"Description."
			::= { sleBGPPeerEntry 16 }


		-- 1.3.6.1.4.1.6296.101.53.4.1.1.1.17
		sleBGPPeerConnInterval OBJECT-TYPE
			SYNTAX INTEGER (0..65535)
			MAX-ACCESS read-only
			STATUS current
			DESCRIPTION
				"Description."
			::= { sleBGPPeerEntry 17 }


		-- 1.3.6.1.4.1.6296.101.53.4.1.1.1.18
		sleBGPPeerOverCap OBJECT-TYPE
			SYNTAX INTEGER
				{
				disable(0),
				enable(1)
				}
			MAX-ACCESS read-only
			STATUS current
			DESCRIPTION
				"Description."
			::= { sleBGPPeerEntry 18 }


		-- 1.3.6.1.4.1.6296.101.53.4.1.1.1.19
		sleBGPPeerStrictCapMatch OBJECT-TYPE
			SYNTAX INTEGER
				{
				disable(0),
				enable(1)
				}
			MAX-ACCESS read-only
			STATUS current
			DESCRIPTION
				"Description."
			::= { sleBGPPeerEntry 19 }


		-- 1.3.6.1.4.1.6296.101.53.4.1.1.1.20
		sleBGPPeerIfname OBJECT-TYPE
			SYNTAX OCTET STRING
			MAX-ACCESS read-only
			STATUS current
			DESCRIPTION
				"Description."
			::= { sleBGPPeerEntry 20 }


		-- 1.3.6.1.4.1.6296.101.53.4.1.1.1.21
		sleBGPPeerCapRouteRefresh OBJECT-TYPE
			SYNTAX INTEGER
				{
				disable(0),
				enable(1)
				}
			MAX-ACCESS read-only
			STATUS current
			DESCRIPTION
				"Description."
			::= { sleBGPPeerEntry 21 }


		-- 1.3.6.1.4.1.6296.101.53.4.1.1.1.22
		sleBGPPeerCapDynamic OBJECT-TYPE
			SYNTAX INTEGER
				{
				disable(0),
				enable(1)
				}
			MAX-ACCESS read-only
			STATUS current
			DESCRIPTION
				"Description."
			::= { sleBGPPeerEntry 22 }


		-- 1.3.6.1.4.1.6296.101.53.4.1.1.1.23
		sleBGPPeerEBGPMulthopCount OBJECT-TYPE
			SYNTAX INTEGER (0..255)
			MAX-ACCESS read-only
			STATUS current
			DESCRIPTION
				"Description."
			::= { sleBGPPeerEntry 23 }


		-- 1.3.6.1.4.1.6296.101.53.4.1.1.1.24
		sleBGPPeerPassword OBJECT-TYPE
			SYNTAX OCTET STRING (SIZE (0..512))
			MAX-ACCESS read-only
			STATUS current
			DESCRIPTION
				"Description."
			::= { sleBGPPeerEntry 24 }


		-- 1.3.6.1.4.1.6296.101.53.4.1.2
		sleBGPPeerControl OBJECT IDENTIFIER ::= { sleBGPPeer 2 }


		-- 1.3.6.1.4.1.6296.101.53.4.1.2.1
		sleBGPPeerControlRequest OBJECT-TYPE
			SYNTAX INTEGER
				{
				createBGPPeer(1),
				deleteBGPPeer(2),
				createPeerGroupName(3),
				deletePeerGroupName(4),
				setBGPPeerAdvInterval(5),
				setBGPPeerAsOriInterval(6),
				createBGPPeerDescription(7),
				deleteBGPPeerDescription(8),
				setBGPPeerDontCapNego(9),
				setBGPPeerWeight(10),
				setBGPPeerEnforceMultihop(11),
				setBGPPeerPassive(12),
				createBGPPeerUpSourceName(13),
				deleteBGPPeerUpSourceName(14),
				setBGPPeerPort(15),
				setBGPPeerRestartTime(16),
				setBGPPeerShutDown(17),
				setBGPPeerTimersProfile(18),
				setBGPPeerConnectInterval(19),
				setBGPPeerOverCap(20),
				setBGPPeerStrictCapMatch(21),
				createBGPPeerIfname(22),
				deleteBGPPeerIfname(23),
				setBGPPeerCapRouteRefresh(24),
				setBGPPeerCapDynamic(25),
				setBGPPeerEBGPMulthopCount(26),
				createBGPPeerPassword(27),
				deleteBGPPeerPassword(28)
				}
			MAX-ACCESS read-write
			STATUS current
			DESCRIPTION
				"Description."
			::= { sleBGPPeerControl 1 }


		-- 1.3.6.1.4.1.6296.101.53.4.1.2.2
		sleBGPPeerControlStatus OBJECT-TYPE
			SYNTAX SleControlStatusType
			MAX-ACCESS read-only
			STATUS current
			DESCRIPTION
				"Description."
			::= { sleBGPPeerControl 2 }


		-- 1.3.6.1.4.1.6296.101.53.4.1.2.3
		sleBGPPeerControlTimer OBJECT-TYPE
			SYNTAX Gauge32
			MAX-ACCESS read-write
			STATUS current
			DESCRIPTION
				"Description."
			::= { sleBGPPeerControl 3 }


		-- 1.3.6.1.4.1.6296.101.53.4.1.2.4
		sleBGPPeerControlTimeStamp OBJECT-TYPE
			SYNTAX TimeTicks
			MAX-ACCESS read-only
			STATUS current
			DESCRIPTION
				"Description."
			::= { sleBGPPeerControl 4 }


		-- 1.3.6.1.4.1.6296.101.53.4.1.2.5
		sleBGPPeerControlReqResult OBJECT-TYPE
			SYNTAX SleControlRequestResultType
			MAX-ACCESS read-only
			STATUS current
			DESCRIPTION
				"Description."
			::= { sleBGPPeerControl 5 }


		-- 1.3.6.1.4.1.6296.101.53.4.1.2.6
		sleBGPPeerControlName OBJECT-TYPE
			SYNTAX OCTET STRING (SIZE (0..512))
			MAX-ACCESS read-write
			STATUS current
			DESCRIPTION
				"Description."
			::= { sleBGPPeerControl 6 }


		-- 1.3.6.1.4.1.6296.101.53.4.1.2.7
		sleBGPPeerControlAsNum OBJECT-TYPE
			SYNTAX Gauge32 (1..4294967295)
			MAX-ACCESS read-write
			STATUS current
			DESCRIPTION
				"Description."
			::= { sleBGPPeerControl 7 }


		-- 1.3.6.1.4.1.6296.101.53.4.1.2.8
		sleBGPPeerControlGroupName OBJECT-TYPE
			SYNTAX OCTET STRING (SIZE (0..80))
			MAX-ACCESS read-write
			STATUS current
			DESCRIPTION
				"Description."
			::= { sleBGPPeerControl 8 }


		-- 1.3.6.1.4.1.6296.101.53.4.1.2.9
		sleBGPPeerControlAdvInterval OBJECT-TYPE
			SYNTAX INTEGER (0..600)
			MAX-ACCESS read-write
			STATUS current
			DESCRIPTION
				"Description."
			::= { sleBGPPeerControl 9 }


		-- 1.3.6.1.4.1.6296.101.53.4.1.2.10
		sleBGPPeerControlAsOriInterval OBJECT-TYPE
			SYNTAX INTEGER (0..600)
			MAX-ACCESS read-write
			STATUS current
			DESCRIPTION
				"Description."
			::= { sleBGPPeerControl 10 }


		-- 1.3.6.1.4.1.6296.101.53.4.1.2.11
		sleBGPPeerControlDesc OBJECT-TYPE
			SYNTAX OCTET STRING (SIZE (0..80))
			MAX-ACCESS read-write
			STATUS current
			DESCRIPTION
				"Description."
			::= { sleBGPPeerControl 11 }


		-- 1.3.6.1.4.1.6296.101.53.4.1.2.12
		sleBGPPeerControlDontCapNego OBJECT-TYPE
			SYNTAX INTEGER
				{
				disable(0),
				enable(1)
				}
			MAX-ACCESS read-write
			STATUS current
			DESCRIPTION
				"Description."
			::= { sleBGPPeerControl 12 }


		-- 1.3.6.1.4.1.6296.101.53.4.1.2.13
		sleBGPPeerControlWeight OBJECT-TYPE
			SYNTAX INTEGER (0..65535)
			MAX-ACCESS read-write
			STATUS current
			DESCRIPTION
				"Description."
			::= { sleBGPPeerControl 13 }


		-- 1.3.6.1.4.1.6296.101.53.4.1.2.14
		sleBGPPeerControlEnforcMultiHop OBJECT-TYPE
			SYNTAX INTEGER
				{
				disable(0),
				enable(1)
				}
			MAX-ACCESS read-write
			STATUS current
			DESCRIPTION
				"Description."
			::= { sleBGPPeerControl 14 }


		-- 1.3.6.1.4.1.6296.101.53.4.1.2.15
		sleBGPPeerControlPassive OBJECT-TYPE
			SYNTAX INTEGER
				{
				disable(0),
				enable(1)
				}
			MAX-ACCESS read-write
			STATUS current
			DESCRIPTION
				"Description."
			::= { sleBGPPeerControl 15 }


		-- 1.3.6.1.4.1.6296.101.53.4.1.2.16
		sleBGPPeerControlUpSourceName OBJECT-TYPE
			SYNTAX OCTET STRING
			MAX-ACCESS read-write
			STATUS current
			DESCRIPTION
				"Description."
			::= { sleBGPPeerControl 16 }


		-- 1.3.6.1.4.1.6296.101.53.4.1.2.17
		sleBGPPeerControlPort OBJECT-TYPE
			SYNTAX INTEGER (0..65535)
			MAX-ACCESS read-write
			STATUS current
			DESCRIPTION
				"Description."
			::= { sleBGPPeerControl 17 }


		-- 1.3.6.1.4.1.6296.101.53.4.1.2.18
		sleBGPPeerControlRetstartTime OBJECT-TYPE
			SYNTAX INTEGER (1..65535)
			MAX-ACCESS read-write
			STATUS current
			DESCRIPTION
				"Description."
			::= { sleBGPPeerControl 18 }


		-- 1.3.6.1.4.1.6296.101.53.4.1.2.19
		sleBGPPeerControlShutDown OBJECT-TYPE
			SYNTAX INTEGER
				{
				disable(0),
				enable(1)
				}
			MAX-ACCESS read-write
			STATUS current
			DESCRIPTION
				"Description."
			::= { sleBGPPeerControl 19 }


		-- 1.3.6.1.4.1.6296.101.53.4.1.2.20
		sleBGPPeerControlKeepInterval OBJECT-TYPE
			SYNTAX INTEGER (0..65535)
			MAX-ACCESS read-write
			STATUS current
			DESCRIPTION
				"Description."
			::= { sleBGPPeerControl 20 }


		-- 1.3.6.1.4.1.6296.101.53.4.1.2.21
		sleBGPPeerControlHoldInterval OBJECT-TYPE
			SYNTAX INTEGER (0..65535)
			MAX-ACCESS read-write
			STATUS current
			DESCRIPTION
				"Description."
			::= { sleBGPPeerControl 21 }


		-- 1.3.6.1.4.1.6296.101.53.4.1.2.22
		sleBGPPeerControlConnInterval OBJECT-TYPE
			SYNTAX INTEGER (0..65535)
			MAX-ACCESS read-write
			STATUS current
			DESCRIPTION
				"Description."
			::= { sleBGPPeerControl 22 }


		-- 1.3.6.1.4.1.6296.101.53.4.1.2.23
		sleBGPPeerControlOverCap OBJECT-TYPE
			SYNTAX INTEGER
				{
				disable(0),
				enable(1)
				}
			MAX-ACCESS read-write
			STATUS current
			DESCRIPTION
				"Description."
			::= { sleBGPPeerControl 23 }


		-- 1.3.6.1.4.1.6296.101.53.4.1.2.24
		sleBGPPeerControlStrictCapMatch OBJECT-TYPE
			SYNTAX INTEGER
				{
				disable(0),
				enable(1)
				}
			MAX-ACCESS read-write
			STATUS current
			DESCRIPTION
				"Description."
			::= { sleBGPPeerControl 24 }


		-- 1.3.6.1.4.1.6296.101.53.4.1.2.25
		sleBGPPeerControlIfname OBJECT-TYPE
			SYNTAX OCTET STRING (SIZE (0..80))
			MAX-ACCESS read-write
			STATUS current
			DESCRIPTION
				"Description."
			::= { sleBGPPeerControl 25 }


		-- 1.3.6.1.4.1.6296.101.53.4.1.2.26
		sleBGPPeerControlCapRouteRefresh OBJECT-TYPE
			SYNTAX INTEGER
				{
				disable(0),
				enable(1)
				}
			MAX-ACCESS read-write
			STATUS current
			DESCRIPTION
				"Description."
			::= { sleBGPPeerControl 26 }


		-- 1.3.6.1.4.1.6296.101.53.4.1.2.27
		sleBGPPeerControlCapDynamic OBJECT-TYPE
			SYNTAX INTEGER
				{
				disable(0),
				enable(1)
				}
			MAX-ACCESS read-write
			STATUS current
			DESCRIPTION
				"Description."
			::= { sleBGPPeerControl 27 }


		-- 1.3.6.1.4.1.6296.101.53.4.1.2.28
		sleBGPPeerControlEBGPMulthopCount OBJECT-TYPE
			SYNTAX INTEGER (0..255)
			MAX-ACCESS read-write
			STATUS current
			DESCRIPTION
				"Description."
			::= { sleBGPPeerControl 28 }


		-- 1.3.6.1.4.1.6296.101.53.4.1.2.29
		sleBGPPeerControlPassword OBJECT-TYPE
			SYNTAX OCTET STRING (SIZE (0..80))
			MAX-ACCESS read-write
			STATUS current
			DESCRIPTION
				"Description."
			::= { sleBGPPeerControl 29 }


		-- 1.3.6.1.4.1.6296.101.53.4.1.3
		sleBGPPeerNotification OBJECT IDENTIFIER ::= { sleBGPPeer 3 }


		-- 1.3.6.1.4.1.6296.101.53.4.1.3.1
		sleBGPPeerCreated NOTIFICATION-TYPE
			OBJECTS { sleBGPPeerControlRequest, sleBGPPeerControlTimeStamp, sleBGPPeerControlReqResult, sleBGPPeerName, sleBGPPeerAsNum
				 }
			STATUS current
			DESCRIPTION
				"Description."
			::= { sleBGPPeerNotification 1 }


		-- 1.3.6.1.4.1.6296.101.53.4.1.3.2
		sleBGPPeerDeleted NOTIFICATION-TYPE
			OBJECTS { sleBGPPeerControlRequest, sleBGPPeerControlTimeStamp, sleBGPPeerControlReqResult, sleBGPPeerControlName }
			STATUS current
			DESCRIPTION
				"Description."
			::= { sleBGPPeerNotification 2 }


		-- 1.3.6.1.4.1.6296.101.53.4.1.3.3
		sleBGPPeerGroupNameCreated NOTIFICATION-TYPE
			OBJECTS { sleBGPPeerControlRequest, sleBGPPeerControlTimeStamp, sleBGPPeerControlReqResult, sleBGPPeerName, sleBGPPeerGroupName
				 }
			STATUS current
			DESCRIPTION
				"Description."
			::= { sleBGPPeerNotification 3 }


		-- 1.3.6.1.4.1.6296.101.53.4.1.3.4
		sleBGPPeerGroupNameDeleted NOTIFICATION-TYPE
			OBJECTS { sleBGPPeerControlRequest, sleBGPPeerControlTimeStamp, sleBGPPeerControlReqResult, sleBGPPeerControlName }
			STATUS current
			DESCRIPTION
				"Description."
			::= { sleBGPPeerNotification 4 }


		-- 1.3.6.1.4.1.6296.101.53.4.1.3.5
		sleBGPPeerAdvIntervalChanged NOTIFICATION-TYPE
			OBJECTS { sleBGPPeerControlRequest, sleBGPPeerControlTimeStamp, sleBGPPeerControlReqResult, sleBGPPeerName, sleBGPPeerAdvInterval
				 }
			STATUS current
			DESCRIPTION
				"Description."
			::= { sleBGPPeerNotification 5 }


		-- 1.3.6.1.4.1.6296.101.53.4.1.3.6
		sleBGPPeerAsOriIntervalChanged NOTIFICATION-TYPE
			OBJECTS { sleBGPPeerControlRequest, sleBGPPeerControlTimeStamp, sleBGPPeerControlReqResult, sleBGPPeerName, sleBGPPeerAsOriInterval
				 }
			STATUS current
			DESCRIPTION
				"Description."
			::= { sleBGPPeerNotification 6 }


		-- 1.3.6.1.4.1.6296.101.53.4.1.3.7
		sleBGPPeerDescCreated NOTIFICATION-TYPE
			OBJECTS { sleBGPPeerControlRequest, sleBGPPeerControlTimeStamp, sleBGPPeerControlReqResult, sleBGPPeerName, sleBGPPeerDesc
				 }
			STATUS current
			DESCRIPTION
				"Description."
			::= { sleBGPPeerNotification 7 }


		-- 1.3.6.1.4.1.6296.101.53.4.1.3.8
		sleBGPPeerDescDeleted NOTIFICATION-TYPE
			OBJECTS { sleBGPPeerControlRequest, sleBGPPeerControlTimeStamp, sleBGPPeerControlReqResult, sleBGPPeerControlName, sleBGPPeerControlDesc
				 }
			STATUS current
			DESCRIPTION
				"Description."
			::= { sleBGPPeerNotification 8 }


		-- 1.3.6.1.4.1.6296.101.53.4.1.3.9
		sleBGPPeerDontCapNegoChanged NOTIFICATION-TYPE
			OBJECTS { sleBGPPeerControlRequest, sleBGPPeerControlTimeStamp, sleBGPPeerControlReqResult, sleBGPPeerName, sleBGPPeerDontCapNego
				 }
			STATUS current
			DESCRIPTION
				"Description."
			::= { sleBGPPeerNotification 9 }


		-- 1.3.6.1.4.1.6296.101.53.4.1.3.10
		sleBGPPeerWeightChanged NOTIFICATION-TYPE
			OBJECTS { sleBGPPeerControlRequest, sleBGPPeerControlTimeStamp, sleBGPPeerControlReqResult, sleBGPPeerName, sleBGPPeerDontCapNego
				 }
			STATUS current
			DESCRIPTION
				"Description."
			::= { sleBGPPeerNotification 10 }


		-- 1.3.6.1.4.1.6296.101.53.4.1.3.11
		sleBGPPeerEnforcMultiHopChanged NOTIFICATION-TYPE
			OBJECTS { sleBGPPeerControlRequest, sleBGPPeerControlTimeStamp, sleBGPPeerControlReqResult, sleBGPPeerName, sleBGPPeerEnforcMultiHop
				 }
			STATUS current
			DESCRIPTION
				"Description."
			::= { sleBGPPeerNotification 11 }


		-- 1.3.6.1.4.1.6296.101.53.4.1.3.12
		sleBGPPeerPassiveChanged NOTIFICATION-TYPE
			OBJECTS { sleBGPPeerControlRequest, sleBGPPeerControlTimeStamp, sleBGPPeerControlReqResult, sleBGPPeerName, sleBGPPeerPassive
				 }
			STATUS current
			DESCRIPTION
				"Description."
			::= { sleBGPPeerNotification 12 }


		-- 1.3.6.1.4.1.6296.101.53.4.1.3.13
		sleBGPPeerUpSourceCreated NOTIFICATION-TYPE
			OBJECTS { sleBGPPeerControlRequest, sleBGPPeerControlTimeStamp, sleBGPPeerControlReqResult, sleBGPPeerName, sleBGPPeerUpSourceName
				 }
			STATUS current
			DESCRIPTION
				"Description."
			::= { sleBGPPeerNotification 13 }


		-- 1.3.6.1.4.1.6296.101.53.4.1.3.14
		sleBGPPeerUpSourceDeleted NOTIFICATION-TYPE
			OBJECTS { sleBGPPeerControlRequest, sleBGPPeerControlTimeStamp, sleBGPPeerControlReqResult, sleBGPPeerControlName }
			STATUS current
			DESCRIPTION
				"Description."
			::= { sleBGPPeerNotification 14 }


		-- 1.3.6.1.4.1.6296.101.53.4.1.3.15
		sleBGPPeerPortChanged NOTIFICATION-TYPE
			OBJECTS { sleBGPPeerControlRequest, sleBGPPeerControlTimeStamp, sleBGPPeerControlReqResult, sleBGPPeerName, sleBGPPeerPort
				 }
			STATUS current
			DESCRIPTION
				"Description."
			::= { sleBGPPeerNotification 15 }


		-- 1.3.6.1.4.1.6296.101.53.4.1.3.16
		sleBGPPeerRetstartTimeChanged NOTIFICATION-TYPE
			OBJECTS { sleBGPPeerControlRequest, sleBGPPeerControlTimeStamp, sleBGPPeerControlReqResult, sleBGPPeerName, sleBGPPeerRetstartTime
				 }
			STATUS current
			DESCRIPTION
				"Description."
			::= { sleBGPPeerNotification 16 }


		-- 1.3.6.1.4.1.6296.101.53.4.1.3.17
		sleBGPPeerShutDownChanged NOTIFICATION-TYPE
			OBJECTS { sleBGPPeerControlRequest, sleBGPPeerControlTimeStamp, sleBGPPeerControlReqResult, sleBGPPeerName, sleBGPPeerShutDown
				 }
			STATUS current
			DESCRIPTION
				"Description."
			::= { sleBGPPeerNotification 17 }


		-- 1.3.6.1.4.1.6296.101.53.4.1.3.18
		sleBGPPeerTimersProfileChanged NOTIFICATION-TYPE
			OBJECTS { sleBGPPeerControlRequest, sleBGPPeerControlTimeStamp, sleBGPPeerControlReqResult, sleBGPPeerName, sleBGPPeerKeepInterval,
				sleBGPPeerHoldInterval }
			STATUS current
			DESCRIPTION
				"Description."
			::= { sleBGPPeerNotification 18 }


		-- 1.3.6.1.4.1.6296.101.53.4.1.3.19
		sleBGPPeerConnIntervalChanged NOTIFICATION-TYPE
			OBJECTS { sleBGPPeerControlRequest, sleBGPPeerControlTimeStamp, sleBGPPeerControlReqResult, sleBGPPeerName, sleBGPPeerConnInterval
				 }
			STATUS current
			DESCRIPTION
				"Description."
			::= { sleBGPPeerNotification 19 }


		-- 1.3.6.1.4.1.6296.101.53.4.1.3.20
		sleBGPPeerOverCapChanged NOTIFICATION-TYPE
			OBJECTS { sleBGPPeerControlRequest, sleBGPPeerControlTimeStamp, sleBGPPeerControlReqResult, sleBGPPeerName, sleBGPPeerOverCap
				 }
			STATUS current
			DESCRIPTION
				"Description."
			::= { sleBGPPeerNotification 20 }


		-- 1.3.6.1.4.1.6296.101.53.4.1.3.21
		sleBGPPeerStrictCapMatchChanged NOTIFICATION-TYPE
			OBJECTS { sleBGPPeerControlRequest, sleBGPPeerControlTimeStamp, sleBGPPeerControlReqResult, sleBGPPeerName, sleBGPPeerStrictCapMatch
				 }
			STATUS current
			DESCRIPTION
				"Description."
			::= { sleBGPPeerNotification 21 }


		-- 1.3.6.1.4.1.6296.101.53.4.1.3.22
		sleBGPPeerIfnameCreated NOTIFICATION-TYPE
			OBJECTS { sleBGPPeerControlRequest, sleBGPPeerControlTimeStamp, sleBGPPeerControlReqResult, sleBGPPeerName, sleBGPPeerIfname
				 }
			STATUS current
			DESCRIPTION
				"Description."
			::= { sleBGPPeerNotification 22 }


		-- 1.3.6.1.4.1.6296.101.53.4.1.3.23
		sleBGPPeerIfnameDeleted NOTIFICATION-TYPE
			OBJECTS { sleBGPPeerControlRequest, sleBGPPeerControlTimeStamp, sleBGPPeerControlReqResult, sleBGPPeerControlName }
			STATUS current
			DESCRIPTION
				"Description."
			::= { sleBGPPeerNotification 23 }


		-- 1.3.6.1.4.1.6296.101.53.4.1.3.24
		sleBGPPeerCapRouteRefreshChanged NOTIFICATION-TYPE
			OBJECTS { sleBGPPeerControlRequest, sleBGPPeerControlTimeStamp, sleBGPPeerControlReqResult, sleBGPPeerName, sleBGPPeerCapRouteRefresh
				 }
			STATUS current
			DESCRIPTION
				"Description."
			::= { sleBGPPeerNotification 24 }


		-- 1.3.6.1.4.1.6296.101.53.4.1.3.25
		sleBGPPeerCapDynamicChanged NOTIFICATION-TYPE
			OBJECTS { sleBGPPeerControlRequest, sleBGPPeerControlTimeStamp, sleBGPPeerControlReqResult, sleBGPPeerName, sleBGPPeerCapDynamic
				 }
			STATUS current
			DESCRIPTION
				"Description."
			::= { sleBGPPeerNotification 25 }


		-- 1.3.6.1.4.1.6296.101.53.4.1.3.26
		sleBGPPeerEBGPMultihopCountChanged NOTIFICATION-TYPE
			OBJECTS { sleBGPPeerControlRequest, sleBGPPeerControlTimeStamp, sleBGPPeerControlReqResult, sleBGPPeerName, sleBGPPeerEBGPMulthopCount
				 }
			STATUS current
			DESCRIPTION
				"Description."
			::= { sleBGPPeerNotification 26 }


		-- 1.3.6.1.4.1.6296.101.53.4.1.3.27
		sleBGPPeerPasswordCreated NOTIFICATION-TYPE
			OBJECTS { sleBGPPeerControlRequest, sleBGPPeerControlTimeStamp, sleBGPPeerControlReqResult, sleBGPPeerName, sleBGPPeerPassword
				 }
			STATUS current
			DESCRIPTION
				"Description."
			::= { sleBGPPeerNotification 27 }


		-- 1.3.6.1.4.1.6296.101.53.4.1.3.28
		sleBGPPeerPasswordDeleted NOTIFICATION-TYPE
			OBJECTS { sleBGPPeerControlRequest, sleBGPPeerControlTimeStamp, sleBGPPeerControlReqResult, sleBGPPeerControlName }
			STATUS current
			DESCRIPTION
				"Description."
			::= { sleBGPPeerNotification 28 }


		-- 1.3.6.1.4.1.6296.101.53.4.2
		sleBGPPeerGroup OBJECT IDENTIFIER ::= { sleBGPPeerInfo 2 }


		-- 1.3.6.1.4.1.6296.101.53.4.2.1
		sleBGPPeerGroupTable OBJECT-TYPE
			SYNTAX SEQUENCE OF SleBGPPeerGroupEntry
			MAX-ACCESS not-accessible
			STATUS current
			DESCRIPTION
				"Description."
			::= { sleBGPPeerGroup 1 }


		-- 1.3.6.1.4.1.6296.101.53.4.2.1.1
		sleBGPPeerGroupEntry OBJECT-TYPE
			SYNTAX SleBGPPeerGroupEntry
			MAX-ACCESS not-accessible
			STATUS current
			DESCRIPTION
				"Description."
			INDEX { sleBGPPeerGroupStr }
			::= { sleBGPPeerGroupTable 1 }


		SleBGPPeerGroupEntry ::=
			SEQUENCE {
				sleBGPPeerGroupStr
					OCTET STRING,
				sleBGPPeerGroupAsNum
					Gauge32,
				sleBGPPeerGroupAdvInterval
					INTEGER,
				sleBGPPeerGroupAsOriInterval
					INTEGER,
				sleBGPPeerGroupDesc
					OCTET STRING,
				sleBGPPeerGroupDontCapNego
					INTEGER,
				sleBGPPeerGroupWeight
					INTEGER,
				sleBGPPeerGroupEnforcMultiHop
					INTEGER,
				sleBGPPeerGroupPassive
					INTEGER,
				sleBGPPeerGroupUpSourceName
					OCTET STRING,
				sleBGPPeerGroupPort
					INTEGER,
				sleBGPPeerGroupRetstartTime
					INTEGER,
				sleBGPPeerGroupShutDown
					INTEGER,
				sleBGPPeerGroupKeepInterval
					INTEGER,
				sleBGPPeerGroupHoldInterval
					INTEGER,
				sleBGPPeerGroupConnInterval
					INTEGER,
				sleBGPPeerGroupOverCap
					INTEGER,
				sleBGPPeerGroupStrictCapMatch
					INTEGER,
				sleBGPPeerGroupCapRouteRefresh
					INTEGER,
				sleBGPPeerGroupCapDynamic
					INTEGER,
				sleBGPPeerGroupEBGPMulthopCount
					INTEGER,
				sleBGPPeerGroupPassword
					OCTET STRING
			 }

		-- 1.3.6.1.4.1.6296.101.53.4.2.1.1.1
		sleBGPPeerGroupStr OBJECT-TYPE
			SYNTAX OCTET STRING (SIZE (0..512))
			MAX-ACCESS read-only
			STATUS current
			DESCRIPTION
				"Description."
			::= { sleBGPPeerGroupEntry 1 }


		-- 1.3.6.1.4.1.6296.101.53.4.2.1.1.2
		sleBGPPeerGroupAsNum OBJECT-TYPE
			SYNTAX Gauge32 (1..4294967295)
			MAX-ACCESS read-only
			STATUS current
			DESCRIPTION
				"Description."
			::= { sleBGPPeerGroupEntry 2 }


		-- 1.3.6.1.4.1.6296.101.53.4.2.1.1.3
		sleBGPPeerGroupAdvInterval OBJECT-TYPE
			SYNTAX INTEGER (0..600)
			MAX-ACCESS read-only
			STATUS current
			DESCRIPTION
				"Description."
			::= { sleBGPPeerGroupEntry 3 }


		-- 1.3.6.1.4.1.6296.101.53.4.2.1.1.4
		sleBGPPeerGroupAsOriInterval OBJECT-TYPE
			SYNTAX INTEGER (0..600)
			MAX-ACCESS read-only
			STATUS current
			DESCRIPTION
				"Description."
			::= { sleBGPPeerGroupEntry 4 }


		-- 1.3.6.1.4.1.6296.101.53.4.2.1.1.5
		sleBGPPeerGroupDesc OBJECT-TYPE
			SYNTAX OCTET STRING (SIZE (0..80))
			MAX-ACCESS read-only
			STATUS current
			DESCRIPTION
				"Description."
			::= { sleBGPPeerGroupEntry 5 }


		-- 1.3.6.1.4.1.6296.101.53.4.2.1.1.6
		sleBGPPeerGroupDontCapNego OBJECT-TYPE
			SYNTAX INTEGER
				{
				disable(0),
				enable(1)
				}
			MAX-ACCESS read-only
			STATUS current
			DESCRIPTION
				"Description."
			::= { sleBGPPeerGroupEntry 6 }


		-- 1.3.6.1.4.1.6296.101.53.4.2.1.1.7
		sleBGPPeerGroupWeight OBJECT-TYPE
			SYNTAX INTEGER (0..65535)
			MAX-ACCESS read-only
			STATUS current
			DESCRIPTION
				"Description."
			::= { sleBGPPeerGroupEntry 7 }


		-- 1.3.6.1.4.1.6296.101.53.4.2.1.1.8
		sleBGPPeerGroupEnforcMultiHop OBJECT-TYPE
			SYNTAX INTEGER
				{
				disable(0),
				enable(1)
				}
			MAX-ACCESS read-only
			STATUS current
			DESCRIPTION
				"Description."
			::= { sleBGPPeerGroupEntry 8 }


		-- 1.3.6.1.4.1.6296.101.53.4.2.1.1.9
		sleBGPPeerGroupPassive OBJECT-TYPE
			SYNTAX INTEGER
				{
				disable(0),
				enable(1)
				}
			MAX-ACCESS read-only
			STATUS current
			DESCRIPTION
				"Description."
			::= { sleBGPPeerGroupEntry 9 }


		-- 1.3.6.1.4.1.6296.101.53.4.2.1.1.10
		sleBGPPeerGroupUpSourceName OBJECT-TYPE
			SYNTAX OCTET STRING
			MAX-ACCESS read-only
			STATUS current
			DESCRIPTION
				"Description."
			::= { sleBGPPeerGroupEntry 10 }


		-- 1.3.6.1.4.1.6296.101.53.4.2.1.1.11
		sleBGPPeerGroupPort OBJECT-TYPE
			SYNTAX INTEGER (0..65535)
			MAX-ACCESS read-only
			STATUS current
			DESCRIPTION
				"Description."
			::= { sleBGPPeerGroupEntry 11 }


		-- 1.3.6.1.4.1.6296.101.53.4.2.1.1.12
		sleBGPPeerGroupRetstartTime OBJECT-TYPE
			SYNTAX INTEGER (1..65535)
			MAX-ACCESS read-only
			STATUS current
			DESCRIPTION
				"Description."
			::= { sleBGPPeerGroupEntry 12 }


		-- 1.3.6.1.4.1.6296.101.53.4.2.1.1.13
		sleBGPPeerGroupShutDown OBJECT-TYPE
			SYNTAX INTEGER
				{
				disable(0),
				enable(1)
				}
			MAX-ACCESS read-only
			STATUS current
			DESCRIPTION
				"Description."
			::= { sleBGPPeerGroupEntry 13 }


		-- 1.3.6.1.4.1.6296.101.53.4.2.1.1.14
		sleBGPPeerGroupKeepInterval OBJECT-TYPE
			SYNTAX INTEGER (0..65535)
			MAX-ACCESS read-only
			STATUS current
			DESCRIPTION
				"Description."
			::= { sleBGPPeerGroupEntry 14 }


		-- 1.3.6.1.4.1.6296.101.53.4.2.1.1.15
		sleBGPPeerGroupHoldInterval OBJECT-TYPE
			SYNTAX INTEGER (0..65535)
			MAX-ACCESS read-only
			STATUS current
			DESCRIPTION
				"Description."
			::= { sleBGPPeerGroupEntry 15 }


		-- 1.3.6.1.4.1.6296.101.53.4.2.1.1.16
		sleBGPPeerGroupConnInterval OBJECT-TYPE
			SYNTAX INTEGER (0..65535)
			MAX-ACCESS read-only
			STATUS current
			DESCRIPTION
				"Description."
			::= { sleBGPPeerGroupEntry 16 }


		-- 1.3.6.1.4.1.6296.101.53.4.2.1.1.17
		sleBGPPeerGroupOverCap OBJECT-TYPE
			SYNTAX INTEGER
				{
				disable(0),
				enable(1)
				}
			MAX-ACCESS read-only
			STATUS current
			DESCRIPTION
				"Description."
			::= { sleBGPPeerGroupEntry 17 }


		-- 1.3.6.1.4.1.6296.101.53.4.2.1.1.18
		sleBGPPeerGroupStrictCapMatch OBJECT-TYPE
			SYNTAX INTEGER
				{
				disable(0),
				enable(1)
				}
			MAX-ACCESS read-only
			STATUS current
			DESCRIPTION
				"Description."
			::= { sleBGPPeerGroupEntry 18 }


		-- 1.3.6.1.4.1.6296.101.53.4.2.1.1.19
		sleBGPPeerGroupCapRouteRefresh OBJECT-TYPE
			SYNTAX INTEGER
				{
				disable(0),
				enable(1)
				}
			MAX-ACCESS read-only
			STATUS current
			DESCRIPTION
				"Description."
			::= { sleBGPPeerGroupEntry 19 }


		-- 1.3.6.1.4.1.6296.101.53.4.2.1.1.20
		sleBGPPeerGroupCapDynamic OBJECT-TYPE
			SYNTAX INTEGER
				{
				disable(0),
				enable(1)
				}
			MAX-ACCESS read-only
			STATUS current
			DESCRIPTION
				"Description."
			::= { sleBGPPeerGroupEntry 20 }


		-- 1.3.6.1.4.1.6296.101.53.4.2.1.1.21
		sleBGPPeerGroupEBGPMulthopCount OBJECT-TYPE
			SYNTAX INTEGER (0..255)
			MAX-ACCESS read-only
			STATUS current
			DESCRIPTION
				"Description."
			::= { sleBGPPeerGroupEntry 21 }


		-- 1.3.6.1.4.1.6296.101.53.4.2.1.1.22
		sleBGPPeerGroupPassword OBJECT-TYPE
			SYNTAX OCTET STRING (SIZE (0..512))
			MAX-ACCESS read-only
			STATUS current
			DESCRIPTION
				"Description."
			::= { sleBGPPeerGroupEntry 22 }


		-- 1.3.6.1.4.1.6296.101.53.4.2.2
		sleBGPPeerGroupControl OBJECT IDENTIFIER ::= { sleBGPPeerGroup 2 }


		-- 1.3.6.1.4.1.6296.101.53.4.2.2.1
		sleBGPPeerGroupControlRequest OBJECT-TYPE
			SYNTAX INTEGER
				{
				createBGPPeerGroup(1),
				deleteBGPPeerGroup(2),
				setBGPPeerGroupRemoteAs(3),
				setBGPPeerGroupAdvInterval(4),
				setBGPPeerGroupAsOriInterval(5),
				createBGPPeerGroupDescription(6),
				deleteBGPPeerGroupDescription(7),
				setBGPPeerGroupDontCapNego(8),
				setBGPPeerGroupWeight(9),
				setBGPPeerGroupEnforceMultihop(10),
				setBGPPeerGroupPassive(11),
				createBGPPeerGroupUpSourceName(12),
				deleteBGPPeerGroupUpSourceName(13),
				setBGPPeerGroupPort(14),
				setBGPPeerGroupRestartTime(15),
				setBGPPeerGroupShutDown(16),
				setBGPPeerGroupTimersProfile(17),
				setBGPPeerGroupConnInterval(18),
				setBGPPeerGroupOverCap(19),
				setBGPPeerGroupStrictCapMatch(20),
				setBGPPeerGroupCapRouteRefresh(21),
				setBGPPeerGroupCapDynamic(22),
				setBGPPeerGroupEBGPMulthopCount(23),
				createBGPPeerGroupPassword(24),
				deleteBGPPeerGroupPassword(25)
				}
			MAX-ACCESS read-write
			STATUS current
			DESCRIPTION
				"Description."
			::= { sleBGPPeerGroupControl 1 }


		-- 1.3.6.1.4.1.6296.101.53.4.2.2.2
		sleBGPPeerGroupControlStatus OBJECT-TYPE
			SYNTAX SleControlStatusType
			MAX-ACCESS read-only
			STATUS current
			DESCRIPTION
				"Description."
			::= { sleBGPPeerGroupControl 2 }


		-- 1.3.6.1.4.1.6296.101.53.4.2.2.3
		sleBGPPeerGroupControlTimer OBJECT-TYPE
			SYNTAX Gauge32
			MAX-ACCESS read-write
			STATUS current
			DESCRIPTION
				"Description."
			::= { sleBGPPeerGroupControl 3 }


		-- 1.3.6.1.4.1.6296.101.53.4.2.2.4
		sleBGPPeerGroupControlTimeStamp OBJECT-TYPE
			SYNTAX TimeTicks
			MAX-ACCESS read-only
			STATUS current
			DESCRIPTION
				"Description."
			::= { sleBGPPeerGroupControl 4 }


		-- 1.3.6.1.4.1.6296.101.53.4.2.2.5
		sleBGPPeerGroupControlReqResult OBJECT-TYPE
			SYNTAX SleControlRequestResultType
			MAX-ACCESS read-only
			STATUS current
			DESCRIPTION
				"Description."
			::= { sleBGPPeerGroupControl 5 }


		-- 1.3.6.1.4.1.6296.101.53.4.2.2.6
		sleBGPPeerGroupControlStr OBJECT-TYPE
			SYNTAX OCTET STRING (SIZE (0..512))
			MAX-ACCESS read-write
			STATUS current
			DESCRIPTION
				"Description."
			::= { sleBGPPeerGroupControl 6 }


		-- 1.3.6.1.4.1.6296.101.53.4.2.2.7
		sleBGPPeerGroupControlAsNum OBJECT-TYPE
			SYNTAX Gauge32 (1..4294967295)
			MAX-ACCESS read-write
			STATUS current
			DESCRIPTION
				"Description."
			::= { sleBGPPeerGroupControl 7 }


		-- 1.3.6.1.4.1.6296.101.53.4.2.2.8
		sleBGPPeerGroupControlAdvInterval OBJECT-TYPE
			SYNTAX INTEGER (0..600)
			MAX-ACCESS read-write
			STATUS current
			DESCRIPTION
				"Description."
			::= { sleBGPPeerGroupControl 8 }


		-- 1.3.6.1.4.1.6296.101.53.4.2.2.9
		sleBGPPeerGroupControlAsOriInterval OBJECT-TYPE
			SYNTAX INTEGER (0..600)
			MAX-ACCESS read-write
			STATUS current
			DESCRIPTION
				"Description."
			::= { sleBGPPeerGroupControl 9 }


		-- 1.3.6.1.4.1.6296.101.53.4.2.2.10
		sleBGPPeerGroupControlDesc OBJECT-TYPE
			SYNTAX OCTET STRING (SIZE (0..80))
			MAX-ACCESS read-write
			STATUS current
			DESCRIPTION
				"Description."
			::= { sleBGPPeerGroupControl 10 }


		-- 1.3.6.1.4.1.6296.101.53.4.2.2.11
		sleBGPPeerGroupControlDontCapNego OBJECT-TYPE
			SYNTAX INTEGER
				{
				disable(0),
				enable(1)
				}
			MAX-ACCESS read-write
			STATUS current
			DESCRIPTION
				"Description."
			::= { sleBGPPeerGroupControl 11 }


		-- 1.3.6.1.4.1.6296.101.53.4.2.2.12
		sleBGPPeerGroupControlWeight OBJECT-TYPE
			SYNTAX INTEGER (0..65535)
			MAX-ACCESS read-write
			STATUS current
			DESCRIPTION
				"Description."
			::= { sleBGPPeerGroupControl 12 }


		-- 1.3.6.1.4.1.6296.101.53.4.2.2.13
		sleBGPPeerGroupControlEnforcMultiHop OBJECT-TYPE
			SYNTAX INTEGER
				{
				disable(0),
				enable(1)
				}
			MAX-ACCESS read-write
			STATUS current
			DESCRIPTION
				"Description."
			::= { sleBGPPeerGroupControl 13 }


		-- 1.3.6.1.4.1.6296.101.53.4.2.2.14
		sleBGPPeerGroupControlPassive OBJECT-TYPE
			SYNTAX INTEGER
				{
				disable(0),
				enable(1)
				}
			MAX-ACCESS read-write
			STATUS current
			DESCRIPTION
				"Description."
			::= { sleBGPPeerGroupControl 14 }


		-- 1.3.6.1.4.1.6296.101.53.4.2.2.15
		sleBGPPeerGroupControlUpSourceName OBJECT-TYPE
			SYNTAX OCTET STRING
			MAX-ACCESS read-write
			STATUS current
			DESCRIPTION
				"Description."
			::= { sleBGPPeerGroupControl 15 }


		-- 1.3.6.1.4.1.6296.101.53.4.2.2.16
		sleBGPPeerGroupControlPort OBJECT-TYPE
			SYNTAX INTEGER (0..65535)
			MAX-ACCESS read-write
			STATUS current
			DESCRIPTION
				"Description."
			::= { sleBGPPeerGroupControl 16 }


		-- 1.3.6.1.4.1.6296.101.53.4.2.2.17
		sleBGPPeerGroupControlRetstartTime OBJECT-TYPE
			SYNTAX INTEGER (1..65535)
			MAX-ACCESS read-write
			STATUS current
			DESCRIPTION
				"Description."
			::= { sleBGPPeerGroupControl 17 }


		-- 1.3.6.1.4.1.6296.101.53.4.2.2.18
		sleBGPPeerGroupControlShutDown OBJECT-TYPE
			SYNTAX INTEGER
				{
				disable(0),
				enable(1)
				}
			MAX-ACCESS read-write
			STATUS current
			DESCRIPTION
				"Description."
			::= { sleBGPPeerGroupControl 18 }


		-- 1.3.6.1.4.1.6296.101.53.4.2.2.19
		sleBGPPeerGroupControlKeepInterval OBJECT-TYPE
			SYNTAX INTEGER (0..65535)
			MAX-ACCESS read-write
			STATUS current
			DESCRIPTION
				"Description."
			::= { sleBGPPeerGroupControl 19 }


		-- 1.3.6.1.4.1.6296.101.53.4.2.2.20
		sleBGPPeerGroupControlHoldInterval OBJECT-TYPE
			SYNTAX INTEGER (0..65535)
			MAX-ACCESS read-write
			STATUS current
			DESCRIPTION
				"Description."
			::= { sleBGPPeerGroupControl 20 }


		-- 1.3.6.1.4.1.6296.101.53.4.2.2.21
		sleBGPPeerGroupControlConnInterval OBJECT-TYPE
			SYNTAX INTEGER (0..65535)
			MAX-ACCESS read-write
			STATUS current
			DESCRIPTION
				"Description."
			::= { sleBGPPeerGroupControl 21 }


		-- 1.3.6.1.4.1.6296.101.53.4.2.2.22
		sleBGPPeerGroupControlOverCap OBJECT-TYPE
			SYNTAX INTEGER
				{
				disable(0),
				enable(1)
				}
			MAX-ACCESS read-write
			STATUS current
			DESCRIPTION
				"Description."
			::= { sleBGPPeerGroupControl 22 }


		-- 1.3.6.1.4.1.6296.101.53.4.2.2.23
		sleBGPPeerGroupControlStrictCapMatch OBJECT-TYPE
			SYNTAX INTEGER
				{
				disable(0),
				enable(1)
				}
			MAX-ACCESS read-write
			STATUS current
			DESCRIPTION
				"Description."
			::= { sleBGPPeerGroupControl 23 }


		-- 1.3.6.1.4.1.6296.101.53.4.2.2.24
		sleBGPPeerGroupControlCapRouteRefresh OBJECT-TYPE
			SYNTAX INTEGER
				{
				disable(0),
				enable(1)
				}
			MAX-ACCESS read-write
			STATUS current
			DESCRIPTION
				"Description."
			::= { sleBGPPeerGroupControl 24 }


		-- 1.3.6.1.4.1.6296.101.53.4.2.2.25
		sleBGPPeerGroupControlCapDynamic OBJECT-TYPE
			SYNTAX INTEGER
				{
				disable(0),
				enable(1)
				}
			MAX-ACCESS read-write
			STATUS current
			DESCRIPTION
				"Description."
			::= { sleBGPPeerGroupControl 25 }


		-- 1.3.6.1.4.1.6296.101.53.4.2.2.26
		sleBGPPeerGroupControlEBGPMulthopCount OBJECT-TYPE
			SYNTAX INTEGER (0..255)
			MAX-ACCESS read-write
			STATUS current
			DESCRIPTION
				"Description."
			::= { sleBGPPeerGroupControl 26 }


		-- 1.3.6.1.4.1.6296.101.53.4.2.2.27
		sleBGPPeerGroupControlPassword OBJECT-TYPE
			SYNTAX OCTET STRING (SIZE (0..80))
			MAX-ACCESS read-write
			STATUS current
			DESCRIPTION
				"Description."
			::= { sleBGPPeerGroupControl 27 }


		-- 1.3.6.1.4.1.6296.101.53.4.2.3
		sleBGPPeerGroupNotification OBJECT IDENTIFIER ::= { sleBGPPeerGroup 3 }


		-- 1.3.6.1.4.1.6296.101.53.4.2.3.1
		sleBGPPeerGroupCreated NOTIFICATION-TYPE
			OBJECTS { sleBGPPeerGroupControlRequest, sleBGPPeerGroupControlTimeStamp, sleBGPPeerGroupControlReqResult, sleBGPPeerGroupStr }
			STATUS current
			DESCRIPTION
				"Description."
			::= { sleBGPPeerGroupNotification 1 }


		-- 1.3.6.1.4.1.6296.101.53.4.2.3.2
		sleBGPPeerGroupDeleted NOTIFICATION-TYPE
			OBJECTS { sleBGPPeerGroupControlRequest, sleBGPPeerGroupControlTimeStamp, sleBGPPeerGroupControlReqResult, sleBGPPeerGroupControlStr }
			STATUS current
			DESCRIPTION
				"Description."
			::= { sleBGPPeerGroupNotification 2 }


		-- 1.3.6.1.4.1.6296.101.53.4.2.3.3
		sleBGPPeerGroupRemoteAsChanged NOTIFICATION-TYPE
			OBJECTS { sleBGPPeerGroupControlRequest, sleBGPPeerGroupControlTimeStamp, sleBGPPeerGroupControlReqResult, sleBGPPeerGroupStr, sleBGPPeerGroupAsNum
				 }
			STATUS current
			DESCRIPTION
				"Description."
			::= { sleBGPPeerGroupNotification 3 }


		-- 1.3.6.1.4.1.6296.101.53.4.2.3.4
		sleBGPPeerGroupAdvIntervalChanged NOTIFICATION-TYPE
			OBJECTS { sleBGPPeerGroupControlRequest, sleBGPPeerGroupControlTimeStamp, sleBGPPeerGroupControlReqResult, sleBGPPeerGroupStr, sleBGPPeerGroupAdvInterval
				 }
			STATUS current
			DESCRIPTION
				"Description."
			::= { sleBGPPeerGroupNotification 4 }


		-- 1.3.6.1.4.1.6296.101.53.4.2.3.5
		sleBGPPeerGroupAsOriIntervalChanged NOTIFICATION-TYPE
			OBJECTS { sleBGPPeerGroupControlRequest, sleBGPPeerGroupControlTimeStamp, sleBGPPeerGroupControlReqResult, sleBGPPeerGroupStr, sleBGPPeerGroupAsOriInterval
				 }
			STATUS current
			DESCRIPTION
				"Description."
			::= { sleBGPPeerGroupNotification 5 }


		-- 1.3.6.1.4.1.6296.101.53.4.2.3.6
		sleBGPPeerGroupDescCreated NOTIFICATION-TYPE
			OBJECTS { sleBGPPeerGroupControlRequest, sleBGPPeerGroupControlTimeStamp, sleBGPPeerGroupControlReqResult, sleBGPPeerGroupStr, sleBGPPeerGroupDesc
				 }
			STATUS current
			DESCRIPTION
				"Description."
			::= { sleBGPPeerGroupNotification 6 }


		-- 1.3.6.1.4.1.6296.101.53.4.2.3.7
		sleBGPPeerGroupDescDeleted NOTIFICATION-TYPE
			OBJECTS { sleBGPPeerGroupControlRequest, sleBGPPeerGroupControlTimeStamp, sleBGPPeerGroupControlReqResult, sleBGPPeerGroupControlStr, sleBGPPeerGroupControlDesc
				 }
			STATUS current
			DESCRIPTION
				"Description."
			::= { sleBGPPeerGroupNotification 7 }


		-- 1.3.6.1.4.1.6296.101.53.4.2.3.8
		sleBGPPeerGroupDontCapNegoChanged NOTIFICATION-TYPE
			OBJECTS { sleBGPPeerGroupControlRequest, sleBGPPeerGroupControlTimeStamp, sleBGPPeerGroupControlReqResult, sleBGPPeerGroupStr, sleBGPPeerGroupDontCapNego
				 }
			STATUS current
			DESCRIPTION
				"Description."
			::= { sleBGPPeerGroupNotification 8 }


		-- 1.3.6.1.4.1.6296.101.53.4.2.3.9
		sleBGPPeerGroupWeightChanged NOTIFICATION-TYPE
			OBJECTS { sleBGPPeerGroupControlRequest, sleBGPPeerGroupControlTimeStamp, sleBGPPeerGroupControlReqResult, sleBGPPeerGroupStr, sleBGPPeerWeight
				 }
			STATUS current
			DESCRIPTION
				"Description."
			::= { sleBGPPeerGroupNotification 9 }


		-- 1.3.6.1.4.1.6296.101.53.4.2.3.10
		sleBGPPeerGroupPassiveChanged NOTIFICATION-TYPE
			OBJECTS { sleBGPPeerGroupControlRequest, sleBGPPeerGroupControlTimeStamp, sleBGPPeerGroupControlReqResult, sleBGPPeerGroupStr, sleBGPPeerGroupPassive
				 }
			STATUS current
			DESCRIPTION
				"Description."
			::= { sleBGPPeerGroupNotification 10 }


		-- 1.3.6.1.4.1.6296.101.53.4.2.3.11
		sleBGPPeerGroupUpSourceCreated NOTIFICATION-TYPE
			OBJECTS { sleBGPPeerGroupControlRequest, sleBGPPeerGroupControlTimeStamp, sleBGPPeerGroupControlReqResult, sleBGPPeerGroupStr, sleBGPPeerGroupUpSourceName
				 }
			STATUS current
			DESCRIPTION
				"Description."
			::= { sleBGPPeerGroupNotification 11 }


		-- 1.3.6.1.4.1.6296.101.53.4.2.3.12
		sleBGPPeerGroupUpSourceDeleted NOTIFICATION-TYPE
			OBJECTS { sleBGPPeerGroupControlRequest, sleBGPPeerGroupControlTimeStamp, sleBGPPeerGroupControlReqResult, sleBGPPeerGroupControlStr, sleBGPPeerGroupControlUpSourceName
				 }
			STATUS current
			DESCRIPTION
				"Description."
			::= { sleBGPPeerGroupNotification 12 }


		-- 1.3.6.1.4.1.6296.101.53.4.2.3.13
		sleBGPPeerGroupPortChanged NOTIFICATION-TYPE
			OBJECTS { sleBGPPeerGroupControlRequest, sleBGPPeerGroupControlTimeStamp, sleBGPPeerGroupControlReqResult, sleBGPPeerGroupStr, sleBGPPeerGroupPort
				 }
			STATUS current
			DESCRIPTION
				"Description."
			::= { sleBGPPeerGroupNotification 13 }


		-- 1.3.6.1.4.1.6296.101.53.4.2.3.14
		sleBGPPeerGroupRetstartTimeChanged NOTIFICATION-TYPE
			OBJECTS { sleBGPPeerGroupControlRequest, sleBGPPeerGroupControlTimeStamp, sleBGPPeerGroupControlReqResult, sleBGPPeerGroupStr, sleBGPPeerGroupRetstartTime
				 }
			STATUS current
			DESCRIPTION
				"Description."
			::= { sleBGPPeerGroupNotification 14 }


		-- 1.3.6.1.4.1.6296.101.53.4.2.3.15
		sleBGPPeerGroupShutDownChanged NOTIFICATION-TYPE
			OBJECTS { sleBGPPeerGroupControlRequest, sleBGPPeerGroupControlTimeStamp, sleBGPPeerGroupControlReqResult, sleBGPPeerGroupStr, sleBGPPeerShutDown
				 }
			STATUS current
			DESCRIPTION
				"Description."
			::= { sleBGPPeerGroupNotification 15 }


		-- 1.3.6.1.4.1.6296.101.53.4.2.3.16
		sleBGPPeerGroupTimersProfileChanged NOTIFICATION-TYPE
			OBJECTS { sleBGPPeerGroupControlRequest, sleBGPPeerGroupControlTimeStamp, sleBGPPeerGroupControlReqResult, sleBGPPeerGroupStr, sleBGPPeerGroupKeepInterval,
				sleBGPPeerGroupHoldInterval }
			STATUS current
			DESCRIPTION
				"Description."
			::= { sleBGPPeerGroupNotification 16 }


		-- 1.3.6.1.4.1.6296.101.53.4.2.3.17
		sleBGPPeerGroupConnIntervalChanged NOTIFICATION-TYPE
			OBJECTS { sleBGPPeerGroupControlRequest, sleBGPPeerGroupControlTimeStamp, sleBGPPeerGroupControlReqResult, sleBGPPeerGroupStr, sleBGPPeerGroupConnInterval
				 }
			STATUS current
			DESCRIPTION
				"Description."
			::= { sleBGPPeerGroupNotification 17 }


		-- 1.3.6.1.4.1.6296.101.53.4.2.3.18
		sleBGPPeerGroupOverCapChanged NOTIFICATION-TYPE
			OBJECTS { sleBGPPeerGroupControlRequest, sleBGPPeerGroupControlTimeStamp, sleBGPPeerGroupControlReqResult, sleBGPPeerGroupStr, sleBGPPeerGroupOverCap
				 }
			STATUS current
			DESCRIPTION
				"Description."
			::= { sleBGPPeerGroupNotification 18 }


		-- 1.3.6.1.4.1.6296.101.53.4.2.3.19
		sleBGPPeerGroupStrictCapMatchChanged NOTIFICATION-TYPE
			OBJECTS { sleBGPPeerGroupControlRequest, sleBGPPeerGroupControlTimeStamp, sleBGPPeerGroupControlReqResult, sleBGPPeerGroupStr, sleBGPPeerGroupStrictCapMatch
				 }
			STATUS current
			DESCRIPTION
				"Description."
			::= { sleBGPPeerGroupNotification 19 }


		-- 1.3.6.1.4.1.6296.101.53.4.2.3.20
		sleBGPPeerGroupCapRouteRefreshChanged NOTIFICATION-TYPE
			OBJECTS { sleBGPPeerGroupControlRequest, sleBGPPeerGroupControlTimeStamp, sleBGPPeerGroupControlReqResult, sleBGPPeerGroupStr, sleBGPPeerGroupCapRouteRefresh
				 }
			STATUS current
			DESCRIPTION
				"Description."
			::= { sleBGPPeerGroupNotification 20 }


		-- 1.3.6.1.4.1.6296.101.53.4.2.3.21
		sleBGPPeerGroupCapDynamicChanged NOTIFICATION-TYPE
			OBJECTS { sleBGPPeerGroupControlRequest, sleBGPPeerGroupControlTimeStamp, sleBGPPeerGroupControlReqResult, sleBGPPeerGroupStr, sleBGPPeerGroupCapDynamic
				 }
			STATUS current
			DESCRIPTION
				"Description."
			::= { sleBGPPeerGroupNotification 21 }


		-- 1.3.6.1.4.1.6296.101.53.4.2.3.22
		sleBGPPeerGroupEBGPMultihopCountChanged NOTIFICATION-TYPE
			OBJECTS { sleBGPPeerGroupControlRequest, sleBGPPeerGroupControlTimeStamp, sleBGPPeerGroupControlReqResult, sleBGPPeerGroupStr, sleBGPPeerGroupEBGPMulthopCount
				 }
			STATUS current
			DESCRIPTION
				"Description."
			::= { sleBGPPeerGroupNotification 22 }


		-- 1.3.6.1.4.1.6296.101.53.4.2.3.23
		sleBGPPeerGroupPasswordCreated NOTIFICATION-TYPE
			OBJECTS { sleBGPPeerGroupControlRequest, sleBGPPeerGroupControlTimeStamp, sleBGPPeerGroupControlReqResult, sleBGPPeerGroupStr, sleBGPPeerGroupPassword
				 }
			STATUS current
			DESCRIPTION
				"Description."
			::= { sleBGPPeerGroupNotification 23 }


		-- 1.3.6.1.4.1.6296.101.53.4.2.3.24
		sleBGPPeerGroupPasswordDeleted NOTIFICATION-TYPE
			OBJECTS { sleBGPPeerGroupControlRequest, sleBGPPeerGroupControlTimeStamp, sleBGPPeerGroupControlReqResult, sleBGPPeerGroupControlStr, sleBGPPeerControlPassword
				 }
			STATUS current
			DESCRIPTION
				"Description."
			::= { sleBGPPeerGroupNotification 24 }


		-- 1.3.6.1.4.1.6296.101.53.5
		sleBGPAFInfo OBJECT IDENTIFIER ::= { sleBGP 5 }


		-- 1.3.6.1.4.1.6296.101.53.5.1
		sleBGPAFBase OBJECT IDENTIFIER ::= { sleBGPAFInfo 1 }


		-- 1.3.6.1.4.1.6296.101.53.5.1.1
		sleBGPAFBaseTable OBJECT-TYPE
			SYNTAX SEQUENCE OF SleBGPAFBaseEntry
			MAX-ACCESS not-accessible
			STATUS current
			DESCRIPTION
				"Description."
			::= { sleBGPAFBase 1 }


		-- 1.3.6.1.4.1.6296.101.53.5.1.1.1
		sleBGPAFBaseEntry OBJECT-TYPE
			SYNTAX SleBGPAFBaseEntry
			MAX-ACCESS not-accessible
			STATUS current
			DESCRIPTION
				"Description."
			INDEX { sleBGPAFBaseMode, sleBGPAFBaseType }
			::= { sleBGPAFBaseTable 1 }


		SleBGPAFBaseEntry ::=
			SEQUENCE {
				sleBGPAFBaseMode
					INTEGER,
				sleBGPAFBaseType
					INTEGER,
				sleBGPAFBaseNetworkCheck
					INTEGER,
				sleBGPAFBaseSync
					INTEGER,
				sleBGPAFBaseDefOrg
					INTEGER,
				sleBGPAFBaseDampRoutemapName
					OCTET STRING,
				sleBGPAFBaseDampReachHlife
					INTEGER,
				sleBGPAFBaseDampReuse
					INTEGER,
				sleBGPAFBaseDampSuppress
					INTEGER,
				sleBGPAFBaseDampMaxSuppress
					INTEGER,
				sleBGPAFBaseDampUnReachHlife
					INTEGER
			 }

		-- 1.3.6.1.4.1.6296.101.53.5.1.1.1.1
		sleBGPAFBaseMode OBJECT-TYPE
			SYNTAX INTEGER
				{
				ipv4(1),
				ipv6(2)
				}
			MAX-ACCESS read-only
			STATUS current
			DESCRIPTION
				"1: ipv4
				2: ipv6
				"
			::= { sleBGPAFBaseEntry 1 }


		-- 1.3.6.1.4.1.6296.101.53.5.1.1.1.2
		sleBGPAFBaseType OBJECT-TYPE
			SYNTAX INTEGER
				{
				unicast(1),
				multicast(2),
				vpn4(3)
				}
			MAX-ACCESS read-only
			STATUS current
			DESCRIPTION
				"1: unicast
				2: multicast (only ipv4)
				3: vrf (only ipv4)
				"
			::= { sleBGPAFBaseEntry 2 }


		-- 1.3.6.1.4.1.6296.101.53.5.1.1.1.3
		sleBGPAFBaseNetworkCheck OBJECT-TYPE
			SYNTAX INTEGER
				{
				disable(0),
				enable(1)
				}
			MAX-ACCESS read-only
			STATUS current
			DESCRIPTION
				"Only ipv4 unicast, ipv4 vrf, ipv6 unicast"
			::= { sleBGPAFBaseEntry 3 }


		-- 1.3.6.1.4.1.6296.101.53.5.1.1.1.4
		sleBGPAFBaseSync OBJECT-TYPE
			SYNTAX INTEGER
				{
				disable(0),
				enable(1)
				}
			MAX-ACCESS read-only
			STATUS current
			DESCRIPTION
				"Only ipv4 unicast, ipv4 vrf, ipv6 unicast"
			::= { sleBGPAFBaseEntry 4 }


		-- 1.3.6.1.4.1.6296.101.53.5.1.1.1.5
		sleBGPAFBaseDefOrg OBJECT-TYPE
			SYNTAX INTEGER
				{
				disable(0),
				enable(1)
				}
			MAX-ACCESS read-only
			STATUS current
			DESCRIPTION
				"Only ipv4 unicast"
			::= { sleBGPAFBaseEntry 5 }


		-- 1.3.6.1.4.1.6296.101.53.5.1.1.1.6
		sleBGPAFBaseDampRoutemapName OBJECT-TYPE
			SYNTAX OCTET STRING (SIZE (0..512))
			MAX-ACCESS read-only
			STATUS current
			DESCRIPTION
				"Description."
			::= { sleBGPAFBaseEntry 6 }


		-- 1.3.6.1.4.1.6296.101.53.5.1.1.1.7
		sleBGPAFBaseDampReachHlife OBJECT-TYPE
			SYNTAX INTEGER (0..45)
			MAX-ACCESS read-only
			STATUS current
			DESCRIPTION
				"Description."
			::= { sleBGPAFBaseEntry 7 }


		-- 1.3.6.1.4.1.6296.101.53.5.1.1.1.8
		sleBGPAFBaseDampReuse OBJECT-TYPE
			SYNTAX INTEGER (0..20000)
			MAX-ACCESS read-only
			STATUS current
			DESCRIPTION
				"Description."
			::= { sleBGPAFBaseEntry 8 }


		-- 1.3.6.1.4.1.6296.101.53.5.1.1.1.9
		sleBGPAFBaseDampSuppress OBJECT-TYPE
			SYNTAX INTEGER (0..20000)
			MAX-ACCESS read-only
			STATUS current
			DESCRIPTION
				"Description."
			::= { sleBGPAFBaseEntry 9 }


		-- 1.3.6.1.4.1.6296.101.53.5.1.1.1.10
		sleBGPAFBaseDampMaxSuppress OBJECT-TYPE
			SYNTAX INTEGER (0..255)
			MAX-ACCESS read-only
			STATUS current
			DESCRIPTION
				"Description."
			::= { sleBGPAFBaseEntry 10 }


		-- 1.3.6.1.4.1.6296.101.53.5.1.1.1.11
		sleBGPAFBaseDampUnReachHlife OBJECT-TYPE
			SYNTAX INTEGER (0..45)
			MAX-ACCESS read-only
			STATUS current
			DESCRIPTION
				"Description."
			::= { sleBGPAFBaseEntry 11 }


		-- 1.3.6.1.4.1.6296.101.53.5.1.2
		sleBGPAFBaseControl OBJECT IDENTIFIER ::= { sleBGPAFBase 2 }


		-- 1.3.6.1.4.1.6296.101.53.5.1.2.1
		sleBGPAFBaseControlRequest OBJECT-TYPE
			SYNTAX INTEGER
				{
				setBGPAFBaseNetworkCheck(1),
				setBGPAFBaseSync(2),
				setBGPAFBaseDefOrg(3),
				setBGPAFBaseDampRoutemap(4),
				setBGPAFBaseDampTimeProfile(5),
				deleteBGPAFBaseDamp(6)
				}
			MAX-ACCESS read-write
			STATUS current
			DESCRIPTION
				"Description."
			::= { sleBGPAFBaseControl 1 }


		-- 1.3.6.1.4.1.6296.101.53.5.1.2.2
		sleBGPAFBaseControlStatus OBJECT-TYPE
			SYNTAX SleControlStatusType
			MAX-ACCESS read-only
			STATUS current
			DESCRIPTION
				"Description."
			::= { sleBGPAFBaseControl 2 }


		-- 1.3.6.1.4.1.6296.101.53.5.1.2.3
		sleBGPAFBaseControlTimer OBJECT-TYPE
			SYNTAX Gauge32
			MAX-ACCESS read-write
			STATUS current
			DESCRIPTION
				"Description."
			::= { sleBGPAFBaseControl 3 }


		-- 1.3.6.1.4.1.6296.101.53.5.1.2.4
		sleBGPAFBaseControlTimeStamp OBJECT-TYPE
			SYNTAX TimeTicks
			MAX-ACCESS read-only
			STATUS current
			DESCRIPTION
				"Description."
			::= { sleBGPAFBaseControl 4 }


		-- 1.3.6.1.4.1.6296.101.53.5.1.2.5
		sleBGPAFBaseControlReqResult OBJECT-TYPE
			SYNTAX SleControlRequestResultType
			MAX-ACCESS read-only
			STATUS current
			DESCRIPTION
				"Description."
			::= { sleBGPAFBaseControl 5 }


		-- 1.3.6.1.4.1.6296.101.53.5.1.2.6
		sleBGPAFBaseControlMode OBJECT-TYPE
			SYNTAX INTEGER
				{
				ipv4(1),
				ipv6(2)
				}
			MAX-ACCESS read-write
			STATUS current
			DESCRIPTION
				"1: ipv4
				2: ipv6
				"
			::= { sleBGPAFBaseControl 6 }


		-- 1.3.6.1.4.1.6296.101.53.5.1.2.7
		sleBGPAFBaseControlType OBJECT-TYPE
			SYNTAX INTEGER
				{
				unicast(1),
				multicast(2),
				vpn4(3)
				}
			MAX-ACCESS read-write
			STATUS current
			DESCRIPTION
				"1: unicast
				2: multicast (only ipv4)
				3: vrf (only ipv4)
				"
			::= { sleBGPAFBaseControl 7 }


		-- 1.3.6.1.4.1.6296.101.53.5.1.2.8
		sleBGPAFBaseControlNetworkCheck OBJECT-TYPE
			SYNTAX INTEGER
				{
				disable(0),
				enable(1)
				}
			MAX-ACCESS read-write
			STATUS current
			DESCRIPTION
				"Only ipv4 unicast, ipv4 vrf, ipv6 unicast"
			::= { sleBGPAFBaseControl 8 }


		-- 1.3.6.1.4.1.6296.101.53.5.1.2.9
		sleBGPAFBaseControlSync OBJECT-TYPE
			SYNTAX INTEGER
				{
				disable(0),
				enable(1)
				}
			MAX-ACCESS read-write
			STATUS current
			DESCRIPTION
				"Only ipv4 unicast, ipv4 vrf, ipv6 unicast"
			::= { sleBGPAFBaseControl 9 }


		-- 1.3.6.1.4.1.6296.101.53.5.1.2.10
		sleBGPAFBaseControlDefOrg OBJECT-TYPE
			SYNTAX INTEGER
				{
				disable(0),
				enable(1)
				}
			MAX-ACCESS read-write
			STATUS current
			DESCRIPTION
				"Only ipv4 unicast"
			::= { sleBGPAFBaseControl 10 }


		-- 1.3.6.1.4.1.6296.101.53.5.1.2.11
		sleBGPAFBaseControlDampRoutemapName OBJECT-TYPE
			SYNTAX OCTET STRING (SIZE (0..512))
			MAX-ACCESS read-write
			STATUS current
			DESCRIPTION
				" "
			::= { sleBGPAFBaseControl 11 }


		-- 1.3.6.1.4.1.6296.101.53.5.1.2.12
		sleBGPAFBaseControlDampReachHlife OBJECT-TYPE
			SYNTAX INTEGER (0..45)
			MAX-ACCESS read-write
			STATUS current
			DESCRIPTION
				" "
			::= { sleBGPAFBaseControl 12 }


		-- 1.3.6.1.4.1.6296.101.53.5.1.2.13
		sleBGPAFBaseControlDampReuse OBJECT-TYPE
			SYNTAX INTEGER (0..20000)
			MAX-ACCESS read-write
			STATUS current
			DESCRIPTION
				" "
			::= { sleBGPAFBaseControl 13 }


		-- 1.3.6.1.4.1.6296.101.53.5.1.2.14
		sleBGPAFBaseControlDampSuppress OBJECT-TYPE
			SYNTAX INTEGER (0..20000)
			MAX-ACCESS read-write
			STATUS current
			DESCRIPTION
				" "
			::= { sleBGPAFBaseControl 14 }


		-- 1.3.6.1.4.1.6296.101.53.5.1.2.15
		sleBGPAFBaseControlDampMaxSuppress OBJECT-TYPE
			SYNTAX INTEGER (0..255)
			MAX-ACCESS read-write
			STATUS current
			DESCRIPTION
				" "
			::= { sleBGPAFBaseControl 15 }


		-- 1.3.6.1.4.1.6296.101.53.5.1.2.16
		sleBGPAFBaseControlDampUnReachHlife OBJECT-TYPE
			SYNTAX INTEGER (0..45)
			MAX-ACCESS read-write
			STATUS current
			DESCRIPTION
				" "
			::= { sleBGPAFBaseControl 16 }


		-- 1.3.6.1.4.1.6296.101.53.5.1.3
		sleBGPAFBaseNotification OBJECT IDENTIFIER ::= { sleBGPAFBase 3 }


		-- 1.3.6.1.4.1.6296.101.53.5.1.3.1
		sleBGPAFBaseNetworkCheckChanged NOTIFICATION-TYPE
			OBJECTS { sleBGPAFBaseControlRequest, sleBGPAFBaseControlTimeStamp, sleBGPAFBaseControlReqResult, sleBGPAFBaseMode, sleBGPAFBaseType,
				sleBGPAFBaseNetworkCheck }
			STATUS current
			DESCRIPTION
				"Description."
			::= { sleBGPAFBaseNotification 1 }


		-- 1.3.6.1.4.1.6296.101.53.5.1.3.2
		sleBGPAFBaseSyncChanged NOTIFICATION-TYPE
			OBJECTS { sleBGPAFBaseControlRequest, sleBGPAFBaseControlTimeStamp, sleBGPAFBaseControlReqResult, sleBGPAFBaseMode, sleBGPAFBaseType,
				sleBGPAFBaseSync }
			STATUS current
			DESCRIPTION
				"Description."
			::= { sleBGPAFBaseNotification 2 }


		-- 1.3.6.1.4.1.6296.101.53.5.1.3.3
		sleBGPAFBaseDefOrgChanged NOTIFICATION-TYPE
			OBJECTS { sleBGPAFBaseControlRequest, sleBGPAFBaseControlTimeStamp, sleBGPAFBaseControlReqResult, sleBGPAFBaseMode, sleBGPAFBaseType,
				sleBGPAFBaseDefOrg }
			STATUS current
			DESCRIPTION
				"Description."
			::= { sleBGPAFBaseNotification 3 }


		-- 1.3.6.1.4.1.6296.101.53.5.1.3.4
		sleBGPAFBaseDampRoutemapNameChanged NOTIFICATION-TYPE
			OBJECTS { sleBGPAFBaseControlRequest, sleBGPAFBaseControlTimeStamp, sleBGPAFBaseControlReqResult, sleBGPAFBaseMode, sleBGPAFBaseType,
				sleBGPAFBaseDampRoutemapName }
			STATUS current
			DESCRIPTION
				"Description."
			::= { sleBGPAFBaseNotification 4 }


		-- 1.3.6.1.4.1.6296.101.53.5.1.3.5
		sleBGPAFBaseDampTimeProfileChanged NOTIFICATION-TYPE
			OBJECTS { sleBGPAFBaseControlRequest, sleBGPAFBaseControlTimeStamp, sleBGPAFBaseControlReqResult, sleBGPAFBaseMode, sleBGPAFBaseType,
				sleBGPAFBaseDampReachHlife, sleBGPAFBaseDampReuse, sleBGPAFBaseDampSuppress, sleBGPAFBaseDampMaxSuppress, sleBGPAFBaseDampUnReachHlife
				 }
			STATUS current
			DESCRIPTION
				"Description."
			::= { sleBGPAFBaseNotification 5 }


		-- 1.3.6.1.4.1.6296.101.53.5.1.3.6
		sleBGPAFBaseDampDeleted NOTIFICATION-TYPE
			OBJECTS { sleBGPAFBaseControlRequest, sleBGPAFBaseControlTimeStamp, sleBGPAFBaseControlReqResult, sleBGPAFBaseMode, sleBGPAFBaseType
				 }
			STATUS current
			DESCRIPTION
				"Description."
			::= { sleBGPAFBaseNotification 6 }


		-- 1.3.6.1.4.1.6296.101.53.5.2
		sleBGPAFRedist OBJECT IDENTIFIER ::= { sleBGPAFInfo 2 }


		-- 1.3.6.1.4.1.6296.101.53.5.2.1
		sleBGPAFRedistTable OBJECT-TYPE
			SYNTAX SEQUENCE OF SleBGPAFRedistEntry
			MAX-ACCESS not-accessible
			STATUS current
			DESCRIPTION
				"Description."
			::= { sleBGPAFRedist 1 }


		-- 1.3.6.1.4.1.6296.101.53.5.2.1.1
		sleBGPAFRedistEntry OBJECT-TYPE
			SYNTAX SleBGPAFRedistEntry
			MAX-ACCESS not-accessible
			STATUS current
			DESCRIPTION
				"Description."
			INDEX { sleBGPAFRedistMode, sleBGPAFRedistType, sleBGPAFRedistProtoType }
			::= { sleBGPAFRedistTable 1 }


		SleBGPAFRedistEntry ::=
			SEQUENCE {
				sleBGPAFRedistMode
					INTEGER,
				sleBGPAFRedistType
					INTEGER,
				sleBGPAFRedistProtoType
					INTEGER,
				sleBGPAFRedistRoutemapName
					OCTET STRING
			 }

		-- 1.3.6.1.4.1.6296.101.53.5.2.1.1.1
		sleBGPAFRedistMode OBJECT-TYPE
			SYNTAX INTEGER
				{
				ipv4(1),
				ipv6(2)
				}
			MAX-ACCESS read-only
			STATUS current
			DESCRIPTION
				"1: ipv4
				2: ipv6
				"
			::= { sleBGPAFRedistEntry 1 }


		-- 1.3.6.1.4.1.6296.101.53.5.2.1.1.2
		sleBGPAFRedistType OBJECT-TYPE
			SYNTAX INTEGER { unicast(1) }
			MAX-ACCESS read-only
			STATUS current
			DESCRIPTION
				"Only ipv4 unicast, ipv6 unicast
				"
			::= { sleBGPAFRedistEntry 2 }


		-- 1.3.6.1.4.1.6296.101.53.5.2.1.1.3
		sleBGPAFRedistProtoType OBJECT-TYPE
			SYNTAX INTEGER
				{
				kernel(1),
				connected(2),
				static(3),
				rip(4),
				ospf(5)
				}
			MAX-ACCESS read-only
			STATUS current
			DESCRIPTION
				" "
			::= { sleBGPAFRedistEntry 3 }


		-- 1.3.6.1.4.1.6296.101.53.5.2.1.1.4
		sleBGPAFRedistRoutemapName OBJECT-TYPE
			SYNTAX OCTET STRING (SIZE (0..512))
			MAX-ACCESS read-only
			STATUS current
			DESCRIPTION
				"
				"
			::= { sleBGPAFRedistEntry 4 }


		-- 1.3.6.1.4.1.6296.101.53.5.2.2
		sleBGPAFRedistControl OBJECT IDENTIFIER ::= { sleBGPAFRedist 2 }


		-- 1.3.6.1.4.1.6296.101.53.5.2.2.1
		sleBGPAFRedistControlRequest OBJECT-TYPE
			SYNTAX INTEGER
				{
				createBGPAFRedistribute(1),
				deleteBGPAFRedistribute(2),
				setBGPAFRedistribute(3)
				}
			MAX-ACCESS read-write
			STATUS current
			DESCRIPTION
				"Description."
			::= { sleBGPAFRedistControl 1 }


		-- 1.3.6.1.4.1.6296.101.53.5.2.2.2
		sleBGPAFRedistControlStatus OBJECT-TYPE
			SYNTAX SleControlStatusType
			MAX-ACCESS read-only
			STATUS current
			DESCRIPTION
				"Description."
			::= { sleBGPAFRedistControl 2 }


		-- 1.3.6.1.4.1.6296.101.53.5.2.2.3
		sleBGPAFRedistControlTimer OBJECT-TYPE
			SYNTAX Gauge32
			MAX-ACCESS read-write
			STATUS current
			DESCRIPTION
				"Description."
			::= { sleBGPAFRedistControl 3 }


		-- 1.3.6.1.4.1.6296.101.53.5.2.2.4
		sleBGPAFRedistControlTimeStamp OBJECT-TYPE
			SYNTAX TimeTicks
			MAX-ACCESS read-only
			STATUS current
			DESCRIPTION
				"Description."
			::= { sleBGPAFRedistControl 4 }


		-- 1.3.6.1.4.1.6296.101.53.5.2.2.5
		sleBGPAFRedistControlReqResult OBJECT-TYPE
			SYNTAX SleControlRequestResultType
			MAX-ACCESS read-only
			STATUS current
			DESCRIPTION
				"Description."
			::= { sleBGPAFRedistControl 5 }


		-- 1.3.6.1.4.1.6296.101.53.5.2.2.6
		sleBGPAFRedistControlMode OBJECT-TYPE
			SYNTAX INTEGER
				{
				ipv4(1),
				ipv6(2)
				}
			MAX-ACCESS read-write
			STATUS current
			DESCRIPTION
				"1: ipv4
				2: ipv6
				"
			::= { sleBGPAFRedistControl 6 }


		-- 1.3.6.1.4.1.6296.101.53.5.2.2.7
		sleBGPAFRedistControlType OBJECT-TYPE
			SYNTAX INTEGER { unicast(1) }
			MAX-ACCESS read-write
			STATUS current
			DESCRIPTION
				"1: unicast
				2: multicast (only ipv4)
				3: vrf (only ipv4)
				"
			::= { sleBGPAFRedistControl 7 }


		-- 1.3.6.1.4.1.6296.101.53.5.2.2.8
		sleBGPAFRedistControlProtoType OBJECT-TYPE
			SYNTAX INTEGER
				{
				kernel(1),
				connected(2),
				static(3),
				rip(4),
				ospf(5)
				}
			MAX-ACCESS read-write
			STATUS current
			DESCRIPTION
				"Only ipv4 unicast, ipv4 vrf, ipv6 unicast"
			::= { sleBGPAFRedistControl 8 }


		-- 1.3.6.1.4.1.6296.101.53.5.2.2.9
		sleBGPAFRedistControlRoutemapName OBJECT-TYPE
			SYNTAX OCTET STRING (SIZE (0..512))
			MAX-ACCESS read-write
			STATUS current
			DESCRIPTION
				"Only ipv4 unicast, ipv4 vrf, ipv6 unicast"
			::= { sleBGPAFRedistControl 9 }


		-- 1.3.6.1.4.1.6296.101.53.5.2.3
		sleBGPAFRedistNotification OBJECT IDENTIFIER ::= { sleBGPAFRedist 3 }


		-- 1.3.6.1.4.1.6296.101.53.5.2.3.1
		sleBGPAFRedistributeCreated NOTIFICATION-TYPE
			OBJECTS { sleBGPAFRedistControlRequest, sleBGPAFRedistControlTimeStamp, sleBGPAFRedistControlReqResult, sleBGPAFRedistMode, sleBGPAFRedistType,
				sleBGPAFRedistProtoType, sleBGPAFRedistRoutemapName }
			STATUS current
			DESCRIPTION
				"Description."
			::= { sleBGPAFRedistNotification 1 }


		-- 1.3.6.1.4.1.6296.101.53.5.2.3.2
		sleBGPAFRedistributeDeleted NOTIFICATION-TYPE
			OBJECTS { sleBGPAFRedistControlRequest, sleBGPAFRedistControlTimeStamp, sleBGPAFRedistControlReqResult, sleBGPAFRedistMode, sleBGPAFRedistType,
				sleBGPAFRedistControlProtoType, sleBGPAFRedistControlRoutemapName }
			STATUS current
			DESCRIPTION
				"Description."
			::= { sleBGPAFRedistNotification 2 }


		-- 1.3.6.1.4.1.6296.101.53.5.2.3.3
		sleBGPAFRedistributeChanged NOTIFICATION-TYPE
			OBJECTS { sleBGPAFRedistControlRequest, sleBGPAFRedistControlTimeStamp, sleBGPAFRedistControlReqResult, sleBGPAFRedistMode, sleBGPAFRedistType,
				sleBGPAFRedistProtoType, sleBGPAFRedistRoutemapName }
			STATUS current
			DESCRIPTION
				"Description."
			::= { sleBGPAFRedistNotification 3 }


		-- 1.3.6.1.4.1.6296.101.53.5.3
		sleBGPAFAggreAddr OBJECT IDENTIFIER ::= { sleBGPAFInfo 3 }


		-- 1.3.6.1.4.1.6296.101.53.5.3.1
		sleBGPAFAggreAddrTable OBJECT-TYPE
			SYNTAX SEQUENCE OF SleBGPAFAggreAddrEntry
			MAX-ACCESS not-accessible
			STATUS current
			DESCRIPTION
				"Description."
			::= { sleBGPAFAggreAddr 1 }


		-- 1.3.6.1.4.1.6296.101.53.5.3.1.1
		sleBGPAFAggreAddrEntry OBJECT-TYPE
			SYNTAX SleBGPAFAggreAddrEntry
			MAX-ACCESS not-accessible
			STATUS current
			DESCRIPTION
				"Description."
			INDEX { sleBGPAFAggreAddrMode, sleBGPAFAggreAddrType, sleBGPAFAggreAddrPrefix }
			::= { sleBGPAFAggreAddrTable 1 }


		SleBGPAFAggreAddrEntry ::=
			SEQUENCE {
				sleBGPAFAggreAddrMode
					INTEGER,
				sleBGPAFAggreAddrType
					INTEGER,
				sleBGPAFAggreAddrPrefix
					OCTET STRING,
				sleBGPAFAggreAddrAsSet
					INTEGER,
				sleBGPAFAggreAddrSummOnly
					INTEGER
			 }

		-- 1.3.6.1.4.1.6296.101.53.5.3.1.1.1
		sleBGPAFAggreAddrMode OBJECT-TYPE
			SYNTAX INTEGER
				{
				ipv4(1),
				ipv6(2)
				}
			MAX-ACCESS read-only
			STATUS current
			DESCRIPTION
				"1: ipv4
				2: ipv6
				"
			::= { sleBGPAFAggreAddrEntry 1 }


		-- 1.3.6.1.4.1.6296.101.53.5.3.1.1.2
		sleBGPAFAggreAddrType OBJECT-TYPE
			SYNTAX INTEGER { unicast(1) }
			MAX-ACCESS read-only
			STATUS current
			DESCRIPTION
				"Only ipv4 unicast, ipv6 unicast
				"
			::= { sleBGPAFAggreAddrEntry 2 }


		-- 1.3.6.1.4.1.6296.101.53.5.3.1.1.3
		sleBGPAFAggreAddrPrefix OBJECT-TYPE
			SYNTAX OCTET STRING
			MAX-ACCESS read-only
			STATUS current
			DESCRIPTION
				"example:
				1.1.1.1/24 or 1:1::1/64"
			::= { sleBGPAFAggreAddrEntry 3 }


		-- 1.3.6.1.4.1.6296.101.53.5.3.1.1.4
		sleBGPAFAggreAddrAsSet OBJECT-TYPE
			SYNTAX INTEGER
				{
				disable(0),
				enable(1)
				}
			MAX-ACCESS read-only
			STATUS current
			DESCRIPTION
				" "
			::= { sleBGPAFAggreAddrEntry 4 }


		-- 1.3.6.1.4.1.6296.101.53.5.3.1.1.5
		sleBGPAFAggreAddrSummOnly OBJECT-TYPE
			SYNTAX INTEGER
				{
				disable(0),
				enable(1)
				}
			MAX-ACCESS read-only
			STATUS current
			DESCRIPTION
				" "
			::= { sleBGPAFAggreAddrEntry 5 }


		-- 1.3.6.1.4.1.6296.101.53.5.3.2
		sleBGPAFAggreAddrControl OBJECT IDENTIFIER ::= { sleBGPAFAggreAddr 2 }


		-- 1.3.6.1.4.1.6296.101.53.5.3.2.1
		sleBGPAFAggreAddrControlRequest OBJECT-TYPE
			SYNTAX INTEGER
				{
				createBGPAFAggreAddress(1),
				deleteBGPAFAggreAddress(2)
				}
			MAX-ACCESS read-write
			STATUS current
			DESCRIPTION
				"Description."
			::= { sleBGPAFAggreAddrControl 1 }


		-- 1.3.6.1.4.1.6296.101.53.5.3.2.2
		sleBGPAFAggreAddrControlStatus OBJECT-TYPE
			SYNTAX SleControlStatusType
			MAX-ACCESS read-only
			STATUS current
			DESCRIPTION
				"Description."
			::= { sleBGPAFAggreAddrControl 2 }


		-- 1.3.6.1.4.1.6296.101.53.5.3.2.3
		sleBGPAFAggreAddrControlTimer OBJECT-TYPE
			SYNTAX Gauge32
			MAX-ACCESS read-write
			STATUS current
			DESCRIPTION
				"Description."
			::= { sleBGPAFAggreAddrControl 3 }


		-- 1.3.6.1.4.1.6296.101.53.5.3.2.4
		sleBGPAFAggreAddrControlTimeStamp OBJECT-TYPE
			SYNTAX TimeTicks
			MAX-ACCESS read-only
			STATUS current
			DESCRIPTION
				"Description."
			::= { sleBGPAFAggreAddrControl 4 }


		-- 1.3.6.1.4.1.6296.101.53.5.3.2.5
		sleBGPAFAggreAddrControlReqResult OBJECT-TYPE
			SYNTAX SleControlRequestResultType
			MAX-ACCESS read-only
			STATUS current
			DESCRIPTION
				"Description."
			::= { sleBGPAFAggreAddrControl 5 }


		-- 1.3.6.1.4.1.6296.101.53.5.3.2.6
		sleBGPAFAggreAddrControlMode OBJECT-TYPE
			SYNTAX INTEGER
				{
				ipv4(1),
				ipv6(2)
				}
			MAX-ACCESS read-write
			STATUS current
			DESCRIPTION
				"1: ipv4
				2: ipv6
				"
			::= { sleBGPAFAggreAddrControl 6 }


		-- 1.3.6.1.4.1.6296.101.53.5.3.2.7
		sleBGPAFAggreAddrControlType OBJECT-TYPE
			SYNTAX INTEGER { unicast(1) }
			MAX-ACCESS read-write
			STATUS current
			DESCRIPTION
				"Only ipv4 unicast, ipv6 unicast"
			::= { sleBGPAFAggreAddrControl 7 }


		-- 1.3.6.1.4.1.6296.101.53.5.3.2.8
		sleBGPAFAggreAddrControlAddrPrefix OBJECT-TYPE
			SYNTAX OCTET STRING
			MAX-ACCESS read-write
			STATUS current
			DESCRIPTION
				"example:
				1.1.1.1/24 or 1:1::1/64"
			::= { sleBGPAFAggreAddrControl 8 }


		-- 1.3.6.1.4.1.6296.101.53.5.3.2.9
		sleBGPAFAggreAddrControlAsSet OBJECT-TYPE
			SYNTAX INTEGER
				{
				disable(0),
				enable(1)
				}
			MAX-ACCESS read-write
			STATUS current
			DESCRIPTION
				" "
			::= { sleBGPAFAggreAddrControl 9 }


		-- 1.3.6.1.4.1.6296.101.53.5.3.2.10
		sleBGPAFAggreAddrControlSummOnly OBJECT-TYPE
			SYNTAX INTEGER
				{
				disable(0),
				enable(1)
				}
			MAX-ACCESS read-write
			STATUS current
			DESCRIPTION
				" "
			::= { sleBGPAFAggreAddrControl 10 }


		-- 1.3.6.1.4.1.6296.101.53.5.3.3
		sleBGPAFAggreAddrNotification OBJECT IDENTIFIER ::= { sleBGPAFAggreAddr 3 }


		-- 1.3.6.1.4.1.6296.101.53.5.3.3.1
		sleBGPAFAggreAddressCreated NOTIFICATION-TYPE
			OBJECTS { sleBGPAFAggreAddrControlRequest, sleBGPAFAggreAddrControlTimeStamp, sleBGPAFAggreAddrControlReqResult, sleBGPAFAggreAddrMode, sleBGPAFAggreAddrType,
				sleBGPAFAggreAddrPrefix, sleBGPAFAggreAddrAsSet, sleBGPAFAggreAddrSummOnly }
			STATUS current
			DESCRIPTION
				"Description."
			::= { sleBGPAFAggreAddrNotification 1 }


		-- 1.3.6.1.4.1.6296.101.53.5.3.3.2
		sleBGPAFAggreAddressDeleted NOTIFICATION-TYPE
			OBJECTS { sleBGPAFAggreAddrControlRequest, sleBGPAFAggreAddrControlTimeStamp, sleBGPAFAggreAddrControlReqResult, sleBGPAFAggreAddrControlMode, sleBGPAFAggreAddrControlType,
				sleBGPAFAggreAddrControlAddrPrefix, sleBGPAFAggreAddrControlAsSet, sleBGPAFAggreAddrControlSummOnly }
			STATUS current
			DESCRIPTION
				"Description."
			::= { sleBGPAFAggreAddrNotification 2 }


		-- 1.3.6.1.4.1.6296.101.53.5.4
		sleBGPAFPeerInfo OBJECT IDENTIFIER ::= { sleBGPAFInfo 4 }


		-- 1.3.6.1.4.1.6296.101.53.5.4.1
		sleBGPAFPeer OBJECT IDENTIFIER ::= { sleBGPAFPeerInfo 1 }


		-- 1.3.6.1.4.1.6296.101.53.5.4.1.1
		sleBGPAFPeerTable OBJECT-TYPE
			SYNTAX SEQUENCE OF SleBGPAFPeerEntry
			MAX-ACCESS not-accessible
			STATUS current
			DESCRIPTION
				"Description."
			::= { sleBGPAFPeer 1 }


		-- 1.3.6.1.4.1.6296.101.53.5.4.1.1.1
		sleBGPAFPeerEntry OBJECT-TYPE
			SYNTAX SleBGPAFPeerEntry
			MAX-ACCESS not-accessible
			STATUS current
			DESCRIPTION
				"Description."
			INDEX { sleBGPAFPeerMode, sleBGPAFPeerType, sleBGPAFPeerName }
			::= { sleBGPAFPeerTable 1 }


		SleBGPAFPeerEntry ::=
			SEQUENCE {
				sleBGPAFPeerMode
					INTEGER,
				sleBGPAFPeerType
					INTEGER,
				sleBGPAFPeerName
					OCTET STRING,
				sleBGPAFPeerActviate
					INTEGER,
				sleBGPAFPeerAllowAsIn
					INTEGER,
				sleBGPAFPeerAllowAsInNum
					INTEGER,
				sleBGPAFPeerAttrUnchangedAsPath
					INTEGER,
				sleBGPAFPeerAttrUnchangedMed
					INTEGER,
				sleBGPAFPeerAttrUnchangedNexthop
					INTEGER,
				sleBGPAFPeerCapGracefulRestart
					INTEGER,
				sleBGPAFPeerCapOrfMode
					INTEGER,
				sleBGPAFPeerDefOriginate
					INTEGER,
				sleBGPAFPeerDefOriginateRoutemap
					OCTET STRING,
				sleBGPAFPeerFLInAccName
					OCTET STRING,
				sleBGPAFPeerFLOutAccName
					OCTET STRING,
				sleBGPAFPeerMaxPrefixNum
					Gauge32,
				sleBGPAFPeerMaxPrefixThreshold
					INTEGER,
				sleBGPAFPeerMaxPrefixWarnOnly
					INTEGER,
				sleBGPAFPeerRemotePrivateAs
					INTEGER,
				sleBGPAFPeerInRoutemap
					OCTET STRING,
				sleBGPAFPeerOutRoutemap
					OCTET STRING,
				sleBGPAFPeerRouteReflectClient
					INTEGER,
				sleBGPAFPeerRouteServerClient
					INTEGER,
				sleBGPAFPeerInDistListName
					OCTET STRING,
				sleBGPAFPeerOutDistListName
					OCTET STRING,
				sleBGPAFPeerInPrefixListName
					OCTET STRING,
				sleBGPAFPeerOutPrefixListName
					OCTET STRING,
				sleBGPAFPeerSendCommunity
					INTEGER,
				sleBGPAFPeerNexthopSelf
					INTEGER,
				sleBGPAFPeerSoftReconfig
					INTEGER,
				sleBGPAFPeerUnsuppressMapName
					OCTET STRING
			 }

		-- 1.3.6.1.4.1.6296.101.53.5.4.1.1.1.1
		sleBGPAFPeerMode OBJECT-TYPE
			SYNTAX INTEGER
				{
				ipv4(1),
				ipv6(2),
				vpn4(3)
				}
			MAX-ACCESS read-only
			STATUS current
			DESCRIPTION
				"1: ipv4
				2: ipv6
				3: vpn4"
			::= { sleBGPAFPeerEntry 1 }


		-- 1.3.6.1.4.1.6296.101.53.5.4.1.1.1.2
		sleBGPAFPeerType OBJECT-TYPE
			SYNTAX INTEGER
				{
				unicast(1),
				multicast(2),
				vrf(3)
				}
			MAX-ACCESS read-only
			STATUS current
			DESCRIPTION
				"1: unicast
				2: multicast (only ipv4)
				3: vrf (only ipv4)
				"
			::= { sleBGPAFPeerEntry 2 }


		-- 1.3.6.1.4.1.6296.101.53.5.4.1.1.1.3
		sleBGPAFPeerName OBJECT-TYPE
			SYNTAX OCTET STRING
			MAX-ACCESS read-only
			STATUS current
			DESCRIPTION
				"
				"
			::= { sleBGPAFPeerEntry 3 }


		-- 1.3.6.1.4.1.6296.101.53.5.4.1.1.1.4
		sleBGPAFPeerActviate OBJECT-TYPE
			SYNTAX INTEGER
				{
				disable(0),
				enable(1)
				}
			MAX-ACCESS read-only
			STATUS current
			DESCRIPTION
				" "
			::= { sleBGPAFPeerEntry 4 }


		-- 1.3.6.1.4.1.6296.101.53.5.4.1.1.1.5
		sleBGPAFPeerAllowAsIn OBJECT-TYPE
			SYNTAX INTEGER
				{
				disable(0),
				enable(1)
				}
			MAX-ACCESS read-only
			STATUS current
			DESCRIPTION
				" "
			::= { sleBGPAFPeerEntry 5 }


		-- 1.3.6.1.4.1.6296.101.53.5.4.1.1.1.6
		sleBGPAFPeerAllowAsInNum OBJECT-TYPE
			SYNTAX INTEGER (0..10)
			MAX-ACCESS read-only
			STATUS current
			DESCRIPTION
				" "
			::= { sleBGPAFPeerEntry 6 }


		-- 1.3.6.1.4.1.6296.101.53.5.4.1.1.1.7
		sleBGPAFPeerAttrUnchangedAsPath OBJECT-TYPE
			SYNTAX INTEGER
				{
				disable(0),
				enable(1)
				}
			MAX-ACCESS read-only
			STATUS current
			DESCRIPTION
				" "
			::= { sleBGPAFPeerEntry 7 }


		-- 1.3.6.1.4.1.6296.101.53.5.4.1.1.1.8
		sleBGPAFPeerAttrUnchangedMed OBJECT-TYPE
			SYNTAX INTEGER
				{
				disable(0),
				enable(1)
				}
			MAX-ACCESS read-only
			STATUS current
			DESCRIPTION
				" "
			::= { sleBGPAFPeerEntry 8 }


		-- 1.3.6.1.4.1.6296.101.53.5.4.1.1.1.9
		sleBGPAFPeerAttrUnchangedNexthop OBJECT-TYPE
			SYNTAX INTEGER
				{
				disable(0),
				enable(1)
				}
			MAX-ACCESS read-only
			STATUS current
			DESCRIPTION
				" "
			::= { sleBGPAFPeerEntry 9 }


		-- 1.3.6.1.4.1.6296.101.53.5.4.1.1.1.10
		sleBGPAFPeerCapGracefulRestart OBJECT-TYPE
			SYNTAX INTEGER
				{
				disable(0),
				enable(1)
				}
			MAX-ACCESS read-only
			STATUS current
			DESCRIPTION
				" "
			::= { sleBGPAFPeerEntry 10 }


		-- 1.3.6.1.4.1.6296.101.53.5.4.1.1.1.11
		sleBGPAFPeerCapOrfMode OBJECT-TYPE
			SYNTAX INTEGER
				{
				disable(0),
				send(1),
				recevie(2),
				both(3)
				}
			MAX-ACCESS read-only
			STATUS current
			DESCRIPTION
				" "
			::= { sleBGPAFPeerEntry 11 }


		-- 1.3.6.1.4.1.6296.101.53.5.4.1.1.1.12
		sleBGPAFPeerDefOriginate OBJECT-TYPE
			SYNTAX INTEGER
				{
				disable(0),
				enable(1)
				}
			MAX-ACCESS read-only
			STATUS current
			DESCRIPTION
				" "
			::= { sleBGPAFPeerEntry 12 }


		-- 1.3.6.1.4.1.6296.101.53.5.4.1.1.1.13
		sleBGPAFPeerDefOriginateRoutemap OBJECT-TYPE
			SYNTAX OCTET STRING (SIZE (0..512))
			MAX-ACCESS read-only
			STATUS current
			DESCRIPTION
				" "
			::= { sleBGPAFPeerEntry 13 }


		-- 1.3.6.1.4.1.6296.101.53.5.4.1.1.1.14
		sleBGPAFPeerFLInAccName OBJECT-TYPE
			SYNTAX OCTET STRING (SIZE (0..512))
			MAX-ACCESS read-only
			STATUS current
			DESCRIPTION
				" "
			::= { sleBGPAFPeerEntry 14 }


		-- 1.3.6.1.4.1.6296.101.53.5.4.1.1.1.15
		sleBGPAFPeerFLOutAccName OBJECT-TYPE
			SYNTAX OCTET STRING (SIZE (0..512))
			MAX-ACCESS read-only
			STATUS current
			DESCRIPTION
				" "
			::= { sleBGPAFPeerEntry 15 }


		-- 1.3.6.1.4.1.6296.101.53.5.4.1.1.1.16
		sleBGPAFPeerMaxPrefixNum OBJECT-TYPE
			SYNTAX Gauge32 (0..4294967295)
			MAX-ACCESS read-only
			STATUS current
			DESCRIPTION
				" "
			::= { sleBGPAFPeerEntry 16 }


		-- 1.3.6.1.4.1.6296.101.53.5.4.1.1.1.17
		sleBGPAFPeerMaxPrefixThreshold OBJECT-TYPE
			SYNTAX INTEGER (0..100)
			MAX-ACCESS read-only
			STATUS current
			DESCRIPTION
				" "
			::= { sleBGPAFPeerEntry 17 }


		-- 1.3.6.1.4.1.6296.101.53.5.4.1.1.1.18
		sleBGPAFPeerMaxPrefixWarnOnly OBJECT-TYPE
			SYNTAX INTEGER
				{
				disable(0),
				enable(1)
				}
			MAX-ACCESS read-only
			STATUS current
			DESCRIPTION
				" "
			::= { sleBGPAFPeerEntry 18 }


		-- 1.3.6.1.4.1.6296.101.53.5.4.1.1.1.19
		sleBGPAFPeerRemotePrivateAs OBJECT-TYPE
			SYNTAX INTEGER
				{
				disable(0),
				enable(1)
				}
			MAX-ACCESS read-only
			STATUS current
			DESCRIPTION
				" "
			::= { sleBGPAFPeerEntry 19 }


		-- 1.3.6.1.4.1.6296.101.53.5.4.1.1.1.20
		sleBGPAFPeerInRoutemap OBJECT-TYPE
			SYNTAX OCTET STRING (SIZE (0..512))
			MAX-ACCESS read-only
			STATUS current
			DESCRIPTION
				" "
			::= { sleBGPAFPeerEntry 20 }


		-- 1.3.6.1.4.1.6296.101.53.5.4.1.1.1.21
		sleBGPAFPeerOutRoutemap OBJECT-TYPE
			SYNTAX OCTET STRING (SIZE (0..512))
			MAX-ACCESS read-only
			STATUS current
			DESCRIPTION
				" "
			::= { sleBGPAFPeerEntry 21 }


		-- 1.3.6.1.4.1.6296.101.53.5.4.1.1.1.22
		sleBGPAFPeerRouteReflectClient OBJECT-TYPE
			SYNTAX INTEGER
				{
				disable(0),
				enable(1)
				}
			MAX-ACCESS read-only
			STATUS current
			DESCRIPTION
				" "
			::= { sleBGPAFPeerEntry 22 }


		-- 1.3.6.1.4.1.6296.101.53.5.4.1.1.1.23
		sleBGPAFPeerRouteServerClient OBJECT-TYPE
			SYNTAX INTEGER
				{
				disable(0),
				enable(1)
				}
			MAX-ACCESS read-only
			STATUS current
			DESCRIPTION
				" "
			::= { sleBGPAFPeerEntry 23 }


		-- 1.3.6.1.4.1.6296.101.53.5.4.1.1.1.24
		sleBGPAFPeerInDistListName OBJECT-TYPE
			SYNTAX OCTET STRING (SIZE (0..512))
			MAX-ACCESS read-only
			STATUS current
			DESCRIPTION
				" "
			::= { sleBGPAFPeerEntry 24 }


		-- 1.3.6.1.4.1.6296.101.53.5.4.1.1.1.25
		sleBGPAFPeerOutDistListName OBJECT-TYPE
			SYNTAX OCTET STRING (SIZE (0..512))
			MAX-ACCESS read-only
			STATUS current
			DESCRIPTION
				" "
			::= { sleBGPAFPeerEntry 25 }


		-- 1.3.6.1.4.1.6296.101.53.5.4.1.1.1.26
		sleBGPAFPeerInPrefixListName OBJECT-TYPE
			SYNTAX OCTET STRING (SIZE (0..512))
			MAX-ACCESS read-only
			STATUS current
			DESCRIPTION
				" "
			::= { sleBGPAFPeerEntry 26 }


		-- 1.3.6.1.4.1.6296.101.53.5.4.1.1.1.27
		sleBGPAFPeerOutPrefixListName OBJECT-TYPE
			SYNTAX OCTET STRING (SIZE (0..512))
			MAX-ACCESS read-only
			STATUS current
			DESCRIPTION
				" "
			::= { sleBGPAFPeerEntry 27 }


		-- 1.3.6.1.4.1.6296.101.53.5.4.1.1.1.28
		sleBGPAFPeerSendCommunity OBJECT-TYPE
			SYNTAX INTEGER
				{
				disable(0),
				standard(1),
				extended(2),
				both(3)
				}
			MAX-ACCESS read-only
			STATUS current
			DESCRIPTION
				"Except vpn4."
			::= { sleBGPAFPeerEntry 28 }


		-- 1.3.6.1.4.1.6296.101.53.5.4.1.1.1.29
		sleBGPAFPeerNexthopSelf OBJECT-TYPE
			SYNTAX INTEGER
				{
				disable(0),
				enable(1)
				}
			MAX-ACCESS read-only
			STATUS current
			DESCRIPTION
				"Except vpn4."
			::= { sleBGPAFPeerEntry 29 }


		-- 1.3.6.1.4.1.6296.101.53.5.4.1.1.1.30
		sleBGPAFPeerSoftReconfig OBJECT-TYPE
			SYNTAX INTEGER
				{
				disable(0),
				enable(1)
				}
			MAX-ACCESS read-only
			STATUS current
			DESCRIPTION
				"Except vpn4."
			::= { sleBGPAFPeerEntry 30 }


		-- 1.3.6.1.4.1.6296.101.53.5.4.1.1.1.31
		sleBGPAFPeerUnsuppressMapName OBJECT-TYPE
			SYNTAX OCTET STRING (SIZE (0..512))
			MAX-ACCESS read-only
			STATUS current
			DESCRIPTION
				"Except vpn4."
			::= { sleBGPAFPeerEntry 31 }


		-- 1.3.6.1.4.1.6296.101.53.5.4.1.2
		sleBGPAFPeerControl OBJECT IDENTIFIER ::= { sleBGPAFPeer 2 }


		-- 1.3.6.1.4.1.6296.101.53.5.4.1.2.1
		sleBGPAFPeerControlRequest OBJECT-TYPE
			SYNTAX INTEGER
				{
				setBGPAFPeerActivate(1),
				setBGPAFPeerAllowAsInProfile(2),
				setBGPAFPeerAttrUnchangedProfile(3),
				setBGPAFPeerCapGracefulRestart(4),
				setBGPAFPeerCapOrfMode(5),
				setBGPAFPeerDefaultOriginate(6),
				setBGPAFPeerFLInAccName(7),
				unsetBGPAFPeerFLInAccName(8),
				setBGPAFPeerFLOutAccName(9),
				unsetBGPAFPeerFLOutAccName(10),
				setBGPAFPeerMaxPrefixProfile(11),
				setBGPAFPeerRemotePrivateAs(12),
				setBGPAFPeerInRoutemap(13),
				unsetBGPAFPeerInRoutemap(14),
				setBGPAFPeerOutRoutemap(15),
				unsetBGPAFPeerOutRoutemap(16),
				setBGPAFPeerRouteReflectClient(17),
				setBGPAFPeerRouteServerClient(18),
				setBGPAFPeerSendCommunity(19),
				setBGPAFPeerNexthopSelf(20),
				setBGPAFPeerSoftReconfig(21),
				setBGPAFPeerUnsupressMapName(22),
				unsetBGPAFPeerUnsupressMapName(23),
				setBGPAFPeerInDistListName(24),
				unsetBGPAFPeerInDistListName(25),
				setBGPAFPeerOutDistListName(26),
				unsetBGPAFPeerOutDistListName(27),
				setBGPAFPeerInPrefixListName(28),
				unsetBGPAFPeerInPrefixListName(29),
				setBGPAFPeerOutPrefixListName(30),
				unsetBGPAFPeerOutPrefixListName(31)
				}
			MAX-ACCESS read-write
			STATUS current
			DESCRIPTION
				"Description."
			::= { sleBGPAFPeerControl 1 }


		-- 1.3.6.1.4.1.6296.101.53.5.4.1.2.2
		sleBGPAFPeerControlStatus OBJECT-TYPE
			SYNTAX SleControlStatusType
			MAX-ACCESS read-only
			STATUS current
			DESCRIPTION
				"Description."
			::= { sleBGPAFPeerControl 2 }


		-- 1.3.6.1.4.1.6296.101.53.5.4.1.2.3
		sleBGPAFPeerControlTimer OBJECT-TYPE
			SYNTAX Gauge32
			MAX-ACCESS read-write
			STATUS current
			DESCRIPTION
				"Description."
			::= { sleBGPAFPeerControl 3 }


		-- 1.3.6.1.4.1.6296.101.53.5.4.1.2.4
		sleBGPAFPeerControlTimeStamp OBJECT-TYPE
			SYNTAX TimeTicks
			MAX-ACCESS read-only
			STATUS current
			DESCRIPTION
				"Description."
			::= { sleBGPAFPeerControl 4 }


		-- 1.3.6.1.4.1.6296.101.53.5.4.1.2.5
		sleBGPAFPeerControlReqResult OBJECT-TYPE
			SYNTAX SleControlRequestResultType
			MAX-ACCESS read-only
			STATUS current
			DESCRIPTION
				"Description."
			::= { sleBGPAFPeerControl 5 }


		-- 1.3.6.1.4.1.6296.101.53.5.4.1.2.6
		sleBGPAFPeerControlMode OBJECT-TYPE
			SYNTAX INTEGER
				{
				ipv4(1),
				ipv6(2),
				vpn4(3)
				}
			MAX-ACCESS read-write
			STATUS current
			DESCRIPTION
				"1: ipv4
				2: ipv6
				3: vpn4"
			::= { sleBGPAFPeerControl 6 }


		-- 1.3.6.1.4.1.6296.101.53.5.4.1.2.7
		sleBGPAFPeerControlType OBJECT-TYPE
			SYNTAX INTEGER
				{
				unicast(1),
				multicast(2),
				vrf(3)
				}
			MAX-ACCESS read-write
			STATUS current
			DESCRIPTION
				"1: unicast
				2: multicast (only ipv4)
				3: vrf (only ipv4)
				"
			::= { sleBGPAFPeerControl 7 }


		-- 1.3.6.1.4.1.6296.101.53.5.4.1.2.8
		sleBGPAFPeerControlName OBJECT-TYPE
			SYNTAX OCTET STRING
			MAX-ACCESS read-write
			STATUS current
			DESCRIPTION
				" "
			::= { sleBGPAFPeerControl 8 }


		-- 1.3.6.1.4.1.6296.101.53.5.4.1.2.9
		sleBGPAFPeerControlActviate OBJECT-TYPE
			SYNTAX INTEGER
				{
				disable(0),
				enable(1)
				}
			MAX-ACCESS read-write
			STATUS current
			DESCRIPTION
				" "
			::= { sleBGPAFPeerControl 9 }


		-- 1.3.6.1.4.1.6296.101.53.5.4.1.2.10
		sleBGPAFPeerControlAllowAsIn OBJECT-TYPE
			SYNTAX INTEGER
				{
				disable(0),
				enable(1)
				}
			MAX-ACCESS read-write
			STATUS current
			DESCRIPTION
				" "
			::= { sleBGPAFPeerControl 10 }


		-- 1.3.6.1.4.1.6296.101.53.5.4.1.2.11
		sleBGPAFPeerControlAllowAsInNum OBJECT-TYPE
			SYNTAX INTEGER (0..10)
			MAX-ACCESS read-write
			STATUS current
			DESCRIPTION
				" "
			::= { sleBGPAFPeerControl 11 }


		-- 1.3.6.1.4.1.6296.101.53.5.4.1.2.12
		sleBGPAFPeerControlAttrUnchangedAsPath OBJECT-TYPE
			SYNTAX INTEGER
				{
				disable(0),
				enable(1)
				}
			MAX-ACCESS read-write
			STATUS current
			DESCRIPTION
				" "
			::= { sleBGPAFPeerControl 12 }


		-- 1.3.6.1.4.1.6296.101.53.5.4.1.2.13
		sleBGPAFPeerControlAttrUnchangedMed OBJECT-TYPE
			SYNTAX INTEGER
				{
				disable(0),
				enable(1)
				}
			MAX-ACCESS read-write
			STATUS current
			DESCRIPTION
				" "
			::= { sleBGPAFPeerControl 13 }


		-- 1.3.6.1.4.1.6296.101.53.5.4.1.2.14
		sleBGPAFPeerControlAttrUnchangedNexthop OBJECT-TYPE
			SYNTAX INTEGER
				{
				disable(0),
				enable(1)
				}
			MAX-ACCESS read-write
			STATUS current
			DESCRIPTION
				" "
			::= { sleBGPAFPeerControl 14 }


		-- 1.3.6.1.4.1.6296.101.53.5.4.1.2.15
		sleBGPAFPeerControlCapGracefulRestart OBJECT-TYPE
			SYNTAX INTEGER
				{
				disable(0),
				enable(1)
				}
			MAX-ACCESS read-write
			STATUS current
			DESCRIPTION
				" "
			::= { sleBGPAFPeerControl 15 }


		-- 1.3.6.1.4.1.6296.101.53.5.4.1.2.16
		sleBGPAFPeerControlCapOrfMode OBJECT-TYPE
			SYNTAX INTEGER
				{
				disable(0),
				send(1),
				receive(2),
				both(3)
				}
			MAX-ACCESS read-write
			STATUS current
			DESCRIPTION
				" "
			::= { sleBGPAFPeerControl 16 }


		-- 1.3.6.1.4.1.6296.101.53.5.4.1.2.17
		sleBGPAFPeerControlDefOriginate OBJECT-TYPE
			SYNTAX INTEGER
				{
				disable(0),
				enable(1)
				}
			MAX-ACCESS read-write
			STATUS current
			DESCRIPTION
				" "
			::= { sleBGPAFPeerControl 17 }


		-- 1.3.6.1.4.1.6296.101.53.5.4.1.2.18
		sleBGPAFPeerControlDefOriginateRoutemap OBJECT-TYPE
			SYNTAX OCTET STRING (SIZE (0..512))
			MAX-ACCESS read-write
			STATUS current
			DESCRIPTION
				" "
			::= { sleBGPAFPeerControl 18 }


		-- 1.3.6.1.4.1.6296.101.53.5.4.1.2.19
		sleBGPAFPeerControlFLInAccName OBJECT-TYPE
			SYNTAX OCTET STRING (SIZE (0..512))
			MAX-ACCESS read-write
			STATUS current
			DESCRIPTION
				" "
			::= { sleBGPAFPeerControl 19 }


		-- 1.3.6.1.4.1.6296.101.53.5.4.1.2.20
		sleBGPAFPeerControlFLOutAccName OBJECT-TYPE
			SYNTAX OCTET STRING (SIZE (0..512))
			MAX-ACCESS read-write
			STATUS current
			DESCRIPTION
				" "
			::= { sleBGPAFPeerControl 20 }


		-- 1.3.6.1.4.1.6296.101.53.5.4.1.2.21
		sleBGPAFPeerControlMaxPrefixNum OBJECT-TYPE
			SYNTAX Gauge32 (1..4294967295)
			MAX-ACCESS read-write
			STATUS current
			DESCRIPTION
				" "
			::= { sleBGPAFPeerControl 21 }


		-- 1.3.6.1.4.1.6296.101.53.5.4.1.2.22
		sleBGPAFPeerControlMaxPrefixThreshold OBJECT-TYPE
			SYNTAX INTEGER (0..100)
			MAX-ACCESS read-write
			STATUS current
			DESCRIPTION
				" "
			::= { sleBGPAFPeerControl 22 }


		-- 1.3.6.1.4.1.6296.101.53.5.4.1.2.23
		sleBGPAFPeerControlMaxPrefixWarnOnly OBJECT-TYPE
			SYNTAX INTEGER
				{
				disable(0),
				enable(1)
				}
			MAX-ACCESS read-write
			STATUS current
			DESCRIPTION
				" "
			::= { sleBGPAFPeerControl 23 }


		-- 1.3.6.1.4.1.6296.101.53.5.4.1.2.24
		sleBGPAFPeerControlRemotePrivateAs OBJECT-TYPE
			SYNTAX INTEGER
				{
				disable(0),
				enable(1)
				}
			MAX-ACCESS read-write
			STATUS current
			DESCRIPTION
				" "
			::= { sleBGPAFPeerControl 24 }


		-- 1.3.6.1.4.1.6296.101.53.5.4.1.2.25
		sleBGPAFPeerControlInRoutemap OBJECT-TYPE
			SYNTAX OCTET STRING (SIZE (0..512))
			MAX-ACCESS read-write
			STATUS current
			DESCRIPTION
				" "
			::= { sleBGPAFPeerControl 25 }


		-- 1.3.6.1.4.1.6296.101.53.5.4.1.2.26
		sleBGPAFPeerControlOutRoutemap OBJECT-TYPE
			SYNTAX OCTET STRING (SIZE (0..512))
			MAX-ACCESS read-write
			STATUS current
			DESCRIPTION
				" "
			::= { sleBGPAFPeerControl 26 }


		-- 1.3.6.1.4.1.6296.101.53.5.4.1.2.27
		sleBGPAFPeerControlRouteReflectClient OBJECT-TYPE
			SYNTAX INTEGER
				{
				disable(0),
				enable(1)
				}
			MAX-ACCESS read-write
			STATUS current
			DESCRIPTION
				" "
			::= { sleBGPAFPeerControl 27 }


		-- 1.3.6.1.4.1.6296.101.53.5.4.1.2.28
		sleBGPAFPeerControlRouteServerClient OBJECT-TYPE
			SYNTAX INTEGER
				{
				disable(0),
				enable(1)
				}
			MAX-ACCESS read-write
			STATUS current
			DESCRIPTION
				" "
			::= { sleBGPAFPeerControl 28 }


		-- 1.3.6.1.4.1.6296.101.53.5.4.1.2.29
		sleBGPAFPeerControlInDistListName OBJECT-TYPE
			SYNTAX OCTET STRING (SIZE (0..512))
			MAX-ACCESS read-write
			STATUS current
			DESCRIPTION
				" "
			::= { sleBGPAFPeerControl 29 }


		-- 1.3.6.1.4.1.6296.101.53.5.4.1.2.30
		sleBGPAFPeerControlOutDistListName OBJECT-TYPE
			SYNTAX OCTET STRING (SIZE (0..512))
			MAX-ACCESS read-write
			STATUS current
			DESCRIPTION
				" "
			::= { sleBGPAFPeerControl 30 }


		-- 1.3.6.1.4.1.6296.101.53.5.4.1.2.31
		sleBGPAFPeerControlInPrefixListName OBJECT-TYPE
			SYNTAX OCTET STRING (SIZE (0..512))
			MAX-ACCESS read-write
			STATUS current
			DESCRIPTION
				" "
			::= { sleBGPAFPeerControl 31 }


		-- 1.3.6.1.4.1.6296.101.53.5.4.1.2.32
		sleBGPAFPeerControlOutPrefixListName OBJECT-TYPE
			SYNTAX OCTET STRING (SIZE (0..512))
			MAX-ACCESS read-write
			STATUS current
			DESCRIPTION
				" "
			::= { sleBGPAFPeerControl 32 }


		-- 1.3.6.1.4.1.6296.101.53.5.4.1.2.33
		sleBGPAFPeerControlSendCommunity OBJECT-TYPE
			SYNTAX INTEGER
				{
				disable(0),
				standard(1),
				extended(2),
				both(3)
				}
			MAX-ACCESS read-write
			STATUS current
			DESCRIPTION
				" "
			::= { sleBGPAFPeerControl 33 }


		-- 1.3.6.1.4.1.6296.101.53.5.4.1.2.34
		sleBGPAFPeerControlNexthopSelf OBJECT-TYPE
			SYNTAX INTEGER
				{
				disable(0),
				enable(1)
				}
			MAX-ACCESS read-write
			STATUS current
			DESCRIPTION
				" "
			::= { sleBGPAFPeerControl 34 }


		-- 1.3.6.1.4.1.6296.101.53.5.4.1.2.35
		sleBGPAFPeerControlSoftReconfig OBJECT-TYPE
			SYNTAX INTEGER
				{
				disable(0),
				enable(1)
				}
			MAX-ACCESS read-write
			STATUS current
			DESCRIPTION
				" "
			::= { sleBGPAFPeerControl 35 }


		-- 1.3.6.1.4.1.6296.101.53.5.4.1.2.36
		sleBGPAFPeerControlUnsuppressMapName OBJECT-TYPE
			SYNTAX OCTET STRING (SIZE (0..512))
			MAX-ACCESS read-write
			STATUS current
			DESCRIPTION
				" "
			::= { sleBGPAFPeerControl 36 }


		-- 1.3.6.1.4.1.6296.101.53.5.4.1.3
		sleBGPAFPeerNotification OBJECT IDENTIFIER ::= { sleBGPAFPeer 3 }


		-- 1.3.6.1.4.1.6296.101.53.5.4.1.3.1
		sleBGPAFPeerActviateChanged NOTIFICATION-TYPE
			OBJECTS { sleBGPAFPeerControlRequest, sleBGPAFPeerControlTimeStamp, sleBGPAFPeerControlReqResult, sleBGPAFPeerMode, sleBGPAFPeerType,
				sleBGPAFPeerName, sleBGPAFPeerActviate }
			STATUS current
			DESCRIPTION
				"Description."
			::= { sleBGPAFPeerNotification 1 }


		-- 1.3.6.1.4.1.6296.101.53.5.4.1.3.2
		sleBGPAFPeerAllowAsInChanged NOTIFICATION-TYPE
			OBJECTS { sleBGPAFPeerControlRequest, sleBGPAFPeerControlTimeStamp, sleBGPAFPeerControlReqResult, sleBGPAFPeerMode, sleBGPAFPeerType,
				sleBGPAFPeerName, sleBGPAFPeerAllowAsIn, sleBGPAFPeerAllowAsInNum }
			STATUS current
			DESCRIPTION
				"Description."
			::= { sleBGPAFPeerNotification 2 }


		-- 1.3.6.1.4.1.6296.101.53.5.4.1.3.3
		sleBGPAFPeerAttrUnchangedProfileChanged NOTIFICATION-TYPE
			OBJECTS { sleBGPAFPeerControlRequest, sleBGPAFPeerControlTimeStamp, sleBGPAFPeerControlReqResult, sleBGPAFPeerMode, sleBGPAFPeerType,
				sleBGPAFPeerName, sleBGPAFPeerAttrUnchangedAsPath, sleBGPAFPeerAttrUnchangedMed, sleBGPAFPeerAttrUnchangedNexthop }
			STATUS current
			DESCRIPTION
				"Description."
			::= { sleBGPAFPeerNotification 3 }


		-- 1.3.6.1.4.1.6296.101.53.5.4.1.3.4
		sleBGPAFPeerCapGracefulRestartChanged NOTIFICATION-TYPE
			OBJECTS { sleBGPAFPeerControlRequest, sleBGPAFPeerControlTimeStamp, sleBGPAFPeerControlReqResult, sleBGPAFPeerMode, sleBGPAFPeerType,
				sleBGPAFPeerName, sleBGPAFPeerCapGracefulRestart }
			STATUS current
			DESCRIPTION
				"Description."
			::= { sleBGPAFPeerNotification 4 }


		-- 1.3.6.1.4.1.6296.101.53.5.4.1.3.5
		sleBGPAFPeerCapOrfModeChanged NOTIFICATION-TYPE
			OBJECTS { sleBGPAFPeerControlRequest, sleBGPAFPeerControlTimeStamp, sleBGPAFPeerControlReqResult, sleBGPAFPeerMode, sleBGPAFPeerName,
				sleBGPAFPeerCapOrfMode }
			STATUS current
			DESCRIPTION
				"Description."
			::= { sleBGPAFPeerNotification 5 }


		-- 1.3.6.1.4.1.6296.101.53.5.4.1.3.6
		sleBGPAFPeerDefOriginateChanged NOTIFICATION-TYPE
			OBJECTS { sleBGPAFPeerControlRequest, sleBGPAFPeerControlTimeStamp, sleBGPAFPeerControlReqResult, sleBGPAFPeerMode, sleBGPAFPeerType,
				sleBGPAFPeerName, sleBGPAFPeerDefOriginate, sleBGPAFPeerDefOriginateRoutemap }
			STATUS current
			DESCRIPTION
				"Description."
			::= { sleBGPAFPeerNotification 6 }


		-- 1.3.6.1.4.1.6296.101.53.5.4.1.3.7
		sleBGPAFPeerFLInAccNameChanged NOTIFICATION-TYPE
			OBJECTS { sleBGPAFPeerControlRequest, sleBGPAFPeerControlTimeStamp, sleBGPAFPeerControlReqResult, sleBGPAFPeerMode, sleBGPAFPeerType,
				sleBGPAFPeerName, sleBGPAFPeerFLInAccName }
			STATUS current
			DESCRIPTION
				"Description."
			::= { sleBGPAFPeerNotification 7 }


		-- 1.3.6.1.4.1.6296.101.53.5.4.1.3.8
		sleBGPAFPeerFLOutAccNameChanged NOTIFICATION-TYPE
			OBJECTS { sleBGPAFPeerControlRequest, sleBGPAFPeerControlTimeStamp, sleBGPAFPeerControlReqResult, sleBGPAFPeerMode, sleBGPAFPeerType,
				sleBGPAFPeerName, sleBGPAFPeerFLOutAccName }
			STATUS current
			DESCRIPTION
				"Description."
			::= { sleBGPAFPeerNotification 8 }


		-- 1.3.6.1.4.1.6296.101.53.5.4.1.3.9
		sleBGPAFPeerMaxPrefixProfileChanged NOTIFICATION-TYPE
			OBJECTS { sleBGPAFPeerControlRequest, sleBGPAFPeerControlTimeStamp, sleBGPAFPeerControlReqResult, sleBGPAFPeerMode, sleBGPAFPeerType,
				sleBGPAFPeerName, sleBGPAFPeerMaxPrefixNum, sleBGPAFPeerMaxPrefixThreshold, sleBGPAFPeerMaxPrefixWarnOnly }
			STATUS current
			DESCRIPTION
				"Description."
			::= { sleBGPAFPeerNotification 9 }


		-- 1.3.6.1.4.1.6296.101.53.5.4.1.3.10
		sleBGPAFPeerRemotePrivateAsChanged NOTIFICATION-TYPE
			OBJECTS { sleBGPAFPeerControlRequest, sleBGPAFPeerControlTimeStamp, sleBGPAFPeerControlReqResult, sleBGPAFPeerMode, sleBGPAFPeerType,
				sleBGPAFPeerName, sleBGPAFPeerRemotePrivateAs }
			STATUS current
			DESCRIPTION
				"Description."
			::= { sleBGPAFPeerNotification 10 }


		-- 1.3.6.1.4.1.6296.101.53.5.4.1.3.11
		sleBGPAFPeerInRoutemapChanged NOTIFICATION-TYPE
			OBJECTS { sleBGPAFPeerControlRequest, sleBGPAFPeerControlTimeStamp, sleBGPAFPeerControlReqResult, sleBGPAFPeerMode, sleBGPAFPeerType,
				sleBGPAFPeerName, sleBGPAFPeerInRoutemap }
			STATUS current
			DESCRIPTION
				"Description."
			::= { sleBGPAFPeerNotification 11 }


		-- 1.3.6.1.4.1.6296.101.53.5.4.1.3.12
		sleBGPAFPeerOutRoutemapChanged NOTIFICATION-TYPE
			OBJECTS { sleBGPAFPeerControlRequest, sleBGPAFPeerControlTimeStamp, sleBGPAFPeerControlReqResult, sleBGPAFPeerMode, sleBGPAFPeerType,
				sleBGPAFPeerName, sleBGPAFPeerOutRoutemap }
			STATUS current
			DESCRIPTION
				"Description."
			::= { sleBGPAFPeerNotification 12 }


		-- 1.3.6.1.4.1.6296.101.53.5.4.1.3.13
		sleBGPAFPeerRouteReflectClientChanged NOTIFICATION-TYPE
			OBJECTS { sleBGPAFPeerControlRequest, sleBGPAFPeerControlTimeStamp, sleBGPAFPeerControlReqResult, sleBGPAFPeerMode, sleBGPAFPeerType,
				sleBGPAFPeerName, sleBGPAFPeerRouteReflectClient }
			STATUS current
			DESCRIPTION
				"Description."
			::= { sleBGPAFPeerNotification 13 }


		-- 1.3.6.1.4.1.6296.101.53.5.4.1.3.14
		sleBGPAFPeerRouteServerClientChanged NOTIFICATION-TYPE
			OBJECTS { sleBGPAFPeerControlRequest, sleBGPAFPeerControlTimeStamp, sleBGPAFPeerControlReqResult, sleBGPAFPeerMode, sleBGPAFPeerType,
				sleBGPAFPeerName, sleBGPAFPeerRouteServerClient }
			STATUS current
			DESCRIPTION
				"Description."
			::= { sleBGPAFPeerNotification 14 }


		-- 1.3.6.1.4.1.6296.101.53.5.4.1.3.15
		sleBGPAFPeerInDistListNameChanged NOTIFICATION-TYPE
			OBJECTS { sleBGPAFPeerControlRequest, sleBGPAFPeerControlTimeStamp, sleBGPAFPeerControlReqResult, sleBGPAFPeerMode, sleBGPAFPeerType,
				sleBGPAFPeerName, sleBGPAFPeerInDistListName }
			STATUS current
			DESCRIPTION
				"Description."
			::= { sleBGPAFPeerNotification 15 }


		-- 1.3.6.1.4.1.6296.101.53.5.4.1.3.16
		sleBGPAFPeerOutDistListNameChanged NOTIFICATION-TYPE
			OBJECTS { sleBGPAFPeerControlRequest, sleBGPAFPeerControlTimeStamp, sleBGPAFPeerControlReqResult, sleBGPAFPeerMode, sleBGPAFPeerType,
				sleBGPAFPeerName, sleBGPAFPeerOutDistListName }
			STATUS current
			DESCRIPTION
				"Description."
			::= { sleBGPAFPeerNotification 16 }


		-- 1.3.6.1.4.1.6296.101.53.5.4.1.3.17
		sleBGPAFPeerInPrefixListNameChanged NOTIFICATION-TYPE
			OBJECTS { sleBGPAFPeerControlRequest, sleBGPAFPeerControlTimeStamp, sleBGPAFPeerControlReqResult, sleBGPAFPeerMode, sleBGPAFPeerType,
				sleBGPAFPeerName, sleBGPAFPeerInPrefixListName }
			STATUS current
			DESCRIPTION
				"Description."
			::= { sleBGPAFPeerNotification 17 }


		-- 1.3.6.1.4.1.6296.101.53.5.4.1.3.18
		sleBGPAFPeerOutPrefixListNameChanged NOTIFICATION-TYPE
			OBJECTS { sleBGPAFPeerControlRequest, sleBGPAFPeerControlTimeStamp, sleBGPAFPeerControlReqResult, sleBGPAFPeerMode, sleBGPAFPeerType,
				sleBGPAFPeerName, sleBGPAFPeerOutPrefixListName }
			STATUS current
			DESCRIPTION
				"Description."
			::= { sleBGPAFPeerNotification 18 }


		-- 1.3.6.1.4.1.6296.101.53.5.4.1.3.19
		sleBGPAFPeerSendCommunityChanged NOTIFICATION-TYPE
			OBJECTS { sleBGPAFPeerControlRequest, sleBGPAFPeerControlTimeStamp, sleBGPAFPeerControlReqResult, sleBGPAFPeerMode, sleBGPAFPeerType,
				sleBGPAFPeerName, sleBGPAFPeerSendCommunity }
			STATUS current
			DESCRIPTION
				"Except vpn4."
			::= { sleBGPAFPeerNotification 19 }


		-- 1.3.6.1.4.1.6296.101.53.5.4.1.3.20
		sleBGPAFPeerNexthopSelfChanged NOTIFICATION-TYPE
			OBJECTS { sleBGPAFPeerControlRequest, sleBGPAFPeerControlTimeStamp, sleBGPAFPeerControlReqResult, sleBGPAFPeerMode, sleBGPAFPeerType,
				sleBGPAFPeerName, sleBGPAFPeerNexthopSelf }
			STATUS current
			DESCRIPTION
				"Except vpn4."
			::= { sleBGPAFPeerNotification 20 }


		-- 1.3.6.1.4.1.6296.101.53.5.4.1.3.21
		sleBGPAFPeerSoftReconfigChanged NOTIFICATION-TYPE
			OBJECTS { sleBGPAFPeerControlRequest, sleBGPAFPeerControlTimeStamp, sleBGPAFPeerControlReqResult, sleBGPAFPeerMode, sleBGPAFPeerType,
				sleBGPAFPeerName, sleBGPAFPeerSoftReconfig }
			STATUS current
			DESCRIPTION
				"Except vpn4."
			::= { sleBGPAFPeerNotification 21 }


		-- 1.3.6.1.4.1.6296.101.53.5.4.1.3.22
		sleBGPAFPeerUnsuppressMapNameChanged NOTIFICATION-TYPE
			OBJECTS { sleBGPAFPeerControlRequest, sleBGPAFPeerControlTimeStamp, sleBGPAFPeerControlReqResult, sleBGPAFPeerMode, sleBGPAFPeerType,
				sleBGPAFPeerName, sleBGPAFPeerUnsuppressMapName }
			STATUS current
			DESCRIPTION
				"Except vpn4."
			::= { sleBGPAFPeerNotification 22 }


		-- 1.3.6.1.4.1.6296.101.53.5.4.2
		sleBGPAFPeerGroup OBJECT IDENTIFIER ::= { sleBGPAFPeerInfo 2 }


		-- 1.3.6.1.4.1.6296.101.53.5.4.2.1
		sleBGPAFPeerGroupTable OBJECT-TYPE
			SYNTAX SEQUENCE OF SleBGPAFPeerGroupEntry
			MAX-ACCESS not-accessible
			STATUS current
			DESCRIPTION
				"Description."
			::= { sleBGPAFPeerGroup 1 }


		-- 1.3.6.1.4.1.6296.101.53.5.4.2.1.1
		sleBGPAFPeerGroupEntry OBJECT-TYPE
			SYNTAX SleBGPAFPeerGroupEntry
			MAX-ACCESS not-accessible
			STATUS current
			DESCRIPTION
				"Description."
			INDEX { sleBGPAFPeerMode, sleBGPAFPeerType, sleBGPAFPeerName }
			::= { sleBGPAFPeerGroupTable 1 }


		SleBGPAFPeerGroupEntry ::=
			SEQUENCE {
				sleBGPAFPeerGroupMode
					INTEGER,
				sleBGPAFPeerGroupType
					INTEGER,
				sleBGPAFPeerGroupName
					OCTET STRING,
				sleBGPAFPeerGroupActviate
					INTEGER,
				sleBGPAFPeerGroupAllowAsIn
					INTEGER,
				sleBGPAFPeerGroupAllowAsInNum
					INTEGER,
				sleBGPAFPeerGroupAttrUnchangedAsPath
					INTEGER,
				sleBGPAFPeerGroupAttrUnchangedMed
					INTEGER,
				sleBGPAFPeerGroupAttrUnchangedNexthop
					INTEGER,
				sleBGPAFPeerGroupCapGracefulRestart
					INTEGER,
				sleBGPAFPeerGroupCapOrfMode
					INTEGER,
				sleBGPAFPeerGroupDefOriginate
					INTEGER,
				sleBGPAFPeerGroupDefOriginateRoutemap
					OCTET STRING,
				sleBGPAFPeerGroupFLInAccName
					OCTET STRING,
				sleBGPAFPeerGroupFLOutAccName
					OCTET STRING,
				sleBGPAFPeerGroupMaxPrefixNum
					Gauge32,
				sleBGPAFPeerGroupMaxPrefixThreshold
					INTEGER,
				sleBGPAFPeerGroupMaxPrefixWarnOnly
					INTEGER,
				sleBGPAFPeerGroupRemotePrivateAs
					INTEGER,
				sleBGPAFPeerGroupInRoutemap
					OCTET STRING,
				sleBGPAFPeerGroupOutRoutemap
					OCTET STRING,
				sleBGPAFPeerGroupRouteReflectClient
					INTEGER,
				sleBGPAFPeerGroupRouteServerClient
					INTEGER,
				sleBGPAFPeerGroupInDistListName
					OCTET STRING,
				sleBGPAFPeerGroupOutDistListName
					OCTET STRING,
				sleBGPAFPeerGroupInPrefixListName
					OCTET STRING,
				sleBGPAFPeerGroupOutPrefixListName
					OCTET STRING,
				sleBGPAFPeerGroupSendCommunity
					INTEGER,
				sleBGPAFPeerGroupNexthopSelf
					INTEGER,
				sleBGPAFPeerGroupSoftReconfig
					INTEGER,
				sleBGPAFPeerGroupUnsuppressMapName
					OCTET STRING
			 }

		-- 1.3.6.1.4.1.6296.101.53.5.4.2.1.1.1
		sleBGPAFPeerGroupMode OBJECT-TYPE
			SYNTAX INTEGER
				{
				ipv4(1),
				ipv6(2),
				vpn4(3)
				}
			MAX-ACCESS read-only
			STATUS current
			DESCRIPTION
				"1: ipv4
				2: ipv6
				3: vpn4"
			::= { sleBGPAFPeerGroupEntry 1 }


		-- 1.3.6.1.4.1.6296.101.53.5.4.2.1.1.2
		sleBGPAFPeerGroupType OBJECT-TYPE
			SYNTAX INTEGER
				{
				unicast(1),
				multicast(2),
				vrf(3)
				}
			MAX-ACCESS read-only
			STATUS current
			DESCRIPTION
				"1: unicast
				2: multicast (only ipv4)
				3: vrf (only ipv4)
				"
			::= { sleBGPAFPeerGroupEntry 2 }


		-- 1.3.6.1.4.1.6296.101.53.5.4.2.1.1.3
		sleBGPAFPeerGroupName OBJECT-TYPE
			SYNTAX OCTET STRING
			MAX-ACCESS read-only
			STATUS current
			DESCRIPTION
				"
				"
			::= { sleBGPAFPeerGroupEntry 3 }


		-- 1.3.6.1.4.1.6296.101.53.5.4.2.1.1.4
		sleBGPAFPeerGroupActviate OBJECT-TYPE
			SYNTAX INTEGER
				{
				disable(0),
				enable(1)
				}
			MAX-ACCESS read-only
			STATUS current
			DESCRIPTION
				" "
			::= { sleBGPAFPeerGroupEntry 4 }


		-- 1.3.6.1.4.1.6296.101.53.5.4.2.1.1.5
		sleBGPAFPeerGroupAllowAsIn OBJECT-TYPE
			SYNTAX INTEGER
				{
				disable(0),
				enable(1)
				}
			MAX-ACCESS read-only
			STATUS current
			DESCRIPTION
				" "
			::= { sleBGPAFPeerGroupEntry 5 }


		-- 1.3.6.1.4.1.6296.101.53.5.4.2.1.1.6
		sleBGPAFPeerGroupAllowAsInNum OBJECT-TYPE
			SYNTAX INTEGER (0..10)
			MAX-ACCESS read-only
			STATUS current
			DESCRIPTION
				" "
			::= { sleBGPAFPeerGroupEntry 6 }


		-- 1.3.6.1.4.1.6296.101.53.5.4.2.1.1.7
		sleBGPAFPeerGroupAttrUnchangedAsPath OBJECT-TYPE
			SYNTAX INTEGER
				{
				disable(0),
				enable(1)
				}
			MAX-ACCESS read-only
			STATUS current
			DESCRIPTION
				" "
			::= { sleBGPAFPeerGroupEntry 7 }


		-- 1.3.6.1.4.1.6296.101.53.5.4.2.1.1.8
		sleBGPAFPeerGroupAttrUnchangedMed OBJECT-TYPE
			SYNTAX INTEGER
				{
				disable(0),
				enable(1)
				}
			MAX-ACCESS read-only
			STATUS current
			DESCRIPTION
				" "
			::= { sleBGPAFPeerGroupEntry 8 }


		-- 1.3.6.1.4.1.6296.101.53.5.4.2.1.1.9
		sleBGPAFPeerGroupAttrUnchangedNexthop OBJECT-TYPE
			SYNTAX INTEGER
				{
				disable(0),
				enable(1)
				}
			MAX-ACCESS read-only
			STATUS current
			DESCRIPTION
				" "
			::= { sleBGPAFPeerGroupEntry 9 }


		-- 1.3.6.1.4.1.6296.101.53.5.4.2.1.1.10
		sleBGPAFPeerGroupCapGracefulRestart OBJECT-TYPE
			SYNTAX INTEGER
				{
				disable(0),
				enable(1)
				}
			MAX-ACCESS read-only
			STATUS current
			DESCRIPTION
				" "
			::= { sleBGPAFPeerGroupEntry 10 }


		-- 1.3.6.1.4.1.6296.101.53.5.4.2.1.1.11
		sleBGPAFPeerGroupCapOrfMode OBJECT-TYPE
			SYNTAX INTEGER
				{
				disable(0),
				send(1),
				receive(2),
				both(3)
				}
			MAX-ACCESS read-only
			STATUS current
			DESCRIPTION
				" "
			::= { sleBGPAFPeerGroupEntry 11 }


		-- 1.3.6.1.4.1.6296.101.53.5.4.2.1.1.12
		sleBGPAFPeerGroupDefOriginate OBJECT-TYPE
			SYNTAX INTEGER
				{
				disable(0),
				enable(1)
				}
			MAX-ACCESS read-only
			STATUS current
			DESCRIPTION
				" "
			::= { sleBGPAFPeerGroupEntry 12 }


		-- 1.3.6.1.4.1.6296.101.53.5.4.2.1.1.13
		sleBGPAFPeerGroupDefOriginateRoutemap OBJECT-TYPE
			SYNTAX OCTET STRING (SIZE (0..512))
			MAX-ACCESS read-only
			STATUS current
			DESCRIPTION
				" "
			::= { sleBGPAFPeerGroupEntry 13 }


		-- 1.3.6.1.4.1.6296.101.53.5.4.2.1.1.14
		sleBGPAFPeerGroupFLInAccName OBJECT-TYPE
			SYNTAX OCTET STRING (SIZE (0..512))
			MAX-ACCESS read-only
			STATUS current
			DESCRIPTION
				" "
			::= { sleBGPAFPeerGroupEntry 14 }


		-- 1.3.6.1.4.1.6296.101.53.5.4.2.1.1.15
		sleBGPAFPeerGroupFLOutAccName OBJECT-TYPE
			SYNTAX OCTET STRING (SIZE (0..512))
			MAX-ACCESS read-only
			STATUS current
			DESCRIPTION
				" "
			::= { sleBGPAFPeerGroupEntry 15 }


		-- 1.3.6.1.4.1.6296.101.53.5.4.2.1.1.16
		sleBGPAFPeerGroupMaxPrefixNum OBJECT-TYPE
			SYNTAX Gauge32 (1..4294967295)
			MAX-ACCESS read-only
			STATUS current
			DESCRIPTION
				" "
			::= { sleBGPAFPeerGroupEntry 16 }


		-- 1.3.6.1.4.1.6296.101.53.5.4.2.1.1.17
		sleBGPAFPeerGroupMaxPrefixThreshold OBJECT-TYPE
			SYNTAX INTEGER (0..100)
			MAX-ACCESS read-only
			STATUS current
			DESCRIPTION
				" "
			::= { sleBGPAFPeerGroupEntry 17 }


		-- 1.3.6.1.4.1.6296.101.53.5.4.2.1.1.18
		sleBGPAFPeerGroupMaxPrefixWarnOnly OBJECT-TYPE
			SYNTAX INTEGER
				{
				disable(0),
				enable(1)
				}
			MAX-ACCESS read-only
			STATUS current
			DESCRIPTION
				" "
			::= { sleBGPAFPeerGroupEntry 18 }


		-- 1.3.6.1.4.1.6296.101.53.5.4.2.1.1.19
		sleBGPAFPeerGroupRemotePrivateAs OBJECT-TYPE
			SYNTAX INTEGER
				{
				disable(0),
				enable(1)
				}
			MAX-ACCESS read-only
			STATUS current
			DESCRIPTION
				" "
			::= { sleBGPAFPeerGroupEntry 19 }


		-- 1.3.6.1.4.1.6296.101.53.5.4.2.1.1.20
		sleBGPAFPeerGroupInRoutemap OBJECT-TYPE
			SYNTAX OCTET STRING (SIZE (0..512))
			MAX-ACCESS read-only
			STATUS current
			DESCRIPTION
				" "
			::= { sleBGPAFPeerGroupEntry 20 }


		-- 1.3.6.1.4.1.6296.101.53.5.4.2.1.1.21
		sleBGPAFPeerGroupOutRoutemap OBJECT-TYPE
			SYNTAX OCTET STRING (SIZE (0..512))
			MAX-ACCESS read-only
			STATUS current
			DESCRIPTION
				" "
			::= { sleBGPAFPeerGroupEntry 21 }


		-- 1.3.6.1.4.1.6296.101.53.5.4.2.1.1.22
		sleBGPAFPeerGroupRouteReflectClient OBJECT-TYPE
			SYNTAX INTEGER
				{
				disable(0),
				enable(1)
				}
			MAX-ACCESS read-only
			STATUS current
			DESCRIPTION
				" "
			::= { sleBGPAFPeerGroupEntry 22 }


		-- 1.3.6.1.4.1.6296.101.53.5.4.2.1.1.23
		sleBGPAFPeerGroupRouteServerClient OBJECT-TYPE
			SYNTAX INTEGER
				{
				disable(0),
				enable(1)
				}
			MAX-ACCESS read-only
			STATUS current
			DESCRIPTION
				" "
			::= { sleBGPAFPeerGroupEntry 23 }


		-- 1.3.6.1.4.1.6296.101.53.5.4.2.1.1.24
		sleBGPAFPeerGroupInDistListName OBJECT-TYPE
			SYNTAX OCTET STRING (SIZE (0..512))
			MAX-ACCESS read-only
			STATUS current
			DESCRIPTION
				" "
			::= { sleBGPAFPeerGroupEntry 24 }


		-- 1.3.6.1.4.1.6296.101.53.5.4.2.1.1.25
		sleBGPAFPeerGroupOutDistListName OBJECT-TYPE
			SYNTAX OCTET STRING (SIZE (0..512))
			MAX-ACCESS read-only
			STATUS current
			DESCRIPTION
				" "
			::= { sleBGPAFPeerGroupEntry 25 }


		-- 1.3.6.1.4.1.6296.101.53.5.4.2.1.1.26
		sleBGPAFPeerGroupInPrefixListName OBJECT-TYPE
			SYNTAX OCTET STRING (SIZE (0..512))
			MAX-ACCESS read-only
			STATUS current
			DESCRIPTION
				" "
			::= { sleBGPAFPeerGroupEntry 26 }


		-- 1.3.6.1.4.1.6296.101.53.5.4.2.1.1.27
		sleBGPAFPeerGroupOutPrefixListName OBJECT-TYPE
			SYNTAX OCTET STRING (SIZE (0..512))
			MAX-ACCESS read-only
			STATUS current
			DESCRIPTION
				" "
			::= { sleBGPAFPeerGroupEntry 27 }


		-- 1.3.6.1.4.1.6296.101.53.5.4.2.1.1.28
		sleBGPAFPeerGroupSendCommunity OBJECT-TYPE
			SYNTAX INTEGER
				{
				disable(0),
				standard(1),
				extended(2),
				both(3)
				}
			MAX-ACCESS read-only
			STATUS current
			DESCRIPTION
				"Except vpn4."
			::= { sleBGPAFPeerGroupEntry 28 }


		-- 1.3.6.1.4.1.6296.101.53.5.4.2.1.1.29
		sleBGPAFPeerGroupNexthopSelf OBJECT-TYPE
			SYNTAX INTEGER
				{
				disable(0),
				enable(1)
				}
			MAX-ACCESS read-only
			STATUS current
			DESCRIPTION
				"Except vpn4."
			::= { sleBGPAFPeerGroupEntry 29 }


		-- 1.3.6.1.4.1.6296.101.53.5.4.2.1.1.30
		sleBGPAFPeerGroupSoftReconfig OBJECT-TYPE
			SYNTAX INTEGER
				{
				disable(0),
				enable(1)
				}
			MAX-ACCESS read-only
			STATUS current
			DESCRIPTION
				"Except vpn4."
			::= { sleBGPAFPeerGroupEntry 30 }


		-- 1.3.6.1.4.1.6296.101.53.5.4.2.1.1.31
		sleBGPAFPeerGroupUnsuppressMapName OBJECT-TYPE
			SYNTAX OCTET STRING (SIZE (0..512))
			MAX-ACCESS read-only
			STATUS current
			DESCRIPTION
				"Except vpn4."
			::= { sleBGPAFPeerGroupEntry 31 }


		-- 1.3.6.1.4.1.6296.101.53.5.4.2.2
		sleBGPAFPeerGroupControl OBJECT IDENTIFIER ::= { sleBGPAFPeerGroup 2 }


		-- 1.3.6.1.4.1.6296.101.53.5.4.2.2.1
		sleBGPAFPeerGroupControlRequest OBJECT-TYPE
			SYNTAX INTEGER
				{
				setBGPAFPeerGroupActivate(1),
				setBGPAFPeerGroupAllowAsInProfile(2),
				setBGPAFPeerGroupAttrUnchangedProfile(3),
				setBGPAFPeerGroupCapGracefulRestart(4),
				setBGPAFPeerGroupCapOrfMode(5),
				setBGPAFPeerGroupDefaultOriginate(6),
				setBGPAFPeerGroupFLInAccName(7),
				unsetBGPAFPeerGroupFLInAccName(8),
				setBGPAFPeerGroupFLOutAccName(9),
				unsetBGPAFPeerGroupFLOutAccName(10),
				setBGPAFPeerGroupMaxPrefixProfile(11),
				setBGPAFPeerGroupRemotePrivateAs(12),
				setBGPAFPeerGroupInRoutemap(13),
				unsetBGPAFPeerGroupInRoutemap(14),
				setBGPAFPeerGroupOutRoutemap(15),
				unsetBGPAFPeerGroupOutRoutemap(16),
				setBGPAFPeerGroupRouteReflectClient(17),
				setBGPAFPeerGroupRouteServerClient(18),
				setBGPAFPeerGroupSendCommunity(19),
				setBGPAFPeerGroupNexthopSelf(20),
				setBGPAFPeerGroupSoftReconfig(21),
				setBGPAFPeerGroupUnsupressMapName(22),
				unsetBGPAFPeerGroupUnsupressMapName(23),
				setBGPAFPeerGroupInDistListName(24),
				unsetBGPAFPeerGroupInDistListName(25),
				setBGPAFPeerGroupOutDistListName(26),
				unsetBGPAFPeerGroupOutDistListName(27),
				setBGPAFPeerGroupInPrefixListName(28),
				unsetBGPAFPeerGroupInPrefixListName(29),
				setBGPAFPeerGroupOutPrefixListName(30),
				unsetBGPAFPeerGroupOutPrefixListName(31)
				}
			MAX-ACCESS read-write
			STATUS current
			DESCRIPTION
				"Description."
			::= { sleBGPAFPeerGroupControl 1 }


		-- 1.3.6.1.4.1.6296.101.53.5.4.2.2.2
		sleBGPAFPeerGroupControlStatus OBJECT-TYPE
			SYNTAX SleControlStatusType
			MAX-ACCESS read-only
			STATUS current
			DESCRIPTION
				"Description."
			::= { sleBGPAFPeerGroupControl 2 }


		-- 1.3.6.1.4.1.6296.101.53.5.4.2.2.3
		sleBGPAFPeerGroupControlTimer OBJECT-TYPE
			SYNTAX Gauge32
			MAX-ACCESS read-write
			STATUS current
			DESCRIPTION
				"Description."
			::= { sleBGPAFPeerGroupControl 3 }


		-- 1.3.6.1.4.1.6296.101.53.5.4.2.2.4
		sleBGPAFPeerGroupControlTimeStamp OBJECT-TYPE
			SYNTAX TimeTicks
			MAX-ACCESS read-only
			STATUS current
			DESCRIPTION
				"Description."
			::= { sleBGPAFPeerGroupControl 4 }


		-- 1.3.6.1.4.1.6296.101.53.5.4.2.2.5
		sleBGPAFPeerGroupControlReqResult OBJECT-TYPE
			SYNTAX SleControlRequestResultType
			MAX-ACCESS read-only
			STATUS current
			DESCRIPTION
				"Description."
			::= { sleBGPAFPeerGroupControl 5 }


		-- 1.3.6.1.4.1.6296.101.53.5.4.2.2.6
		sleBGPAFPeerGroupControlMode OBJECT-TYPE
			SYNTAX INTEGER
				{
				ipv4(1),
				ipv6(2),
				vpn4(3)
				}
			MAX-ACCESS read-write
			STATUS current
			DESCRIPTION
				"1: ipv4
				2: ipv6
				3: vpn4"
			::= { sleBGPAFPeerGroupControl 6 }


		-- 1.3.6.1.4.1.6296.101.53.5.4.2.2.7
		sleBGPAFPeerGroupControlType OBJECT-TYPE
			SYNTAX INTEGER
				{
				unicast(1),
				multicast(2),
				vrf(3)
				}
			MAX-ACCESS read-write
			STATUS current
			DESCRIPTION
				"1: unicast
				2: multicast (only ipv4)
				3: vrf (only ipv4)
				"
			::= { sleBGPAFPeerGroupControl 7 }


		-- 1.3.6.1.4.1.6296.101.53.5.4.2.2.8
		sleBGPAFPeerGroupControlName OBJECT-TYPE
			SYNTAX OCTET STRING
			MAX-ACCESS read-write
			STATUS current
			DESCRIPTION
				" "
			::= { sleBGPAFPeerGroupControl 8 }


		-- 1.3.6.1.4.1.6296.101.53.5.4.2.2.9
		sleBGPAFPeerGroupControlActviate OBJECT-TYPE
			SYNTAX INTEGER
				{
				disable(0),
				enable(1)
				}
			MAX-ACCESS read-write
			STATUS current
			DESCRIPTION
				" "
			::= { sleBGPAFPeerGroupControl 9 }


		-- 1.3.6.1.4.1.6296.101.53.5.4.2.2.10
		sleBGPAFPeerGroupControlAllowAsIn OBJECT-TYPE
			SYNTAX INTEGER
				{
				disable(0),
				enable(1)
				}
			MAX-ACCESS read-write
			STATUS current
			DESCRIPTION
				" "
			::= { sleBGPAFPeerGroupControl 10 }


		-- 1.3.6.1.4.1.6296.101.53.5.4.2.2.11
		sleBGPAFPeerGroupControlAllowAsInNum OBJECT-TYPE
			SYNTAX INTEGER (0..10)
			MAX-ACCESS read-write
			STATUS current
			DESCRIPTION
				" "
			::= { sleBGPAFPeerGroupControl 11 }


		-- 1.3.6.1.4.1.6296.101.53.5.4.2.2.12
		sleBGPAFPeerGroupControlAttrUnchangedAsPath OBJECT-TYPE
			SYNTAX INTEGER
				{
				disable(0),
				enable(1)
				}
			MAX-ACCESS read-write
			STATUS current
			DESCRIPTION
				" "
			::= { sleBGPAFPeerGroupControl 12 }


		-- 1.3.6.1.4.1.6296.101.53.5.4.2.2.13
		sleBGPAFPeerGroupControlAttrUnchangedMed OBJECT-TYPE
			SYNTAX INTEGER
				{
				disable(0),
				enable(1)
				}
			MAX-ACCESS read-write
			STATUS current
			DESCRIPTION
				" "
			::= { sleBGPAFPeerGroupControl 13 }


		-- 1.3.6.1.4.1.6296.101.53.5.4.2.2.14
		sleBGPAFPeerGroupControlAttrUnchangedNexthop OBJECT-TYPE
			SYNTAX INTEGER
				{
				disable(0),
				enable(1)
				}
			MAX-ACCESS read-write
			STATUS current
			DESCRIPTION
				" "
			::= { sleBGPAFPeerGroupControl 14 }


		-- 1.3.6.1.4.1.6296.101.53.5.4.2.2.15
		sleBGPAFPeerGroupControlCapGracefulRestart OBJECT-TYPE
			SYNTAX INTEGER
				{
				disable(0),
				enable(1)
				}
			MAX-ACCESS read-write
			STATUS current
			DESCRIPTION
				" "
			::= { sleBGPAFPeerGroupControl 15 }


		-- 1.3.6.1.4.1.6296.101.53.5.4.2.2.16
		sleBGPAFPeerGroupControlCapOrfMode OBJECT-TYPE
			SYNTAX INTEGER
				{
				disable(0),
				send(1),
				receive(2),
				both(3)
				}
			MAX-ACCESS read-write
			STATUS current
			DESCRIPTION
				" "
			::= { sleBGPAFPeerGroupControl 16 }


		-- 1.3.6.1.4.1.6296.101.53.5.4.2.2.17
		sleBGPAFPeerGroupControlDefOriginate OBJECT-TYPE
			SYNTAX INTEGER
				{
				disable(0),
				enable(1)
				}
			MAX-ACCESS read-write
			STATUS current
			DESCRIPTION
				" "
			::= { sleBGPAFPeerGroupControl 17 }


		-- 1.3.6.1.4.1.6296.101.53.5.4.2.2.18
		sleBGPAFPeerGroupControlDefOriginateRoutemap OBJECT-TYPE
			SYNTAX OCTET STRING (SIZE (0..512))
			MAX-ACCESS read-write
			STATUS current
			DESCRIPTION
				" "
			::= { sleBGPAFPeerGroupControl 18 }


		-- 1.3.6.1.4.1.6296.101.53.5.4.2.2.19
		sleBGPAFPeerGroupControlFLInAccName OBJECT-TYPE
			SYNTAX OCTET STRING (SIZE (0..512))
			MAX-ACCESS read-write
			STATUS current
			DESCRIPTION
				" "
			::= { sleBGPAFPeerGroupControl 19 }


		-- 1.3.6.1.4.1.6296.101.53.5.4.2.2.20
		sleBGPAFPeerGroupControlFLOutAccName OBJECT-TYPE
			SYNTAX OCTET STRING (SIZE (0..512))
			MAX-ACCESS read-write
			STATUS current
			DESCRIPTION
				" "
			::= { sleBGPAFPeerGroupControl 20 }


		-- 1.3.6.1.4.1.6296.101.53.5.4.2.2.21
		sleBGPAFPeerGroupControlMaxPrefixNum OBJECT-TYPE
			SYNTAX Gauge32 (1..4294967295)
			MAX-ACCESS read-write
			STATUS current
			DESCRIPTION
				" "
			::= { sleBGPAFPeerGroupControl 21 }


		-- 1.3.6.1.4.1.6296.101.53.5.4.2.2.22
		sleBGPAFPeerGroupControlMaxPrefixThreshold OBJECT-TYPE
			SYNTAX INTEGER (0..100)
			MAX-ACCESS read-write
			STATUS current
			DESCRIPTION
				" "
			::= { sleBGPAFPeerGroupControl 22 }


		-- 1.3.6.1.4.1.6296.101.53.5.4.2.2.23
		sleBGPAFPeerGroupControlMaxPrefixWarnOnly OBJECT-TYPE
			SYNTAX INTEGER
				{
				disable(0),
				enable(1)
				}
			MAX-ACCESS read-write
			STATUS current
			DESCRIPTION
				" "
			::= { sleBGPAFPeerGroupControl 23 }


		-- 1.3.6.1.4.1.6296.101.53.5.4.2.2.24
		sleBGPAFPeerGroupControlRemotePrivateAs OBJECT-TYPE
			SYNTAX INTEGER
				{
				disable(0),
				enable(1)
				}
			MAX-ACCESS read-write
			STATUS current
			DESCRIPTION
				" "
			::= { sleBGPAFPeerGroupControl 24 }


		-- 1.3.6.1.4.1.6296.101.53.5.4.2.2.25
		sleBGPAFPeerGroupControlInRoutemap OBJECT-TYPE
			SYNTAX OCTET STRING (SIZE (0..512))
			MAX-ACCESS read-write
			STATUS current
			DESCRIPTION
				" "
			::= { sleBGPAFPeerGroupControl 25 }


		-- 1.3.6.1.4.1.6296.101.53.5.4.2.2.26
		sleBGPAFPeerGroupControlOutRoutemap OBJECT-TYPE
			SYNTAX OCTET STRING (SIZE (0..512))
			MAX-ACCESS read-write
			STATUS current
			DESCRIPTION
				" "
			::= { sleBGPAFPeerGroupControl 26 }


		-- 1.3.6.1.4.1.6296.101.53.5.4.2.2.27
		sleBGPAFPeerGroupControlRouteReflectClient OBJECT-TYPE
			SYNTAX INTEGER
				{
				disable(0),
				enable(1)
				}
			MAX-ACCESS read-write
			STATUS current
			DESCRIPTION
				" "
			::= { sleBGPAFPeerGroupControl 27 }


		-- 1.3.6.1.4.1.6296.101.53.5.4.2.2.28
		sleBGPAFPeerGroupControlRouteServerClient OBJECT-TYPE
			SYNTAX INTEGER
				{
				disable(0),
				enable(1)
				}
			MAX-ACCESS read-write
			STATUS current
			DESCRIPTION
				" "
			::= { sleBGPAFPeerGroupControl 28 }


		-- 1.3.6.1.4.1.6296.101.53.5.4.2.2.29
		sleBGPAFPeerGroupControlInDistListName OBJECT-TYPE
			SYNTAX OCTET STRING (SIZE (0..512))
			MAX-ACCESS read-write
			STATUS current
			DESCRIPTION
				" "
			::= { sleBGPAFPeerGroupControl 29 }


		-- 1.3.6.1.4.1.6296.101.53.5.4.2.2.30
		sleBGPAFPeerGroupControlOutDistListName OBJECT-TYPE
			SYNTAX OCTET STRING (SIZE (0..512))
			MAX-ACCESS read-write
			STATUS current
			DESCRIPTION
				" "
			::= { sleBGPAFPeerGroupControl 30 }


		-- 1.3.6.1.4.1.6296.101.53.5.4.2.2.31
		sleBGPAFPeerGroupControlInPrefixListName OBJECT-TYPE
			SYNTAX OCTET STRING (SIZE (0..512))
			MAX-ACCESS read-write
			STATUS current
			DESCRIPTION
				" "
			::= { sleBGPAFPeerGroupControl 31 }


		-- 1.3.6.1.4.1.6296.101.53.5.4.2.2.32
		sleBGPAFPeerGroupControlOutPrefixListName OBJECT-TYPE
			SYNTAX OCTET STRING (SIZE (0..512))
			MAX-ACCESS read-write
			STATUS current
			DESCRIPTION
				" "
			::= { sleBGPAFPeerGroupControl 32 }


		-- 1.3.6.1.4.1.6296.101.53.5.4.2.2.33
		sleBGPAFPeerGroupControlSendCommunity OBJECT-TYPE
			SYNTAX INTEGER
				{
				disable(0),
				standard(1),
				extended(2),
				both(3)
				}
			MAX-ACCESS read-write
			STATUS current
			DESCRIPTION
				" "
			::= { sleBGPAFPeerGroupControl 33 }


		-- 1.3.6.1.4.1.6296.101.53.5.4.2.2.34
		sleBGPAFPeerGroupControlNexthopSelf OBJECT-TYPE
			SYNTAX INTEGER
				{
				disable(0),
				enable(1)
				}
			MAX-ACCESS read-write
			STATUS current
			DESCRIPTION
				" "
			::= { sleBGPAFPeerGroupControl 34 }


		-- 1.3.6.1.4.1.6296.101.53.5.4.2.2.35
		sleBGPAFPeerGroupControlSoftReconfig OBJECT-TYPE
			SYNTAX INTEGER
				{
				disable(0),
				enable(1)
				}
			MAX-ACCESS read-write
			STATUS current
			DESCRIPTION
				" "
			::= { sleBGPAFPeerGroupControl 35 }


		-- 1.3.6.1.4.1.6296.101.53.5.4.2.2.36
		sleBGPAFPeerGroupControlUnsuppressMapName OBJECT-TYPE
			SYNTAX OCTET STRING (SIZE (0..512))
			MAX-ACCESS read-write
			STATUS current
			DESCRIPTION
				" "
			::= { sleBGPAFPeerGroupControl 36 }


		-- 1.3.6.1.4.1.6296.101.53.5.4.2.3
		sleBGPAFPeerGroupNotification OBJECT IDENTIFIER ::= { sleBGPAFPeerGroup 3 }


		-- 1.3.6.1.4.1.6296.101.53.5.4.2.3.1
		sleBGPAFPeerGroupActviateChanged NOTIFICATION-TYPE
			OBJECTS { sleBGPAFPeerControlRequest, sleBGPAFPeerControlTimeStamp, sleBGPAFPeerControlReqResult, sleBGPAFPeerMode, sleBGPAFPeerType,
				sleBGPAFPeerName, sleBGPAFPeerActviate }
			STATUS current
			DESCRIPTION
				"Description."
			::= { sleBGPAFPeerGroupNotification 1 }


		-- 1.3.6.1.4.1.6296.101.53.5.4.2.3.2
		sleBGPAFPeerGroupAllowAsInChanged NOTIFICATION-TYPE
			OBJECTS { sleBGPAFPeerControlRequest, sleBGPAFPeerControlTimeStamp, sleBGPAFPeerControlReqResult, sleBGPAFPeerMode, sleBGPAFPeerType,
				sleBGPAFPeerName, sleBGPAFPeerAllowAsIn, sleBGPAFPeerAllowAsInNum }
			STATUS current
			DESCRIPTION
				"Description."
			::= { sleBGPAFPeerGroupNotification 2 }


		-- 1.3.6.1.4.1.6296.101.53.5.4.2.3.3
		sleBGPAFPeerGroupAttrUnchangedProfileChanged NOTIFICATION-TYPE
			OBJECTS { sleBGPAFPeerControlRequest, sleBGPAFPeerControlTimeStamp, sleBGPAFPeerControlReqResult, sleBGPAFPeerMode, sleBGPAFPeerType,
				sleBGPAFPeerName, sleBGPAFPeerAttrUnchangedAsPath, sleBGPAFPeerAttrUnchangedMed, sleBGPAFPeerAttrUnchangedNexthop }
			STATUS current
			DESCRIPTION
				"Description."
			::= { sleBGPAFPeerGroupNotification 3 }


		-- 1.3.6.1.4.1.6296.101.53.5.4.2.3.4
		sleBGPAFPeerGroupCapGracefulRestartChanged NOTIFICATION-TYPE
			OBJECTS { sleBGPAFPeerControlRequest, sleBGPAFPeerControlTimeStamp, sleBGPAFPeerControlReqResult, sleBGPAFPeerMode, sleBGPAFPeerType,
				sleBGPAFPeerName, sleBGPAFPeerCapGracefulRestart }
			STATUS current
			DESCRIPTION
				"Description."
			::= { sleBGPAFPeerGroupNotification 4 }


		-- 1.3.6.1.4.1.6296.101.53.5.4.2.3.5
		sleBGPAFPeerGroupCapOrfModeChanged NOTIFICATION-TYPE
			OBJECTS { sleBGPAFPeerControlRequest, sleBGPAFPeerControlTimeStamp, sleBGPAFPeerControlReqResult, sleBGPAFPeerMode, sleBGPAFPeerType,
				sleBGPAFPeerName, sleBGPAFPeerCapOrfMode }
			STATUS current
			DESCRIPTION
				"Description."
			::= { sleBGPAFPeerGroupNotification 5 }


		-- 1.3.6.1.4.1.6296.101.53.5.4.2.3.6
		sleBGPAFPeerGroupDefOriginateChanged NOTIFICATION-TYPE
			OBJECTS { sleBGPAFPeerControlRequest, sleBGPAFPeerControlTimeStamp, sleBGPAFPeerControlReqResult, sleBGPAFPeerMode, sleBGPAFPeerType,
				sleBGPAFPeerName, sleBGPAFPeerGroupDefOriginate, sleBGPAFPeerGroupDefOriginateRoutemap }
			STATUS current
			DESCRIPTION
				"Description."
			::= { sleBGPAFPeerGroupNotification 6 }


		-- 1.3.6.1.4.1.6296.101.53.5.4.2.3.7
		sleBGPAFPeerGroupFLInAccNameChanged NOTIFICATION-TYPE
			OBJECTS { sleBGPAFPeerControlRequest, sleBGPAFPeerControlTimeStamp, sleBGPAFPeerControlReqResult, sleBGPAFPeerMode, sleBGPAFPeerType,
				sleBGPAFPeerName, sleBGPAFPeerFLInAccName }
			STATUS current
			DESCRIPTION
				"Description."
			::= { sleBGPAFPeerGroupNotification 7 }


		-- 1.3.6.1.4.1.6296.101.53.5.4.2.3.8
		sleBGPAFPeerGroupFLOutAccNameChanged NOTIFICATION-TYPE
			OBJECTS { sleBGPAFPeerControlRequest, sleBGPAFPeerControlTimeStamp, sleBGPAFPeerControlReqResult, sleBGPAFPeerMode, sleBGPAFPeerType,
				sleBGPAFPeerName, sleBGPAFPeerFLOutAccName }
			STATUS current
			DESCRIPTION
				"Description."
			::= { sleBGPAFPeerGroupNotification 8 }


		-- 1.3.6.1.4.1.6296.101.53.5.4.2.3.9
		sleBGPAFPeerGroupMaxPrefixProfileChanged NOTIFICATION-TYPE
			OBJECTS { sleBGPAFPeerControlRequest, sleBGPAFPeerControlTimeStamp, sleBGPAFPeerControlReqResult, sleBGPAFPeerMode, sleBGPAFPeerType,
				sleBGPAFPeerName, sleBGPAFPeerMaxPrefixNum, sleBGPAFPeerMaxPrefixThreshold, sleBGPAFPeerMaxPrefixWarnOnly }
			STATUS current
			DESCRIPTION
				"Description."
			::= { sleBGPAFPeerGroupNotification 9 }


		-- 1.3.6.1.4.1.6296.101.53.5.4.2.3.10
		sleBGPAFPeerGroupRemotePrivateAsChanged NOTIFICATION-TYPE
			OBJECTS { sleBGPAFPeerControlRequest, sleBGPAFPeerControlTimeStamp, sleBGPAFPeerControlReqResult, sleBGPAFPeerMode, sleBGPAFPeerType,
				sleBGPAFPeerName, sleBGPAFPeerRemotePrivateAs }
			STATUS current
			DESCRIPTION
				"Description."
			::= { sleBGPAFPeerGroupNotification 10 }


		-- 1.3.6.1.4.1.6296.101.53.5.4.2.3.11
		sleBGPAFPeerGroupInRoutemapChanged NOTIFICATION-TYPE
			OBJECTS { sleBGPAFPeerControlRequest, sleBGPAFPeerControlTimeStamp, sleBGPAFPeerControlReqResult, sleBGPAFPeerMode, sleBGPAFPeerType,
				sleBGPAFPeerName, sleBGPAFPeerInRoutemap }
			STATUS current
			DESCRIPTION
				"Description."
			::= { sleBGPAFPeerGroupNotification 11 }


		-- 1.3.6.1.4.1.6296.101.53.5.4.2.3.12
		sleBGPAFPeerGroupOutRoutemapChanged NOTIFICATION-TYPE
			OBJECTS { sleBGPAFPeerControlRequest, sleBGPAFPeerControlTimeStamp, sleBGPAFPeerControlReqResult, sleBGPAFPeerMode, sleBGPAFPeerType,
				sleBGPAFPeerName, sleBGPAFPeerOutRoutemap }
			STATUS current
			DESCRIPTION
				"Description."
			::= { sleBGPAFPeerGroupNotification 12 }


		-- 1.3.6.1.4.1.6296.101.53.5.4.2.3.13
		sleBGPAFPeerGroupRouteReflectClientChanged NOTIFICATION-TYPE
			OBJECTS { sleBGPAFPeerControlRequest, sleBGPAFPeerControlTimeStamp, sleBGPAFPeerControlReqResult, sleBGPAFPeerMode, sleBGPAFPeerType,
				sleBGPAFPeerName, sleBGPAFPeerRouteReflectClient }
			STATUS current
			DESCRIPTION
				"Description."
			::= { sleBGPAFPeerGroupNotification 13 }


		-- 1.3.6.1.4.1.6296.101.53.5.4.2.3.14
		sleBGPAFPeerGroupRouteServerClientChanged NOTIFICATION-TYPE
			OBJECTS { sleBGPAFPeerControlRequest, sleBGPAFPeerControlTimeStamp, sleBGPAFPeerControlReqResult, sleBGPAFPeerMode, sleBGPAFPeerType,
				sleBGPAFPeerName, sleBGPAFPeerRouteServerClient }
			STATUS current
			DESCRIPTION
				"Description."
			::= { sleBGPAFPeerGroupNotification 14 }


		-- 1.3.6.1.4.1.6296.101.53.5.4.2.3.15
		sleBGPAFPeerGroupInDistListNameChanged NOTIFICATION-TYPE
			OBJECTS { sleBGPAFPeerControlRequest, sleBGPAFPeerControlTimeStamp, sleBGPAFPeerControlReqResult, sleBGPAFPeerMode, sleBGPAFPeerType,
				sleBGPAFPeerName, sleBGPAFPeerInDistListName }
			STATUS current
			DESCRIPTION
				"Description."
			::= { sleBGPAFPeerGroupNotification 15 }


		-- 1.3.6.1.4.1.6296.101.53.5.4.2.3.16
		sleBGPAFPeerGroupOutDistListNameChanged NOTIFICATION-TYPE
			OBJECTS { sleBGPAFPeerControlRequest, sleBGPAFPeerControlTimeStamp, sleBGPAFPeerControlReqResult, sleBGPAFPeerMode, sleBGPAFPeerType,
				sleBGPAFPeerName, sleBGPAFPeerOutDistListName }
			STATUS current
			DESCRIPTION
				"Description."
			::= { sleBGPAFPeerGroupNotification 16 }


		-- 1.3.6.1.4.1.6296.101.53.5.4.2.3.17
		sleBGPAFPeerGroupInPrefixListNameChanged NOTIFICATION-TYPE
			OBJECTS { sleBGPAFPeerControlRequest, sleBGPAFPeerControlTimeStamp, sleBGPAFPeerControlReqResult, sleBGPAFPeerMode, sleBGPAFPeerType,
				sleBGPAFPeerName, sleBGPAFPeerInPrefixListName }
			STATUS current
			DESCRIPTION
				"Description."
			::= { sleBGPAFPeerGroupNotification 17 }


		-- 1.3.6.1.4.1.6296.101.53.5.4.2.3.18
		sleBGPAFPeerGroupOutPrefixListNameChanged NOTIFICATION-TYPE
			OBJECTS { sleBGPAFPeerControlRequest, sleBGPAFPeerControlTimeStamp, sleBGPAFPeerControlReqResult, sleBGPAFPeerMode, sleBGPAFPeerType,
				sleBGPAFPeerName, sleBGPAFPeerOutPrefixListName }
			STATUS current
			DESCRIPTION
				"Description."
			::= { sleBGPAFPeerGroupNotification 18 }


		-- 1.3.6.1.4.1.6296.101.53.5.4.2.3.19
		sleBGPAFPeerGroupSendCommunityChanged NOTIFICATION-TYPE
			OBJECTS { sleBGPAFPeerControlRequest, sleBGPAFPeerControlTimeStamp, sleBGPAFPeerControlReqResult, sleBGPAFPeerMode, sleBGPAFPeerType,
				sleBGPAFPeerName, sleBGPAFPeerSendCommunity }
			STATUS current
			DESCRIPTION
				"Except vpn4."
			::= { sleBGPAFPeerGroupNotification 19 }


		-- 1.3.6.1.4.1.6296.101.53.5.4.2.3.20
		sleBGPAFPeerGroupNexthopSelfChanged NOTIFICATION-TYPE
			OBJECTS { sleBGPAFPeerControlRequest, sleBGPAFPeerControlTimeStamp, sleBGPAFPeerControlReqResult, sleBGPAFPeerMode, sleBGPAFPeerType,
				sleBGPAFPeerName, sleBGPAFPeerNexthopSelf }
			STATUS current
			DESCRIPTION
				"Except vpn4."
			::= { sleBGPAFPeerGroupNotification 20 }


		-- 1.3.6.1.4.1.6296.101.53.5.4.2.3.21
		sleBGPAFPeerGroupSoftReconfigChanged NOTIFICATION-TYPE
			OBJECTS { sleBGPAFPeerControlRequest, sleBGPAFPeerControlTimeStamp, sleBGPAFPeerControlReqResult, sleBGPAFPeerMode, sleBGPAFPeerType,
				sleBGPAFPeerName, sleBGPAFPeerSoftReconfig }
			STATUS current
			DESCRIPTION
				"Except vpn4."
			::= { sleBGPAFPeerGroupNotification 21 }


		-- 1.3.6.1.4.1.6296.101.53.5.4.2.3.22
		sleBGPAFPeerGroupUnsuppressMapNameChanged NOTIFICATION-TYPE
			OBJECTS { sleBGPAFPeerControlRequest, sleBGPAFPeerControlTimeStamp, sleBGPAFPeerControlReqResult, sleBGPAFPeerMode, sleBGPAFPeerType,
				sleBGPAFPeerName, sleBGPAFPeerUnsuppressMapName }
			STATUS current
			DESCRIPTION
				"Except vpn4."
			::= { sleBGPAFPeerGroupNotification 22 }


		-- 1.3.6.1.4.1.6296.101.53.5.5
		sleBGPAFNetwork OBJECT IDENTIFIER ::= { sleBGPAFInfo 5 }


		-- 1.3.6.1.4.1.6296.101.53.5.5.1
		sleBGPAFNetworkTable OBJECT-TYPE
			SYNTAX SEQUENCE OF SleBGPAFNetworkEntry
			MAX-ACCESS not-accessible
			STATUS current
			DESCRIPTION
				"Description."
			::= { sleBGPAFNetwork 1 }


		-- 1.3.6.1.4.1.6296.101.53.5.5.1.1
		sleBGPAFNetworkEntry OBJECT-TYPE
			SYNTAX SleBGPAFNetworkEntry
			MAX-ACCESS not-accessible
			STATUS current
			DESCRIPTION
				"Description."
			INDEX { sleBGPAFNetworkMode, sleBGPAFNetworkType, sleBGPAFNetworkAddrPrefix }
			::= { sleBGPAFNetworkTable 1 }


		SleBGPAFNetworkEntry ::=
			SEQUENCE {
				sleBGPAFNetworkMode
					INTEGER,
				sleBGPAFNetworkType
					INTEGER,
				sleBGPAFNetworkAddrPrefix
					OCTET STRING,
				sleBGPAFNetworkBackdoor
					INTEGER,
				sleBGPAFNetworkRoutemap
					OCTET STRING
			 }

		-- 1.3.6.1.4.1.6296.101.53.5.5.1.1.1
		sleBGPAFNetworkMode OBJECT-TYPE
			SYNTAX INTEGER
				{
				ipv4(1),
				ipv6(2)
				}
			MAX-ACCESS read-only
			STATUS current
			DESCRIPTION
				"1: ipv4
				2: ipv6
				"
			::= { sleBGPAFNetworkEntry 1 }


		-- 1.3.6.1.4.1.6296.101.53.5.5.1.1.2
		sleBGPAFNetworkType OBJECT-TYPE
			SYNTAX INTEGER
				{
				unicast(1),
				multicast(2)
				}
			MAX-ACCESS read-only
			STATUS current
			DESCRIPTION
				"1: unicast
				2: multicast (only ipv4)
				3: vrf (only ipv4)
				"
			::= { sleBGPAFNetworkEntry 2 }


		-- 1.3.6.1.4.1.6296.101.53.5.5.1.1.3
		sleBGPAFNetworkAddrPrefix OBJECT-TYPE
			SYNTAX OCTET STRING
			MAX-ACCESS read-only
			STATUS current
			DESCRIPTION
				"example:
				1.1.1.1/24 or 1:1::1/64"
			::= { sleBGPAFNetworkEntry 3 }


		-- 1.3.6.1.4.1.6296.101.53.5.5.1.1.4
		sleBGPAFNetworkBackdoor OBJECT-TYPE
			SYNTAX INTEGER
				{
				disable(0),
				enable(1)
				}
			MAX-ACCESS read-only
			STATUS current
			DESCRIPTION
				" "
			::= { sleBGPAFNetworkEntry 4 }


		-- 1.3.6.1.4.1.6296.101.53.5.5.1.1.5
		sleBGPAFNetworkRoutemap OBJECT-TYPE
			SYNTAX OCTET STRING (SIZE (0..512))
			MAX-ACCESS read-only
			STATUS current
			DESCRIPTION
				" "
			::= { sleBGPAFNetworkEntry 5 }


		-- 1.3.6.1.4.1.6296.101.53.5.5.2
		sleBGPAFNetworkControl OBJECT IDENTIFIER ::= { sleBGPAFNetwork 2 }


		-- 1.3.6.1.4.1.6296.101.53.5.5.2.1
		sleBGPAFNetworkControlRequest OBJECT-TYPE
			SYNTAX INTEGER
				{
				createBGPAFNetwork(1),
				deleteBGPAFNetwork(2)
				}
			MAX-ACCESS read-write
			STATUS current
			DESCRIPTION
				"Description."
			::= { sleBGPAFNetworkControl 1 }


		-- 1.3.6.1.4.1.6296.101.53.5.5.2.2
		sleBGPAFNetworkControlStatus OBJECT-TYPE
			SYNTAX SleControlStatusType
			MAX-ACCESS read-only
			STATUS current
			DESCRIPTION
				"Description."
			::= { sleBGPAFNetworkControl 2 }


		-- 1.3.6.1.4.1.6296.101.53.5.5.2.3
		sleBGPAFNetworkControlTimer OBJECT-TYPE
			SYNTAX Gauge32
			MAX-ACCESS read-write
			STATUS current
			DESCRIPTION
				"Description."
			::= { sleBGPAFNetworkControl 3 }


		-- 1.3.6.1.4.1.6296.101.53.5.5.2.4
		sleBGPAFNetworkControlTimeStamp OBJECT-TYPE
			SYNTAX TimeTicks
			MAX-ACCESS read-only
			STATUS current
			DESCRIPTION
				"Description."
			::= { sleBGPAFNetworkControl 4 }


		-- 1.3.6.1.4.1.6296.101.53.5.5.2.5
		sleBGPAFNetworkControlReqResult OBJECT-TYPE
			SYNTAX SleControlRequestResultType
			MAX-ACCESS read-only
			STATUS current
			DESCRIPTION
				"Description."
			::= { sleBGPAFNetworkControl 5 }


		-- 1.3.6.1.4.1.6296.101.53.5.5.2.6
		sleBGPAFNetworkControlMode OBJECT-TYPE
			SYNTAX INTEGER
				{
				ipv4(1),
				ipv6(2)
				}
			MAX-ACCESS read-write
			STATUS current
			DESCRIPTION
				"1: ipv4
				2: ipv6
				"
			::= { sleBGPAFNetworkControl 6 }


		-- 1.3.6.1.4.1.6296.101.53.5.5.2.7
		sleBGPAFNetworkControlType OBJECT-TYPE
			SYNTAX INTEGER
				{
				unicast(1),
				multicast(2)
				}
			MAX-ACCESS read-write
			STATUS current
			DESCRIPTION
				"1: unicast
				2: multicast (only ipv4)
				3: vrf (only ipv4)
				"
			::= { sleBGPAFNetworkControl 7 }


		-- 1.3.6.1.4.1.6296.101.53.5.5.2.8
		sleBGPAFNetworkControlAddrPrefix OBJECT-TYPE
			SYNTAX OCTET STRING
			MAX-ACCESS read-write
			STATUS current
			DESCRIPTION
				"example:
				1.1.1.1/24 or 1:1::1/64"
			::= { sleBGPAFNetworkControl 8 }


		-- 1.3.6.1.4.1.6296.101.53.5.5.2.9
		sleBGPAFNetworkControlBackdoor OBJECT-TYPE
			SYNTAX INTEGER
				{
				disable(0),
				enable(1)
				}
			MAX-ACCESS read-write
			STATUS current
			DESCRIPTION
				" "
			::= { sleBGPAFNetworkControl 9 }


		-- 1.3.6.1.4.1.6296.101.53.5.5.2.10
		sleBGPAFNetworkControlRoutemap OBJECT-TYPE
			SYNTAX OCTET STRING (SIZE (0..512))
			MAX-ACCESS read-write
			STATUS current
			DESCRIPTION
				" "
			::= { sleBGPAFNetworkControl 10 }


		-- 1.3.6.1.4.1.6296.101.53.5.5.3
		sleBGPAFNetworkNotification OBJECT IDENTIFIER ::= { sleBGPAFNetwork 3 }


		-- 1.3.6.1.4.1.6296.101.53.5.5.3.1
		sleBGPAFNetworkCreated NOTIFICATION-TYPE
			OBJECTS { sleBGPAFNetworkControlRequest, sleBGPAFNetworkControlTimeStamp, sleBGPAFNetworkControlReqResult, sleBGPAFNetworkMode, sleBGPAFNetworkType,
				sleBGPAFNetworkAddrPrefix, sleBGPAFNetworkBackdoor, sleBGPAFNetworkRoutemap }
			STATUS current
			DESCRIPTION
				"Description."
			::= { sleBGPAFNetworkNotification 1 }


		-- 1.3.6.1.4.1.6296.101.53.5.5.3.2
		sleBGPAFNetworkDeleted NOTIFICATION-TYPE
			OBJECTS { sleBGPAFNetworkControlRequest, sleBGPAFNetworkControlTimeStamp, sleBGPAFNetworkControlReqResult, sleBGPAFNetworkControlMode, sleBGPAFNetworkControlType,
				sleBGPAFNetworkControlAddrPrefix, sleBGPAFNetworkControlBackdoor, sleBGPAFNetworkControlRoutemap }
			STATUS current
			DESCRIPTION
				"Description."
			::= { sleBGPAFNetworkNotification 2 }


		-- 1.3.6.1.4.1.6296.101.53.6
		sleBGPStatus OBJECT IDENTIFIER ::= { sleBGP 6 }


		-- 1.3.6.1.4.1.6296.101.53.6.1
		sleBGPStatusPeer OBJECT IDENTIFIER ::= { sleBGPStatus 1 }


		-- 1.3.6.1.4.1.6296.101.53.6.1.1
		sleBGPStatusPeerV4 OBJECT IDENTIFIER ::= { sleBGPStatusPeer 1 }


		-- 1.3.6.1.4.1.6296.101.53.6.1.1.1
		sleBGPStatusPeerV4Table OBJECT-TYPE
			SYNTAX SEQUENCE OF SleBGPStatusPeerV4Entry
			MAX-ACCESS not-accessible
			STATUS current
			DESCRIPTION
				"Description."
			::= { sleBGPStatusPeerV4 1 }


		-- 1.3.6.1.4.1.6296.101.53.6.1.1.1.1
		sleBGPStatusPeerV4Entry OBJECT-TYPE
			SYNTAX SleBGPStatusPeerV4Entry
			MAX-ACCESS not-accessible
			STATUS current
			DESCRIPTION
				"Description."
			INDEX { sleBGPStatusPeerV4Name }
			::= { sleBGPStatusPeerV4Table 1 }


		SleBGPStatusPeerV4Entry ::=
			SEQUENCE {
				sleBGPStatusPeerV4Name
					OCTET STRING,
				sleBGPStatusPeerV4RemoteAs
					Gauge32,
				sleBGPStatusPeerV4LocalAs
					Gauge32,
				sleBGPStatusPeerV4LinkState
					INTEGER,
				sleBGPStatusPeerV4RouterID
					IpAddress,
				sleBGPStatusPeerV4State
					INTEGER,
				sleBGPStatusPeerV4HoldTime
					INTEGER,
				sleBGPStatusPeerV4KeepAlive
					INTEGER,
				sleBGPStatusPeerV4Uptime
					OCTET STRING,
				sleBGPStatusPeerV4LastReadTime
					OCTET STRING,
				sleBGPStatusPeerV4RecvMessageCount
					Gauge32,
				sleBGPStatusPeerV4RecvNotificationCount
					Gauge32,
				sleBGPStatusPeerV4SentMessageCount
					Gauge32,
				sleBGPStatusPeerV4SentNotificationCount
					Gauge32,
				sleBGPStatusPeerV4RouteRefreshRecvRequestCount
					Gauge32,
				sleBGPStatusPeerV4RouteRefreshSentRequestCount
					Gauge32,
				sleBGPStatusPeerV4RouteAdvTime
					INTEGER,
				sleBGPStatusPeerV4EstablishedCount
					Gauge32,
				sleBGPStatusPeerV4DroppedCount
					Gauge32,
				sleBGPStatusPeerV4EBgpMultihopCount
					Gauge32,
				sleBGPStatusPeerV4LocalHost
					OCTET STRING,
				sleBGPStatusPeerV4LocalPort
					INTEGER,
				sleBGPStatusPeerV4ForeignHost
					OCTET STRING,
				sleBGPStatusPeerV4ForeignPort
					INTEGER,
				sleBGPStatusPeerV4RemainNextConnTime
					INTEGER
			 }

		-- 1.3.6.1.4.1.6296.101.53.6.1.1.1.1.1
		sleBGPStatusPeerV4Name OBJECT-TYPE
			SYNTAX OCTET STRING
			MAX-ACCESS read-only
			STATUS current
			DESCRIPTION
				"Description."
			::= { sleBGPStatusPeerV4Entry 1 }


		-- 1.3.6.1.4.1.6296.101.53.6.1.1.1.1.2
		sleBGPStatusPeerV4RemoteAs OBJECT-TYPE
			SYNTAX Gauge32
			MAX-ACCESS read-only
			STATUS current
			DESCRIPTION
				"Description."
			::= { sleBGPStatusPeerV4Entry 2 }


		-- 1.3.6.1.4.1.6296.101.53.6.1.1.1.1.3
		sleBGPStatusPeerV4LocalAs OBJECT-TYPE
			SYNTAX Gauge32
			MAX-ACCESS read-only
			STATUS current
			DESCRIPTION
				"Description."
			::= { sleBGPStatusPeerV4Entry 3 }


		-- 1.3.6.1.4.1.6296.101.53.6.1.1.1.1.4
		sleBGPStatusPeerV4LinkState OBJECT-TYPE
			SYNTAX INTEGER
				{
				internal(1),
				external(2)
				}
			MAX-ACCESS read-only
			STATUS current
			DESCRIPTION
				"Description."
			::= { sleBGPStatusPeerV4Entry 4 }


		-- 1.3.6.1.4.1.6296.101.53.6.1.1.1.1.5
		sleBGPStatusPeerV4RouterID OBJECT-TYPE
			SYNTAX IpAddress
			MAX-ACCESS read-only
			STATUS current
			DESCRIPTION
				"Description."
			::= { sleBGPStatusPeerV4Entry 5 }


		-- 1.3.6.1.4.1.6296.101.53.6.1.1.1.1.6
		sleBGPStatusPeerV4State OBJECT-TYPE
			SYNTAX INTEGER
				{
				invalid(0),
				idle(1),
				connect(2),
				active(3),
				opensent(4),
				openconfirm(5),
				established(6)
				}
			MAX-ACCESS read-only
			STATUS current
			DESCRIPTION
				"Description."
			::= { sleBGPStatusPeerV4Entry 6 }


		-- 1.3.6.1.4.1.6296.101.53.6.1.1.1.1.7
		sleBGPStatusPeerV4HoldTime OBJECT-TYPE
			SYNTAX INTEGER
			MAX-ACCESS read-only
			STATUS current
			DESCRIPTION
				"Description."
			::= { sleBGPStatusPeerV4Entry 7 }


		-- 1.3.6.1.4.1.6296.101.53.6.1.1.1.1.8
		sleBGPStatusPeerV4KeepAlive OBJECT-TYPE
			SYNTAX INTEGER
			MAX-ACCESS read-only
			STATUS current
			DESCRIPTION
				"Description."
			::= { sleBGPStatusPeerV4Entry 8 }


		-- 1.3.6.1.4.1.6296.101.53.6.1.1.1.1.9
		sleBGPStatusPeerV4Uptime OBJECT-TYPE
			SYNTAX OCTET STRING
			MAX-ACCESS read-only
			STATUS current
			DESCRIPTION
				"Description."
			::= { sleBGPStatusPeerV4Entry 9 }


		-- 1.3.6.1.4.1.6296.101.53.6.1.1.1.1.10
		sleBGPStatusPeerV4LastReadTime OBJECT-TYPE
			SYNTAX OCTET STRING
			MAX-ACCESS read-only
			STATUS current
			DESCRIPTION
				"Description."
			::= { sleBGPStatusPeerV4Entry 10 }


		-- 1.3.6.1.4.1.6296.101.53.6.1.1.1.1.11
		sleBGPStatusPeerV4RecvMessageCount OBJECT-TYPE
			SYNTAX Gauge32
			MAX-ACCESS read-only
			STATUS current
			DESCRIPTION
				"Description."
			::= { sleBGPStatusPeerV4Entry 11 }


		-- 1.3.6.1.4.1.6296.101.53.6.1.1.1.1.12
		sleBGPStatusPeerV4RecvNotificationCount OBJECT-TYPE
			SYNTAX Gauge32
			MAX-ACCESS read-only
			STATUS current
			DESCRIPTION
				"Description."
			::= { sleBGPStatusPeerV4Entry 12 }


		-- 1.3.6.1.4.1.6296.101.53.6.1.1.1.1.13
		sleBGPStatusPeerV4SentMessageCount OBJECT-TYPE
			SYNTAX Gauge32
			MAX-ACCESS read-only
			STATUS current
			DESCRIPTION
				"Description."
			::= { sleBGPStatusPeerV4Entry 13 }


		-- 1.3.6.1.4.1.6296.101.53.6.1.1.1.1.14
		sleBGPStatusPeerV4SentNotificationCount OBJECT-TYPE
			SYNTAX Gauge32
			MAX-ACCESS read-only
			STATUS current
			DESCRIPTION
				"Description."
			::= { sleBGPStatusPeerV4Entry 14 }


		-- 1.3.6.1.4.1.6296.101.53.6.1.1.1.1.15
		sleBGPStatusPeerV4RouteRefreshRecvRequestCount OBJECT-TYPE
			SYNTAX Gauge32
			MAX-ACCESS read-only
			STATUS current
			DESCRIPTION
				"Description."
			::= { sleBGPStatusPeerV4Entry 15 }


		-- 1.3.6.1.4.1.6296.101.53.6.1.1.1.1.16
		sleBGPStatusPeerV4RouteRefreshSentRequestCount OBJECT-TYPE
			SYNTAX Gauge32
			MAX-ACCESS read-only
			STATUS current
			DESCRIPTION
				"Description."
			::= { sleBGPStatusPeerV4Entry 16 }


		-- 1.3.6.1.4.1.6296.101.53.6.1.1.1.1.17
		sleBGPStatusPeerV4RouteAdvTime OBJECT-TYPE
			SYNTAX INTEGER
			MAX-ACCESS read-only
			STATUS current
			DESCRIPTION
				"Description."
			::= { sleBGPStatusPeerV4Entry 17 }


		-- 1.3.6.1.4.1.6296.101.53.6.1.1.1.1.18
		sleBGPStatusPeerV4EstablishedCount OBJECT-TYPE
			SYNTAX Gauge32
			MAX-ACCESS read-only
			STATUS current
			DESCRIPTION
				"Description."
			::= { sleBGPStatusPeerV4Entry 18 }


		-- 1.3.6.1.4.1.6296.101.53.6.1.1.1.1.19
		sleBGPStatusPeerV4DroppedCount OBJECT-TYPE
			SYNTAX Gauge32
			MAX-ACCESS read-only
			STATUS current
			DESCRIPTION
				"Description."
			::= { sleBGPStatusPeerV4Entry 19 }


		-- 1.3.6.1.4.1.6296.101.53.6.1.1.1.1.20
		sleBGPStatusPeerV4EBgpMultihopCount OBJECT-TYPE
			SYNTAX Gauge32
			MAX-ACCESS read-only
			STATUS current
			DESCRIPTION
				"Description."
			::= { sleBGPStatusPeerV4Entry 20 }


		-- 1.3.6.1.4.1.6296.101.53.6.1.1.1.1.21
		sleBGPStatusPeerV4LocalHost OBJECT-TYPE
			SYNTAX OCTET STRING
			MAX-ACCESS read-only
			STATUS current
			DESCRIPTION
				"Description."
			::= { sleBGPStatusPeerV4Entry 21 }


		-- 1.3.6.1.4.1.6296.101.53.6.1.1.1.1.22
		sleBGPStatusPeerV4LocalPort OBJECT-TYPE
			SYNTAX INTEGER
			MAX-ACCESS read-only
			STATUS current
			DESCRIPTION
				"Description."
			::= { sleBGPStatusPeerV4Entry 22 }


		-- 1.3.6.1.4.1.6296.101.53.6.1.1.1.1.23
		sleBGPStatusPeerV4ForeignHost OBJECT-TYPE
			SYNTAX OCTET STRING
			MAX-ACCESS read-only
			STATUS current
			DESCRIPTION
				"Description."
			::= { sleBGPStatusPeerV4Entry 23 }


		-- 1.3.6.1.4.1.6296.101.53.6.1.1.1.1.24
		sleBGPStatusPeerV4ForeignPort OBJECT-TYPE
			SYNTAX INTEGER
			MAX-ACCESS read-only
			STATUS current
			DESCRIPTION
				"Description."
			::= { sleBGPStatusPeerV4Entry 24 }


		-- 1.3.6.1.4.1.6296.101.53.6.1.1.1.1.25
		sleBGPStatusPeerV4RemainNextConnTime OBJECT-TYPE
			SYNTAX INTEGER
			MAX-ACCESS read-only
			STATUS current
			DESCRIPTION
				"Description."
			::= { sleBGPStatusPeerV4Entry 25 }


		-- 1.3.6.1.4.1.6296.101.53.6.1.2
		sleBGPStatusPeerV6 OBJECT IDENTIFIER ::= { sleBGPStatusPeer 2 }


		-- 1.3.6.1.4.1.6296.101.53.6.1.2.1
		sleBGPStatusPeerV6Table OBJECT-TYPE
			SYNTAX SEQUENCE OF SleBGPStatusPeerV6Entry
			MAX-ACCESS not-accessible
			STATUS current
			DESCRIPTION
				"Description."
			::= { sleBGPStatusPeerV6 1 }


		-- 1.3.6.1.4.1.6296.101.53.6.1.2.1.1
		sleBGPStatusPeerV6Entry OBJECT-TYPE
			SYNTAX SleBGPStatusPeerV6Entry
			MAX-ACCESS not-accessible
			STATUS current
			DESCRIPTION
				"Description."
			INDEX { sleBGPStatusPeerV6Name }
			::= { sleBGPStatusPeerV6Table 1 }


		SleBGPStatusPeerV6Entry ::=
			SEQUENCE {
				sleBGPStatusPeerV6Name
					OCTET STRING,
				sleBGPStatusPeerV6RemoteAs
					Gauge32,
				sleBGPStatusPeerV6LocalAs
					Gauge32,
				sleBGPStatusPeerV6LinkState
					INTEGER,
				sleBGPStatusPeerV6RouterID
					IpAddress,
				sleBGPStatusPeerV6State
					INTEGER,
				sleBGPStatusPeerV6HoldTime
					INTEGER,
				sleBGPStatusPeerV6KeepAlive
					INTEGER,
				sleBGPStatusPeerV6Uptime
					OCTET STRING,
				sleBGPStatusPeerV6LastReadTime
					OCTET STRING,
				sleBGPStatusPeerV6RecvMessageCount
					Gauge32,
				sleBGPStatusPeerV6RecvNotificationCount
					Gauge32,
				sleBGPStatusPeerV6SentMessageCount
					Gauge32,
				sleBGPStatusPeerV6SentNotificationCount
					Gauge32,
				sleBGPStatusPeerV6RouteRefreshRecvRequestCount
					Gauge32,
				sleBGPStatusPeerV6RouteRefreshSentRequestCount
					Gauge32,
				sleBGPStatusPeerV6RouteAdvTime
					INTEGER,
				sleBGPStatusPeerV6EstablishedCount
					Gauge32,
				sleBGPStatusPeerV6DroppedCount
					Gauge32,
				sleBGPStatusPeerV6EBgpMultihopCount
					Gauge32,
				sleBGPStatusPeerV6LocalHost
					OCTET STRING,
				sleBGPStatusPeerV6LocalPort
					INTEGER,
				sleBGPStatusPeerV6ForeignHost
					OCTET STRING,
				sleBGPStatusPeerV6ForeignPort
					INTEGER,
				sleBGPStatusPeerV6RemainNextConnTime
					INTEGER
			 }

		-- 1.3.6.1.4.1.6296.101.53.6.1.2.1.1.1
		sleBGPStatusPeerV6Name OBJECT-TYPE
			SYNTAX OCTET STRING
			MAX-ACCESS read-only
			STATUS current
			DESCRIPTION
				"Description."
			::= { sleBGPStatusPeerV6Entry 1 }


		-- 1.3.6.1.4.1.6296.101.53.6.1.2.1.1.2
		sleBGPStatusPeerV6RemoteAs OBJECT-TYPE
			SYNTAX Gauge32
			MAX-ACCESS read-only
			STATUS current
			DESCRIPTION
				"Description."
			::= { sleBGPStatusPeerV6Entry 2 }


		-- 1.3.6.1.4.1.6296.101.53.6.1.2.1.1.3
		sleBGPStatusPeerV6LocalAs OBJECT-TYPE
			SYNTAX Gauge32
			MAX-ACCESS read-only
			STATUS current
			DESCRIPTION
				"Description."
			::= { sleBGPStatusPeerV6Entry 3 }


		-- 1.3.6.1.4.1.6296.101.53.6.1.2.1.1.4
		sleBGPStatusPeerV6LinkState OBJECT-TYPE
			SYNTAX INTEGER
				{
				internal(1),
				external(2)
				}
			MAX-ACCESS read-only
			STATUS current
			DESCRIPTION
				"Description."
			::= { sleBGPStatusPeerV6Entry 4 }


		-- 1.3.6.1.4.1.6296.101.53.6.1.2.1.1.5
		sleBGPStatusPeerV6RouterID OBJECT-TYPE
			SYNTAX IpAddress
			MAX-ACCESS read-only
			STATUS current
			DESCRIPTION
				"Description."
			::= { sleBGPStatusPeerV6Entry 5 }


		-- 1.3.6.1.4.1.6296.101.53.6.1.2.1.1.6
		sleBGPStatusPeerV6State OBJECT-TYPE
			SYNTAX INTEGER
				{
				invalid(0),
				idle(1),
				connect(2),
				active(3),
				opensent(4),
				openconfirm(5),
				established(6)
				}
			MAX-ACCESS read-only
			STATUS current
			DESCRIPTION
				"Description."
			::= { sleBGPStatusPeerV6Entry 6 }


		-- 1.3.6.1.4.1.6296.101.53.6.1.2.1.1.7
		sleBGPStatusPeerV6HoldTime OBJECT-TYPE
			SYNTAX INTEGER
			MAX-ACCESS read-only
			STATUS current
			DESCRIPTION
				"Description."
			::= { sleBGPStatusPeerV6Entry 7 }


		-- 1.3.6.1.4.1.6296.101.53.6.1.2.1.1.8
		sleBGPStatusPeerV6KeepAlive OBJECT-TYPE
			SYNTAX INTEGER
			MAX-ACCESS read-only
			STATUS current
			DESCRIPTION
				"Description."
			::= { sleBGPStatusPeerV6Entry 8 }


		-- 1.3.6.1.4.1.6296.101.53.6.1.2.1.1.9
		sleBGPStatusPeerV6Uptime OBJECT-TYPE
			SYNTAX OCTET STRING
			MAX-ACCESS read-only
			STATUS current
			DESCRIPTION
				"Description."
			::= { sleBGPStatusPeerV6Entry 9 }


		-- 1.3.6.1.4.1.6296.101.53.6.1.2.1.1.10
		sleBGPStatusPeerV6LastReadTime OBJECT-TYPE
			SYNTAX OCTET STRING
			MAX-ACCESS read-only
			STATUS current
			DESCRIPTION
				"Description."
			::= { sleBGPStatusPeerV6Entry 10 }


		-- 1.3.6.1.4.1.6296.101.53.6.1.2.1.1.11
		sleBGPStatusPeerV6RecvMessageCount OBJECT-TYPE
			SYNTAX Gauge32
			MAX-ACCESS read-only
			STATUS current
			DESCRIPTION
				"Description."
			::= { sleBGPStatusPeerV6Entry 11 }


		-- 1.3.6.1.4.1.6296.101.53.6.1.2.1.1.12
		sleBGPStatusPeerV6RecvNotificationCount OBJECT-TYPE
			SYNTAX Gauge32
			MAX-ACCESS read-only
			STATUS current
			DESCRIPTION
				"Description."
			::= { sleBGPStatusPeerV6Entry 12 }


		-- 1.3.6.1.4.1.6296.101.53.6.1.2.1.1.13
		sleBGPStatusPeerV6SentMessageCount OBJECT-TYPE
			SYNTAX Gauge32
			MAX-ACCESS read-only
			STATUS current
			DESCRIPTION
				"Description."
			::= { sleBGPStatusPeerV6Entry 13 }


		-- 1.3.6.1.4.1.6296.101.53.6.1.2.1.1.14
		sleBGPStatusPeerV6SentNotificationCount OBJECT-TYPE
			SYNTAX Gauge32
			MAX-ACCESS read-only
			STATUS current
			DESCRIPTION
				"Description."
			::= { sleBGPStatusPeerV6Entry 14 }


		-- 1.3.6.1.4.1.6296.101.53.6.1.2.1.1.15
		sleBGPStatusPeerV6RouteRefreshRecvRequestCount OBJECT-TYPE
			SYNTAX Gauge32
			MAX-ACCESS read-only
			STATUS current
			DESCRIPTION
				"Description."
			::= { sleBGPStatusPeerV6Entry 15 }


		-- 1.3.6.1.4.1.6296.101.53.6.1.2.1.1.16
		sleBGPStatusPeerV6RouteRefreshSentRequestCount OBJECT-TYPE
			SYNTAX Gauge32
			MAX-ACCESS read-only
			STATUS current
			DESCRIPTION
				"Description."
			::= { sleBGPStatusPeerV6Entry 16 }


		-- 1.3.6.1.4.1.6296.101.53.6.1.2.1.1.17
		sleBGPStatusPeerV6RouteAdvTime OBJECT-TYPE
			SYNTAX INTEGER
			MAX-ACCESS read-only
			STATUS current
			DESCRIPTION
				"Description."
			::= { sleBGPStatusPeerV6Entry 17 }


		-- 1.3.6.1.4.1.6296.101.53.6.1.2.1.1.18
		sleBGPStatusPeerV6EstablishedCount OBJECT-TYPE
			SYNTAX Gauge32
			MAX-ACCESS read-only
			STATUS current
			DESCRIPTION
				"Description."
			::= { sleBGPStatusPeerV6Entry 18 }


		-- 1.3.6.1.4.1.6296.101.53.6.1.2.1.1.19
		sleBGPStatusPeerV6DroppedCount OBJECT-TYPE
			SYNTAX Gauge32
			MAX-ACCESS read-only
			STATUS current
			DESCRIPTION
				"Description."
			::= { sleBGPStatusPeerV6Entry 19 }


		-- 1.3.6.1.4.1.6296.101.53.6.1.2.1.1.20
		sleBGPStatusPeerV6EBgpMultihopCount OBJECT-TYPE
			SYNTAX Gauge32
			MAX-ACCESS read-only
			STATUS current
			DESCRIPTION
				"Description."
			::= { sleBGPStatusPeerV6Entry 20 }


		-- 1.3.6.1.4.1.6296.101.53.6.1.2.1.1.21
		sleBGPStatusPeerV6LocalHost OBJECT-TYPE
			SYNTAX OCTET STRING
			MAX-ACCESS read-only
			STATUS current
			DESCRIPTION
				"Description."
			::= { sleBGPStatusPeerV6Entry 21 }


		-- 1.3.6.1.4.1.6296.101.53.6.1.2.1.1.22
		sleBGPStatusPeerV6LocalPort OBJECT-TYPE
			SYNTAX INTEGER
			MAX-ACCESS read-only
			STATUS current
			DESCRIPTION
				"Description."
			::= { sleBGPStatusPeerV6Entry 22 }


		-- 1.3.6.1.4.1.6296.101.53.6.1.2.1.1.23
		sleBGPStatusPeerV6ForeignHost OBJECT-TYPE
			SYNTAX OCTET STRING
			MAX-ACCESS read-only
			STATUS current
			DESCRIPTION
				"Description."
			::= { sleBGPStatusPeerV6Entry 23 }


		-- 1.3.6.1.4.1.6296.101.53.6.1.2.1.1.24
		sleBGPStatusPeerV6ForeignPort OBJECT-TYPE
			SYNTAX INTEGER
			MAX-ACCESS read-only
			STATUS current
			DESCRIPTION
				"Description."
			::= { sleBGPStatusPeerV6Entry 24 }


		-- 1.3.6.1.4.1.6296.101.53.6.1.2.1.1.25
		sleBGPStatusPeerV6RemainNextConnTime OBJECT-TYPE
			SYNTAX INTEGER
			MAX-ACCESS read-only
			STATUS current
			DESCRIPTION
				"Description."
			::= { sleBGPStatusPeerV6Entry 25 }


		-- 1.3.6.1.4.1.6296.101.53.6.2
		sleBGPRoutes OBJECT IDENTIFIER ::= { sleBGPStatus 2 }


		-- 1.3.6.1.4.1.6296.101.53.6.2.1
		sleBGPRoutesV4 OBJECT IDENTIFIER ::= { sleBGPRoutes 1 }


		-- 1.3.6.1.4.1.6296.101.53.6.2.1.1
		sleBGPRoutesV4Table OBJECT-TYPE
			SYNTAX SEQUENCE OF SleBGPRoutesV4Entry
			MAX-ACCESS not-accessible
			STATUS current
			DESCRIPTION
				"Description."
			::= { sleBGPRoutesV4 1 }


		-- 1.3.6.1.4.1.6296.101.53.6.2.1.1.1
		sleBGPRoutesV4Entry OBJECT-TYPE
			SYNTAX SleBGPRoutesV4Entry
			MAX-ACCESS not-accessible
			STATUS current
			DESCRIPTION
				"Description."
			INDEX { sleBGPRoutesV4SAFIType, sleBGPRoutesV4RoutePrefix, sleBGPRoutesV4Nexthop }
			::= { sleBGPRoutesV4Table 1 }


		SleBGPRoutesV4Entry ::=
			SEQUENCE {
				sleBGPRoutesV4SAFIType
					INTEGER,
				sleBGPRoutesV4RoutePrefix
					OCTET STRING,
				sleBGPRoutesV4Nexthop
					OCTET STRING,
				sleBGPRoutesV4NexthopSelected
					INTEGER,
				sleBGPRoutesV4NexthopInternal
					INTEGER,
				sleBGPRoutesV4NexthopMed
					INTEGER,
				sleBGPRoutesV4NexthopLocPref
					Gauge32,
				sleBGPRoutesV4NexthopWeight
					INTEGER,
				sleBGPRoutesV4NexthopSuppress
					INTEGER,
				sleBGPRoutesV4NexthopValid
					INTEGER,
				sleBGPRoutesV4NexthopStale
					INTEGER,
				sleBGPRoutesV4NexthopDamped
					INTEGER,
				sleBGPRoutesV4NexthopStaleHistory
					INTEGER
			 }

		-- 1.3.6.1.4.1.6296.101.53.6.2.1.1.1.1
		sleBGPRoutesV4SAFIType OBJECT-TYPE
			SYNTAX INTEGER
				{
				unicast(1),
				multicast(2)
				}
			MAX-ACCESS read-only
			STATUS current
			DESCRIPTION
				"Description."
			::= { sleBGPRoutesV4Entry 1 }


		-- 1.3.6.1.4.1.6296.101.53.6.2.1.1.1.2
		sleBGPRoutesV4RoutePrefix OBJECT-TYPE
			SYNTAX OCTET STRING
			MAX-ACCESS read-only
			STATUS current
			DESCRIPTION
				"Description."
			::= { sleBGPRoutesV4Entry 2 }


		-- 1.3.6.1.4.1.6296.101.53.6.2.1.1.1.3
		sleBGPRoutesV4Nexthop OBJECT-TYPE
			SYNTAX OCTET STRING
			MAX-ACCESS read-only
			STATUS current
			DESCRIPTION
				"Description."
			::= { sleBGPRoutesV4Entry 3 }


		-- 1.3.6.1.4.1.6296.101.53.6.2.1.1.1.4
		sleBGPRoutesV4NexthopSelected OBJECT-TYPE
			SYNTAX INTEGER
				{
				disable(0),
				enable(1)
				}
			MAX-ACCESS read-only
			STATUS current
			DESCRIPTION
				"Description."
			::= { sleBGPRoutesV4Entry 4 }


		-- 1.3.6.1.4.1.6296.101.53.6.2.1.1.1.5
		sleBGPRoutesV4NexthopInternal OBJECT-TYPE
			SYNTAX INTEGER
				{
				internal(1),
				external(2)
				}
			MAX-ACCESS read-only
			STATUS current
			DESCRIPTION
				"Description."
			::= { sleBGPRoutesV4Entry 5 }


		-- 1.3.6.1.4.1.6296.101.53.6.2.1.1.1.6
		sleBGPRoutesV4NexthopMed OBJECT-TYPE
			SYNTAX INTEGER (1..65535)
			MAX-ACCESS read-only
			STATUS current
			DESCRIPTION
				"Description."
			::= { sleBGPRoutesV4Entry 6 }


		-- 1.3.6.1.4.1.6296.101.53.6.2.1.1.1.7
		sleBGPRoutesV4NexthopLocPref OBJECT-TYPE
			SYNTAX Gauge32
			MAX-ACCESS read-only
			STATUS current
			DESCRIPTION
				"Description."
			::= { sleBGPRoutesV4Entry 7 }


		-- 1.3.6.1.4.1.6296.101.53.6.2.1.1.1.8
		sleBGPRoutesV4NexthopWeight OBJECT-TYPE
			SYNTAX INTEGER (1..65535)
			MAX-ACCESS read-only
			STATUS current
			DESCRIPTION
				"Description."
			::= { sleBGPRoutesV4Entry 8 }


		-- 1.3.6.1.4.1.6296.101.53.6.2.1.1.1.9
		sleBGPRoutesV4NexthopSuppress OBJECT-TYPE
			SYNTAX INTEGER
				{
				disable(0),
				enable(1)
				}
			MAX-ACCESS read-only
			STATUS current
			DESCRIPTION
				"Description."
			::= { sleBGPRoutesV4Entry 9 }


		-- 1.3.6.1.4.1.6296.101.53.6.2.1.1.1.10
		sleBGPRoutesV4NexthopValid OBJECT-TYPE
			SYNTAX INTEGER
				{
				disable(0),
				enable(1)
				}
			MAX-ACCESS read-only
			STATUS current
			DESCRIPTION
				"Description."
			::= { sleBGPRoutesV4Entry 10 }


		-- 1.3.6.1.4.1.6296.101.53.6.2.1.1.1.11
		sleBGPRoutesV4NexthopStale OBJECT-TYPE
			SYNTAX INTEGER
				{
				disable(0),
				enable(1)
				}
			MAX-ACCESS read-only
			STATUS current
			DESCRIPTION
				"Description."
			::= { sleBGPRoutesV4Entry 11 }


		-- 1.3.6.1.4.1.6296.101.53.6.2.1.1.1.12
		sleBGPRoutesV4NexthopDamped OBJECT-TYPE
			SYNTAX INTEGER
				{
				disable(0),
				enable(1)
				}
			MAX-ACCESS read-only
			STATUS current
			DESCRIPTION
				"Description."
			::= { sleBGPRoutesV4Entry 12 }


		-- 1.3.6.1.4.1.6296.101.53.6.2.1.1.1.13
		sleBGPRoutesV4NexthopStaleHistory OBJECT-TYPE
			SYNTAX INTEGER
				{
				disable(0),
				enable(1)
				}
			MAX-ACCESS read-only
			STATUS current
			DESCRIPTION
				"Description."
			::= { sleBGPRoutesV4Entry 13 }


		-- 1.3.6.1.4.1.6296.101.53.6.2.2
		sleBGPRoutesV6 OBJECT IDENTIFIER ::= { sleBGPRoutes 2 }


		-- 1.3.6.1.4.1.6296.101.53.6.2.2.1
		sleBGPRoutesV6Table OBJECT-TYPE
			SYNTAX SEQUENCE OF SleBGPRoutesV6Entry
			MAX-ACCESS not-accessible
			STATUS current
			DESCRIPTION
				"Description."
			::= { sleBGPRoutesV6 1 }


		-- 1.3.6.1.4.1.6296.101.53.6.2.2.1.1
		sleBGPRoutesV6Entry OBJECT-TYPE
			SYNTAX SleBGPRoutesV6Entry
			MAX-ACCESS not-accessible
			STATUS current
			DESCRIPTION
				"Description."
			INDEX { sleBGPRoutesV4SAFIType, sleBGPRoutesV4RoutePrefix, sleBGPRoutesV4Nexthop }
			::= { sleBGPRoutesV6Table 1 }


		SleBGPRoutesV6Entry ::=
			SEQUENCE {
				sleBGPRoutesV6SAFIType
					INTEGER,
				sleBGPRoutesV6RoutePrefix
					OCTET STRING,
				sleBGPRoutesV6Nexthop
					OCTET STRING,
				sleBGPRoutesV6NexthopSelected
					INTEGER,
				sleBGPRoutesV6NexthopInternal
					INTEGER,
				sleBGPRoutesV6NexthopMed
					INTEGER,
				sleBGPRoutesV6NexthopLocPref
					Gauge32,
				sleBGPRoutesV6NexthopWeight
					INTEGER,
				sleBGPRoutesV6NexthopSuppress
					INTEGER,
				sleBGPRoutesV6NexthopValid
					INTEGER,
				sleBGPRoutesV6NexthopStale
					INTEGER,
				sleBGPRoutesV6NexthopDamped
					INTEGER,
				sleBGPRoutesV6NexthopStaleHistory
					INTEGER
			 }

		-- 1.3.6.1.4.1.6296.101.53.6.2.2.1.1.1
		sleBGPRoutesV6SAFIType OBJECT-TYPE
			SYNTAX INTEGER
				{
				unicast(1),
				multicast(2)
				}
			MAX-ACCESS read-only
			STATUS current
			DESCRIPTION
				"Description."
			::= { sleBGPRoutesV6Entry 1 }


		-- 1.3.6.1.4.1.6296.101.53.6.2.2.1.1.2
		sleBGPRoutesV6RoutePrefix OBJECT-TYPE
			SYNTAX OCTET STRING
			MAX-ACCESS read-only
			STATUS current
			DESCRIPTION
				"Description."
			::= { sleBGPRoutesV6Entry 2 }


		-- 1.3.6.1.4.1.6296.101.53.6.2.2.1.1.3
		sleBGPRoutesV6Nexthop OBJECT-TYPE
			SYNTAX OCTET STRING
			MAX-ACCESS read-only
			STATUS current
			DESCRIPTION
				"Description."
			::= { sleBGPRoutesV6Entry 3 }


		-- 1.3.6.1.4.1.6296.101.53.6.2.2.1.1.4
		sleBGPRoutesV6NexthopSelected OBJECT-TYPE
			SYNTAX INTEGER
				{
				disable(0),
				enable(1)
				}
			MAX-ACCESS read-only
			STATUS current
			DESCRIPTION
				"Description."
			::= { sleBGPRoutesV6Entry 4 }


		-- 1.3.6.1.4.1.6296.101.53.6.2.2.1.1.5
		sleBGPRoutesV6NexthopInternal OBJECT-TYPE
			SYNTAX INTEGER
				{
				internal(1),
				external(2)
				}
			MAX-ACCESS read-only
			STATUS current
			DESCRIPTION
				"Description."
			::= { sleBGPRoutesV6Entry 5 }


		-- 1.3.6.1.4.1.6296.101.53.6.2.2.1.1.6
		sleBGPRoutesV6NexthopMed OBJECT-TYPE
			SYNTAX INTEGER (1..65535)
			MAX-ACCESS read-only
			STATUS current
			DESCRIPTION
				"Description."
			::= { sleBGPRoutesV6Entry 6 }


		-- 1.3.6.1.4.1.6296.101.53.6.2.2.1.1.7
		sleBGPRoutesV6NexthopLocPref OBJECT-TYPE
			SYNTAX Gauge32
			MAX-ACCESS read-only
			STATUS current
			DESCRIPTION
				"Description."
			::= { sleBGPRoutesV6Entry 7 }


		-- 1.3.6.1.4.1.6296.101.53.6.2.2.1.1.8
		sleBGPRoutesV6NexthopWeight OBJECT-TYPE
			SYNTAX INTEGER (1..65535)
			MAX-ACCESS read-only
			STATUS current
			DESCRIPTION
				"Description."
			::= { sleBGPRoutesV6Entry 8 }


		-- 1.3.6.1.4.1.6296.101.53.6.2.2.1.1.9
		sleBGPRoutesV6NexthopSuppress OBJECT-TYPE
			SYNTAX INTEGER
				{
				disable(0),
				enable(1)
				}
			MAX-ACCESS read-only
			STATUS current
			DESCRIPTION
				"Description."
			::= { sleBGPRoutesV6Entry 9 }


		-- 1.3.6.1.4.1.6296.101.53.6.2.2.1.1.10
		sleBGPRoutesV6NexthopValid OBJECT-TYPE
			SYNTAX INTEGER { disable(0) }
			MAX-ACCESS read-only
			STATUS current
			DESCRIPTION
				"Description."
			::= { sleBGPRoutesV6Entry 10 }


		-- 1.3.6.1.4.1.6296.101.53.6.2.2.1.1.11
		sleBGPRoutesV6NexthopStale OBJECT-TYPE
			SYNTAX INTEGER
				{
				disable(0),
				enable(1)
				}
			MAX-ACCESS read-only
			STATUS current
			DESCRIPTION
				"Description."
			::= { sleBGPRoutesV6Entry 11 }


		-- 1.3.6.1.4.1.6296.101.53.6.2.2.1.1.12
		sleBGPRoutesV6NexthopDamped OBJECT-TYPE
			SYNTAX INTEGER
				{
				disable(0),
				enable(1)
				}
			MAX-ACCESS read-only
			STATUS current
			DESCRIPTION
				"Description."
			::= { sleBGPRoutesV6Entry 12 }


		-- 1.3.6.1.4.1.6296.101.53.6.2.2.1.1.13
		sleBGPRoutesV6NexthopStaleHistory OBJECT-TYPE
			SYNTAX INTEGER
				{
				disable(0),
				enable(1)
				}
			MAX-ACCESS read-only
			STATUS current
			DESCRIPTION
				"Description."
			::= { sleBGPRoutesV6Entry 13 }


		-- 1.3.6.1.4.1.6296.101.53.7
		sleBGPGroup OBJECT-GROUP
			OBJECTS { sleBGPBaseAsNumber, sleBGPBaseConfigType, sleBGPBaseRfc1771PathSelect, sleBGPBaseRfc1771Strict, sleBGPBaseAggregateNextHop,
				sleBGPBaseExtendAsnCap, sleBGPBaseControlRequest, sleBGPBaseControlStatus, sleBGPBaseControlTimer, sleBGPBaseControlTimeStamp,
				sleBGPBaseControlReqResult, sleBGPBaseControlAsNumber, sleBGPBaseControlConfigType, sleBGPBaseControlRfc1771PathSelect, sleBGPBaseControlRfc1771Strict,
				sleBGPBaseControlAggregateNextHop, sleBGPBaseControlExtendAsnCap, sleBGPBaseControlClearFamilyMode, sleBGPBaseControlClearFamilyType, sleBGPBaseControlClearDirection,
				sleBGPBaseControlClearSoft, sleBGPBaseControlClearPrefixFilter, sleBGPBaseControlClearPeerName, sleBGPBaseControlClearAddr, sleBGPBaseControlClearViewName,
				sleBGPBaseControlClearDampFlag, sleBGPInfoRouterID, sleBGPInfoLogNeighborChange, sleBGPInfoAlwaysCompareMed, sleBGPInfoBestPathAsPathIgnore,
				sleBGPInfoBestPathCompareConfedAsPath, sleBGPInfoBestPathCompareRouterID, sleBGPInfoBestPathCompareMedConfed, sleBGPInfoBestPathCompareMedMisAsWorst, sleBGPInfoClientToClient,
				sleBGPInfoClusterID, sleBGPInfoConfederationID, sleBGPInfoDeterministicMed, sleBGPInfoEnforceFirstAs, sleBGPInfoFastExternalFailOver,
				sleBGPInfoGracefulRestartTime, sleBGPInfoGracefulStalepathTime, sleBGPInfoScanTime, sleBGPInfoNexthopTriggerStatus, sleBGPInfoNexthopTriggerDelay,
				sleBGPInfoSnmpNotification, sleBGPInfoUpdateDelay, sleBGPInfoExternalRouteDistance, sleBGPInfoInternalRouteDistance, sleBGPInfoLocalRouteDistance,
				sleBGPInfoMaximumPath, sleBGPInfoMaximumPathIBGP, sleBGPInfoKeepAliveInterval, sleBGPInfoHoldTime, sleBGPInfoControlRequest,
				sleBGPInfoControlStatus, sleBGPInfoControlTimer, sleBGPInfoControlTimeStamp, sleBGPInfoControlReqResult, sleBGPInfoControlRouterID,
				sleBGPInfoControlLogNeighborChange, sleBGPInfoControlAlwaysCompareMed, sleBGPInfoControlBestPathAsPathIgnore, sleBGPInfoControlBestPathCompareConfedAsPath, sleBGPInfoControlBestPathCompareRouterID,
				sleBGPInfoControlBestPathCompareMedConfed, sleBGPInfoControlBestPathCompareMedMisAsWorst, sleBGPInfoControlClientToClient, sleBGPInfoControlClusterID, sleBGPInfoControlConfederationID,
				sleBGPInfoControlDeterministicMed, sleBGPInfoControlEnforceFirstAs, sleBGPInfoControlFastExternalFailOver, sleBGPInfoControlGracefulRestartTime, sleBGPInfoControlGracefulStalepathTime,
				sleBGPInfoControlScanTime, sleBGPInfoControlNexthopTriggerStatus, sleBGPInfoControlNexthopTriggerDelay, sleBGPInfoControlSnmpNotification, sleBGPInfoControlUpdateDelay,
				sleBGPInfoControlExternalRouteDistance, sleBGPInfoControlInternalRouteDistance, sleBGPInfoControlLocalRouteDistance, sleBGPInfoControlMaximumPath, sleBGPInfoControlMaximumPathIBGP,
				sleBGPInfoControlKeepAliveInterval, sleBGPInfoControlHoldTime, sleBGPAdminDistanceAddrPrefix, sleBGPAdminDistanceValue, sleBGPAdminDistanceAccName,
				sleBGPAdminDistanceControlRequest, sleBGPAdminDistanceControlStatus, sleBGPAdminDistanceControlTimer, sleBGPAdminDistanceControlTimeStamp, sleBGPAdminDistanceControlReqResult,
				sleBGPAdminDistanceControlAddrPrefix, sleBGPAdminDistanceControlValue, sleBGPAdminDistanceControlAccName, sleBGPPeerName, sleBGPPeerAsNum,
				sleBGPPeerGroupName, sleBGPPeerAdvInterval, sleBGPPeerAsOriInterval, sleBGPPeerDesc, sleBGPPeerDontCapNego,
				sleBGPPeerWeight, sleBGPPeerEnforcMultiHop, sleBGPPeerPassive, sleBGPPeerUpSourceName, sleBGPPeerPort,
				sleBGPPeerRetstartTime, sleBGPPeerShutDown, sleBGPPeerKeepInterval, sleBGPPeerHoldInterval, sleBGPPeerConnInterval,
				sleBGPPeerOverCap, sleBGPPeerStrictCapMatch, sleBGPPeerIfname, sleBGPPeerCapRouteRefresh, sleBGPPeerCapDynamic,
				sleBGPPeerEBGPMulthopCount, sleBGPPeerPassword, sleBGPPeerControlRequest, sleBGPPeerControlStatus, sleBGPPeerControlTimer,
				sleBGPPeerControlTimeStamp, sleBGPPeerControlReqResult, sleBGPPeerControlName, sleBGPPeerControlAsNum, sleBGPPeerControlGroupName,
				sleBGPPeerControlAdvInterval, sleBGPPeerControlAsOriInterval, sleBGPPeerControlDesc, sleBGPPeerControlDontCapNego, sleBGPPeerControlWeight,
				sleBGPPeerControlEnforcMultiHop, sleBGPPeerControlPassive, sleBGPPeerControlUpSourceName, sleBGPPeerControlPort, sleBGPPeerControlRetstartTime,
				sleBGPPeerControlShutDown, sleBGPPeerControlKeepInterval, sleBGPPeerControlHoldInterval, sleBGPPeerControlConnInterval, sleBGPPeerControlOverCap,
				sleBGPPeerControlStrictCapMatch, sleBGPPeerControlIfname, sleBGPPeerControlCapRouteRefresh, sleBGPPeerControlCapDynamic, sleBGPPeerControlEBGPMulthopCount,
				sleBGPPeerControlPassword, sleBGPPeerGroupStr, sleBGPPeerGroupAsNum, sleBGPPeerGroupAdvInterval, sleBGPPeerGroupAsOriInterval,
				sleBGPPeerGroupDesc, sleBGPPeerGroupDontCapNego, sleBGPPeerGroupWeight, sleBGPPeerGroupEnforcMultiHop, sleBGPPeerGroupPassive,
				sleBGPPeerGroupUpSourceName, sleBGPPeerGroupPort, sleBGPPeerGroupRetstartTime, sleBGPPeerGroupShutDown, sleBGPPeerGroupKeepInterval,
				sleBGPPeerGroupHoldInterval, sleBGPPeerGroupConnInterval, sleBGPPeerGroupOverCap, sleBGPPeerGroupStrictCapMatch, sleBGPPeerGroupCapRouteRefresh,
				sleBGPPeerGroupCapDynamic, sleBGPPeerGroupEBGPMulthopCount, sleBGPPeerGroupPassword, sleBGPPeerGroupControlRequest, sleBGPPeerGroupControlStatus,
				sleBGPPeerGroupControlTimer, sleBGPPeerGroupControlTimeStamp, sleBGPPeerGroupControlReqResult, sleBGPPeerGroupControlStr, sleBGPPeerGroupControlAsNum,
				sleBGPPeerGroupControlAdvInterval, sleBGPPeerGroupControlAsOriInterval, sleBGPPeerGroupControlDesc, sleBGPPeerGroupControlDontCapNego, sleBGPPeerGroupControlWeight,
				sleBGPPeerGroupControlEnforcMultiHop, sleBGPPeerGroupControlPassive, sleBGPPeerGroupControlUpSourceName, sleBGPPeerGroupControlPort, sleBGPPeerGroupControlRetstartTime,
				sleBGPPeerGroupControlShutDown, sleBGPPeerGroupControlKeepInterval, sleBGPPeerGroupControlHoldInterval, sleBGPPeerGroupControlConnInterval, sleBGPPeerGroupControlOverCap,
				sleBGPPeerGroupControlStrictCapMatch, sleBGPPeerGroupControlCapRouteRefresh, sleBGPPeerGroupControlCapDynamic, sleBGPPeerGroupControlEBGPMulthopCount, sleBGPPeerGroupControlPassword,
				sleBGPAFBaseMode, sleBGPAFBaseType, sleBGPAFBaseNetworkCheck, sleBGPAFBaseSync, sleBGPAFBaseDefOrg,
				sleBGPAFBaseDampRoutemapName, sleBGPAFBaseDampReachHlife, sleBGPAFBaseDampReuse, sleBGPAFBaseDampSuppress, sleBGPAFBaseDampMaxSuppress,
				sleBGPAFBaseDampUnReachHlife, sleBGPAFBaseControlRequest, sleBGPAFBaseControlStatus, sleBGPAFBaseControlTimer, sleBGPAFBaseControlTimeStamp,
				sleBGPAFBaseControlReqResult, sleBGPAFBaseControlMode, sleBGPAFBaseControlType, sleBGPAFBaseControlNetworkCheck, sleBGPAFBaseControlSync,
				sleBGPAFBaseControlDefOrg, sleBGPAFBaseControlDampRoutemapName, sleBGPAFBaseControlDampReachHlife, sleBGPAFBaseControlDampReuse, sleBGPAFBaseControlDampSuppress,
				sleBGPAFBaseControlDampMaxSuppress, sleBGPAFBaseControlDampUnReachHlife, sleBGPAFRedistMode, sleBGPAFRedistType, sleBGPAFRedistProtoType,
				sleBGPAFRedistRoutemapName, sleBGPAFRedistControlRequest, sleBGPAFRedistControlStatus, sleBGPAFRedistControlTimer, sleBGPAFRedistControlTimeStamp,
				sleBGPAFRedistControlReqResult, sleBGPAFRedistControlMode, sleBGPAFRedistControlType, sleBGPAFRedistControlProtoType, sleBGPAFRedistControlRoutemapName,
				sleBGPAFAggreAddrMode, sleBGPAFAggreAddrType, sleBGPAFAggreAddrPrefix, sleBGPAFAggreAddrAsSet, sleBGPAFAggreAddrSummOnly,
				sleBGPAFAggreAddrControlRequest, sleBGPAFAggreAddrControlStatus, sleBGPAFAggreAddrControlTimer, sleBGPAFAggreAddrControlTimeStamp, sleBGPAFAggreAddrControlReqResult,
				sleBGPAFAggreAddrControlMode, sleBGPAFAggreAddrControlType, sleBGPAFAggreAddrControlAddrPrefix, sleBGPAFAggreAddrControlAsSet, sleBGPAFAggreAddrControlSummOnly,
				sleBGPAFPeerMode, sleBGPAFPeerType, sleBGPAFPeerName, sleBGPAFPeerActviate, sleBGPAFPeerAllowAsIn,
				sleBGPAFPeerAllowAsInNum, sleBGPAFPeerAttrUnchangedAsPath, sleBGPAFPeerAttrUnchangedMed, sleBGPAFPeerAttrUnchangedNexthop, sleBGPAFPeerCapGracefulRestart,
				sleBGPAFPeerCapOrfMode, sleBGPAFPeerDefOriginate, sleBGPAFPeerDefOriginateRoutemap, sleBGPAFPeerFLInAccName, sleBGPAFPeerFLOutAccName,
				sleBGPAFPeerMaxPrefixNum, sleBGPAFPeerMaxPrefixThreshold, sleBGPAFPeerMaxPrefixWarnOnly, sleBGPAFPeerRemotePrivateAs, sleBGPAFPeerInRoutemap,
				sleBGPAFPeerOutRoutemap, sleBGPAFPeerRouteReflectClient, sleBGPAFPeerRouteServerClient, sleBGPAFPeerInDistListName, sleBGPAFPeerOutDistListName,
				sleBGPAFPeerInPrefixListName, sleBGPAFPeerOutPrefixListName, sleBGPAFPeerSendCommunity, sleBGPAFPeerNexthopSelf, sleBGPAFPeerSoftReconfig,
				sleBGPAFPeerUnsuppressMapName, sleBGPAFPeerControlRequest, sleBGPAFPeerControlStatus, sleBGPAFPeerControlTimer, sleBGPAFPeerControlTimeStamp,
				sleBGPAFPeerControlReqResult, sleBGPAFPeerControlMode, sleBGPAFPeerControlType, sleBGPAFPeerControlName, sleBGPAFPeerControlActviate,
				sleBGPAFPeerControlAllowAsIn, sleBGPAFPeerControlAllowAsInNum, sleBGPAFPeerControlAttrUnchangedAsPath, sleBGPAFPeerControlAttrUnchangedMed, sleBGPAFPeerControlAttrUnchangedNexthop,
				sleBGPAFPeerControlCapGracefulRestart, sleBGPAFPeerControlCapOrfMode, sleBGPAFPeerControlDefOriginate, sleBGPAFPeerControlDefOriginateRoutemap, sleBGPAFPeerControlFLInAccName,
				sleBGPAFPeerControlFLOutAccName, sleBGPAFPeerControlMaxPrefixNum, sleBGPAFPeerControlMaxPrefixThreshold, sleBGPAFPeerControlMaxPrefixWarnOnly, sleBGPAFPeerControlRemotePrivateAs,
				sleBGPAFPeerControlInRoutemap, sleBGPAFPeerControlOutRoutemap, sleBGPAFPeerControlRouteReflectClient, sleBGPAFPeerControlRouteServerClient, sleBGPAFPeerControlInDistListName,
				sleBGPAFPeerControlOutDistListName, sleBGPAFPeerControlInPrefixListName, sleBGPAFPeerControlOutPrefixListName, sleBGPAFPeerControlSendCommunity, sleBGPAFPeerControlNexthopSelf,
				sleBGPAFPeerControlSoftReconfig, sleBGPAFPeerControlUnsuppressMapName, sleBGPAFPeerGroupMode, sleBGPAFPeerGroupType, sleBGPAFPeerGroupName,
				sleBGPAFPeerGroupActviate, sleBGPAFPeerGroupAllowAsIn, sleBGPAFPeerGroupAllowAsInNum, sleBGPAFPeerGroupAttrUnchangedAsPath, sleBGPAFPeerGroupAttrUnchangedMed,
				sleBGPAFPeerGroupAttrUnchangedNexthop, sleBGPAFPeerGroupCapGracefulRestart, sleBGPAFPeerGroupCapOrfMode, sleBGPAFPeerGroupDefOriginate, sleBGPAFPeerGroupDefOriginateRoutemap,
				sleBGPAFPeerGroupFLInAccName, sleBGPAFPeerGroupFLOutAccName, sleBGPAFPeerGroupMaxPrefixNum, sleBGPAFPeerGroupMaxPrefixThreshold, sleBGPAFPeerGroupMaxPrefixWarnOnly,
				sleBGPAFPeerGroupRemotePrivateAs, sleBGPAFPeerGroupInRoutemap, sleBGPAFPeerGroupOutRoutemap, sleBGPAFPeerGroupRouteReflectClient, sleBGPAFPeerGroupRouteServerClient,
				sleBGPAFPeerGroupInDistListName, sleBGPAFPeerGroupOutDistListName, sleBGPAFPeerGroupInPrefixListName, sleBGPAFPeerGroupOutPrefixListName, sleBGPAFPeerGroupSendCommunity,
				sleBGPAFPeerGroupNexthopSelf, sleBGPAFPeerGroupSoftReconfig, sleBGPAFPeerGroupUnsuppressMapName, sleBGPAFPeerGroupControlRequest, sleBGPAFPeerGroupControlStatus,
				sleBGPAFPeerGroupControlTimer, sleBGPAFPeerGroupControlTimeStamp, sleBGPAFPeerGroupControlReqResult, sleBGPAFPeerGroupControlMode, sleBGPAFPeerGroupControlType,
				sleBGPAFPeerGroupControlName, sleBGPAFPeerGroupControlActviate, sleBGPAFPeerGroupControlAllowAsIn, sleBGPAFPeerGroupControlAllowAsInNum, sleBGPAFPeerGroupControlAttrUnchangedAsPath,
				sleBGPAFPeerGroupControlAttrUnchangedMed, sleBGPAFPeerGroupControlAttrUnchangedNexthop, sleBGPAFPeerGroupControlCapGracefulRestart, sleBGPAFPeerGroupControlCapOrfMode, sleBGPAFPeerGroupControlDefOriginate,
				sleBGPAFPeerGroupControlDefOriginateRoutemap, sleBGPAFPeerGroupControlFLInAccName, sleBGPAFPeerGroupControlFLOutAccName, sleBGPAFPeerGroupControlMaxPrefixNum, sleBGPAFPeerGroupControlMaxPrefixThreshold,
				sleBGPAFPeerGroupControlMaxPrefixWarnOnly, sleBGPAFPeerGroupControlRemotePrivateAs, sleBGPAFPeerGroupControlInRoutemap, sleBGPAFPeerGroupControlOutRoutemap, sleBGPAFPeerGroupControlRouteReflectClient,
				sleBGPAFPeerGroupControlRouteServerClient, sleBGPAFPeerGroupControlInDistListName, sleBGPAFPeerGroupControlOutDistListName, sleBGPAFPeerGroupControlInPrefixListName, sleBGPAFPeerGroupControlOutPrefixListName,
				sleBGPAFPeerGroupControlSendCommunity, sleBGPAFPeerGroupControlNexthopSelf, sleBGPAFPeerGroupControlSoftReconfig, sleBGPAFPeerGroupControlUnsuppressMapName, sleBGPAFNetworkMode,
				sleBGPAFNetworkType, sleBGPAFNetworkAddrPrefix, sleBGPAFNetworkBackdoor, sleBGPAFNetworkRoutemap, sleBGPAFNetworkControlRequest,
				sleBGPAFNetworkControlStatus, sleBGPAFNetworkControlTimer, sleBGPAFNetworkControlTimeStamp, sleBGPAFNetworkControlReqResult, sleBGPAFNetworkControlMode,
				sleBGPAFNetworkControlType, sleBGPAFNetworkControlAddrPrefix, sleBGPAFNetworkControlBackdoor, sleBGPAFNetworkControlRoutemap, sleBGPStatusPeerV4Name,
				sleBGPStatusPeerV4RemoteAs, sleBGPStatusPeerV4LocalAs, sleBGPStatusPeerV4LinkState, sleBGPStatusPeerV4State, sleBGPStatusPeerV4HoldTime,
				sleBGPStatusPeerV4KeepAlive, sleBGPStatusPeerV4Uptime, sleBGPStatusPeerV4LastReadTime, sleBGPStatusPeerV4RecvMessageCount, sleBGPStatusPeerV4RecvNotificationCount,
				sleBGPStatusPeerV4SentMessageCount, sleBGPStatusPeerV4SentNotificationCount, sleBGPStatusPeerV4RouteRefreshRecvRequestCount, sleBGPStatusPeerV4RouteRefreshSentRequestCount, sleBGPStatusPeerV4RouteAdvTime,
				sleBGPStatusPeerV4EstablishedCount, sleBGPStatusPeerV4DroppedCount, sleBGPStatusPeerV4EBgpMultihopCount, sleBGPStatusPeerV4LocalHost, sleBGPStatusPeerV4LocalPort,
				sleBGPStatusPeerV4ForeignHost, sleBGPStatusPeerV4ForeignPort, sleBGPStatusPeerV4RemainNextConnTime, sleBGPStatusPeerV6Name, sleBGPStatusPeerV6RemoteAs,
				sleBGPStatusPeerV6LocalAs, sleBGPStatusPeerV6LinkState, sleBGPStatusPeerV6State, sleBGPStatusPeerV6HoldTime, sleBGPStatusPeerV6KeepAlive,
				sleBGPStatusPeerV6Uptime, sleBGPStatusPeerV6LastReadTime, sleBGPStatusPeerV6RecvMessageCount, sleBGPStatusPeerV6RecvNotificationCount, sleBGPStatusPeerV6SentMessageCount,
				sleBGPStatusPeerV6SentNotificationCount, sleBGPStatusPeerV6RouteRefreshRecvRequestCount, sleBGPStatusPeerV6RouteRefreshSentRequestCount, sleBGPStatusPeerV6RouteAdvTime, sleBGPStatusPeerV6EstablishedCount,
				sleBGPStatusPeerV6DroppedCount, sleBGPStatusPeerV6EBgpMultihopCount, sleBGPStatusPeerV6LocalHost, sleBGPStatusPeerV6LocalPort, sleBGPStatusPeerV6ForeignHost,
				sleBGPStatusPeerV6ForeignPort, sleBGPStatusPeerV6RemainNextConnTime, sleBGPRoutesV4SAFIType, sleBGPRoutesV4RoutePrefix, sleBGPRoutesV4Nexthop,
				sleBGPRoutesV4NexthopMed, sleBGPRoutesV4NexthopLocPref, sleBGPRoutesV4NexthopWeight, sleBGPRoutesV4NexthopSuppress, sleBGPRoutesV4NexthopValid,
				sleBGPRoutesV4NexthopStale, sleBGPRoutesV4NexthopDamped, sleBGPRoutesV4NexthopStaleHistory, sleBGPRoutesV4NexthopSelected, sleBGPRoutesV4NexthopInternal,
				sleBGPRoutesV6SAFIType, sleBGPRoutesV6RoutePrefix, sleBGPRoutesV6Nexthop, sleBGPRoutesV6NexthopMed, sleBGPRoutesV6NexthopLocPref,
				sleBGPRoutesV6NexthopWeight, sleBGPRoutesV6NexthopSuppress, sleBGPRoutesV6NexthopValid, sleBGPRoutesV6NexthopStale, sleBGPRoutesV6NexthopDamped,
				sleBGPRoutesV6NexthopStaleHistory, sleBGPRoutesV6NexthopSelected, sleBGPRoutesV6NexthopInternal, sleBGPStatusPeerV4RouterID, sleBGPStatusPeerV6RouterID
				 }
			STATUS current
			DESCRIPTION
				"Description."
			::= { sleBGP 7 }


		-- 1.3.6.1.4.1.6296.101.53.8
		sleBGPNotificationGroup NOTIFICATION-GROUP
			NOTIFICATIONS { sleBGPBaseAsModeCreated, sleBGPBaseAsModeDeleted, sleBGPBaseConfigTypeChanged, sleBGPBaseRfc1771PathSelectChanged, sleBGPBaseRfc1771StrictChanged,
				sleBGPBaseAggregateNextHopChanged, sleBGPBaseExtendAsnCapChanged, sleBGPBaseAllCleared, sleBGPBaseAsNumberCleared, sleBGPBasePeerCleared,
				sleBGPBaseDampCleared, sleBGPBaseExternalCleared, sleBGPBaseViewCleared, sleBGPInfoRouterIDCreated, sleBGPInfoRouterIDDeleted,
				sleBGPInfoLogNeighborChanged, sleBGPInfoAlwaysCompareMedChanged, sleBGPInfoBestPathAsPathIgnoreChanged, sleBGPInfoBestPathCompareConfedAsPathChanged, sleBGPInfoBestPathCompareRouterIDChanged,
				sleBGPInfoBestPathCompareMedConfedChanged, sleBGPInfoBestPathCompareMedMisAsWorstChanged, sleBGPInfoClientToClientChanged, sleBGPInfoClusterIDCreated, sleBGPInfoClusterIDDeleted,
				sleBGPInfoConfederationIDChanged, sleBGPInfoDeterministicMedChanged, sleBGPInfoEnforceFirstAsChanged, sleBGPInfoFastExternalFailOverChanged, sleBGPInfoGracefulRestartProfileChanged,
				sleBGPInfoScanTimeChanged, sleBGPInfoNexthopTriggerStatusChanged, sleBGPInfoNexthopTriggerDelayChanged, sleBGPInfoSnmpNotificationChanged, sleBGPInfoUpdateDelayChanged,
				sleBGPInfoDistanceCreated, sleBGPInfoDistanceDeleted, sleBGPInfoMaximumPathChanged, sleBGPInfoMaximumPathIBGPChanged, sleBGPInfoTimersChanged,
				sleBGPAdminDistanceCreated, sleBGPAdminDistanceDeleted, sleBGPPeerCreated, sleBGPPeerDeleted, sleBGPPeerGroupNameCreated,
				sleBGPPeerGroupNameDeleted, sleBGPPeerAdvIntervalChanged, sleBGPPeerAsOriIntervalChanged, sleBGPPeerDescCreated, sleBGPPeerDescDeleted,
				sleBGPPeerDontCapNegoChanged, sleBGPPeerWeightChanged, sleBGPPeerEnforcMultiHopChanged, sleBGPPeerPassiveChanged, sleBGPPeerUpSourceCreated,
				sleBGPPeerUpSourceDeleted, sleBGPPeerPortChanged, sleBGPPeerRetstartTimeChanged, sleBGPPeerShutDownChanged, sleBGPPeerTimersProfileChanged,
				sleBGPPeerConnIntervalChanged, sleBGPPeerOverCapChanged, sleBGPPeerStrictCapMatchChanged, sleBGPPeerIfnameCreated, sleBGPPeerIfnameDeleted,
				sleBGPPeerCapRouteRefreshChanged, sleBGPPeerCapDynamicChanged, sleBGPPeerEBGPMultihopCountChanged, sleBGPPeerPasswordCreated, sleBGPPeerPasswordDeleted,
				sleBGPPeerGroupCreated, sleBGPPeerGroupDeleted, sleBGPPeerGroupRemoteAsChanged, sleBGPPeerGroupAdvIntervalChanged, sleBGPPeerGroupAsOriIntervalChanged,
				sleBGPPeerGroupDescCreated, sleBGPPeerGroupDescDeleted, sleBGPPeerGroupDontCapNegoChanged, sleBGPPeerGroupWeightChanged, sleBGPPeerGroupPassiveChanged,
				sleBGPPeerGroupUpSourceCreated, sleBGPPeerGroupUpSourceDeleted, sleBGPPeerGroupPortChanged, sleBGPPeerGroupRetstartTimeChanged, sleBGPPeerGroupShutDownChanged,
				sleBGPPeerGroupTimersProfileChanged, sleBGPPeerGroupConnIntervalChanged, sleBGPPeerGroupOverCapChanged, sleBGPPeerGroupStrictCapMatchChanged, sleBGPPeerGroupCapRouteRefreshChanged,
				sleBGPPeerGroupCapDynamicChanged, sleBGPPeerGroupEBGPMultihopCountChanged, sleBGPPeerGroupPasswordCreated, sleBGPPeerGroupPasswordDeleted, sleBGPAFBaseNetworkCheckChanged,
				sleBGPAFBaseSyncChanged, sleBGPAFBaseDefOrgChanged, sleBGPAFBaseDampRoutemapNameChanged, sleBGPAFBaseDampTimeProfileChanged, sleBGPAFBaseDampDeleted,
				sleBGPAFRedistributeCreated, sleBGPAFRedistributeDeleted, sleBGPAFRedistributeChanged, sleBGPAFAggreAddressCreated, sleBGPAFAggreAddressDeleted,
				sleBGPAFPeerActviateChanged, sleBGPAFPeerAllowAsInChanged, sleBGPAFPeerAttrUnchangedProfileChanged, sleBGPAFPeerCapGracefulRestartChanged, sleBGPAFPeerCapOrfModeChanged,
				sleBGPAFPeerDefOriginateChanged, sleBGPAFPeerFLInAccNameChanged, sleBGPAFPeerFLOutAccNameChanged, sleBGPAFPeerMaxPrefixProfileChanged, sleBGPAFPeerRemotePrivateAsChanged,
				sleBGPAFPeerInRoutemapChanged, sleBGPAFPeerOutRoutemapChanged, sleBGPAFPeerRouteReflectClientChanged, sleBGPAFPeerRouteServerClientChanged, sleBGPAFPeerInDistListNameChanged,
				sleBGPAFPeerOutDistListNameChanged, sleBGPAFPeerInPrefixListNameChanged, sleBGPAFPeerOutPrefixListNameChanged, sleBGPAFPeerSendCommunityChanged, sleBGPAFPeerNexthopSelfChanged,
				sleBGPAFPeerSoftReconfigChanged, sleBGPAFPeerUnsuppressMapNameChanged, sleBGPAFPeerGroupActviateChanged, sleBGPAFPeerGroupAllowAsInChanged, sleBGPAFPeerGroupAttrUnchangedProfileChanged,
				sleBGPAFPeerGroupCapGracefulRestartChanged, sleBGPAFPeerGroupCapOrfModeChanged, sleBGPAFPeerGroupDefOriginateChanged, sleBGPAFPeerGroupFLInAccNameChanged, sleBGPAFPeerGroupFLOutAccNameChanged,
				sleBGPAFPeerGroupMaxPrefixProfileChanged, sleBGPAFPeerGroupRemotePrivateAsChanged, sleBGPAFPeerGroupInRoutemapChanged, sleBGPAFPeerGroupOutRoutemapChanged, sleBGPAFPeerGroupRouteReflectClientChanged,
				sleBGPAFPeerGroupRouteServerClientChanged, sleBGPAFPeerGroupInDistListNameChanged, sleBGPAFPeerGroupOutDistListNameChanged, sleBGPAFPeerGroupInPrefixListNameChanged, sleBGPAFPeerGroupOutPrefixListNameChanged,
				sleBGPAFPeerGroupSendCommunityChanged, sleBGPAFPeerGroupNexthopSelfChanged, sleBGPAFPeerGroupSoftReconfigChanged, sleBGPAFPeerGroupUnsuppressMapNameChanged, sleBGPAFNetworkCreated,
				sleBGPAFNetworkDeleted }
			STATUS current
			DESCRIPTION
				"Description."
			::= { sleBGP 8 }



	END

--
-- sle-bgp-mib.mib
--
