--
-- SLE-GPON-MIB.my
-- MIB generated by MG-SOFT Visual MIB Builder Version 6.0  Build 88
-- Wednesday, March 30, 2016 at 16:08:10
--

--  SLE-GPON-MIB.my
-- MIB generated by MG-SOFT Visual MIB Builder Version 6.0  Build 88
-- Sunday, May 04, 2014 at 14:28:05
--
--  sle-gpon-mib.mib
-- MIB generated by MG-SOFT Visual MIB Builder Version 6.0  Build 88
-- Friday, December 24, 2010 at 11:42:45
--

	SLE-GPON-MIB DEFINITIONS ::= BEGIN

		IMPORTS
			sleMgmt
				FROM DASAN-SMI
			SleControlStatusType, SleControlRequestResultType
				FROM SLE-TC-MIB
			OBJECT-GROUP, NOTIFICATION-GROUP
				FROM SNMPv2-CONF
			TimeTicks, IpAddress, Integer32, Unsigned32, Gauge32,
			Counter32, Counter64, BITS, OBJECT-TYPE, MODULE-IDENTITY,
			NOTIFICATION-TYPE
				FROM SNMPv2-SMI
			TEXTUAL-CONVENTION
				FROM SNMPv2-TC;


--   1.3.6.1.4.1.6296.101.23
-- January 25, 2006 at 17:53 GMT
-- 1.3.6.1.4.1.6296.101.23
-- January 25, 2006 at 17:53 GMT
		sleGpon MODULE-IDENTITY
			LAST-UPDATED "200601251753Z"		-- January 25, 2006 at 17:53 GMT
			ORGANIZATION
				"Organization."
			CONTACT-INFO
				"Contact-info."
			DESCRIPTION
				"sle Gpon"
			::= { sleMgmt 23 }



--
-- Textual conventions
--

--  Textual conventions
--
-- Textual conventions
--
-- Textual conventions
--
-- Textual conventions
--
		EnableFlag ::= TEXTUAL-CONVENTION
			STATUS current
			DESCRIPTION
				"Description."
			SYNTAX INTEGER
				{
				enable(1),
				disable(2)
				}

		InetAddressType ::= TEXTUAL-CONVENTION
			STATUS current
			DESCRIPTION
				"A value that represents a type of Internet address.
				unknown(0)  An unknown address type. This value MUST
				            be used if the value of the corresponding
				            InetAddress object is a zero-length string.
				            It may also be used to indicate an IP address
				            which is not in one of the formats defined
				            below.

				ipv4(1)     An IPv4 address as defined by the
				            InetAddressIPv4 textual convention.

				ipv6(2)     A global IPv6 address as defined by the
				            InetAddressIPv6 textual convention.

				ipv4z(3)    A non-global IPv4 address including a zone
				            index as defined by the InetAddressIPv4z
				            textual convention.

				ipv6z(4)    A non-global IPv6 address including a zone
				            index as defined by the InetAddressIPv6z
				            textual convention.

				dns(16)     A DNS domain name as defined by the
				            InetAddressDNS textual convention.

				Each definition of a concrete InetAddressType value must be
				accompanied by a definition of a textual convention for use
				with that InetAddressType.

				To support future extensions, the InetAddressType textual
				convention SHOULD NOT be sub-typed in object type definitions.
				It MAY be sub-typed in compliance statements in order to
				require only a subset of these address types for a compliant
				implementation.

				Implementations must ensure that InetAddressType objects

				and any dependent objects (e.g. InetAddress objects) are
				consistent.  An inconsistentValue error must be generated
				if an attempt to change an InetAddressType object would,
				for example, lead to an undefined InetAddress value.  In
				particular, InetAddressType/InetAddress pairs must be
				changed together if the address type changes (e.g. from
				ipv6(2) to ipv4(1))."
			SYNTAX INTEGER
				{
				unknown(0),
				ipv4(1),
				ipv6(2),
				ipv4z(3),
				ipv6z(4),
				dns(16)
				}

		InetAddress ::= TEXTUAL-CONVENTION
			STATUS current
			DESCRIPTION
				"Denotes a generic Internet address.

				An InetAddress value is always interpreted within the context
				of an InetAddressType value. Every usage of the InetAddress
				textual convention is required to specify the InetAddressType
				object which provides the context.  It is suggested that the
				InetAddressType object is logically registered before the
				object(s) which use the InetAddress textual convention if
				they appear in the same logical row.

				The value of an InetAddress object must always be
				consistent with the value of the associated InetAddressType
				object. Attempts to set an InetAddress object to a value
				which is inconsistent with the associated InetAddressType
				must fail with an inconsistentValue error.

				When this textual convention is used as the syntax of an
				index object, there may be issues with the limit of 128
				sub-identifiers specified in SMIv2, STD 58. In this case,
				the object definition MUST include a 'SIZE' clause to
				limit the number of potential instance sub-identifiers."
			SYNTAX OCTET STRING (SIZE (0..255))

		InetAddressPrefixLength ::= TEXTUAL-CONVENTION
			STATUS current
			DESCRIPTION
				"Denotes the length of a generic Internet network address
				prefix. A value of n corresponds to an IP address mask
				which has n contiguous 1-bits from the most significant
				bit (MSB) and all other bits set to 0.

				An InetAddressPrefixLength value is always interpreted within
				the context of an InetAddressType value. Every usage of the
				InetAddressPrefixLength textual convention is required to
				specify the InetAddressType object which provides the
				context.  It is suggested that the InetAddressType object is
				logically registered before the object(s) which use the
				InetAddressPrefixLength textual convention if they appear in
				the same logical row.

				InetAddressPrefixLength values that are larger than
				the maximum length of an IP address for a specific
				InetAddressType are treated as the maximum significant
				value applicable for the InetAddressType. The maximum
				significant value is 32 for the InetAddressType
				'ipv4(1)' and 'ipv4z(3)' and 128 for the InetAddressType
				'ipv6(2)' and 'ipv6z(4)'. The maximum significant value
				for the InetAddressType 'dns(16)' is 0.

				The value zero is object-specific and must be defined as
				part of the description of any object which uses this
				syntax. Examples of the usage of zero might include
				situations where the Internet network address prefix
				is unknown or does not apply."
			SYNTAX Unsigned32


--
-- Node definitions
--

--  Node definitions
--
-- Node definitions
--
-- Node definitions
--
-- 1.3.6.1.4.1.6296.101.23.1
-- 1.3.6.1.4.1.6296.101.23.1
		sleGponBase OBJECT IDENTIFIER ::= { sleGpon 1 }


--    1.3.6.1.4.1.6296.101.23.1.1
-- 1.3.6.1.4.1.6296.101.23.1.1
-- 1.3.6.1.4.1.6296.101.23.1.1
		sleGponBaseInfo OBJECT IDENTIFIER ::= { sleGponBase 1 }


--    1.3.6.1.4.1.6296.101.23.1.1.1
-- 1.3.6.1.4.1.6296.101.23.1.1.1
-- 1.3.6.1.4.1.6296.101.23.1.1.1
		sleGponCableDownStatus OBJECT-TYPE
			SYNTAX EnableFlag
			MAX-ACCESS read-only
			STATUS current
			DESCRIPTION
				"cable-down admin status"
			::= { sleGponBaseInfo 1 }


--    1.3.6.1.4.1.6296.101.23.1.1.2
-- 1.3.6.1.4.1.6296.101.23.1.1.2
-- 1.3.6.1.4.1.6296.101.23.1.1.2
		sleGponCableDownRefCount OBJECT-TYPE
			SYNTAX Integer32
			MAX-ACCESS read-only
			STATUS current
			DESCRIPTION
				"cable-down reference count"
			::= { sleGponBaseInfo 2 }


--    1.3.6.1.4.1.6296.101.23.1.1.3
-- 1.3.6.1.4.1.6296.101.23.1.1.3
-- 1.3.6.1.4.1.6296.101.23.1.1.3
		sleGponDefaultServiceProfile OBJECT-TYPE
			SYNTAX OCTET STRING
			MAX-ACCESS read-only
			STATUS current
			DESCRIPTION
				"The default service profile."
			::= { sleGponBaseInfo 3 }


--   1.3.6.1.4.1.6296.101.23.1.1.4
-- 1.3.6.1.4.1.6296.101.23.1.1.4
		sleGponSystemOltVendorId OBJECT-TYPE
			SYNTAX OCTET STRING (SIZE (1..4))
			MAX-ACCESS read-only
			STATUS current
			DESCRIPTION
				"The OLT Vendor ID.
				Only valid in case that this equipment is used as ONT."
			::= { sleGponBaseInfo 4 }


--   1.3.6.1.4.1.6296.101.23.1.1.5
-- sleGponSystemOltEquipId OBJECT-TYPE
-- 	SYNTAX OCTET STRING (SIZE (1..20))
-- 	MAX-ACCESS read-only
-- 	STATUS current
-- 	DESCRIPTION
-- 		"The OLT Equipment ID.
-- 		Only valid in case that this equipment is used as ONT."
-- 	::= { sleGponBaseInfo 5 }
-- 1.3.6.1.4.1.6296.101.23.1.1.5
-- 1.3.6.1.4.1.6296.101.23.1.1.5
		sleGponSystemOltVersion OBJECT-TYPE
			SYNTAX OCTET STRING (SIZE (1..14))
			MAX-ACCESS read-only
			STATUS current
			DESCRIPTION
				"The OLT Version Info.
				Only valid in case that this equipment is used as ONT."
			::= { sleGponBaseInfo 5 }


--  1.3.6.1.4.1.6296.101.23.1.1.6
		sleGponSystemOltModel OBJECT-TYPE
			SYNTAX OCTET STRING
			MAX-ACCESS read-only
			STATUS current
			DESCRIPTION
				"The OLT Model.
				Only valid in case that this equipment is used as ONT."
			::= { sleGponBaseInfo 6 }


--  1.3.6.1.4.1.6296.101.23.1.1.7
		sleGponSystemOltMac OBJECT-TYPE
			SYNTAX OCTET STRING (SIZE (0..6))
			MAX-ACCESS read-only
			STATUS current
			DESCRIPTION
				"The OLT Mac address.
				Only valid in case that this equipment is used as ONT."
			::= { sleGponBaseInfo 7 }


--  1.3.6.1.4.1.6296.101.23.1.1.8
		sleGponSystemOltSlot OBJECT-TYPE
			SYNTAX Integer32
			MAX-ACCESS read-only
			STATUS current
			DESCRIPTION
				"The OLT Slot index.
				Only valid in case that this equipment is used as ONT."
			::= { sleGponBaseInfo 8 }


--  1.3.6.1.4.1.6296.101.23.1.1.9
		sleGponSystemOltPort OBJECT-TYPE
			SYNTAX Integer32
			MAX-ACCESS read-only
			STATUS current
			DESCRIPTION
				"The OLT Port index.
				Only valid in case that this equipment is used as ONT."
			::= { sleGponBaseInfo 9 }


--  1.3.6.1.4.1.6296.101.23.1.1.10
		sleGponSystemOltOnuId OBJECT-TYPE
			SYNTAX Integer32
			MAX-ACCESS read-only
			STATUS current
			DESCRIPTION
				"The OLT ONU index.
				Only valid in case that this equipment is used as ONT."
			::= { sleGponBaseInfo 10 }


--  1.3.6.1.4.1.6296.101.23.1.1.11
		sleGponOnuPasswordType OBJECT-TYPE
			SYNTAX INTEGER
				{
				hex(0),
				ascii(1)
				}
			MAX-ACCESS read-only
			STATUS current
			DESCRIPTION
				"The Password Type."
			::= { sleGponBaseInfo 11 }


--  1.3.6.1.4.1.6296.101.23.1.1.12
		sleGponOnuRxPowerUpdateTime OBJECT-TYPE
			SYNTAX Integer32 (0..1440)
			MAX-ACCESS read-only
			STATUS current
			DESCRIPTION
				"The ONU rx-power update Time
				0: disable
				1~1440: available values"
			::= { sleGponBaseInfo 12 }


--  1.3.6.1.4.1.6296.101.23.1.1.13
		sleGponOltMulticastGem OBJECT-TYPE
			SYNTAX Integer32 (4094..4095)
			MAX-ACCESS read-only
			STATUS current
			DESCRIPTION
				"The OLT multicast Gem."
			::= { sleGponBaseInfo 13 }


--  1.3.6.1.4.1.6296.101.23.1.1.14
		sleGponOltInterworkIgmpSnooping OBJECT-TYPE
			SYNTAX INTEGER
				{
				disable(0),
				enable(1)
				}
			MAX-ACCESS read-only
			STATUS current
			DESCRIPTION
				"The OLT interwork igmp-snooping"
			::= { sleGponBaseInfo 14 }


--  1.3.6.1.4.1.6296.101.23.1.1.15
		sleGponOnuRFPseudowireMode OBJECT-TYPE
			SYNTAX INTEGER
				{
				disable(0),
				enable(1)
				}
			MAX-ACCESS read-only
			STATUS current
			DESCRIPTION
				"The ONU RF Pseudowire Mode"
			::= { sleGponBaseInfo 15 }


--  1.3.6.1.4.1.6296.101.23.1.1.16
		sleGponOnuRFPseudowireDstMac OBJECT-TYPE
			SYNTAX OCTET STRING
			MAX-ACCESS read-only
			STATUS current
			DESCRIPTION
				"The Destination MAC address by ONU RF Pseudowire.
				This is valid when only sleGponOnuRFPseudowireMode is enable."
			::= { sleGponBaseInfo 16 }


--  1.3.6.1.4.1.6296.101.23.1.1.17
		sleGponOnuActiveMode OBJECT-TYPE
			SYNTAX INTEGER
				{
				serialNumber(1),
				registerationId(2)
				}
			MAX-ACCESS read-only
			STATUS current
			DESCRIPTION
				"The GPON ONU active mode"
			::= { sleGponBaseInfo 17 }


--  1.3.6.1.4.1.6296.101.23.1.1.18
		sleGponOnuRFPseudowireEthType OBJECT-TYPE
			SYNTAX Integer32 (0..65535)
			MAX-ACCESS read-only
			STATUS current
			DESCRIPTION
				"The RF Pseudowire Ethernet Type"
			::= { sleGponBaseInfo 18 }


--  1.3.6.1.4.1.6296.101.23.1.1.19
		sleGponOnuRFPseudowireVlanId OBJECT-TYPE
			SYNTAX Integer32 (0..4094)
			MAX-ACCESS read-only
			STATUS current
			DESCRIPTION
				"The RF Pseudowire vlan index"
			::= { sleGponBaseInfo 19 }


--  1.3.6.1.4.1.6296.101.23.1.1.20
		sleGponOltRxPowerUpdateTime OBJECT-TYPE
			SYNTAX Integer32 (1..1440)
			MAX-ACCESS read-only
			STATUS current
			DESCRIPTION
				"The OLT rx-power update cycle
				1~1440: available values
				"
			::= { sleGponBaseInfo 20 }


--  1.3.6.1.4.1.6296.101.23.1.1.21
		sleGponOnuAuthRadiusUserName OBJECT-TYPE
			SYNTAX INTEGER
				{
				serialNumber(1),
				modelName(2)
				}
			MAX-ACCESS read-only
			STATUS current
			DESCRIPTION
				"Onu authentication radius user name"
			::= { sleGponBaseInfo 21 }


		sleGponOnuAuthRadiusUserPassword OBJECT-TYPE
			SYNTAX INTEGER
				{
				modelName(1),
				serialNumber(2)
				}
			MAX-ACCESS read-only
			STATUS current
			DESCRIPTION
				"Onu authentication radius user password"
			::= { sleGponBaseInfo 22 }


		sleGponOnuReauthStartTime OBJECT-TYPE
			SYNTAX Integer32 (0..23)
			MAX-ACCESS read-only
			STATUS current
			DESCRIPTION
				"Onu reathentication start time(hour)"
			::= { sleGponBaseInfo 23 }


		sleGponOnuReauthEndTime OBJECT-TYPE
			SYNTAX Integer32 (0..23)
			MAX-ACCESS read-only
			STATUS current
			DESCRIPTION
				"Onu reathentication end time(hour)"
			::= { sleGponBaseInfo 24 }


		sleGponOnuAuthFailInterval1 OBJECT-TYPE
			SYNTAX Integer32 (1..60)
			MAX-ACCESS read-only
			STATUS current
			DESCRIPTION
				"Onu authentication attempt interval when authentication fails"
			::= { sleGponBaseInfo 25 }


		sleGponOnuAuthFailInterval2 OBJECT-TYPE
			SYNTAX Integer32 (1..60)
			MAX-ACCESS read-only
			STATUS current
			DESCRIPTION
				"Onu authentication attempt interval when authentication fails"
			::= { sleGponBaseInfo 26 }


		sleGponOnuAuthFailInterval3 OBJECT-TYPE
			SYNTAX Integer32 (1..60)
			MAX-ACCESS read-only
			STATUS current
			DESCRIPTION
				"Onu authentication attempt interval when authentication fails"
			::= { sleGponBaseInfo 27 }


		sleGponOnuAuthFailInterval4 OBJECT-TYPE
			SYNTAX Integer32 (1..60)
			MAX-ACCESS read-only
			STATUS current
			DESCRIPTION
				"Onu authentication attempt interval when authentication fails"
			::= { sleGponBaseInfo 28 }


		sleGponOnuAuthFailInterval5 OBJECT-TYPE
			SYNTAX Integer32
			MAX-ACCESS read-only
			STATUS current
			DESCRIPTION
				"Onu authentication attempt interval when authentication fails"
			::= { sleGponBaseInfo 29 }


		sleGponOnuAuthServerTimeout OBJECT-TYPE
			SYNTAX Integer32 (0..3600)
			MAX-ACCESS read-only
			STATUS current
			DESCRIPTION
				"RADIUS Server Timeout seconds"
			::= { sleGponBaseInfo 30 }


		sleGponOnuAuthServerRetry OBJECT-TYPE
			SYNTAX Integer32 (0..10)
			MAX-ACCESS read-only
			STATUS current
			DESCRIPTION
				"RADIUS Server retry counts"
			::= { sleGponBaseInfo 31 }


		sleGponOnuAuthPps OBJECT-TYPE
			SYNTAX Integer32 (0..65535)
			MAX-ACCESS read-only
			STATUS current
			DESCRIPTION
				"Onu Pakcets per second(PPS)"
			::= { sleGponBaseInfo 32 }


		sleGponOnuAuthErrorReport OBJECT-TYPE
			SYNTAX INTEGER
				{
				disable(0),
				enable(1)
				}
			MAX-ACCESS read-only
			STATUS current
			DESCRIPTION
				"Onu Authentication Error Report enable status"
			::= { sleGponBaseInfo 33 }


		sleGponOnuVideoStatusUpdateTime OBJECT-TYPE
			SYNTAX Integer32 (0..1440)
			MAX-ACCESS read-only
			STATUS current
			DESCRIPTION
				"The ONU video-status update Time
				0: disable
				1~1440: available values"
			::= { sleGponBaseInfo 34 }


		sleGponOnuPppoeStatusUpdateTime OBJECT-TYPE
			SYNTAX Integer32 (0..1440)
			MAX-ACCESS read-only
			STATUS current
			DESCRIPTION
				"The ONU Pppoe-status update Time
				0: disable
				1~1440: available values"
			::= { sleGponBaseInfo 35 }


--
--
-- 1.3.6.1.4.1.6296.101.23.1.2
-- 1.3.6.1.4.1.6296.101.23.1.2
		sleGponBaseControl OBJECT IDENTIFIER ::= { sleGponBase 2 }


--
--
-- 1.3.6.1.4.1.6296.101.23.1.2.1
-- 1.3.6.1.4.1.6296.101.23.1.2.1
		sleGponBaseControlRequest OBJECT-TYPE
			SYNTAX INTEGER
				{
				setCableDownStatus(1),
				setCableDownRefCnt(2),
				setDefaultServiceProfile(3),
				setOnuPasswordType(4),
				setOnuRxPowerUpdateTime(5),
				setMulticastGem(6),
				setInterworkIgmpSnooping(7),
				setOnuRFPseudowireDstMac(8),
				setOnuActiveMode(9),
				setOnuRFPseudowireEthType(10),
				setOnuRFPseudowireVlanId(11),
				setOltRxPowerUpdateTime(12),
				setOnuAuthRadiusUserName(13),
				setOnuAuthRadiusUserPassword(14),
				setOnuReauthTime(15),
				delOnuReauthTime(16),
				setOnuAuthFailInterval(17),
				setOnuAuthFailDisable(18),
				setOnuAuthServerTimeout(19),
				setOnuAuthPps(20),
				setOnuAuthErrorReport(21),
				setOnuVideoStatusUpdateTime(22),
				setOnuPppoeStatusUpdateTime(23)
				}
			MAX-ACCESS read-write
			STATUS current
			DESCRIPTION
				"The request of a user command"
			::= { sleGponBaseControl 1 }


--
--
-- 1.3.6.1.4.1.6296.101.23.1.2.2
-- 1.3.6.1.4.1.6296.101.23.1.2.2
		sleGponBaseControlStatus OBJECT-TYPE
			SYNTAX SleControlStatusType
			MAX-ACCESS read-only
			STATUS current
			DESCRIPTION
				"The status of user command"
			::= { sleGponBaseControl 2 }


--   1.3.6.1.4.1.6296.101.23.1.2.3
-- 1.3.6.1.4.1.6296.101.23.1.2.3
		sleGponBaseControlTimer OBJECT-TYPE
			SYNTAX Gauge32
			MAX-ACCESS read-write
			STATUS current
			DESCRIPTION
				"The maximum time for the manager for a long running user command"
			::= { sleGponBaseControl 3 }


--   1.3.6.1.4.1.6296.101.23.1.2.4
-- 1.3.6.1.4.1.6296.101.23.1.2.4
		sleGponBaseControlTimeStamp OBJECT-TYPE
			SYNTAX TimeTicks
			MAX-ACCESS read-only
			STATUS current
			DESCRIPTION
				"The time stamp of the last command(end of command)"
			::= { sleGponBaseControl 4 }


--   1.3.6.1.4.1.6296.101.23.1.2.5
-- 1.3.6.1.4.1.6296.101.23.1.2.5
		sleGponBaseControlReqResult OBJECT-TYPE
			SYNTAX SleControlRequestResultType
			MAX-ACCESS read-only
			STATUS current
			DESCRIPTION
				"The result of the last user command"
			::= { sleGponBaseControl 5 }


--   1.3.6.1.4.1.6296.101.23.1.2.6
-- 1.3.6.1.4.1.6296.101.23.1.2.6
		sleGponBaseControlCableDownStatus OBJECT-TYPE
			SYNTAX EnableFlag
			MAX-ACCESS read-write
			STATUS current
			DESCRIPTION
				"cable-down admin status"
			::= { sleGponBaseControl 6 }


--   1.3.6.1.4.1.6296.101.23.1.2.7
-- 1.3.6.1.4.1.6296.101.23.1.2.7
		sleGponBaseControlCableDwonRefCnt OBJECT-TYPE
			SYNTAX Integer32
			MAX-ACCESS read-write
			STATUS current
			DESCRIPTION
				"cable-down reference count"
			::= { sleGponBaseControl 7 }


--   1.3.6.1.4.1.6296.101.23.1.2.8
-- 1.3.6.1.4.1.6296.101.23.1.2.8
		sleGponBaseControlDeaultServiceProfile OBJECT-TYPE
			SYNTAX OCTET STRING
			MAX-ACCESS read-write
			STATUS current
			DESCRIPTION
				"The default service profile."
			::= { sleGponBaseControl 8 }


--  1.3.6.1.4.1.6296.101.23.1.2.9
		sleGponBaseControlOnuPasswordType OBJECT-TYPE
			SYNTAX INTEGER
				{
				hex(0),
				ascii(1)
				}
			MAX-ACCESS read-write
			STATUS current
			DESCRIPTION
				"The Password Type."
			::= { sleGponBaseControl 9 }


--  1.3.6.1.4.1.6296.101.23.1.2.10
		sleGponBaseControlOnuRxPowerUpdateTime OBJECT-TYPE
			SYNTAX Integer32 (0..1440)
			MAX-ACCESS read-write
			STATUS current
			DESCRIPTION
				"The ONU rx-power update time
				0: disable
				1~1440: available values"
			::= { sleGponBaseControl 10 }


--  1.3.6.1.4.1.6296.101.23.1.2.11
		sleGponBaseControlOltMulticastGem OBJECT-TYPE
			SYNTAX Integer32 (4094..4095)
			MAX-ACCESS read-write
			STATUS current
			DESCRIPTION
				"The OLT multicast Gem."
			::= { sleGponBaseControl 11 }


--  1.3.6.1.4.1.6296.101.23.1.2.12
		sleGponBaseControlOltInterworkIgmpSnooping OBJECT-TYPE
			SYNTAX INTEGER
				{
				disable(0),
				enable(1)
				}
			MAX-ACCESS read-only
			STATUS current
			DESCRIPTION
				"The OLT interwork igmp-snooping"
			::= { sleGponBaseControl 12 }


--  1.3.6.1.4.1.6296.101.23.1.2.13
		sleGponBaseControlOnuRFPseudowireMode OBJECT-TYPE
			SYNTAX INTEGER
				{
				disable(0),
				enable(1)
				}
			MAX-ACCESS read-write
			STATUS current
			DESCRIPTION
				"The ONU RF Pseudowire Mode"
			::= { sleGponBaseControl 13 }


--  1.3.6.1.4.1.6296.101.23.1.2.14
		sleGponBaseControlOnuRFPseudowireDstMac OBJECT-TYPE
			SYNTAX OCTET STRING
			MAX-ACCESS read-write
			STATUS current
			DESCRIPTION
				"The Destination MAC address by ONU RF Pseudowire.
				This is valid when only sleGponOnuRFPseudowireMode is enable."
			::= { sleGponBaseControl 14 }


--  1.3.6.1.4.1.6296.101.23.1.2.15
		sleGponbaseControlOnuActiveMode OBJECT-TYPE
			SYNTAX INTEGER
				{
				serialNumber(1),
				registerationId(2)
				}
			MAX-ACCESS read-write
			STATUS current
			DESCRIPTION
				"The GPON ONU active mode"
			::= { sleGponBaseControl 15 }


--  1.3.6.1.4.1.6296.101.23.1.2.16
		sleGponBaseControlOnuRFPseudowireEthType OBJECT-TYPE
			SYNTAX Integer32 (0..65535)
			MAX-ACCESS read-write
			STATUS current
			DESCRIPTION
				"The RF Pseudowire Ethernet Type (0:del)"
			::= { sleGponBaseControl 16 }


--  1.3.6.1.4.1.6296.101.23.1.2.17
		sleGponBaseControlOnuRFPseudowireVlanId OBJECT-TYPE
			SYNTAX Integer32 (0..4094)
			MAX-ACCESS read-write
			STATUS current
			DESCRIPTION
				"The RF Pseudowire vlan index (0:del)"
			::= { sleGponBaseControl 17 }


--  1.3.6.1.4.1.6296.101.23.1.2.18
		sleGponBaseControlOltRxPowerUpdateTime OBJECT-TYPE
			SYNTAX Integer32 (1..1440)
			MAX-ACCESS read-write
			STATUS current
			DESCRIPTION
				"The OLT rx-power update cycle
				1~1440: available values
				"
			::= { sleGponBaseControl 18 }


--  1.3.6.1.4.1.6296.101.23.1.2.19
		sleGponBaseControlOnuAuthRadiusUserName OBJECT-TYPE
			SYNTAX INTEGER
				{
				serialNumber(1),
				modelName(2)
				}
			MAX-ACCESS read-write
			STATUS current
			DESCRIPTION
				"Onu authentication radius user name"
			::= { sleGponBaseControl 19 }


		sleGponBaseControlOnuAuthRadiusUserPassword OBJECT-TYPE
			SYNTAX INTEGER
				{
				modelName(1),
				serialNumber(2)
				}
			MAX-ACCESS read-write
			STATUS current
			DESCRIPTION
				"Onu authentication radius user password"
			::= { sleGponBaseControl 20 }


		sleGponBaseControlOnuReauthStartTime OBJECT-TYPE
			SYNTAX Integer32 (0..23)
			MAX-ACCESS read-write
			STATUS current
			DESCRIPTION
				"Onu reathentication start time(hour)"
			::= { sleGponBaseControl 21 }


		sleGponBaseControlOnuReauthEndTime OBJECT-TYPE
			SYNTAX Integer32 (0..23)
			MAX-ACCESS read-write
			STATUS current
			DESCRIPTION
				"Onu reathentication end time(hour)"
			::= { sleGponBaseControl 22 }


		sleGponBaseControlOnuAuthFailInterval1 OBJECT-TYPE
			SYNTAX Integer32 (1..60)
			MAX-ACCESS read-write
			STATUS current
			DESCRIPTION
				"Onu authentication attempt interval when authentication fails"
			::= { sleGponBaseControl 23 }


		sleGponBaseControlOnuAuthFailInterval2 OBJECT-TYPE
			SYNTAX Integer32 (1..60)
			MAX-ACCESS read-write
			STATUS current
			DESCRIPTION
				"Onu authentication attempt interval when authentication fails"
			::= { sleGponBaseControl 24 }


		sleGponBaseControlOnuAuthFailInterval3 OBJECT-TYPE
			SYNTAX Integer32 (1..60)
			MAX-ACCESS read-write
			STATUS current
			DESCRIPTION
				"Onu authentication attempt interval when authentication fails"
			::= { sleGponBaseControl 25 }


		sleGponBaseControlOnuAuthFailInterval4 OBJECT-TYPE
			SYNTAX Integer32 (1..60)
			MAX-ACCESS read-write
			STATUS current
			DESCRIPTION
				"Onu authentication attempt interval when authentication fails"
			::= { sleGponBaseControl 26 }


		sleGponBaseControlOnuAuthFailInterval5 OBJECT-TYPE
			SYNTAX Integer32 (1..60)
			MAX-ACCESS read-write
			STATUS current
			DESCRIPTION
				"Onu authentication attempt interval when authentication fails"
			::= { sleGponBaseControl 27 }


		sleGponBaseControlOnuAuthServerTimeout OBJECT-TYPE
			SYNTAX Integer32 (0..3600)
			MAX-ACCESS read-write
			STATUS current
			DESCRIPTION
				"RADIUS Server Timeout secondssleGponOnuAuthServerRetry"
			::= { sleGponBaseControl 28 }


		sleGponBaseControlOnuAuthServerRetry OBJECT-TYPE
			SYNTAX Integer32 (0..10)
			MAX-ACCESS read-write
			STATUS current
			DESCRIPTION
				"RADIUS Server retry counts"
			::= { sleGponBaseControl 29 }


		sleGponBaseControlOnuAuthPps OBJECT-TYPE
			SYNTAX Integer32 (0..65535)
			MAX-ACCESS read-write
			STATUS current
			DESCRIPTION
				"Description."
			::= { sleGponBaseControl 30 }


		sleGponBaseControlOnuAuthErrorReport OBJECT-TYPE
			SYNTAX INTEGER
				{
				disable(0),
				enable(1)
				}
			MAX-ACCESS read-write
			STATUS current
			DESCRIPTION
				"Description."
			::= { sleGponBaseControl 31 }


		sleGponBaseControlOnuVideoStatusUpdateTime OBJECT-TYPE
			SYNTAX Integer32 (0..1440)
			MAX-ACCESS read-write
			STATUS current
			DESCRIPTION
				"The ONU video-status update Time
				0: disable
				1~1440: available values"
			::= { sleGponBaseControl 32 }


		sleGponBaseControlOnuPppoeStatusUpdateTime OBJECT-TYPE
			SYNTAX Integer32 (0..1440)
			MAX-ACCESS read-write
			STATUS current
			DESCRIPTION
				"The ONU Pppoe-status update Time
				0: disable
				1~1440: available values"
			::= { sleGponBaseControl 33 }


--   1.3.6.1.4.1.6296.101.23.1.3
-- 1.3.6.1.4.1.6296.101.23.1.3
		sleGponBaseNotification OBJECT IDENTIFIER ::= { sleGponBase 3 }


--   1.3.6.1.4.1.6296.101.23.1.3.1
-- 1.3.6.1.4.1.6296.101.23.1.3.1
		sleGponBaseCableDownStatusChanged NOTIFICATION-TYPE
			OBJECTS { sleGponBaseControlRequest, sleGponBaseControlTimeStamp, sleGponBaseControlReqResult, sleGponBaseControlCableDownStatus }
			STATUS current
			DESCRIPTION
				"Description."
			::= { sleGponBaseNotification 1 }


--   1.3.6.1.4.1.6296.101.23.1.3.2
-- 1.3.6.1.4.1.6296.101.23.1.3.2
		sleGponBaseCableDownRefCntChanged NOTIFICATION-TYPE
			OBJECTS { sleGponBaseControlRequest, sleGponBaseControlTimeStamp, sleGponBaseControlReqResult, sleGponBaseControlCableDwonRefCnt }
			STATUS current
			DESCRIPTION
				"Description."
			::= { sleGponBaseNotification 2 }


--   1.3.6.1.4.1.6296.101.23.1.3.3
-- 1.3.6.1.4.1.6296.101.23.1.3.3
		sleGponBaseDefaultServiceProfileChanged NOTIFICATION-TYPE
			OBJECTS { sleGponBaseControlRequest, sleGponBaseControlTimeStamp, sleGponBaseControlReqResult, sleGponBaseControlDeaultServiceProfile }
			STATUS current
			DESCRIPTION
				"Description."
			::= { sleGponBaseNotification 3 }


--  1.3.6.1.4.1.6296.101.23.1.3.4
		sleGponBasePasswordTypeChanged NOTIFICATION-TYPE
			OBJECTS { sleGponBaseControlRequest, sleGponBaseControlTimeStamp, sleGponBaseControlReqResult, sleGponBaseControlOnuPasswordType }
			STATUS current
			DESCRIPTION
				"setOnuPasswordType"
			::= { sleGponBaseNotification 4 }


--  1.3.6.1.4.1.6296.101.23.1.3.5
		sleGponBaseOnuRxPowerUpdateTimeChanged NOTIFICATION-TYPE
			OBJECTS { sleGponBaseControlRequest, sleGponBaseControlTimeStamp, sleGponBaseControlReqResult, sleGponBaseControlOnuRxPowerUpdateTime }
			STATUS current
			DESCRIPTION
				"setOnuRxPowerUpdateTime"
			::= { sleGponBaseNotification 5 }


--  1.3.6.1.4.1.6296.101.23.1.3.6
		sleGponBaseOltMulticastGemChanged NOTIFICATION-TYPE
			OBJECTS { sleGponBaseControlRequest, sleGponBaseControlTimeStamp, sleGponBaseControlReqResult, sleGponBaseControlOltMulticastGem }
			STATUS current
			DESCRIPTION
				"setMulticastGem "
			::= { sleGponBaseNotification 6 }


--  1.3.6.1.4.1.6296.101.23.1.3.7
		sleGponBaseOltInterworkIgmpSnoopingChanged NOTIFICATION-TYPE
			OBJECTS { sleGponBaseControlRequest, sleGponBaseControlTimeStamp, sleGponBaseControlReqResult, sleGponBaseControlOltInterworkIgmpSnooping }
			STATUS current
			DESCRIPTION
				"setInterworkIgmpSnooping "
			::= { sleGponBaseNotification 7 }


--  1.3.6.1.4.1.6296.101.23.1.3.8
		sleGponBaseOnuRFPseudowireDstMacChanged NOTIFICATION-TYPE
			OBJECTS { sleGponBaseControlRequest, sleGponBaseControlTimeStamp, sleGponBaseControlReqResult, sleGponBaseControlOnuRFPseudowireMode, sleGponBaseControlOnuRFPseudowireDstMac
				 }
			STATUS current
			DESCRIPTION
				"setOnuRFPseudowireDstMac"
			::= { sleGponBaseNotification 8 }


--  1.3.6.1.4.1.6296.101.23.1.3.9
		sleGponBaseOnuActiveModeChanged NOTIFICATION-TYPE
			OBJECTS { sleGponBaseControlRequest, sleGponBaseControlTimeStamp, sleGponBaseControlReqResult, sleGponbaseControlOnuActiveMode }
			STATUS current
			DESCRIPTION
				"setOnuActiveMode"
			::= { sleGponBaseNotification 9 }


--  1.3.6.1.4.1.6296.101.23.1.3.10
		sleGponBaseOnuRFPseudowireEthTypeChanged NOTIFICATION-TYPE
			OBJECTS { sleGponBaseControlRequest, sleGponBaseControlTimeStamp, sleGponBaseControlReqResult, sleGponBaseControlOnuRFPseudowireEthType }
			STATUS current
			DESCRIPTION
				"setOnuRFPseudowireEthType"
			::= { sleGponBaseNotification 10 }


--  1.3.6.1.4.1.6296.101.23.1.3.11
		sleGponBaseOnuRFPseudowireVlanIdChanged NOTIFICATION-TYPE
			OBJECTS { sleGponBaseControlRequest, sleGponBaseControlTimeStamp, sleGponBaseControlReqResult, sleGponBaseControlOnuRFPseudowireVlanId }
			STATUS current
			DESCRIPTION
				"setOnuRFPseudowireVlanId"
			::= { sleGponBaseNotification 11 }


--  1.3.6.1.4.1.6296.101.23.1.3.12
		sleGponBaseOltRxPowerUpdateTimeChanged NOTIFICATION-TYPE
			OBJECTS { sleGponBaseControlRequest, sleGponBaseControlTimeStamp, sleGponBaseControlReqResult, sleGponBaseControlOltRxPowerUpdateTime }
			STATUS current
			DESCRIPTION
				"setOltRxPowerUpdateTime "
			::= { sleGponBaseNotification 12 }


--  1.3.6.1.4.1.6296.101.23.1.3.13
		sleGponBaseOnuAuthRadiusUserNameChanged NOTIFICATION-TYPE
			OBJECTS { sleGponBaseControlRequest, sleGponBaseControlTimeStamp, sleGponBaseControlReqResult, sleGponBaseControlOnuAuthRadiusUserName }
			STATUS current
			DESCRIPTION
				"Description."
			::= { sleGponBaseNotification 13 }


		sleGponBaseOnuAuthRadiusUserPasswordChanged NOTIFICATION-TYPE
			OBJECTS { sleGponBaseControlRequest, sleGponBaseControlTimeStamp, sleGponBaseControlReqResult, sleGponBaseControlOnuAuthRadiusUserPassword }
			STATUS current
			DESCRIPTION
				"setOnuAuthRadiusUserPassword"
			::= { sleGponBaseNotification 14 }


		sleGponBaseOnuVideoStatusUpdateTimeChanged NOTIFICATION-TYPE
			OBJECTS { sleGponBaseControlRequest, sleGponBaseControlTimeStamp, sleGponBaseControlReqResult, sleGponOnuVideoStatusUpdateTime }
			STATUS current
			DESCRIPTION
				"Notify when user change value of interval time

				Binding OIDs:
				sleGponBaseControlRequest
				sleGponBaseControlTimeStamp
				sleGponBaseControlReqResult
				sleGponBaseControlOnuVideoStatusUpdateTime"
			::= { sleGponBaseNotification 22 }


		sleGponBaseOnuPppoeStatusUpdateTimeChanged NOTIFICATION-TYPE
			OBJECTS { sleGponBaseControlRequest, sleGponBaseControlTimeStamp, sleGponBaseControlOnuPppoeStatusUpdateTime, sleGponBaseControlReqResult }
			STATUS current
			DESCRIPTION
				"Notify when user change value of interval time

				Binding OIDs:
				sleGponBaseControlRequest
				sleGponBaseControlTimeStamp
				sleGponBaseControlReqResult
				sleGponBaseControlOnuPppoeStatusUpdateTime"
			::= { sleGponBaseNotification 23 }


--   1.3.6.1.4.1.6296.101.23.2
-- 1.3.6.1.4.1.6296.101.23.2
		sleGponOlt OBJECT IDENTIFIER ::= { sleGpon 2 }


--   1.3.6.1.4.1.6296.101.23.2.1
-- 1.3.6.1.4.1.6296.101.23.2.1
		sleGponOltTable OBJECT-TYPE
			SYNTAX SEQUENCE OF SleGponOltEntry
			MAX-ACCESS not-accessible
			STATUS current
			DESCRIPTION
				"sleGponOltTable"
			::= { sleGponOlt 1 }


--   1.3.6.1.4.1.6296.101.23.2.1.1
-- 1.3.6.1.4.1.6296.101.23.2.1.1
		sleGponOltEntry OBJECT-TYPE
			SYNTAX SleGponOltEntry
			MAX-ACCESS not-accessible
			STATUS current
			DESCRIPTION
				"key: sleGponOltId"
			INDEX { sleGponOltId }
			::= { sleGponOltTable 1 }


		SleGponOltEntry ::=
			SEQUENCE {
				sleGponOltId
					INTEGER,
				sleGponOltStatus
					INTEGER,
				sleGponOltDiscoverySerialStart
					INTEGER,
				sleGponOltLinkMaxDistance
					INTEGER,
				sleGponOltKeyExchange
					INTEGER,
				sleGponOltSignalCheck
					INTEGER,
				sleGponOltSignalCheckAutoOnuBlock
					INTEGER,
				sleGponOltDescription
					OCTET STRING,
				sleGponOltAutoToManual
					INTEGER,
				sleGponOltDefaultTcontDBAMode
					INTEGER,
				sleGponOltDefaultTcontFixedBw
					INTEGER,
				sleGponOltDefaultTcontAssuredBw
					INTEGER,
				sleGponOltDefaultTcontMaxBw
					INTEGER,
				sleGponOltDefaultProfileName
					OCTET STRING,
				sleGponOltFecModeUS
					INTEGER,
				sleGponOltFecModeDS
					INTEGER,
				sleGponOltMacAgingTime
					INTEGER,
				sleGponOltTransceiverPort
					INTEGER,
				sleGponOltActivateStatus
					INTEGER,
				sleGponOltProtection
					INTEGER,
				sleGponOltActiveOnuCount
					Integer32,
				sleGponOltInactiveOnuCount
					Integer32,
				sleGponOltLinkUpCount
					Counter32,
				sleGponOltLinkDownCount
					Counter32,
				sleGponOltAuthenCount
					Counter32,
				sleGponOltElapsedTimeAfterClearAuthStats
					Counter64,
				sleGponOltUpElapsedTime
					Counter64,
				sleGponOltDownElapsedTime
					Counter64,
				sleGponOltOpticParam
					INTEGER,
				sleGponOltSrcMacMonitorStatus
					EnableFlag,
				sleGponOltSrcMacMonitorAutoBlock
					EnableFlag,
				sleGponOltSrcMacMonitoEexpireTimeout
					INTEGER,
				sleGponOltTotalUsBw
					INTEGER,
				sleGponOltMaxOnuCount
					INTEGER,
				sleGponOltAntiSpoofingFilter
					INTEGER,
				sleGponOltAntiSpoofingExpireTime
					INTEGER,
				sleGponOltBwBEMethod
					INTEGER,
				sleGponOltDsGemMapping
					INTEGER,
				sleGponOltFixedTcontCount
					Integer32,
				sleGponOltDynamicTcontCount
					Integer32,
				sleGponOltPortCount
					Integer32,
				sleGponOltDeactiveMonitorStatus
					INTEGER,
				sleGponOltDeactiveMonitorRaisePercent
					Integer32,
				sleGponOltDeactiveMonitorClearPercent
					Integer32,
				sleGponOltDeactiveMonitorPeriod
					Integer32,
				sleGponOltDeactiveMonitorActiveOnuCount
					Integer32,
				sleGponOltDeactiveMonitorCurrentPercent
					Integer32,
				sleGponOltDeactiveMonitorInAlamStatus
					INTEGER,
				sleGponOltBerUpInterval
					Integer32,
				sleGponOltBerDownInterval
					Integer32,
				sleGponOltBerSfThreshold
					Integer32,
				sleGponOltBerSdThreshold
					Integer32,
				sleGponOltUsFlowMapping
					INTEGER,
				sleGponOltDsQosMappingQueueCount
					Integer32,
				sleGponOltDsQosMappingCos0Queue
					Integer32,
				sleGponOltDsQosMappingCos1Queue
					Integer32,
				sleGponOltDsQosMappingCos2Queue
					Integer32,
				sleGponOltDsQosMappingCos3Queue
					Integer32,
				sleGponOltDsQosMappingCos4Queue
					Integer32,
				sleGponOltDsQosMappingCos5Queue
					Integer32,
				sleGponOltDsQosMappingCos6Queue
					Integer32,
				sleGponOltDsQosMappingCos7Queue
					Integer32,
				sleGponOltDsQosMappingMode
					INTEGER,
				sleGponOltPortServiceStatus
					INTEGER,
				sleGponOltAutoOnuBlockContMoveMac
					INTEGER,
				sleGponOltRxPowerUpdateMode
					INTEGER,
				sleGponOltRxPowerLowThreshold
					Integer32,
				sleGponOltRxPowerHighThreshold
					Integer32,
				sleGponOltOnuInactiveAgingTime
					Integer32,
				sleGponOltBcastThreshold
					Integer32,
				sleGponOltMcastThreshold
					Integer32,
				sleGponOltDlfThreshold
					Integer32,
				sleGponOltOnuAuthControlMode
					INTEGER,
				sleGponOltTransceiverType
					INTEGER,
				sleGponOltOmccRecovery
					INTEGER,
				sleGponOltOmccRecoveryMethod
					INTEGER,
				sleGponOltOmccRecoveryThreshold
					Integer32
			 }

		sleGponOltId OBJECT-TYPE
			SYNTAX INTEGER (1..2147483647)
			MAX-ACCESS read-only
			STATUS current
			DESCRIPTION
				"Gpon Olt Index"
			::= { sleGponOltEntry 1 }


--   1.3.6.1.4.1.6296.101.23.2.1.1.2
-- 1.3.6.1.4.1.6296.101.23.2.1.1.2
		sleGponOltStatus OBJECT-TYPE
			SYNTAX INTEGER
				{
				disable(0),
				notReady(1),
				inactive(2),
				active(3),
				activePending(4),
				deactivePending(5),
				switchOverPending(6),
				unknown(255)
				}
			MAX-ACCESS read-only
			STATUS current
			DESCRIPTION
				"Gpon Olt Status"
			::= { sleGponOltEntry 2 }


--   1.3.6.1.4.1.6296.101.23.2.1.1.3
-- 1.3.6.1.4.1.6296.101.23.2.1.1.3
		sleGponOltDiscoverySerialStart OBJECT-TYPE
			SYNTAX INTEGER (1..65535)
			UNITS "seconds"
			MAX-ACCESS read-only
			STATUS current
			DESCRIPTION
				"Serial number acquisition Interval Time (seconds)"
			::= { sleGponOltEntry 3 }


--   1.3.6.1.4.1.6296.101.23.2.1.1.4
-- 1.3.6.1.4.1.6296.101.23.2.1.1.4
		sleGponOltLinkMaxDistance OBJECT-TYPE
			SYNTAX INTEGER (1..65535)
			MAX-ACCESS read-only
			STATUS current
			DESCRIPTION
				"Optical link  distance configuration.
				30       10 ~ 30 Km
				40       20 ~ 40 Km
				50       30 ~ 50 Km
				60       40 ~ 60 Km
				default  default distance (0~20Km)"
			::= { sleGponOltEntry 4 }


--   1.3.6.1.4.1.6296.101.23.2.1.1.5
-- 1.3.6.1.4.1.6296.101.23.2.1.1.5
		sleGponOltKeyExchange OBJECT-TYPE
			SYNTAX INTEGER (1..65535)
			UNITS "seconds"
			MAX-ACCESS read-only
			STATUS current
			DESCRIPTION
				"Units:seconds, Encryption key exchange configuration."
			::= { sleGponOltEntry 5 }


--   1.3.6.1.4.1.6296.101.23.2.1.1.6
-- 1.3.6.1.4.1.6296.101.23.2.1.1.6
		sleGponOltSignalCheck OBJECT-TYPE
			SYNTAX INTEGER
				{
				enable(1),
				disable(2)
				}
			MAX-ACCESS read-only
			STATUS current
			DESCRIPTION
				"Optic signal check."
			::= { sleGponOltEntry 6 }


--   1.3.6.1.4.1.6296.101.23.2.1.1.7
-- 1.3.6.1.4.1.6296.101.23.2.1.1.7
		sleGponOltSignalCheckAutoOnuBlock OBJECT-TYPE
			SYNTAX INTEGER
				{
				enable(1),
				disable(2)
				}
			MAX-ACCESS read-only
			STATUS current
			DESCRIPTION
				"block ONU automatically using optic power off."
			::= { sleGponOltEntry 7 }


--   1.3.6.1.4.1.6296.101.23.2.1.1.8
-- 1.3.6.1.4.1.6296.101.23.2.1.1.8
		sleGponOltDescription OBJECT-TYPE
			SYNTAX OCTET STRING
			MAX-ACCESS read-only
			STATUS current
			DESCRIPTION
				"OLT description."
			::= { sleGponOltEntry 8 }


--   1.3.6.1.4.1.6296.101.23.2.1.1.9
-- 1.3.6.1.4.1.6296.101.23.2.1.1.9
		sleGponOltAutoToManual OBJECT-TYPE
			SYNTAX INTEGER
				{
				enable(1),
				disable(2)
				}
			MAX-ACCESS read-only
			STATUS current
			DESCRIPTION
				"Automatically changes to manual register"
			::= { sleGponOltEntry 9 }


--   1.3.6.1.4.1.6296.101.23.2.1.1.10
-- 1.3.6.1.4.1.6296.101.23.2.1.1.10
		sleGponOltDefaultTcontDBAMode OBJECT-TYPE
			SYNTAX INTEGER
				{
				none(0),
				nsr(1),
				sr(2),
				fixed(3)
				}
			MAX-ACCESS read-only
			STATUS current
			DESCRIPTION
				"Default status reports received from ONUs"
			::= { sleGponOltEntry 10 }


--   1.3.6.1.4.1.6296.101.23.2.1.1.11
-- 1.3.6.1.4.1.6296.101.23.2.1.1.11
		sleGponOltDefaultTcontFixedBw OBJECT-TYPE
			SYNTAX INTEGER (1..65535)
			UNITS "64kbps"
			MAX-ACCESS read-only
			STATUS current
			DESCRIPTION
				"Default upstream fixed bandwidth.<128-1031616>"
			::= { sleGponOltEntry 11 }


--   1.3.6.1.4.1.6296.101.23.2.1.1.12
-- 1.3.6.1.4.1.6296.101.23.2.1.1.12
		sleGponOltDefaultTcontAssuredBw OBJECT-TYPE
			SYNTAX INTEGER (1..65535)
			UNITS "64kbps"
			MAX-ACCESS read-only
			STATUS current
			DESCRIPTION
				"Default upstream assured bandwidth.<0-1031616>"
			::= { sleGponOltEntry 12 }


--   1.3.6.1.4.1.6296.101.23.2.1.1.13
-- 1.3.6.1.4.1.6296.101.23.2.1.1.13
		sleGponOltDefaultTcontMaxBw OBJECT-TYPE
			SYNTAX INTEGER (1..65535)
			UNITS "64kbps"
			MAX-ACCESS read-only
			STATUS current
			DESCRIPTION
				"Default upstream max bandwidth.<128-1031616>"
			::= { sleGponOltEntry 13 }


--   1.3.6.1.4.1.6296.101.23.2.1.1.14
-- 1.3.6.1.4.1.6296.101.23.2.1.1.14
		sleGponOltDefaultProfileName OBJECT-TYPE
			SYNTAX OCTET STRING
			MAX-ACCESS read-only
			STATUS current
			DESCRIPTION
				"Default Profile Name"
			::= { sleGponOltEntry 14 }


--   1.3.6.1.4.1.6296.101.23.2.1.1.15
-- 1.3.6.1.4.1.6296.101.23.2.1.1.15
		sleGponOltFecModeUS OBJECT-TYPE
			SYNTAX INTEGER
				{
				enable(1),
				disable(2)
				}
			MAX-ACCESS read-only
			STATUS current
			DESCRIPTION
				"UpStream FEC mode"
			::= { sleGponOltEntry 15 }


--   1.3.6.1.4.1.6296.101.23.2.1.1.16
-- 1.3.6.1.4.1.6296.101.23.2.1.1.16
		sleGponOltFecModeDS OBJECT-TYPE
			SYNTAX INTEGER
				{
				enable(1),
				disable(2)
				}
			MAX-ACCESS read-only
			STATUS current
			DESCRIPTION
				"DownStream FEC mode"
			::= { sleGponOltEntry 16 }


--   1.3.6.1.4.1.6296.101.23.2.1.1.17
-- 1.3.6.1.4.1.6296.101.23.2.1.1.17
		sleGponOltMacAgingTime OBJECT-TYPE
			SYNTAX INTEGER (30..2147480)
			MAX-ACCESS read-only
			STATUS current
			DESCRIPTION
				"Mac Aging Time"
			::= { sleGponOltEntry 17 }


--   1.3.6.1.4.1.6296.101.23.2.1.1.18
-- 1.3.6.1.4.1.6296.101.23.2.1.1.18
		sleGponOltTransceiverPort OBJECT-TYPE
			SYNTAX INTEGER
				{
				portA(1),
				portB(2)
				}
			MAX-ACCESS read-only
			STATUS current
			DESCRIPTION
				"Transceiver Port"
			::= { sleGponOltEntry 18 }


--   1.3.6.1.4.1.6296.101.23.2.1.1.19
-- 1.3.6.1.4.1.6296.101.23.2.1.1.19
		sleGponOltActivateStatus OBJECT-TYPE
			SYNTAX INTEGER
				{
				activate(1),
				deActivate(2)
				}
			MAX-ACCESS read-only
			STATUS current
			DESCRIPTION
				"OLT activation status."
			::= { sleGponOltEntry 19 }


--   1.3.6.1.4.1.6296.101.23.2.1.1.20
-- 1.3.6.1.4.1.6296.101.23.2.1.1.20
		sleGponOltProtection OBJECT-TYPE
			SYNTAX INTEGER
				{
				enable(1),
				disable(2)
				}
			MAX-ACCESS read-only
			STATUS current
			DESCRIPTION
				"OLT protection status."
			::= { sleGponOltEntry 20 }


--   1.3.6.1.4.1.6296.101.23.2.1.1.21
-- 1.3.6.1.4.1.6296.101.23.2.1.1.21
		sleGponOltActiveOnuCount OBJECT-TYPE
			SYNTAX Integer32
			MAX-ACCESS read-only
			STATUS current
			DESCRIPTION
				"The active ONU count."
			::= { sleGponOltEntry 21 }


--   1.3.6.1.4.1.6296.101.23.2.1.1.22
-- 1.3.6.1.4.1.6296.101.23.2.1.1.22
		sleGponOltInactiveOnuCount OBJECT-TYPE
			SYNTAX Integer32
			MAX-ACCESS read-only
			STATUS current
			DESCRIPTION
				"The inactive ONU count."
			::= { sleGponOltEntry 22 }


--   1.3.6.1.4.1.6296.101.23.2.1.1.23
-- 1.3.6.1.4.1.6296.101.23.2.1.1.23
		sleGponOltLinkUpCount OBJECT-TYPE
			SYNTAX Counter32
			MAX-ACCESS read-only
			STATUS current
			DESCRIPTION
				"The link up count"
			::= { sleGponOltEntry 23 }


--   1.3.6.1.4.1.6296.101.23.2.1.1.24
-- 1.3.6.1.4.1.6296.101.23.2.1.1.24
		sleGponOltLinkDownCount OBJECT-TYPE
			SYNTAX Counter32
			MAX-ACCESS read-only
			STATUS current
			DESCRIPTION
				"The link down count
				"
			::= { sleGponOltEntry 24 }


--   1.3.6.1.4.1.6296.101.23.2.1.1.25
-- 1.3.6.1.4.1.6296.101.23.2.1.1.25
		sleGponOltAuthenCount OBJECT-TYPE
			SYNTAX Counter32
			MAX-ACCESS read-only
			STATUS current
			DESCRIPTION
				"The number of password-authed onu."
			::= { sleGponOltEntry 25 }


--   1.3.6.1.4.1.6296.101.23.2.1.1.26
-- 1.3.6.1.4.1.6296.101.23.2.1.1.26
		sleGponOltElapsedTimeAfterClearAuthStats OBJECT-TYPE
			SYNTAX Counter64
			UNITS "1 sec"
			MAX-ACCESS read-only
			STATUS current
			DESCRIPTION
				"The elapsed time after clearing auth-related statistics"
			::= { sleGponOltEntry 26 }


--   1.3.6.1.4.1.6296.101.23.2.1.1.27
-- 1.3.6.1.4.1.6296.101.23.2.1.1.27
		sleGponOltUpElapsedTime OBJECT-TYPE
			SYNTAX Counter64
			UNITS "1 sec"
			MAX-ACCESS read-only
			STATUS current
			DESCRIPTION
				"The elapsed time from link is up."
			::= { sleGponOltEntry 27 }


--   1.3.6.1.4.1.6296.101.23.2.1.1.28
-- 1.3.6.1.4.1.6296.101.23.2.1.1.28
		sleGponOltDownElapsedTime OBJECT-TYPE
			SYNTAX Counter64
			UNITS "1 sec"
			MAX-ACCESS read-only
			STATUS current
			DESCRIPTION
				"The elapsed time from link is down."
			::= { sleGponOltEntry 28 }


--   1.3.6.1.4.1.6296.101.23.2.1.1.29
-- 1.3.6.1.4.1.6296.101.23.2.1.1.29
		sleGponOltOpticParam OBJECT-TYPE
			SYNTAX INTEGER
				{
				default(1),
				user1(2),
				unknown(255)
				}
			MAX-ACCESS read-only
			STATUS current
			DESCRIPTION
				"The optic-module parmater.
				default : Default optic configuration - FUJITSU relaxy configuration.
				user1   : User1 optic configuration - Broadlight suggested."
			::= { sleGponOltEntry 29 }


--   1.3.6.1.4.1.6296.101.23.2.1.1.30
-- 1.3.6.1.4.1.6296.101.23.2.1.1.30
		sleGponOltSrcMacMonitorStatus OBJECT-TYPE
			SYNTAX EnableFlag
			MAX-ACCESS read-only
			STATUS current
			DESCRIPTION
				"The Source Mac Monitor status."
			::= { sleGponOltEntry 30 }


--   1.3.6.1.4.1.6296.101.23.2.1.1.31
-- 1.3.6.1.4.1.6296.101.23.2.1.1.31
		sleGponOltSrcMacMonitorAutoBlock OBJECT-TYPE
			SYNTAX EnableFlag
			MAX-ACCESS read-only
			STATUS current
			DESCRIPTION
				"The Source Mac Monitor Auto block status"
			::= { sleGponOltEntry 31 }


--   1.3.6.1.4.1.6296.101.23.2.1.1.32
-- 1.3.6.1.4.1.6296.101.23.2.1.1.32
		sleGponOltSrcMacMonitoEexpireTimeout OBJECT-TYPE
			SYNTAX INTEGER (0 | 60..65535)
			MAX-ACCESS read-only
			STATUS current
			DESCRIPTION
				"The Source Mac Monitor Expire time."
			::= { sleGponOltEntry 32 }


--   1.3.6.1.4.1.6296.101.23.2.1.1.33
-- 1.3.6.1.4.1.6296.101.23.2.1.1.33
		sleGponOltTotalUsBw OBJECT-TYPE
			SYNTAX INTEGER (1031616..1244160 | 140000000)
			MAX-ACCESS read-only
			STATUS current
			DESCRIPTION
				"The OLT Total US bandwidth."
			::= { sleGponOltEntry 33 }


--  1.3.6.1.4.1.6296.101.23.2.1.1.34
		sleGponOltMaxOnuCount OBJECT-TYPE
			SYNTAX INTEGER (1..65535)
			MAX-ACCESS read-only
			STATUS current
			DESCRIPTION
				"The max ONU count"
			::= { sleGponOltEntry 34 }


--  1.3.6.1.4.1.6296.101.23.2.1.1.35
		sleGponOltAntiSpoofingFilter OBJECT-TYPE
			SYNTAX INTEGER
				{
				enable(1),
				disable(2)
				}
			MAX-ACCESS read-only
			STATUS current
			DESCRIPTION
				"The Anti-Spoofing Configuration"
			::= { sleGponOltEntry 35 }


--  1.3.6.1.4.1.6296.101.23.2.1.1.36
		sleGponOltAntiSpoofingExpireTime OBJECT-TYPE
			SYNTAX INTEGER (0 | 60..65535)
			MAX-ACCESS read-only
			STATUS current
			DESCRIPTION
				"The Expire Timeout Configuration.
				Timeout Seconds (Default : 300 sec)
				"
			::= { sleGponOltEntry 36 }


--  1.3.6.1.4.1.6296.101.23.2.1.1.37
		sleGponOltBwBEMethod OBJECT-TYPE
			SYNTAX INTEGER
				{
				guaranteed(0),
				maximum(1)
				}
			MAX-ACCESS read-only
			STATUS current
			DESCRIPTION
				"The OLT band-width scheduler."
			::= { sleGponOltEntry 37 }


--  1.3.6.1.4.1.6296.101.23.2.1.1.38
		sleGponOltDsGemMapping OBJECT-TYPE
			SYNTAX INTEGER
				{
				mac(0),
				macVid(1),
				vid(2),
				perFlowByMac(3),
				perFlowByMacVid(4)
				}
			MAX-ACCESS read-only
			STATUS current
			DESCRIPTION
				"The OLT ds gem mapping."
			::= { sleGponOltEntry 38 }


--  1.3.6.1.4.1.6296.101.23.2.1.1.39
		sleGponOltFixedTcontCount OBJECT-TYPE
			SYNTAX Integer32 (0..384)
			MAX-ACCESS read-only
			STATUS current
			DESCRIPTION
				"The fixed tcont count. (0 is disable)."
			::= { sleGponOltEntry 39 }


--  1.3.6.1.4.1.6296.101.23.2.1.1.40
		sleGponOltDynamicTcontCount OBJECT-TYPE
			SYNTAX Integer32 (0..384)
			MAX-ACCESS read-only
			STATUS current
			DESCRIPTION
				"The dynamic tcont count. (0 is disable)."
			::= { sleGponOltEntry 40 }


--  1.3.6.1.4.1.6296.101.23.2.1.1.41
		sleGponOltPortCount OBJECT-TYPE
			SYNTAX Integer32 (0..3966)
			MAX-ACCESS read-only
			STATUS current
			DESCRIPTION
				"The port count. (0 is disable)."
			::= { sleGponOltEntry 41 }


--  1.3.6.1.4.1.6296.101.23.2.1.1.42
		sleGponOltDeactiveMonitorStatus OBJECT-TYPE
			SYNTAX INTEGER
				{
				disable(0),
				enable(1)
				}
			MAX-ACCESS read-only
			STATUS current
			DESCRIPTION
				"The deactive monitor status."
			::= { sleGponOltEntry 42 }


--  1.3.6.1.4.1.6296.101.23.2.1.1.43
		sleGponOltDeactiveMonitorRaisePercent OBJECT-TYPE
			SYNTAX Integer32 (1..100)
			MAX-ACCESS read-only
			STATUS current
			DESCRIPTION
				"The deactive monitor raise percent."
			::= { sleGponOltEntry 43 }


--  1.3.6.1.4.1.6296.101.23.2.1.1.44
		sleGponOltDeactiveMonitorClearPercent OBJECT-TYPE
			SYNTAX Integer32 (1..100)
			MAX-ACCESS read-only
			STATUS current
			DESCRIPTION
				"The deactive monitor clear percent."
			::= { sleGponOltEntry 44 }


--  1.3.6.1.4.1.6296.101.23.2.1.1.45
		sleGponOltDeactiveMonitorPeriod OBJECT-TYPE
			SYNTAX Integer32 (10..86400)
			MAX-ACCESS read-only
			STATUS current
			DESCRIPTION
				"The deactive monitor period. (per 10 multiple)"
			::= { sleGponOltEntry 45 }


--  1.3.6.1.4.1.6296.101.23.2.1.1.46
		sleGponOltDeactiveMonitorActiveOnuCount OBJECT-TYPE
			SYNTAX Integer32
			MAX-ACCESS read-only
			STATUS current
			DESCRIPTION
				"the OLT deactive monitor active ONU count."
			::= { sleGponOltEntry 46 }


--  1.3.6.1.4.1.6296.101.23.2.1.1.47
		sleGponOltDeactiveMonitorCurrentPercent OBJECT-TYPE
			SYNTAX Integer32 (0..100)
			MAX-ACCESS read-only
			STATUS current
			DESCRIPTION
				"The OLT deactive monitor current percent.(%)"
			::= { sleGponOltEntry 47 }


--  1.3.6.1.4.1.6296.101.23.2.1.1.48
		sleGponOltDeactiveMonitorInAlamStatus OBJECT-TYPE
			SYNTAX INTEGER
				{
				off(0),
				on(1)
				}
			MAX-ACCESS read-only
			STATUS current
			DESCRIPTION
				"The OLT deactive monitor alarm status."
			::= { sleGponOltEntry 48 }


--  1.3.6.1.4.1.6296.101.23.2.1.1.49
		sleGponOltBerUpInterval OBJECT-TYPE
			SYNTAX Integer32 (1000..10000)
			MAX-ACCESS read-only
			STATUS current
			DESCRIPTION
				"The OLT BER up interval"
			::= { sleGponOltEntry 49 }


--  1.3.6.1.4.1.6296.101.23.2.1.1.50
		sleGponOltBerDownInterval OBJECT-TYPE
			SYNTAX Integer32 (1000..10000)
			MAX-ACCESS read-only
			STATUS current
			DESCRIPTION
				"The OLT BER down interval"
			::= { sleGponOltEntry 50 }


--  1.3.6.1.4.1.6296.101.23.2.1.1.51
		sleGponOltBerSfThreshold OBJECT-TYPE
			SYNTAX Integer32 (3..8)
			MAX-ACCESS read-only
			STATUS current
			DESCRIPTION
				"The OLT BER SF threshold"
			::= { sleGponOltEntry 51 }


--  1.3.6.1.4.1.6296.101.23.2.1.1.52
		sleGponOltBerSdThreshold OBJECT-TYPE
			SYNTAX Integer32 (4..9)
			MAX-ACCESS read-only
			STATUS current
			DESCRIPTION
				"The OLT BER SD threshold"
			::= { sleGponOltEntry 52 }


--  1.3.6.1.4.1.6296.101.23.2.1.1.53
		sleGponOltUsFlowMapping OBJECT-TYPE
			SYNTAX INTEGER
				{
				perMapper(0),
				perGem(1)
				}
			MAX-ACCESS read-only
			STATUS current
			DESCRIPTION
				"The OLT us flow mapping"
			::= { sleGponOltEntry 53 }


--   1.3.6.1.4.1.6296.101.23.2.1.1.54
-- 1.3.6.1.4.1.6296.101.23.2.1.1.54
		sleGponOltDsQosMappingQueueCount OBJECT-TYPE
			SYNTAX Integer32 (0..8)
			MAX-ACCESS read-only
			STATUS current
			DESCRIPTION
				"The OLT ds Qos mapping Queue Count"
			::= { sleGponOltEntry 54 }


--   1.3.6.1.4.1.6296.101.23.2.1.1.55
-- 1.3.6.1.4.1.6296.101.23.2.1.1.55
		sleGponOltDsQosMappingCos0Queue OBJECT-TYPE
			SYNTAX Integer32 (0..7)
			MAX-ACCESS read-only
			STATUS current
			DESCRIPTION
				"The OLT ds Qos mapping Cos 0 to Priority Queue"
			::= { sleGponOltEntry 55 }


--   1.3.6.1.4.1.6296.101.23.2.1.1.56
-- 1.3.6.1.4.1.6296.101.23.2.1.1.56
		sleGponOltDsQosMappingCos1Queue OBJECT-TYPE
			SYNTAX Integer32 (0..7)
			MAX-ACCESS read-only
			STATUS current
			DESCRIPTION
				"The OLT ds Qos mapping Cos 1 to Priority Queue"
			::= { sleGponOltEntry 56 }


--   1.3.6.1.4.1.6296.101.23.2.1.1.57
-- 1.3.6.1.4.1.6296.101.23.2.1.1.57
		sleGponOltDsQosMappingCos2Queue OBJECT-TYPE
			SYNTAX Integer32 (0..7)
			MAX-ACCESS read-only
			STATUS current
			DESCRIPTION
				"The OLT ds Qos mapping Cos 2 to Priority Queue"
			::= { sleGponOltEntry 57 }


--   1.3.6.1.4.1.6296.101.23.2.1.1.58
-- 1.3.6.1.4.1.6296.101.23.2.1.1.58
		sleGponOltDsQosMappingCos3Queue OBJECT-TYPE
			SYNTAX Integer32 (0..7)
			MAX-ACCESS read-only
			STATUS current
			DESCRIPTION
				"The OLT ds Qos mapping Cos 3 to Priority Queue"
			::= { sleGponOltEntry 58 }


--   1.3.6.1.4.1.6296.101.23.2.1.1.59
-- 1.3.6.1.4.1.6296.101.23.2.1.1.59
		sleGponOltDsQosMappingCos4Queue OBJECT-TYPE
			SYNTAX Integer32 (0..7)
			MAX-ACCESS read-only
			STATUS current
			DESCRIPTION
				"The OLT ds Qos mapping Cos 4 to Priority Queue"
			::= { sleGponOltEntry 59 }


--   1.3.6.1.4.1.6296.101.23.2.1.1.60
-- 1.3.6.1.4.1.6296.101.23.2.1.1.60
		sleGponOltDsQosMappingCos5Queue OBJECT-TYPE
			SYNTAX Integer32 (0..7)
			MAX-ACCESS read-only
			STATUS current
			DESCRIPTION
				"The OLT ds Qos mapping Cos 5 to Priority Queue"
			::= { sleGponOltEntry 60 }


--   1.3.6.1.4.1.6296.101.23.2.1.1.61
-- 1.3.6.1.4.1.6296.101.23.2.1.1.61
		sleGponOltDsQosMappingCos6Queue OBJECT-TYPE
			SYNTAX Integer32 (0..7)
			MAX-ACCESS read-only
			STATUS current
			DESCRIPTION
				"The OLT ds Qos mapping Cos 6 to Priority Queue"
			::= { sleGponOltEntry 61 }


--   1.3.6.1.4.1.6296.101.23.2.1.1.62
-- 1.3.6.1.4.1.6296.101.23.2.1.1.62
		sleGponOltDsQosMappingCos7Queue OBJECT-TYPE
			SYNTAX Integer32 (0..7)
			MAX-ACCESS read-only
			STATUS current
			DESCRIPTION
				"The OLT ds Qos mapping Cos 7 to Priority Queue"
			::= { sleGponOltEntry 62 }


--   1.3.6.1.4.1.6296.101.23.2.1.1.63
-- 1.3.6.1.4.1.6296.101.23.2.1.1.63
		sleGponOltDsQosMappingMode OBJECT-TYPE
			SYNTAX INTEGER
				{
				none(0),
				mac(1),
				macVid(2),
				vid(3)
				}
			MAX-ACCESS read-only
			STATUS current
			DESCRIPTION
				"The OLT us flow mapping"
			::= { sleGponOltEntry 63 }


--  1.3.6.1.4.1.6296.101.23.2.1.1.64
		sleGponOltPortServiceStatus OBJECT-TYPE
			SYNTAX INTEGER
				{
				disable(0),
				enable(1)
				}
			MAX-ACCESS read-only
			STATUS current
			DESCRIPTION
				"The GPON port service status."
			::= { sleGponOltEntry 64 }


--  1.3.6.1.4.1.6296.101.23.2.1.1.65
		sleGponOltAutoOnuBlockContMoveMac OBJECT-TYPE
			SYNTAX INTEGER
				{
				disable(0),
				enable(1)
				}
			MAX-ACCESS read-write
			STATUS current
			DESCRIPTION
				"The Continuous move mac Auto block status"
			::= { sleGponOltEntry 65 }


--  1.3.6.1.4.1.6296.101.23.2.1.1.66
		sleGponOltRxPowerUpdateMode OBJECT-TYPE
			SYNTAX INTEGER
				{
				disable(0),
				enable(1)
				}
			MAX-ACCESS read-only
			STATUS current
			DESCRIPTION
				"The OLT Rx-power update mode"
			::= { sleGponOltEntry 66 }


--  1.3.6.1.4.1.6296.101.23.2.1.1.67
		sleGponOltRxPowerLowThreshold OBJECT-TYPE
			SYNTAX Integer32 (-1270..0 | 255)
			MAX-ACCESS read-only
			STATUS current
			DESCRIPTION
				"The OLT Rx-power Low threshold (Units 0.1dbm)
				255: unused"
			::= { sleGponOltEntry 67 }


--  1.3.6.1.4.1.6296.101.23.2.1.1.68
		sleGponOltRxPowerHighThreshold OBJECT-TYPE
			SYNTAX Integer32 (-1270..0 | 255)
			MAX-ACCESS read-only
			STATUS current
			DESCRIPTION
				"The OLT Rx-power High threshold (Units 0.1dbm)
				255: unused"
			::= { sleGponOltEntry 68 }


--  1.3.6.1.4.1.6296.101.23.2.1.1.69
		sleGponOltOnuInactiveAgingTime OBJECT-TYPE
			SYNTAX Integer32 (0..30)
			MAX-ACCESS read-only
			STATUS current
			DESCRIPTION
				"The ONU Inactive aging time (Units Days)
				0 means disable"
			::= { sleGponOltEntry 69 }


--  1.3.6.1.4.1.6296.101.23.2.1.1.70
		sleGponOltBcastThreshold OBJECT-TYPE
			SYNTAX Integer32
			MAX-ACCESS read-only
			STATUS current
			DESCRIPTION
				"The Broadcast Storm Control threshold of GPON OLT Port."
			::= { sleGponOltEntry 70 }


--  1.3.6.1.4.1.6296.101.23.2.1.1.71
		sleGponOltMcastThreshold OBJECT-TYPE
			SYNTAX Integer32
			MAX-ACCESS read-only
			STATUS current
			DESCRIPTION
				"The Multicast Storm Control threshold of GPON OLT Port."
			::= { sleGponOltEntry 71 }


--  1.3.6.1.4.1.6296.101.23.2.1.1.72
		sleGponOltDlfThreshold OBJECT-TYPE
			SYNTAX Integer32
			MAX-ACCESS read-only
			STATUS current
			DESCRIPTION
				"The DLF Storm Control threshold of GPON OLT Port."
			::= { sleGponOltEntry 72 }


--  1.3.6.1.4.1.6296.101.23.2.1.1.73
		sleGponOltOnuAuthControlMode OBJECT-TYPE
			SYNTAX INTEGER
				{
				disable(0),
				enable(1)
				}
			MAX-ACCESS read-only
			STATUS current
			DESCRIPTION
				"The Onu Authentication Control Mode"
			::= { sleGponOltEntry 73 }


		sleGponOltTransceiverType OBJECT-TYPE
			SYNTAX INTEGER
				{
				fujitsu(1),
				neophotonics(2),
				neophotonicsA(3),
				hisense(4),
				optowiz(5),
				superxon(6),
				wtd(7),
				sourcephotonics(8)
				}
			MAX-ACCESS read-only
			STATUS current
			DESCRIPTION
				"OLT Transceiver Type"
			::= { sleGponOltEntry 74 }


		sleGponOltOmccRecovery OBJECT-TYPE
			SYNTAX INTEGER
				{
				disable(0),
				enable(1)
				}
			MAX-ACCESS read-only
			STATUS current
			DESCRIPTION
				"The Onu OMCC Recovery Mode"
			::= { sleGponOltEntry 75 }


		sleGponOltOmccRecoveryMethod OBJECT-TYPE
			SYNTAX INTEGER
				{
				deactivation(0),
				reset(1)
				}
			MAX-ACCESS read-only
			STATUS current
			DESCRIPTION
				"The Onu OMCC Recovery method"
			::= { sleGponOltEntry 76 }


		sleGponOltOmccRecoveryThreshold OBJECT-TYPE
			SYNTAX Integer32 (5..720)
			MAX-ACCESS read-only
			STATUS current
			DESCRIPTION
				"The Onu OMCC Recovery threshold
				Default value is 5
				"
			::= { sleGponOltEntry 77 }


--   1.3.6.1.4.1.6296.101.23.2.2
-- 1.3.6.1.4.1.6296.101.23.2.2
		sleGponOltControl OBJECT IDENTIFIER ::= { sleGponOlt 2 }


--   1.3.6.1.4.1.6296.101.23.2.2.1
-- 1.3.6.1.4.1.6296.101.23.2.2.1
		sleGponOltControlRequest OBJECT-TYPE
			SYNTAX INTEGER
				{
				setDiscoverySerialStart(1),
				setDiscoverySerialStop(2),
				setLinkMaxDistance(3),
				setKeyExchangeStart(4),
				setKeyExchangeStop(5),
				setSignalCheck(6),
				setSignalCheckAutoOnuBlock(7),
				setDescription(8),
				setAutoToManual(9),
				setDefaultTcont(10),
				setDefaultTcontRemove(11),
				setDefaultProfile(12),
				setDefaultProfileRemove(13),
				setOltFecModeUS(14),
				setOltFecModeDs(15),
				setOltMacAgingTime(16),
				setOltTransceiverPort(17),
				setOltActivateStatus(18),
				setOltProtection(19),
				clearOltAuthStats(20),
				setOltOpticParam(21),
				setOltSrcMacMonitor(22),
				setOltTotalUsBw(23),
				setMaxOnuCount(24),
				setAntiSpoofingFilter(25),
				setBwBEMethod(26),
				setDsGemMapping(27),
				setFixedTcontCount(28),
				setDynamicTcontCount(29),
				setPortCount(30),
				setDeactiveMonitorStatus(31),
				setDeactiveMonitorRaisePercent(32),
				setDeactiveMonitorClearPercent(33),
				setDeactiveMonitorPeriod(34),
				clearDeactiveMonitorAlarm(35),
				setOltRegister(36),
				setOltBerUsInterval(37),
				setOltBerDsInterval(38),
				setOltBerSfThreshold(39),
				setOltBerSdThreshold(40),
				setUsFlowMapping(41),
				setDsQosMapping(42),
				clearDsQosMapping(43),
				setDsQosMappingMode(44),
				setAutoOnuBlockContMoveMac(45),
				setOltRxPowerUpdateMode(46),
				setOltRxPowerThreshold(47),
				setOnuInactiveAgingTime(48),
				setOltStormControlThreshold(49),
				setOnuAuthControlMode(50),
				setOnuAuthReauthentication(51),
				setOltTransceiverType(52),
				setOltOmccRecovery(53)
				}
			MAX-ACCESS read-write
			STATUS current
			DESCRIPTION
				"The request of a user command"
			::= { sleGponOltControl 1 }


--   1.3.6.1.4.1.6296.101.23.2.2.2
-- 1.3.6.1.4.1.6296.101.23.2.2.2
		sleGponOltControlStatus OBJECT-TYPE
			SYNTAX SleControlStatusType
			MAX-ACCESS read-only
			STATUS current
			DESCRIPTION
				"The status of user command"
			::= { sleGponOltControl 2 }


--   1.3.6.1.4.1.6296.101.23.2.2.3
-- 1.3.6.1.4.1.6296.101.23.2.2.3
		sleGponOltControlTimer OBJECT-TYPE
			SYNTAX Gauge32
			MAX-ACCESS read-write
			STATUS current
			DESCRIPTION
				"The maximum time for the manager for a long running user command"
			::= { sleGponOltControl 3 }


--   1.3.6.1.4.1.6296.101.23.2.2.4
-- 1.3.6.1.4.1.6296.101.23.2.2.4
		sleGponOltControlTimeStamp OBJECT-TYPE
			SYNTAX TimeTicks
			MAX-ACCESS read-only
			STATUS current
			DESCRIPTION
				"The time stamp of the last command(end of command)"
			::= { sleGponOltControl 4 }


--   1.3.6.1.4.1.6296.101.23.2.2.5
-- 1.3.6.1.4.1.6296.101.23.2.2.5
		sleGponOltControlReqResult OBJECT-TYPE
			SYNTAX SleControlRequestResultType
			MAX-ACCESS read-only
			STATUS current
			DESCRIPTION
				"The result of the last user command"
			::= { sleGponOltControl 5 }


		sleGponOltControllndex OBJECT-TYPE
			SYNTAX INTEGER (1..2147483647)
			MAX-ACCESS read-write
			STATUS current
			DESCRIPTION
				"Gpon Olt Index"
			::= { sleGponOltControl 6 }


--   1.3.6.1.4.1.6296.101.23.2.2.7
-- 1.3.6.1.4.1.6296.101.23.2.2.7
		sleGponOltControlDiscoverySerialStart OBJECT-TYPE
			SYNTAX INTEGER (1..65535)
			MAX-ACCESS read-write
			STATUS current
			DESCRIPTION
				"Serial number acquisition Interval Time (seconds) <1-1200>"
			::= { sleGponOltControl 7 }


--   1.3.6.1.4.1.6296.101.23.2.2.8
-- 1.3.6.1.4.1.6296.101.23.2.2.8
		sleGponOltControlLinkMaxDistance OBJECT-TYPE
			SYNTAX INTEGER (1..65535)
			MAX-ACCESS read-write
			STATUS current
			DESCRIPTION
				"Optical link  distance configuration.
				30       10 ~ 30 Km
				40       20 ~ 40 Km
				50       30 ~ 50 Km
				60       40 ~ 60 Km
				default  default distance (0~20Km)
				"
			::= { sleGponOltControl 8 }


--   1.3.6.1.4.1.6296.101.23.2.2.9
-- 1.3.6.1.4.1.6296.101.23.2.2.9
		sleGponOltControlKeyExchange OBJECT-TYPE
			SYNTAX INTEGER (1..65535)
			MAX-ACCESS read-only
			STATUS current
			DESCRIPTION
				"Units:seconds, Encryption key exchange configuration. <10-86400>"
			::= { sleGponOltControl 9 }


--   1.3.6.1.4.1.6296.101.23.2.2.10
-- 1.3.6.1.4.1.6296.101.23.2.2.10
		sleGponOltControlSignalCheck OBJECT-TYPE
			SYNTAX INTEGER
				{
				enable(1),
				disable(2)
				}
			MAX-ACCESS read-only
			STATUS current
			DESCRIPTION
				"Optic signal check."
			::= { sleGponOltControl 10 }


--   1.3.6.1.4.1.6296.101.23.2.2.11
-- 1.3.6.1.4.1.6296.101.23.2.2.11
		sleGponOltControlSignalCheckAutoOnuBlock OBJECT-TYPE
			SYNTAX INTEGER
				{
				enable(1),
				disable(2)
				}
			MAX-ACCESS read-only
			STATUS current
			DESCRIPTION
				"block ONU automatically using optic power off."
			::= { sleGponOltControl 11 }


--   1.3.6.1.4.1.6296.101.23.2.2.12
-- 1.3.6.1.4.1.6296.101.23.2.2.12
		sleGponOltControlDescription OBJECT-TYPE
			SYNTAX OCTET STRING
			MAX-ACCESS read-write
			STATUS current
			DESCRIPTION
				"OLT Description."
			::= { sleGponOltControl 12 }


--   1.3.6.1.4.1.6296.101.23.2.2.13
-- 1.3.6.1.4.1.6296.101.23.2.2.13
		sleGponOltControlAutoToManual OBJECT-TYPE
			SYNTAX INTEGER
				{
				enable(1),
				disable(2)
				}
			MAX-ACCESS read-write
			STATUS current
			DESCRIPTION
				"Automatically changes to manual register"
			::= { sleGponOltControl 13 }


--   1.3.6.1.4.1.6296.101.23.2.2.14
-- 1.3.6.1.4.1.6296.101.23.2.2.14
		sleGponOltControlDefaultTcontDBAMode OBJECT-TYPE
			SYNTAX INTEGER
				{
				nsr(1),
				sr(2),
				fixed(3)
				}
			MAX-ACCESS read-write
			STATUS current
			DESCRIPTION
				"Default status reports received from ONUs"
			::= { sleGponOltControl 14 }


--   1.3.6.1.4.1.6296.101.23.2.2.15
-- 1.3.6.1.4.1.6296.101.23.2.2.15
		sleGponOltControlDefaultTcontFixedBw OBJECT-TYPE
			SYNTAX INTEGER (1..65535)
			MAX-ACCESS read-write
			STATUS current
			DESCRIPTION
				"Default upstream fixed bandwidth.<128-1031616>"
			::= { sleGponOltControl 15 }


--   1.3.6.1.4.1.6296.101.23.2.2.16
-- 1.3.6.1.4.1.6296.101.23.2.2.16
		sleGponOltControlDefaultTcontAssuredBw OBJECT-TYPE
			SYNTAX INTEGER (1..65535)
			MAX-ACCESS read-write
			STATUS current
			DESCRIPTION
				"Default upstream assured bandwidth.<0-1031616>"
			::= { sleGponOltControl 16 }


--   1.3.6.1.4.1.6296.101.23.2.2.17
-- 1.3.6.1.4.1.6296.101.23.2.2.17
		sleGponOltControlDefaultTcontMaxBw OBJECT-TYPE
			SYNTAX INTEGER (1..65535)
			MAX-ACCESS read-write
			STATUS current
			DESCRIPTION
				"Default upstream max bandwidth.<128-1031616>"
			::= { sleGponOltControl 17 }


--   1.3.6.1.4.1.6296.101.23.2.2.18
-- 1.3.6.1.4.1.6296.101.23.2.2.18
		sleGponOltControlDefaultProfileName OBJECT-TYPE
			SYNTAX OCTET STRING
			MAX-ACCESS read-write
			STATUS current
			DESCRIPTION
				"Default Profile Name"
			::= { sleGponOltControl 18 }


--   1.3.6.1.4.1.6296.101.23.2.2.19
-- 1.3.6.1.4.1.6296.101.23.2.2.19
		sleGponOltControlFecModeUS OBJECT-TYPE
			SYNTAX INTEGER
				{
				enable(1),
				disable(2)
				}
			MAX-ACCESS read-write
			STATUS current
			DESCRIPTION
				"UpStream FEC mode"
			::= { sleGponOltControl 19 }


--   1.3.6.1.4.1.6296.101.23.2.2.20
-- 1.3.6.1.4.1.6296.101.23.2.2.20
		sleGponOltControlFecModeDS OBJECT-TYPE
			SYNTAX INTEGER
				{
				enable(1),
				disable(2)
				}
			MAX-ACCESS read-write
			STATUS current
			DESCRIPTION
				"DownStream FEC mode"
			::= { sleGponOltControl 20 }


--   1.3.6.1.4.1.6296.101.23.2.2.21
-- 1.3.6.1.4.1.6296.101.23.2.2.21
		sleGponOltControlMacAgingTime OBJECT-TYPE
			SYNTAX INTEGER (30..2147480)
			MAX-ACCESS read-write
			STATUS current
			DESCRIPTION
				"Mac Aging Time"
			::= { sleGponOltControl 21 }


--   1.3.6.1.4.1.6296.101.23.2.2.22
-- 1.3.6.1.4.1.6296.101.23.2.2.22
		sleGponOltControlTransceiverPort OBJECT-TYPE
			SYNTAX INTEGER
				{
				portA(1),
				portB(2)
				}
			MAX-ACCESS read-write
			STATUS current
			DESCRIPTION
				"Transceiver Port"
			::= { sleGponOltControl 22 }


--   1.3.6.1.4.1.6296.101.23.2.2.23
-- 1.3.6.1.4.1.6296.101.23.2.2.23
		sleGponOltControlActivateStatus OBJECT-TYPE
			SYNTAX INTEGER
				{
				activate(1),
				deActivate(2)
				}
			MAX-ACCESS read-write
			STATUS current
			DESCRIPTION
				"OLT activation status."
			::= { sleGponOltControl 23 }


--   1.3.6.1.4.1.6296.101.23.2.2.24
-- 1.3.6.1.4.1.6296.101.23.2.2.24
		sleGponOltControlProtection OBJECT-TYPE
			SYNTAX INTEGER
				{
				enable(1),
				disable(2)
				}
			MAX-ACCESS read-write
			STATUS current
			DESCRIPTION
				"OLT protection status."
			::= { sleGponOltControl 24 }


--   1.3.6.1.4.1.6296.101.23.2.2.25
-- 1.3.6.1.4.1.6296.101.23.2.2.25
		sleGponOltControlOpticParam OBJECT-TYPE
			SYNTAX INTEGER
				{
				default(1),
				user1(2)
				}
			MAX-ACCESS read-write
			STATUS current
			DESCRIPTION
				"The optic-module parmater.
				default : Default optic configuration - FUJITSU relaxy configuration.
				user1   : User1 optic configuration - Broadlight suggested.
				"
			::= { sleGponOltControl 25 }


--   1.3.6.1.4.1.6296.101.23.2.2.26
-- 1.3.6.1.4.1.6296.101.23.2.2.26
		sleGponOltControlSrcMacMonitorStatus OBJECT-TYPE
			SYNTAX EnableFlag
			MAX-ACCESS read-write
			STATUS current
			DESCRIPTION
				"The Source Mac Monitor status."
			::= { sleGponOltControl 26 }


--   1.3.6.1.4.1.6296.101.23.2.2.27
-- 1.3.6.1.4.1.6296.101.23.2.2.27
		sleGponOltControlSrcMacMonitorAutoBlock OBJECT-TYPE
			SYNTAX EnableFlag
			MAX-ACCESS read-write
			STATUS current
			DESCRIPTION
				"The Source Mac Monitor Auto block status"
			::= { sleGponOltControl 27 }


--   1.3.6.1.4.1.6296.101.23.2.2.28
-- 1.3.6.1.4.1.6296.101.23.2.2.28
		sleGponOltControlSrcMacMonitoEexpireTimeout OBJECT-TYPE
			SYNTAX INTEGER (0 | 60..65535)
			MAX-ACCESS read-write
			STATUS current
			DESCRIPTION
				"The Source Mac Monitor Expire time."
			::= { sleGponOltControl 28 }


--   1.3.6.1.4.1.6296.101.23.2.2.29
-- 1.3.6.1.4.1.6296.101.23.2.2.29
		sleGponOltControlTotalUsBw OBJECT-TYPE
			SYNTAX INTEGER (1031616..1244160 | 140000000)
			MAX-ACCESS read-write
			STATUS current
			DESCRIPTION
				"The OLT Total US bandwidth."
			::= { sleGponOltControl 29 }


--  1.3.6.1.4.1.6296.101.23.2.2.30
		sleGponOltControlMaxOnuCount OBJECT-TYPE
			SYNTAX INTEGER (1..65535)
			MAX-ACCESS read-write
			STATUS current
			DESCRIPTION
				"The max ONU count"
			::= { sleGponOltControl 30 }


--  1.3.6.1.4.1.6296.101.23.2.2.31
		sleGponOltControlAntiSpoofingFilter OBJECT-TYPE
			SYNTAX INTEGER
				{
				enable(1),
				disable(2)
				}
			MAX-ACCESS read-write
			STATUS current
			DESCRIPTION
				"The Anti-Spoofing Configuration"
			::= { sleGponOltControl 31 }


--  1.3.6.1.4.1.6296.101.23.2.2.32
		sleGponOltControlAntiSpoofingExpireTime OBJECT-TYPE
			SYNTAX INTEGER (0 | 60..65535)
			MAX-ACCESS read-write
			STATUS current
			DESCRIPTION
				"The Expire Timeout Configuration.
				Timeout Seconds (Default : 300 sec)"
			::= { sleGponOltControl 32 }


--  1.3.6.1.4.1.6296.101.23.2.2.33
		sleGponOltControlBwBEMethod OBJECT-TYPE
			SYNTAX INTEGER
				{
				guaranteed(0),
				maximum(1)
				}
			MAX-ACCESS read-write
			STATUS current
			DESCRIPTION
				"The OLT band-width scheduler."
			::= { sleGponOltControl 33 }


--  1.3.6.1.4.1.6296.101.23.2.2.34
		sleGponOltControlDsGemMapping OBJECT-TYPE
			SYNTAX INTEGER
				{
				mac(0),
				macVid(1),
				vid(2),
				perFlowByMac(3),
				perFlowByMacVid(4)
				}
			MAX-ACCESS read-write
			STATUS current
			DESCRIPTION
				"The OLT ds gem mapping."
			::= { sleGponOltControl 34 }


--  1.3.6.1.4.1.6296.101.23.2.2.35
		sleGponOltControlFixedTcontCount OBJECT-TYPE
			SYNTAX Integer32 (0..384)
			MAX-ACCESS read-write
			STATUS current
			DESCRIPTION
				"The fixed tcont count"
			::= { sleGponOltControl 35 }


--  1.3.6.1.4.1.6296.101.23.2.2.36
		sleGponOltControlDynamicTcontCount OBJECT-TYPE
			SYNTAX Integer32 (0..384)
			MAX-ACCESS read-write
			STATUS current
			DESCRIPTION
				"The dynamic tcont count"
			::= { sleGponOltControl 36 }


--  1.3.6.1.4.1.6296.101.23.2.2.37
		sleGponOltControlPortCount OBJECT-TYPE
			SYNTAX Integer32 (0..3966)
			MAX-ACCESS read-write
			STATUS current
			DESCRIPTION
				"The port count"
			::= { sleGponOltControl 37 }


--  1.3.6.1.4.1.6296.101.23.2.2.38
		sleGponOltControlDeactiveMonitorStatus OBJECT-TYPE
			SYNTAX INTEGER
				{
				disable(0),
				enable(1)
				}
			MAX-ACCESS read-write
			STATUS current
			DESCRIPTION
				"The deactive monitor status."
			::= { sleGponOltControl 38 }


--  1.3.6.1.4.1.6296.101.23.2.2.39
		sleGponOltControlDeactiveMonitorRaisePercent OBJECT-TYPE
			SYNTAX Integer32 (1..100)
			MAX-ACCESS read-write
			STATUS current
			DESCRIPTION
				"The deactive monitor raise percent."
			::= { sleGponOltControl 39 }


--  1.3.6.1.4.1.6296.101.23.2.2.40
		sleGponOltControlDeactiveMonitorClearPercent OBJECT-TYPE
			SYNTAX Integer32 (1..100)
			MAX-ACCESS read-write
			STATUS current
			DESCRIPTION
				"The deactive monitor clear percent."
			::= { sleGponOltControl 40 }


--  1.3.6.1.4.1.6296.101.23.2.2.41
		sleGponOltControlDeactiveMonitorPeriod OBJECT-TYPE
			SYNTAX Integer32 (10..86400)
			MAX-ACCESS read-write
			STATUS current
			DESCRIPTION
				"The deactive monitor period. (per 10 multiple)"
			::= { sleGponOltControl 41 }


--  1.3.6.1.4.1.6296.101.23.2.2.42
		sleGponOltControlBerUpInterval OBJECT-TYPE
			SYNTAX Integer32 (1000..10000)
			MAX-ACCESS read-write
			STATUS current
			DESCRIPTION
				"The OLT BER up interval"
			::= { sleGponOltControl 42 }


--  1.3.6.1.4.1.6296.101.23.2.2.43
		sleGponOltControlBerDownInterval OBJECT-TYPE
			SYNTAX Integer32 (1000..10000)
			MAX-ACCESS read-write
			STATUS current
			DESCRIPTION
				"The OLT BER down interval"
			::= { sleGponOltControl 43 }


--  1.3.6.1.4.1.6296.101.23.2.2.44
		sleGponOltControlBerSfThreshold OBJECT-TYPE
			SYNTAX Integer32 (3..8)
			MAX-ACCESS read-write
			STATUS current
			DESCRIPTION
				"The OLT BER SF threshold"
			::= { sleGponOltControl 44 }


--  1.3.6.1.4.1.6296.101.23.2.2.45
		sleGponOltControlBerSdThreshold OBJECT-TYPE
			SYNTAX Integer32 (4..9)
			MAX-ACCESS read-write
			STATUS current
			DESCRIPTION
				"The OLT BER SD threshold"
			::= { sleGponOltControl 45 }


--  1.3.6.1.4.1.6296.101.23.2.2.46
		sleGponOltControlUsFlowMapping OBJECT-TYPE
			SYNTAX INTEGER
				{
				perMapper(0),
				perGem(1)
				}
			MAX-ACCESS read-write
			STATUS current
			DESCRIPTION
				"The OLT us flow mapping"
			::= { sleGponOltControl 46 }


--   1.3.6.1.4.1.6296.101.23.2.2.47
-- 1.3.6.1.4.1.6296.101.23.2.2.47
		sleGponOltControlDsQosMappingQueueCount OBJECT-TYPE
			SYNTAX Integer32 (0..8)
			MAX-ACCESS read-write
			STATUS current
			DESCRIPTION
				"The OLT ds Qos mapping Queue Count"
			::= { sleGponOltControl 47 }


--   1.3.6.1.4.1.6296.101.23.2.2.48
-- 1.3.6.1.4.1.6296.101.23.2.2.48
		sleGponOltControlDsQosMappingCos0Queue OBJECT-TYPE
			SYNTAX Integer32 (0..7)
			MAX-ACCESS read-write
			STATUS current
			DESCRIPTION
				"The OLT ds Qos mapping Cos 0 to Priority Queue"
			::= { sleGponOltControl 48 }


--   1.3.6.1.4.1.6296.101.23.2.2.49
-- 1.3.6.1.4.1.6296.101.23.2.2.49
		sleGponOltControlDsQosMappingCos1Queue OBJECT-TYPE
			SYNTAX Integer32 (0..7)
			MAX-ACCESS read-write
			STATUS current
			DESCRIPTION
				"The OLT ds Qos mapping Cos 1 to Priority Queue"
			::= { sleGponOltControl 49 }


--   1.3.6.1.4.1.6296.101.23.2.2.50
-- 1.3.6.1.4.1.6296.101.23.2.2.50
		sleGponOltControlDsQosMappingCos2Queue OBJECT-TYPE
			SYNTAX Integer32 (0..7)
			MAX-ACCESS read-write
			STATUS current
			DESCRIPTION
				"The OLT ds Qos mapping Cos 2 to Priority Queue"
			::= { sleGponOltControl 50 }


--   1.3.6.1.4.1.6296.101.23.2.2.51
-- 1.3.6.1.4.1.6296.101.23.2.2.51
		sleGponOltControlDsQosMappingCos3Queue OBJECT-TYPE
			SYNTAX Integer32 (0..7)
			MAX-ACCESS read-write
			STATUS current
			DESCRIPTION
				"The OLT ds Qos mapping Cos 3 to Priority Queue"
			::= { sleGponOltControl 51 }


--   1.3.6.1.4.1.6296.101.23.2.2.52
-- 1.3.6.1.4.1.6296.101.23.2.2.52
		sleGponOltControlDsQosMappingCos4Queue OBJECT-TYPE
			SYNTAX Integer32 (0..7)
			MAX-ACCESS read-write
			STATUS current
			DESCRIPTION
				"The OLT ds Qos mapping Cos 4 to Priority Queue"
			::= { sleGponOltControl 52 }


--   1.3.6.1.4.1.6296.101.23.2.2.53
-- 1.3.6.1.4.1.6296.101.23.2.2.53
		sleGponOltControlDsQosMappingCos5Queue OBJECT-TYPE
			SYNTAX Integer32 (0..7)
			MAX-ACCESS read-write
			STATUS current
			DESCRIPTION
				"The OLT ds Qos mapping Cos 5 to Priority Queue"
			::= { sleGponOltControl 53 }


--   1.3.6.1.4.1.6296.101.23.2.2.54
-- 1.3.6.1.4.1.6296.101.23.2.2.54
		sleGponOltControlDsQosMappingCos6Queue OBJECT-TYPE
			SYNTAX Integer32 (0..7)
			MAX-ACCESS read-write
			STATUS current
			DESCRIPTION
				"The OLT ds Qos mapping Cos 6 to Priority Queue"
			::= { sleGponOltControl 54 }


--   1.3.6.1.4.1.6296.101.23.2.2.55
-- 1.3.6.1.4.1.6296.101.23.2.2.55
		sleGponOltControlDsQosMappingCos7Queue OBJECT-TYPE
			SYNTAX Integer32 (0..7)
			MAX-ACCESS read-write
			STATUS current
			DESCRIPTION
				"The OLT ds Qos mapping Cos 7 to Priority Queue"
			::= { sleGponOltControl 55 }


--   1.3.6.1.4.1.6296.101.23.2.2.56
-- 1.3.6.1.4.1.6296.101.23.2.2.56
		sleGponOltControlDsQosMappingMode OBJECT-TYPE
			SYNTAX INTEGER
				{
				none(0),
				mac(1),
				macVid(2),
				vid(3)
				}
			MAX-ACCESS read-write
			STATUS current
			DESCRIPTION
				"The OLT us flow mapping"
			::= { sleGponOltControl 56 }


--  1.3.6.1.4.1.6296.101.23.2.2.57
		sleGponOltControlAutoOnuBlockContMoveMac OBJECT-TYPE
			SYNTAX INTEGER
				{
				disable(0),
				enable(1)
				}
			MAX-ACCESS read-write
			STATUS current
			DESCRIPTION
				"The Continuous move mac Auto block status"
			::= { sleGponOltControl 57 }


--  1.3.6.1.4.1.6296.101.23.2.2.58
		sleGponOltControlRxPowerUpdateMode OBJECT-TYPE
			SYNTAX INTEGER
				{
				disable(0),
				enable(1)
				}
			MAX-ACCESS read-write
			STATUS current
			DESCRIPTION
				"The OLT Rx-power update mode"
			::= { sleGponOltControl 58 }


--  1.3.6.1.4.1.6296.101.23.2.2.59
		sleGponOltControlRxPowerLowThreshold OBJECT-TYPE
			SYNTAX Integer32 (-1270..0 | 255)
			MAX-ACCESS read-write
			STATUS current
			DESCRIPTION
				"The OLT Rx-power Low threshold (Units 0.1dbm)
				255: unused"
			::= { sleGponOltControl 59 }


--  1.3.6.1.4.1.6296.101.23.2.2.60
		sleGponOltControlRxPowerHighThreshold OBJECT-TYPE
			SYNTAX Integer32 (-1270..0 | 255)
			MAX-ACCESS read-write
			STATUS current
			DESCRIPTION
				"The OLT Rx-power Highthreshold (Units 0.1dbm)
				255: unused"
			::= { sleGponOltControl 60 }


--  1.3.6.1.4.1.6296.101.23.2.2.61
		sleGponOltControlOnuInactiveAgingTime OBJECT-TYPE
			SYNTAX Integer32 (0..30)
			MAX-ACCESS read-write
			STATUS current
			DESCRIPTION
				"The ONU Inactive aging time (Units Days)
				0 means disable"
			::= { sleGponOltControl 61 }


--  1.3.6.1.4.1.6296.101.23.2.2.62
		sleGponOltControlBcastThreshold OBJECT-TYPE
			SYNTAX Integer32
			MAX-ACCESS read-write
			STATUS current
			DESCRIPTION
				"Description."
			::= { sleGponOltControl 62 }


--  1.3.6.1.4.1.6296.101.23.2.2.63
		sleGponOltControlMulticastThreshold OBJECT-TYPE
			SYNTAX Integer32
			MAX-ACCESS read-write
			STATUS current
			DESCRIPTION
				"Description."
			::= { sleGponOltControl 63 }


--  1.3.6.1.4.1.6296.101.23.2.2.64
		sleGponOltControlDLFThreshold OBJECT-TYPE
			SYNTAX Integer32
			MAX-ACCESS read-write
			STATUS current
			DESCRIPTION
				"Description."
			::= { sleGponOltControl 64 }


--  1.3.6.1.4.1.6296.101.23.2.2.65
		sleGponOltControlOnuAuthControlMode OBJECT-TYPE
			SYNTAX INTEGER
				{
				disable(0),
				enable(1)
				}
			MAX-ACCESS read-write
			STATUS current
			DESCRIPTION
				"The Onu Authentication Control Mode"
			::= { sleGponOltControl 65 }


		sleGponOltControlTransceiverType OBJECT-TYPE
			SYNTAX INTEGER
				{
				fujitsu(1),
				neophotonics(2),
				neophotonicsA(3),
				hisense(4),
				optowiz(5),
				superxon(6),
				wtd(7),
				sourcephotonics(8)
				}
			MAX-ACCESS read-write
			STATUS current
			DESCRIPTION
				"OLT Transceiver Type"
			::= { sleGponOltControl 66 }


		sleGponOltControlOmccRecovery OBJECT-TYPE
			SYNTAX INTEGER
				{
				disable(0),
				enable(1)
				}
			MAX-ACCESS read-write
			STATUS current
			DESCRIPTION
				"The Onu OMCC Recovery Mode"
			::= { sleGponOltControl 67 }


		sleGponOltControlOmccRecoveryMethod OBJECT-TYPE
			SYNTAX INTEGER
				{
				deactivation(0),
				reset(1)
				}
			MAX-ACCESS read-write
			STATUS current
			DESCRIPTION
				"The Onu OMCC Recovery method"
			::= { sleGponOltControl 68 }


		sleGponOltControlOmccRecoveryThreshold OBJECT-TYPE
			SYNTAX Integer32 (5..720)
			MAX-ACCESS read-write
			STATUS current
			DESCRIPTION
				"The Onu OMCC Recovery threshold
				Default value is 5
				"
			::= { sleGponOltControl 69 }


--   1.3.6.1.4.1.6296.101.23.2.3
-- 1.3.6.1.4.1.6296.101.23.2.3
		sleGponOltNotification OBJECT IDENTIFIER ::= { sleGponOlt 3 }


--   1.3.6.1.4.1.6296.101.23.2.3.1
-- 1.3.6.1.4.1.6296.101.23.2.3.1
		sleGponOltDiscoverySerialStarted NOTIFICATION-TYPE
			OBJECTS { sleGponOltControlRequest, sleGponOltControlTimeStamp, sleGponOltControlReqResult, sleGponOltControllndex, sleGponOltControlDiscoverySerialStart
				 }
			STATUS current
			DESCRIPTION
				"Description."
			::= { sleGponOltNotification 1 }


--   1.3.6.1.4.1.6296.101.23.2.3.2
-- 1.3.6.1.4.1.6296.101.23.2.3.2
		sleGponOltDiscoverySerialStopped NOTIFICATION-TYPE
			OBJECTS { sleGponOltControlRequest, sleGponOltControlTimeStamp, sleGponOltControlReqResult, sleGponOltControllndex }
			STATUS current
			DESCRIPTION
				"Description."
			::= { sleGponOltNotification 2 }


--   1.3.6.1.4.1.6296.101.23.2.3.3
-- 1.3.6.1.4.1.6296.101.23.2.3.3
		sleGponOltLinkMaxDistanceChanged NOTIFICATION-TYPE
			OBJECTS { sleGponOltControlRequest, sleGponOltControlTimeStamp, sleGponOltControlReqResult, sleGponOltControllndex, sleGponOltControlLinkMaxDistance
				 }
			STATUS current
			DESCRIPTION
				"Description."
			::= { sleGponOltNotification 3 }


--   1.3.6.1.4.1.6296.101.23.2.3.4
-- 1.3.6.1.4.1.6296.101.23.2.3.4
		sleGponOltKeyExchangeStarted NOTIFICATION-TYPE
			OBJECTS { sleGponOltControlRequest, sleGponOltControlTimeStamp, sleGponOltControlReqResult, sleGponOltControllndex, sleGponOltControlKeyExchange
				 }
			STATUS current
			DESCRIPTION
				"Description."
			::= { sleGponOltNotification 4 }


--   1.3.6.1.4.1.6296.101.23.2.3.5
-- 1.3.6.1.4.1.6296.101.23.2.3.5
		sleGponOltKeyExchangeStopped NOTIFICATION-TYPE
			OBJECTS { sleGponOltControlRequest, sleGponOltControlTimeStamp, sleGponOltControlReqResult, sleGponOltControllndex }
			STATUS current
			DESCRIPTION
				"Description."
			::= { sleGponOltNotification 5 }


--   1.3.6.1.4.1.6296.101.23.2.3.6
-- 1.3.6.1.4.1.6296.101.23.2.3.6
		sleGponOltSignalCheckChanged NOTIFICATION-TYPE
			OBJECTS { sleGponOltControlRequest, sleGponOltControlTimeStamp, sleGponOltControlReqResult, sleGponOltControllndex, sleGponOltControlSignalCheck
				 }
			STATUS current
			DESCRIPTION
				"Description."
			::= { sleGponOltNotification 6 }


--   1.3.6.1.4.1.6296.101.23.2.3.7
-- 1.3.6.1.4.1.6296.101.23.2.3.7
		sleGponOltSignalCheckAutoOnuBlockChanged NOTIFICATION-TYPE
			OBJECTS { sleGponOltControlRequest, sleGponOltControlTimeStamp, sleGponOltControlReqResult, sleGponOltControllndex, sleGponOltControlSignalCheckAutoOnuBlock
				 }
			STATUS current
			DESCRIPTION
				"Description."
			::= { sleGponOltNotification 7 }


--   1.3.6.1.4.1.6296.101.23.2.3.8
-- 1.3.6.1.4.1.6296.101.23.2.3.8
		sleGponOltDescriptionChanged NOTIFICATION-TYPE
			OBJECTS { sleGponOltControlRequest, sleGponOltControlTimeStamp, sleGponOltControlReqResult, sleGponOltControllndex, sleGponOltControlDescription
				 }
			STATUS current
			DESCRIPTION
				"Description."
			::= { sleGponOltNotification 8 }


--
-- 1.3.6.1.4.1.6296.101.23.2.3.9
-- 1.3.6.1.4.1.6296.101.23.2.3.9
		sleGponOltAutoToManualChanged NOTIFICATION-TYPE
			OBJECTS { sleGponOltControlRequest, sleGponOltControlTimeStamp, sleGponOltControlReqResult, sleGponOltControllndex, sleGponOltControlAutoToManual
				 }
			STATUS current
			DESCRIPTION
				"Description."
			::= { sleGponOltNotification 9 }


--   1.3.6.1.4.1.6296.101.23.2.3.10
-- 1.3.6.1.4.1.6296.101.23.2.3.10
		sleGponOltDefaultTcontChanged NOTIFICATION-TYPE
			OBJECTS { sleGponOltControlRequest, sleGponOltControlTimeStamp, sleGponOltControlReqResult, sleGponOltControllndex, sleGponOltControlDefaultTcontDBAMode,
				sleGponOltControlDefaultTcontFixedBw, sleGponOltControlDefaultTcontAssuredBw, sleGponOltControlDefaultTcontMaxBw }
			STATUS current
			DESCRIPTION
				"Description."
			::= { sleGponOltNotification 10 }


--   1.3.6.1.4.1.6296.101.23.2.3.11
-- 1.3.6.1.4.1.6296.101.23.2.3.11
		sleGponOltDefaultTcontRemoved NOTIFICATION-TYPE
			OBJECTS { sleGponOltControlRequest, sleGponOltControlTimeStamp, sleGponOltControlReqResult, sleGponOltControllndex }
			STATUS current
			DESCRIPTION
				"Description."
			::= { sleGponOltNotification 11 }


--   1.3.6.1.4.1.6296.101.23.2.3.12
-- 1.3.6.1.4.1.6296.101.23.2.3.12
		sleGponOltDefaultProfileChanged NOTIFICATION-TYPE
			OBJECTS { sleGponOltControlRequest, sleGponOltControlTimeStamp, sleGponOltControlReqResult, sleGponOltControllndex, sleGponOltControlDefaultProfileName
				 }
			STATUS current
			DESCRIPTION
				"Description."
			::= { sleGponOltNotification 12 }


--   1.3.6.1.4.1.6296.101.23.2.3.13
-- 1.3.6.1.4.1.6296.101.23.2.3.13
		sleGponOltDefaultProfileRemoved NOTIFICATION-TYPE
			OBJECTS { sleGponOltControlRequest, sleGponOltControlTimeStamp, sleGponOltControlReqResult, sleGponOltControllndex }
			STATUS current
			DESCRIPTION
				"Description."
			::= { sleGponOltNotification 13 }


--   1.3.6.1.4.1.6296.101.23.2.3.14
-- 1.3.6.1.4.1.6296.101.23.2.3.14
		sleGponOltFecModeUSChanged NOTIFICATION-TYPE
			OBJECTS { sleGponOltControlRequest, sleGponOltControlTimeStamp, sleGponOltControlReqResult, sleGponOltControllndex, sleGponOltControlFecModeUS
				 }
			STATUS current
			DESCRIPTION
				"Description."
			::= { sleGponOltNotification 14 }


--   1.3.6.1.4.1.6296.101.23.2.3.15
-- 1.3.6.1.4.1.6296.101.23.2.3.15
		sleGponOltFecModeDSChanged NOTIFICATION-TYPE
			OBJECTS { sleGponOltControlRequest, sleGponOltControlTimeStamp, sleGponOltControlReqResult, sleGponOltControllndex, sleGponOltControlFecModeDS
				 }
			STATUS current
			DESCRIPTION
				"Description."
			::= { sleGponOltNotification 15 }


--   1.3.6.1.4.1.6296.101.23.2.3.16
-- 1.3.6.1.4.1.6296.101.23.2.3.16
		sleGponOltMacAgingTimeChanged NOTIFICATION-TYPE
			OBJECTS { sleGponOltControlRequest, sleGponOltControlTimeStamp, sleGponOltControlReqResult, sleGponOltControllndex, sleGponOltControlMacAgingTime
				 }
			STATUS current
			DESCRIPTION
				"Description."
			::= { sleGponOltNotification 16 }


--   1.3.6.1.4.1.6296.101.23.2.3.17
-- 1.3.6.1.4.1.6296.101.23.2.3.17
		sleGponOltTransceiverPortChanged NOTIFICATION-TYPE
			OBJECTS { sleGponOltControlRequest, sleGponOltControlTimeStamp, sleGponOltControlReqResult, sleGponOltControllndex, sleGponOltControlTransceiverPort
				 }
			STATUS current
			DESCRIPTION
				"Description."
			::= { sleGponOltNotification 17 }


--   1.3.6.1.4.1.6296.101.23.2.3.18
-- 1.3.6.1.4.1.6296.101.23.2.3.18
		sleGponOltActivateStatusChanged NOTIFICATION-TYPE
			OBJECTS { sleGponOltControlRequest, sleGponOltControlTimeStamp, sleGponOltControlReqResult, sleGponOltControllndex, sleGponOltControlActivateStatus
				 }
			STATUS current
			DESCRIPTION
				"Description."
			::= { sleGponOltNotification 18 }


--   1.3.6.1.4.1.6296.101.23.2.3.19
-- 1.3.6.1.4.1.6296.101.23.2.3.19
		sleGponOltProtectionChanged NOTIFICATION-TYPE
			OBJECTS { sleGponOltControlRequest, sleGponOltControlTimeStamp, sleGponOltControlReqResult, sleGponOltControllndex, sleGponOltControlProtection
				 }
			STATUS current
			DESCRIPTION
				"Description."
			::= { sleGponOltNotification 19 }


--   1.3.6.1.4.1.6296.101.23.2.3.20
-- 1.3.6.1.4.1.6296.101.23.2.3.20
		sleGponOltAuthStatsCleared NOTIFICATION-TYPE
			OBJECTS { sleGponOltControlRequest, sleGponOltControlTimeStamp, sleGponOltControlReqResult, sleGponOltControllndex }
			STATUS current
			DESCRIPTION
				"Description."
			::= { sleGponOltNotification 20 }


--   1.3.6.1.4.1.6296.101.23.2.3.21
-- 1.3.6.1.4.1.6296.101.23.2.3.21
		sleGponOltOpticParamChanged NOTIFICATION-TYPE
			OBJECTS { sleGponOltControlRequest, sleGponOltControlTimeStamp, sleGponOltControlReqResult, sleGponOltControllndex, sleGponOltControlOpticParam
				 }
			STATUS current
			DESCRIPTION
				"Description."
			::= { sleGponOltNotification 21 }


--   1.3.6.1.4.1.6296.101.23.2.3.22
-- 1.3.6.1.4.1.6296.101.23.2.3.22
		sleGponOltSrcMacMonitorChanged NOTIFICATION-TYPE
			OBJECTS { sleGponOltControlRequest, sleGponOltControlTimeStamp, sleGponOltControlReqResult, sleGponOltControlSrcMacMonitorAutoBlock, sleGponOltControlSrcMacMonitoEexpireTimeout,
				sleGponOltControlSrcMacMonitorStatus, sleGponOltControllndex }
			STATUS current
			DESCRIPTION
				"Description."
			::= { sleGponOltNotification 22 }


--   1.3.6.1.4.1.6296.101.23.2.3.23
-- 1.3.6.1.4.1.6296.101.23.2.3.23
		sleGponOltTotalUsBwChanged NOTIFICATION-TYPE
			OBJECTS { sleGponOltControlRequest, sleGponOltControlTimeStamp, sleGponOltControlReqResult, sleGponOltControllndex, sleGponOltControlTotalUsBw
				 }
			STATUS current
			DESCRIPTION
				"Description."
			::= { sleGponOltNotification 23 }


--  1.3.6.1.4.1.6296.101.23.2.3.24
		sleGponOltMaxOnuCountChanged NOTIFICATION-TYPE
			OBJECTS { sleGponOltControlRequest, sleGponOltControlTimeStamp, sleGponOltControlReqResult, sleGponOltControllndex, sleGponOltControlMaxOnuCount
				 }
			STATUS current
			DESCRIPTION
				"Description."
			::= { sleGponOltNotification 24 }


--  1.3.6.1.4.1.6296.101.23.2.3.25
		sleGponOltAntiSpoofingFilterChanged NOTIFICATION-TYPE
			OBJECTS { sleGponOltControlRequest, sleGponOltControlTimeStamp, sleGponOltControlReqResult, sleGponOltControllndex, sleGponOltControlAntiSpoofingFilter,
				sleGponOltControlAntiSpoofingExpireTime }
			STATUS current
			DESCRIPTION
				"Description."
			::= { sleGponOltNotification 25 }


--  1.3.6.1.4.1.6296.101.23.2.3.26
		sleGponOltBwBEMethodChanged NOTIFICATION-TYPE
			OBJECTS { sleGponOltControlRequest, sleGponOltControlTimeStamp, sleGponOltControlReqResult, sleGponOltControllndex, sleGponOltControlBwBEMethod
				 }
			STATUS current
			DESCRIPTION
				"setBwBEMethod"
			::= { sleGponOltNotification 26 }


--  1.3.6.1.4.1.6296.101.23.2.3.27
		sleGponOltDsGemMappingChanged NOTIFICATION-TYPE
			OBJECTS { sleGponOltControlRequest, sleGponOltControlTimeStamp, sleGponOltControlReqResult, sleGponOltControllndex, sleGponOltControlDsGemMapping
				 }
			STATUS current
			DESCRIPTION
				"setDsGemMapping"
			::= { sleGponOltNotification 27 }


--  1.3.6.1.4.1.6296.101.23.2.3.28
		sleGponOltFixedTcontCountChanged NOTIFICATION-TYPE
			OBJECTS { sleGponOltControlRequest, sleGponOltControlTimeStamp, sleGponOltControlReqResult, sleGponOltControllndex, sleGponOltControlFixedTcontCount
				 }
			STATUS current
			DESCRIPTION
				"setFixedTcontCount"
			::= { sleGponOltNotification 28 }


--  1.3.6.1.4.1.6296.101.23.2.3.29
		sleGponOltDynamicTcontCountChanged NOTIFICATION-TYPE
			OBJECTS { sleGponOltControlRequest, sleGponOltControlTimeStamp, sleGponOltControlReqResult, sleGponOltControllndex, sleGponOltControlDynamicTcontCount
				 }
			STATUS current
			DESCRIPTION
				"setDynamicTcontCount"
			::= { sleGponOltNotification 29 }


--  1.3.6.1.4.1.6296.101.23.2.3.30
		sleGponOltPortCountChanged NOTIFICATION-TYPE
			OBJECTS { sleGponOltControlRequest, sleGponOltControlTimeStamp, sleGponOltControlReqResult, sleGponOltControllndex, sleGponOltControlPortCount
				 }
			STATUS current
			DESCRIPTION
				"setPortCount"
			::= { sleGponOltNotification 30 }


--  1.3.6.1.4.1.6296.101.23.2.3.31
		sleGponOltDeactiveMonitorStatusChanged NOTIFICATION-TYPE
			OBJECTS { sleGponOltControlRequest, sleGponOltControlTimeStamp, sleGponOltControlReqResult, sleGponOltControllndex, sleGponOltControlDeactiveMonitorStatus
				 }
			STATUS current
			DESCRIPTION
				"setDeactiveMonitorStatus "
			::= { sleGponOltNotification 31 }


--  1.3.6.1.4.1.6296.101.23.2.3.32
		sleGponOltDeactiveMonitorRaisePercentChanged NOTIFICATION-TYPE
			OBJECTS { sleGponOltControlRequest, sleGponOltControlTimeStamp, sleGponOltControlReqResult, sleGponOltControllndex, sleGponOltControlDeactiveMonitorRaisePercent
				 }
			STATUS current
			DESCRIPTION
				"setDeactiveMonitorRaisePercent "
			::= { sleGponOltNotification 32 }


--  1.3.6.1.4.1.6296.101.23.2.3.33
		sleGponOltDeactiveMonitorClearPercentChanged NOTIFICATION-TYPE
			OBJECTS { sleGponOltControlRequest, sleGponOltControlTimeStamp, sleGponOltControlReqResult, sleGponOltControllndex, sleGponOltControlDeactiveMonitorClearPercent
				 }
			STATUS current
			DESCRIPTION
				"setDeactiveMonitorClearPercent "
			::= { sleGponOltNotification 33 }


--  1.3.6.1.4.1.6296.101.23.2.3.34
		sleGponOltDeactiveMonitorPeriodChanged NOTIFICATION-TYPE
			OBJECTS { sleGponOltControlRequest, sleGponOltControlTimeStamp, sleGponOltControlReqResult, sleGponOltControllndex, sleGponOltControlDeactiveMonitorPeriod
				 }
			STATUS current
			DESCRIPTION
				"setDeactiveMonitorPeriod "
			::= { sleGponOltNotification 34 }


--  1.3.6.1.4.1.6296.101.23.2.3.35
		sleGponOltDeactiveMonitorAlarmCleared NOTIFICATION-TYPE
			OBJECTS { sleGponOltControlRequest, sleGponOltControlTimeStamp, sleGponOltControlReqResult }
			STATUS current
			DESCRIPTION
				"clearDeactiveMonitorAlarm "
			::= { sleGponOltNotification 35 }


--  1.3.6.1.4.1.6296.101.23.2.3.36
		sleGponOltRegisterd NOTIFICATION-TYPE
			OBJECTS { sleGponOltControlRequest, sleGponOltControlTimeStamp, sleGponOltControlReqResult, sleGponOltControllndex }
			STATUS current
			DESCRIPTION
				"setOltRegister"
			::= { sleGponOltNotification 36 }


--  1.3.6.1.4.1.6296.101.23.2.3.37
		sleGponOltBerUsIntervalChanged NOTIFICATION-TYPE
			OBJECTS { sleGponOltControlRequest, sleGponOltControlTimeStamp, sleGponOltControlReqResult, sleGponOltControllndex, sleGponOltControlBerUpInterval
				 }
			STATUS current
			DESCRIPTION
				"setOltBer"
			::= { sleGponOltNotification 37 }


--  1.3.6.1.4.1.6296.101.23.2.3.38
		sleGponOltBerDsIntervalChanged NOTIFICATION-TYPE
			OBJECTS { sleGponOltControlRequest, sleGponOltControlTimeStamp, sleGponOltControlReqResult, sleGponOltControllndex, sleGponOltControlBerDownInterval
				 }
			STATUS current
			DESCRIPTION
				"setOltBer"
			::= { sleGponOltNotification 38 }


--  1.3.6.1.4.1.6296.101.23.2.3.39
		sleGponOltBerSfThresholdChanged NOTIFICATION-TYPE
			OBJECTS { sleGponOltControlRequest, sleGponOltControlTimeStamp, sleGponOltControlReqResult, sleGponOltControllndex, sleGponOltControlBerSfThreshold
				 }
			STATUS current
			DESCRIPTION
				"setOltBer"
			::= { sleGponOltNotification 39 }


--  1.3.6.1.4.1.6296.101.23.2.3.40
		sleGponOltBerSdThresholdChanged NOTIFICATION-TYPE
			OBJECTS { sleGponOltControlRequest, sleGponOltControlTimeStamp, sleGponOltControlReqResult, sleGponOltControllndex, sleGponOltControlBerSdThreshold
				 }
			STATUS current
			DESCRIPTION
				"setOltBer"
			::= { sleGponOltNotification 40 }


--  1.3.6.1.4.1.6296.101.23.2.3.41
		sleGponOltUsFlowMappingChanged NOTIFICATION-TYPE
			OBJECTS { sleGponOltControlRequest, sleGponOltControlTimeStamp, sleGponOltControlReqResult, sleGponOltControllndex, sleGponOltControlUsFlowMapping
				 }
			STATUS current
			DESCRIPTION
				"setUsFlowMapping"
			::= { sleGponOltNotification 41 }


--   1.3.6.1.4.1.6296.101.23.2.3.42
-- 1.3.6.1.4.1.6296.101.23.2.3.42
		sleGponOltDsQosMappingChanged NOTIFICATION-TYPE
			OBJECTS { sleGponOltControlRequest, sleGponOltControlTimeStamp, sleGponOltControlReqResult, sleGponOltControllndex, sleGponOltControlDsQosMappingQueueCount,
				sleGponOltControlDsQosMappingCos0Queue, sleGponOltControlDsQosMappingCos1Queue, sleGponOltControlDsQosMappingCos2Queue, sleGponOltControlDsQosMappingCos3Queue, sleGponOltControlDsQosMappingCos4Queue,
				sleGponOltControlDsQosMappingCos5Queue, sleGponOltControlDsQosMappingCos6Queue, sleGponOltControlDsQosMappingCos7Queue }
			STATUS current
			DESCRIPTION
				"setDsQosMapping"
			::= { sleGponOltNotification 42 }


--   1.3.6.1.4.1.6296.101.23.2.3.43
-- 1.3.6.1.4.1.6296.101.23.2.3.43
		sleGponOltDsQosMappingCleared NOTIFICATION-TYPE
			OBJECTS { sleGponOltControlRequest, sleGponOltControlTimeStamp, sleGponOltControlReqResult, sleGponOltControllndex }
			STATUS current
			DESCRIPTION
				"clearDsQosMapping"
			::= { sleGponOltNotification 43 }


--   1.3.6.1.4.1.6296.101.23.2.3.44
-- 1.3.6.1.4.1.6296.101.23.2.3.44
		sleGponOltDsQosMappingModeChanged NOTIFICATION-TYPE
			OBJECTS { sleGponOltControlRequest, sleGponOltControlTimeStamp, sleGponOltControlReqResult, sleGponOltControllndex, sleGponOltControlDsQosMappingMode
				 }
			STATUS current
			DESCRIPTION
				"setDsQosMappingMode"
			::= { sleGponOltNotification 44 }


--   1.3.6.1.4.1.6296.101.23.2.3.44
-- 1.3.6.1.4.1.6296.101.23.2.3.45
		sleGponOltAutoOnuBlockContMoveMacChanged NOTIFICATION-TYPE
			OBJECTS { sleGponOltControlRequest, sleGponOltControlTimeStamp, sleGponOltControlReqResult, sleGponOltControllndex, sleGponOltControlAutoOnuBlockContMoveMac
				 }
			STATUS current
			DESCRIPTION
				"setAutoOnuBlockContMoveMac  "
			::= { sleGponOltNotification 45 }


--  1.3.6.1.4.1.6296.101.23.2.3.46
		sleGponOltRxPowerUpdateModeChanged NOTIFICATION-TYPE
			OBJECTS { sleGponOltControlRequest, sleGponOltControlTimeStamp, sleGponOltControlReqResult, sleGponOltControllndex, sleGponOltControlRxPowerUpdateMode
				 }
			STATUS current
			DESCRIPTION
				"setOltRxPowerUpdateMode"
			::= { sleGponOltNotification 46 }


--  1.3.6.1.4.1.6296.101.23.2.3.47
		sleGponOltRxPowerThresholdChanged NOTIFICATION-TYPE
			OBJECTS { sleGponOltControlRequest, sleGponOltControlTimeStamp, sleGponOltControlReqResult, sleGponOltControllndex, sleGponOltControlRxPowerLowThreshold,
				sleGponOltControlRxPowerHighThreshold }
			STATUS current
			DESCRIPTION
				"setOltRxPowerThreshold"
			::= { sleGponOltNotification 47 }


--  1.3.6.1.4.1.6296.101.23.2.3.48
		sleGponOltStormControlThresholdChanged NOTIFICATION-TYPE
			OBJECTS { sleGponOltControlRequest, sleGponOltControlTimeStamp, sleGponOltControlReqResult, sleGponOltControlOnuInactiveAgingTime }
			STATUS current
			DESCRIPTION
				"Description."
			::= { sleGponOltNotification 48 }


--  1.3.6.1.4.1.6296.101.23.2.3.49
		sleGponOltStormControlChanged NOTIFICATION-TYPE
			OBJECTS { sleGponOltControlRequest, sleGponOltControlTimeStamp, sleGponOltControlReqResult, sleGponOltControllndex, sleGponOltControlBcastThreshold,
				sleGponOltControlMulticastThreshold, sleGponOltControlDLFThreshold }
			STATUS current
			DESCRIPTION
				"setOltRxPowerThreshold"
			::= { sleGponOltNotification 49 }


--  1.3.6.1.4.1.6296.101.23.2.3.50
		sleGponOltControlOnuAuthControlModeChanged NOTIFICATION-TYPE
			OBJECTS { sleGponOltControlRequest, sleGponOltControlTimeStamp, sleGponOltControlReqResult, sleGponOltControllndex, sleGponOltControlOnuAuthControlMode
				 }
			STATUS current
			DESCRIPTION
				"setOltRxPowerThreshold"
			::= { sleGponOltNotification 50 }


--  1.3.6.1.4.1.6296.101.23.2.3.51
		sleGponOltControlOnuAuthReauthenChanged NOTIFICATION-TYPE
			OBJECTS { sleGponOltControlRequest, sleGponOltControlTimeStamp, sleGponOltControlReqResult, sleGponOltControllndex }
			STATUS current
			DESCRIPTION
				"setOltRxPowerThreshold"
			::= { sleGponOltNotification 51 }


		sleGponOltTransceiverTypeChanged NOTIFICATION-TYPE
			OBJECTS { sleGponOltControlRequest, sleGponOltControlTimeStamp, sleGponOltControlReqResult, sleGponOltControllndex, sleGponOltControlTransceiverType
				 }
			STATUS current
			DESCRIPTION
				"setOltTransceiverType"
			::= { sleGponOltNotification 52 }


		sleGponOltOmccRecoveryChanged NOTIFICATION-TYPE
			OBJECTS { sleGponOltControlRequest, sleGponOltControlTimeStamp, sleGponOltControlReqResult, sleGponOltControllndex, sleGponOltControlOmccRecovery,
				sleGponOltControlOmccRecoveryMethod, sleGponOltControlOmccRecoveryThreshold }
			STATUS current
			DESCRIPTION
				"setOltOmccRecovery"
			::= { sleGponOltNotification 53 }


--   1.3.6.1.4.1.6296.101.23.3
-- 1.3.6.1.4.1.6296.101.23.3
		sleGponOnu OBJECT IDENTIFIER ::= { sleGpon 3 }


--   1.3.6.1.4.1.6296.101.23.3.1
-- 1.3.6.1.4.1.6296.101.23.3.1
		sleGponOnuTable OBJECT-TYPE
			SYNTAX SEQUENCE OF SleGponOnuEntry
			MAX-ACCESS not-accessible
			STATUS current
			DESCRIPTION
				"sleGponOnuTable"
			::= { sleGponOnu 1 }


--   1.3.6.1.4.1.6296.101.23.3.1.1
-- 1.3.6.1.4.1.6296.101.23.3.1.1
		sleGponOnuEntry OBJECT-TYPE
			SYNTAX SleGponOnuEntry
			MAX-ACCESS not-accessible
			STATUS current
			DESCRIPTION
				"key: sleGponOltId, sleGponOnuId"
			INDEX { sleGponOltId, sleGponOnuId }
			::= { sleGponOnuTable 1 }


		SleGponOnuEntry ::=
			SEQUENCE {
				sleGponOnuId
					INTEGER,
				sleGponOnuStatus
					INTEGER,
				sleGponOnuMode
					INTEGER,
				sleGponOnuSerial
					OCTET STRING,
				sleGponOnuPasswd
					OCTET STRING,
				sleGponOnuPasswdMode
					INTEGER,
				sleGponOnuEncMode
					INTEGER,
				sleGponOnuProfile
					OCTET STRING,
				sleGponOnuHostname
					OCTET STRING,
				sleGponOnuDistance
					INTEGER,
				sleGponOnuHwAddress
					OCTET STRING,
				sleGponOnuNosActiveVersion
					OCTET STRING,
				sleGponOnuNosStandbyVersion
					OCTET STRING,
				sleGponOnuNosUpgradeStatus
					INTEGER,
				sleGponOnuIsFirst
					INTEGER,
				sleGponOnuRxPower
					INTEGER,
				sleGponOnuModelName
					OCTET STRING,
				sleGponOnuDescription
					OCTET STRING,
				sleGponOnuNosAutoUpgradeWaitStatus
					INTEGER,
				sleGponOnuNosAutoUpgradeFailCount
					INTEGER,
				sleGponOnuOltRxPower
					INTEGER,
				sleGponOnuRTD
					Integer32,
				sleGponOnuLinkUpTime
					Counter64,
				sleGponOnuAuthenticationStatus
					INTEGER,
				sleGponOnuVlanID
					INTEGER,
				sleGponOnuIpAddress
					IpAddress,
				sleGponOnuNetmask
					IpAddress,
				sleGponOnuHWType
					INTEGER,
				sleGponOnuRegistrationCnt
					Integer32,
				sleGponOnuAuthAcceptedCnt
					Integer32,
				sleGponOnuAuthRejectedCnt
					Integer32,
				sleGponOnuAuthChallengedCnt
					Integer32,
				sleGponOnuFecModeUS
					INTEGER,
				sleGponOnuIPMode
					INTEGER,
				sleGponOnuIPAddr
					IpAddress,
				sleGponOnuIPMask
					IpAddress,
				sleGponOnuIPGw
					IpAddress,
				sleGponOnuIPDns1
					IpAddress,
				sleGponOnuIPDns2
					IpAddress,
				sleGponOnuBatteryStatus
					INTEGER,
				sleGponOnuMgmtSerialNo
					OCTET STRING,
				sleGponOnuUserMacCnt
					Integer32,
				sleGponOnuOmciPingTestResult
					OCTET STRING,
				sleGponOnuOmciPingTestResultAvg
					OCTET STRING,
				sleGponOnuDeactiveReason
					INTEGER,
				sleGponOnuControlPathIpAddr
					IpAddress,
				sleGponOnuControlPathMacAddr
					OCTET STRING,
				sleGponOnuControlPathStatus
					Integer32,
				sleGponOnuControlPathUptime
					TimeTicks,
				sleGponOnuPMProfile
					OCTET STRING,
				sleGponOnuUpCount
					Integer32,
				sleGponOnuDownCount
					Integer32,
				sleGponOnuNosDefaultPartition
					INTEGER,
				sleGponOnuNosActivePartition
					INTEGER,
				sleGponOnuBlockStatus
					INTEGER,
				sleGponOnuBlockReason
					INTEGER,
				sleGponOnuLastActiveFailReason
					INTEGER,
				sleGponOnuEqD
					INTEGER,
				sleGponOnuMaxTcont
					INTEGER,
				sleGponOnuMaxUsQueuePerTcont
					INTEGER,
				sleGponOnuSysUpTime
					Counter64,
				sleGponOnuVenderProduct
					INTEGER,
				sleGponOnuSlotId
					INTEGER,
				sleGponOnuPortsID
					INTEGER,
				sleGponOnuOperStatus
					Integer32,
				sleGponOnuMapperID
					Integer32,
				sleGponOnuVoipAvailSignalProtocol
					BITS,
				sleGponOnuVoipAvailConfigMethod
					BITS,
				sleGponOnuSupplierSerial
					OCTET STRING,
				sleGponOnuHWRevision
					OCTET STRING,
				sleGponOnuCPULoad
					INTEGER,
				sleGponOnuCPULoadThreshold
					INTEGER,
				sleGponOnuMemoryUsage
					INTEGER,
				sleGponOnuMemoryThreshold
					INTEGER,
				sleGponOnuTemperature
					INTEGER,
				sleGponOnuTemperatureHighThreshold
					INTEGER,
				sleGponOnuTemperatureLowThreshold
					INTEGER,
				sleGponOnuLoopDetectStateSupport
					INTEGER,
				sleGponOnuLoopDetectStateDetect
					INTEGER,
				sleGponOnuLoopDetectStateBlock
					INTEGER,
				sleGponOnuLoopDetectUnblockReason
					INTEGER,
				sleGponOnuSupportFunction
					BITS,
				sleGponOnuAccountUserName
					OCTET STRING,
				sleGponOnuAccountPassword
					OCTET STRING,
				sleGponOnuInactiveTime
					Counter64,
				sleGponOnuRadiusAuthStatus
					INTEGER,
				sleGponOnuRadiusAuthReceiveProfile
					OCTET STRING,
				sleGponOnuMgmtIpPathProtocol
					INTEGER,
				sleGponOnuMgmtIpPathId
					OCTET STRING,
				sleGponOnuMgmtIpPathPassword
					OCTET STRING,
				sleGponOnuMgmtIpPathUrl
					OCTET STRING,
				sleGponOnuMgmtIpPathFileName
					OCTET STRING,
				sleGponOnuMgmtIpPathState
					INTEGER,
				sleGponOnuServiceMode
					INTEGER,
				sleGponOnuServiceStatus
					INTEGER,
				sleGponOnuAutoUpgradeMode
					INTEGER,
				sleGponOnuBootReason
					INTEGER,
				sleGponOnuAlarmStatus
					BITS,
				sleGponOnuAuthOnuProfile
					OCTET STRING,
				sleGponOnuAuthOnuVlan4
					Integer32,
				sleGponOnuAuthOnuVlan6
					Integer32,
				sleGponOnuAuthOnuIpv4
					OCTET STRING,
				sleGponOnuAuthOnuIpv6
					OCTET STRING,
				sleGponOnuAuthOnuUniPortAdmin
					Integer32,
				sleGponOnuAuthOnuUniEthMedium
					Integer32,
				sleGponOnuAuthOnuUniEthSpeed
					Integer32,
				sleGponOnuAuthOnuUniEthDuplex
					Integer32,
				sleGponOnuAuthOnuErrorReason
					INTEGER,
				sleGponOnuAuthOnuOmccVersion
					Integer32,
				sleGponOnuGspStstusUptime
					TimeTicks,
				sleGponOnuGspConfigUptime
					TimeTicks
			 }

--   1.3.6.1.4.1.6296.101.23.3.1.1.1
-- 1.3.6.1.4.1.6296.101.23.3.1.1.1
		sleGponOnuId OBJECT-TYPE
			SYNTAX INTEGER (1..256)
			MAX-ACCESS read-only
			STATUS current
			DESCRIPTION
				"Gpon Onu Index"
			::= { sleGponOnuEntry 1 }


--   1.3.6.1.4.1.6296.101.23.3.1.1.2
-- 1.3.6.1.4.1.6296.101.23.3.1.1.2
		sleGponOnuStatus OBJECT-TYPE
			SYNTAX INTEGER
				{
				invalid(0),
				inactive(1),
				active(2),
				running(3),
				activePending(4),
				deactivePending(5),
				disablePending(6),
				disable(7),
				unknown(255)
				}
			MAX-ACCESS read-only
			STATUS current
			DESCRIPTION
				"Gpon Onu Status"
			::= { sleGponOnuEntry 2 }


--   1.3.6.1.4.1.6296.101.23.3.1.1.3
-- 1.3.6.1.4.1.6296.101.23.3.1.1.3
		sleGponOnuMode OBJECT-TYPE
			SYNTAX INTEGER
				{
				notlearned(0),
				manual(1),
				auto(2)
				}
			MAX-ACCESS read-only
			STATUS current
			DESCRIPTION
				"Gpon Onu register-mode"
			::= { sleGponOnuEntry 3 }


--   1.3.6.1.4.1.6296.101.23.3.1.1.4
-- 1.3.6.1.4.1.6296.101.23.3.1.1.4
		sleGponOnuSerial OBJECT-TYPE
			SYNTAX OCTET STRING (SIZE (1..64))
			MAX-ACCESS read-only
			STATUS current
			DESCRIPTION
				"ONU Serial Number"
			::= { sleGponOnuEntry 4 }


--   1.3.6.1.4.1.6296.101.23.3.1.1.5
-- 1.3.6.1.4.1.6296.101.23.3.1.1.5
		sleGponOnuPasswd OBJECT-TYPE
			SYNTAX OCTET STRING (SIZE (1..64))
			MAX-ACCESS read-only
			STATUS current
			DESCRIPTION
				"ONU Password"
			::= { sleGponOnuEntry 5 }


--   1.3.6.1.4.1.6296.101.23.3.1.1.6
-- 1.3.6.1.4.1.6296.101.23.3.1.1.6
		sleGponOnuPasswdMode OBJECT-TYPE
			SYNTAX INTEGER
				{
				enable(1),
				disable(2)
				}
			MAX-ACCESS read-only
			STATUS current
			DESCRIPTION
				"Password auto-learning "
			::= { sleGponOnuEntry 6 }


--   1.3.6.1.4.1.6296.101.23.3.1.1.7
-- 1.3.6.1.4.1.6296.101.23.3.1.1.7
		sleGponOnuEncMode OBJECT-TYPE
			SYNTAX INTEGER
				{
				enable(1),
				disable(2)
				}
			MAX-ACCESS read-only
			STATUS current
			DESCRIPTION
				"Encryption mode"
			::= { sleGponOnuEntry 7 }


--   1.3.6.1.4.1.6296.101.23.3.1.1.8
-- 1.3.6.1.4.1.6296.101.23.3.1.1.8
		sleGponOnuProfile OBJECT-TYPE
			SYNTAX OCTET STRING
			MAX-ACCESS read-only
			STATUS current
			DESCRIPTION
				"Onu assigned Profile."
			::= { sleGponOnuEntry 8 }


--   1.3.6.1.4.1.6296.101.23.3.1.1.9
-- 1.3.6.1.4.1.6296.101.23.3.1.1.9
		sleGponOnuHostname OBJECT-TYPE
			SYNTAX OCTET STRING
			MAX-ACCESS read-only
			STATUS current
			DESCRIPTION
				"ONU Hostname."
			::= { sleGponOnuEntry 9 }


--   1.3.6.1.4.1.6296.101.23.3.1.1.10
-- 1.3.6.1.4.1.6296.101.23.3.1.1.10
		sleGponOnuDistance OBJECT-TYPE
			SYNTAX INTEGER (1..65535)
			UNITS "1m"
			MAX-ACCESS read-only
			STATUS current
			DESCRIPTION
				"ONU Distance information."
			::= { sleGponOnuEntry 10 }


--   1.3.6.1.4.1.6296.101.23.3.1.1.11
-- 1.3.6.1.4.1.6296.101.23.3.1.1.11
		sleGponOnuHwAddress OBJECT-TYPE
			SYNTAX OCTET STRING (SIZE (0..6))
			MAX-ACCESS read-only
			STATUS current
			DESCRIPTION
				"Onu System H/W address."
			::= { sleGponOnuEntry 11 }


--   1.3.6.1.4.1.6296.101.23.3.1.1.12
-- 1.3.6.1.4.1.6296.101.23.3.1.1.12
		sleGponOnuNosActiveVersion OBJECT-TYPE
			SYNTAX OCTET STRING
			MAX-ACCESS read-only
			STATUS current
			DESCRIPTION
				"ONU Firmware Version of Active"
			::= { sleGponOnuEntry 12 }


--   1.3.6.1.4.1.6296.101.23.3.1.1.13
-- 1.3.6.1.4.1.6296.101.23.3.1.1.13
		sleGponOnuNosStandbyVersion OBJECT-TYPE
			SYNTAX OCTET STRING
			MAX-ACCESS read-only
			STATUS current
			DESCRIPTION
				"ONU Firmware Version of Standby"
			::= { sleGponOnuEntry 13 }


--   1.3.6.1.4.1.6296.101.23.3.1.1.14
-- 1.3.6.1.4.1.6296.101.23.3.1.1.14
		sleGponOnuNosUpgradeStatus OBJECT-TYPE
			SYNTAX INTEGER
				{
				none(0),
				downloadProgress(1),
				downloadProgressforDevBusy(2),
				endDownloadForDevBusy(3),
				downloadComplete(4),
				downloadFail(5),
				commitWaitValid(6),
				commitProgress(7),
				commitProgressforDevBusy(8),
				commitFailForDevBusy(9),
				commitComplete(10),
				commitFail(11),
				changeActiveComplete(12),
				changeActiveFailforDevBusy(13),
				changeActiveFail(14),
				autoUpgradeResetWaiting(15),
				autoUpgradeFail(16),
				endDownloadSend(17),
				endDownloadComplete(18),
				bootloaderDownloadProgress(19),
				bootloaderDownloadDevBusy(20),
				bootloaderEndDownloadDevBusy(21),
				bootloaderDownloadComplete(22),
				bootloaderDownloadFail(23),
				bootloaderEndDownloadRequest(24),
				bootloaderEndDownloadComplete(25),
				autoUpgradeComplete(26),
				downloadWait(27),
				unknown(255)
				}
			MAX-ACCESS read-only
			STATUS current
			DESCRIPTION
				"Onu firmware upgrade status."
			::= { sleGponOnuEntry 14 }


--   1.3.6.1.4.1.6296.101.23.3.1.1.15
-- 1.3.6.1.4.1.6296.101.23.3.1.1.15
		sleGponOnuIsFirst OBJECT-TYPE
			SYNTAX INTEGER
				{
				true(1),
				false(2)
				}
			MAX-ACCESS accessible-for-notify
			STATUS current
			DESCRIPTION
				"Whether it is first registration or not."
			::= { sleGponOnuEntry 15 }


--   1.3.6.1.4.1.6296.101.23.3.1.1.16
-- 1.3.6.1.4.1.6296.101.23.3.1.1.16
		sleGponOnuRxPower OBJECT-TYPE
			SYNTAX INTEGER (1..65535)
			UNITS "0.1dBm"
			MAX-ACCESS read-only
			STATUS current
			DESCRIPTION
				"Rx Optical power."
			::= { sleGponOnuEntry 16 }


--   1.3.6.1.4.1.6296.101.23.3.1.1.17
-- 1.3.6.1.4.1.6296.101.23.3.1.1.17
		sleGponOnuModelName OBJECT-TYPE
			SYNTAX OCTET STRING
			MAX-ACCESS read-only
			STATUS current
			DESCRIPTION
				"ONU Model name."
			::= { sleGponOnuEntry 17 }


--   1.3.6.1.4.1.6296.101.23.3.1.1.18
-- 1.3.6.1.4.1.6296.101.23.3.1.1.18
		sleGponOnuDescription OBJECT-TYPE
			SYNTAX OCTET STRING
			MAX-ACCESS read-only
			STATUS current
			DESCRIPTION
				"ONU description."
			::= { sleGponOnuEntry 18 }


--   1.3.6.1.4.1.6296.101.23.3.1.1.19
-- 1.3.6.1.4.1.6296.101.23.3.1.1.19
		sleGponOnuNosAutoUpgradeWaitStatus OBJECT-TYPE
			SYNTAX INTEGER
				{
				waiting(1),
				nowaiting(2)
				}
			MAX-ACCESS read-only
			STATUS current
			DESCRIPTION
				"Onu firmware auto-upgrade wait status."
			::= { sleGponOnuEntry 19 }


--   1.3.6.1.4.1.6296.101.23.3.1.1.20
-- 1.3.6.1.4.1.6296.101.23.3.1.1.20
		sleGponOnuNosAutoUpgradeFailCount OBJECT-TYPE
			SYNTAX INTEGER (1..65535)
			MAX-ACCESS read-only
			STATUS current
			DESCRIPTION
				"Onu firmware upgrade fail count."
			::= { sleGponOnuEntry 20 }


--   1.3.6.1.4.1.6296.101.23.3.1.1.21
-- 1.3.6.1.4.1.6296.101.23.3.1.1.21
		sleGponOnuOltRxPower OBJECT-TYPE
			SYNTAX INTEGER (1..65535)
			UNITS "0.1dBm"
			MAX-ACCESS read-only
			STATUS current
			DESCRIPTION
				"Rx Optical power of olt-side."
			::= { sleGponOnuEntry 21 }


--   1.3.6.1.4.1.6296.101.23.3.1.1.22
-- 1.3.6.1.4.1.6296.101.23.3.1.1.22
		sleGponOnuRTD OBJECT-TYPE
			SYNTAX Integer32
			UNITS "bit"
			MAX-ACCESS read-only
			STATUS current
			DESCRIPTION
				"The RTD."
			::= { sleGponOnuEntry 22 }


--   1.3.6.1.4.1.6296.101.23.3.1.1.23
-- 1.3.6.1.4.1.6296.101.23.3.1.1.23
		sleGponOnuLinkUpTime OBJECT-TYPE
			SYNTAX Counter64
			UNITS "1 sec"
			MAX-ACCESS read-only
			STATUS current
			DESCRIPTION
				"The elapsed time after ont is up."
			::= { sleGponOnuEntry 23 }


--   1.3.6.1.4.1.6296.101.23.3.1.1.24
-- 1.3.6.1.4.1.6296.101.23.3.1.1.24
		sleGponOnuAuthenticationStatus OBJECT-TYPE
			SYNTAX INTEGER
				{
				normal(1),
				rangingFail(2),
				passwdInconsistencyFail(3),
				passwdMismatchFail(4),
				passwdTimeoutFail(5),
				passwdONUAlarmFail(6),
				passwdDisableEventFail(7),
				passwdLosFail(8),
				unknown(255)
				}
			MAX-ACCESS read-only
			STATUS current
			DESCRIPTION
				"The authentication status."
			::= { sleGponOnuEntry 24 }


--   1.3.6.1.4.1.6296.101.23.3.1.1.25
-- 1.3.6.1.4.1.6296.101.23.3.1.1.25
		sleGponOnuVlanID OBJECT-TYPE
			SYNTAX INTEGER (1..65535)
			MAX-ACCESS read-only
			STATUS current
			DESCRIPTION
				"The ont's vlan id."
			::= { sleGponOnuEntry 25 }


--   1.3.6.1.4.1.6296.101.23.3.1.1.26
-- 1.3.6.1.4.1.6296.101.23.3.1.1.26
		sleGponOnuIpAddress OBJECT-TYPE
			SYNTAX IpAddress
			MAX-ACCESS read-only
			STATUS current
			DESCRIPTION
				"The ont's ip address."
			::= { sleGponOnuEntry 26 }


--   1.3.6.1.4.1.6296.101.23.3.1.1.27
-- 1.3.6.1.4.1.6296.101.23.3.1.1.27
		sleGponOnuNetmask OBJECT-TYPE
			SYNTAX IpAddress
			MAX-ACCESS read-only
			STATUS current
			DESCRIPTION
				"The ont's netmask."
			::= { sleGponOnuEntry 27 }


--   1.3.6.1.4.1.6296.101.23.3.1.1.28
-- 1.3.6.1.4.1.6296.101.23.3.1.1.28
		sleGponOnuHWType OBJECT-TYPE
			SYNTAX INTEGER (1..65535)
			MAX-ACCESS read-only
			STATUS current
			DESCRIPTION
				"The ont's HW type."
			::= { sleGponOnuEntry 28 }


--   1.3.6.1.4.1.6296.101.23.3.1.1.29
-- 1.3.6.1.4.1.6296.101.23.3.1.1.29
		sleGponOnuRegistrationCnt OBJECT-TYPE
			SYNTAX Integer32
			MAX-ACCESS read-only
			STATUS current
			DESCRIPTION
				"The times of registration."
			::= { sleGponOnuEntry 29 }


--   1.3.6.1.4.1.6296.101.23.3.1.1.30
-- 1.3.6.1.4.1.6296.101.23.3.1.1.30
		sleGponOnuAuthAcceptedCnt OBJECT-TYPE
			SYNTAX Integer32
			MAX-ACCESS read-only
			STATUS current
			DESCRIPTION
				"The times of acception."
			::= { sleGponOnuEntry 30 }


--   1.3.6.1.4.1.6296.101.23.3.1.1.31
-- 1.3.6.1.4.1.6296.101.23.3.1.1.31
		sleGponOnuAuthRejectedCnt OBJECT-TYPE
			SYNTAX Integer32
			MAX-ACCESS read-only
			STATUS current
			DESCRIPTION
				"The times of rejection."
			::= { sleGponOnuEntry 31 }


--   1.3.6.1.4.1.6296.101.23.3.1.1.32
-- 1.3.6.1.4.1.6296.101.23.3.1.1.32
		sleGponOnuAuthChallengedCnt OBJECT-TYPE
			SYNTAX Integer32
			MAX-ACCESS read-only
			STATUS current
			DESCRIPTION
				"The times of challenge."
			::= { sleGponOnuEntry 32 }


--   1.3.6.1.4.1.6296.101.23.3.1.1.33
-- 1.3.6.1.4.1.6296.101.23.3.1.1.33
		sleGponOnuFecModeUS OBJECT-TYPE
			SYNTAX INTEGER
				{
				enable(1),
				disable(2)
				}
			MAX-ACCESS read-only
			STATUS current
			DESCRIPTION
				"UpStream FEC mode"
			::= { sleGponOnuEntry 33 }


--   1.3.6.1.4.1.6296.101.23.3.1.1.34
-- 1.3.6.1.4.1.6296.101.23.3.1.1.34
		sleGponOnuIPMode OBJECT-TYPE
			SYNTAX INTEGER
				{
				dhcp(1),
				manual(2)
				}
			MAX-ACCESS read-only
			STATUS current
			DESCRIPTION
				"Ip Addressing mode
				DHCP or Manual (UnUsed)"
			::= { sleGponOnuEntry 34 }


--   1.3.6.1.4.1.6296.101.23.3.1.1.35
-- 1.3.6.1.4.1.6296.101.23.3.1.1.35
		sleGponOnuIPAddr OBJECT-TYPE
			SYNTAX IpAddress
			MAX-ACCESS read-only
			STATUS current
			DESCRIPTION
				"Onu IP address(UnUsed)"
			::= { sleGponOnuEntry 35 }


--   1.3.6.1.4.1.6296.101.23.3.1.1.36
-- 1.3.6.1.4.1.6296.101.23.3.1.1.36
		sleGponOnuIPMask OBJECT-TYPE
			SYNTAX IpAddress
			MAX-ACCESS read-only
			STATUS current
			DESCRIPTION
				"Onu IP Netmask(UnUsed)"
			::= { sleGponOnuEntry 36 }


--   1.3.6.1.4.1.6296.101.23.3.1.1.37
-- 1.3.6.1.4.1.6296.101.23.3.1.1.37
		sleGponOnuIPGw OBJECT-TYPE
			SYNTAX IpAddress
			MAX-ACCESS read-only
			STATUS current
			DESCRIPTION
				"Onu Gateway(UnUsed)"
			::= { sleGponOnuEntry 37 }


--   1.3.6.1.4.1.6296.101.23.3.1.1.38
-- 1.3.6.1.4.1.6296.101.23.3.1.1.38
		sleGponOnuIPDns1 OBJECT-TYPE
			SYNTAX IpAddress
			MAX-ACCESS read-only
			STATUS current
			DESCRIPTION
				"Onu DNS primary(UnUsed)"
			::= { sleGponOnuEntry 38 }


--   1.3.6.1.4.1.6296.101.23.3.1.1.39
-- 1.3.6.1.4.1.6296.101.23.3.1.1.39
		sleGponOnuIPDns2 OBJECT-TYPE
			SYNTAX IpAddress
			MAX-ACCESS read-only
			STATUS current
			DESCRIPTION
				"Onu DNS secondary(Unused)"
			::= { sleGponOnuEntry 39 }


--   1.3.6.1.4.1.6296.101.23.3.1.1.40
-- 1.3.6.1.4.1.6296.101.23.3.1.1.40
		sleGponOnuBatteryStatus OBJECT-TYPE
			SYNTAX INTEGER
				{
				powering(1),
				missing(2),
				failure(3),
				low(4)
				}
			MAX-ACCESS read-only
			STATUS current
			DESCRIPTION
				"Onu battery status."
			::= { sleGponOnuEntry 40 }


--   1.3.6.1.4.1.6296.101.23.3.1.1.41
-- 1.3.6.1.4.1.6296.101.23.3.1.1.41
		sleGponOnuMgmtSerialNo OBJECT-TYPE
			SYNTAX OCTET STRING
			MAX-ACCESS read-only
			STATUS current
			DESCRIPTION
				"The ONU management serial number"
			::= { sleGponOnuEntry 41 }


--   1.3.6.1.4.1.6296.101.23.3.1.1.42
-- 1.3.6.1.4.1.6296.101.23.3.1.1.42
		sleGponOnuUserMacCnt OBJECT-TYPE
			SYNTAX Integer32
			MAX-ACCESS read-only
			STATUS current
			DESCRIPTION
				"The count of MAC addresses that are leant at the running ONU."
			::= { sleGponOnuEntry 42 }


--   1.3.6.1.4.1.6296.101.23.3.1.1.43
-- 1.3.6.1.4.1.6296.101.23.3.1.1.43
		sleGponOnuOmciPingTestResult OBJECT-TYPE
			SYNTAX OCTET STRING
			MAX-ACCESS read-only
			STATUS current
			DESCRIPTION
				"OMCI ping test result.
				Result Format : Sent Packets/Received Packets/Lost Packets"
			::= { sleGponOnuEntry 43 }


--   1.3.6.1.4.1.6296.101.23.3.1.1.44
-- 1.3.6.1.4.1.6296.101.23.3.1.1.44
		sleGponOnuOmciPingTestResultAvg OBJECT-TYPE
			SYNTAX OCTET STRING
			MAX-ACCESS read-only
			STATUS current
			DESCRIPTION
				"OMCI ping test result average.
				Result Average Format : minimum/maximum/averge"
			::= { sleGponOnuEntry 44 }


--   1.3.6.1.4.1.6296.101.23.3.1.1.45
-- 1.3.6.1.4.1.6296.101.23.3.1.1.45
		sleGponOnuDeactiveReason OBJECT-TYPE
			SYNTAX INTEGER
				{
				none(1),
				dgi(2),
				losi(3),
				lofi(4),
				sfi(5),
				sufi(6),
				loai(7),
				loami(8),
				loki(9),
				adminReset(10),
				adminActiveChange(11),
				adminOltConfiguration(12),
				adminSlotRestart(13),
				adminSlotRemove(14),
				adminRogueOnuCandidate(15),
				adminRogueOnu(16),
				adminRogueOnuSelfDetectBlock(17),
				adminTxOffOptic(18),
				adminDeactivate(19),
				adminOltDeactivate(20),
				adminOmccDown(21),
				adminSetRedundancy(22),
				adminRemoveOnu(23),
				adminServiceMode(24),
				adminManualPowerOff(25),
				los(100),
				onuDeactReasonRanging(101),
				onuDeactReasonPasswdAuthentication(102),
				onuDeactReasonPasswdInconsistency(103),
				onuDeactReasonPasswdMismatch(104),
				onuDeactReasonPasswdTimeout(105),
				onuDeactReasonPasswdOnuAlarm(106),
				onuDeactReasonPasswdDisableEvent(107),
				unknown(255)
				}
			MAX-ACCESS read-only
			STATUS current
			DESCRIPTION
				"Onu inactive reason."
			::= { sleGponOnuEntry 45 }


--   1.3.6.1.4.1.6296.101.23.3.1.1.46
-- 1.3.6.1.4.1.6296.101.23.3.1.1.46
		sleGponOnuControlPathIpAddr OBJECT-TYPE
			SYNTAX IpAddress
			MAX-ACCESS read-only
			STATUS current
			DESCRIPTION
				"IP Address for ONU Control plane"
			::= { sleGponOnuEntry 46 }


--   1.3.6.1.4.1.6296.101.23.3.1.1.47
-- 1.3.6.1.4.1.6296.101.23.3.1.1.47
		sleGponOnuControlPathMacAddr OBJECT-TYPE
			SYNTAX OCTET STRING
			MAX-ACCESS read-only
			STATUS current
			DESCRIPTION
				"MAC Address for ONU Control plane"
			::= { sleGponOnuEntry 47 }


--   1.3.6.1.4.1.6296.101.23.3.1.1.48
-- 1.3.6.1.4.1.6296.101.23.3.1.1.48
		sleGponOnuControlPathStatus OBJECT-TYPE
			SYNTAX Integer32
			MAX-ACCESS read-only
			STATUS current
			DESCRIPTION
				"The status about ONU's control path."
			::= { sleGponOnuEntry 48 }


--   1.3.6.1.4.1.6296.101.23.3.1.1.49
-- 1.3.6.1.4.1.6296.101.23.3.1.1.49
		sleGponOnuControlPathUptime OBJECT-TYPE
			SYNTAX TimeTicks
			MAX-ACCESS read-only
			STATUS current
			DESCRIPTION
				"The elapsed time that control path has been connect."
			::= { sleGponOnuEntry 49 }


--   1.3.6.1.4.1.6296.101.23.3.1.1.50
-- 1.3.6.1.4.1.6296.101.23.3.1.1.50
		sleGponOnuPMProfile OBJECT-TYPE
			SYNTAX OCTET STRING
			MAX-ACCESS read-only
			STATUS current
			DESCRIPTION
				"The assigned PM-profile
				"
			::= { sleGponOnuEntry 50 }


--   1.3.6.1.4.1.6296.101.23.3.1.1.51
-- 1.3.6.1.4.1.6296.101.23.3.1.1.51
		sleGponOnuUpCount OBJECT-TYPE
			SYNTAX Integer32
			MAX-ACCESS read-only
			STATUS current
			DESCRIPTION
				"The link up count"
			::= { sleGponOnuEntry 51 }


--   1.3.6.1.4.1.6296.101.23.3.1.1.52
-- 1.3.6.1.4.1.6296.101.23.3.1.1.52
		sleGponOnuDownCount OBJECT-TYPE
			SYNTAX Integer32
			MAX-ACCESS read-only
			STATUS current
			DESCRIPTION
				"The link up count"
			::= { sleGponOnuEntry 52 }


--   1.3.6.1.4.1.6296.101.23.3.1.1.53
-- 1.3.6.1.4.1.6296.101.23.3.1.1.53
		sleGponOnuNosDefaultPartition OBJECT-TYPE
			SYNTAX INTEGER
				{
				os1(1),
				os2(2),
				unknown(255)
				}
			MAX-ACCESS read-only
			STATUS current
			DESCRIPTION
				"The default NOS partition."
			::= { sleGponOnuEntry 53 }


--   1.3.6.1.4.1.6296.101.23.3.1.1.54
-- 1.3.6.1.4.1.6296.101.23.3.1.1.54
		sleGponOnuNosActivePartition OBJECT-TYPE
			SYNTAX INTEGER
				{
				os1(1),
				os2(2),
				unknown(255)
				}
			MAX-ACCESS read-only
			STATUS current
			DESCRIPTION
				"The current active NOS partition.."
			::= { sleGponOnuEntry 54 }


--   1.3.6.1.4.1.6296.101.23.3.1.1.55
-- 1.3.6.1.4.1.6296.101.23.3.1.1.55
		sleGponOnuBlockStatus OBJECT-TYPE
			SYNTAX INTEGER
				{
				autoblock(1),
				manualblock(2),
				unblock(255)
				}
			MAX-ACCESS read-only
			STATUS current
			DESCRIPTION
				"The ONU block status."
			::= { sleGponOnuEntry 55 }


--   1.3.6.1.4.1.6296.101.23.3.1.1.56
-- 1.3.6.1.4.1.6296.101.23.3.1.1.56
		sleGponOnuBlockReason OBJECT-TYPE
			SYNTAX INTEGER
				{
				mnanualblock(1),
				sourcemac(2),
				movemac(3),
				none(255)
				}
			MAX-ACCESS read-only
			STATUS current
			DESCRIPTION
				"The ONU Block reason."
			::= { sleGponOnuEntry 56 }


--   1.3.6.1.4.1.6296.101.23.3.1.1.57
-- 1.3.6.1.4.1.6296.101.23.3.1.1.57
		sleGponOnuLastActiveFailReason OBJECT-TYPE
			SYNTAX INTEGER
				{
				ranging(1),
				passwdInconsistency(2),
				passwdMismatch(3),
				passwdTimeout(4),
				passwdONUAlarm(5),
				passwdDisableEvent(6),
				passwdLosl(7),
				unknown(255)
				}
			MAX-ACCESS read-only
			STATUS current
			DESCRIPTION
				"The ONU Last active fail  Reason."
			::= { sleGponOnuEntry 57 }


--   1.3.6.1.4.1.6296.101.23.3.1.1.58
-- 1.3.6.1.4.1.6296.101.23.3.1.1.58
		sleGponOnuEqD OBJECT-TYPE
			SYNTAX INTEGER (1..65535)
			MAX-ACCESS read-only
			STATUS current
			DESCRIPTION
				"The ONU EqD."
			::= { sleGponOnuEntry 58 }


--   1.3.6.1.4.1.6296.101.23.3.1.1.59
-- 1.3.6.1.4.1.6296.101.23.3.1.1.59
		sleGponOnuMaxTcont OBJECT-TYPE
			SYNTAX INTEGER (1..65535)
			MAX-ACCESS read-only
			STATUS current
			DESCRIPTION
				"The ONU Max tcont"
			::= { sleGponOnuEntry 59 }


--   1.3.6.1.4.1.6296.101.23.3.1.1.60
-- 1.3.6.1.4.1.6296.101.23.3.1.1.60
		sleGponOnuMaxUsQueuePerTcont OBJECT-TYPE
			SYNTAX INTEGER (1..65535)
			MAX-ACCESS read-only
			STATUS current
			DESCRIPTION
				"The ONU Max US queue per Tcont"
			::= { sleGponOnuEntry 60 }


--   1.3.6.1.4.1.6296.101.23.3.1.1.61
-- 1.3.6.1.4.1.6296.101.23.3.1.1.61
		sleGponOnuSysUpTime OBJECT-TYPE
			SYNTAX Counter64
			MAX-ACCESS read-only
			STATUS current
			DESCRIPTION
				"The ONU sysUptime"
			::= { sleGponOnuEntry 61 }


--   1.3.6.1.4.1.6296.101.23.3.1.1.62
-- 1.3.6.1.4.1.6296.101.23.3.1.1.62
		sleGponOnuVenderProduct OBJECT-TYPE
			SYNTAX INTEGER (1..65535)
			MAX-ACCESS read-only
			STATUS current
			DESCRIPTION
				"The ONU Vendor"
			::= { sleGponOnuEntry 62 }


--   1.3.6.1.4.1.6296.101.23.3.1.1.63
-- 1.3.6.1.4.1.6296.101.23.3.1.1.63
		sleGponOnuSlotId OBJECT-TYPE
			SYNTAX INTEGER (1..65535)
			MAX-ACCESS read-only
			STATUS current
			DESCRIPTION
				"The ONU slotId"
			::= { sleGponOnuEntry 63 }


--   1.3.6.1.4.1.6296.101.23.3.1.1.64
-- 1.3.6.1.4.1.6296.101.23.3.1.1.64
		sleGponOnuPortsID OBJECT-TYPE
			SYNTAX INTEGER (1..65535)
			MAX-ACCESS read-only
			STATUS current
			DESCRIPTION
				"The ONU Port ID"
			::= { sleGponOnuEntry 64 }


--   1.3.6.1.4.1.6296.101.23.3.1.1.65
-- 1.3.6.1.4.1.6296.101.23.3.1.1.65
		sleGponOnuOperStatus OBJECT-TYPE
			SYNTAX Integer32
			MAX-ACCESS read-only
			STATUS current
			DESCRIPTION
				"The ONU Oper status"
			::= { sleGponOnuEntry 65 }


--   1.3.6.1.4.1.6296.101.23.3.1.1.66
-- 1.3.6.1.4.1.6296.101.23.3.1.1.66
		sleGponOnuMapperID OBJECT-TYPE
			SYNTAX Integer32
			MAX-ACCESS read-only
			STATUS current
			DESCRIPTION
				"The ONU MapperID"
			::= { sleGponOnuEntry 66 }


--  1.3.6.1.4.1.6296.101.23.3.1.1.67
		sleGponOnuVoipAvailSignalProtocol OBJECT-TYPE
			SYNTAX BITS
				{
				sip(0),
				h248(1),
				mgcp(2)
				}
			MAX-ACCESS read-only
			STATUS current
			DESCRIPTION
				"The Signal protocol"
			::= { sleGponOnuEntry 67 }


--  1.3.6.1.4.1.6296.101.23.3.1.1.68
		sleGponOnuVoipAvailConfigMethod OBJECT-TYPE
			SYNTAX BITS
				{
				omci(0),
				configrationFile(1),
				tr69(2),
				ietf(3)
				}
			MAX-ACCESS read-only
			STATUS current
			DESCRIPTION
				"The Configuration method"
			::= { sleGponOnuEntry 68 }


--  1.3.6.1.4.1.6296.101.23.3.1.1.69
		sleGponOnuSupplierSerial OBJECT-TYPE
			SYNTAX OCTET STRING
			MAX-ACCESS read-only
			STATUS current
			DESCRIPTION
				"The supplier serial."
			::= { sleGponOnuEntry 69 }


--  1.3.6.1.4.1.6296.101.23.3.1.1.70
		sleGponOnuHWRevision OBJECT-TYPE
			SYNTAX OCTET STRING
			MAX-ACCESS read-only
			STATUS current
			DESCRIPTION
				"The H/W revision."
			::= { sleGponOnuEntry 70 }


--  1.3.6.1.4.1.6296.101.23.3.1.1.71
		sleGponOnuCPULoad OBJECT-TYPE
			SYNTAX INTEGER (1..65535)
			MAX-ACCESS read-only
			STATUS current
			DESCRIPTION
				"The cpu load (%)."
			::= { sleGponOnuEntry 71 }


--  1.3.6.1.4.1.6296.101.23.3.1.1.72
		sleGponOnuCPULoadThreshold OBJECT-TYPE
			SYNTAX INTEGER (1..65535)
			MAX-ACCESS read-only
			STATUS current
			DESCRIPTION
				"The CPU load threshold(%)."
			::= { sleGponOnuEntry 72 }


--  1.3.6.1.4.1.6296.101.23.3.1.1.73
		sleGponOnuMemoryUsage OBJECT-TYPE
			SYNTAX INTEGER (1..65535)
			MAX-ACCESS read-only
			STATUS current
			DESCRIPTION
				"The memory usage(%)."
			::= { sleGponOnuEntry 73 }


--  1.3.6.1.4.1.6296.101.23.3.1.1.74
		sleGponOnuMemoryThreshold OBJECT-TYPE
			SYNTAX INTEGER (1..65535)
			MAX-ACCESS read-only
			STATUS current
			DESCRIPTION
				"The memory threshold(%)."
			::= { sleGponOnuEntry 74 }


--  1.3.6.1.4.1.6296.101.23.3.1.1.75
		sleGponOnuTemperature OBJECT-TYPE
			SYNTAX INTEGER (1..65535)
			MAX-ACCESS read-only
			STATUS current
			DESCRIPTION
				"The temperature(C)."
			::= { sleGponOnuEntry 75 }


--  1.3.6.1.4.1.6296.101.23.3.1.1.76
		sleGponOnuTemperatureHighThreshold OBJECT-TYPE
			SYNTAX INTEGER (1..65535)
			MAX-ACCESS read-only
			STATUS current
			DESCRIPTION
				"The temperature high threshold(C)."
			::= { sleGponOnuEntry 76 }


--  1.3.6.1.4.1.6296.101.23.3.1.1.77
		sleGponOnuTemperatureLowThreshold OBJECT-TYPE
			SYNTAX INTEGER (1..65535)
			MAX-ACCESS read-write
			STATUS current
			DESCRIPTION
				"The temperature low threshold(C)."
			::= { sleGponOnuEntry 77 }


--  1.3.6.1.4.1.6296.101.23.3.1.1.78
		sleGponOnuLoopDetectStateSupport OBJECT-TYPE
			SYNTAX INTEGER
				{
				unSupported(0),
				supported(1)
				}
			MAX-ACCESS read-only
			STATUS current
			DESCRIPTION
				"The supported state."
			::= { sleGponOnuEntry 78 }


--  1.3.6.1.4.1.6296.101.23.3.1.1.79
		sleGponOnuLoopDetectStateDetect OBJECT-TYPE
			SYNTAX INTEGER
				{
				unDetected(0),
				detected(1)
				}
			MAX-ACCESS read-only
			STATUS current
			DESCRIPTION
				"The detect state."
			::= { sleGponOnuEntry 79 }


--  1.3.6.1.4.1.6296.101.23.3.1.1.80
		sleGponOnuLoopDetectStateBlock OBJECT-TYPE
			SYNTAX INTEGER
				{
				unBlocked(0),
				blocked(1)
				}
			MAX-ACCESS read-only
			STATUS current
			DESCRIPTION
				"The block state."
			::= { sleGponOnuEntry 80 }


--  1.3.6.1.4.1.6296.101.23.3.1.1.81
		sleGponOnuLoopDetectUnblockReason OBJECT-TYPE
			SYNTAX INTEGER
				{
				unBlockByInit(0),
				unBlockByCommand(1),
				unBlockByTimerExpire(2),
				unBlockByDisable(3),
				unknown(255)
				}
			MAX-ACCESS read-only
			STATUS current
			DESCRIPTION
				"The unblock reason.
				0: Unblock by init
				1: Unblock by command
				2: Unblock by timer expire
				3: Unblock by disable
				255: Unknown"
			::= { sleGponOnuEntry 81 }


--  1.3.6.1.4.1.6296.101.23.3.1.1.82
		sleGponOnuSupportFunction OBJECT-TYPE
			SYNTAX BITS { systemStatus(0) }
			MAX-ACCESS read-only
			STATUS current
			DESCRIPTION
				"The support function."
			::= { sleGponOnuEntry 82 }


--  1.3.6.1.4.1.6296.101.23.3.1.1.83
		sleGponOnuAccountUserName OBJECT-TYPE
			SYNTAX OCTET STRING
			MAX-ACCESS read-only
			STATUS current
			DESCRIPTION
				"The account user name."
			::= { sleGponOnuEntry 83 }


--  1.3.6.1.4.1.6296.101.23.3.1.1.84
		sleGponOnuAccountPassword OBJECT-TYPE
			SYNTAX OCTET STRING
			MAX-ACCESS read-only
			STATUS current
			DESCRIPTION
				"The account password."
			::= { sleGponOnuEntry 84 }


--  1.3.6.1.4.1.6296.101.23.3.1.1.85
		sleGponOnuInactiveTime OBJECT-TYPE
			SYNTAX Counter64
			MAX-ACCESS read-only
			STATUS current
			DESCRIPTION
				"The elapsed time after ont Inactive."
			::= { sleGponOnuEntry 85 }


--  1.3.6.1.4.1.6296.101.23.3.1.1.86
		sleGponOnuRadiusAuthStatus OBJECT-TYPE
			SYNTAX INTEGER
				{
				none(0),
				try(1),
				success(2),
				noOnuProfile(3),
				fail(4),
				unknown(255)
				}
			MAX-ACCESS read-only
			STATUS current
			DESCRIPTION
				"The Onu Authentication Status"
			::= { sleGponOnuEntry 86 }


--  1.3.6.1.4.1.6296.101.23.3.1.1.87
		sleGponOnuRadiusAuthReceiveProfile OBJECT-TYPE
			SYNTAX OCTET STRING
			MAX-ACCESS read-only
			STATUS current
			DESCRIPTION
				"Onu received profile form authentication server
				"
			::= { sleGponOnuEntry 87 }


--  1.3.6.1.4.1.6296.101.23.3.1.1.88
		sleGponOnuMgmtIpPathProtocol OBJECT-TYPE
			SYNTAX INTEGER
				{
				ftp(1),
				tftp(2)
				}
			MAX-ACCESS read-only
			STATUS current
			DESCRIPTION
				"The Ip-path management protocol"
			::= { sleGponOnuEntry 88 }


--  1.3.6.1.4.1.6296.101.23.3.1.1.89
		sleGponOnuMgmtIpPathId OBJECT-TYPE
			SYNTAX OCTET STRING
			MAX-ACCESS read-only
			STATUS current
			DESCRIPTION
				"The Ip-path management access ID"
			::= { sleGponOnuEntry 89 }


--  1.3.6.1.4.1.6296.101.23.3.1.1.90
		sleGponOnuMgmtIpPathPassword OBJECT-TYPE
			SYNTAX OCTET STRING
			MAX-ACCESS read-only
			STATUS current
			DESCRIPTION
				"The Ip-path management access password"
			::= { sleGponOnuEntry 90 }


--  1.3.6.1.4.1.6296.101.23.3.1.1.91
		sleGponOnuMgmtIpPathUrl OBJECT-TYPE
			SYNTAX OCTET STRING
			MAX-ACCESS read-only
			STATUS current
			DESCRIPTION
				"The Ip-path management URL"
			::= { sleGponOnuEntry 91 }


--  1.3.6.1.4.1.6296.101.23.3.1.1.92
		sleGponOnuMgmtIpPathFileName OBJECT-TYPE
			SYNTAX OCTET STRING
			MAX-ACCESS read-only
			STATUS current
			DESCRIPTION
				"The Ip-path management File name"
			::= { sleGponOnuEntry 92 }


--  1.3.6.1.4.1.6296.101.23.3.1.1.93
		sleGponOnuMgmtIpPathState OBJECT-TYPE
			SYNTAX INTEGER
			MAX-ACCESS read-only
			STATUS current
			DESCRIPTION
				"The Ip-path management State
				0:File transfer completed successfully
				1:File transfer aborted successfully
				2:File deleted
				3:URL undefined or unreachable
				4:Failure to authenticate
				5:File transfer in progress
				6:Remote failure
				7:Local failure
				255: Unknown "
			::= { sleGponOnuEntry 93 }


		sleGponOnuServiceMode OBJECT-TYPE
			SYNTAX INTEGER
				{
				none(0),
				hgu(1),
				sfu(2)
				}
			MAX-ACCESS read-only
			STATUS current
			DESCRIPTION
				"ONU Service Mode
				0:None
				1:HGU (Home Gateway Unit)
				2:SFU (Single Family Unit)"
			::= { sleGponOnuEntry 94 }


		sleGponOnuServiceStatus OBJECT-TYPE
			SYNTAX INTEGER
				{
				notSupport(0),
				hgu(1),
				sfu(2)
				}
			MAX-ACCESS read-only
			STATUS current
			DESCRIPTION
				"ONU Service Status
				INTEGER
				0:Not Support
				1:HGU (Home Gateway Unit)
				2:SFU (Single Family Unit)"
			::= { sleGponOnuEntry 95 }


		sleGponOnuAutoUpgradeMode OBJECT-TYPE
			SYNTAX INTEGER
				{
				enable(1),
				disable(2)
				}
			MAX-ACCESS read-only
			STATUS current
			DESCRIPTION
				"ONU Auto Upgrade enable / disable"
			::= { sleGponOnuEntry 96 }


		sleGponOnuBootReason OBJECT-TYPE
			SYNTAX INTEGER
				{
				newLabel(1),
				powerRebootByLocal(2),
				swReboot(3),
				swRebootByLocal(4),
				swRebootByOlt(5),
				swRebootByOnuApplication(6),
				swRebootByActiveImageChange(7),
				swRebootByTcont(8),
				swRebootByPanic(9),
				watchdog(10),
				watchdogByLocal(11),
				swWatchdog(12),
				swWatchdogByCpuOver(13),
				swWatchdogByMemLow(14),
				autoProvision(15),
				applyWebConfig(16),
				webSystemReboot(17),
				adminPortChange(18),
				factoryRestore(19),
				userFactoryRestore(20),
				wifiOnOffChange(21),
				unknown(255)
				}
			MAX-ACCESS read-only
			STATUS current
			DESCRIPTION
				"ONU Boot Reason"
			::= { sleGponOnuEntry 97 }


		sleGponOnuAlarmStatus OBJECT-TYPE
			SYNTAX BITS
				{
				losi(0),
				lofi(1),
				loami(2),
				lcdgi(3),
				rdii(4),
				sufi(5),
				loai(6),
				dgi(7),
				dfi(8),
				dowi(9),
				tiwi(10),
				sfii(11),
				loki(12),
				equipment(13),
				alarmPowering(14),
				batteryMissing(15),
				batteryFailure(16),
				batteryLow(17),
				physicalIntrusion(18),
				selfTestFailure(19),
				dyingGasp(20),
				temperatureYellow(21),
				temperatureRed(22),
				voltageYellow(23),
				voltageRed(24),
				highCpuLoad(25),
				memoryUsage(26),
				lowTemperature(27),
				highTemperature(28),
				aniSf(29),
				aniSd(30),
				lowThresholdRxOpticPower(31),
				highThresholdRxOpticPower(32),
				lowThresholdTxOpticPower(33),
				highThresholdTxOpticPower(34),
				lowThresholdOpticVoltage(35),
				highThresholdOpticVoltage(36),
				lowThresholdOpticTemperature(37),
				highThresholdOpticTemperature(38),
				lowThresholdOpticBias(39),
				highThresholdOpticBias(40),
				manualPowerOff(41)
				}
			MAX-ACCESS read-only
			STATUS current
			DESCRIPTION
				"ONU Alarm Status"
			::= { sleGponOnuEntry 98 }


		sleGponOnuAuthOnuProfile OBJECT-TYPE
			SYNTAX OCTET STRING
			MAX-ACCESS read-only
			STATUS current
			DESCRIPTION
				"The ONU Profile in RADIUS attribute structure"
			::= { sleGponOnuEntry 99 }


		sleGponOnuAuthOnuVlan4 OBJECT-TYPE
			SYNTAX Integer32 (2101..3636)
			MAX-ACCESS read-only
			STATUS current
			DESCRIPTION
				"The vlan id for IPv4 in RADIUS attribute structure"
			::= { sleGponOnuEntry 100 }


		sleGponOnuAuthOnuVlan6 OBJECT-TYPE
			SYNTAX Integer32 (101..1636)
			MAX-ACCESS read-only
			STATUS current
			DESCRIPTION
				"The vlan id for IPv6 in RADIUS attribute structure"
			::= { sleGponOnuEntry 101 }


		sleGponOnuAuthOnuIpv4 OBJECT-TYPE
			SYNTAX OCTET STRING
			MAX-ACCESS read-only
			STATUS current
			DESCRIPTION
				"The IPv4 address with subnet mask in RADIUS attribute structure"
			::= { sleGponOnuEntry 102 }


		sleGponOnuAuthOnuIpv6 OBJECT-TYPE
			SYNTAX OCTET STRING
			MAX-ACCESS read-only
			STATUS current
			DESCRIPTION
				"The IPv6 address with subnet mask in RADIUS attribute structure"
			::= { sleGponOnuEntry 103 }


		sleGponOnuAuthOnuUniPortAdmin OBJECT-TYPE
			SYNTAX Integer32 (0..22222)
			MAX-ACCESS read-only
			STATUS current
			DESCRIPTION
				"A=Port1, B=Port2, C=Port3, D=Port4, E=Port5(POTS)
				0: Not used
				1: UNI UP
				2: UNI DOWN
				"
			::= { sleGponOnuEntry 104 }


		sleGponOnuAuthOnuUniEthMedium OBJECT-TYPE
			SYNTAX Integer32 (0..3333)
			MAX-ACCESS read-only
			STATUS current
			DESCRIPTION
				"A=Port1, B=Port2, C=Port3, D=Port4
				0: Not used
				1: Auto
				2: MDI-X
				3: MDI
				"
			::= { sleGponOnuEntry 105 }


		sleGponOnuAuthOnuUniEthSpeed OBJECT-TYPE
			SYNTAX Integer32 (0..5555)
			MAX-ACCESS read-only
			STATUS current
			DESCRIPTION
				"A=Port1, B=Port2, C=Port3, D=Port4
				0: Not used
				1: Auto
				2: 10
				3: 100
				4: 1000
				5: 10000
				"
			::= { sleGponOnuEntry 106 }


		sleGponOnuAuthOnuUniEthDuplex OBJECT-TYPE
			SYNTAX Integer32 (0..3333)
			MAX-ACCESS read-only
			STATUS current
			DESCRIPTION
				"A=Port1, B=Port2, C=Port3, D=Port4
				0: Not used
				1: Auto
				2: Half
				3: Full
				"
			::= { sleGponOnuEntry 107 }


		sleGponOnuAuthOnuErrorReason OBJECT-TYPE
			SYNTAX INTEGER
				{
				errorRadAttrUnknown(100),
				errorRadAttrInvalid(101),
				errorRadAttrFail(102),
				errorRadAttrVendorInvalid(103),
				errorRadAttrLen(104),
				errorRadAttrPrfLen(105),
				errorRadAttrPrfNo(106),
				errorRadAttrPrfFail(107),
				errorRadAttrPrfDb(108),
				errorRadAttrPrfRmInact(109),
				errorRadAttrPrfRmNo(110),
				errorRadAttrPrfRmFail(111),
				errorRadAttrIpv4Size(112),
				errorRadAttrSubnetSize(113),
				errorRadAttrIpv6Size(114),
				errorRadAttrVlan6Size(115),
				errorRadAttrVlan4Size(116),
				errorRadAttrOnuIdLen(117),
				errorRadAttrOnuIdFail(118),
				errorRadAttrAdminSize(119),
				errorRadAttrAdminInvalid(120),
				errorRadAttrAdminFail(121),
				errorRadAttrAdminDb(122),
				errorRadAttrMediumSize(123),
				errorRadAttrMediumInvalid(124),
				errorRadAttrMediumFail(125),
				errorRadAttrMediumDb(126),
				errorRadAttrSpeedSize(127),
				errorRadAttrSpeedInvalid(128),
				errorRadAerrorRadAttrSpeedDbttrSpeedInvalid(129),
				errorRadAttrDuplexSize(130),
				errorRadAttrDuplexInvalid(131),
				errorRadAttrDuplexDb(132),
				errorRadAttrAutoFail(133),
				errorRadDbSetAttrFail(300),
				errorRadDbGetOnuFail(301),
				errorRadNoParser(302),
				errorRadAVlanBase(400),
				errorRadAVlanPort(401),
				errorRadAVlanVlan(402),
				errorRadAVlanFail(403),
				errorRadAVlanIntfFail(404),
				errorRadAVlanMemFail(405),
				errorRadAVlanDbDup(406),
				errorRadAVlanPrefix(407),
				errorRadAVlanNo(408),
				errorExtVlan6Fail(500),
				errorExtVlan4Fail(501)
				}
			MAX-ACCESS read-only
			STATUS current
			DESCRIPTION
				"GPON_ERROR_RAD_ATTR_UNKNOWN(100): Unknown Attribute
				GPON_ERROR_RAD_ATTR_INVALID(101): Invalid Attributes
				GOPN_ERROR_RAD_ATTR_FAIL(102): Fail to apply attribute
				GOPN_ERROR_RAD_ATTR_VENDOR_INVALID(103): Unknown vendor id
				GOPN_ERROR_RAD_ATTR_LEN(104): Negative or overflow length
				GPON_ERROR_RAD_ATTR_PRF_LEN(105):Length of profile name is over
				GPON_ERROR_RAD_ATTR_PRF_NO(106): There is no profile
				GPON_ERROR_RAD_ATTR_PRF_FAIL(107): Fail to apply profile
				GPON_ERROR_RAD_ATTR_PRF_DB(108): Fail to set DB for profile
				GPON_ERROR_RAD_ATTR_PRF_RM_INACT(109): Cannot remove a profile for inactive ONU
				GPON_ERROR_RAD_ATTR_PRF_RM_NO(110): There is no profile to remove
				GPON_ERROR_RAD_ATTR_PRF_RM_FAIL(111): Fail to remove a profile
				GPON_ERROR_RAD_ATTR_IPV4_SIZE(112): Size of IPv4 is not 32bit
				GPON_ERROR_RAD_ATTR_SUBNET_SIZE(113): Size of IPv4 subnet is not 32bit
				GPON_ERROR_RAD_ATTR_IPV6_SIZE(114): Size of IPv6 is not 18 bit
				GPON_ERROR_RAD_ATTR_VLAN6_SIZE(115): Size of VID for IPv6 is not integer
				GPON_ERROR_RAD_ATTR_VLAN4_SIZE(116): Size of VID for IPv4 is not integer
				GPON_ERROR_RAD_ATTR_ONU_ID_LEN(117): Size of IPv6 is not integer
				GPON_ERROR_RAD_ATTR_ONU_ID_FAIL(118): Fail to call gpon_retry_wrap_add()
				GPON_ERROR_RAD_ATTR_ADMIN_SIZE(119): Size of UNI port admin is not integer
				GPON_ERROR_RAD_ATTR_ADMIN_INVALID(120): Invalid or undefined value on UNI admin
				GPON_ERROR_RAD_ATTR_ADMIN_FAIL(121): Fail to configure UNI admin
				GPON_ERROR_RAD_ATTR_ADMIN_DB(122): Fail to set DB for UNI admin
				GPON_ERROR_RAD_ATTR_MEDIUM_SIZE(123): Size of ethernet medium is not integer
				GPON_ERROR_RAD_ATTR_MEDIUM_INVALID(124):Invalid or undefined value on medium
				GPON_ERROR_RAD_ATTR_MEDIUM_FAIL(125): Fail to configure medium control
				GPON_ERROR_RAD_ATTR_MEDIUM_DB(126): Fail to set DB for medium control
				GPON_ERROR_RAD_ATTR_SPEED_SIZE(127): Size of ethernet speed is not integer
				GPON_ERROR_RAD_ATTR_SPEED_INVALID(128): Invalid or undefined value on speed
				GPON_ERROR_RAD_ATTR_SPEED_DB(129): Fail to set DB for speed control
				GPON_ERROR_RAD_ATTR_DUPLEX_SIZE(130): Size of ethernet duplex is not integer
				GPON_ERROR_RAD_ATTR_DUPLEX_INVALID(131): Invalid or undefined value on duplex
				GPON_ERROR_RAD_ATTR_DUPLEX_DB(132): fail to set DB for duplex control
				GPON_ERROR_RAD_ATTR_AUTO_FAIL(133): Fail to configure speed and/or duplex
				GPON_ERROR_RAD_DB_SET_ATTR_FAIL(300): Cannot archive attributes
				GPON_ERROR_RAD_DB_GET_ONU_FAIL(301): Cannot get ONU DB
				GPON_ERROR_RAD_NO_PARSER(302): Unknown attribute
				GPON_ERROR_RAD_A_VLAN_BASE(400): N/A
				GPON_ERROR_RAD_A_VLAN_PORT(401): Cannot found port for ambiguous VLAN
				GPON_ERROR_RAD_A_VLAN_VLAN(402): Invalid VID of VLAN
				GPON_ERROR_RAD_A_VLAN_FAIL(403): Fail to confiugure extended VLAN
				GPON_ERROR_RAD_A_VLAN_INTF_FAIL(404): Fail to create ambiguous VLAN interface
				GPON_ERROR_RAD_A_VLAN_MEM_FAIL(405): Fail to create VLAN DB
				GPON_ERROR_RAD_A_VLAN_DB_DUP(406): Duplcated VID of VLAN
				GPON_ERROR_RAD_A_VLAN_PREFIX(407): Invalid length of prefix
				GPON_ERROR_RAD_A_VLAN_NO(408): Cannot found ambiguous VLAN interface
				GPON_ERROR_EXT_VLAN6_FAIL(500): Fail to confiugure extended VLAN for IPv6
				GPON_ERROR_EXT_VLAN4_FAIL(501): Fail to confiugure extended VLAN for IPv4
				"
			::= { sleGponOnuEntry 108 }


		sleGponOnuAuthOnuOmccVersion OBJECT-TYPE
			SYNTAX Integer32
			MAX-ACCESS read-only
			STATUS current
			DESCRIPTION
				"ONU Omcc Version"
			::= { sleGponOnuEntry 109 }


		sleGponOnuGspStstusUptime OBJECT-TYPE
			SYNTAX TimeTicks
			MAX-ACCESS read-only
			STATUS current
			DESCRIPTION
				"GSP ststus uptime "
			::= { sleGponOnuEntry 110 }


		sleGponOnuGspConfigUptime OBJECT-TYPE
			SYNTAX TimeTicks
			MAX-ACCESS read-only
			STATUS current
			DESCRIPTION
				"GSP config uptime "
			::= { sleGponOnuEntry 111 }


--   1.3.6.1.4.1.6296.101.23.3.2
-- 1.3.6.1.4.1.6296.101.23.3.2
		sleGponOnuControl OBJECT IDENTIFIER ::= { sleGponOnu 2 }


--   1.3.6.1.4.1.6296.101.23.3.2.1
-- 1.3.6.1.4.1.6296.101.23.3.2.1
		sleGponOnuControlRequest OBJECT-TYPE
			SYNTAX INTEGER
				{
				setOnuRegister(1),
				setOnuDeregister(2),
				setOnuProfile(3),
				setOnuFix(4),
				setOnuUpgradeNos(5),
				setOnuNosActiveChange(6),
				setOnuEncMode(7),
				setOnuReset(8),
				setOnuTxOffOptic(9),
				setOnuDescription(10),
				setOnuFecModeUS(11),
				setOnuIpInfo(12),
				setOnuOmciPingTest(13),
				setOnuActiveStatus(14),
				setOnuPMProfile(15),
				setOnuUpgradeNosPartition(16),
				setOnuUpgradeNosCommit(17),
				setOnuUpgradeNosActiveChange(18),
				setOnuBlock(19),
				updateOltRxPower(20),
				updateOnuSystemInfo(21),
				setOnuTxOnOptic(22),
				setOnuLoopDetectUnblock(23),
				updateOnuUserMacCnt(24),
				updateOnuAccount(25),
				setOnuAccount(26),
				removeOnuSerialNumber(27),
				setOnuMgmtIpPathProtocol(28),
				setOnuMgmtIpPathInfo(29),
				clearOnuMgmtIpPath(30),
				setOnuServiceMode(31),
				clearOnuServiceMode(32),
				setOnuAutoUpgradeMode(33),
				setOnuMibUpload(34),
				setOnuReconfig(35),
				setOnuRestoreFactoryReset(36),
				setOnuMove(37),
				setOnuAuthReauthSpecific(38),
				setOnuRadiusAttribute(39),
				setOnuPloamReset(40)
				}
			MAX-ACCESS read-write
			STATUS current
			DESCRIPTION
				"The request of a user command"
			::= { sleGponOnuControl 1 }


--   1.3.6.1.4.1.6296.101.23.3.2.2
-- 1.3.6.1.4.1.6296.101.23.3.2.2
		sleGponOnuControlStatus OBJECT-TYPE
			SYNTAX SleControlStatusType
			MAX-ACCESS read-only
			STATUS current
			DESCRIPTION
				"The status of user command"
			::= { sleGponOnuControl 2 }


--   1.3.6.1.4.1.6296.101.23.3.2.3
-- 1.3.6.1.4.1.6296.101.23.3.2.3
		sleGponOnuControlTimer OBJECT-TYPE
			SYNTAX Gauge32
			MAX-ACCESS read-write
			STATUS current
			DESCRIPTION
				"The maximum time for the manager for a long running user command"
			::= { sleGponOnuControl 3 }


--   1.3.6.1.4.1.6296.101.23.3.2.4
-- 1.3.6.1.4.1.6296.101.23.3.2.4
		sleGponOnuControlTimeStamp OBJECT-TYPE
			SYNTAX TimeTicks
			MAX-ACCESS read-only
			STATUS current
			DESCRIPTION
				"The time stamp of the last command(end of command)"
			::= { sleGponOnuControl 4 }


--   1.3.6.1.4.1.6296.101.23.3.2.5
-- 1.3.6.1.4.1.6296.101.23.3.2.5
		sleGponOnuControlReqResult OBJECT-TYPE
			SYNTAX SleControlRequestResultType
			MAX-ACCESS read-only
			STATUS current
			DESCRIPTION
				"The result of the last user command"
			::= { sleGponOnuControl 5 }


		sleGponOnuControlOltId OBJECT-TYPE
			SYNTAX INTEGER (1..2147483647)
			MAX-ACCESS read-write
			STATUS current
			DESCRIPTION
				"Gpon Olt Index"
			::= { sleGponOnuControl 6 }


--   1.3.6.1.4.1.6296.101.23.3.2.7
-- 1.3.6.1.4.1.6296.101.23.3.2.7
		sleGponOnuControlId OBJECT-TYPE
			SYNTAX INTEGER (1..65535)
			MAX-ACCESS read-write
			STATUS current
			DESCRIPTION
				"Gpon Onu Index. (0xFF is all onu)"
			::= { sleGponOnuControl 7 }


--   1.3.6.1.4.1.6296.101.23.3.2.8
-- 1.3.6.1.4.1.6296.101.23.3.2.8
		sleGponOnuControlSerial OBJECT-TYPE
			SYNTAX OCTET STRING
			MAX-ACCESS read-write
			STATUS current
			DESCRIPTION
				"ONU Serial Number"
			::= { sleGponOnuControl 8 }


--   1.3.6.1.4.1.6296.101.23.3.2.9
-- 1.3.6.1.4.1.6296.101.23.3.2.9
		sleGponOnuControlPasswd OBJECT-TYPE
			SYNTAX OCTET STRING
			MAX-ACCESS read-write
			STATUS current
			DESCRIPTION
				"ONU Password"
			::= { sleGponOnuControl 9 }


--   1.3.6.1.4.1.6296.101.23.3.2.10
-- 1.3.6.1.4.1.6296.101.23.3.2.10
		sleGponOnuControlPasswdMode OBJECT-TYPE
			SYNTAX INTEGER
				{
				enable(1),
				disable(2)
				}
			MAX-ACCESS read-write
			STATUS current
			DESCRIPTION
				"Password auto-learning"
			::= { sleGponOnuControl 10 }


--   1.3.6.1.4.1.6296.101.23.3.2.11
-- 1.3.6.1.4.1.6296.101.23.3.2.11
		sleGponOnuControlEncMode OBJECT-TYPE
			SYNTAX INTEGER
				{
				enable(1),
				disable(2)
				}
			MAX-ACCESS read-write
			STATUS current
			DESCRIPTION
				"Encryption mode"
			::= { sleGponOnuControl 11 }


--   1.3.6.1.4.1.6296.101.23.3.2.12
-- 1.3.6.1.4.1.6296.101.23.3.2.12
		sleGponOnuControlProfile OBJECT-TYPE
			SYNTAX OCTET STRING
			MAX-ACCESS read-write
			STATUS current
			DESCRIPTION
				"Onu assigned Profile"
			::= { sleGponOnuControl 12 }


--   1.3.6.1.4.1.6296.101.23.3.2.13
-- 1.3.6.1.4.1.6296.101.23.3.2.13
		sleGponOnuControlNosUpgradePath OBJECT-TYPE
			SYNTAX OCTET STRING
			MAX-ACCESS read-write
			STATUS current
			DESCRIPTION
				"Onu Firmware Path."
			::= { sleGponOnuControl 13 }


--   1.3.6.1.4.1.6296.101.23.3.2.14
-- 1.3.6.1.4.1.6296.101.23.3.2.14
		sleGponOnuControlHwAddr OBJECT-TYPE
			SYNTAX OCTET STRING
			MAX-ACCESS read-write
			STATUS current
			DESCRIPTION
				"Onu H/W address. (0 is unused)"
			::= { sleGponOnuControl 14 }


--   1.3.6.1.4.1.6296.101.23.3.2.15
-- 1.3.6.1.4.1.6296.101.23.3.2.15
		sleGponOnuControlTxOffOptic OBJECT-TYPE
			SYNTAX INTEGER (0..65525)
			UNITS "seconds"
			MAX-ACCESS read-write
			STATUS current
			DESCRIPTION
				"Tx power disable of the tranceiver"
			::= { sleGponOnuControl 15 }


--   1.3.6.1.4.1.6296.101.23.3.2.16
-- 1.3.6.1.4.1.6296.101.23.3.2.16
		sleGponOnuControlDescription OBJECT-TYPE
			SYNTAX OCTET STRING
			MAX-ACCESS read-write
			STATUS current
			DESCRIPTION
				"ONU description."
			::= { sleGponOnuControl 16 }


--   1.3.6.1.4.1.6296.101.23.3.2.17
-- 1.3.6.1.4.1.6296.101.23.3.2.17
		sleGponOnuControlFecModeUS OBJECT-TYPE
			SYNTAX INTEGER
				{
				enable(1),
				disable(2)
				}
			MAX-ACCESS read-write
			STATUS current
			DESCRIPTION
				"UpStream FEC mode"
			::= { sleGponOnuControl 17 }


--   1.3.6.1.4.1.6296.101.23.3.2.18
-- 1.3.6.1.4.1.6296.101.23.3.2.18
		sleGponOnuControlIPMode OBJECT-TYPE
			SYNTAX INTEGER
				{
				dhcp(1),
				manual(2)
				}
			MAX-ACCESS read-write
			STATUS current
			DESCRIPTION
				"Ip Addressing mode
				DHCP or Manual"
			::= { sleGponOnuControl 18 }


--   1.3.6.1.4.1.6296.101.23.3.2.19
-- 1.3.6.1.4.1.6296.101.23.3.2.19
		sleGponOnuControlIPAddr OBJECT-TYPE
			SYNTAX IpAddress
			MAX-ACCESS read-write
			STATUS current
			DESCRIPTION
				"Onu IP address"
			::= { sleGponOnuControl 19 }


--   1.3.6.1.4.1.6296.101.23.3.2.20
-- 1.3.6.1.4.1.6296.101.23.3.2.20
		sleGponOnuControlIPMask OBJECT-TYPE
			SYNTAX IpAddress
			MAX-ACCESS read-write
			STATUS current
			DESCRIPTION
				"Onu IP Netmask"
			::= { sleGponOnuControl 20 }


--   1.3.6.1.4.1.6296.101.23.3.2.21
-- 1.3.6.1.4.1.6296.101.23.3.2.21
		sleGponOnuControlIPGw OBJECT-TYPE
			SYNTAX IpAddress
			MAX-ACCESS read-write
			STATUS current
			DESCRIPTION
				"Onu Gateway"
			::= { sleGponOnuControl 21 }


--   1.3.6.1.4.1.6296.101.23.3.2.22
-- 1.3.6.1.4.1.6296.101.23.3.2.22
		sleGponOnuControlIPDns1 OBJECT-TYPE
			SYNTAX IpAddress
			MAX-ACCESS read-write
			STATUS current
			DESCRIPTION
				"Onu DNS primary"
			::= { sleGponOnuControl 22 }


--   1.3.6.1.4.1.6296.101.23.3.2.23
-- 1.3.6.1.4.1.6296.101.23.3.2.23
		sleGponOnuControlIPDns2 OBJECT-TYPE
			SYNTAX IpAddress
			MAX-ACCESS read-write
			STATUS current
			DESCRIPTION
				"Onu DNS secondary"
			::= { sleGponOnuControl 23 }


--   1.3.6.1.4.1.6296.101.23.3.2.24
-- 1.3.6.1.4.1.6296.101.23.3.2.24
		sleGponOnuControlOmciPingTestTimeout OBJECT-TYPE
			SYNTAX Integer32 (1..1000)
			UNITS "msec"
			MAX-ACCESS read-write
			STATUS current
			DESCRIPTION
				"OMCI ping test timeout. <1-1000> (msec)"
			::= { sleGponOnuControl 24 }


--   1.3.6.1.4.1.6296.101.23.3.2.25
-- 1.3.6.1.4.1.6296.101.23.3.2.25
		sleGponOnuControlActiveStatus OBJECT-TYPE
			SYNTAX INTEGER
				{
				activate(1),
				deactivate(2)
				}
			MAX-ACCESS read-write
			STATUS current
			DESCRIPTION
				"ONU activation/deactivation."
			::= { sleGponOnuControl 25 }


--   1.3.6.1.4.1.6296.101.23.3.2.26
-- 1.3.6.1.4.1.6296.101.23.3.2.26
		sleGponOnuControlPMProfile OBJECT-TYPE
			SYNTAX OCTET STRING
			MAX-ACCESS read-write
			STATUS current
			DESCRIPTION
				"The assigned PM-profile"
			::= { sleGponOnuControl 26 }


--   1.3.6.1.4.1.6296.101.23.3.2.27
-- 1.3.6.1.4.1.6296.101.23.3.2.27
		sleGponOnuControlNosPartition OBJECT-TYPE
			SYNTAX INTEGER
				{
				os1(1),
				os2(2),
				unknown(255)
				}
			MAX-ACCESS read-write
			STATUS current
			DESCRIPTION
				"The partition of ONU OS."
			::= { sleGponOnuControl 27 }


--   1.3.6.1.4.1.6296.101.23.3.2.28
-- 1.3.6.1.4.1.6296.101.23.3.2.28
		sleGponOnuControlBlock OBJECT-TYPE
			SYNTAX INTEGER
				{
				block(1),
				unblock(2)
				}
			MAX-ACCESS read-write
			STATUS current
			DESCRIPTION
				"The Onu Block status."
			::= { sleGponOnuControl 28 }


--  1.3.6.1.4.1.6296.101.23.3.2.29
		sleGponOnuControlAccountUserName OBJECT-TYPE
			SYNTAX OCTET STRING
			MAX-ACCESS read-write
			STATUS current
			DESCRIPTION
				"The account user name."
			::= { sleGponOnuControl 29 }


--  1.3.6.1.4.1.6296.101.23.3.2.30
		sleGponOnuControlAccountPassword OBJECT-TYPE
			SYNTAX OCTET STRING
			MAX-ACCESS read-write
			STATUS current
			DESCRIPTION
				"The account password."
			::= { sleGponOnuControl 30 }


--  1.3.6.1.4.1.6296.101.23.3.2.31
		sleGponOnuControlMgmtIpPathProtocol OBJECT-TYPE
			SYNTAX INTEGER
				{
				ftp(1),
				tftp(2)
				}
			MAX-ACCESS read-write
			STATUS current
			DESCRIPTION
				"The Ip-path management protocol"
			::= { sleGponOnuControl 31 }


--  1.3.6.1.4.1.6296.101.23.3.2.32
		sleGponOnuControlMgmtIpPathId OBJECT-TYPE
			SYNTAX OCTET STRING
			MAX-ACCESS read-write
			STATUS current
			DESCRIPTION
				"The Ip-path management access ID"
			::= { sleGponOnuControl 32 }


--  1.3.6.1.4.1.6296.101.23.3.2.33
		sleGponOnuControlMgmtIpPathPassword OBJECT-TYPE
			SYNTAX OCTET STRING
			MAX-ACCESS read-write
			STATUS current
			DESCRIPTION
				"The Ip-path management access password"
			::= { sleGponOnuControl 33 }


--  1.3.6.1.4.1.6296.101.23.3.2.34
		sleGponOnuControlMgmtIpPathUrl OBJECT-TYPE
			SYNTAX OCTET STRING
			MAX-ACCESS read-write
			STATUS current
			DESCRIPTION
				"The Ip-path management URL"
			::= { sleGponOnuControl 34 }


--  1.3.6.1.4.1.6296.101.23.3.2.35
		sleGponOnuControlMgmtIpPathFilename OBJECT-TYPE
			SYNTAX OCTET STRING
			MAX-ACCESS read-write
			STATUS current
			DESCRIPTION
				"The Ip-path management File name"
			::= { sleGponOnuControl 35 }


		sleGponOnuControlServiceMode OBJECT-TYPE
			SYNTAX INTEGER
				{
				hgu(1),
				sfu(2)
				}
			MAX-ACCESS read-write
			STATUS current
			DESCRIPTION
				"ONU Service Mode
				1:HGU (Home Gateway Unit)
				2:SFU (Single Family Unit)"
			::= { sleGponOnuControl 36 }


		sleGponOnuControlAutoUpgradeMode OBJECT-TYPE
			SYNTAX INTEGER
				{
				enable(1),
				disable(2)
				}
			MAX-ACCESS read-write
			STATUS current
			DESCRIPTION
				"ONU Auto Upgrade enable/disable"
			::= { sleGponOnuControl 37 }


		sleGponOnuControlMoveOltId OBJECT-TYPE
			SYNTAX Integer32 (1..2147483647)
			MAX-ACCESS read-write
			STATUS current
			DESCRIPTION
				"Move to Gpon Olt Index"
			::= { sleGponOnuControl 38 }


		sleGponOnuControlMoveOnuId OBJECT-TYPE
			SYNTAX Integer32 (1..65535)
			MAX-ACCESS read-write
			STATUS current
			DESCRIPTION
				"Move to Gpon Onu Index (OxFF is auto onu)"
			::= { sleGponOnuControl 39 }


		sleGponOnuControlAuthOnuProfile OBJECT-TYPE
			SYNTAX OCTET STRING
			MAX-ACCESS read-write
			STATUS current
			DESCRIPTION
				"The ONU Profile in RADIUS attribute structure"
			::= { sleGponOnuControl 40 }


		sleGponOnuControlAuthOnuVlan4 OBJECT-TYPE
			SYNTAX Integer32 (2101..3636)
			MAX-ACCESS read-write
			STATUS current
			DESCRIPTION
				"The vlan id for IPv4 in RADIUS attribute structure"
			::= { sleGponOnuControl 41 }


		sleGponOnuControlAuthOnuVlan6 OBJECT-TYPE
			SYNTAX Integer32 (101..1636)
			MAX-ACCESS read-write
			STATUS current
			DESCRIPTION
				"The vlan id for IPv6 in RADIUS attribute structure"
			::= { sleGponOnuControl 42 }


		sleGponOnuControlAuthOnuIpv4 OBJECT-TYPE
			SYNTAX OCTET STRING
			MAX-ACCESS read-write
			STATUS current
			DESCRIPTION
				"The IPv4 address with subnet mask in RADIUS attribute structure"
			::= { sleGponOnuControl 43 }


		sleGponOnuControlAuthOnuIpv6 OBJECT-TYPE
			SYNTAX OCTET STRING
			MAX-ACCESS read-write
			STATUS current
			DESCRIPTION
				"The IPv4 address with subnet mask in RADIUS attribute structure"
			::= { sleGponOnuControl 44 }


		sleGponOnuControlAuthOnuUniPortAdmin OBJECT-TYPE
			SYNTAX Integer32 (0..22222)
			MAX-ACCESS read-write
			STATUS current
			DESCRIPTION
				"A=Port1, B=Port2, C=Port3, D=Port4
				0: Not used
				1: Auto
				2: MDI-X
				3: MDI
				"
			::= { sleGponOnuControl 45 }


		sleGponOnuControlAuthOnuUniEthMedium OBJECT-TYPE
			SYNTAX Integer32 (0..3333)
			MAX-ACCESS read-write
			STATUS current
			DESCRIPTION
				"A=Port1, B=Port2, C=Port3, D=Port4
				0: Not used
				1: Auto
				2: MDI-X
				3: MDI
				"
			::= { sleGponOnuControl 46 }


		sleGponOnuControlAuthOnuUniEthSpeed OBJECT-TYPE
			SYNTAX Integer32 (0..5555)
			MAX-ACCESS read-write
			STATUS current
			DESCRIPTION
				"A=Port1, B=Port2, C=Port3, D=Port4
				0: Not used
				1: Auto
				2: 10
				3: 100
				4: 1000
				5: 10000
				"
			::= { sleGponOnuControl 47 }


		sleGponOnuControlAuthOnuUniEthDuplex OBJECT-TYPE
			SYNTAX Integer32 (0..3333)
			MAX-ACCESS read-write
			STATUS current
			DESCRIPTION
				"A=Port1, B=Port2, C=Port3, D=Port4
				0: Not used
				1: Auto
				2: Half
				3: Full
				"
			::= { sleGponOnuControl 48 }


--   1.3.6.1.4.1.6296.101.23.3.3
-- 1.3.6.1.4.1.6296.101.23.3.3
		sleGponOnuNotification OBJECT IDENTIFIER ::= { sleGponOnu 3 }


--   1.3.6.1.4.1.6296.101.23.3.3.1
-- 1.3.6.1.4.1.6296.101.23.3.3.1
		sleGponOnuRegistered NOTIFICATION-TYPE
			OBJECTS { sleGponOnuControlRequest, sleGponOnuControlTimeStamp, sleGponOnuControlReqResult, sleGponOnuControlOltId, sleGponOnuControlId,
				sleGponOnuControlSerial, sleGponOnuControlPasswd, sleGponOnuControlPasswdMode, sleGponOnuControlHwAddr }
			STATUS current
			DESCRIPTION
				"Description."
			::= { sleGponOnuNotification 1 }


--   1.3.6.1.4.1.6296.101.23.3.3.2
-- 1.3.6.1.4.1.6296.101.23.3.3.2
		sleGponOnuDeregistered NOTIFICATION-TYPE
			OBJECTS { sleGponOnuControlRequest, sleGponOnuControlTimeStamp, sleGponOnuControlReqResult, sleGponOnuControlOltId, sleGponOnuControlId,
				sleGponOnuControlSerial }
			STATUS current
			DESCRIPTION
				"Description."
			::= { sleGponOnuNotification 2 }


--   1.3.6.1.4.1.6296.101.23.3.3.3
-- 1.3.6.1.4.1.6296.101.23.3.3.3
		sleGponOnuProfileChanged NOTIFICATION-TYPE
			OBJECTS { sleGponOnuControlRequest, sleGponOnuControlTimeStamp, sleGponOnuControlReqResult, sleGponOnuControlOltId, sleGponOnuControlId,
				sleGponOnuControlSerial, sleGponOnuControlProfile }
			STATUS current
			DESCRIPTION
				"Description."
			::= { sleGponOnuNotification 3 }


--   1.3.6.1.4.1.6296.101.23.3.3.4
-- 1.3.6.1.4.1.6296.101.23.3.3.4
		sleGponOnuFixed NOTIFICATION-TYPE
			OBJECTS { sleGponOnuControlRequest, sleGponOnuControlTimeStamp, sleGponOnuControlReqResult, sleGponOnuControlOltId, sleGponOnuControlId,
				sleGponOnuControlSerial }
			STATUS current
			DESCRIPTION
				"Description."
			::= { sleGponOnuNotification 4 }


--   1.3.6.1.4.1.6296.101.23.3.3.5
-- 1.3.6.1.4.1.6296.101.23.3.3.5
		sleGponOnuUpgradeNosChanged NOTIFICATION-TYPE
			OBJECTS { sleGponOnuControlRequest, sleGponOnuControlTimeStamp, sleGponOnuControlReqResult, sleGponOnuControlOltId, sleGponOnuControlId,
				sleGponOnuControlSerial, sleGponOnuControlNosUpgradePath }
			STATUS current
			DESCRIPTION
				"Description."
			::= { sleGponOnuNotification 5 }


--   1.3.6.1.4.1.6296.101.23.3.3.6
-- 1.3.6.1.4.1.6296.101.23.3.3.6
		sleGponOnuNosActiveChanged NOTIFICATION-TYPE
			OBJECTS { sleGponOnuControlRequest, sleGponOnuControlTimeStamp, sleGponOnuControlReqResult, sleGponOnuControlOltId, sleGponOnuControlId,
				sleGponOnuControlSerial }
			STATUS current
			DESCRIPTION
				"Description."
			::= { sleGponOnuNotification 6 }


--   1.3.6.1.4.1.6296.101.23.3.3.7
-- 1.3.6.1.4.1.6296.101.23.3.3.7
		sleGponOnuEncModeChanged NOTIFICATION-TYPE
			OBJECTS { sleGponOnuControlRequest, sleGponOnuControlTimeStamp, sleGponOnuControlReqResult, sleGponOnuControlOltId, sleGponOnuControlId,
				sleGponOnuControlSerial, sleGponOnuControlEncMode }
			STATUS current
			DESCRIPTION
				"Description."
			::= { sleGponOnuNotification 7 }


--   1.3.6.1.4.1.6296.101.23.3.3.8
-- 1.3.6.1.4.1.6296.101.23.3.3.8
		sleGponOnuReset NOTIFICATION-TYPE
			OBJECTS { sleGponOnuControlRequest, sleGponOnuControlTimeStamp, sleGponOnuControlReqResult, sleGponOnuControlOltId, sleGponOnuControlId,
				sleGponOnuControlSerial }
			STATUS current
			DESCRIPTION
				"Description."
			::= { sleGponOnuNotification 8 }


--   1.3.6.1.4.1.6296.101.23.3.3.9
-- 1.3.6.1.4.1.6296.101.23.3.3.9
		sleGponOnuTxOffOpticChanged NOTIFICATION-TYPE
			OBJECTS { sleGponOnuControlRequest, sleGponOnuControlTimeStamp, sleGponOnuControlReqResult, sleGponOnuControlOltId, sleGponOnuControlId,
				sleGponOnuControlSerial, sleGponOnuControlTxOffOptic }
			STATUS current
			DESCRIPTION
				"Description."
			::= { sleGponOnuNotification 9 }


--   1.3.6.1.4.1.6296.101.23.3.3.10
-- 1.3.6.1.4.1.6296.101.23.3.3.10
		sleGponOnuDescriptionChanged NOTIFICATION-TYPE
			OBJECTS { sleGponOnuControlRequest, sleGponOnuControlTimeStamp, sleGponOnuControlReqResult, sleGponOnuControlOltId, sleGponOnuControlId,
				sleGponOnuControlSerial, sleGponOnuControlDescription }
			STATUS current
			DESCRIPTION
				"Description."
			::= { sleGponOnuNotification 10 }


--   1.3.6.1.4.1.6296.101.23.3.3.11
-- 1.3.6.1.4.1.6296.101.23.3.3.11
		sleGponOnuFecModeChanged NOTIFICATION-TYPE
			OBJECTS { sleGponOnuControlRequest, sleGponOnuControlTimeStamp, sleGponOnuControlReqResult, sleGponOnuControlOltId, sleGponOnuControlId,
				sleGponOnuControlFecModeUS }
			STATUS current
			DESCRIPTION
				"Description."
			::= { sleGponOnuNotification 11 }


--   1.3.6.1.4.1.6296.101.23.3.3.12
-- 1.3.6.1.4.1.6296.101.23.3.3.12
		sleGponOnuIPInfoChanged NOTIFICATION-TYPE
			OBJECTS { sleGponOnuControlRequest, sleGponOnuControlTimeStamp, sleGponOnuControlReqResult, sleGponOnuControlOltId, sleGponOnuControlId,
				sleGponOnuControlIPMode, sleGponOnuControlIPAddr, sleGponOnuControlIPMask, sleGponOnuControlIPGw, sleGponOnuControlIPDns1,
				sleGponOnuControlIPDns2 }
			STATUS current
			DESCRIPTION
				"Description."
			::= { sleGponOnuNotification 12 }


--   1.3.6.1.4.1.6296.101.23.3.3.13
-- 1.3.6.1.4.1.6296.101.23.3.3.13
		sleGponOnuOmciPingTest NOTIFICATION-TYPE
			OBJECTS { sleGponOnuControlRequest, sleGponOnuControlTimeStamp, sleGponOnuControlReqResult, sleGponOnuControlOltId, sleGponOnuControlId,
				sleGponOnuControlOmciPingTestTimeout }
			STATUS current
			DESCRIPTION
				"Description."
			::= { sleGponOnuNotification 13 }


--   1.3.6.1.4.1.6296.101.23.3.3.14
-- 1.3.6.1.4.1.6296.101.23.3.3.14
		sleGponOnuActivationChanged NOTIFICATION-TYPE
			OBJECTS { sleGponOnuControlRequest, sleGponOnuControlTimeStamp, sleGponOnuControlReqResult, sleGponOnuControlOltId, sleGponOnuControlId,
				sleGponOnuControlActiveStatus }
			STATUS current
			DESCRIPTION
				"Description."
			::= { sleGponOnuNotification 14 }


--   1.3.6.1.4.1.6296.101.23.3.3.15
-- 1.3.6.1.4.1.6296.101.23.3.3.15
		sleGponOnuPMProfileChanged NOTIFICATION-TYPE
			OBJECTS { sleGponOnuControlRequest, sleGponOnuControlTimeStamp, sleGponOnuControlReqResult, sleGponOnuControlOltId, sleGponOnuControlId,
				sleGponOnuControlPMProfile }
			STATUS current
			DESCRIPTION
				"Description."
			::= { sleGponOnuNotification 15 }


--   1.3.6.1.4.1.6296.101.23.3.3.16
-- 1.3.6.1.4.1.6296.101.23.3.3.16
		sleGponOnuUpgradeNosPartitionChanged NOTIFICATION-TYPE
			OBJECTS { sleGponOnuControlRequest, sleGponOnuControlTimeStamp, sleGponOnuControlReqResult, sleGponOnuControlOltId, sleGponOnuControlId,
				sleGponOnuControlSerial, sleGponOnuControlNosUpgradePath, sleGponOnuControlNosPartition }
			STATUS current
			DESCRIPTION
				"Description."
			::= { sleGponOnuNotification 16 }


--   1.3.6.1.4.1.6296.101.23.3.3.17
-- 1.3.6.1.4.1.6296.101.23.3.3.17
		sleGponOnuUpgradeNosCommited NOTIFICATION-TYPE
			OBJECTS { sleGponOnuControlRequest, sleGponOnuControlTimeStamp, sleGponOnuControlReqResult, sleGponOnuControlOltId, sleGponOnuControlId,
				sleGponOnuControlSerial, sleGponOnuControlNosPartition }
			STATUS current
			DESCRIPTION
				"Description."
			::= { sleGponOnuNotification 17 }


--   1.3.6.1.4.1.6296.101.23.3.3.18
-- 1.3.6.1.4.1.6296.101.23.3.3.18
		sleGponOnuUpgradeNosActiveChanged NOTIFICATION-TYPE
			OBJECTS { sleGponOnuControlRequest, sleGponOnuControlTimeStamp, sleGponOnuControlReqResult, sleGponOnuControlOltId, sleGponOnuControlId,
				sleGponOnuControlSerial }
			STATUS current
			DESCRIPTION
				"Description."
			::= { sleGponOnuNotification 18 }


--   1.3.6.1.4.1.6296.101.23.3.3.19
-- 1.3.6.1.4.1.6296.101.23.3.3.19
		sleGponOnuBlockChanged NOTIFICATION-TYPE
			OBJECTS { sleGponOnuControlRequest, sleGponOnuControlTimeStamp, sleGponOnuControlReqResult, sleGponOnuControlBlock, sleGponOnuControlSerial,
				sleGponOnuControlId, sleGponOnuControlOltId }
			STATUS current
			DESCRIPTION
				"Description."
			::= { sleGponOnuNotification 19 }


--  1.3.6.1.4.1.6296.101.23.3.3.20
		sleGponOnuUpdateOltRxPowerChanged NOTIFICATION-TYPE
			OBJECTS { sleGponOnuControlRequest, sleGponOnuControlTimeStamp, sleGponOnuControlReqResult, sleGponOnuControlOltId, sleGponOnuControlId
				 }
			STATUS current
			DESCRIPTION
				"sleGponOnuUpdateOltRxPowerChanged"
			::= { sleGponOnuNotification 20 }


--  1.3.6.1.4.1.6296.101.23.3.3.21
		sleGponOnuSystemInfoUpdated NOTIFICATION-TYPE
			OBJECTS { sleGponOnuControlRequest, sleGponOnuControlTimeStamp, sleGponOnuControlReqResult, sleGponOnuControlOltId, sleGponOnuControlId
				 }
			STATUS current
			DESCRIPTION
				"Description."
			::= { sleGponOnuNotification 21 }


--  1.3.6.1.4.1.6296.101.23.3.3.22
		sleGponOnuTxOnOptic NOTIFICATION-TYPE
			OBJECTS { sleGponOnuControlRequest, sleGponOnuControlTimeStamp, sleGponOnuControlReqResult, sleGponOnuControlOltId, sleGponOnuControlId
				 }
			STATUS current
			DESCRIPTION
				"Description."
			::= { sleGponOnuNotification 22 }


--  1.3.6.1.4.1.6296.101.23.3.3.23
		sleGponOnuLoopDetectUnblockChanged NOTIFICATION-TYPE
			OBJECTS { sleGponOnuControlRequest, sleGponOnuControlTimeStamp, sleGponOnuControlReqResult, sleGponOnuControlOltId, sleGponOnuControlId
				 }
			STATUS current
			DESCRIPTION
				"setOnuLoopDetectUnblock"
			::= { sleGponOnuNotification 23 }


--  1.3.6.1.4.1.6296.101.23.3.3.24
		sleGponOnuUserMacCntUpdated NOTIFICATION-TYPE
			OBJECTS { sleGponOnuControlRequest, sleGponOnuControlTimeStamp, sleGponOnuControlReqResult, sleGponOltId, sleGponOnuId
				 }
			STATUS current
			DESCRIPTION
				"updateOnuUserMacCnt"
			::= { sleGponOnuNotification 24 }


--  1.3.6.1.4.1.6296.101.23.3.3.25
		sleGponOnuAccountUpdated NOTIFICATION-TYPE
			OBJECTS { sleGponOnuControlRequest, sleGponOnuControlTimeStamp, sleGponOnuControlReqResult, sleGponOnuControlOltId, sleGponOnuControlId
				 }
			STATUS current
			DESCRIPTION
				"updateOnuAccount "
			::= { sleGponOnuNotification 25 }


--  1.3.6.1.4.1.6296.101.23.3.3.26
		sleGponOnuAccountChanged NOTIFICATION-TYPE
			OBJECTS { sleGponOnuControlRequest, sleGponOnuControlTimeStamp, sleGponOnuControlReqResult, sleGponOnuControlOltId, sleGponOnuControlId
				 }
			STATUS current
			DESCRIPTION
				"setOnuAccount "
			::= { sleGponOnuNotification 26 }


--  1.3.6.1.4.1.6296.101.23.3.3.27
		sleGponOnuSerialNumberRemoved NOTIFICATION-TYPE
			OBJECTS { sleGponOnuControlRequest, sleGponOnuControlTimeStamp, sleGponOnuControlReqResult, sleGponOnuControlOltId, sleGponOnuControlId
				 }
			STATUS current
			DESCRIPTION
				"removeOnuSerialNumber"
			::= { sleGponOnuNotification 27 }


--  1.3.6.1.4.1.6296.101.23.3.3.28
		sleGponOnuMgmtIpPathProtocolChanged NOTIFICATION-TYPE
			OBJECTS { sleGponOnuControlRequest, sleGponOnuControlTimeStamp, sleGponOnuControlReqResult, sleGponOnuControlOltId, sleGponOnuControlId,
				sleGponOnuControlMgmtIpPathProtocol, sleGponOnuControlMgmtIpPathId, sleGponOnuControlMgmtIpPathPassword }
			STATUS current
			DESCRIPTION
				"removeOnuSerialNumber"
			::= { sleGponOnuNotification 28 }


--  1.3.6.1.4.1.6296.101.23.3.3.29
		sleGponOnuMgmtIpPathInfoChanged NOTIFICATION-TYPE
			OBJECTS { sleGponOnuControlRequest, sleGponOnuControlTimeStamp, sleGponOnuControlReqResult, sleGponOnuControlOltId, sleGponOnuControlId,
				sleGponOnuControlMgmtIpPathUrl, sleGponOnuControlMgmtIpPathFilename }
			STATUS current
			DESCRIPTION
				"removeOnuSerialNumber"
			::= { sleGponOnuNotification 29 }


--  1.3.6.1.4.1.6296.101.23.3.3.30
		sleGponOnuMgmtIpPathCleared NOTIFICATION-TYPE
			OBJECTS { sleGponOnuControlRequest, sleGponOnuControlTimeStamp, sleGponOnuControlReqResult, sleGponOnuControlOltId, sleGponOnuControlId
				 }
			STATUS current
			DESCRIPTION
				"removeOnuSerialNumber"
			::= { sleGponOnuNotification 30 }


		sleGponOnuServiceModeChanged NOTIFICATION-TYPE
			OBJECTS { sleGponOnuControlRequest, sleGponOnuControlTimeStamp, sleGponOnuControlReqResult, sleGponOnuControlOltId, sleGponOnuControlId,
				sleGponOnuControlServiceMode }
			STATUS current
			DESCRIPTION
				"setOnuServiceMode"
			::= { sleGponOnuNotification 31 }


		sleGponOnuServiceModeCleared NOTIFICATION-TYPE
			OBJECTS { sleGponOnuControlRequest, sleGponOnuControlTimeStamp, sleGponOnuControlReqResult, sleGponOnuControlOltId, sleGponOnuControlId
				 }
			STATUS current
			DESCRIPTION
				"clearOnuServiceMode"
			::= { sleGponOnuNotification 32 }


		sleGponOnuAutoUpgradeModeChanged NOTIFICATION-TYPE
			OBJECTS { sleGponOnuControlRequest, sleGponOnuControlTimeStamp, sleGponOnuControlReqResult, sleGponOnuControlOltId, sleGponOnuControlId,
				sleGponOnuControlAutoUpgradeMode }
			STATUS current
			DESCRIPTION
				"setOnuAutoUpgradeMode"
			::= { sleGponOnuNotification 33 }


		sleGponOnuMibUpload NOTIFICATION-TYPE
			OBJECTS { sleGponOnuControlRequest, sleGponOnuControlTimeStamp, sleGponOnuControlReqResult, sleGponOnuControlOltId, sleGponOnuControlId
				 }
			STATUS current
			DESCRIPTION
				"setOnuMibUpload"
			::= { sleGponOnuNotification 34 }


		sleGponOnuReconfig NOTIFICATION-TYPE
			OBJECTS { sleGponOnuControlRequest, sleGponOnuControlTimeStamp, sleGponOnuControlReqResult, sleGponOnuControlOltId, sleGponOnuControlId
				 }
			STATUS current
			DESCRIPTION
				"setOnuReconfig"
			::= { sleGponOnuNotification 35 }


		sleGponOnuRestoreFactoryReset NOTIFICATION-TYPE
			OBJECTS { sleGponOnuControlRequest, sleGponOnuControlTimeStamp, sleGponOnuControlReqResult, sleGponOnuControlOltId, sleGponOnuControlId
				 }
			STATUS current
			DESCRIPTION
				"setOnuRestoreFactoryReset"
			::= { sleGponOnuNotification 36 }


		sleGponOnuMoveChanged NOTIFICATION-TYPE
			OBJECTS { sleGponOnuControlRequest, sleGponOnuControlTimeStamp, sleGponOnuControlReqResult, sleGponOnuControlOltId, sleGponOnuControlId,
				sleGponOnuControlMoveOltId, sleGponOnuControlMoveOnuId }
			STATUS current
			DESCRIPTION
				"setOnuMove"
			::= { sleGponOnuNotification 37 }


		sleGponOnuAuthReauthSpecificChanged NOTIFICATION-TYPE
			OBJECTS { sleGponOnuControlRequest, sleGponOnuControlTimeStamp, sleGponOnuControlReqResult, sleGponOnuControlOltId, sleGponOnuControlId
				 }
			STATUS current
			DESCRIPTION
				"setOnuAuthReauthSpecific"
			::= { sleGponOnuNotification 38 }


		sleGponOnuRadiusAttributeChanged NOTIFICATION-TYPE
			OBJECTS { sleGponOnuControlRequest, sleGponOnuControlTimeStamp, sleGponOnuControlReqResult, sleGponOnuControlOltId, sleGponOnuControlId,
				sleGponOnuControlAuthOnuProfile, sleGponOnuControlAuthOnuVlan4, sleGponOnuControlAuthOnuVlan6, sleGponOnuControlAuthOnuIpv4, sleGponOnuControlAuthOnuIpv6,
				sleGponOnuControlAuthOnuUniPortAdmin, sleGponOnuControlAuthOnuUniEthMedium, sleGponOnuControlAuthOnuUniEthSpeed, sleGponOnuControlAuthOnuUniEthDuplex }
			STATUS current
			DESCRIPTION
				"setOnuRadiusAttribute"
			::= { sleGponOnuNotification 39 }


		sleGponOnuPloamReset NOTIFICATION-TYPE
			OBJECTS { sleGponOnuControlRequest, sleGponOnuControlTimeStamp, sleGponOnuControlReqResult, sleGponOnuControlOltId, sleGponOnuControlId,
				sleGponOnuControlSerial }
			STATUS current
			DESCRIPTION
				"setOnuPloamReset "
			::= { sleGponOnuNotification 40 }


--   1.3.6.1.4.1.6296.101.23.4
-- 1.3.6.1.4.1.6296.101.23.4
		sleGponTcont OBJECT IDENTIFIER ::= { sleGpon 4 }


--   1.3.6.1.4.1.6296.101.23.4.1
-- 1.3.6.1.4.1.6296.101.23.4.1
		sleGponTcontTable OBJECT-TYPE
			SYNTAX SEQUENCE OF SleGponTcontEntry
			MAX-ACCESS not-accessible
			STATUS current
			DESCRIPTION
				"sleGponTcontTable"
			::= { sleGponTcont 1 }


--   1.3.6.1.4.1.6296.101.23.4.1.1
-- 1.3.6.1.4.1.6296.101.23.4.1.1
		sleGponTcontEntry OBJECT-TYPE
			SYNTAX SleGponTcontEntry
			MAX-ACCESS not-accessible
			STATUS current
			DESCRIPTION
				"key: sleGponOltId, sleGponTcontId"
			INDEX { sleGponOltId, sleGponTcontId }
			::= { sleGponTcontTable 1 }


		SleGponTcontEntry ::=
			SEQUENCE {
				sleGponTcontId
					INTEGER,
				sleGponTcontOnuId
					INTEGER,
				sleGponTcontDBAMode
					INTEGER,
				sleGponTcontFixedBw
					INTEGER,
				sleGponTcontAssuredBw
					INTEGER,
				sleGponTcontMaxBw
					INTEGER
			 }

--   1.3.6.1.4.1.6296.101.23.4.1.1.1
-- 1.3.6.1.4.1.6296.101.23.4.1.1.1
		sleGponTcontId OBJECT-TYPE
			SYNTAX INTEGER (1..512)
			MAX-ACCESS read-only
			STATUS current
			DESCRIPTION
				"Tcon Id"
			::= { sleGponTcontEntry 1 }


--   1.3.6.1.4.1.6296.101.23.4.1.1.2
-- 1.3.6.1.4.1.6296.101.23.4.1.1.2
		sleGponTcontOnuId OBJECT-TYPE
			SYNTAX INTEGER (1..65535)
			MAX-ACCESS read-only
			STATUS current
			DESCRIPTION
				"Tcont assigned ONU Id"
			::= { sleGponTcontEntry 2 }


--   1.3.6.1.4.1.6296.101.23.4.1.1.3
-- 1.3.6.1.4.1.6296.101.23.4.1.1.3
		sleGponTcontDBAMode OBJECT-TYPE
			SYNTAX INTEGER
				{
				nsr(1),
				sr(2),
				fixed(3)
				}
			MAX-ACCESS read-only
			STATUS current
			DESCRIPTION
				"Status reports received from ONUs"
			::= { sleGponTcontEntry 3 }


--   1.3.6.1.4.1.6296.101.23.4.1.1.4
-- 1.3.6.1.4.1.6296.101.23.4.1.1.4
		sleGponTcontFixedBw OBJECT-TYPE
			SYNTAX INTEGER (1..65535)
			UNITS "64kbps"
			MAX-ACCESS read-only
			STATUS current
			DESCRIPTION
				"Upstream fixed bandwidth.<128-1031616>"
			::= { sleGponTcontEntry 4 }


--   1.3.6.1.4.1.6296.101.23.4.1.1.5
-- 1.3.6.1.4.1.6296.101.23.4.1.1.5
		sleGponTcontAssuredBw OBJECT-TYPE
			SYNTAX INTEGER (1..65535)
			UNITS "64kbps"
			MAX-ACCESS read-only
			STATUS current
			DESCRIPTION
				"Upstream assured bandwidth.<0-1031616>"
			::= { sleGponTcontEntry 5 }


--   1.3.6.1.4.1.6296.101.23.4.1.1.6
-- 1.3.6.1.4.1.6296.101.23.4.1.1.6
		sleGponTcontMaxBw OBJECT-TYPE
			SYNTAX INTEGER (1..65535)
			UNITS "64kbps"
			MAX-ACCESS read-only
			STATUS current
			DESCRIPTION
				"Upstream max bandwidth.<128-1031616>"
			::= { sleGponTcontEntry 6 }


--   1.3.6.1.4.1.6296.101.23.4.2
-- 1.3.6.1.4.1.6296.101.23.4.2
		sleGponTcontControl OBJECT IDENTIFIER ::= { sleGponTcont 2 }


--   1.3.6.1.4.1.6296.101.23.4.2.1
-- 1.3.6.1.4.1.6296.101.23.4.2.1
		sleGponTcontControlRequest OBJECT-TYPE
			SYNTAX INTEGER
				{
				createTcon(1),
				destroyTcon(2)
				}
			MAX-ACCESS read-write
			STATUS current
			DESCRIPTION
				"The request of a user command"
			::= { sleGponTcontControl 1 }


--   1.3.6.1.4.1.6296.101.23.4.2.2
-- 1.3.6.1.4.1.6296.101.23.4.2.2
		sleGponTcontControlStatus OBJECT-TYPE
			SYNTAX SleControlStatusType
			MAX-ACCESS read-only
			STATUS current
			DESCRIPTION
				"The status of user command"
			::= { sleGponTcontControl 2 }


--   1.3.6.1.4.1.6296.101.23.4.2.3
-- 1.3.6.1.4.1.6296.101.23.4.2.3
		sleGponTcontControlTimer OBJECT-TYPE
			SYNTAX Gauge32
			MAX-ACCESS read-write
			STATUS current
			DESCRIPTION
				"The maximum time for the manager for a long running user command"
			::= { sleGponTcontControl 3 }


--   1.3.6.1.4.1.6296.101.23.4.2.4
-- 1.3.6.1.4.1.6296.101.23.4.2.4
		sleGponTcontControlTimeStamp OBJECT-TYPE
			SYNTAX TimeTicks
			MAX-ACCESS read-only
			STATUS current
			DESCRIPTION
				"The time stamp of the last command(end of command)"
			::= { sleGponTcontControl 4 }


--   1.3.6.1.4.1.6296.101.23.4.2.5
-- 1.3.6.1.4.1.6296.101.23.4.2.5
		sleGponTcontControlReqResult OBJECT-TYPE
			SYNTAX SleControlRequestResultType
			MAX-ACCESS read-only
			STATUS current
			DESCRIPTION
				"The result of the last user command"
			::= { sleGponTcontControl 5 }


--   1.3.6.1.4.1.6296.101.23.4.2.6
-- 1.3.6.1.4.1.6296.101.23.4.2.6
		sleGponTcontControlId OBJECT-TYPE
			SYNTAX INTEGER (1..65535)
			MAX-ACCESS read-write
			STATUS current
			DESCRIPTION
				"Tcon Id.<256-1023>"
			::= { sleGponTcontControl 6 }


		sleGponTcontControlOltId OBJECT-TYPE
			SYNTAX INTEGER (1..2147483647)
			MAX-ACCESS read-write
			STATUS current
			DESCRIPTION
				"Gpon Olt Id"
			::= { sleGponTcontControl 7 }


--   1.3.6.1.4.1.6296.101.23.4.2.8
-- 1.3.6.1.4.1.6296.101.23.4.2.8
		sleGponTcontControlOnuId OBJECT-TYPE
			SYNTAX INTEGER (1..65535)
			MAX-ACCESS read-write
			STATUS current
			DESCRIPTION
				"Gpon Onu Id"
			::= { sleGponTcontControl 8 }


--   1.3.6.1.4.1.6296.101.23.4.2.9
-- 1.3.6.1.4.1.6296.101.23.4.2.9
		sleGponTcontControlDBAMode OBJECT-TYPE
			SYNTAX INTEGER
				{
				nsr(1),
				sr(2),
				fixed(3)
				}
			MAX-ACCESS read-write
			STATUS current
			DESCRIPTION
				"Status reports received from ONUs"
			::= { sleGponTcontControl 9 }


--   1.3.6.1.4.1.6296.101.23.4.2.10
-- 1.3.6.1.4.1.6296.101.23.4.2.10
		sleGponTcontControlFixedBw OBJECT-TYPE
			SYNTAX INTEGER (1..65535)
			MAX-ACCESS read-write
			STATUS current
			DESCRIPTION
				"Upstream fixed bandwidth.<128-1031616>"
			::= { sleGponTcontControl 10 }


--   1.3.6.1.4.1.6296.101.23.4.2.11
-- 1.3.6.1.4.1.6296.101.23.4.2.11
		sleGponTcontControlAssuredBw OBJECT-TYPE
			SYNTAX INTEGER (1..65535)
			MAX-ACCESS read-write
			STATUS current
			DESCRIPTION
				"Upstream assured bandwidth.<0-1031616>"
			::= { sleGponTcontControl 11 }


--   1.3.6.1.4.1.6296.101.23.4.2.12
-- 1.3.6.1.4.1.6296.101.23.4.2.12
		sleGponTcontControlMaxBw OBJECT-TYPE
			SYNTAX INTEGER (1..65535)
			MAX-ACCESS read-write
			STATUS current
			DESCRIPTION
				"Upstream max bandwidth.<128-1031616>"
			::= { sleGponTcontControl 12 }


--   1.3.6.1.4.1.6296.101.23.4.2.13
-- 1.3.6.1.4.1.6296.101.23.4.2.13
		sleGponTcontControlOnuSerial OBJECT-TYPE
			SYNTAX OCTET STRING
			MAX-ACCESS read-write
			STATUS current
			DESCRIPTION
				"ONU Serial Number"
			::= { sleGponTcontControl 13 }


--   1.3.6.1.4.1.6296.101.23.4.3
-- 1.3.6.1.4.1.6296.101.23.4.3
		sleGponTcontNotification OBJECT IDENTIFIER ::= { sleGponTcont 3 }


--   1.3.6.1.4.1.6296.101.23.4.3.1
-- 1.3.6.1.4.1.6296.101.23.4.3.1
		sleGponTcontCreated NOTIFICATION-TYPE
			OBJECTS { sleGponTcontControlRequest, sleGponTcontControlTimeStamp, sleGponTcontControlReqResult, sleGponTcontControlId, sleGponTcontControlOltId,
				sleGponTcontControlOnuId, sleGponTcontControlDBAMode, sleGponTcontControlFixedBw, sleGponTcontControlAssuredBw, sleGponTcontControlMaxBw,
				sleGponTcontControlOnuSerial }
			STATUS current
			DESCRIPTION
				"Description."
			::= { sleGponTcontNotification 1 }


--   1.3.6.1.4.1.6296.101.23.4.3.2
-- 1.3.6.1.4.1.6296.101.23.4.3.2
		sleGponTcontDestroyed NOTIFICATION-TYPE
			OBJECTS { sleGponTcontControlRequest, sleGponTcontControlTimeStamp, sleGponTcontControlReqResult, sleGponTcontControlId, sleGponTcontControlOltId,
				sleGponTcontControlOnuId, sleGponTcontControlOnuSerial }
			STATUS current
			DESCRIPTION
				"Description."
			::= { sleGponTcontNotification 2 }


--   1.3.6.1.4.1.6296.101.23.5
-- 1.3.6.1.4.1.6296.101.23.5
		sleGponProfile OBJECT IDENTIFIER ::= { sleGpon 5 }


--   1.3.6.1.4.1.6296.101.23.5.1
-- 1.3.6.1.4.1.6296.101.23.5.1
		sleGponProfileBase OBJECT IDENTIFIER ::= { sleGponProfile 1 }


--   1.3.6.1.4.1.6296.101.23.5.1.1
-- 1.3.6.1.4.1.6296.101.23.5.1.1
		sleGponProfileBaseTable OBJECT-TYPE
			SYNTAX SEQUENCE OF SleGponProfileBaseEntry
			MAX-ACCESS not-accessible
			STATUS current
			DESCRIPTION
				"sleGponProfileBaseTable"
			::= { sleGponProfileBase 1 }


--   1.3.6.1.4.1.6296.101.23.5.1.1.1
-- 1.3.6.1.4.1.6296.101.23.5.1.1.1
		sleGponProfileBaseEntry OBJECT-TYPE
			SYNTAX SleGponProfileBaseEntry
			MAX-ACCESS not-accessible
			STATUS current
			DESCRIPTION
				"key: sleGponProfileId"
			INDEX { sleGponProfileId }
			::= { sleGponProfileBaseTable 1 }


		SleGponProfileBaseEntry ::=
			SEQUENCE {
				sleGponProfileId
					INTEGER,
				sleGponProfileName
					OCTET STRING,
				sleGponProfileDscpToPbit
					INTEGER,
				sleGponProfileTcontProfileCnt
					INTEGER,
				sleGponProfileTcontProfile
					OCTET STRING,
				sleGponProfileVoIPProfileCnt
					INTEGER,
				sleGponProfileVoIPProfile
					OCTET STRING
			 }

--   1.3.6.1.4.1.6296.101.23.5.1.1.1.1
-- 1.3.6.1.4.1.6296.101.23.5.1.1.1.1
		sleGponProfileId OBJECT-TYPE
			SYNTAX INTEGER (1..512)
			MAX-ACCESS read-only
			STATUS current
			DESCRIPTION
				"Profile Id"
			::= { sleGponProfileBaseEntry 1 }


--   1.3.6.1.4.1.6296.101.23.5.1.1.1.2
-- 1.3.6.1.4.1.6296.101.23.5.1.1.1.2
		sleGponProfileName OBJECT-TYPE
			SYNTAX OCTET STRING
			MAX-ACCESS read-only
			STATUS current
			DESCRIPTION
				"Profile Name"
			::= { sleGponProfileBaseEntry 2 }


--   1.3.6.1.4.1.6296.101.23.5.1.1.1.3
-- 1.3.6.1.4.1.6296.101.23.5.1.1.1.3
		sleGponProfileDscpToPbit OBJECT-TYPE
			SYNTAX INTEGER
				{
				enable(1),
				disable(2)
				}
			MAX-ACCESS read-only
			STATUS current
			DESCRIPTION
				"DSCP to P bit marking"
			::= { sleGponProfileBaseEntry 3 }


--   1.3.6.1.4.1.6296.101.23.5.1.1.1.4
-- 1.3.6.1.4.1.6296.101.23.5.1.1.1.4
		sleGponProfileTcontProfileCnt OBJECT-TYPE
			SYNTAX INTEGER (1..65535)
			MAX-ACCESS read-only
			STATUS current
			DESCRIPTION
				"Assgined Tcont Profile count
				Indicate how many tcont profile assigned"
			::= { sleGponProfileBaseEntry 4 }


--   1.3.6.1.4.1.6296.101.23.5.1.1.1.5
-- 1.3.6.1.4.1.6296.101.23.5.1.1.1.5
		sleGponProfileTcontProfile OBJECT-TYPE
			SYNTAX OCTET STRING
			MAX-ACCESS read-only
			STATUS current
			DESCRIPTION
				"Assigned TconT Profile Map
				2bytes indicate TconT Profile Index.
				# 0001 0003 0004 ....."
			::= { sleGponProfileBaseEntry 5 }


--   1.3.6.1.4.1.6296.101.23.5.1.1.1.6
-- 1.3.6.1.4.1.6296.101.23.5.1.1.1.6
		sleGponProfileVoIPProfileCnt OBJECT-TYPE
			SYNTAX INTEGER (1..65535)
			MAX-ACCESS read-only
			STATUS current
			DESCRIPTION
				"Assgined VoIP Profile count
				Indicate how many VoIP profile assigned(UnUsed)"
			::= { sleGponProfileBaseEntry 6 }


--   1.3.6.1.4.1.6296.101.23.5.1.1.1.7
-- 1.3.6.1.4.1.6296.101.23.5.1.1.1.7
		sleGponProfileVoIPProfile OBJECT-TYPE
			SYNTAX OCTET STRING
			MAX-ACCESS read-only
			STATUS current
			DESCRIPTION
				"Assigned VoIP Profile Map
				2bytes indicate VoIP Profile Index(UnUsed)"
			::= { sleGponProfileBaseEntry 7 }


--   1.3.6.1.4.1.6296.101.23.5.1.2
-- 1.3.6.1.4.1.6296.101.23.5.1.2
		sleGponProfileBaseControl OBJECT IDENTIFIER ::= { sleGponProfileBase 2 }


--   1.3.6.1.4.1.6296.101.23.5.1.2.1
-- 1.3.6.1.4.1.6296.101.23.5.1.2.1
		sleGponProfileBaseControlRequest OBJECT-TYPE
			SYNTAX INTEGER
				{
				createProfile(1),
				modifyProfile(2),
				destroyProfile(3),
				updateTcontProfile(4),
				updateVoipProfile(5)
				}
			MAX-ACCESS read-write
			STATUS current
			DESCRIPTION
				"The request of a user command"
			::= { sleGponProfileBaseControl 1 }


--   1.3.6.1.4.1.6296.101.23.5.1.2.2
-- 1.3.6.1.4.1.6296.101.23.5.1.2.2
		sleGponProfileBaseControlStatus OBJECT-TYPE
			SYNTAX SleControlStatusType
			MAX-ACCESS read-only
			STATUS current
			DESCRIPTION
				"The status of user command"
			::= { sleGponProfileBaseControl 2 }


--   1.3.6.1.4.1.6296.101.23.5.1.2.3
-- 1.3.6.1.4.1.6296.101.23.5.1.2.3
		sleGponProfileBaseControlTimer OBJECT-TYPE
			SYNTAX Gauge32
			MAX-ACCESS read-write
			STATUS current
			DESCRIPTION
				"The maximum time for the manager for a long running user command"
			::= { sleGponProfileBaseControl 3 }


--   1.3.6.1.4.1.6296.101.23.5.1.2.4
-- 1.3.6.1.4.1.6296.101.23.5.1.2.4
		sleGponProfileBaseControlTimeStamp OBJECT-TYPE
			SYNTAX TimeTicks
			MAX-ACCESS read-only
			STATUS current
			DESCRIPTION
				"The time stamp of the last command(end of command)"
			::= { sleGponProfileBaseControl 4 }


--   1.3.6.1.4.1.6296.101.23.5.1.2.5
-- 1.3.6.1.4.1.6296.101.23.5.1.2.5
		sleGponProfileBaseControlReqResult OBJECT-TYPE
			SYNTAX SleControlRequestResultType
			MAX-ACCESS read-only
			STATUS current
			DESCRIPTION
				"The result of the last user command"
			::= { sleGponProfileBaseControl 5 }


--   1.3.6.1.4.1.6296.101.23.5.1.2.6
-- 1.3.6.1.4.1.6296.101.23.5.1.2.6
		sleGponProfileBaseControlName OBJECT-TYPE
			SYNTAX OCTET STRING
			MAX-ACCESS read-write
			STATUS current
			DESCRIPTION
				"Profile Name"
			::= { sleGponProfileBaseControl 6 }


--   1.3.6.1.4.1.6296.101.23.5.1.2.7
-- 1.3.6.1.4.1.6296.101.23.5.1.2.7
		sleGponProfileBaseControlDscpToPbit OBJECT-TYPE
			SYNTAX INTEGER
				{
				enable(1),
				disable(2)
				}
			MAX-ACCESS read-write
			STATUS current
			DESCRIPTION
				"DSCP to P bit marking"
			::= { sleGponProfileBaseControl 7 }


--   1.3.6.1.4.1.6296.101.23.5.1.2.8
-- 1.3.6.1.4.1.6296.101.23.5.1.2.8
		sleGponProfileControlTcontProfileCnt OBJECT-TYPE
			SYNTAX INTEGER (1..65535)
			MAX-ACCESS read-write
			STATUS current
			DESCRIPTION
				"Assgined Tcont Profile count"
			::= { sleGponProfileBaseControl 8 }


--   1.3.6.1.4.1.6296.101.23.5.1.2.9
-- 1.3.6.1.4.1.6296.101.23.5.1.2.9
		sleGponProfileControlTcontProfile OBJECT-TYPE
			SYNTAX OCTET STRING
			MAX-ACCESS read-write
			STATUS current
			DESCRIPTION
				"Assigned TconT Profile Map"
			::= { sleGponProfileBaseControl 9 }


--   1.3.6.1.4.1.6296.101.23.5.1.2.10
-- 1.3.6.1.4.1.6296.101.23.5.1.2.10
		sleGponProfileControlVoipProfileCnt OBJECT-TYPE
			SYNTAX INTEGER (1..65535)
			MAX-ACCESS read-write
			STATUS current
			DESCRIPTION
				"Assgined VoIP Profile count"
			::= { sleGponProfileBaseControl 10 }


--   1.3.6.1.4.1.6296.101.23.5.1.2.11
-- 1.3.6.1.4.1.6296.101.23.5.1.2.11
		sleGponProfileControlVoipProfile OBJECT-TYPE
			SYNTAX OCTET STRING
			MAX-ACCESS read-write
			STATUS current
			DESCRIPTION
				"Assigned VoIP Profile Map"
			::= { sleGponProfileBaseControl 11 }


--   1.3.6.1.4.1.6296.101.23.5.1.3
-- 1.3.6.1.4.1.6296.101.23.5.1.3
		sleGponProfileBaseNotification OBJECT IDENTIFIER ::= { sleGponProfileBase 3 }


--   1.3.6.1.4.1.6296.101.23.5.1.3.1
-- 1.3.6.1.4.1.6296.101.23.5.1.3.1
		sleGponProfileBaseCreated NOTIFICATION-TYPE
			OBJECTS { sleGponProfileBaseControlRequest, sleGponProfileBaseControlTimeStamp, sleGponProfileBaseControlReqResult, sleGponProfileBaseControlName, sleGponProfileBaseControlDscpToPbit
				 }
			STATUS current
			DESCRIPTION
				"Description."
			::= { sleGponProfileBaseNotification 1 }


--   1.3.6.1.4.1.6296.101.23.5.1.3.2
-- 1.3.6.1.4.1.6296.101.23.5.1.3.2
		sleGponProfileBaseModified NOTIFICATION-TYPE
			OBJECTS { sleGponProfileBaseControlRequest, sleGponProfileBaseControlTimeStamp, sleGponProfileBaseControlReqResult, sleGponProfileBaseControlName, sleGponProfileBaseControlDscpToPbit
				 }
			STATUS current
			DESCRIPTION
				"Description."
			::= { sleGponProfileBaseNotification 2 }


--   1.3.6.1.4.1.6296.101.23.5.1.3.3
-- 1.3.6.1.4.1.6296.101.23.5.1.3.3
		sleGponProfileBaseDestroyed NOTIFICATION-TYPE
			OBJECTS { sleGponProfileBaseControlRequest, sleGponProfileBaseControlTimeStamp, sleGponProfileBaseControlReqResult, sleGponProfileBaseControlName }
			STATUS current
			DESCRIPTION
				"Description."
			::= { sleGponProfileBaseNotification 3 }


--   1.3.6.1.4.1.6296.101.23.5.1.3.4
-- 1.3.6.1.4.1.6296.101.23.5.1.3.4
		sleGponProfileTcontProfileChanged NOTIFICATION-TYPE
			OBJECTS { sleGponProfileBaseControlRequest, sleGponProfileBaseControlTimeStamp, sleGponProfileBaseControlReqResult, sleGponProfileBaseControlName, sleGponProfileControlTcontProfileCnt,
				sleGponProfileControlTcontProfile }
			STATUS current
			DESCRIPTION
				"Description."
			::= { sleGponProfileBaseNotification 4 }


--   1.3.6.1.4.1.6296.101.23.5.1.3.5
-- 1.3.6.1.4.1.6296.101.23.5.1.3.5
		sleGponProfileBaseVoIPProfileChanged NOTIFICATION-TYPE
			OBJECTS { sleGponProfileBaseControlRequest, sleGponProfileBaseControlTimeStamp, sleGponProfileBaseControlReqResult, sleGponProfileBaseControlName, sleGponProfileControlVoipProfileCnt,
				sleGponProfileControlVoipProfile }
			STATUS current
			DESCRIPTION
				"Description."
			::= { sleGponProfileBaseNotification 5 }


--   1.3.6.1.4.1.6296.101.23.5.2
-- 1.3.6.1.4.1.6296.101.23.5.2
		sleGponProfilePort OBJECT IDENTIFIER ::= { sleGponProfile 2 }


--   1.3.6.1.4.1.6296.101.23.5.2.1
-- 1.3.6.1.4.1.6296.101.23.5.2.1
		sleGponProfilePortTable OBJECT-TYPE
			SYNTAX SEQUENCE OF SleGponProfilePortEntry
			MAX-ACCESS not-accessible
			STATUS current
			DESCRIPTION
				"sleGponProfilePortTable"
			::= { sleGponProfilePort 1 }


--   1.3.6.1.4.1.6296.101.23.5.2.1.1
-- 1.3.6.1.4.1.6296.101.23.5.2.1.1
		sleGponProfilePortEntry OBJECT-TYPE
			SYNTAX SleGponProfilePortEntry
			MAX-ACCESS not-accessible
			STATUS current
			DESCRIPTION
				"key: sleGponProfileId, sleGponProfilePortId"
			INDEX { sleGponProfileId, sleGponProfilePortId }
			::= { sleGponProfilePortTable 1 }


		SleGponProfilePortEntry ::=
			SEQUENCE {
				sleGponProfilePortId
					Integer32,
				sleGponProfilePortRateLimit
					INTEGER,
				sleGponProfilePortMaxHost
					INTEGER,
				sleGponProfilePortVlan
					INTEGER,
				sleGponProfilePortCosValue
					INTEGER,
				sleGponProfilePortVlanMode
					INTEGER,
				sleGponProfilePortVlanFilter
					OCTET STRING,
				sleGponProfilePortAdmin
					INTEGER,
				sleGponProfilePortDuplex
					INTEGER,
				sleGponProfilePortSpeed
					INTEGER,
				sleGponProfilePortPause
					Integer32
			 }

--   1.3.6.1.4.1.6296.101.23.5.2.1.1.1
-- 1.3.6.1.4.1.6296.101.23.5.2.1.1.1
		sleGponProfilePortId OBJECT-TYPE
			SYNTAX Integer32 (1..65535)
			MAX-ACCESS read-only
			STATUS current
			DESCRIPTION
				"UNI Port number."
			::= { sleGponProfilePortEntry 1 }


--   1.3.6.1.4.1.6296.101.23.5.2.1.1.2
-- 1.3.6.1.4.1.6296.101.23.5.2.1.1.2
		sleGponProfilePortRateLimit OBJECT-TYPE
			SYNTAX INTEGER (1..65535)
			MAX-ACCESS read-only
			STATUS current
			DESCRIPTION
				"port through which packets are incoming. Bandwidth in steps of 64Kbps."
			::= { sleGponProfilePortEntry 2 }


--   1.3.6.1.4.1.6296.101.23.5.2.1.1.3
-- 1.3.6.1.4.1.6296.101.23.5.2.1.1.3
		sleGponProfilePortMaxHost OBJECT-TYPE
			SYNTAX INTEGER (1..65535)
			MAX-ACCESS read-only
			STATUS current
			DESCRIPTION
				"Maximum Mac learning number."
			::= { sleGponProfilePortEntry 3 }


--   1.3.6.1.4.1.6296.101.23.5.2.1.1.4
-- 1.3.6.1.4.1.6296.101.23.5.2.1.1.4
		sleGponProfilePortVlan OBJECT-TYPE
			SYNTAX INTEGER (1..65535)
			MAX-ACCESS read-only
			STATUS current
			DESCRIPTION
				"Port VLAN tagging operation."
			::= { sleGponProfilePortEntry 4 }


--   1.3.6.1.4.1.6296.101.23.5.2.1.1.5
-- 1.3.6.1.4.1.6296.101.23.5.2.1.1.5
		sleGponProfilePortCosValue OBJECT-TYPE
			SYNTAX INTEGER (1..65535)
			MAX-ACCESS read-only
			STATUS current
			DESCRIPTION
				"COS Value."
			::= { sleGponProfilePortEntry 5 }


--   1.3.6.1.4.1.6296.101.23.5.2.1.1.6
-- 1.3.6.1.4.1.6296.101.23.5.2.1.1.6
		sleGponProfilePortVlanMode OBJECT-TYPE
			SYNTAX INTEGER
				{
				keep(1),
				remove(2)
				}
			MAX-ACCESS read-only
			STATUS current
			DESCRIPTION
				"Port VLAN tagging operation mode."
			::= { sleGponProfilePortEntry 6 }


--   1.3.6.1.4.1.6296.101.23.5.2.1.1.7
-- 1.3.6.1.4.1.6296.101.23.5.2.1.1.7
		sleGponProfilePortVlanFilter OBJECT-TYPE
			SYNTAX OCTET STRING
			MAX-ACCESS read-only
			STATUS current
			DESCRIPTION
				"VLAN tagging filter configuration."
			::= { sleGponProfilePortEntry 7 }


--   1.3.6.1.4.1.6296.101.23.5.2.1.1.8
-- 1.3.6.1.4.1.6296.101.23.5.2.1.1.8
		sleGponProfilePortAdmin OBJECT-TYPE
			SYNTAX INTEGER
				{
				enable(1),
				disable(2)
				}
			MAX-ACCESS read-only
			STATUS current
			DESCRIPTION
				"Port Admin status"
			::= { sleGponProfilePortEntry 8 }


--   1.3.6.1.4.1.6296.101.23.5.2.1.1.9
-- 1.3.6.1.4.1.6296.101.23.5.2.1.1.9
		sleGponProfilePortDuplex OBJECT-TYPE
			SYNTAX INTEGER
				{
				auto(1),
				full(2),
				half(3)
				}
			MAX-ACCESS read-only
			STATUS current
			DESCRIPTION
				"Port Duplex configuration"
			::= { sleGponProfilePortEntry 9 }


--   1.3.6.1.4.1.6296.101.23.5.2.1.1.10
-- 1.3.6.1.4.1.6296.101.23.5.2.1.1.10
		sleGponProfilePortSpeed OBJECT-TYPE
			SYNTAX INTEGER
				{
				auto(1),
				speed10M(2),
				speed100M(3),
				speed1000M(4)
				}
			MAX-ACCESS read-only
			STATUS current
			DESCRIPTION
				"Port Speed configuration"
			::= { sleGponProfilePortEntry 10 }


--   1.3.6.1.4.1.6296.101.23.5.2.1.1.11
-- 1.3.6.1.4.1.6296.101.23.5.2.1.1.11
		sleGponProfilePortPause OBJECT-TYPE
			SYNTAX Integer32
			MAX-ACCESS read-only
			STATUS current
			DESCRIPTION
				"Port Pause-time configuration"
			::= { sleGponProfilePortEntry 11 }


--   1.3.6.1.4.1.6296.101.23.5.2.2
-- 1.3.6.1.4.1.6296.101.23.5.2.2
		sleGponProfilePortControl OBJECT IDENTIFIER ::= { sleGponProfilePort 2 }


--   1.3.6.1.4.1.6296.101.23.5.2.2.1
-- 1.3.6.1.4.1.6296.101.23.5.2.2.1
		sleGponProfilePortControlRequest OBJECT-TYPE
			SYNTAX INTEGER
				{
				setPortRateLimit(1),
				setPortMaxHost(2),
				setPortVlanOper(3),
				setPortVlanFilter(4),
				setPortAdmin(5),
				setPortDuplex(6),
				setPortSpeed(7),
				setPortPause(8)
				}
			MAX-ACCESS read-write
			STATUS current
			DESCRIPTION
				"The request of a user command"
			::= { sleGponProfilePortControl 1 }


--   1.3.6.1.4.1.6296.101.23.5.2.2.2
-- 1.3.6.1.4.1.6296.101.23.5.2.2.2
		sleGponProfilePortControlStatus OBJECT-TYPE
			SYNTAX SleControlStatusType
			MAX-ACCESS read-only
			STATUS current
			DESCRIPTION
				"The status of user command"
			::= { sleGponProfilePortControl 2 }


--   1.3.6.1.4.1.6296.101.23.5.2.2.3
-- 1.3.6.1.4.1.6296.101.23.5.2.2.3
		sleGponProfilePortControlTimer OBJECT-TYPE
			SYNTAX Gauge32
			MAX-ACCESS read-write
			STATUS current
			DESCRIPTION
				"The maximum time for the manager for a long running user command"
			::= { sleGponProfilePortControl 3 }


--   1.3.6.1.4.1.6296.101.23.5.2.2.4
-- 1.3.6.1.4.1.6296.101.23.5.2.2.4
		sleGponProfilePortControlTimeStamp OBJECT-TYPE
			SYNTAX TimeTicks
			MAX-ACCESS read-only
			STATUS current
			DESCRIPTION
				"The time stamp of the last command(end of command)"
			::= { sleGponProfilePortControl 4 }


--   1.3.6.1.4.1.6296.101.23.5.2.2.5
-- 1.3.6.1.4.1.6296.101.23.5.2.2.5
		sleGponProfilePortControlReqResult OBJECT-TYPE
			SYNTAX SleControlRequestResultType
			MAX-ACCESS read-only
			STATUS current
			DESCRIPTION
				"The result of the last user command"
			::= { sleGponProfilePortControl 5 }


--   1.3.6.1.4.1.6296.101.23.5.2.2.6
-- 1.3.6.1.4.1.6296.101.23.5.2.2.6
		sleGponProfilePortControlId OBJECT-TYPE
			SYNTAX INTEGER (1..65535)
			MAX-ACCESS read-write
			STATUS current
			DESCRIPTION
				"Profile Index"
			::= { sleGponProfilePortControl 6 }


--   1.3.6.1.4.1.6296.101.23.5.2.2.7
-- 1.3.6.1.4.1.6296.101.23.5.2.2.7
		sleGponProfilePortControlPortId OBJECT-TYPE
			SYNTAX INTEGER (1..65535)
			MAX-ACCESS read-write
			STATUS current
			DESCRIPTION
				"UNI Port number"
			::= { sleGponProfilePortControl 7 }


--   1.3.6.1.4.1.6296.101.23.5.2.2.8
-- 1.3.6.1.4.1.6296.101.23.5.2.2.8
		sleGponProfilePortControlRateLimit OBJECT-TYPE
			SYNTAX INTEGER (1..65535)
			MAX-ACCESS read-write
			STATUS current
			DESCRIPTION
				"port through which packets are incoming. Bandwidth in steps of 64Kbps"
			::= { sleGponProfilePortControl 8 }


--   1.3.6.1.4.1.6296.101.23.5.2.2.9
-- 1.3.6.1.4.1.6296.101.23.5.2.2.9
		sleGponProfilePortControlMaxHost OBJECT-TYPE
			SYNTAX INTEGER (1..65535)
			MAX-ACCESS read-write
			STATUS current
			DESCRIPTION
				"Maximum Mac learning number"
			::= { sleGponProfilePortControl 9 }


--   1.3.6.1.4.1.6296.101.23.5.2.2.10
-- 1.3.6.1.4.1.6296.101.23.5.2.2.10
		sleGponProfilePortControlVlan OBJECT-TYPE
			SYNTAX INTEGER (1..65535)
			MAX-ACCESS read-write
			STATUS current
			DESCRIPTION
				"Port VLAN tagging operation"
			::= { sleGponProfilePortControl 10 }


--   1.3.6.1.4.1.6296.101.23.5.2.2.11
-- 1.3.6.1.4.1.6296.101.23.5.2.2.11
		sleGponProfilePortControlCosValue OBJECT-TYPE
			SYNTAX INTEGER (1..65535)
			MAX-ACCESS read-write
			STATUS current
			DESCRIPTION
				"COS Value"
			::= { sleGponProfilePortControl 11 }


--   1.3.6.1.4.1.6296.101.23.5.2.2.12
-- 1.3.6.1.4.1.6296.101.23.5.2.2.12
		sleGponProfilePortControlVlanMode OBJECT-TYPE
			SYNTAX INTEGER
				{
				keep(1),
				remove(2)
				}
			MAX-ACCESS read-write
			STATUS current
			DESCRIPTION
				"Port VLAN tagging operation mode."
			::= { sleGponProfilePortControl 12 }


--   1.3.6.1.4.1.6296.101.23.5.2.2.13
-- 1.3.6.1.4.1.6296.101.23.5.2.2.13
		sleGponProfilePortControlVlanFilter OBJECT-TYPE
			SYNTAX OCTET STRING
			MAX-ACCESS read-write
			STATUS current
			DESCRIPTION
				"VLAN tagging filter configuration."
			::= { sleGponProfilePortControl 13 }


--   1.3.6.1.4.1.6296.101.23.5.2.2.14
-- 1.3.6.1.4.1.6296.101.23.5.2.2.14
		sleGponProfilePortControlPortAdmin OBJECT-TYPE
			SYNTAX INTEGER
				{
				enable(1),
				disable(2)
				}
			MAX-ACCESS read-write
			STATUS current
			DESCRIPTION
				"Port Admin status"
			::= { sleGponProfilePortControl 14 }


--   1.3.6.1.4.1.6296.101.23.5.2.2.15
-- 1.3.6.1.4.1.6296.101.23.5.2.2.15
		sleGponProfilePortControlPortDuplex OBJECT-TYPE
			SYNTAX INTEGER
				{
				auto(1),
				full(2),
				half(3)
				}
			MAX-ACCESS read-write
			STATUS current
			DESCRIPTION
				"Port Duplex configuration"
			::= { sleGponProfilePortControl 15 }


--   1.3.6.1.4.1.6296.101.23.5.2.2.16
-- 1.3.6.1.4.1.6296.101.23.5.2.2.16
		sleGponProfilePortControlPortSpeed OBJECT-TYPE
			SYNTAX INTEGER
				{
				auto(1),
				speed10M(2),
				speed100M(3),
				speed1000M(4)
				}
			MAX-ACCESS read-write
			STATUS current
			DESCRIPTION
				"Port Speed configuration"
			::= { sleGponProfilePortControl 16 }


--   1.3.6.1.4.1.6296.101.23.5.2.2.17
-- 1.3.6.1.4.1.6296.101.23.5.2.2.17
		sleGponProfilePortControlPortPause OBJECT-TYPE
			SYNTAX Integer32
			MAX-ACCESS read-write
			STATUS current
			DESCRIPTION
				"Port Pause-time configuration"
			::= { sleGponProfilePortControl 17 }


--   1.3.6.1.4.1.6296.101.23.5.2.3
-- 1.3.6.1.4.1.6296.101.23.5.2.3
		sleGponProfilePortNotification OBJECT IDENTIFIER ::= { sleGponProfilePort 3 }


--   1.3.6.1.4.1.6296.101.23.5.2.3.1
-- 1.3.6.1.4.1.6296.101.23.5.2.3.1
		sleGponProfilePortRateLimitChanged NOTIFICATION-TYPE
			OBJECTS { sleGponProfilePortControlRequest, sleGponProfilePortControlTimeStamp, sleGponProfilePortControlReqResult, sleGponProfilePortControlId, sleGponProfilePortControlPortId,
				sleGponProfilePortControlRateLimit }
			STATUS current
			DESCRIPTION
				"Description."
			::= { sleGponProfilePortNotification 1 }


--   1.3.6.1.4.1.6296.101.23.5.2.3.2
-- 1.3.6.1.4.1.6296.101.23.5.2.3.2
		sleGponProfilePortMaxHostChanged NOTIFICATION-TYPE
			OBJECTS { sleGponProfilePortControlRequest, sleGponProfilePortControlTimeStamp, sleGponProfilePortControlReqResult, sleGponProfilePortControlId, sleGponProfilePortControlPortId,
				sleGponProfilePortControlMaxHost }
			STATUS current
			DESCRIPTION
				"Description."
			::= { sleGponProfilePortNotification 2 }


--   1.3.6.1.4.1.6296.101.23.5.2.3.3
-- 1.3.6.1.4.1.6296.101.23.5.2.3.3
		sleGponProfilePortVlanOperChanged NOTIFICATION-TYPE
			OBJECTS { sleGponProfilePortControlRequest, sleGponProfilePortControlTimeStamp, sleGponProfilePortControlReqResult, sleGponProfilePortControlId, sleGponProfilePortControlPortId,
				sleGponProfilePortControlVlan, sleGponProfilePortControlCosValue, sleGponProfilePortControlVlanMode }
			STATUS current
			DESCRIPTION
				"Description."
			::= { sleGponProfilePortNotification 3 }


--   1.3.6.1.4.1.6296.101.23.5.2.3.4
-- 1.3.6.1.4.1.6296.101.23.5.2.3.4
		sleGponProfilePortVlanFilterChanged NOTIFICATION-TYPE
			OBJECTS { sleGponProfilePortControlRequest, sleGponProfilePortControlTimeStamp, sleGponProfilePortControlReqResult, sleGponProfilePortControlId, sleGponProfilePortControlPortId,
				sleGponProfilePortControlVlanFilter }
			STATUS current
			DESCRIPTION
				"Description."
			::= { sleGponProfilePortNotification 4 }


--   1.3.6.1.4.1.6296.101.23.5.2.3.5
-- 1.3.6.1.4.1.6296.101.23.5.2.3.5
		sleGponProfilePortAdminChanged NOTIFICATION-TYPE
			OBJECTS { sleGponProfilePortControlRequest, sleGponProfilePortControlTimeStamp, sleGponProfilePortControlReqResult, sleGponProfilePortControlId, sleGponProfilePortControlPortId,
				sleGponProfilePortControlPortAdmin }
			STATUS current
			DESCRIPTION
				"Description."
			::= { sleGponProfilePortNotification 5 }


--   1.3.6.1.4.1.6296.101.23.5.2.3.6
-- 1.3.6.1.4.1.6296.101.23.5.2.3.6
		sleGponProfilePortDuplexChanged NOTIFICATION-TYPE
			OBJECTS { sleGponProfilePortControlRequest, sleGponProfilePortControlTimeStamp, sleGponProfilePortControlReqResult, sleGponProfilePortControlId, sleGponProfilePortControlPortId,
				sleGponProfilePortControlPortDuplex }
			STATUS current
			DESCRIPTION
				"Description."
			::= { sleGponProfilePortNotification 6 }


--   1.3.6.1.4.1.6296.101.23.5.2.3.7
-- 1.3.6.1.4.1.6296.101.23.5.2.3.7
		sleGponProfilePortSpeedChanged NOTIFICATION-TYPE
			OBJECTS { sleGponProfilePortControlRequest, sleGponProfilePortControlTimeStamp, sleGponProfilePortControlReqResult, sleGponProfilePortControlId, sleGponProfilePortControlPortId,
				sleGponProfilePortControlPortSpeed }
			STATUS current
			DESCRIPTION
				"Description."
			::= { sleGponProfilePortNotification 7 }


--   1.3.6.1.4.1.6296.101.23.5.2.3.8
-- 1.3.6.1.4.1.6296.101.23.5.2.3.8
		sleGponProfilePorPauseChanged NOTIFICATION-TYPE
			OBJECTS { sleGponProfilePortControlRequest, sleGponProfilePortControlTimeStamp, sleGponProfilePortControlReqResult, sleGponProfilePortControlId, sleGponProfilePortControlPortId,
				sleGponProfilePortControlPortPause }
			STATUS current
			DESCRIPTION
				"Description."
			::= { sleGponProfilePortNotification 8 }


--   1.3.6.1.4.1.6296.101.23.5.3
-- 1.3.6.1.4.1.6296.101.23.5.3
		sleGponProfileDba OBJECT IDENTIFIER ::= { sleGponProfile 3 }


--   1.3.6.1.4.1.6296.101.23.5.3.1
-- 1.3.6.1.4.1.6296.101.23.5.3.1
		sleGponProfileDbaTable OBJECT-TYPE
			SYNTAX SEQUENCE OF SleGponProfileDbaEntry
			MAX-ACCESS not-accessible
			STATUS current
			DESCRIPTION
				"sleGponProfileDbaTable"
			::= { sleGponProfileDba 1 }


--   1.3.6.1.4.1.6296.101.23.5.3.1.1
-- 1.3.6.1.4.1.6296.101.23.5.3.1.1
		sleGponProfileDbaEntry OBJECT-TYPE
			SYNTAX SleGponProfileDbaEntry
			MAX-ACCESS not-accessible
			STATUS current
			DESCRIPTION
				"key: sleGponProfileDbaId"
			INDEX { sleGponProfileDbaId }
			::= { sleGponProfileDbaTable 1 }


		SleGponProfileDbaEntry ::=
			SEQUENCE {
				sleGponProfileDbaId
					Integer32,
				sleGponProfileDbaName
					OCTET STRING,
				sleGponProfileDbaMode
					INTEGER,
				sleGponProfileDbaSlaFixedBw
					Integer32,
				sleGponProfileDbaSlaAssuredBw
					Integer32,
				sleGponProfileDbaSlaMaxBw
					Integer32
			 }

--   1.3.6.1.4.1.6296.101.23.5.3.1.1.1
-- 1.3.6.1.4.1.6296.101.23.5.3.1.1.1
		sleGponProfileDbaId OBJECT-TYPE
			SYNTAX Integer32 (1..65535)
			MAX-ACCESS read-only
			STATUS current
			DESCRIPTION
				"DBA Profile Id"
			::= { sleGponProfileDbaEntry 1 }


--   1.3.6.1.4.1.6296.101.23.5.3.1.1.2
-- 1.3.6.1.4.1.6296.101.23.5.3.1.1.2
		sleGponProfileDbaName OBJECT-TYPE
			SYNTAX OCTET STRING
			MAX-ACCESS read-only
			STATUS current
			DESCRIPTION
				"DBA Profile Name"
			::= { sleGponProfileDbaEntry 2 }


--   1.3.6.1.4.1.6296.101.23.5.3.1.1.3
-- 1.3.6.1.4.1.6296.101.23.5.3.1.1.3
		sleGponProfileDbaMode OBJECT-TYPE
			SYNTAX INTEGER
				{
				fixed(1),
				sr(2),
				nsr(3),
				unknown(255)
				}
			MAX-ACCESS read-only
			STATUS current
			DESCRIPTION
				"DBA mode"
			::= { sleGponProfileDbaEntry 3 }


--   1.3.6.1.4.1.6296.101.23.5.3.1.1.4
-- 1.3.6.1.4.1.6296.101.23.5.3.1.1.4
		sleGponProfileDbaSlaFixedBw OBJECT-TYPE
			SYNTAX Integer32
			UNITS "64 kbps"
			MAX-ACCESS read-only
			STATUS current
			DESCRIPTION
				"128-1031616, unit : 64kbps"
			::= { sleGponProfileDbaEntry 4 }


--   1.3.6.1.4.1.6296.101.23.5.3.1.1.5
-- 1.3.6.1.4.1.6296.101.23.5.3.1.1.5
		sleGponProfileDbaSlaAssuredBw OBJECT-TYPE
			SYNTAX Integer32
			UNITS "64 kbps"
			MAX-ACCESS read-only
			STATUS current
			DESCRIPTION
				"0-1031616, unit : 64kbps"
			::= { sleGponProfileDbaEntry 5 }


--   1.3.6.1.4.1.6296.101.23.5.3.1.1.6
-- 1.3.6.1.4.1.6296.101.23.5.3.1.1.6
		sleGponProfileDbaSlaMaxBw OBJECT-TYPE
			SYNTAX Integer32
			UNITS "64 kbps"
			MAX-ACCESS read-only
			STATUS current
			DESCRIPTION
				"128-1031616, unit : 64kbps"
			::= { sleGponProfileDbaEntry 6 }


--   1.3.6.1.4.1.6296.101.23.5.3.2
-- 1.3.6.1.4.1.6296.101.23.5.3.2
		sleGponProfileDbaControl OBJECT IDENTIFIER ::= { sleGponProfileDba 2 }


--   1.3.6.1.4.1.6296.101.23.5.3.2.1
-- 1.3.6.1.4.1.6296.101.23.5.3.2.1
		sleGponProfileDbaControlRequest OBJECT-TYPE
			SYNTAX INTEGER
				{
				createProfile(1),
				destroyProfile(2),
				updateProfile(3)
				}
			MAX-ACCESS read-write
			STATUS current
			DESCRIPTION
				"The request of a user command"
			::= { sleGponProfileDbaControl 1 }


--   1.3.6.1.4.1.6296.101.23.5.3.2.2
-- 1.3.6.1.4.1.6296.101.23.5.3.2.2
		sleGponProfileDbaControlStatus OBJECT-TYPE
			SYNTAX SleControlStatusType
			MAX-ACCESS read-only
			STATUS current
			DESCRIPTION
				"The status of user command"
			::= { sleGponProfileDbaControl 2 }


--   1.3.6.1.4.1.6296.101.23.5.3.2.3
-- 1.3.6.1.4.1.6296.101.23.5.3.2.3
		sleGponProfileDbaControlTimer OBJECT-TYPE
			SYNTAX Gauge32
			MAX-ACCESS read-write
			STATUS current
			DESCRIPTION
				"The maximum time for the manager for a long running user command"
			::= { sleGponProfileDbaControl 3 }


--   1.3.6.1.4.1.6296.101.23.5.3.2.4
-- 1.3.6.1.4.1.6296.101.23.5.3.2.4
		sleGponProfileDbaControlTimeStamp OBJECT-TYPE
			SYNTAX TimeTicks
			MAX-ACCESS read-only
			STATUS current
			DESCRIPTION
				"The time stamp of the last command(end of command)"
			::= { sleGponProfileDbaControl 4 }


--   1.3.6.1.4.1.6296.101.23.5.3.2.5
-- 1.3.6.1.4.1.6296.101.23.5.3.2.5
		sleGponProfileDbaControlReqResult OBJECT-TYPE
			SYNTAX SleControlRequestResultType
			MAX-ACCESS read-only
			STATUS current
			DESCRIPTION
				"The result of the last user command"
			::= { sleGponProfileDbaControl 5 }


--   1.3.6.1.4.1.6296.101.23.5.3.2.6
-- 1.3.6.1.4.1.6296.101.23.5.3.2.6
		sleGponProfileDbaControlId OBJECT-TYPE
			SYNTAX INTEGER (1..65535)
			MAX-ACCESS read-write
			STATUS current
			DESCRIPTION
				"DBA profile Index"
			::= { sleGponProfileDbaControl 6 }


--   1.3.6.1.4.1.6296.101.23.5.3.2.7
-- 1.3.6.1.4.1.6296.101.23.5.3.2.7
		sleGponProfileDbaControlName OBJECT-TYPE
			SYNTAX OCTET STRING
			MAX-ACCESS read-write
			STATUS current
			DESCRIPTION
				"DBA Profile Name"
			::= { sleGponProfileDbaControl 7 }


--   1.3.6.1.4.1.6296.101.23.5.3.2.8
-- 1.3.6.1.4.1.6296.101.23.5.3.2.8
		sleGponProfileDbaControlMode OBJECT-TYPE
			SYNTAX INTEGER
				{
				fixed(1),
				sr(2),
				nsr(3),
				unknown(255)
				}
			MAX-ACCESS read-write
			STATUS current
			DESCRIPTION
				"DBA mode"
			::= { sleGponProfileDbaControl 8 }


--   1.3.6.1.4.1.6296.101.23.5.3.2.9
-- 1.3.6.1.4.1.6296.101.23.5.3.2.9
		sleGponProfileDbaControlSlaFixedBw OBJECT-TYPE
			SYNTAX Integer32
			UNITS "64 kbps"
			MAX-ACCESS read-write
			STATUS current
			DESCRIPTION
				"128-1031616, unit : 64kbps"
			::= { sleGponProfileDbaControl 9 }


--   1.3.6.1.4.1.6296.101.23.5.3.2.10
-- 1.3.6.1.4.1.6296.101.23.5.3.2.10
		sleGponProfileDbaControlSlaAssuredBw OBJECT-TYPE
			SYNTAX Integer32
			UNITS "64 kbps"
			MAX-ACCESS read-write
			STATUS current
			DESCRIPTION
				"0-1031616, unit : 64kbps"
			::= { sleGponProfileDbaControl 10 }


--   1.3.6.1.4.1.6296.101.23.5.3.2.11
-- 1.3.6.1.4.1.6296.101.23.5.3.2.11
		sleGponProfileDbaControlSlaMaxBw OBJECT-TYPE
			SYNTAX Integer32
			UNITS "64 kbps"
			MAX-ACCESS read-write
			STATUS current
			DESCRIPTION
				"128-1031616, unit : 64kbps"
			::= { sleGponProfileDbaControl 11 }


--   1.3.6.1.4.1.6296.101.23.5.3.3
-- 1.3.6.1.4.1.6296.101.23.5.3.3
		sleGponProfileDbaNotification OBJECT IDENTIFIER ::= { sleGponProfileDba 3 }


--   1.3.6.1.4.1.6296.101.23.5.3.3.1
-- 1.3.6.1.4.1.6296.101.23.5.3.3.1
		sleGponProfileDbaCreated NOTIFICATION-TYPE
			OBJECTS { sleGponProfileDbaControlRequest, sleGponProfileDbaControlTimeStamp, sleGponProfileDbaControlReqResult, sleGponProfileDbaControlName, sleGponProfileDbaControlMode,
				sleGponProfileDbaControlSlaFixedBw, sleGponProfileDbaControlSlaAssuredBw, sleGponProfileDbaControlSlaMaxBw }
			STATUS current
			DESCRIPTION
				"Description."
			::= { sleGponProfileDbaNotification 1 }


--   1.3.6.1.4.1.6296.101.23.5.3.3.2
-- 1.3.6.1.4.1.6296.101.23.5.3.3.2
		sleGponProfileDbaDestroyed NOTIFICATION-TYPE
			OBJECTS { sleGponProfileDbaControlRequest, sleGponProfileDbaControlTimeStamp, sleGponProfileDbaControlReqResult, sleGponProfileDbaControlId, sleGponProfileDbaControlName
				 }
			STATUS current
			DESCRIPTION
				"Description."
			::= { sleGponProfileDbaNotification 2 }


--   1.3.6.1.4.1.6296.101.23.5.3.3.3
-- 1.3.6.1.4.1.6296.101.23.5.3.3.3
		sleGponProfileDbaChanged NOTIFICATION-TYPE
			OBJECTS { sleGponProfileDbaControlRequest, sleGponProfileDbaControlTimeStamp, sleGponProfileDbaControlReqResult, sleGponProfileDbaControlId, sleGponProfileDbaControlMode,
				sleGponProfileDbaControlSlaFixedBw, sleGponProfileDbaControlSlaAssuredBw, sleGponProfileDbaControlSlaMaxBw }
			STATUS current
			DESCRIPTION
				"Description."
			::= { sleGponProfileDbaNotification 3 }


--   1.3.6.1.4.1.6296.101.23.5.4
-- 1.3.6.1.4.1.6296.101.23.5.4
		sleGponProfileMultiTcont OBJECT IDENTIFIER ::= { sleGponProfile 4 }


--   1.3.6.1.4.1.6296.101.23.5.4.1
-- 1.3.6.1.4.1.6296.101.23.5.4.1
		sleGponProfileMultiTcontTable OBJECT-TYPE
			SYNTAX SEQUENCE OF SleGponProfileMultiTcontEntry
			MAX-ACCESS not-accessible
			STATUS current
			DESCRIPTION
				"sleGponProfileMultiTcontTable"
			::= { sleGponProfileMultiTcont 1 }


--   1.3.6.1.4.1.6296.101.23.5.4.1.1
-- 1.3.6.1.4.1.6296.101.23.5.4.1.1
		sleGponProfileMultiTcontEntry OBJECT-TYPE
			SYNTAX SleGponProfileMultiTcontEntry
			MAX-ACCESS not-accessible
			STATUS current
			DESCRIPTION
				"key: sleGponProfileMultiTcontIndex"
			INDEX { sleGponProfileMultiTcontIndex }
			::= { sleGponProfileMultiTcontTable 1 }


		SleGponProfileMultiTcontEntry ::=
			SEQUENCE {
				sleGponProfileMultiTcontIndex
					Integer32,
				sleGponProfileMultiTcontName
					OCTET STRING,
				sleGponProfileMultiTconTDscp2Pbit
					INTEGER,
				sleGponProfileMultiTconTPriQWeightCnt
					INTEGER,
				sleGponProfileMultiTconTPriQWeight
					OCTET STRING,
				sleGponProfileMultiTcontGemPortType
					INTEGER,
				sleGponProfileMultiTcontGemportUniPortList
					BITS,
				sleGponProfileMultiTcontGemPortVlanCnt
					INTEGER,
				sleGponProfileMultiTcontGemPortVlanList
					OCTET STRING,
				sleGponProfileMultiTcontGemPortCount
					Integer32,
				sleGponProfileMultiTcontGemPortDbaProfileName1
					OCTET STRING,
				sleGponProfileMultiTcontGemPortDbaProfileMask1
					BITS,
				sleGponProfileMultiTcontGemPortDbaProfileName2
					OCTET STRING,
				sleGponProfileMultiTcontGemPortDbaProfileMask2
					BITS,
				sleGponProfileMultiTcontGemPortDbaProfileName3
					OCTET STRING,
				sleGponProfileMultiTcontGemPortDbaProfileMask3
					BITS,
				sleGponProfileMultiTcontGemPortDbaProfileName4
					OCTET STRING,
				sleGponProfileMultiTcontGemPortDbaProfileMask4
					BITS,
				sleGponProfileMultiTcontGemPortDbaProfileName5
					OCTET STRING,
				sleGponProfileMultiTcontGemPortDbaProfileMask5
					BITS,
				sleGponProfileMultiTcontGemPortDbaProfileName6
					OCTET STRING,
				sleGponProfileMultiTcontGemPortDbaProfileMask6
					BITS,
				sleGponProfileMultiTcontGemPortDbaProfileName7
					OCTET STRING,
				sleGponProfileMultiTcontGemPortDbaProfileMask7
					BITS,
				sleGponProfileMultiTcontGemPortDbaProfileName8
					OCTET STRING,
				sleGponProfileMultiTcontGemPortDbaProfileMask8
					BITS
			 }

--   1.3.6.1.4.1.6296.101.23.5.4.1.1.1
-- 1.3.6.1.4.1.6296.101.23.5.4.1.1.1
		sleGponProfileMultiTcontIndex OBJECT-TYPE
			SYNTAX Integer32 (1..65535)
			MAX-ACCESS read-only
			STATUS current
			DESCRIPTION
				"MultiTconT Profile Id"
			::= { sleGponProfileMultiTcontEntry 1 }


--   1.3.6.1.4.1.6296.101.23.5.4.1.1.2
-- 1.3.6.1.4.1.6296.101.23.5.4.1.1.2
		sleGponProfileMultiTcontName OBJECT-TYPE
			SYNTAX OCTET STRING
			MAX-ACCESS read-only
			STATUS current
			DESCRIPTION
				"MultiTconT Profile Name"
			::= { sleGponProfileMultiTcontEntry 2 }


--   1.3.6.1.4.1.6296.101.23.5.4.1.1.3
-- 1.3.6.1.4.1.6296.101.23.5.4.1.1.3
		sleGponProfileMultiTconTDscp2Pbit OBJECT-TYPE
			SYNTAX INTEGER
				{
				enable(1),
				disable(2),
				unknown(255)
				}
			MAX-ACCESS read-only
			STATUS current
			DESCRIPTION
				"Multi-Tcont DSCP2Pbit."
			::= { sleGponProfileMultiTcontEntry 3 }


--   1.3.6.1.4.1.6296.101.23.5.4.1.1.4
-- 1.3.6.1.4.1.6296.101.23.5.4.1.1.4
		sleGponProfileMultiTconTPriQWeightCnt OBJECT-TYPE
			SYNTAX INTEGER (1..65535)
			MAX-ACCESS read-only
			STATUS current
			DESCRIPTION
				"Priority Q & Weight mapping count"
			::= { sleGponProfileMultiTcontEntry 4 }


--   1.3.6.1.4.1.6296.101.23.5.4.1.1.5
-- 1.3.6.1.4.1.6296.101.23.5.4.1.1.5
		sleGponProfileMultiTconTPriQWeight OBJECT-TYPE
			SYNTAX OCTET STRING
			MAX-ACCESS read-only
			STATUS current
			DESCRIPTION
				"Priority Q & Weight MAP
				2bytes per each Q-ID,
				Example)
				queue-weight 1-2,5 63 / queue-weight 8 22
				 -->  # 003f 003f 0000 0000 003f 0000 0000 0016"
			::= { sleGponProfileMultiTcontEntry 5 }


--   1.3.6.1.4.1.6296.101.23.5.4.1.1.6
-- 1.3.6.1.4.1.6296.101.23.5.4.1.1.6
		sleGponProfileMultiTcontGemPortType OBJECT-TYPE
			SYNTAX INTEGER
				{
				eth(1),
				voip(2),
				unknown(255)
				}
			MAX-ACCESS read-only
			STATUS current
			DESCRIPTION
				"Multi Tcon Gem port type"
			::= { sleGponProfileMultiTcontEntry 6 }


--   1.3.6.1.4.1.6296.101.23.5.4.1.1.7
-- 1.3.6.1.4.1.6296.101.23.5.4.1.1.7
		sleGponProfileMultiTcontGemportUniPortList OBJECT-TYPE
			SYNTAX BITS
				{
				uni1(0),
				uni2(1),
				uni3(2),
				uni4(3),
				uni5(4),
				uni6(5),
				uni7(6),
				uni8(7)
				}
			MAX-ACCESS read-only
			STATUS current
			DESCRIPTION
				"Multi Tcon Gem port Uni port list"
			::= { sleGponProfileMultiTcontEntry 7 }


--   1.3.6.1.4.1.6296.101.23.5.4.1.1.8
-- 1.3.6.1.4.1.6296.101.23.5.4.1.1.8
		sleGponProfileMultiTcontGemPortVlanCnt OBJECT-TYPE
			SYNTAX INTEGER (1..65535)
			MAX-ACCESS read-only
			STATUS current
			DESCRIPTION
				"VLAN ID counter"
			::= { sleGponProfileMultiTcontEntry 8 }


--   1.3.6.1.4.1.6296.101.23.5.4.1.1.9
-- 1.3.6.1.4.1.6296.101.23.5.4.1.1.9
		sleGponProfileMultiTcontGemPortVlanList OBJECT-TYPE
			SYNTAX OCTET STRING
			MAX-ACCESS read-only
			STATUS current
			DESCRIPTION
				"bitmap, Vlan ID List,  2 bytes per each VLAN.
				Exampel)
				gemport eth 1 vid 1-8,10 count 1
				 -->  # 0001 0002 0003 0004 0005 0006 0007 0008 000a"
			::= { sleGponProfileMultiTcontEntry 9 }


--   1.3.6.1.4.1.6296.101.23.5.4.1.1.10
-- 1.3.6.1.4.1.6296.101.23.5.4.1.1.10
		sleGponProfileMultiTcontGemPortCount OBJECT-TYPE
			SYNTAX Integer32
			MAX-ACCESS read-only
			STATUS current
			DESCRIPTION
				"Gem port count"
			::= { sleGponProfileMultiTcontEntry 10 }


--   1.3.6.1.4.1.6296.101.23.5.4.1.1.11
-- 1.3.6.1.4.1.6296.101.23.5.4.1.1.11
		sleGponProfileMultiTcontGemPortDbaProfileName1 OBJECT-TYPE
			SYNTAX OCTET STRING
			MAX-ACCESS read-only
			STATUS current
			DESCRIPTION
				"Dba Profile name"
			::= { sleGponProfileMultiTcontEntry 11 }


--   1.3.6.1.4.1.6296.101.23.5.4.1.1.12
-- 1.3.6.1.4.1.6296.101.23.5.4.1.1.12
		sleGponProfileMultiTcontGemPortDbaProfileMask1 OBJECT-TYPE
			SYNTAX BITS
				{
				port1(0),
				port2(1),
				port3(2),
				port4(3),
				port5(4),
				port6(5),
				port7(6),
				port8(7)
				}
			MAX-ACCESS read-only
			STATUS current
			DESCRIPTION
				"Dba Profile Mask (gemport List)"
			::= { sleGponProfileMultiTcontEntry 12 }


--   1.3.6.1.4.1.6296.101.23.5.4.1.1.13
-- 1.3.6.1.4.1.6296.101.23.5.4.1.1.13
		sleGponProfileMultiTcontGemPortDbaProfileName2 OBJECT-TYPE
			SYNTAX OCTET STRING
			MAX-ACCESS read-only
			STATUS current
			DESCRIPTION
				"Multi-Tcont Gemport DBA profile Mask"
			::= { sleGponProfileMultiTcontEntry 13 }


--   1.3.6.1.4.1.6296.101.23.5.4.1.1.14
-- 1.3.6.1.4.1.6296.101.23.5.4.1.1.14
		sleGponProfileMultiTcontGemPortDbaProfileMask2 OBJECT-TYPE
			SYNTAX BITS
				{
				port1(0),
				port2(1),
				port3(2),
				port4(3),
				port5(4),
				port6(5),
				port7(6),
				port8(7)
				}
			MAX-ACCESS read-only
			STATUS current
			DESCRIPTION
				"Dba Profile Mask (gemport List)"
			::= { sleGponProfileMultiTcontEntry 14 }


--   1.3.6.1.4.1.6296.101.23.5.4.1.1.15
-- 1.3.6.1.4.1.6296.101.23.5.4.1.1.15
		sleGponProfileMultiTcontGemPortDbaProfileName3 OBJECT-TYPE
			SYNTAX OCTET STRING
			MAX-ACCESS read-only
			STATUS current
			DESCRIPTION
				"Dba Profile name"
			::= { sleGponProfileMultiTcontEntry 15 }


--   1.3.6.1.4.1.6296.101.23.5.4.1.1.16
-- 1.3.6.1.4.1.6296.101.23.5.4.1.1.16
		sleGponProfileMultiTcontGemPortDbaProfileMask3 OBJECT-TYPE
			SYNTAX BITS
				{
				port1(0),
				port2(1),
				port3(2),
				port4(3),
				port5(4),
				port6(5),
				port7(6),
				port8(7)
				}
			MAX-ACCESS read-only
			STATUS current
			DESCRIPTION
				"Dba Profile Mask (gemport List)"
			::= { sleGponProfileMultiTcontEntry 16 }


--   1.3.6.1.4.1.6296.101.23.5.4.1.1.17
-- 1.3.6.1.4.1.6296.101.23.5.4.1.1.17
		sleGponProfileMultiTcontGemPortDbaProfileName4 OBJECT-TYPE
			SYNTAX OCTET STRING
			MAX-ACCESS read-only
			STATUS current
			DESCRIPTION
				"Dba Profile name"
			::= { sleGponProfileMultiTcontEntry 17 }


--   1.3.6.1.4.1.6296.101.23.5.4.1.1.18
-- 1.3.6.1.4.1.6296.101.23.5.4.1.1.18
		sleGponProfileMultiTcontGemPortDbaProfileMask4 OBJECT-TYPE
			SYNTAX BITS
				{
				port1(0),
				port2(1),
				port3(2),
				port4(3),
				port5(4),
				port6(5),
				port7(6),
				port8(7)
				}
			MAX-ACCESS read-only
			STATUS current
			DESCRIPTION
				"Dba Profile Mask (gemport List)"
			::= { sleGponProfileMultiTcontEntry 18 }


--   1.3.6.1.4.1.6296.101.23.5.4.1.1.19
-- 1.3.6.1.4.1.6296.101.23.5.4.1.1.19
		sleGponProfileMultiTcontGemPortDbaProfileName5 OBJECT-TYPE
			SYNTAX OCTET STRING
			MAX-ACCESS read-only
			STATUS current
			DESCRIPTION
				"Dba Profile name"
			::= { sleGponProfileMultiTcontEntry 19 }


--   1.3.6.1.4.1.6296.101.23.5.4.1.1.20
-- 1.3.6.1.4.1.6296.101.23.5.4.1.1.20
		sleGponProfileMultiTcontGemPortDbaProfileMask5 OBJECT-TYPE
			SYNTAX BITS
				{
				port1(0),
				port2(1),
				port3(2),
				port4(3),
				port5(4),
				port6(5),
				port7(6),
				port8(7)
				}
			MAX-ACCESS read-only
			STATUS current
			DESCRIPTION
				"Dba Profile Mask (gemport List)"
			::= { sleGponProfileMultiTcontEntry 20 }


--   1.3.6.1.4.1.6296.101.23.5.4.1.1.21
-- 1.3.6.1.4.1.6296.101.23.5.4.1.1.21
		sleGponProfileMultiTcontGemPortDbaProfileName6 OBJECT-TYPE
			SYNTAX OCTET STRING
			MAX-ACCESS read-only
			STATUS current
			DESCRIPTION
				"Dba Profile name"
			::= { sleGponProfileMultiTcontEntry 21 }


--   1.3.6.1.4.1.6296.101.23.5.4.1.1.22
-- 1.3.6.1.4.1.6296.101.23.5.4.1.1.22
		sleGponProfileMultiTcontGemPortDbaProfileMask6 OBJECT-TYPE
			SYNTAX BITS
				{
				port1(0),
				port2(1),
				port3(2),
				port4(3),
				port5(4),
				port6(5),
				port7(6),
				port8(7)
				}
			MAX-ACCESS read-only
			STATUS current
			DESCRIPTION
				"Dba Profile Mask (gemport List)"
			::= { sleGponProfileMultiTcontEntry 22 }


--   1.3.6.1.4.1.6296.101.23.5.4.1.1.23
-- 1.3.6.1.4.1.6296.101.23.5.4.1.1.23
		sleGponProfileMultiTcontGemPortDbaProfileName7 OBJECT-TYPE
			SYNTAX OCTET STRING
			MAX-ACCESS read-only
			STATUS current
			DESCRIPTION
				"Dba Profile name"
			::= { sleGponProfileMultiTcontEntry 23 }


--   1.3.6.1.4.1.6296.101.23.5.4.1.1.24
-- 1.3.6.1.4.1.6296.101.23.5.4.1.1.24
		sleGponProfileMultiTcontGemPortDbaProfileMask7 OBJECT-TYPE
			SYNTAX BITS
				{
				port1(0),
				port2(1),
				port3(2),
				port4(3),
				port5(4),
				port6(5),
				port7(6),
				port8(7)
				}
			MAX-ACCESS read-only
			STATUS current
			DESCRIPTION
				"Dba Profile Mask (gemport List)"
			::= { sleGponProfileMultiTcontEntry 24 }


--   1.3.6.1.4.1.6296.101.23.5.4.1.1.25
-- 1.3.6.1.4.1.6296.101.23.5.4.1.1.25
		sleGponProfileMultiTcontGemPortDbaProfileName8 OBJECT-TYPE
			SYNTAX OCTET STRING
			MAX-ACCESS read-only
			STATUS current
			DESCRIPTION
				"Dba Profile name"
			::= { sleGponProfileMultiTcontEntry 25 }


--   1.3.6.1.4.1.6296.101.23.5.4.1.1.26
-- 1.3.6.1.4.1.6296.101.23.5.4.1.1.26
		sleGponProfileMultiTcontGemPortDbaProfileMask8 OBJECT-TYPE
			SYNTAX BITS
				{
				port1(0),
				port2(1),
				port3(2),
				port4(3),
				port5(4),
				port6(5),
				port7(6),
				port8(7)
				}
			MAX-ACCESS read-only
			STATUS current
			DESCRIPTION
				"Dba Profile Mask (gemport List)"
			::= { sleGponProfileMultiTcontEntry 26 }


--   1.3.6.1.4.1.6296.101.23.5.4.2
-- 1.3.6.1.4.1.6296.101.23.5.4.2
		sleGponProfileMultiTcontControl OBJECT IDENTIFIER ::= { sleGponProfileMultiTcont 2 }


--   1.3.6.1.4.1.6296.101.23.5.4.2.1
-- 1.3.6.1.4.1.6296.101.23.5.4.2.1
		sleGponProfileMultiTcontControllRequest OBJECT-TYPE
			SYNTAX INTEGER
				{
				createProfile(1),
				destroyProfile(2),
				updateDscp2Pbit(3),
				updatePriQWeight(4),
				updateGemport(5)
				}
			MAX-ACCESS read-write
			STATUS current
			DESCRIPTION
				"The request of a user command"
			::= { sleGponProfileMultiTcontControl 1 }


--   1.3.6.1.4.1.6296.101.23.5.4.2.2
-- 1.3.6.1.4.1.6296.101.23.5.4.2.2
		sleGponProfileMultiTcontControlStatus OBJECT-TYPE
			SYNTAX SleControlStatusType
			MAX-ACCESS read-only
			STATUS current
			DESCRIPTION
				"The status of user command"
			::= { sleGponProfileMultiTcontControl 2 }


--   1.3.6.1.4.1.6296.101.23.5.4.2.3
-- 1.3.6.1.4.1.6296.101.23.5.4.2.3
		sleGponProfileMultiTcontControlTimer OBJECT-TYPE
			SYNTAX Gauge32
			MAX-ACCESS read-write
			STATUS current
			DESCRIPTION
				"The maximum time for the manager for a long running user command"
			::= { sleGponProfileMultiTcontControl 3 }


--   1.3.6.1.4.1.6296.101.23.5.4.2.4
-- 1.3.6.1.4.1.6296.101.23.5.4.2.4
		sleGponProfileMultiTcontControlTimeStamp OBJECT-TYPE
			SYNTAX TimeTicks
			MAX-ACCESS read-only
			STATUS current
			DESCRIPTION
				"The time stamp of the last command(end of command)"
			::= { sleGponProfileMultiTcontControl 4 }


--   1.3.6.1.4.1.6296.101.23.5.4.2.5
-- 1.3.6.1.4.1.6296.101.23.5.4.2.5
		sleGponProfileMultiTcontControlReqResult OBJECT-TYPE
			SYNTAX SleControlRequestResultType
			MAX-ACCESS read-only
			STATUS current
			DESCRIPTION
				"The result of the last user command"
			::= { sleGponProfileMultiTcontControl 5 }


--   1.3.6.1.4.1.6296.101.23.5.4.2.6
-- 1.3.6.1.4.1.6296.101.23.5.4.2.6
		sleGponProfileMultiTcontControlIndex OBJECT-TYPE
			SYNTAX INTEGER (1..65535)
			MAX-ACCESS read-write
			STATUS current
			DESCRIPTION
				"Multi Tcont profile Index"
			::= { sleGponProfileMultiTcontControl 6 }


--   1.3.6.1.4.1.6296.101.23.5.4.2.7
-- 1.3.6.1.4.1.6296.101.23.5.4.2.7
		sleGponProfileMultiTcontControlName OBJECT-TYPE
			SYNTAX OCTET STRING
			MAX-ACCESS read-write
			STATUS current
			DESCRIPTION
				"Profile Name"
			::= { sleGponProfileMultiTcontControl 7 }


--   1.3.6.1.4.1.6296.101.23.5.4.2.8
-- 1.3.6.1.4.1.6296.101.23.5.4.2.8
		sleGponProfileMultiTcontControlDscp2Pbit OBJECT-TYPE
			SYNTAX INTEGER
				{
				enable(1),
				disable(2),
				unknown(255)
				}
			MAX-ACCESS read-write
			STATUS current
			DESCRIPTION
				"DSCP to P bit marking"
			::= { sleGponProfileMultiTcontControl 8 }


--   1.3.6.1.4.1.6296.101.23.5.4.2.9
-- 1.3.6.1.4.1.6296.101.23.5.4.2.9
		sleGponProfileMultiTcontControlPriQWeightCnt OBJECT-TYPE
			SYNTAX Integer32
			MAX-ACCESS read-write
			STATUS current
			DESCRIPTION
				"TconT PrioQ mapping count"
			::= { sleGponProfileMultiTcontControl 9 }


--   1.3.6.1.4.1.6296.101.23.5.4.2.10
-- 1.3.6.1.4.1.6296.101.23.5.4.2.10
		sleGponProfileMultiTcontControlPriQWeight OBJECT-TYPE
			SYNTAX OCTET STRING
			MAX-ACCESS read-write
			STATUS current
			DESCRIPTION
				"Tcont PriQ weight MAP."
			::= { sleGponProfileMultiTcontControl 10 }


--   1.3.6.1.4.1.6296.101.23.5.4.2.11
-- 1.3.6.1.4.1.6296.101.23.5.4.2.11
		sleGponProfileMultiTcontControlGemPortType OBJECT-TYPE
			SYNTAX INTEGER
				{
				eth(1),
				voip(2),
				unknown(255)
				}
			MAX-ACCESS read-write
			STATUS current
			DESCRIPTION
				"Multi Tcon Gem port type"
			::= { sleGponProfileMultiTcontControl 11 }


--   1.3.6.1.4.1.6296.101.23.5.4.2.12
-- 1.3.6.1.4.1.6296.101.23.5.4.2.12
		sleGponProfileMultiTcontControlGemportUniPortList OBJECT-TYPE
			SYNTAX BITS
				{
				uni1(0),
				uni2(1),
				uni3(2),
				uni4(3),
				uni5(4),
				uni6(5),
				uni7(6),
				uni8(7)
				}
			MAX-ACCESS read-write
			STATUS current
			DESCRIPTION
				"Multi Tcon Gem port Uni port list"
			::= { sleGponProfileMultiTcontControl 12 }


--   1.3.6.1.4.1.6296.101.23.5.4.2.13
-- 1.3.6.1.4.1.6296.101.23.5.4.2.13
		sleGponProfileMultiTcontControlGemPortVlanCnt OBJECT-TYPE
			SYNTAX Integer32
			MAX-ACCESS read-write
			STATUS current
			DESCRIPTION
				"VLAN list mappling  count"
			::= { sleGponProfileMultiTcontControl 13 }


--   1.3.6.1.4.1.6296.101.23.5.4.2.14
-- 1.3.6.1.4.1.6296.101.23.5.4.2.14
		sleGponProfileMultiTcontControlGemPortVlanList OBJECT-TYPE
			SYNTAX OCTET STRING
			MAX-ACCESS read-write
			STATUS current
			DESCRIPTION
				"VLAN MAP."
			::= { sleGponProfileMultiTcontControl 14 }


--   1.3.6.1.4.1.6296.101.23.5.4.2.15
-- 1.3.6.1.4.1.6296.101.23.5.4.2.15
		sleGponProfileMultiTcontControlGemPortCount OBJECT-TYPE
			SYNTAX Integer32
			MAX-ACCESS read-write
			STATUS current
			DESCRIPTION
				"Gemport count"
			::= { sleGponProfileMultiTcontControl 15 }


--   1.3.6.1.4.1.6296.101.23.5.4.2.16
-- 1.3.6.1.4.1.6296.101.23.5.4.2.16
		sleGponProfileMultiTcontControlGemPortDbaProfileName1 OBJECT-TYPE
			SYNTAX OCTET STRING
			MAX-ACCESS read-write
			STATUS current
			DESCRIPTION
				"Dba Profile name"
			::= { sleGponProfileMultiTcontControl 16 }


--   1.3.6.1.4.1.6296.101.23.5.4.2.17
-- 1.3.6.1.4.1.6296.101.23.5.4.2.17
		sleGponProfileMultiTcontControlGemPortDbaProfileMask1 OBJECT-TYPE
			SYNTAX BITS
				{
				port1(0),
				port2(1),
				port3(2),
				port4(3),
				port5(4),
				port6(5),
				port7(6),
				port8(7)
				}
			MAX-ACCESS read-write
			STATUS current
			DESCRIPTION
				"Dba Profile Mask (gemport List)"
			::= { sleGponProfileMultiTcontControl 17 }


--   1.3.6.1.4.1.6296.101.23.5.4.2.18
-- 1.3.6.1.4.1.6296.101.23.5.4.2.18
		sleGponProfileMultiTcontControlGemPortDbaProfileName2 OBJECT-TYPE
			SYNTAX OCTET STRING
			MAX-ACCESS read-write
			STATUS current
			DESCRIPTION
				"Dba Profile name"
			::= { sleGponProfileMultiTcontControl 18 }


--   1.3.6.1.4.1.6296.101.23.5.4.2.19
-- 1.3.6.1.4.1.6296.101.23.5.4.2.19
		sleGponProfileMultiTcontControlGemPortDbaProfileMask2 OBJECT-TYPE
			SYNTAX BITS
				{
				port1(0),
				port2(1),
				port3(2),
				port4(3),
				port5(4),
				port6(5),
				port7(6),
				port8(7)
				}
			MAX-ACCESS read-write
			STATUS current
			DESCRIPTION
				"Dba Profile Mask (gemport List)"
			::= { sleGponProfileMultiTcontControl 19 }


--   1.3.6.1.4.1.6296.101.23.5.4.2.20
-- 1.3.6.1.4.1.6296.101.23.5.4.2.20
		sleGponProfileMultiTcontControlGemPortDbaProfileName3 OBJECT-TYPE
			SYNTAX OCTET STRING
			MAX-ACCESS read-write
			STATUS current
			DESCRIPTION
				"Dba Profile name"
			::= { sleGponProfileMultiTcontControl 20 }


--   1.3.6.1.4.1.6296.101.23.5.4.2.21
-- 1.3.6.1.4.1.6296.101.23.5.4.2.21
		sleGponProfileMultiTcontControlGemPortDbaProfileMask3 OBJECT-TYPE
			SYNTAX BITS
				{
				port1(0),
				port2(1),
				port3(2),
				port4(3),
				port5(4),
				port6(5),
				port7(6),
				port8(7)
				}
			MAX-ACCESS read-write
			STATUS current
			DESCRIPTION
				"Dba Profile Mask (gemport List)"
			::= { sleGponProfileMultiTcontControl 21 }


--   1.3.6.1.4.1.6296.101.23.5.4.2.22
-- 1.3.6.1.4.1.6296.101.23.5.4.2.22
		sleGponProfileMultiTcontControlGemPortDbaProfileName4 OBJECT-TYPE
			SYNTAX OCTET STRING
			MAX-ACCESS read-write
			STATUS current
			DESCRIPTION
				"Dba Profile name"
			::= { sleGponProfileMultiTcontControl 22 }


--   1.3.6.1.4.1.6296.101.23.5.4.2.23
-- 1.3.6.1.4.1.6296.101.23.5.4.2.23
		sleGponProfileMultiTcontControlGemPortDbaProfileMask4 OBJECT-TYPE
			SYNTAX BITS
				{
				port1(0),
				port2(1),
				port3(2),
				port4(3),
				port5(4),
				port6(5),
				port7(6),
				port8(7)
				}
			MAX-ACCESS read-write
			STATUS current
			DESCRIPTION
				"Dba Profile Mask (gemport List)"
			::= { sleGponProfileMultiTcontControl 23 }


--   1.3.6.1.4.1.6296.101.23.5.4.2.24
-- 1.3.6.1.4.1.6296.101.23.5.4.2.24
		sleGponProfileMultiTcontControlGemPortDbaProfileName5 OBJECT-TYPE
			SYNTAX OCTET STRING
			MAX-ACCESS read-write
			STATUS current
			DESCRIPTION
				"Dba Profile name"
			::= { sleGponProfileMultiTcontControl 24 }


--   1.3.6.1.4.1.6296.101.23.5.4.2.25
-- 1.3.6.1.4.1.6296.101.23.5.4.2.25
		sleGponProfileMultiTcontControlGemPortDbaProfileMask5 OBJECT-TYPE
			SYNTAX BITS
				{
				port1(0),
				port2(1),
				port3(2),
				port4(3),
				port5(4),
				port6(5),
				port7(6),
				port8(7)
				}
			MAX-ACCESS read-write
			STATUS current
			DESCRIPTION
				"Dba Profile Mask (gemport List)"
			::= { sleGponProfileMultiTcontControl 25 }


--   1.3.6.1.4.1.6296.101.23.5.4.2.26
-- 1.3.6.1.4.1.6296.101.23.5.4.2.26
		sleGponProfileMultiTcontControlGemPortDbaProfileName6 OBJECT-TYPE
			SYNTAX OCTET STRING
			MAX-ACCESS read-write
			STATUS current
			DESCRIPTION
				"Dba Profile name"
			::= { sleGponProfileMultiTcontControl 26 }


--   1.3.6.1.4.1.6296.101.23.5.4.2.27
-- 1.3.6.1.4.1.6296.101.23.5.4.2.27
		sleGponProfileMultiTcontControlGemPortDbaProfileMask6 OBJECT-TYPE
			SYNTAX BITS
				{
				port1(0),
				port2(1),
				port3(2),
				port4(3),
				port5(4),
				port6(5),
				port7(6),
				port8(7)
				}
			MAX-ACCESS read-write
			STATUS current
			DESCRIPTION
				"Dba Profile Mask (gemport List)"
			::= { sleGponProfileMultiTcontControl 27 }


--   1.3.6.1.4.1.6296.101.23.5.4.2.28
-- 1.3.6.1.4.1.6296.101.23.5.4.2.28
		sleGponProfileMultiTcontControlGemPortDbaProfileName7 OBJECT-TYPE
			SYNTAX OCTET STRING
			MAX-ACCESS read-write
			STATUS current
			DESCRIPTION
				"Dba Profile name"
			::= { sleGponProfileMultiTcontControl 28 }


--   1.3.6.1.4.1.6296.101.23.5.4.2.29
-- 1.3.6.1.4.1.6296.101.23.5.4.2.29
		sleGponProfileMultiTcontControlGemPortDbaProfileMask7 OBJECT-TYPE
			SYNTAX BITS
				{
				port1(0),
				port2(1),
				port3(2),
				port4(3),
				port5(4),
				port6(5),
				port7(6),
				port8(7)
				}
			MAX-ACCESS read-write
			STATUS current
			DESCRIPTION
				"Dba Profile Mask (gemport List)"
			::= { sleGponProfileMultiTcontControl 29 }


--   1.3.6.1.4.1.6296.101.23.5.4.2.30
-- 1.3.6.1.4.1.6296.101.23.5.4.2.30
		sleGponProfileMultiTcontControlGemPortDbaProfileName8 OBJECT-TYPE
			SYNTAX OCTET STRING
			MAX-ACCESS read-write
			STATUS current
			DESCRIPTION
				"Dba Profile name"
			::= { sleGponProfileMultiTcontControl 30 }


--   1.3.6.1.4.1.6296.101.23.5.4.2.31
-- 1.3.6.1.4.1.6296.101.23.5.4.2.31
		sleGponProfileMultiTcontControlGemPortDbaProfileMask8 OBJECT-TYPE
			SYNTAX BITS
				{
				port1(0),
				port2(1),
				port3(2),
				port4(3),
				port5(4),
				port6(5),
				port7(6),
				port8(7)
				}
			MAX-ACCESS read-write
			STATUS current
			DESCRIPTION
				"Dba Profile Mask (gemport List)"
			::= { sleGponProfileMultiTcontControl 31 }


--   1.3.6.1.4.1.6296.101.23.5.4.3
-- 1.3.6.1.4.1.6296.101.23.5.4.3
		sleGponProfileMultiTcontNotification OBJECT IDENTIFIER ::= { sleGponProfileMultiTcont 3 }


--   1.3.6.1.4.1.6296.101.23.5.4.3.1
-- 1.3.6.1.4.1.6296.101.23.5.4.3.1
		sleGponProfileMultiTcontProfileCreated NOTIFICATION-TYPE
			OBJECTS { sleGponProfileMultiTcontControllRequest, sleGponProfileMultiTcontControlTimeStamp, sleGponProfileMultiTcontControlReqResult, sleGponProfileMultiTcontControlName, sleGponProfileMultiTcontControlDscp2Pbit,
				sleGponProfileMultiTcontControlPriQWeightCnt, sleGponProfileMultiTcontControlPriQWeight, sleGponProfileMultiTcontControlGemPortType, sleGponProfileMultiTcontControlGemportUniPortList, sleGponProfileMultiTcontControlGemPortVlanCnt,
				sleGponProfileMultiTcontControlGemPortVlanList, sleGponProfileMultiTcontControlGemPortCount, sleGponProfileMultiTcontControlGemPortDbaProfileName1, sleGponProfileMultiTcontControlGemPortDbaProfileMask1, sleGponProfileMultiTcontControlGemPortDbaProfileName2,
				sleGponProfileMultiTcontControlGemPortDbaProfileMask2, sleGponProfileMultiTcontControlGemPortDbaProfileName3, sleGponProfileMultiTcontControlGemPortDbaProfileMask3, sleGponProfileMultiTcontControlGemPortDbaProfileName4, sleGponProfileMultiTcontControlGemPortDbaProfileMask4,
				sleGponProfileMultiTcontControlGemPortDbaProfileName5, sleGponProfileMultiTcontControlGemPortDbaProfileMask5, sleGponProfileMultiTcontControlGemPortDbaProfileName6, sleGponProfileMultiTcontControlGemPortDbaProfileMask6, sleGponProfileMultiTcontControlGemPortDbaProfileName7,
				sleGponProfileMultiTcontControlGemPortDbaProfileMask7, sleGponProfileMultiTcontControlGemPortDbaProfileName8, sleGponProfileMultiTcontControlGemPortDbaProfileMask8 }
			STATUS current
			DESCRIPTION
				"Description."
			::= { sleGponProfileMultiTcontNotification 1 }


--   1.3.6.1.4.1.6296.101.23.5.4.3.2
-- 1.3.6.1.4.1.6296.101.23.5.4.3.2
		sleGponProfileMultiTcontProfileDestroyed NOTIFICATION-TYPE
			OBJECTS { sleGponProfileMultiTcontControllRequest, sleGponProfileMultiTcontControlTimeStamp, sleGponProfileMultiTcontControlReqResult, sleGponProfileMultiTcontControlIndex }
			STATUS current
			DESCRIPTION
				"Description."
			::= { sleGponProfileMultiTcontNotification 2 }


--   1.3.6.1.4.1.6296.101.23.5.4.3.3
-- 1.3.6.1.4.1.6296.101.23.5.4.3.3
		sleGponProfileMultiTcontProfileDscp2PbitChanged NOTIFICATION-TYPE
			OBJECTS { sleGponProfileMultiTcontControllRequest, sleGponProfileMultiTcontControlTimeStamp, sleGponProfileMultiTcontControlReqResult, sleGponProfileMultiTcontControlIndex, sleGponProfileMultiTcontControlDscp2Pbit
				 }
			STATUS current
			DESCRIPTION
				"Description."
			::= { sleGponProfileMultiTcontNotification 3 }


--   1.3.6.1.4.1.6296.101.23.5.4.3.4
-- 1.3.6.1.4.1.6296.101.23.5.4.3.4
		sleGponProfileMultiTcontProfilePriQWeightChanged NOTIFICATION-TYPE
			OBJECTS { sleGponProfileMultiTcontControllRequest, sleGponProfileMultiTcontControlTimeStamp, sleGponProfileMultiTcontControlReqResult, sleGponProfileMultiTcontControlIndex, sleGponProfileMultiTcontControlPriQWeightCnt,
				sleGponProfileMultiTcontControlPriQWeight }
			STATUS current
			DESCRIPTION
				"Description."
			::= { sleGponProfileMultiTcontNotification 4 }


--   1.3.6.1.4.1.6296.101.23.5.4.3.5
-- 1.3.6.1.4.1.6296.101.23.5.4.3.5
		sleGponProfileMultiTcontProfileGemportChanged NOTIFICATION-TYPE
			OBJECTS { sleGponProfileMultiTcontControllRequest, sleGponProfileMultiTcontControlTimeStamp, sleGponProfileMultiTcontControlReqResult, sleGponProfileMultiTcontControlIndex, sleGponProfileMultiTcontControlGemPortType,
				sleGponProfileMultiTcontControlGemportUniPortList, sleGponProfileMultiTcontControlGemPortVlanCnt, sleGponProfileMultiTcontControlGemPortVlanList, sleGponProfileMultiTcontControlGemPortCount, sleGponProfileMultiTcontControlGemPortDbaProfileName1,
				sleGponProfileMultiTcontControlGemPortDbaProfileMask1, sleGponProfileMultiTcontControlGemPortDbaProfileName2, sleGponProfileMultiTcontControlGemPortDbaProfileMask2, sleGponProfileMultiTcontControlGemPortDbaProfileName3, sleGponProfileMultiTcontControlGemPortDbaProfileMask3,
				sleGponProfileMultiTcontControlGemPortDbaProfileName4, sleGponProfileMultiTcontControlGemPortDbaProfileMask4, sleGponProfileMultiTcontControlGemPortDbaProfileName5, sleGponProfileMultiTcontControlGemPortDbaProfileMask5, sleGponProfileMultiTcontControlGemPortDbaProfileName6,
				sleGponProfileMultiTcontControlGemPortDbaProfileMask6, sleGponProfileMultiTcontControlGemPortDbaProfileName7, sleGponProfileMultiTcontControlGemPortDbaProfileMask7, sleGponProfileMultiTcontControlGemPortDbaProfileName8, sleGponProfileMultiTcontControlGemPortDbaProfileMask8
				 }
			STATUS current
			DESCRIPTION
				"Description."
			::= { sleGponProfileMultiTcontNotification 5 }


--   1.3.6.1.4.1.6296.101.23.5.5
-- 1.3.6.1.4.1.6296.101.23.5.5
		sleGponVoIP OBJECT IDENTIFIER ::= { sleGponProfile 5 }


--   1.3.6.1.4.1.6296.101.23.5.5.1
-- 1.3.6.1.4.1.6296.101.23.5.5.1
		sleGponProfileVoIP OBJECT IDENTIFIER ::= { sleGponVoIP 1 }


--   1.3.6.1.4.1.6296.101.23.5.5.1.1
-- 1.3.6.1.4.1.6296.101.23.5.5.1.1
		sleGponProfileVoIPTable OBJECT-TYPE
			SYNTAX SEQUENCE OF SleGponProfileVoIPEntry
			MAX-ACCESS not-accessible
			STATUS current
			DESCRIPTION
				"sleGponProfileVoIPTable"
			::= { sleGponProfileVoIP 1 }


--   1.3.6.1.4.1.6296.101.23.5.5.1.1.1
-- 1.3.6.1.4.1.6296.101.23.5.5.1.1.1
		sleGponProfileVoIPEntry OBJECT-TYPE
			SYNTAX SleGponProfileVoIPEntry
			MAX-ACCESS not-accessible
			STATUS current
			DESCRIPTION
				"sleGponProfileVoIPIndex"
			INDEX { sleGponProfileVoIPIndex }
			::= { sleGponProfileVoIPTable 1 }


		SleGponProfileVoIPEntry ::=
			SEQUENCE {
				sleGponProfileVoIPIndex
					Integer32,
				sleGponProfileVoIPName
					OCTET STRING,
				sleGponProfileVoIPServiceMode
					INTEGER,
				sleGponProfileVoIPServiceProtocol
					INTEGER,
				sleGponProfileVoIPOmciAgentURL
					OCTET STRING,
				sleGponProfileVoIPOmciAgentProxy
					OCTET STRING,
				sleGponProfileVoIPOmciAgentDns1
					IpAddress,
				sleGponProfileVoIPOmciAgentDns2
					IpAddress,
				sleGponProfileVoIPIpwayAuthName
					OCTET STRING,
				sleGponProfileVoIPIpwayAuthPasswd
					OCTET STRING,
				sleGponProfileVoIPIpwayURL
					OCTET STRING
			 }

--   1.3.6.1.4.1.6296.101.23.5.5.1.1.1.1
-- 1.3.6.1.4.1.6296.101.23.5.5.1.1.1.1
		sleGponProfileVoIPIndex OBJECT-TYPE
			SYNTAX Integer32 (1..65535)
			MAX-ACCESS read-only
			STATUS current
			DESCRIPTION
				"VoIP Profile Index."
			::= { sleGponProfileVoIPEntry 1 }


--   1.3.6.1.4.1.6296.101.23.5.5.1.1.1.2
-- 1.3.6.1.4.1.6296.101.23.5.5.1.1.1.2
		sleGponProfileVoIPName OBJECT-TYPE
			SYNTAX OCTET STRING
			MAX-ACCESS read-only
			STATUS current
			DESCRIPTION
				"VoIP profile name."
			::= { sleGponProfileVoIPEntry 2 }


--   1.3.6.1.4.1.6296.101.23.5.5.1.1.1.3
-- 1.3.6.1.4.1.6296.101.23.5.5.1.1.1.3
		sleGponProfileVoIPServiceMode OBJECT-TYPE
			SYNTAX INTEGER
				{
				ipPath(1),
				omci(2),
				unknown(3)
				}
			MAX-ACCESS read-only
			STATUS current
			DESCRIPTION
				"VoIP service mode."
			::= { sleGponProfileVoIPEntry 3 }


--   1.3.6.1.4.1.6296.101.23.5.5.1.1.1.4
-- 1.3.6.1.4.1.6296.101.23.5.5.1.1.1.4
		sleGponProfileVoIPServiceProtocol OBJECT-TYPE
			SYNTAX INTEGER
				{
				h248(1),
				mgcp(2),
				sip(3),
				unknown(4)
				}
			MAX-ACCESS read-only
			STATUS current
			DESCRIPTION
				"VoIP service Protocol."
			::= { sleGponProfileVoIPEntry 4 }


--   1.3.6.1.4.1.6296.101.23.5.5.1.1.1.5
-- 1.3.6.1.4.1.6296.101.23.5.5.1.1.1.5
		sleGponProfileVoIPOmciAgentURL OBJECT-TYPE
			SYNTAX OCTET STRING
			MAX-ACCESS read-only
			STATUS current
			DESCRIPTION
				"OMCI agent URL."
			::= { sleGponProfileVoIPEntry 5 }


--   1.3.6.1.4.1.6296.101.23.5.5.1.1.1.6
-- 1.3.6.1.4.1.6296.101.23.5.5.1.1.1.6
		sleGponProfileVoIPOmciAgentProxy OBJECT-TYPE
			SYNTAX OCTET STRING
			MAX-ACCESS read-only
			STATUS current
			DESCRIPTION
				"OMCI agent proxy."
			::= { sleGponProfileVoIPEntry 6 }


--   1.3.6.1.4.1.6296.101.23.5.5.1.1.1.7
-- 1.3.6.1.4.1.6296.101.23.5.5.1.1.1.7
		sleGponProfileVoIPOmciAgentDns1 OBJECT-TYPE
			SYNTAX IpAddress
			MAX-ACCESS read-only
			STATUS current
			DESCRIPTION
				"OCMI agent DNS primary"
			::= { sleGponProfileVoIPEntry 7 }


--   1.3.6.1.4.1.6296.101.23.5.5.1.1.1.8
-- 1.3.6.1.4.1.6296.101.23.5.5.1.1.1.8
		sleGponProfileVoIPOmciAgentDns2 OBJECT-TYPE
			SYNTAX IpAddress
			MAX-ACCESS read-only
			STATUS current
			DESCRIPTION
				"OMCI agent DNS secondary"
			::= { sleGponProfileVoIPEntry 8 }


--   1.3.6.1.4.1.6296.101.23.5.5.1.1.1.9
-- 1.3.6.1.4.1.6296.101.23.5.5.1.1.1.9
		sleGponProfileVoIPIpwayAuthName OBJECT-TYPE
			SYNTAX OCTET STRING
			MAX-ACCESS read-only
			STATUS current
			DESCRIPTION
				"IP PATH AUTH name"
			::= { sleGponProfileVoIPEntry 9 }


--   1.3.6.1.4.1.6296.101.23.5.5.1.1.1.10
-- 1.3.6.1.4.1.6296.101.23.5.5.1.1.1.10
		sleGponProfileVoIPIpwayAuthPasswd OBJECT-TYPE
			SYNTAX OCTET STRING
			MAX-ACCESS read-only
			STATUS current
			DESCRIPTION
				"IP PATH AUTH Password(UnUsed)"
			::= { sleGponProfileVoIPEntry 10 }


--   1.3.6.1.4.1.6296.101.23.5.5.1.1.1.11
-- 1.3.6.1.4.1.6296.101.23.5.5.1.1.1.11
		sleGponProfileVoIPIpwayURL OBJECT-TYPE
			SYNTAX OCTET STRING
			MAX-ACCESS read-only
			STATUS current
			DESCRIPTION
				"IP PATH AUTH URL"
			::= { sleGponProfileVoIPEntry 11 }


--   1.3.6.1.4.1.6296.101.23.5.5.1.2
-- 1.3.6.1.4.1.6296.101.23.5.5.1.2
		sleGponProfileVoIPControl OBJECT IDENTIFIER ::= { sleGponProfileVoIP 2 }


--   1.3.6.1.4.1.6296.101.23.5.5.1.2.1
-- 1.3.6.1.4.1.6296.101.23.5.5.1.2.1
		sleGponProfileVoIPControlRequest OBJECT-TYPE
			SYNTAX INTEGER
				{
				createProfile(1),
				destroyProfile(2),
				updateService(3),
				updateOmci(4),
				updateIpWay(5)
				}
			MAX-ACCESS read-write
			STATUS current
			DESCRIPTION
				"The request of a user command"
			::= { sleGponProfileVoIPControl 1 }


--   1.3.6.1.4.1.6296.101.23.5.5.1.2.2
-- 1.3.6.1.4.1.6296.101.23.5.5.1.2.2
		sleGponProfileVoIPControlStatus OBJECT-TYPE
			SYNTAX SleControlStatusType
			MAX-ACCESS read-only
			STATUS current
			DESCRIPTION
				"The status of user command"
			::= { sleGponProfileVoIPControl 2 }


--   1.3.6.1.4.1.6296.101.23.5.5.1.2.3
-- 1.3.6.1.4.1.6296.101.23.5.5.1.2.3
		sleGponProfileVoIPControlTimer OBJECT-TYPE
			SYNTAX Gauge32
			MAX-ACCESS read-write
			STATUS current
			DESCRIPTION
				"The maximum time for the manager for a long running user command"
			::= { sleGponProfileVoIPControl 3 }


--   1.3.6.1.4.1.6296.101.23.5.5.1.2.4
-- 1.3.6.1.4.1.6296.101.23.5.5.1.2.4
		sleGponProfileVoIPControlTimeStamp OBJECT-TYPE
			SYNTAX TimeTicks
			MAX-ACCESS read-only
			STATUS current
			DESCRIPTION
				"The time stamp of the last command(end of command)"
			::= { sleGponProfileVoIPControl 4 }


--   1.3.6.1.4.1.6296.101.23.5.5.1.2.5
-- 1.3.6.1.4.1.6296.101.23.5.5.1.2.5
		sleGponProfileVoIPControlReqResult OBJECT-TYPE
			SYNTAX SleControlRequestResultType
			MAX-ACCESS read-only
			STATUS current
			DESCRIPTION
				"The result of the last user command"
			::= { sleGponProfileVoIPControl 5 }


--   1.3.6.1.4.1.6296.101.23.5.5.1.2.6
-- 1.3.6.1.4.1.6296.101.23.5.5.1.2.6
		sleGponProfileVoIPControlIndex OBJECT-TYPE
			SYNTAX INTEGER (1..65535)
			MAX-ACCESS read-write
			STATUS current
			DESCRIPTION
				"Multi Tcont profile Index"
			::= { sleGponProfileVoIPControl 6 }


--   1.3.6.1.4.1.6296.101.23.5.5.1.2.7
-- 1.3.6.1.4.1.6296.101.23.5.5.1.2.7
		sleGponProfileVoIPControlName OBJECT-TYPE
			SYNTAX OCTET STRING
			MAX-ACCESS read-write
			STATUS current
			DESCRIPTION
				"Profile Name"
			::= { sleGponProfileVoIPControl 7 }


--   1.3.6.1.4.1.6296.101.23.5.5.1.2.8
-- 1.3.6.1.4.1.6296.101.23.5.5.1.2.8
		sleGponProfileVoIPControlServiceMode OBJECT-TYPE
			SYNTAX INTEGER
				{
				ipPath(1),
				omci(2),
				unknown(3)
				}
			MAX-ACCESS read-write
			STATUS current
			DESCRIPTION
				"VoIP service mode"
			::= { sleGponProfileVoIPControl 8 }


--   1.3.6.1.4.1.6296.101.23.5.5.1.2.9
-- 1.3.6.1.4.1.6296.101.23.5.5.1.2.9
		sleGponProfileVoIPControlServiceProtocol OBJECT-TYPE
			SYNTAX INTEGER
				{
				h248(1),
				mgcp(2),
				sip(3),
				unknown(4)
				}
			MAX-ACCESS read-write
			STATUS current
			DESCRIPTION
				"VoIP service Protocol."
			::= { sleGponProfileVoIPControl 9 }


--   1.3.6.1.4.1.6296.101.23.5.5.1.2.10
-- 1.3.6.1.4.1.6296.101.23.5.5.1.2.10
		sleGponProfileVoIPControlOmciAgentURL OBJECT-TYPE
			SYNTAX OCTET STRING
			MAX-ACCESS read-write
			STATUS current
			DESCRIPTION
				"OMCI agent URL."
			::= { sleGponProfileVoIPControl 10 }


--   1.3.6.1.4.1.6296.101.23.5.5.1.2.11
-- 1.3.6.1.4.1.6296.101.23.5.5.1.2.11
		sleGponProfileVoIPControlOmciAgentProxy OBJECT-TYPE
			SYNTAX OCTET STRING
			MAX-ACCESS read-write
			STATUS current
			DESCRIPTION
				"OMCI agent proxy."
			::= { sleGponProfileVoIPControl 11 }


--   1.3.6.1.4.1.6296.101.23.5.5.1.2.12
-- 1.3.6.1.4.1.6296.101.23.5.5.1.2.12
		sleGponProfileVoIPControlOmciAgentDns1 OBJECT-TYPE
			SYNTAX IpAddress
			MAX-ACCESS read-write
			STATUS current
			DESCRIPTION
				"OCMI agent DNS primary"
			::= { sleGponProfileVoIPControl 12 }


--   1.3.6.1.4.1.6296.101.23.5.5.1.2.13
-- 1.3.6.1.4.1.6296.101.23.5.5.1.2.13
		sleGponProfileVoIPControlOmciAgentDns2 OBJECT-TYPE
			SYNTAX IpAddress
			MAX-ACCESS read-write
			STATUS current
			DESCRIPTION
				"OMCI agent DNS secondary"
			::= { sleGponProfileVoIPControl 13 }


--   1.3.6.1.4.1.6296.101.23.5.5.1.2.14
-- 1.3.6.1.4.1.6296.101.23.5.5.1.2.14
		sleGponProfileVoIPControlIpwayAuthName OBJECT-TYPE
			SYNTAX OCTET STRING
			MAX-ACCESS read-write
			STATUS current
			DESCRIPTION
				"IP PATH AUTH name"
			::= { sleGponProfileVoIPControl 14 }


--   1.3.6.1.4.1.6296.101.23.5.5.1.2.15
-- 1.3.6.1.4.1.6296.101.23.5.5.1.2.15
		sleGponProfileVoIPControlIpwayAuthPasswd OBJECT-TYPE
			SYNTAX OCTET STRING
			MAX-ACCESS read-write
			STATUS current
			DESCRIPTION
				"IP PATH AUTH Password(UnUsed)"
			::= { sleGponProfileVoIPControl 15 }


--   1.3.6.1.4.1.6296.101.23.5.5.1.2.16
-- 1.3.6.1.4.1.6296.101.23.5.5.1.2.16
		sleGponProfileVoIPControlIpwayURL OBJECT-TYPE
			SYNTAX OCTET STRING
			MAX-ACCESS read-write
			STATUS current
			DESCRIPTION
				"IP PATH AUTH URL"
			::= { sleGponProfileVoIPControl 16 }


--   1.3.6.1.4.1.6296.101.23.5.5.1.3
-- 1.3.6.1.4.1.6296.101.23.5.5.1.3
		sleGponProfileVoIPNotification OBJECT IDENTIFIER ::= { sleGponProfileVoIP 3 }


--   1.3.6.1.4.1.6296.101.23.5.5.1.3.1
-- 1.3.6.1.4.1.6296.101.23.5.5.1.3.1
		sleGponProfileVoIPProfileCreated NOTIFICATION-TYPE
			OBJECTS { sleGponProfileVoIPControlRequest, sleGponProfileVoIPControlTimeStamp, sleGponProfileVoIPControlReqResult, sleGponProfileVoIPControlName }
			STATUS current
			DESCRIPTION
				"Description."
			::= { sleGponProfileVoIPNotification 1 }


--   1.3.6.1.4.1.6296.101.23.5.5.1.3.2
-- 1.3.6.1.4.1.6296.101.23.5.5.1.3.2
		sleGponProfileVoIPProfileDestroyed NOTIFICATION-TYPE
			OBJECTS { sleGponProfileVoIPControlRequest, sleGponProfileVoIPControlTimeStamp, sleGponProfileVoIPControlReqResult, sleGponProfileVoIPControlIndex }
			STATUS current
			DESCRIPTION
				"Description."
			::= { sleGponProfileVoIPNotification 2 }


--   1.3.6.1.4.1.6296.101.23.5.5.1.3.3
-- 1.3.6.1.4.1.6296.101.23.5.5.1.3.3
		sleGponProfilVoIPProfileServiceChanged NOTIFICATION-TYPE
			OBJECTS { sleGponProfileVoIPControlRequest, sleGponProfileVoIPControlTimeStamp, sleGponProfileVoIPControlReqResult, sleGponProfileVoIPControlIndex, sleGponProfileVoIPControlServiceMode,
				sleGponProfileVoIPControlServiceProtocol }
			STATUS current
			DESCRIPTION
				"Description."
			::= { sleGponProfileVoIPNotification 3 }


--   1.3.6.1.4.1.6296.101.23.5.5.1.3.4
-- 1.3.6.1.4.1.6296.101.23.5.5.1.3.4
		sleGponProfileVoIPProfileOmciChanged NOTIFICATION-TYPE
			OBJECTS { sleGponProfileVoIPControlRequest, sleGponProfileVoIPControlTimeStamp, sleGponProfileVoIPControlReqResult, sleGponProfileVoIPControlIndex, sleGponProfileVoIPControlOmciAgentURL,
				sleGponProfileVoIPControlOmciAgentProxy, sleGponProfileVoIPControlOmciAgentDns1, sleGponProfileVoIPControlOmciAgentDns2 }
			STATUS current
			DESCRIPTION
				"Description."
			::= { sleGponProfileVoIPNotification 4 }


--   1.3.6.1.4.1.6296.101.23.5.5.1.3.5
-- 1.3.6.1.4.1.6296.101.23.5.5.1.3.5
		sleGponProfileVoIPProfileIpwayChanged NOTIFICATION-TYPE
			OBJECTS { sleGponProfileVoIPControlRequest, sleGponProfileVoIPControlTimer, sleGponProfileVoIPControlReqResult, sleGponProfileVoIPControlIndex, sleGponProfileVoIPControlIpwayAuthName,
				sleGponProfileVoIPControlIpwayAuthPasswd, sleGponProfileVoIPControlIpwayURL }
			STATUS current
			DESCRIPTION
				"Description."
			::= { sleGponProfileVoIPNotification 5 }


--   1.3.6.1.4.1.6296.101.23.5.5.2
-- 1.3.6.1.4.1.6296.101.23.5.5.2
		sleGponProfileVoIPOmci OBJECT IDENTIFIER ::= { sleGponVoIP 2 }


--   1.3.6.1.4.1.6296.101.23.5.5.2.1
-- 1.3.6.1.4.1.6296.101.23.5.5.2.1
		sleGponProfileVoIPOmciTable OBJECT-TYPE
			SYNTAX SEQUENCE OF SleGponProfileVoIPOmciEntry
			MAX-ACCESS not-accessible
			STATUS current
			DESCRIPTION
				"sleGponProfileVoIPOmciTable"
			::= { sleGponProfileVoIPOmci 1 }


--   1.3.6.1.4.1.6296.101.23.5.5.2.1.1
-- 1.3.6.1.4.1.6296.101.23.5.5.2.1.1
		sleGponProfileVoIPOmciEntry OBJECT-TYPE
			SYNTAX SleGponProfileVoIPOmciEntry
			MAX-ACCESS not-accessible
			STATUS current
			DESCRIPTION
				"key: sleGponOltId, sleGponOnuId, sleGponProfileVoIPOmciUniPortId"
			INDEX { sleGponOltId, sleGponOnuId, sleGponProfileVoIPOmciUniPortId }
			::= { sleGponProfileVoIPOmciTable 1 }


		SleGponProfileVoIPOmciEntry ::=
			SEQUENCE {
				sleGponProfileVoIPOmciUniPortId
					Integer32,
				sleGponProfileVoIPOmciAuthName
					OCTET STRING,
				sleGponProfileVoIPOmciAuthPasswd
					OCTET STRING,
				sleGponProfileVoIPOmciPhoneNumber
					OCTET STRING,
				sleGponProfileVoIPOmciDisplay
					OCTET STRING,
				sleGponProfileVoIPOmciMgcTerminationId
					OCTET STRING
			 }

--   1.3.6.1.4.1.6296.101.23.5.5.2.1.1.1
-- 1.3.6.1.4.1.6296.101.23.5.5.2.1.1.1
		sleGponProfileVoIPOmciUniPortId OBJECT-TYPE
			SYNTAX Integer32 (1..65535)
			MAX-ACCESS read-only
			STATUS current
			DESCRIPTION
				"OMCI UNI port Id"
			::= { sleGponProfileVoIPOmciEntry 1 }


--   1.3.6.1.4.1.6296.101.23.5.5.2.1.1.2
-- 1.3.6.1.4.1.6296.101.23.5.5.2.1.1.2
		sleGponProfileVoIPOmciAuthName OBJECT-TYPE
			SYNTAX OCTET STRING
			MAX-ACCESS read-only
			STATUS current
			DESCRIPTION
				"OMCI AUTH name"
			::= { sleGponProfileVoIPOmciEntry 2 }


--   1.3.6.1.4.1.6296.101.23.5.5.2.1.1.3
-- 1.3.6.1.4.1.6296.101.23.5.5.2.1.1.3
		sleGponProfileVoIPOmciAuthPasswd OBJECT-TYPE
			SYNTAX OCTET STRING
			MAX-ACCESS read-only
			STATUS current
			DESCRIPTION
				"OMCI AUTH Password"
			::= { sleGponProfileVoIPOmciEntry 3 }


--   1.3.6.1.4.1.6296.101.23.5.5.2.1.1.4
-- 1.3.6.1.4.1.6296.101.23.5.5.2.1.1.4
		sleGponProfileVoIPOmciPhoneNumber OBJECT-TYPE
			SYNTAX OCTET STRING
			MAX-ACCESS read-only
			STATUS current
			DESCRIPTION
				"OMCI Phone number"
			::= { sleGponProfileVoIPOmciEntry 4 }


--   1.3.6.1.4.1.6296.101.23.5.5.2.1.1.5
-- 1.3.6.1.4.1.6296.101.23.5.5.2.1.1.5
		sleGponProfileVoIPOmciDisplay OBJECT-TYPE
			SYNTAX OCTET STRING
			MAX-ACCESS read-only
			STATUS current
			DESCRIPTION
				"OMCI Phone Display"
			::= { sleGponProfileVoIPOmciEntry 5 }


--   1.3.6.1.4.1.6296.101.23.5.5.2.1.1.5
-- 1.3.6.1.4.1.6296.101.23.5.5.2.1.1.6
		sleGponProfileVoIPOmciMgcTerminationId OBJECT-TYPE
			SYNTAX OCTET STRING
			MAX-ACCESS read-only
			STATUS current
			DESCRIPTION
				"The MGC termination ID"
			::= { sleGponProfileVoIPOmciEntry 6 }


--   1.3.6.1.4.1.6296.101.23.5.5.2.2
-- 1.3.6.1.4.1.6296.101.23.5.5.2.2
		sleGponProfileVoIPOmciControl OBJECT IDENTIFIER ::= { sleGponProfileVoIPOmci 2 }


--   1.3.6.1.4.1.6296.101.23.5.5.2.2.1
-- 1.3.6.1.4.1.6296.101.23.5.5.2.2.1
		sleGponProfileVoIPOmciControlRequest OBJECT-TYPE
			SYNTAX INTEGER
				{
				setSIPAuth(1),
				setSIPPhone(2),
				setMGCTermination(3)
				}
			MAX-ACCESS read-write
			STATUS current
			DESCRIPTION
				"The request of a user command"
			::= { sleGponProfileVoIPOmciControl 1 }


--   1.3.6.1.4.1.6296.101.23.5.5.2.2.2
-- 1.3.6.1.4.1.6296.101.23.5.5.2.2.2
		sleGponProfileVoIPOmciControlStatus OBJECT-TYPE
			SYNTAX SleControlStatusType
			MAX-ACCESS read-only
			STATUS current
			DESCRIPTION
				"The status of user command"
			::= { sleGponProfileVoIPOmciControl 2 }


--   1.3.6.1.4.1.6296.101.23.5.5.2.2.3
-- 1.3.6.1.4.1.6296.101.23.5.5.2.2.3
		sleGponProfileVoIPOmciControlTimer OBJECT-TYPE
			SYNTAX Gauge32
			MAX-ACCESS read-write
			STATUS current
			DESCRIPTION
				"The maximum time for the manager for a long running user command"
			::= { sleGponProfileVoIPOmciControl 3 }


--   1.3.6.1.4.1.6296.101.23.5.5.2.2.4
-- 1.3.6.1.4.1.6296.101.23.5.5.2.2.4
		sleGponProfileVoIPOmciControlTimeStamp OBJECT-TYPE
			SYNTAX TimeTicks
			MAX-ACCESS read-only
			STATUS current
			DESCRIPTION
				"The time stamp of the last command(end of command)"
			::= { sleGponProfileVoIPOmciControl 4 }


--   1.3.6.1.4.1.6296.101.23.5.5.2.2.5
-- 1.3.6.1.4.1.6296.101.23.5.5.2.2.5
		sleGponProfileVoIPOmciControlReqResult OBJECT-TYPE
			SYNTAX SleControlRequestResultType
			MAX-ACCESS read-only
			STATUS current
			DESCRIPTION
				"The result of the last user command"
			::= { sleGponProfileVoIPOmciControl 5 }


		sleGponProfileVoIPOmciControlOltIndex OBJECT-TYPE
			SYNTAX INTEGER (1..2147483647)
			MAX-ACCESS read-write
			STATUS current
			DESCRIPTION
				"OLT Index"
			::= { sleGponProfileVoIPOmciControl 6 }


--   1.3.6.1.4.1.6296.101.23.5.5.2.2.7
-- 1.3.6.1.4.1.6296.101.23.5.5.2.2.7
		sleGponProfileVoIPOmciControlOnuIndex OBJECT-TYPE
			SYNTAX INTEGER (1..65535)
			MAX-ACCESS read-write
			STATUS current
			DESCRIPTION
				"ONU Index"
			::= { sleGponProfileVoIPOmciControl 7 }


--   1.3.6.1.4.1.6296.101.23.5.5.2.2.8
-- 1.3.6.1.4.1.6296.101.23.5.5.2.2.8
		sleGponProfileVoIPOmciControlUniId OBJECT-TYPE
			SYNTAX INTEGER (1..65535)
			MAX-ACCESS read-write
			STATUS current
			DESCRIPTION
				"UNI port Index"
			::= { sleGponProfileVoIPOmciControl 8 }


--   1.3.6.1.4.1.6296.101.23.5.5.2.2.9
-- 1.3.6.1.4.1.6296.101.23.5.5.2.2.9
		sleGponProfileVoIPOmciControlAuthName OBJECT-TYPE
			SYNTAX OCTET STRING
			MAX-ACCESS read-write
			STATUS current
			DESCRIPTION
				"OMCI AUTH name"
			::= { sleGponProfileVoIPOmciControl 9 }


--   1.3.6.1.4.1.6296.101.23.5.5.2.2.10
-- 1.3.6.1.4.1.6296.101.23.5.5.2.2.10
		sleGponProfileVoIPOmciControlAuthPasswd OBJECT-TYPE
			SYNTAX OCTET STRING
			MAX-ACCESS read-write
			STATUS current
			DESCRIPTION
				"OMCI AUTH Password"
			::= { sleGponProfileVoIPOmciControl 10 }


--   1.3.6.1.4.1.6296.101.23.5.5.2.2.11
-- 1.3.6.1.4.1.6296.101.23.5.5.2.2.11
		sleGponProfileVoIPOmciControlPhoneNumber OBJECT-TYPE
			SYNTAX OCTET STRING
			MAX-ACCESS read-write
			STATUS current
			DESCRIPTION
				"OMCI Phone number"
			::= { sleGponProfileVoIPOmciControl 11 }


--   1.3.6.1.4.1.6296.101.23.5.5.2.2.12
-- 1.3.6.1.4.1.6296.101.23.5.5.2.2.12
		sleGponProfileVoIPOmciControlDisplay OBJECT-TYPE
			SYNTAX OCTET STRING
			MAX-ACCESS read-write
			STATUS current
			DESCRIPTION
				"OMCI Phone Display"
			::= { sleGponProfileVoIPOmciControl 12 }


--  1.3.6.1.4.1.6296.101.23.5.5.2.2.13
		sleGponProfileVoIPOmciControlMgcTerminationId OBJECT-TYPE
			SYNTAX OCTET STRING
			MAX-ACCESS read-write
			STATUS current
			DESCRIPTION
				"The MGC termination ID"
			::= { sleGponProfileVoIPOmciControl 13 }


--   1.3.6.1.4.1.6296.101.23.5.5.2.3
-- 1.3.6.1.4.1.6296.101.23.5.5.2.3
		sleGponProfileVoIPOmciNotification OBJECT IDENTIFIER ::= { sleGponProfileVoIPOmci 3 }


--   1.3.6.1.4.1.6296.101.23.5.5.2.3.1
-- 1.3.6.1.4.1.6296.101.23.5.5.2.3.1
		sleGponProfileVoIPOmciSIPAuthChanged NOTIFICATION-TYPE
			OBJECTS { sleGponProfileVoIPOmciControlRequest, sleGponProfileVoIPOmciControlTimeStamp, sleGponProfileVoIPOmciControlReqResult, sleGponProfileVoIPOmciControlOltIndex, sleGponProfileVoIPOmciControlOnuIndex,
				sleGponProfileVoIPOmciControlUniId, sleGponProfileVoIPOmciControlAuthName, sleGponProfileVoIPOmciControlAuthPasswd }
			STATUS current
			DESCRIPTION
				"Description."
			::= { sleGponProfileVoIPOmciNotification 1 }


--   1.3.6.1.4.1.6296.101.23.5.5.2.3.2
-- 1.3.6.1.4.1.6296.101.23.5.5.2.3.2
		sleGponProfileVoIPOmciSIPPhoneChnaged NOTIFICATION-TYPE
			OBJECTS { sleGponProfileVoIPOmciControlRequest, sleGponProfileVoIPOmciControlTimeStamp, sleGponProfileVoIPOmciControlReqResult, sleGponProfileVoIPOmciControlOltIndex, sleGponProfileVoIPOmciControlOnuIndex,
				sleGponProfileVoIPOmciControlUniId, sleGponProfileVoIPOmciControlPhoneNumber, sleGponProfileVoIPOmciControlDisplay }
			STATUS current
			DESCRIPTION
				"Description."
			::= { sleGponProfileVoIPOmciNotification 2 }


--   1.3.6.1.4.1.6296.101.23.5.5.2.3.1
-- 1.3.6.1.4.1.6296.101.23.5.5.2.3.3
		sleGponProfileVoIPOmciMGCTerminationChanged NOTIFICATION-TYPE
			OBJECTS { sleGponProfileVoIPOmciControlRequest, sleGponProfileVoIPOmciControlTimeStamp, sleGponProfileVoIPOmciControlReqResult, sleGponProfileVoIPOmciControlOltIndex, sleGponProfileVoIPOmciControlOnuIndex,
				sleGponProfileVoIPOmciControlUniId, sleGponProfileVoIPOmciControlMgcTerminationId }
			STATUS current
			DESCRIPTION
				"setMGCTermination"
			::= { sleGponProfileVoIPOmciNotification 3 }


--   1.3.6.1.4.1.6296.101.23.5.5.3
-- 1.3.6.1.4.1.6296.101.23.5.5.3
		sleGponProfileVoIPIpPath OBJECT IDENTIFIER ::= { sleGponVoIP 3 }


--   1.3.6.1.4.1.6296.101.23.5.5.3.1
-- 1.3.6.1.4.1.6296.101.23.5.5.3.1
		sleGponProfileVoIPIpPathTable OBJECT-TYPE
			SYNTAX SEQUENCE OF SleGponProfileVoIPIpPathEntry
			MAX-ACCESS not-accessible
			STATUS current
			DESCRIPTION
				"Description."
			::= { sleGponProfileVoIPIpPath 1 }


--   1.3.6.1.4.1.6296.101.23.5.5.3.1.1
-- 1.3.6.1.4.1.6296.101.23.5.5.3.1.1
		sleGponProfileVoIPIpPathEntry OBJECT-TYPE
			SYNTAX SleGponProfileVoIPIpPathEntry
			MAX-ACCESS not-accessible
			STATUS current
			DESCRIPTION
				"Description."
			INDEX { sleGponOltId, sleGponOnuId }
			::= { sleGponProfileVoIPIpPathTable 1 }


		SleGponProfileVoIPIpPathEntry ::=
			SEQUENCE {
				sleGponProfileVoIPIpPathAuthName
					OCTET STRING,
				sleGponProfileVoIPIpPathAuthPasswd
					OCTET STRING,
				sleGponProfileVoIPIpPathURL
					OCTET STRING
			 }

--   1.3.6.1.4.1.6296.101.23.5.5.3.1.1.1
-- 1.3.6.1.4.1.6296.101.23.5.5.3.1.1.1
		sleGponProfileVoIPIpPathAuthName OBJECT-TYPE
			SYNTAX OCTET STRING
			MAX-ACCESS read-only
			STATUS current
			DESCRIPTION
				"IP PATH AUTH name(UnUsed)"
			::= { sleGponProfileVoIPIpPathEntry 1 }


--   1.3.6.1.4.1.6296.101.23.5.5.3.1.1.2
-- 1.3.6.1.4.1.6296.101.23.5.5.3.1.1.2
		sleGponProfileVoIPIpPathAuthPasswd OBJECT-TYPE
			SYNTAX OCTET STRING
			MAX-ACCESS read-only
			STATUS current
			DESCRIPTION
				"IP PATH AUTH Password(UnUsed)"
			::= { sleGponProfileVoIPIpPathEntry 2 }


--   1.3.6.1.4.1.6296.101.23.5.5.3.1.1.3
-- 1.3.6.1.4.1.6296.101.23.5.5.3.1.1.3
		sleGponProfileVoIPIpPathURL OBJECT-TYPE
			SYNTAX OCTET STRING
			MAX-ACCESS read-only
			STATUS current
			DESCRIPTION
				"IP PATH AUTH URL(UnUsed)"
			::= { sleGponProfileVoIPIpPathEntry 3 }


--   1.3.6.1.4.1.6296.101.23.5.5.3.2
-- 1.3.6.1.4.1.6296.101.23.5.5.3.2
		sleGponProfileVoIPIpPathControl OBJECT IDENTIFIER ::= { sleGponProfileVoIPIpPath 2 }


--   1.3.6.1.4.1.6296.101.23.5.5.3.2.1
-- 1.3.6.1.4.1.6296.101.23.5.5.3.2.1
		sleGponProfileVoIPIpPathControlRequest OBJECT-TYPE
			SYNTAX INTEGER { setVoIPIPPathControlInfo(1) }
			MAX-ACCESS read-write
			STATUS current
			DESCRIPTION
				"The request of a user command"
			::= { sleGponProfileVoIPIpPathControl 1 }


--   1.3.6.1.4.1.6296.101.23.5.5.3.2.2
-- 1.3.6.1.4.1.6296.101.23.5.5.3.2.2
		sleGponProfileVoIPIpPathControlStatus OBJECT-TYPE
			SYNTAX SleControlStatusType
			MAX-ACCESS read-only
			STATUS current
			DESCRIPTION
				"The status of user command"
			::= { sleGponProfileVoIPIpPathControl 2 }


--   1.3.6.1.4.1.6296.101.23.5.5.3.2.3
-- 1.3.6.1.4.1.6296.101.23.5.5.3.2.3
		sleGponProfileVoIPIpPathControlTimer OBJECT-TYPE
			SYNTAX Gauge32
			MAX-ACCESS read-write
			STATUS current
			DESCRIPTION
				"The maximum time for the manager for a long running user command"
			::= { sleGponProfileVoIPIpPathControl 3 }


--   1.3.6.1.4.1.6296.101.23.5.5.3.2.4
-- 1.3.6.1.4.1.6296.101.23.5.5.3.2.4
		sleGponProfileVoIPIpPathControlTimeStamp OBJECT-TYPE
			SYNTAX TimeTicks
			MAX-ACCESS read-only
			STATUS current
			DESCRIPTION
				"The time stamp of the last command(end of command)"
			::= { sleGponProfileVoIPIpPathControl 4 }


--   1.3.6.1.4.1.6296.101.23.5.5.3.2.5
-- 1.3.6.1.4.1.6296.101.23.5.5.3.2.5
		sleGponProfileVoIPIpPathControlReqResult OBJECT-TYPE
			SYNTAX SleControlRequestResultType
			MAX-ACCESS read-only
			STATUS current
			DESCRIPTION
				"The result of the last user command"
			::= { sleGponProfileVoIPIpPathControl 5 }


		sleGponProfileVoIPIpPathControlOltIndex OBJECT-TYPE
			SYNTAX INTEGER (1..2147483647)
			MAX-ACCESS read-write
			STATUS current
			DESCRIPTION
				"OLT Index"
			::= { sleGponProfileVoIPIpPathControl 6 }


--   1.3.6.1.4.1.6296.101.23.5.5.3.2.7
-- 1.3.6.1.4.1.6296.101.23.5.5.3.2.7
		sleGponProfileVoIPIpPathControlOnuIndex OBJECT-TYPE
			SYNTAX INTEGER (1..65535)
			MAX-ACCESS read-write
			STATUS current
			DESCRIPTION
				"ONU Index"
			::= { sleGponProfileVoIPIpPathControl 7 }


--   1.3.6.1.4.1.6296.101.23.5.5.3.2.8
-- 1.3.6.1.4.1.6296.101.23.5.5.3.2.8
		sleGponProfileVoIPIpPathControlAuthName OBJECT-TYPE
			SYNTAX OCTET STRING
			MAX-ACCESS read-write
			STATUS current
			DESCRIPTION
				"IP PATH AUTH name"
			::= { sleGponProfileVoIPIpPathControl 8 }


--   1.3.6.1.4.1.6296.101.23.5.5.3.2.9
-- 1.3.6.1.4.1.6296.101.23.5.5.3.2.9
		sleGponProfileVoIPIpPathControlAuthPasswd OBJECT-TYPE
			SYNTAX OCTET STRING
			MAX-ACCESS read-write
			STATUS current
			DESCRIPTION
				"IP PATH AUTH Password"
			::= { sleGponProfileVoIPIpPathControl 9 }


--   1.3.6.1.4.1.6296.101.23.5.5.3.3
-- 1.3.6.1.4.1.6296.101.23.5.5.3.3
		sleGponProfileVoIPIpPathNotification OBJECT IDENTIFIER ::= { sleGponProfileVoIPIpPath 3 }


--   1.3.6.1.4.1.6296.101.23.5.5.3.3.1
-- 1.3.6.1.4.1.6296.101.23.5.5.3.3.1
		sleGponProfileVoIPIpPathInfoChanged NOTIFICATION-TYPE
			OBJECTS { sleGponProfileVoIPIpPathControlRequest, sleGponProfileVoIPIpPathControlTimeStamp, sleGponProfileVoIPIpPathControlReqResult, sleGponProfileVoIPIpPathControlOltIndex, sleGponProfileVoIPIpPathControlOnuIndex,
				sleGponProfileVoIPIpPathControlAuthName, sleGponProfileVoIPIpPathControlAuthPasswd }
			STATUS current
			DESCRIPTION
				"Description."
			::= { sleGponProfileVoIPIpPathNotification 1 }


--   1.3.6.1.4.1.6296.101.23.5.5.4
-- 1.3.6.1.4.1.6296.101.23.5.5.4
		sleGponProfileVoIPPots OBJECT IDENTIFIER ::= { sleGponVoIP 4 }


--   1.3.6.1.4.1.6296.101.23.5.5.4.1
-- 1.3.6.1.4.1.6296.101.23.5.5.4.1
		sleGponProfileVoIPPotsTable OBJECT-TYPE
			SYNTAX SEQUENCE OF SleGponProfileVoIPPotsEntry
			MAX-ACCESS not-accessible
			STATUS current
			DESCRIPTION
				"sleGponProfileVoIPPotsTable"
			::= { sleGponProfileVoIPPots 1 }


--   1.3.6.1.4.1.6296.101.23.5.5.4.1.1
-- 1.3.6.1.4.1.6296.101.23.5.5.4.1.1
		sleGponProfileVoIPPotsEntry OBJECT-TYPE
			SYNTAX SleGponProfileVoIPPotsEntry
			MAX-ACCESS not-accessible
			STATUS current
			DESCRIPTION
				"key: sleGponProfileVoIPPotsPIndex, sleGponProfileVoIPPotsIndex"
			INDEX { sleGponProfileVoIPPotsPIndex, sleGponProfileVoIPPotsIndex }
			::= { sleGponProfileVoIPPotsTable 1 }


		SleGponProfileVoIPPotsEntry ::=
			SEQUENCE {
				sleGponProfileVoIPPotsPIndex
					Integer32,
				sleGponProfileVoIPPotsIndex
					Integer32,
				sleGponProfileVoIPPotsAdmin
					EnableFlag
			 }

--   1.3.6.1.4.1.6296.101.23.5.5.4.1.1.1
-- 1.3.6.1.4.1.6296.101.23.5.5.4.1.1.1
		sleGponProfileVoIPPotsPIndex OBJECT-TYPE
			SYNTAX Integer32 (1..65535)
			MAX-ACCESS read-only
			STATUS current
			DESCRIPTION
				"VoIP Profile Index"
			::= { sleGponProfileVoIPPotsEntry 1 }


--   1.3.6.1.4.1.6296.101.23.5.5.4.1.1.2
-- 1.3.6.1.4.1.6296.101.23.5.5.4.1.1.2
		sleGponProfileVoIPPotsIndex OBJECT-TYPE
			SYNTAX Integer32 (1..65535)
			MAX-ACCESS read-only
			STATUS current
			DESCRIPTION
				"Pptp Pots Index"
			::= { sleGponProfileVoIPPotsEntry 2 }


--   1.3.6.1.4.1.6296.101.23.5.5.4.1.1.3
-- 1.3.6.1.4.1.6296.101.23.5.5.4.1.1.3
		sleGponProfileVoIPPotsAdmin OBJECT-TYPE
			SYNTAX EnableFlag
			MAX-ACCESS read-only
			STATUS current
			DESCRIPTION
				"State of ONU Pots Administratoration"
			::= { sleGponProfileVoIPPotsEntry 3 }


--   1.3.6.1.4.1.6296.101.23.5.5.4.2
-- 1.3.6.1.4.1.6296.101.23.5.5.4.2
		sleGponProfileVoIPPotsControl OBJECT IDENTIFIER ::= { sleGponProfileVoIPPots 2 }


--   1.3.6.1.4.1.6296.101.23.5.5.4.2.1
-- 1.3.6.1.4.1.6296.101.23.5.5.4.2.1
		sleGponProfileVoIPPotsControlRequest OBJECT-TYPE
			SYNTAX INTEGER
				{
				addPots(1),
				delPots(2)
				}
			MAX-ACCESS read-write
			STATUS current
			DESCRIPTION
				"The request of a user command"
			::= { sleGponProfileVoIPPotsControl 1 }


--   1.3.6.1.4.1.6296.101.23.5.5.4.2.2
-- 1.3.6.1.4.1.6296.101.23.5.5.4.2.2
		sleGponProfileVoIPPotsControlStatus OBJECT-TYPE
			SYNTAX SleControlStatusType
			MAX-ACCESS read-only
			STATUS current
			DESCRIPTION
				"The status of user command"
			::= { sleGponProfileVoIPPotsControl 2 }


--   1.3.6.1.4.1.6296.101.23.5.5.4.2.3
-- 1.3.6.1.4.1.6296.101.23.5.5.4.2.3
		sleGponProfileVoIPPotsControlTimer OBJECT-TYPE
			SYNTAX Gauge32
			MAX-ACCESS read-write
			STATUS current
			DESCRIPTION
				"The maximum time for the manager for a long running user command"
			::= { sleGponProfileVoIPPotsControl 3 }


--   1.3.6.1.4.1.6296.101.23.5.5.4.2.4
-- 1.3.6.1.4.1.6296.101.23.5.5.4.2.4
		sleGponProfileVoIPPotsControlTimeStamp OBJECT-TYPE
			SYNTAX TimeTicks
			MAX-ACCESS read-only
			STATUS current
			DESCRIPTION
				"The time stamp of the last command(end of command)"
			::= { sleGponProfileVoIPPotsControl 4 }


--   1.3.6.1.4.1.6296.101.23.5.5.4.2.5
-- 1.3.6.1.4.1.6296.101.23.5.5.4.2.5
		sleGponProfileVoIPPotsControlReqResult OBJECT-TYPE
			SYNTAX SleControlRequestResultType
			MAX-ACCESS read-only
			STATUS current
			DESCRIPTION
				"The result of the last user command"
			::= { sleGponProfileVoIPPotsControl 5 }


--   1.3.6.1.4.1.6296.101.23.5.5.4.2.6
-- 1.3.6.1.4.1.6296.101.23.5.5.4.2.6
		sleGponProfileVoIPPotsControlProfileIndex OBJECT-TYPE
			SYNTAX Integer32
			MAX-ACCESS read-write
			STATUS current
			DESCRIPTION
				"VoIP Profile Index"
			::= { sleGponProfileVoIPPotsControl 6 }


--   1.3.6.1.4.1.6296.101.23.5.5.4.2.7
-- 1.3.6.1.4.1.6296.101.23.5.5.4.2.7
		sleGponProfileVoIPPotsControlPotsIndex OBJECT-TYPE
			SYNTAX Integer32
			MAX-ACCESS read-write
			STATUS current
			DESCRIPTION
				"Pptp Pots Index"
			::= { sleGponProfileVoIPPotsControl 7 }


--   1.3.6.1.4.1.6296.101.23.5.5.4.2.8
-- 1.3.6.1.4.1.6296.101.23.5.5.4.2.8
		sleGponProfileVoIPPotsControlAdmin OBJECT-TYPE
			SYNTAX EnableFlag
			MAX-ACCESS read-write
			STATUS current
			DESCRIPTION
				"State of ONU Pots Administratoration"
			::= { sleGponProfileVoIPPotsControl 8 }


--   1.3.6.1.4.1.6296.101.23.5.5.4.3
-- 1.3.6.1.4.1.6296.101.23.5.5.4.3
		sleGponProfileVoIPPotsNotification OBJECT IDENTIFIER ::= { sleGponProfileVoIPPots 3 }


--   1.3.6.1.4.1.6296.101.23.5.5.4.3.1
-- 1.3.6.1.4.1.6296.101.23.5.5.4.3.1
		sleGponProfileVoIPPotsAdded NOTIFICATION-TYPE
			OBJECTS { sleGponProfileVoIPPotsControlReqResult, sleGponProfileVoIPPotsControlTimeStamp, sleGponProfileVoIPPotsControlProfileIndex, sleGponProfileVoIPPotsControlPotsIndex, sleGponProfileVoIPPotsControlAdmin
				 }
			STATUS current
			DESCRIPTION
				"Description."
			::= { sleGponProfileVoIPPotsNotification 1 }


--   1.3.6.1.4.1.6296.101.23.5.5.4.3.2
-- 1.3.6.1.4.1.6296.101.23.5.5.4.3.2
		sleGponProfileVoIPPotsDeleted NOTIFICATION-TYPE
			OBJECTS { sleGponProfileVoIPPotsControlRequest, sleGponProfileVoIPPotsControlTimeStamp, sleGponProfileVoIPPotsControlReqResult, sleGponProfileVoIPPotsControlProfileIndex, sleGponProfileVoIPPotsControlPotsIndex
				 }
			STATUS current
			DESCRIPTION
				"Description."
			::= { sleGponProfileVoIPPotsNotification 2 }


--   1.3.6.1.4.1.6296.101.23.5.5.1
-- 1.3.6.1.4.1.6296.101.23.5.5.5
		sleGponProfileVoIPDetail OBJECT IDENTIFIER ::= { sleGponVoIP 5 }


--   1.3.6.1.4.1.6296.101.23.5.5.1.1
-- 1.3.6.1.4.1.6296.101.23.5.5.5.1
		sleGponProfileVoIPDetailTable OBJECT-TYPE
			SYNTAX SEQUENCE OF SleGponProfileVoIPDetailEntry
			MAX-ACCESS not-accessible
			STATUS current
			DESCRIPTION
				"sleGponProfileVoIPDetailTable"
			::= { sleGponProfileVoIPDetail 1 }


--   1.3.6.1.4.1.6296.101.23.5.5.1.1.1
-- 1.3.6.1.4.1.6296.101.23.5.5.5.1.1
		sleGponProfileVoIPDetailEntry OBJECT-TYPE
			SYNTAX SleGponProfileVoIPDetailEntry
			MAX-ACCESS not-accessible
			STATUS current
			DESCRIPTION
				"key: sleGponProfileVoIPDetailIndex"
			INDEX { sleGponProfileVoIPDetailIndex }
			::= { sleGponProfileVoIPDetailTable 1 }


		SleGponProfileVoIPDetailEntry ::=
			SEQUENCE {
				sleGponProfileVoIPDetailIndex
					INTEGER,
				sleGponProfileVoIPDetailName
					OCTET STRING,
				sleGponProfileVoIPDetailFaxMode
					INTEGER,
				sleGponProfileVoIPDetailCodecType1st
					INTEGER,
				sleGponProfileVoIPDetailCodecPeriod1st
					INTEGER,
				sleGponProfileVoIPDetailCodecSilenceSuppression1st
					INTEGER,
				sleGponProfileVoIPDetailCodecType2nd
					INTEGER,
				sleGponProfileVoIPDetailCodecPeriod2nd
					INTEGER,
				sleGponProfileVoIPDetailCodecSilenceSuppression2nd
					INTEGER,
				sleGponProfileVoIPDetailCodecType3rd
					INTEGER,
				sleGponProfileVoIPDetailCodecPeriod3rd
					INTEGER,
				sleGponProfileVoIPDetailCodecSilenceSuppression3rd
					INTEGER,
				sleGponProfileVoIPDetailCodecType4th
					INTEGER,
				sleGponProfileVoIPDetailCodecPeriod4th
					INTEGER,
				sleGponProfileVoIPDetailCodecSilenceSuppression4th
					INTEGER,
				sleGponProfileVoIPDetailOobdtmf
					INTEGER,
				sleGponProfileVoIPDetailAnnouncementType
					INTEGER,
				sleGponProfileVoIPDetailJitterTarget
					INTEGER,
				sleGponProfileVoIPDetailJitterBuffMax
					INTEGER,
				sleGponProfileVoIPDetailEchoCancel
					INTEGER,
				sleGponProfileVoIPDetailPstnProtoVariant
					INTEGER,
				sleGponProfileVoIPDetailDtmfDigitLevels
					INTEGER,
				sleGponProfileVoIPDetailDtmfDigitDuration
					INTEGER,
				sleGponProfileVoIPDetailHookFlashTimeMin
					INTEGER,
				sleGponProfileVoIPDetailHookFlashTimeMax
					INTEGER,
				sleGponProfileVoIPDetailSignalingCode
					INTEGER,
				sleGponProfileVoIPDetailRtpLocalPortMin
					INTEGER,
				sleGponProfileVoIPDetailRtpLocalPortMax
					INTEGER,
				sleGponProfileVoIPDetailRtpDscpMark
					INTEGER,
				sleGponProfileVoIPDetailRtpPiggybackEvent
					INTEGER,
				sleGponProfileVoIPDetailRtpToneEvent
					INTEGER,
				sleGponProfileVoIPDetailRtpDtmfEvent
					INTEGER,
				sleGponProfileVoIPDetailRtpCasEvent
					INTEGER,
				sleGponProfileVoIPDetailProtocol
					INTEGER,
				sleGponProfileVoIPDetailMgcPriServer
					OCTET STRING,
				sleGponProfileVoIPDetailMgcSecServer
					OCTET STRING,
				sleGponProfileVoIPDetailMgcMsgVersion
					INTEGER,
				sleGponProfileVoIPDetailMgcMsgFormat
					INTEGER,
				sleGponProfileVoIPDetailMgcMaxRetryTime
					INTEGER,
				sleGponProfileVoIPDetailMgcMaxRetryAttempts
					INTEGER,
				sleGponProfileVoIPDetailMgcSvcChangeDelay
					INTEGER,
				sleGponProfileVoIPDetailMgcTerminationId
					OCTET STRING,
				sleGponProfileVoIPDetailMgcSoftswitch
					OCTET STRING,
				sleGponProfileVoIPDetailVoicemailServer
					OCTET STRING,
				sleGponProfileVoIPDetailVoicemmailExpireTime
					INTEGER,
				sleGponProfileVoIPDetailReleaseTime
					INTEGER,
				sleGponProfileVoIPDetailRohTimer
					INTEGER,
				sleGponProfileVoIPDetailProxyServer
					OCTET STRING,
				sleGponProfileVoIPDetailOutboundProxyServer
					OCTET STRING,
				sleGponProfileVoIPDetailRegisterServer
					OCTET STRING,
				sleGponProfileVoIPDetailHostPartServer
					OCTET STRING,
				sleGponProfileVoIPDetailPriDns
					IpAddress,
				sleGponProfileVoIPDetailSecDns
					IpAddress,
				sleGponProfileVoIPDetailRegExpTime
					INTEGER,
				sleGponProfileVoIPDetailReregHeadStartTime
					INTEGER,
				sleGponProfileVoIPDetailSoftSwitchVendor
					OCTET STRING,
				sleGponProfileVoIPDetailSipOptionTransmitCtl
					INTEGER,
				sleGponProfileVoIPDetailSipUriFormat
					INTEGER,
				sleGponProfileVoIPDetailCallerId
					BITS,
				sleGponProfileVoIPDetailCallWaiting
					BITS,
				sleGponProfileVoIPDetailCallProgressTransfer
					BITS,
				sleGponProfileVoIPDetailCallPresent
					BITS,
				sleGponProfileVoIPDetailDirectConnect
					INTEGER,
				sleGponProfileVoIPDetailDirectConnectUri
					OCTET STRING,
				sleGponProfileVoIPDetailBridgedLineAgentUri
					OCTET STRING,
				sleGponProfileVoIPDetailConferenceFactoryUri
					OCTET STRING,
				sleGponProfileVoIPDetailCancelCallWait
					OCTET STRING,
				sleGponProfileVoIPDetailCallHold
					OCTET STRING,
				sleGponProfileVoIPDetailCallPark
					OCTET STRING,
				sleGponProfileVoIPDetailCallerIdAct
					OCTET STRING,
				sleGponProfileVoIPDetailCallerIdDeact
					OCTET STRING,
				sleGponProfileVoIPDetailDoNotDisturbAct
					OCTET STRING,
				sleGponProfileVoIPDetailDoNotDisturbDeact
					OCTET STRING,
				sleGponProfileVoIPDetailDoNotDisturbPinChange
					OCTET STRING,
				sleGponProfileVoIPDetailEmergServiceNumber
					OCTET STRING,
				sleGponProfileVoIPDetailIntercomService
					OCTET STRING,
				sleGponProfileVoIPDetailDialplanCritTimeout
					INTEGER,
				sleGponProfileVoIPDetailDialplanPartTimeout
					INTEGER,
				sleGponProfileVoIPDetailDialplanFormat
					INTEGER,
				sleGponProfileVoIPDetailSpecialLineService
					INTEGER,
				sleGponProfileVoIPDetailWarmLineTimeout
					Integer32,
				sleGponProfileVoIPDetailLineNumber
					OCTET STRING,
				sleGponProfileVoIPDetailThreeWaySSWMixing
					INTEGER,
				sleGponProfileVoIPDetailSIPDNSCache
					INTEGER,
				sleGponProfileVoIPDetailSIPTimerT1
					Integer32,
				sleGponProfileVoIPDetailSIPTimerT2
					Integer32,
				sleGponProfileVoIPDetailSIPTimerTd
					Integer32,
				sleGponProfileVoIPDetailSIPSessionTimer
					INTEGER,
				sleGponProfileVoIPDetailSIPSessionTimeout
					Integer32,
				sleGponProfileVoIPDetailSIPEndOfDigit
					INTEGER,
				sleGponProfileVoIPDetailSIPEndSharpToken
					INTEGER
			 }

--   1.3.6.1.4.1.6296.101.23.5.5.1.1.1.1
-- 1.3.6.1.4.1.6296.101.23.5.5.5.1.1.1
		sleGponProfileVoIPDetailIndex OBJECT-TYPE
			SYNTAX INTEGER (1..65535)
			MAX-ACCESS read-only
			STATUS current
			DESCRIPTION
				"VoIP Profile Index."
			::= { sleGponProfileVoIPDetailEntry 1 }


--   1.3.6.1.4.1.6296.101.23.5.5.1.1.1.2
-- 1.3.6.1.4.1.6296.101.23.5.5.5.1.1.2
		sleGponProfileVoIPDetailName OBJECT-TYPE
			SYNTAX OCTET STRING
			MAX-ACCESS read-only
			STATUS current
			DESCRIPTION
				"VoIP profile name."
			::= { sleGponProfileVoIPDetailEntry 2 }


--   1.3.6.1.4.1.6296.101.23.5.5.1.1.1.3
-- 1.3.6.1.4.1.6296.101.23.5.5.5.1.1.3
		sleGponProfileVoIPDetailFaxMode OBJECT-TYPE
			SYNTAX INTEGER
				{
				passthru(0),
				t38(1)
				}
			MAX-ACCESS read-only
			STATUS current
			DESCRIPTION
				"VoIP fax mode."
			::= { sleGponProfileVoIPDetailEntry 3 }


--   1.3.6.1.4.1.6296.101.23.5.5.1.1.1.4
-- 1.3.6.1.4.1.6296.101.23.5.5.5.1.1.4
		sleGponProfileVoIPDetailCodecType1st OBJECT-TYPE
			SYNTAX INTEGER
				{
				pcmu(0),
				gsm(3),
				g723(4),
				dvi4and8k(5),
				dvi4and16k(6),
				lpc(7),
				pcma(8),
				g722(9),
				l16and2ch(10),
				l16and1h(11),
				qcelp(12),
				cn(13),
				mpa(14),
				g728(15),
				dvi4and11k(16),
				dvi4and22k(17),
				g729(18)
				}
			MAX-ACCESS read-only
			STATUS current
			DESCRIPTION
				"VoIP codec type 1st."
			::= { sleGponProfileVoIPDetailEntry 4 }


--   1.3.6.1.4.1.6296.101.23.5.5.1.1.1.5
-- 1.3.6.1.4.1.6296.101.23.5.5.5.1.1.5
		sleGponProfileVoIPDetailCodecPeriod1st OBJECT-TYPE
			SYNTAX INTEGER (1..65535)
			MAX-ACCESS read-only
			STATUS current
			DESCRIPTION
				"Codec sampling period1st"
			::= { sleGponProfileVoIPDetailEntry 5 }


--   1.3.6.1.4.1.6296.101.23.5.5.1.1.1.5
-- 1.3.6.1.4.1.6296.101.23.5.5.5.1.1.6
		sleGponProfileVoIPDetailCodecSilenceSuppression1st OBJECT-TYPE
			SYNTAX INTEGER (1..65535)
			MAX-ACCESS read-only
			STATUS current
			DESCRIPTION
				"VoIP codec silence suppression 1st"
			::= { sleGponProfileVoIPDetailEntry 6 }


--   1.3.6.1.4.1.6296.101.23.5.5.1.1.1.5
-- 1.3.6.1.4.1.6296.101.23.5.5.5.1.1.7
		sleGponProfileVoIPDetailCodecType2nd OBJECT-TYPE
			SYNTAX INTEGER
				{
				pcmu(0),
				gsm(3),
				g723(4),
				dvi4and8k(5),
				dvi4and16k(6),
				lpc(7),
				pcma(8),
				g722(9),
				l16and2ch(10),
				l16and1h(11),
				qcelp(12),
				cn(13),
				mpa(14),
				g728(15),
				dvi4and11k(16),
				dvi4and22k(17),
				g729(18)
				}
			MAX-ACCESS read-only
			STATUS current
			DESCRIPTION
				"VoIP codec type 2nd"
			::= { sleGponProfileVoIPDetailEntry 7 }


--   1.3.6.1.4.1.6296.101.23.5.5.1.1.1.5
-- 1.3.6.1.4.1.6296.101.23.5.5.5.1.1.8
		sleGponProfileVoIPDetailCodecPeriod2nd OBJECT-TYPE
			SYNTAX INTEGER (1..65535)
			MAX-ACCESS read-only
			STATUS current
			DESCRIPTION
				"Codec sampling period 2nd"
			::= { sleGponProfileVoIPDetailEntry 8 }


--   1.3.6.1.4.1.6296.101.23.5.5.1.1.1.5
-- 1.3.6.1.4.1.6296.101.23.5.5.5.1.1.9
		sleGponProfileVoIPDetailCodecSilenceSuppression2nd OBJECT-TYPE
			SYNTAX INTEGER (1..65535)
			MAX-ACCESS read-only
			STATUS current
			DESCRIPTION
				"VoIP codec silence suppression 2nd"
			::= { sleGponProfileVoIPDetailEntry 9 }


--   1.3.6.1.4.1.6296.101.23.5.5.1.1.1.5
-- 1.3.6.1.4.1.6296.101.23.5.5.5.1.1.10
		sleGponProfileVoIPDetailCodecType3rd OBJECT-TYPE
			SYNTAX INTEGER
				{
				pcmu(0),
				gsm(3),
				g723(4),
				dvi4and8k(5),
				dvi4and16k(6),
				lpc(7),
				pcma(8),
				g722(9),
				l16and2ch(10),
				l16and1h(11),
				qcelp(12),
				cn(13),
				mpa(14),
				g728(15),
				dvi4and11k(16),
				dvi4and22k(17),
				g729(18)
				}
			MAX-ACCESS read-only
			STATUS current
			DESCRIPTION
				"VoIP codec type 3rd"
			::= { sleGponProfileVoIPDetailEntry 10 }


--   1.3.6.1.4.1.6296.101.23.5.5.1.1.1.5
-- 1.3.6.1.4.1.6296.101.23.5.5.5.1.1.11
		sleGponProfileVoIPDetailCodecPeriod3rd OBJECT-TYPE
			SYNTAX INTEGER (1..65535)
			MAX-ACCESS read-only
			STATUS current
			DESCRIPTION
				"Codec sampling period 3rd"
			::= { sleGponProfileVoIPDetailEntry 11 }


--   1.3.6.1.4.1.6296.101.23.5.5.1.1.1.5
-- 1.3.6.1.4.1.6296.101.23.5.5.5.1.1.12
		sleGponProfileVoIPDetailCodecSilenceSuppression3rd OBJECT-TYPE
			SYNTAX INTEGER (1..65535)
			MAX-ACCESS read-only
			STATUS current
			DESCRIPTION
				"VoIP codec silence suppression 3rd."
			::= { sleGponProfileVoIPDetailEntry 12 }


--   1.3.6.1.4.1.6296.101.23.5.5.1.1.1.5
-- 1.3.6.1.4.1.6296.101.23.5.5.5.1.1.13
		sleGponProfileVoIPDetailCodecType4th OBJECT-TYPE
			SYNTAX INTEGER
				{
				pcmu(0),
				gsm(3),
				g723(4),
				dvi4and8k(5),
				dvi4and16k(6),
				lpc(7),
				pcma(8),
				g722(9),
				l16and2ch(10),
				l16and1h(11),
				qcelp(12),
				cn(13),
				mpa(14),
				g728(15),
				dvi4and11k(16),
				dvi4and22k(17),
				g729(18)
				}
			MAX-ACCESS read-only
			STATUS current
			DESCRIPTION
				"VoIP codec type 4th"
			::= { sleGponProfileVoIPDetailEntry 13 }


--   1.3.6.1.4.1.6296.101.23.5.5.1.1.1.5
-- 1.3.6.1.4.1.6296.101.23.5.5.5.1.1.14
		sleGponProfileVoIPDetailCodecPeriod4th OBJECT-TYPE
			SYNTAX INTEGER (1..65535)
			MAX-ACCESS read-only
			STATUS current
			DESCRIPTION
				"Codec sampling period 4th"
			::= { sleGponProfileVoIPDetailEntry 14 }


--   1.3.6.1.4.1.6296.101.23.5.5.1.1.1.5
-- 1.3.6.1.4.1.6296.101.23.5.5.5.1.1.15
		sleGponProfileVoIPDetailCodecSilenceSuppression4th OBJECT-TYPE
			SYNTAX INTEGER (1..65535)
			MAX-ACCESS read-only
			STATUS current
			DESCRIPTION
				"VoIP codec silence suppression 4th."
			::= { sleGponProfileVoIPDetailEntry 15 }


--   1.3.6.1.4.1.6296.101.23.5.5.1.1.1.5
-- 1.3.6.1.4.1.6296.101.23.5.5.5.1.1.16
		sleGponProfileVoIPDetailOobdtmf OBJECT-TYPE
			SYNTAX INTEGER
				{
				disable(0),
				enable(1)
				}
			MAX-ACCESS read-only
			STATUS current
			DESCRIPTION
				"Control DTMF(Dual Tone Multi-Frequency)"
			::= { sleGponProfileVoIPDetailEntry 16 }


--   1.3.6.1.4.1.6296.101.23.5.5.1.1.1.5
-- 1.3.6.1.4.1.6296.101.23.5.5.5.1.1.17
		sleGponProfileVoIPDetailAnnouncementType OBJECT-TYPE
			SYNTAX INTEGER
				{
				silence(1),
				reorderTone(2),
				fastBusy(3),
				voiceAnnouncement(4)
				}
			MAX-ACCESS read-only
			STATUS current
			DESCRIPTION
				"VoIp announcement type"
			::= { sleGponProfileVoIPDetailEntry 17 }


--   1.3.6.1.4.1.6296.101.23.5.5.1.1.1.5
-- 1.3.6.1.4.1.6296.101.23.5.5.5.1.1.18
		sleGponProfileVoIPDetailJitterTarget OBJECT-TYPE
			SYNTAX INTEGER (1..65535)
			MAX-ACCESS read-only
			STATUS current
			DESCRIPTION
				"Jitter target (milliseconds)"
			::= { sleGponProfileVoIPDetailEntry 18 }


--   1.3.6.1.4.1.6296.101.23.5.5.1.1.1.5
-- 1.3.6.1.4.1.6296.101.23.5.5.5.1.1.19
		sleGponProfileVoIPDetailJitterBuffMax OBJECT-TYPE
			SYNTAX INTEGER (0..65535)
			MAX-ACCESS read-only
			STATUS current
			DESCRIPTION
				"VoIP jitter buffer max."
			::= { sleGponProfileVoIPDetailEntry 19 }


--   1.3.6.1.4.1.6296.101.23.5.5.1.1.1.5
-- 1.3.6.1.4.1.6296.101.23.5.5.5.1.1.20
		sleGponProfileVoIPDetailEchoCancel OBJECT-TYPE
			SYNTAX INTEGER
				{
				false(0),
				ture(1)
				}
			MAX-ACCESS read-only
			STATUS current
			DESCRIPTION
				"VoIP echo cancel"
			::= { sleGponProfileVoIPDetailEntry 20 }


--   1.3.6.1.4.1.6296.101.23.5.5.1.1.1.5
-- 1.3.6.1.4.1.6296.101.23.5.5.5.1.1.21
		sleGponProfileVoIPDetailPstnProtoVariant OBJECT-TYPE
			SYNTAX INTEGER (1..65535)
			MAX-ACCESS read-only
			STATUS current
			DESCRIPTION
				"PSTN Protocol Variant"
			::= { sleGponProfileVoIPDetailEntry 21 }


--   1.3.6.1.4.1.6296.101.23.5.5.1.1.1.5
-- 1.3.6.1.4.1.6296.101.23.5.5.5.1.1.22
		sleGponProfileVoIPDetailDtmfDigitLevels OBJECT-TYPE
			SYNTAX INTEGER (0..65535)
			MAX-ACCESS read-only
			STATUS current
			DESCRIPTION
				"DTMF digit Power Level configuration "
			::= { sleGponProfileVoIPDetailEntry 22 }


--   1.3.6.1.4.1.6296.101.23.5.5.1.1.1.5
-- 1.3.6.1.4.1.6296.101.23.5.5.5.1.1.23
		sleGponProfileVoIPDetailDtmfDigitDuration OBJECT-TYPE
			SYNTAX INTEGER (0..65535)
			MAX-ACCESS read-only
			STATUS current
			DESCRIPTION
				"DTMF digit Power Duration configuration"
			::= { sleGponProfileVoIPDetailEntry 23 }


--   1.3.6.1.4.1.6296.101.23.5.5.1.1.1.5
-- 1.3.6.1.4.1.6296.101.23.5.5.5.1.1.24
		sleGponProfileVoIPDetailHookFlashTimeMin OBJECT-TYPE
			SYNTAX INTEGER (0..65535)
			MAX-ACCESS read-only
			STATUS current
			DESCRIPTION
				"VoIP hook Flash Time Minimum"
			::= { sleGponProfileVoIPDetailEntry 24 }


--   1.3.6.1.4.1.6296.101.23.5.5.1.1.1.5
-- 1.3.6.1.4.1.6296.101.23.5.5.5.1.1.25
		sleGponProfileVoIPDetailHookFlashTimeMax OBJECT-TYPE
			SYNTAX INTEGER (0..65535)
			MAX-ACCESS read-only
			STATUS current
			DESCRIPTION
				"VoIP hook Flash Time Maximum"
			::= { sleGponProfileVoIPDetailEntry 25 }


--   1.3.6.1.4.1.6296.101.23.5.5.1.1.1.5
-- 1.3.6.1.4.1.6296.101.23.5.5.5.1.1.26
		sleGponProfileVoIPDetailSignalingCode OBJECT-TYPE
			SYNTAX INTEGER
				{
				loopStart(1),
				groundStart(2),
				loopReverseBattery(3),
				coinFirst(4),
				dialToneFirst(5),
				multiParty(6)
				}
			MAX-ACCESS read-only
			STATUS current
			DESCRIPTION
				"VoIP signaling code."
			::= { sleGponProfileVoIPDetailEntry 26 }


--   1.3.6.1.4.1.6296.101.23.5.5.1.1.1.5
-- 1.3.6.1.4.1.6296.101.23.5.5.5.1.1.27
		sleGponProfileVoIPDetailRtpLocalPortMin OBJECT-TYPE
			SYNTAX INTEGER (1..65535)
			MAX-ACCESS read-only
			STATUS current
			DESCRIPTION
				"RTP Local Port Min"
			::= { sleGponProfileVoIPDetailEntry 27 }


--   1.3.6.1.4.1.6296.101.23.5.5.1.1.1.5
-- 1.3.6.1.4.1.6296.101.23.5.5.5.1.1.28
		sleGponProfileVoIPDetailRtpLocalPortMax OBJECT-TYPE
			SYNTAX INTEGER (1..65535)
			MAX-ACCESS read-only
			STATUS current
			DESCRIPTION
				"RTP Local Port Max"
			::= { sleGponProfileVoIPDetailEntry 28 }


--  1.3.6.1.4.1.6296.101.23.5.5.5.1.1.29
		sleGponProfileVoIPDetailRtpDscpMark OBJECT-TYPE
			SYNTAX INTEGER (1..65535)
			MAX-ACCESS read-only
			STATUS current
			DESCRIPTION
				"RTP DSCP Mark"
			::= { sleGponProfileVoIPDetailEntry 29 }


--  1.3.6.1.4.1.6296.101.23.5.5.5.1.1.30
		sleGponProfileVoIPDetailRtpPiggybackEvent OBJECT-TYPE
			SYNTAX INTEGER
				{
				disable(0),
				enable(1)
				}
			MAX-ACCESS read-only
			STATUS current
			DESCRIPTION
				"RTP Piggyback event"
			::= { sleGponProfileVoIPDetailEntry 30 }


--  1.3.6.1.4.1.6296.101.23.5.5.5.1.1.31
		sleGponProfileVoIPDetailRtpToneEvent OBJECT-TYPE
			SYNTAX INTEGER
				{
				disable(0),
				enable(1)
				}
			MAX-ACCESS read-only
			STATUS current
			DESCRIPTION
				"RTP Tone event"
			::= { sleGponProfileVoIPDetailEntry 31 }


--  1.3.6.1.4.1.6296.101.23.5.5.5.1.1.32
		sleGponProfileVoIPDetailRtpDtmfEvent OBJECT-TYPE
			SYNTAX INTEGER
				{
				disable(0),
				enable(1)
				}
			MAX-ACCESS read-only
			STATUS current
			DESCRIPTION
				"RTP DTMF event"
			::= { sleGponProfileVoIPDetailEntry 32 }


--  1.3.6.1.4.1.6296.101.23.5.5.5.1.1.33
		sleGponProfileVoIPDetailRtpCasEvent OBJECT-TYPE
			SYNTAX INTEGER
				{
				disable(0),
				enable(1)
				}
			MAX-ACCESS read-only
			STATUS current
			DESCRIPTION
				"RTP CAS events"
			::= { sleGponProfileVoIPDetailEntry 33 }


--  1.3.6.1.4.1.6296.101.23.5.5.5.1.1.34
		sleGponProfileVoIPDetailProtocol OBJECT-TYPE
			SYNTAX INTEGER
				{
				none(0),
				sip(1),
				h248(2),
				mgcp(3)
				}
			MAX-ACCESS read-only
			STATUS current
			DESCRIPTION
				"VoIP Protocol configuration"
			::= { sleGponProfileVoIPDetailEntry 34 }


--  1.3.6.1.4.1.6296.101.23.5.5.5.1.1.35
		sleGponProfileVoIPDetailMgcPriServer OBJECT-TYPE
			SYNTAX OCTET STRING
			MAX-ACCESS read-only
			STATUS current
			DESCRIPTION
				"The primary server name."
			::= { sleGponProfileVoIPDetailEntry 35 }


--  1.3.6.1.4.1.6296.101.23.5.5.5.1.1.36
		sleGponProfileVoIPDetailMgcSecServer OBJECT-TYPE
			SYNTAX OCTET STRING
			MAX-ACCESS read-only
			STATUS current
			DESCRIPTION
				"The secondary server name."
			::= { sleGponProfileVoIPDetailEntry 36 }


--  1.3.6.1.4.1.6296.101.23.5.5.5.1.1.37
		sleGponProfileVoIPDetailMgcMsgVersion OBJECT-TYPE
			SYNTAX INTEGER (1..255)
			MAX-ACCESS read-only
			STATUS current
			DESCRIPTION
				"The message version."
			::= { sleGponProfileVoIPDetailEntry 37 }


--  1.3.6.1.4.1.6296.101.23.5.5.5.1.1.38
		sleGponProfileVoIPDetailMgcMsgFormat OBJECT-TYPE
			SYNTAX INTEGER
				{
				textLong(0),
				textShort(1),
				binary(2)
				}
			MAX-ACCESS read-only
			STATUS current
			DESCRIPTION
				"The message format.
				0:textLong
				1:textShort
				2:binary"
			::= { sleGponProfileVoIPDetailEntry 38 }


--  1.3.6.1.4.1.6296.101.23.5.5.5.1.1.39
		sleGponProfileVoIPDetailMgcMaxRetryTime OBJECT-TYPE
			SYNTAX INTEGER (0..65535)
			MAX-ACCESS read-only
			STATUS current
			DESCRIPTION
				"The max retry time.
				65535: unused"
			::= { sleGponProfileVoIPDetailEntry 39 }


--  1.3.6.1.4.1.6296.101.23.5.5.5.1.1.40
		sleGponProfileVoIPDetailMgcMaxRetryAttempts OBJECT-TYPE
			SYNTAX INTEGER (0..65535)
			MAX-ACCESS read-only
			STATUS current
			DESCRIPTION
				"The max retry attemption
				65535: unused"
			::= { sleGponProfileVoIPDetailEntry 40 }


--  1.3.6.1.4.1.6296.101.23.5.5.5.1.1.41
		sleGponProfileVoIPDetailMgcSvcChangeDelay OBJECT-TYPE
			SYNTAX INTEGER (0..65535)
			MAX-ACCESS read-only
			STATUS current
			DESCRIPTION
				"The service change delay
				65535: unused"
			::= { sleGponProfileVoIPDetailEntry 41 }


--  1.3.6.1.4.1.6296.101.23.5.5.5.1.1.42
		sleGponProfileVoIPDetailMgcTerminationId OBJECT-TYPE
			SYNTAX OCTET STRING
			MAX-ACCESS read-only
			STATUS current
			DESCRIPTION
				"The termination id."
			::= { sleGponProfileVoIPDetailEntry 42 }


--  1.3.6.1.4.1.6296.101.23.5.5.5.1.1.43
		sleGponProfileVoIPDetailMgcSoftswitch OBJECT-TYPE
			SYNTAX OCTET STRING
			MAX-ACCESS read-only
			STATUS current
			DESCRIPTION
				"The soft switch"
			::= { sleGponProfileVoIPDetailEntry 43 }


--  1.3.6.1.4.1.6296.101.23.5.5.5.1.1.44
		sleGponProfileVoIPDetailVoicemailServer OBJECT-TYPE
			SYNTAX OCTET STRING
			MAX-ACCESS read-only
			STATUS current
			DESCRIPTION
				"VoIP voice mail server."
			::= { sleGponProfileVoIPDetailEntry 44 }


--  1.3.6.1.4.1.6296.101.23.5.5.5.1.1.45
		sleGponProfileVoIPDetailVoicemmailExpireTime OBJECT-TYPE
			SYNTAX INTEGER (1..65535)
			MAX-ACCESS read-only
			STATUS current
			DESCRIPTION
				"VoIP voice mail Expire time"
			::= { sleGponProfileVoIPDetailEntry 45 }


--  1.3.6.1.4.1.6296.101.23.5.5.5.1.1.46
		sleGponProfileVoIPDetailReleaseTime OBJECT-TYPE
			SYNTAX INTEGER (1..65535)
			MAX-ACCESS read-only
			STATUS current
			DESCRIPTION
				"VoIp release time"
			::= { sleGponProfileVoIPDetailEntry 46 }


--  1.3.6.1.4.1.6296.101.23.5.5.5.1.1.47
		sleGponProfileVoIPDetailRohTimer OBJECT-TYPE
			SYNTAX INTEGER (1..65535)
			MAX-ACCESS read-only
			STATUS current
			DESCRIPTION
				"ROH timer"
			::= { sleGponProfileVoIPDetailEntry 47 }


--  1.3.6.1.4.1.6296.101.23.5.5.5.1.1.48
		sleGponProfileVoIPDetailProxyServer OBJECT-TYPE
			SYNTAX OCTET STRING
			MAX-ACCESS read-only
			STATUS current
			DESCRIPTION
				"Proxy server address"
			::= { sleGponProfileVoIPDetailEntry 48 }


--  1.3.6.1.4.1.6296.101.23.5.5.5.1.1.49
		sleGponProfileVoIPDetailOutboundProxyServer OBJECT-TYPE
			SYNTAX OCTET STRING
			MAX-ACCESS read-only
			STATUS current
			DESCRIPTION
				"Outbound proxy address"
			::= { sleGponProfileVoIPDetailEntry 49 }


--  1.3.6.1.4.1.6296.101.23.5.5.5.1.1.50
		sleGponProfileVoIPDetailRegisterServer OBJECT-TYPE
			SYNTAX OCTET STRING
			MAX-ACCESS read-only
			STATUS current
			DESCRIPTION
				"VoIP register server"
			::= { sleGponProfileVoIPDetailEntry 50 }


--  1.3.6.1.4.1.6296.101.23.5.5.5.1.1.51
		sleGponProfileVoIPDetailHostPartServer OBJECT-TYPE
			SYNTAX OCTET STRING
			MAX-ACCESS read-only
			STATUS current
			DESCRIPTION
				"VoIp host part server."
			::= { sleGponProfileVoIPDetailEntry 51 }


--  1.3.6.1.4.1.6296.101.23.5.5.5.1.1.52
		sleGponProfileVoIPDetailPriDns OBJECT-TYPE
			SYNTAX IpAddress
			MAX-ACCESS read-only
			STATUS current
			DESCRIPTION
				"VoIP primary dns"
			::= { sleGponProfileVoIPDetailEntry 52 }


--  1.3.6.1.4.1.6296.101.23.5.5.5.1.1.53
		sleGponProfileVoIPDetailSecDns OBJECT-TYPE
			SYNTAX IpAddress
			MAX-ACCESS read-only
			STATUS current
			DESCRIPTION
				"VoIP secondary dns"
			::= { sleGponProfileVoIPDetailEntry 53 }


--  1.3.6.1.4.1.6296.101.23.5.5.5.1.1.54
		sleGponProfileVoIPDetailRegExpTime OBJECT-TYPE
			SYNTAX INTEGER (1..65535)
			MAX-ACCESS read-only
			STATUS current
			DESCRIPTION
				"Registration expiration time"
			::= { sleGponProfileVoIPDetailEntry 54 }


--  1.3.6.1.4.1.6296.101.23.5.5.5.1.1.55
		sleGponProfileVoIPDetailReregHeadStartTime OBJECT-TYPE
			SYNTAX INTEGER (1..65535)
			MAX-ACCESS read-only
			STATUS current
			DESCRIPTION
				"Registration head start time"
			::= { sleGponProfileVoIPDetailEntry 55 }


--  1.3.6.1.4.1.6296.101.23.5.5.5.1.1.56
		sleGponProfileVoIPDetailSoftSwitchVendor OBJECT-TYPE
			SYNTAX OCTET STRING
			MAX-ACCESS read-only
			STATUS current
			DESCRIPTION
				"Softswitch Vendor name"
			::= { sleGponProfileVoIPDetailEntry 56 }


--  1.3.6.1.4.1.6296.101.23.5.5.5.1.1.57
		sleGponProfileVoIPDetailSipOptionTransmitCtl OBJECT-TYPE
			SYNTAX INTEGER
				{
				disable(0),
				enable(1)
				}
			MAX-ACCESS read-only
			STATUS current
			DESCRIPTION
				"Transmit control"
			::= { sleGponProfileVoIPDetailEntry 57 }


--  1.3.6.1.4.1.6296.101.23.5.5.5.1.1.58
		sleGponProfileVoIPDetailSipUriFormat OBJECT-TYPE
			SYNTAX INTEGER
				{
				telUri(0),
				sipUri(1)
				}
			MAX-ACCESS read-only
			STATUS current
			DESCRIPTION
				"URI format"
			::= { sleGponProfileVoIPDetailEntry 58 }


--  1.3.6.1.4.1.6296.101.23.5.5.5.1.1.59
		sleGponProfileVoIPDetailCallerId OBJECT-TYPE
			SYNTAX BITS
				{
				callNumber(0),
				callName(1),
				cidBlocking(2),
				cidNumber(3),
				cidName(4),
				acr(5)
				}
			MAX-ACCESS read-only
			STATUS current
			DESCRIPTION
				"Caller ID feature"
			::= { sleGponProfileVoIPDetailEntry 59 }


--  1.3.6.1.4.1.6296.101.23.5.5.5.1.1.60
		sleGponProfileVoIPDetailCallWaiting OBJECT-TYPE
			SYNTAX BITS
				{
				callFeature(0),
				cidAnnounce(1)
				}
			MAX-ACCESS read-only
			STATUS current
			DESCRIPTION
				"Call waiting features"
			::= { sleGponProfileVoIPDetailEntry 60 }


--  1.3.6.1.4.1.6296.101.23.5.5.5.1.1.61
		sleGponProfileVoIPDetailCallProgressTransfer OBJECT-TYPE
			SYNTAX BITS
				{
				threeWay(0),
				callTransfer(1),
				callHold(2),
				callPark(3),
				notDisturb(4),
				flashEmergCall(5),
				emergOriginatingHold(6)
				}
			MAX-ACCESS read-only
			STATUS current
			DESCRIPTION
				"Call progress or transfer features"
			::= { sleGponProfileVoIPDetailEntry 61 }


--  1.3.6.1.4.1.6296.101.23.5.5.5.1.1.62
		sleGponProfileVoIPDetailCallPresent OBJECT-TYPE
			SYNTAX BITS
				{
				splashRing(0),
				dialTone(1),
				visualIndicate(2),
				callForward(3)
				}
			MAX-ACCESS read-only
			STATUS current
			DESCRIPTION
				"Call presentation features"
			::= { sleGponProfileVoIPDetailEntry 62 }


--  1.3.6.1.4.1.6296.101.23.5.5.5.1.1.63
		sleGponProfileVoIPDetailDirectConnect OBJECT-TYPE
			SYNTAX INTEGER
				{
				disable(0),
				enable(1),
				delayOption(2)
				}
			MAX-ACCESS read-only
			STATUS current
			DESCRIPTION
				"Direct connect feature"
			::= { sleGponProfileVoIPDetailEntry 63 }


--  1.3.6.1.4.1.6296.101.23.5.5.5.1.1.64
		sleGponProfileVoIPDetailDirectConnectUri OBJECT-TYPE
			SYNTAX OCTET STRING
			MAX-ACCESS read-only
			STATUS current
			DESCRIPTION
				"Direct connect URI"
			::= { sleGponProfileVoIPDetailEntry 64 }


--  1.3.6.1.4.1.6296.101.23.5.5.5.1.1.65
		sleGponProfileVoIPDetailBridgedLineAgentUri OBJECT-TYPE
			SYNTAX OCTET STRING
			MAX-ACCESS read-only
			STATUS current
			DESCRIPTION
				"Bridged line agent URI"
			::= { sleGponProfileVoIPDetailEntry 65 }


--  1.3.6.1.4.1.6296.101.23.5.5.5.1.1.66
		sleGponProfileVoIPDetailConferenceFactoryUri OBJECT-TYPE
			SYNTAX OCTET STRING
			MAX-ACCESS read-only
			STATUS current
			DESCRIPTION
				"Conference factory URI"
			::= { sleGponProfileVoIPDetailEntry 66 }


--  1.3.6.1.4.1.6296.101.23.5.5.5.1.1.67
		sleGponProfileVoIPDetailCancelCallWait OBJECT-TYPE
			SYNTAX OCTET STRING
			MAX-ACCESS read-only
			STATUS current
			DESCRIPTION
				"Cancel call waiting"
			::= { sleGponProfileVoIPDetailEntry 67 }


--  1.3.6.1.4.1.6296.101.23.5.5.5.1.1.68
		sleGponProfileVoIPDetailCallHold OBJECT-TYPE
			SYNTAX OCTET STRING
			MAX-ACCESS read-only
			STATUS current
			DESCRIPTION
				"Call hold"
			::= { sleGponProfileVoIPDetailEntry 68 }


--  1.3.6.1.4.1.6296.101.23.5.5.5.1.1.69
		sleGponProfileVoIPDetailCallPark OBJECT-TYPE
			SYNTAX OCTET STRING
			MAX-ACCESS read-only
			STATUS current
			DESCRIPTION
				"Call park"
			::= { sleGponProfileVoIPDetailEntry 69 }


--  1.3.6.1.4.1.6296.101.23.5.5.5.1.1.70
		sleGponProfileVoIPDetailCallerIdAct OBJECT-TYPE
			SYNTAX OCTET STRING
			MAX-ACCESS read-only
			STATUS current
			DESCRIPTION
				"Caller ID activate"
			::= { sleGponProfileVoIPDetailEntry 70 }


--  1.3.6.1.4.1.6296.101.23.5.5.5.1.1.71
		sleGponProfileVoIPDetailCallerIdDeact OBJECT-TYPE
			SYNTAX OCTET STRING
			MAX-ACCESS read-only
			STATUS current
			DESCRIPTION
				"Caller ID deactivate"
			::= { sleGponProfileVoIPDetailEntry 71 }


--  1.3.6.1.4.1.6296.101.23.5.5.5.1.1.72
		sleGponProfileVoIPDetailDoNotDisturbAct OBJECT-TYPE
			SYNTAX OCTET STRING
			MAX-ACCESS read-only
			STATUS current
			DESCRIPTION
				"Do not disturb activation"
			::= { sleGponProfileVoIPDetailEntry 72 }


--  1.3.6.1.4.1.6296.101.23.5.5.5.1.1.73
		sleGponProfileVoIPDetailDoNotDisturbDeact OBJECT-TYPE
			SYNTAX OCTET STRING
			MAX-ACCESS read-only
			STATUS current
			DESCRIPTION
				"Do not disturb deactivation"
			::= { sleGponProfileVoIPDetailEntry 73 }


--  1.3.6.1.4.1.6296.101.23.5.5.5.1.1.74
		sleGponProfileVoIPDetailDoNotDisturbPinChange OBJECT-TYPE
			SYNTAX OCTET STRING
			MAX-ACCESS read-only
			STATUS current
			DESCRIPTION
				"Do not disturb PIN change"
			::= { sleGponProfileVoIPDetailEntry 74 }


--  1.3.6.1.4.1.6296.101.23.5.5.5.1.1.75
		sleGponProfileVoIPDetailEmergServiceNumber OBJECT-TYPE
			SYNTAX OCTET STRING
			MAX-ACCESS read-only
			STATUS current
			DESCRIPTION
				"Emergency service number"
			::= { sleGponProfileVoIPDetailEntry 75 }


--  1.3.6.1.4.1.6296.101.23.5.5.5.1.1.76
		sleGponProfileVoIPDetailIntercomService OBJECT-TYPE
			SYNTAX OCTET STRING
			MAX-ACCESS read-only
			STATUS current
			DESCRIPTION
				"Intercom service"
			::= { sleGponProfileVoIPDetailEntry 76 }


--  1.3.6.1.4.1.6296.101.23.5.5.5.1.1.77
		sleGponProfileVoIPDetailDialplanCritTimeout OBJECT-TYPE
			SYNTAX INTEGER (0..65535)
			MAX-ACCESS read-only
			STATUS current
			DESCRIPTION
				"dial-plan crit-timeout TIMEOUT (ms)"
			::= { sleGponProfileVoIPDetailEntry 77 }


--  1.3.6.1.4.1.6296.101.23.5.5.5.1.1.78
		sleGponProfileVoIPDetailDialplanPartTimeout OBJECT-TYPE
			SYNTAX INTEGER (0..65535)
			MAX-ACCESS read-only
			STATUS current
			DESCRIPTION
				"dial-plan part-timeout TIMEOUT (ms)"
			::= { sleGponProfileVoIPDetailEntry 78 }


--  1.3.6.1.4.1.6296.101.23.5.5.5.1.1.79
		sleGponProfileVoIPDetailDialplanFormat OBJECT-TYPE
			SYNTAX INTEGER
				{
				h248(1),
				nsc(2),
				vendor(3)
				}
			MAX-ACCESS read-only
			STATUS current
			DESCRIPTION
				"dial-plan format (h248|nsc|vendor)"
			::= { sleGponProfileVoIPDetailEntry 79 }


--  1.3.6.1.4.1.6296.101.23.5.5.5.1.1.80
		sleGponProfileVoIPDetailSpecialLineService OBJECT-TYPE
			SYNTAX INTEGER
				{
				disable(0),
				enableHotLine(1),
				enableWarmLine(2)
				}
			MAX-ACCESS read-only
			STATUS current
			DESCRIPTION
				"Special Line Service"
			::= { sleGponProfileVoIPDetailEntry 80 }


--  1.3.6.1.4.1.6296.101.23.5.5.5.1.1.81
		sleGponProfileVoIPDetailWarmLineTimeout OBJECT-TYPE
			SYNTAX Integer32 (0..30)
			MAX-ACCESS read-only
			STATUS current
			DESCRIPTION
				"Warm Line Waiting Time"
			::= { sleGponProfileVoIPDetailEntry 81 }


--  1.3.6.1.4.1.6296.101.23.5.5.5.1.1.82
		sleGponProfileVoIPDetailLineNumber OBJECT-TYPE
			SYNTAX OCTET STRING
			MAX-ACCESS read-only
			STATUS current
			DESCRIPTION
				"Special Line Number"
			::= { sleGponProfileVoIPDetailEntry 82 }


--  1.3.6.1.4.1.6296.101.23.5.5.5.1.1.83
		sleGponProfileVoIPDetailThreeWaySSWMixing OBJECT-TYPE
			SYNTAX INTEGER
				{
				server(0),
				client(1)
				}
			MAX-ACCESS read-only
			STATUS current
			DESCRIPTION
				"3Way Call Voice Mixing"
			::= { sleGponProfileVoIPDetailEntry 83 }


--  1.3.6.1.4.1.6296.101.23.5.5.5.1.1.84
		sleGponProfileVoIPDetailSIPDNSCache OBJECT-TYPE
			SYNTAX INTEGER
				{
				ttl(0),
				permanent(1)
				}
			MAX-ACCESS read-only
			STATUS current
			DESCRIPTION
				"SIP Stack DNS Cache update policy"
			::= { sleGponProfileVoIPDetailEntry 84 }


--  1.3.6.1.4.1.6296.101.23.5.5.5.1.1.85
		sleGponProfileVoIPDetailSIPTimerT1 OBJECT-TYPE
			SYNTAX Integer32 (0..2500)
			MAX-ACCESS read-only
			STATUS current
			DESCRIPTION
				"First Response Wait Time"
			::= { sleGponProfileVoIPDetailEntry 85 }


--  1.3.6.1.4.1.6296.101.23.5.5.5.1.1.86
		sleGponProfileVoIPDetailSIPTimerT2 OBJECT-TYPE
			SYNTAX Integer32 (0..5000)
			MAX-ACCESS read-only
			STATUS current
			DESCRIPTION
				"Next Increase Waiting Time"
			::= { sleGponProfileVoIPDetailEntry 86 }


--  1.3.6.1.4.1.6296.101.23.5.5.5.1.1.87
		sleGponProfileVoIPDetailSIPTimerTd OBJECT-TYPE
			SYNTAX Integer32 (5000..65535)
			MAX-ACCESS read-only
			STATUS current
			DESCRIPTION
				"Max Transaction Time"
			::= { sleGponProfileVoIPDetailEntry 87 }


--  1.3.6.1.4.1.6296.101.23.5.5.5.1.1.88
		sleGponProfileVoIPDetailSIPSessionTimer OBJECT-TYPE
			SYNTAX INTEGER
				{
				disable(0),
				enable(1)
				}
			MAX-ACCESS read-only
			STATUS current
			DESCRIPTION
				"SIP Session Timer"
			::= { sleGponProfileVoIPDetailEntry 88 }


--  1.3.6.1.4.1.6296.101.23.5.5.5.1.1.89
		sleGponProfileVoIPDetailSIPSessionTimeout OBJECT-TYPE
			SYNTAX Integer32 (0..65535)
			MAX-ACCESS read-only
			STATUS current
			DESCRIPTION
				"SIP Session Timer Timeout"
			::= { sleGponProfileVoIPDetailEntry 89 }


--  1.3.6.1.4.1.6296.101.23.5.5.5.1.1.90
		sleGponProfileVoIPDetailSIPEndOfDigit OBJECT-TYPE
			SYNTAX INTEGER
				{
				disable(0),
				enable(1)
				}
			MAX-ACCESS read-only
			STATUS current
			DESCRIPTION
				"SIP End of Digit"
			::= { sleGponProfileVoIPDetailEntry 90 }


--  1.3.6.1.4.1.6296.101.23.5.5.5.1.1.91
		sleGponProfileVoIPDetailSIPEndSharpToken OBJECT-TYPE
			SYNTAX INTEGER
				{
				hex(0),
				ascii(1)
				}
			MAX-ACCESS read-only
			STATUS current
			DESCRIPTION
				"SIP End # Token"
			::= { sleGponProfileVoIPDetailEntry 91 }


--   1.3.6.1.4.1.6296.101.23.5.5.1.2
-- 1.3.6.1.4.1.6296.101.23.5.5.5.2
		sleGponProfileVoIPDetailControl OBJECT IDENTIFIER ::= { sleGponProfileVoIPDetail 2 }


--   1.3.6.1.4.1.6296.101.23.5.5.5.2.1
-- 1.3.6.1.4.1.6296.101.23.5.5.5.2.1
		sleGponProfileVoIPDetailControlRequest OBJECT-TYPE
			SYNTAX INTEGER
				{
				createProfile(1),
				destroylProfile(2),
				setFaxMode(3),
				setCodec1st(4),
				setCodec2nd(5),
				setCodec3rd(6),
				setCodec4th(7),
				setOobDtmf(8),
				setAnnouncementType(9),
				setJitterTarget(10),
				setJitterBuffMax(11),
				setEchoCancel(12),
				setPstnProto(13),
				setDtmfDigit(14),
				setHookFlashTimeMin(15),
				setHookFlashTimeMax(16),
				setSignalingCode(17),
				setRtpLocalPort(18),
				setRtpDscpMark(19),
				setRtpPiggybackEvent(20),
				setRtpToneEvent(21),
				setRtpDtmfEvent(22),
				setRtpCasEvent(23),
				setProtocol(24),
				setMgcPriServer(25),
				setMgcSecServer(26),
				setMgcVersion(27),
				setMgcFormat(28),
				setMgcMaxRetryTime(29),
				setMgcRetryAttempts(30),
				setMgcServiceChangeDelay(31),
				setMgcTerminationId(32),
				setMgcSoftswitch(33),
				setVoicemailServer(34),
				setVoicemailExpireTime(35),
				setReleaseTime(36),
				setRohTimer(37),
				setProxyServer(38),
				setOutboundProxyServer(39),
				setRegisterServer(40),
				setHostpartServer(41),
				setDns(42),
				setRegExpTime(43),
				setReregHeadStartTime(44),
				setSoftSwitch(45),
				setSipOptionTransmitCtl(46),
				setSipUriFormat(47),
				setCallerId(48),
				setCallWaiting(49),
				setCallProgressTransfer(50),
				setCallPresent(51),
				setDirectConnect(52),
				setDirectConnectUri(53),
				setBridgedLineAgentUri(54),
				setConferenceFactoryUri(55),
				setCancelCallWait(56),
				setCallHost(57),
				setCallPark(58),
				setCallerIdAct(59),
				setCallerIdDeact(60),
				setDoNotDisturbAct(61),
				setDoNotDisturbDeact(62),
				setDoNotDisturbPinChange(63),
				setEmergServiceNumber(64),
				setIntercomService(65),
				setDialPlanCritTimeOut(66),
				setDialPlanPartTimeOut(67),
				setDialPlanFormat(68),
				setSpecialLineService(69),
				setThreeWaySSWMixing(70),
				setDNSCachePolicy(71),
				setSIPTimer(72),
				setSessionTimer(73),
				setEndOfDigit(74),
				setEndSharpToken(75)
				}
			MAX-ACCESS read-write
			STATUS current
			DESCRIPTION
				"The request of a user command"
			::= { sleGponProfileVoIPDetailControl 1 }


--   1.3.6.1.4.1.6296.101.23.5.5.1.2.2
-- 1.3.6.1.4.1.6296.101.23.5.5.5.2.2
		sleGponProfileVoIPDetailControlStatus OBJECT-TYPE
			SYNTAX SleControlStatusType
			MAX-ACCESS read-only
			STATUS current
			DESCRIPTION
				"The status of user command"
			::= { sleGponProfileVoIPDetailControl 2 }


--   1.3.6.1.4.1.6296.101.23.5.5.1.2.3
-- 1.3.6.1.4.1.6296.101.23.5.5.5.2.3
		sleGponProfileVoIPDetailControlTimer OBJECT-TYPE
			SYNTAX Gauge32
			MAX-ACCESS read-write
			STATUS current
			DESCRIPTION
				"The maximum time for the manager for a long running user command"
			::= { sleGponProfileVoIPDetailControl 3 }


--   1.3.6.1.4.1.6296.101.23.5.5.1.2.4
-- 1.3.6.1.4.1.6296.101.23.5.5.5.2.4
		sleGponProfileVoIPDetailControlTimeStamp OBJECT-TYPE
			SYNTAX TimeTicks
			MAX-ACCESS read-only
			STATUS current
			DESCRIPTION
				"The time stamp of the last command(end of command)"
			::= { sleGponProfileVoIPDetailControl 4 }


--   1.3.6.1.4.1.6296.101.23.5.5.1.2.5
-- 1.3.6.1.4.1.6296.101.23.5.5.5.2.5
		sleGponProfileVoIPDetailControlReqResult OBJECT-TYPE
			SYNTAX SleControlRequestResultType
			MAX-ACCESS read-only
			STATUS current
			DESCRIPTION
				"The result of the last user command"
			::= { sleGponProfileVoIPDetailControl 5 }


--   1.3.6.1.4.1.6296.101.23.5.5.1.2.6
-- 1.3.6.1.4.1.6296.101.23.5.5.5.2.6
		sleGponProfileVoIPDetailControlIndex OBJECT-TYPE
			SYNTAX INTEGER (1..65535)
			MAX-ACCESS read-write
			STATUS current
			DESCRIPTION
				"VoIP Profile Index"
			::= { sleGponProfileVoIPDetailControl 6 }


--   1.3.6.1.4.1.6296.101.23.5.5.1.2.7
-- 1.3.6.1.4.1.6296.101.23.5.5.5.2.7
		sleGponProfileVoIPDetaiControllName OBJECT-TYPE
			SYNTAX OCTET STRING
			MAX-ACCESS read-write
			STATUS current
			DESCRIPTION
				"The VoIp profile name."
			::= { sleGponProfileVoIPDetailControl 7 }


--   1.3.6.1.4.1.6296.101.23.5.5.1.2.8
-- 1.3.6.1.4.1.6296.101.23.5.5.5.2.8
		sleGponProfileVoIPDetailControlFaxMode OBJECT-TYPE
			SYNTAX INTEGER
				{
				passthru(0),
				t38(1)
				}
			MAX-ACCESS read-write
			STATUS current
			DESCRIPTION
				"VoIP fax mode."
			::= { sleGponProfileVoIPDetailControl 8 }


--  1.3.6.1.4.1.6296.101.23.5.5.5.2.9
		sleGponProfileVoIPDetailControlCodecType1st OBJECT-TYPE
			SYNTAX INTEGER
				{
				pcmu(0),
				gsm(3),
				g723(4),
				dvi4and8k(5),
				dvi4and16k(6),
				lpc(7),
				pcma(8),
				g722(9),
				l16and2ch(10),
				l16and1h(11),
				qcelp(12),
				cn(13),
				mpa(14),
				g728(15),
				dvi4and11k(16),
				dvi4and22k(17),
				g729(18)
				}
			MAX-ACCESS read-write
			STATUS current
			DESCRIPTION
				"Codec type 1st"
			::= { sleGponProfileVoIPDetailControl 9 }


--  1.3.6.1.4.1.6296.101.23.5.5.5.2.10
		sleGponProfileVoIPDetailControlCodecPeriod1st OBJECT-TYPE
			SYNTAX INTEGER (1..65535)
			MAX-ACCESS read-write
			STATUS current
			DESCRIPTION
				"Packet Period Selection
				<10-30> ms (default 10ms)"
			::= { sleGponProfileVoIPDetailControl 10 }


--  1.3.6.1.4.1.6296.101.23.5.5.5.2.11
		sleGponProfileVoIPDetailControlCodecSilenceSuppression1st OBJECT-TYPE
			SYNTAX INTEGER (1..65535)
			MAX-ACCESS read-write
			STATUS current
			DESCRIPTION
				"Silence Suppression
				(0:off 1:on)"
			::= { sleGponProfileVoIPDetailControl 11 }


--  1.3.6.1.4.1.6296.101.23.5.5.5.2.12
		sleGponProfileVoIPDetailControlCodecType2nd OBJECT-TYPE
			SYNTAX INTEGER
				{
				pcmu(0),
				gsm(3),
				g723(4),
				dvi4and8k(5),
				dvi4and16k(6),
				lpc(7),
				pcma(8),
				g722(9),
				l16and2ch(10),
				l16and1h(11),
				qcelp(12),
				cn(13),
				mpa(14),
				g728(15),
				dvi4and11k(16),
				dvi4and22k(17),
				g729(18)
				}
			MAX-ACCESS read-write
			STATUS current
			DESCRIPTION
				"Codec type 2nd "
			::= { sleGponProfileVoIPDetailControl 12 }


--  1.3.6.1.4.1.6296.101.23.5.5.5.2.13
		sleGponProfileVoIPDetailControlCodecPeriod2nd OBJECT-TYPE
			SYNTAX INTEGER (1..65535)
			MAX-ACCESS read-write
			STATUS current
			DESCRIPTION
				"Packet Period Selection
				<10-30> ms (default 10ms)
				"
			::= { sleGponProfileVoIPDetailControl 13 }


--  1.3.6.1.4.1.6296.101.23.5.5.5.2.14
		sleGponProfileVoIPDetailControlCodecSilenceSuppression2nd OBJECT-TYPE
			SYNTAX INTEGER (1..65535)
			MAX-ACCESS read-write
			STATUS current
			DESCRIPTION
				"Silence Suppression
				(0:off 1:on)"
			::= { sleGponProfileVoIPDetailControl 14 }


--  1.3.6.1.4.1.6296.101.23.5.5.5.2.15
		sleGponProfileVoIPDetailControlCodecType3rd OBJECT-TYPE
			SYNTAX INTEGER
				{
				pcmu(0),
				gsm(3),
				g723(4),
				dvi4and8k(5),
				dvi4and16k(6),
				lpc(7),
				pcma(8),
				g722(9),
				l16and2ch(10),
				l16and1h(11),
				qcelp(12),
				cn(13),
				mpa(14),
				g728(15),
				dvi4and11k(16),
				dvi4and22k(17),
				g729(18)
				}
			MAX-ACCESS read-write
			STATUS current
			DESCRIPTION
				"Codec type 3rd"
			::= { sleGponProfileVoIPDetailControl 15 }


--  1.3.6.1.4.1.6296.101.23.5.5.5.2.16
		sleGponProfileVoIPDetailControlCodecPeriod3rd OBJECT-TYPE
			SYNTAX INTEGER (1..65535)
			MAX-ACCESS read-write
			STATUS current
			DESCRIPTION
				"Packet Period Selection
				<10-30> ms (default 10ms)"
			::= { sleGponProfileVoIPDetailControl 16 }


--  1.3.6.1.4.1.6296.101.23.5.5.5.2.17
		sleGponProfileVoIPDetailControlCodecSilenceSuppression3rd OBJECT-TYPE
			SYNTAX INTEGER (1..65535)
			MAX-ACCESS read-write
			STATUS current
			DESCRIPTION
				"Silence Suppression
				(0:off 1:on)"
			::= { sleGponProfileVoIPDetailControl 17 }


--  1.3.6.1.4.1.6296.101.23.5.5.5.2.18
		sleGponProfileVoIPDetailControlCodecType4th OBJECT-TYPE
			SYNTAX INTEGER
				{
				pcmu(0),
				gsm(3),
				g723(4),
				dvi4and8k(5),
				dvi4and16k(6),
				lpc(7),
				pcma(8),
				g722(9),
				l16and2ch(10),
				l16and1h(11),
				qcelp(12),
				cn(13),
				mpa(14),
				g728(15),
				dvi4and11k(16),
				dvi4and22k(17),
				g729(18)
				}
			MAX-ACCESS read-write
			STATUS current
			DESCRIPTION
				"Codec type 4th"
			::= { sleGponProfileVoIPDetailControl 18 }


--  1.3.6.1.4.1.6296.101.23.5.5.5.2.19
		sleGponProfileVoIPDetailCodecControlPeriod4th OBJECT-TYPE
			SYNTAX INTEGER (1..65535)
			MAX-ACCESS read-write
			STATUS current
			DESCRIPTION
				"Packet Period Selection
				<10-30> ms (default 10ms)"
			::= { sleGponProfileVoIPDetailControl 19 }


--  1.3.6.1.4.1.6296.101.23.5.5.5.2.20
		sleGponProfileVoIPDetailControlCodecSilenceSuppression4th OBJECT-TYPE
			SYNTAX INTEGER (1..65535)
			MAX-ACCESS read-write
			STATUS current
			DESCRIPTION
				"Silence Suppression
				(0:off 1:on)"
			::= { sleGponProfileVoIPDetailControl 20 }


--   1.3.6.1.4.1.6296.101.23.5.5.1.2.13
-- 1.3.6.1.4.1.6296.101.23.5.5.5.2.21
		sleGponProfileVoIPDetailControlOobdtmf OBJECT-TYPE
			SYNTAX INTEGER
				{
				disable(0),
				enable(1)
				}
			MAX-ACCESS read-write
			STATUS current
			DESCRIPTION
				"Out-of-band DMTF"
			::= { sleGponProfileVoIPDetailControl 21 }


--   1.3.6.1.4.1.6296.101.23.5.5.1.2.14
-- 1.3.6.1.4.1.6296.101.23.5.5.5.2.22
		sleGponProfileVoIPDetailControlAnnouncementType OBJECT-TYPE
			SYNTAX INTEGER
				{
				silence(1),
				reorderTone(2),
				fastBusy(3),
				voiceAnnouncement(4)
				}
			MAX-ACCESS read-write
			STATUS current
			DESCRIPTION
				"Announcement Type"
			::= { sleGponProfileVoIPDetailControl 22 }


--   1.3.6.1.4.1.6296.101.23.5.5.1.2.15
-- 1.3.6.1.4.1.6296.101.23.5.5.5.2.23
		sleGponProfileVoIPDetailControlJitterTarget OBJECT-TYPE
			SYNTAX INTEGER (1..65535)
			MAX-ACCESS read-write
			STATUS current
			DESCRIPTION
				"Jitter target (milliseconds)"
			::= { sleGponProfileVoIPDetailControl 23 }


--   1.3.6.1.4.1.6296.101.23.5.5.1.2.16
-- 1.3.6.1.4.1.6296.101.23.5.5.5.2.24
		sleGponProfileVoIPDetailControlJitterBuffMax OBJECT-TYPE
			SYNTAX INTEGER (0..65535)
			MAX-ACCESS read-write
			STATUS current
			DESCRIPTION
				"Jitter Buffer Max"
			::= { sleGponProfileVoIPDetailControl 24 }


--   1.3.6.1.4.1.6296.101.23.5.5.1.2.16
-- 1.3.6.1.4.1.6296.101.23.5.5.5.2.25
		sleGponProfileVoIPDetailControlEchoCancel OBJECT-TYPE
			SYNTAX INTEGER
				{
				false(0),
				ture(1)
				}
			MAX-ACCESS read-write
			STATUS current
			DESCRIPTION
				"Echo cancellation"
			::= { sleGponProfileVoIPDetailControl 25 }


--   1.3.6.1.4.1.6296.101.23.5.5.1.2.16
-- 1.3.6.1.4.1.6296.101.23.5.5.5.2.26
		sleGponProfileVoIPDetailControlPstnProtoVariant OBJECT-TYPE
			SYNTAX INTEGER (1..65535)
			MAX-ACCESS read-write
			STATUS current
			DESCRIPTION
				"PSTN Protocol Variant"
			::= { sleGponProfileVoIPDetailControl 26 }


--   1.3.6.1.4.1.6296.101.23.5.5.1.2.16
-- 1.3.6.1.4.1.6296.101.23.5.5.5.2.27
		sleGponProfileVoIPDetailControlDtmfDigitLevels OBJECT-TYPE
			SYNTAX INTEGER (0..65535)
			MAX-ACCESS read-write
			STATUS current
			DESCRIPTION
				"DTMF digit Power Level configuration "
			::= { sleGponProfileVoIPDetailControl 27 }


--   1.3.6.1.4.1.6296.101.23.5.5.1.2.16
-- 1.3.6.1.4.1.6296.101.23.5.5.5.2.28
		sleGponProfileVoIPDetailControlDtmfDigitDuration OBJECT-TYPE
			SYNTAX INTEGER (0..65535)
			MAX-ACCESS read-write
			STATUS current
			DESCRIPTION
				"DTMF digit Power Duration configuration"
			::= { sleGponProfileVoIPDetailControl 28 }


--   1.3.6.1.4.1.6296.101.23.5.5.1.2.16
-- 1.3.6.1.4.1.6296.101.23.5.5.5.2.29
		sleGponProfileVoIPDetailControlHookFlashTimeMin OBJECT-TYPE
			SYNTAX INTEGER (0..65535)
			MAX-ACCESS read-write
			STATUS current
			DESCRIPTION
				"Hook Flash Duration Min"
			::= { sleGponProfileVoIPDetailControl 29 }


--   1.3.6.1.4.1.6296.101.23.5.5.1.2.16
-- 1.3.6.1.4.1.6296.101.23.5.5.5.2.30
		sleGponProfileVoIPDetailControlHookFlashTimeMax OBJECT-TYPE
			SYNTAX INTEGER (0..65535)
			MAX-ACCESS read-write
			STATUS current
			DESCRIPTION
				"Hook Flash Duration Max"
			::= { sleGponProfileVoIPDetailControl 30 }


--   1.3.6.1.4.1.6296.101.23.5.5.1.2.16
-- 1.3.6.1.4.1.6296.101.23.5.5.5.2.31
		sleGponProfileVoIPDetailControlSignalingCode OBJECT-TYPE
			SYNTAX INTEGER
				{
				loopStart(1),
				groundStart(2),
				loopReverseBattery(3),
				coinFirst(4),
				dialToneFirst(5),
				multiParty(6)
				}
			MAX-ACCESS read-write
			STATUS current
			DESCRIPTION
				"POTS-side Signalling"
			::= { sleGponProfileVoIPDetailControl 31 }


--   1.3.6.1.4.1.6296.101.23.5.5.1.2.16
-- 1.3.6.1.4.1.6296.101.23.5.5.5.2.32
		sleGponProfileVoIPDetailControlRtpLocalPortMin OBJECT-TYPE
			SYNTAX INTEGER (1..65535)
			MAX-ACCESS read-write
			STATUS current
			DESCRIPTION
				"RTP Local Port Min"
			::= { sleGponProfileVoIPDetailControl 32 }


--   1.3.6.1.4.1.6296.101.23.5.5.1.2.16
-- 1.3.6.1.4.1.6296.101.23.5.5.5.2.33
		sleGponProfileVoIPDetailControlRtpLocalPortMax OBJECT-TYPE
			SYNTAX INTEGER (1..65535)
			MAX-ACCESS read-write
			STATUS current
			DESCRIPTION
				"RTP Local Port Max"
			::= { sleGponProfileVoIPDetailControl 33 }


--   1.3.6.1.4.1.6296.101.23.5.5.1.2.16
-- 1.3.6.1.4.1.6296.101.23.5.5.5.2.34
		sleGponProfileVoIPDetailControlRtpDscpMark OBJECT-TYPE
			SYNTAX INTEGER (1..65535)
			MAX-ACCESS read-write
			STATUS current
			DESCRIPTION
				"RTP DSCP Mark"
			::= { sleGponProfileVoIPDetailControl 34 }


--   1.3.6.1.4.1.6296.101.23.5.5.1.2.16
-- 1.3.6.1.4.1.6296.101.23.5.5.5.2.35
		sleGponProfileVoIPDetailControlRtpPiggybackEvent OBJECT-TYPE
			SYNTAX INTEGER
				{
				disable(0),
				enable(1)
				}
			MAX-ACCESS read-write
			STATUS current
			DESCRIPTION
				"RTP Piggyback event"
			::= { sleGponProfileVoIPDetailControl 35 }


--   1.3.6.1.4.1.6296.101.23.5.5.1.2.16
-- 1.3.6.1.4.1.6296.101.23.5.5.5.2.36
		sleGponProfileVoIPDetailControlRtpToneEvent OBJECT-TYPE
			SYNTAX INTEGER
				{
				disable(0),
				enable(1)
				}
			MAX-ACCESS read-write
			STATUS current
			DESCRIPTION
				"RTP Tone event"
			::= { sleGponProfileVoIPDetailControl 36 }


--   1.3.6.1.4.1.6296.101.23.5.5.1.2.16
-- 1.3.6.1.4.1.6296.101.23.5.5.5.2.37
		sleGponProfileVoIPDetailControlRtpDtmfEvent OBJECT-TYPE
			SYNTAX INTEGER
				{
				disable(0),
				enable(1)
				}
			MAX-ACCESS read-write
			STATUS current
			DESCRIPTION
				"RTP DTMF event"
			::= { sleGponProfileVoIPDetailControl 37 }


--   1.3.6.1.4.1.6296.101.23.5.5.1.2.16
-- 1.3.6.1.4.1.6296.101.23.5.5.5.2.38
		sleGponProfileVoIPDetailControlRtpCasEvent OBJECT-TYPE
			SYNTAX INTEGER
				{
				disable(0),
				enable(1)
				}
			MAX-ACCESS read-write
			STATUS current
			DESCRIPTION
				"The status of RTP CAS event"
			::= { sleGponProfileVoIPDetailControl 38 }


--   1.3.6.1.4.1.6296.101.23.5.5.1.2.16
-- 1.3.6.1.4.1.6296.101.23.5.5.5.2.39
		sleGponProfileVoIPDetailControlProtocol OBJECT-TYPE
			SYNTAX INTEGER
				{
				none(0),
				sip(1),
				h248(2),
				mgcp(3)
				}
			MAX-ACCESS read-write
			STATUS current
			DESCRIPTION
				"VoIP Protocol configuration"
			::= { sleGponProfileVoIPDetailControl 39 }


--   1.3.6.1.4.1.6296.101.23.5.5.1.2.16
-- 1.3.6.1.4.1.6296.101.23.5.5.5.2.40
		sleGponProfileVoIPDetailControlMgcPriServer OBJECT-TYPE
			SYNTAX OCTET STRING
			MAX-ACCESS read-write
			STATUS current
			DESCRIPTION
				"The primary server name."
			::= { sleGponProfileVoIPDetailControl 40 }


--   1.3.6.1.4.1.6296.101.23.5.5.1.2.16
-- 1.3.6.1.4.1.6296.101.23.5.5.5.2.41
		sleGponProfileVoIPDetailControlMgcSecServer OBJECT-TYPE
			SYNTAX OCTET STRING
			MAX-ACCESS read-write
			STATUS current
			DESCRIPTION
				"The secondary server name."
			::= { sleGponProfileVoIPDetailControl 41 }


--   1.3.6.1.4.1.6296.101.23.5.5.1.2.16
-- 1.3.6.1.4.1.6296.101.23.5.5.5.2.42
		sleGponProfileVoIPDetailControlMgcMsgVersion OBJECT-TYPE
			SYNTAX INTEGER (1..255)
			MAX-ACCESS read-write
			STATUS current
			DESCRIPTION
				"The message version."
			::= { sleGponProfileVoIPDetailControl 42 }


--   1.3.6.1.4.1.6296.101.23.5.5.1.2.16
-- 1.3.6.1.4.1.6296.101.23.5.5.5.2.43
		sleGponProfileVoIPDetailControlMgcMsgFormat OBJECT-TYPE
			SYNTAX INTEGER
				{
				textLong(0),
				textShort(1),
				binary(2)
				}
			MAX-ACCESS read-write
			STATUS current
			DESCRIPTION
				"The message format."
			::= { sleGponProfileVoIPDetailControl 43 }


--   1.3.6.1.4.1.6296.101.23.5.5.1.2.16
-- 1.3.6.1.4.1.6296.101.23.5.5.5.2.44
		sleGponProfileVoIPDetailControlMgcMaxRetryTime OBJECT-TYPE
			SYNTAX INTEGER (0..65535)
			MAX-ACCESS read-write
			STATUS current
			DESCRIPTION
				"The max retry time.
				65535: unused"
			::= { sleGponProfileVoIPDetailControl 44 }


--   1.3.6.1.4.1.6296.101.23.5.5.1.2.16
-- 1.3.6.1.4.1.6296.101.23.5.5.5.2.45
		sleGponProfileVoIPDetailControlMgcMaxRetryAttempts OBJECT-TYPE
			SYNTAX INTEGER (0..65535)
			MAX-ACCESS read-write
			STATUS current
			DESCRIPTION
				"The max retry attemption
				65535: unused"
			::= { sleGponProfileVoIPDetailControl 45 }


--   1.3.6.1.4.1.6296.101.23.5.5.1.2.16
-- 1.3.6.1.4.1.6296.101.23.5.5.5.2.46
		sleGponProfileVoIPDetailControlMgcSvcChangeDelay OBJECT-TYPE
			SYNTAX INTEGER (0..65535)
			MAX-ACCESS read-write
			STATUS current
			DESCRIPTION
				"The service change delay
				65535: unused"
			::= { sleGponProfileVoIPDetailControl 46 }


--   1.3.6.1.4.1.6296.101.23.5.5.1.2.16
-- 1.3.6.1.4.1.6296.101.23.5.5.5.2.47
		sleGponProfileVoIPDetailControlMgcTerminationId OBJECT-TYPE
			SYNTAX OCTET STRING
			MAX-ACCESS read-write
			STATUS current
			DESCRIPTION
				"The termination id."
			::= { sleGponProfileVoIPDetailControl 47 }


--   1.3.6.1.4.1.6296.101.23.5.5.1.2.16
-- 1.3.6.1.4.1.6296.101.23.5.5.5.2.48
		sleGponProfileVoIPDetailControlMgcSoftswitch OBJECT-TYPE
			SYNTAX OCTET STRING
			MAX-ACCESS read-write
			STATUS current
			DESCRIPTION
				"The soft switch"
			::= { sleGponProfileVoIPDetailControl 48 }


--   1.3.6.1.4.1.6296.101.23.5.5.1.2.16
-- 1.3.6.1.4.1.6296.101.23.5.5.5.2.49
		sleGponProfileVoIPDetailControlVoicemailServer OBJECT-TYPE
			SYNTAX OCTET STRING
			MAX-ACCESS read-write
			STATUS current
			DESCRIPTION
				"Voicemail server SIP URI"
			::= { sleGponProfileVoIPDetailControl 49 }


--   1.3.6.1.4.1.6296.101.23.5.5.1.2.16
-- 1.3.6.1.4.1.6296.101.23.5.5.5.2.50
		sleGponProfileVoIPDetailControlVoicemmailExpireTime OBJECT-TYPE
			SYNTAX INTEGER (1..65535)
			MAX-ACCESS read-write
			STATUS current
			DESCRIPTION
				"Voicemail Subscription Expiration Time"
			::= { sleGponProfileVoIPDetailControl 50 }


--   1.3.6.1.4.1.6296.101.23.5.5.1.2.16
-- 1.3.6.1.4.1.6296.101.23.5.5.5.2.51
		sleGponProfileVoIPDetailControlReleaseTime OBJECT-TYPE
			SYNTAX INTEGER (1..65535)
			MAX-ACCESS read-write
			STATUS current
			DESCRIPTION
				"Release timer"
			::= { sleGponProfileVoIPDetailControl 51 }


--   1.3.6.1.4.1.6296.101.23.5.5.1.2.16
-- 1.3.6.1.4.1.6296.101.23.5.5.5.2.52
		sleGponProfileVoIPDetailControlRohTimer OBJECT-TYPE
			SYNTAX INTEGER (1..65535)
			MAX-ACCESS read-write
			STATUS current
			DESCRIPTION
				"ROH timer"
			::= { sleGponProfileVoIPDetailControl 52 }


--   1.3.6.1.4.1.6296.101.23.5.5.1.2.16
-- 1.3.6.1.4.1.6296.101.23.5.5.5.2.53
		sleGponProfileVoIPDetailControlProxyServer OBJECT-TYPE
			SYNTAX OCTET STRING
			MAX-ACCESS read-write
			STATUS current
			DESCRIPTION
				"Proxy server address"
			::= { sleGponProfileVoIPDetailControl 53 }


--   1.3.6.1.4.1.6296.101.23.5.5.1.2.16
-- 1.3.6.1.4.1.6296.101.23.5.5.5.2.54
		sleGponProfileVoIPDetailControlOutboundProxyServer OBJECT-TYPE
			SYNTAX OCTET STRING
			MAX-ACCESS read-write
			STATUS current
			DESCRIPTION
				"Outbound proxy address"
			::= { sleGponProfileVoIPDetailControl 54 }


--   1.3.6.1.4.1.6296.101.23.5.5.1.2.16
-- 1.3.6.1.4.1.6296.101.23.5.5.5.2.55
		sleGponProfileVoIPDetailControlRegisterServer OBJECT-TYPE
			SYNTAX OCTET STRING
			MAX-ACCESS read-write
			STATUS current
			DESCRIPTION
				"Registrar server address"
			::= { sleGponProfileVoIPDetailControl 55 }


--   1.3.6.1.4.1.6296.101.23.5.5.1.2.16
-- 1.3.6.1.4.1.6296.101.23.5.5.5.2.56
		sleGponProfileVoIPDetailControlHostPartServer OBJECT-TYPE
			SYNTAX OCTET STRING
			MAX-ACCESS read-write
			STATUS current
			DESCRIPTION
				"Host part server address"
			::= { sleGponProfileVoIPDetailControl 56 }


--   1.3.6.1.4.1.6296.101.23.5.5.1.2.16
-- 1.3.6.1.4.1.6296.101.23.5.5.5.2.57
		sleGponProfileVoIPDetailControlPriDns OBJECT-TYPE
			SYNTAX IpAddress
			MAX-ACCESS read-write
			STATUS current
			DESCRIPTION
				"Primary DNS Server"
			::= { sleGponProfileVoIPDetailControl 57 }


--   1.3.6.1.4.1.6296.101.23.5.5.1.2.16
-- 1.3.6.1.4.1.6296.101.23.5.5.5.2.58
		sleGponProfileVoIPDetailControlSecDns OBJECT-TYPE
			SYNTAX IpAddress
			MAX-ACCESS read-write
			STATUS current
			DESCRIPTION
				"Secondary DNS Server"
			::= { sleGponProfileVoIPDetailControl 58 }


--   1.3.6.1.4.1.6296.101.23.5.5.1.2.16
-- 1.3.6.1.4.1.6296.101.23.5.5.5.2.59
		sleGponProfileVoIPDetailControlRegExpTime OBJECT-TYPE
			SYNTAX INTEGER (1..65535)
			MAX-ACCESS read-write
			STATUS current
			DESCRIPTION
				"Registration expiration time"
			::= { sleGponProfileVoIPDetailControl 59 }


--   1.3.6.1.4.1.6296.101.23.5.5.1.2.16
-- 1.3.6.1.4.1.6296.101.23.5.5.5.2.60
		sleGponProfileVoIPDetailControlReregHeadStartTime OBJECT-TYPE
			SYNTAX INTEGER (1..65535)
			MAX-ACCESS read-write
			STATUS current
			DESCRIPTION
				"Registration head start time"
			::= { sleGponProfileVoIPDetailControl 60 }


--   1.3.6.1.4.1.6296.101.23.5.5.1.2.16
-- 1.3.6.1.4.1.6296.101.23.5.5.5.2.61
		sleGponProfileVoIPDetailControlSoftSwitchVendor OBJECT-TYPE
			SYNTAX OCTET STRING
			MAX-ACCESS read-write
			STATUS current
			DESCRIPTION
				"Softswitch Vendor name"
			::= { sleGponProfileVoIPDetailControl 61 }


--   1.3.6.1.4.1.6296.101.23.5.5.1.2.16
-- 1.3.6.1.4.1.6296.101.23.5.5.5.2.62
		sleGponProfileVoIPDetailControlSipOptionTransmitCtl OBJECT-TYPE
			SYNTAX INTEGER
				{
				disable(0),
				enable(1)
				}
			MAX-ACCESS read-write
			STATUS current
			DESCRIPTION
				"Transmit control"
			::= { sleGponProfileVoIPDetailControl 62 }


--   1.3.6.1.4.1.6296.101.23.5.5.1.2.16
-- 1.3.6.1.4.1.6296.101.23.5.5.5.2.63
		sleGponProfileVoIPDetailControlSipUriFormat OBJECT-TYPE
			SYNTAX INTEGER
				{
				telUri(0),
				sipUri(1)
				}
			MAX-ACCESS read-write
			STATUS current
			DESCRIPTION
				"URI format"
			::= { sleGponProfileVoIPDetailControl 63 }


--   1.3.6.1.4.1.6296.101.23.5.5.1.2.16
-- 1.3.6.1.4.1.6296.101.23.5.5.5.2.64
		sleGponProfileVoIPDetailControlCallerId OBJECT-TYPE
			SYNTAX BITS
				{
				callNumber(0),
				callName(1),
				cidBlocking(2),
				cidNumber(3),
				cidName(4),
				acr(5)
				}
			MAX-ACCESS read-write
			STATUS current
			DESCRIPTION
				"Caller ID feature"
			::= { sleGponProfileVoIPDetailControl 64 }


--   1.3.6.1.4.1.6296.101.23.5.5.1.2.16
-- 1.3.6.1.4.1.6296.101.23.5.5.5.2.65
		sleGponProfileVoIPDetailControlCallWaiting OBJECT-TYPE
			SYNTAX BITS
				{
				callFeature(0),
				cidAnnounce(1)
				}
			MAX-ACCESS read-write
			STATUS current
			DESCRIPTION
				"Call waiting features"
			::= { sleGponProfileVoIPDetailControl 65 }


--   1.3.6.1.4.1.6296.101.23.5.5.1.2.16
-- 1.3.6.1.4.1.6296.101.23.5.5.5.2.66
		sleGponProfileVoIPDetailControlCallProgressTransfer OBJECT-TYPE
			SYNTAX BITS
				{
				threeWay(0),
				callTransfer(1),
				callHold(2),
				callPark(3),
				notDisturb(4),
				flashEmergCall(5),
				emergOriginatingHold(6)
				}
			MAX-ACCESS read-write
			STATUS current
			DESCRIPTION
				"Call progress or transfer features"
			::= { sleGponProfileVoIPDetailControl 66 }


--   1.3.6.1.4.1.6296.101.23.5.5.1.2.16
-- 1.3.6.1.4.1.6296.101.23.5.5.5.2.67
		sleGponProfileVoIPDetailControlCallPresent OBJECT-TYPE
			SYNTAX BITS
				{
				splashRing(0),
				dialTone(1),
				visualIndicate(2),
				callForward(3)
				}
			MAX-ACCESS read-write
			STATUS current
			DESCRIPTION
				"Call presentation features"
			::= { sleGponProfileVoIPDetailControl 67 }


--   1.3.6.1.4.1.6296.101.23.5.5.1.2.16
-- 1.3.6.1.4.1.6296.101.23.5.5.5.2.68
		sleGponProfileVoIPDetailControlDirectConnect OBJECT-TYPE
			SYNTAX INTEGER
				{
				disable(0),
				enable(1),
				delayOption(2)
				}
			MAX-ACCESS read-write
			STATUS current
			DESCRIPTION
				"Direct connect feature"
			::= { sleGponProfileVoIPDetailControl 68 }


--   1.3.6.1.4.1.6296.101.23.5.5.1.2.16
-- 1.3.6.1.4.1.6296.101.23.5.5.5.2.69
		sleGponProfileVoIPDetailControlDirectConnectUri OBJECT-TYPE
			SYNTAX OCTET STRING
			MAX-ACCESS read-write
			STATUS current
			DESCRIPTION
				"Direct connect URI"
			::= { sleGponProfileVoIPDetailControl 69 }


--   1.3.6.1.4.1.6296.101.23.5.5.1.2.16
-- 1.3.6.1.4.1.6296.101.23.5.5.5.2.70
		sleGponProfileVoIPDetailControlBridgedLineAgentUri OBJECT-TYPE
			SYNTAX OCTET STRING
			MAX-ACCESS read-write
			STATUS current
			DESCRIPTION
				"Bridged line agent URI"
			::= { sleGponProfileVoIPDetailControl 70 }


--   1.3.6.1.4.1.6296.101.23.5.5.1.2.16
-- 1.3.6.1.4.1.6296.101.23.5.5.5.2.71
		sleGponProfileVoIPDetailControlConferenceFactoryUri OBJECT-TYPE
			SYNTAX OCTET STRING
			MAX-ACCESS read-write
			STATUS current
			DESCRIPTION
				"Conference factory URI"
			::= { sleGponProfileVoIPDetailControl 71 }


--   1.3.6.1.4.1.6296.101.23.5.5.1.2.16
-- 1.3.6.1.4.1.6296.101.23.5.5.5.2.72
		sleGponProfileVoIPDetailControlCancelCallWait OBJECT-TYPE
			SYNTAX OCTET STRING
			MAX-ACCESS read-write
			STATUS current
			DESCRIPTION
				"Cancel call waiting"
			::= { sleGponProfileVoIPDetailControl 72 }


--   1.3.6.1.4.1.6296.101.23.5.5.1.2.16
-- 1.3.6.1.4.1.6296.101.23.5.5.5.2.73
		sleGponProfileVoIPDetailControlCallHold OBJECT-TYPE
			SYNTAX OCTET STRING
			MAX-ACCESS read-write
			STATUS current
			DESCRIPTION
				"Call hold"
			::= { sleGponProfileVoIPDetailControl 73 }


--   1.3.6.1.4.1.6296.101.23.5.5.1.2.16
-- 1.3.6.1.4.1.6296.101.23.5.5.5.2.74
		sleGponProfileVoIPDetailControlCallPark OBJECT-TYPE
			SYNTAX OCTET STRING
			MAX-ACCESS read-write
			STATUS current
			DESCRIPTION
				"Call park"
			::= { sleGponProfileVoIPDetailControl 74 }


--   1.3.6.1.4.1.6296.101.23.5.5.1.2.16
-- 1.3.6.1.4.1.6296.101.23.5.5.5.2.75
		sleGponProfileVoIPDetailControlCallerIdAct OBJECT-TYPE
			SYNTAX OCTET STRING
			MAX-ACCESS read-write
			STATUS current
			DESCRIPTION
				"Caller ID activate"
			::= { sleGponProfileVoIPDetailControl 75 }


--   1.3.6.1.4.1.6296.101.23.5.5.1.2.16
-- 1.3.6.1.4.1.6296.101.23.5.5.5.2.76
		sleGponProfileVoIPDetailControlCallerIdDeact OBJECT-TYPE
			SYNTAX OCTET STRING
			MAX-ACCESS read-write
			STATUS current
			DESCRIPTION
				"Caller ID deactivate"
			::= { sleGponProfileVoIPDetailControl 76 }


--   1.3.6.1.4.1.6296.101.23.5.5.1.2.16
-- 1.3.6.1.4.1.6296.101.23.5.5.5.2.77
		sleGponProfileVoIPDetailControlDoNotDisturbAct OBJECT-TYPE
			SYNTAX OCTET STRING
			MAX-ACCESS read-write
			STATUS current
			DESCRIPTION
				"Do not disturb activation"
			::= { sleGponProfileVoIPDetailControl 77 }


--   1.3.6.1.4.1.6296.101.23.5.5.1.2.16
-- 1.3.6.1.4.1.6296.101.23.5.5.5.2.78
		sleGponProfileVoIPDetailControlDoNotDisturbDeact OBJECT-TYPE
			SYNTAX OCTET STRING
			MAX-ACCESS read-write
			STATUS current
			DESCRIPTION
				"Do not disturb deactivation"
			::= { sleGponProfileVoIPDetailControl 78 }


--   1.3.6.1.4.1.6296.101.23.5.5.1.2.16
-- 1.3.6.1.4.1.6296.101.23.5.5.5.2.79
		sleGponProfileVoIPDetailControlDoNotDisturbPinChange OBJECT-TYPE
			SYNTAX OCTET STRING
			MAX-ACCESS read-write
			STATUS current
			DESCRIPTION
				"Do not disturb PIN change"
			::= { sleGponProfileVoIPDetailControl 79 }


--   1.3.6.1.4.1.6296.101.23.5.5.1.2.16
-- 1.3.6.1.4.1.6296.101.23.5.5.5.2.80
		sleGponProfileVoIPDetailControlEmergServiceNumber OBJECT-TYPE
			SYNTAX OCTET STRING
			MAX-ACCESS read-write
			STATUS current
			DESCRIPTION
				"Emergency service number"
			::= { sleGponProfileVoIPDetailControl 80 }


--   1.3.6.1.4.1.6296.101.23.5.5.1.2.16
-- 1.3.6.1.4.1.6296.101.23.5.5.5.2.81
		sleGponProfileVoIPDetailControlIntercomService OBJECT-TYPE
			SYNTAX OCTET STRING
			MAX-ACCESS read-write
			STATUS current
			DESCRIPTION
				"Intercom service"
			::= { sleGponProfileVoIPDetailControl 81 }


--  1.3.6.1.4.1.6296.101.23.5.5.5.2.82
		sleGponProfileVoIPDetailControlDialplanCritTimeout OBJECT-TYPE
			SYNTAX INTEGER (0..65535)
			MAX-ACCESS read-write
			STATUS current
			DESCRIPTION
				"dial-plan crit-timeout TIMEOUT (ms)"
			::= { sleGponProfileVoIPDetailControl 82 }


--  1.3.6.1.4.1.6296.101.23.5.5.5.2.83
		sleGponProfileVoIPDetailControlDialplanPartTimeout OBJECT-TYPE
			SYNTAX INTEGER (0..65535)
			MAX-ACCESS read-write
			STATUS current
			DESCRIPTION
				"dial-plan part-timeout TIMEOUT (ms)"
			::= { sleGponProfileVoIPDetailControl 83 }


--  1.3.6.1.4.1.6296.101.23.5.5.5.2.84
		sleGponProfileVoIPDetailControlDialplanFormat OBJECT-TYPE
			SYNTAX INTEGER
				{
				h248(1),
				nsc(2),
				vendor(3)
				}
			MAX-ACCESS read-write
			STATUS current
			DESCRIPTION
				"dial-plan format (h248|nsc|vendor)"
			::= { sleGponProfileVoIPDetailControl 84 }


--  1.3.6.1.4.1.6296.101.23.5.5.5.2.85
		sleGponProfileVoIPDetailControlSpecialLineService OBJECT-TYPE
			SYNTAX INTEGER
				{
				disable(0),
				enableHotLine(1),
				enableWarmLine(2)
				}
			MAX-ACCESS read-write
			STATUS current
			DESCRIPTION
				"Special Line Service"
			::= { sleGponProfileVoIPDetailControl 85 }


--  1.3.6.1.4.1.6296.101.23.5.5.5.2.86
		sleGponProfileVoIPDetailControlWarmLineTimeout OBJECT-TYPE
			SYNTAX Integer32 (0..30)
			MAX-ACCESS read-write
			STATUS current
			DESCRIPTION
				"Warm Line Waiting Time"
			::= { sleGponProfileVoIPDetailControl 86 }


--  1.3.6.1.4.1.6296.101.23.5.5.5.2.87
		sleGponProfileVoIPDetailControlLineNumber OBJECT-TYPE
			SYNTAX OCTET STRING
			MAX-ACCESS read-write
			STATUS current
			DESCRIPTION
				"Special Line Number"
			::= { sleGponProfileVoIPDetailControl 87 }


--  1.3.6.1.4.1.6296.101.23.5.5.5.2.88
		sleGponProfileVoIPDetailControlThreeWaySSWMixing OBJECT-TYPE
			SYNTAX INTEGER
				{
				server(0),
				client(1)
				}
			MAX-ACCESS read-write
			STATUS current
			DESCRIPTION
				"3Way Call Voice Mixing"
			::= { sleGponProfileVoIPDetailControl 88 }


--  1.3.6.1.4.1.6296.101.23.5.5.5.2.89
		sleGponProfileVoIPDetailControlSIPDNSCache OBJECT-TYPE
			SYNTAX INTEGER
				{
				ttl(0),
				permanent(1)
				}
			MAX-ACCESS read-write
			STATUS current
			DESCRIPTION
				"SIP Stack DNS Cache update policy"
			::= { sleGponProfileVoIPDetailControl 89 }


--  1.3.6.1.4.1.6296.101.23.5.5.5.2.90
		sleGponProfileVoIPDetailControlSIPTimerT1 OBJECT-TYPE
			SYNTAX Integer32 (0..2500)
			MAX-ACCESS read-write
			STATUS current
			DESCRIPTION
				"First Response Wait Time"
			::= { sleGponProfileVoIPDetailControl 90 }


--  1.3.6.1.4.1.6296.101.23.5.5.5.2.91
		sleGponProfileVoIPDetailControlSIPTimerT2 OBJECT-TYPE
			SYNTAX Integer32 (0..5000)
			MAX-ACCESS read-write
			STATUS current
			DESCRIPTION
				"Next Increase Waiting Time"
			::= { sleGponProfileVoIPDetailControl 91 }


--  1.3.6.1.4.1.6296.101.23.5.5.5.2.92
		sleGponProfileVoIPDetailControlSIPTimerTd OBJECT-TYPE
			SYNTAX Integer32 (5000..65535)
			MAX-ACCESS read-write
			STATUS current
			DESCRIPTION
				"Max Transaction Time"
			::= { sleGponProfileVoIPDetailControl 92 }


--  1.3.6.1.4.1.6296.101.23.5.5.5.2.93
		sleGponProfileVoIPDetailControlSIPSessionTimer OBJECT-TYPE
			SYNTAX INTEGER
				{
				disable(0),
				enable(1)
				}
			MAX-ACCESS read-write
			STATUS current
			DESCRIPTION
				"SIP Session Timer"
			::= { sleGponProfileVoIPDetailControl 93 }


--  1.3.6.1.4.1.6296.101.23.5.5.5.2.94
		sleGponProfileVoIPDetailControlSIPSessionTimeout OBJECT-TYPE
			SYNTAX Integer32 (0..65535)
			MAX-ACCESS read-write
			STATUS current
			DESCRIPTION
				"SIP Session Timer Timeout"
			::= { sleGponProfileVoIPDetailControl 94 }


--  1.3.6.1.4.1.6296.101.23.5.5.5.2.95
		sleGponProfileVoIPDetailControlSIPEndOfDigit OBJECT-TYPE
			SYNTAX INTEGER
				{
				disable(0),
				enable(1)
				}
			MAX-ACCESS read-write
			STATUS current
			DESCRIPTION
				"SIP End of Digit"
			::= { sleGponProfileVoIPDetailControl 95 }


--  1.3.6.1.4.1.6296.101.23.5.5.5.2.96
		sleGponProfileVoIPDetailControlSIPEndSharpToken OBJECT-TYPE
			SYNTAX INTEGER
				{
				hex(0),
				ascii(1)
				}
			MAX-ACCESS read-write
			STATUS current
			DESCRIPTION
				"SIP End # Token."
			::= { sleGponProfileVoIPDetailControl 96 }


--   1.3.6.1.4.1.6296.101.23.5.5.1.3
-- 1.3.6.1.4.1.6296.101.23.5.5.5.3
		sleGponProfileVoIPDetailNotification OBJECT IDENTIFIER ::= { sleGponProfileVoIPDetail 3 }


--   1.3.6.1.4.1.6296.101.23.5.5.1.3.1
-- 1.3.6.1.4.1.6296.101.23.5.5.5.3.1
		sleGponProfileVoIPDetailProfileCreated NOTIFICATION-TYPE
			OBJECTS { sleGponProfileVoIPDetailControlRequest, sleGponProfileVoIPDetailControlTimeStamp, sleGponProfileVoIPDetailControlReqResult, sleGponProfileVoIPDetaiControllName, sleGponProfileVoIPDetailControlProtocol
				 }
			STATUS current
			DESCRIPTION
				"Description."
			::= { sleGponProfileVoIPDetailNotification 1 }


--   1.3.6.1.4.1.6296.101.23.5.5.1.3.1
-- 1.3.6.1.4.1.6296.101.23.5.5.5.3.2
		sleGponProfileVoIPDetailProfileDeleted NOTIFICATION-TYPE
			OBJECTS { sleGponProfileVoIPDetailControlRequest, sleGponProfileVoIPDetailControlTimeStamp, sleGponProfileVoIPDetailControlReqResult, sleGponProfileVoIPDetailControlIndex }
			STATUS current
			DESCRIPTION
				"Description."
			::= { sleGponProfileVoIPDetailNotification 2 }


--   1.3.6.1.4.1.6296.101.23.5.5.1.3.1
-- 1.3.6.1.4.1.6296.101.23.5.5.5.3.3
		sleGponProfileVoIPDetailFaxModeChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlFaxMode
				 }
			STATUS current
			DESCRIPTION
				"Description."
			::= { sleGponProfileVoIPDetailNotification 3 }


--   1.3.6.1.4.1.6296.101.23.5.5.1.3.1
-- 1.3.6.1.4.1.6296.101.23.5.5.5.3.4
		sleGponProfileVoIPDetailCodec1stChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlCodecType1st,
				sleGponProfileVoIPDetailControlCodecPeriod1st, sleGponProfileVoIPDetailControlCodecSilenceSuppression1st }
			STATUS current
			DESCRIPTION
				"Description."
			::= { sleGponProfileVoIPDetailNotification 4 }


--   1.3.6.1.4.1.6296.101.23.5.5.1.3.1
-- 1.3.6.1.4.1.6296.101.23.5.5.5.3.5
		sleGponProfileVoIPDetailCodec2ndChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlCodecType2nd,
				sleGponProfileVoIPDetailControlCodecPeriod2nd, sleGponProfileVoIPDetailControlCodecSilenceSuppression2nd }
			STATUS current
			DESCRIPTION
				"Description."
			::= { sleGponProfileVoIPDetailNotification 5 }


--   1.3.6.1.4.1.6296.101.23.5.5.1.3.1
-- 1.3.6.1.4.1.6296.101.23.5.5.5.3.6
		sleGponProfileVoIPDetailCodec3rdChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlCodecType3rd,
				sleGponProfileVoIPDetailControlCodecPeriod3rd, sleGponProfileVoIPDetailControlCodecSilenceSuppression3rd }
			STATUS current
			DESCRIPTION
				"Description."
			::= { sleGponProfileVoIPDetailNotification 6 }


--   1.3.6.1.4.1.6296.101.23.5.5.1.3.1
-- 1.3.6.1.4.1.6296.101.23.5.5.5.3.7
		sleGponProfileVoIPDetailCodec4thChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlCodecType4th,
				sleGponProfileVoIPDetailCodecControlPeriod4th, sleGponProfileVoIPDetailControlCodecSilenceSuppression4th }
			STATUS current
			DESCRIPTION
				"Description."
			::= { sleGponProfileVoIPDetailNotification 7 }


--   1.3.6.1.4.1.6296.101.23.5.5.1.3.1
-- 1.3.6.1.4.1.6296.101.23.5.5.5.3.8
		sleGponProfileVoIPDetailOobDtmfChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlOobdtmf
				 }
			STATUS current
			DESCRIPTION
				"Description."
			::= { sleGponProfileVoIPDetailNotification 8 }


--   1.3.6.1.4.1.6296.101.23.5.5.1.3.1
-- 1.3.6.1.4.1.6296.101.23.5.5.5.3.9
		sleGponProfileVoIPDetailAnnouncementTypeChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlAnnouncementType
				 }
			STATUS current
			DESCRIPTION
				"Description."
			::= { sleGponProfileVoIPDetailNotification 9 }


--   1.3.6.1.4.1.6296.101.23.5.5.1.3.1
-- 1.3.6.1.4.1.6296.101.23.5.5.5.3.10
		sleGponProfileVoIPDetailJitterTargetChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlJitterTarget
				 }
			STATUS current
			DESCRIPTION
				"Description."
			::= { sleGponProfileVoIPDetailNotification 10 }


--   1.3.6.1.4.1.6296.101.23.5.5.1.3.1
-- 1.3.6.1.4.1.6296.101.23.5.5.5.3.11
		sleGponProfileVoIPDetailJitterBuffMaxChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlJitterBuffMax
				 }
			STATUS current
			DESCRIPTION
				"Description."
			::= { sleGponProfileVoIPDetailNotification 11 }


--   1.3.6.1.4.1.6296.101.23.5.5.1.3.1
-- 1.3.6.1.4.1.6296.101.23.5.5.5.3.12
		sleGponProfileVoIPDetailEchoCancelChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlEchoCancel
				 }
			STATUS current
			DESCRIPTION
				"Description."
			::= { sleGponProfileVoIPDetailNotification 12 }


--   1.3.6.1.4.1.6296.101.23.5.5.1.3.1
-- 1.3.6.1.4.1.6296.101.23.5.5.5.3.13
		sleGponProfileVoIPDetailPstnProtoChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlPstnProtoVariant
				 }
			STATUS current
			DESCRIPTION
				"Description."
			::= { sleGponProfileVoIPDetailNotification 13 }


--   1.3.6.1.4.1.6296.101.23.5.5.1.3.1
-- 1.3.6.1.4.1.6296.101.23.5.5.5.3.14
		sleGponProfileVoIPDetailDtmfDigitChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlDtmfDigitLevels,
				sleGponProfileVoIPDetailControlDtmfDigitDuration }
			STATUS current
			DESCRIPTION
				"Description."
			::= { sleGponProfileVoIPDetailNotification 14 }


--   1.3.6.1.4.1.6296.101.23.5.5.1.3.1
-- 1.3.6.1.4.1.6296.101.23.5.5.5.3.15
		sleGponProfileVoIPDetailHookFlashTimeMinChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlHookFlashTimeMin
				 }
			STATUS current
			DESCRIPTION
				"Description."
			::= { sleGponProfileVoIPDetailNotification 15 }


--   1.3.6.1.4.1.6296.101.23.5.5.1.3.1
-- 1.3.6.1.4.1.6296.101.23.5.5.5.3.16
		sleGponProfileVoIPDetailHookFlashTimeMaxChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlHookFlashTimeMax
				 }
			STATUS current
			DESCRIPTION
				"Description."
			::= { sleGponProfileVoIPDetailNotification 16 }


--   1.3.6.1.4.1.6296.101.23.5.5.1.3.1
-- 1.3.6.1.4.1.6296.101.23.5.5.5.3.17
		sleGponProfileVoIPDetailSignalingCodeChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlSignalingCode
				 }
			STATUS current
			DESCRIPTION
				"Description."
			::= { sleGponProfileVoIPDetailNotification 17 }


--   1.3.6.1.4.1.6296.101.23.5.5.1.3.1
-- 1.3.6.1.4.1.6296.101.23.5.5.5.3.18
		sleGponProfileVoIPDetailRtpLocalPortChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlRtpLocalPortMin,
				sleGponProfileVoIPDetailControlRtpLocalPortMax }
			STATUS current
			DESCRIPTION
				"Description."
			::= { sleGponProfileVoIPDetailNotification 18 }


--   1.3.6.1.4.1.6296.101.23.5.5.1.3.1
-- 1.3.6.1.4.1.6296.101.23.5.5.5.3.19
		sleGponProfileVoIPDetailRtpDscpMarkChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlRtpDscpMark
				 }
			STATUS current
			DESCRIPTION
				"Description."
			::= { sleGponProfileVoIPDetailNotification 19 }


--   1.3.6.1.4.1.6296.101.23.5.5.1.3.1
-- 1.3.6.1.4.1.6296.101.23.5.5.5.3.20
		sleGponProfileVoIPDetailRtpPiggybackEventChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlRtpPiggybackEvent
				 }
			STATUS current
			DESCRIPTION
				"Description."
			::= { sleGponProfileVoIPDetailNotification 20 }


--   1.3.6.1.4.1.6296.101.23.5.5.1.3.1
-- 1.3.6.1.4.1.6296.101.23.5.5.5.3.21
		sleGponProfileVoIPDetailRtpToneEventChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlRtpToneEvent
				 }
			STATUS current
			DESCRIPTION
				"Description."
			::= { sleGponProfileVoIPDetailNotification 21 }


--   1.3.6.1.4.1.6296.101.23.5.5.1.3.1
-- 1.3.6.1.4.1.6296.101.23.5.5.5.3.22
		sleGponProfileVoIPDetailRtpDtmfEventChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlRtpDtmfEvent
				 }
			STATUS current
			DESCRIPTION
				"Description."
			::= { sleGponProfileVoIPDetailNotification 22 }


--   1.3.6.1.4.1.6296.101.23.5.5.1.3.1
-- 1.3.6.1.4.1.6296.101.23.5.5.5.3.23
		sleGponProfileVoIPDetailRtpCasEventChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlRtpCasEvent
				 }
			STATUS current
			DESCRIPTION
				"Description."
			::= { sleGponProfileVoIPDetailNotification 23 }


--   1.3.6.1.4.1.6296.101.23.5.5.1.3.1
-- 1.3.6.1.4.1.6296.101.23.5.5.5.3.24
		sleGponProfileVoIPDetailProtocolChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlProtocol
				 }
			STATUS current
			DESCRIPTION
				"Description."
			::= { sleGponProfileVoIPDetailNotification 24 }


--   1.3.6.1.4.1.6296.101.23.5.5.1.3.1
-- 1.3.6.1.4.1.6296.101.23.5.5.5.3.25
		sleGponProfileVoIPDetailMgcPriServerChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlMgcPriServer
				 }
			STATUS current
			DESCRIPTION
				"Description."
			::= { sleGponProfileVoIPDetailNotification 25 }


--   1.3.6.1.4.1.6296.101.23.5.5.1.3.1
-- 1.3.6.1.4.1.6296.101.23.5.5.5.3.26
		sleGponProfileVoIPDetailMgcSecServerChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlMgcSecServer
				 }
			STATUS current
			DESCRIPTION
				"Description."
			::= { sleGponProfileVoIPDetailNotification 26 }


--   1.3.6.1.4.1.6296.101.23.5.5.1.3.1
-- 1.3.6.1.4.1.6296.101.23.5.5.5.3.27
		sleGponProfileVoIPDetailMgcVersionChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlMgcMsgVersion
				 }
			STATUS current
			DESCRIPTION
				"Description."
			::= { sleGponProfileVoIPDetailNotification 27 }


--   1.3.6.1.4.1.6296.101.23.5.5.1.3.1
-- 1.3.6.1.4.1.6296.101.23.5.5.5.3.28
		sleGponProfileVoIPDetailMgcFormatChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlMgcMsgFormat
				 }
			STATUS current
			DESCRIPTION
				"Description."
			::= { sleGponProfileVoIPDetailNotification 28 }


--   1.3.6.1.4.1.6296.101.23.5.5.1.3.1
-- 1.3.6.1.4.1.6296.101.23.5.5.5.3.29
		sleGponProfileVoIPDetailMgcMaxRetryTimeChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlMgcMaxRetryTime
				 }
			STATUS current
			DESCRIPTION
				"Description."
			::= { sleGponProfileVoIPDetailNotification 29 }


--   1.3.6.1.4.1.6296.101.23.5.5.1.3.1
-- 1.3.6.1.4.1.6296.101.23.5.5.5.3.30
		sleGponProfileVoIPDetailMgcRetryAttemptsChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlMgcMaxRetryAttempts
				 }
			STATUS current
			DESCRIPTION
				"Description."
			::= { sleGponProfileVoIPDetailNotification 30 }


--   1.3.6.1.4.1.6296.101.23.5.5.1.3.1
-- 1.3.6.1.4.1.6296.101.23.5.5.5.3.31
		sleGponProfileVoIPDetailMgcServiceChangeDelayChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlMgcSvcChangeDelay
				 }
			STATUS current
			DESCRIPTION
				"Description."
			::= { sleGponProfileVoIPDetailNotification 31 }


--   1.3.6.1.4.1.6296.101.23.5.5.1.3.1
-- 1.3.6.1.4.1.6296.101.23.5.5.5.3.32
		sleGponProfileVoIPDetailMgcTerminationIdChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlMgcTerminationId
				 }
			STATUS current
			DESCRIPTION
				"Description."
			::= { sleGponProfileVoIPDetailNotification 32 }


--   1.3.6.1.4.1.6296.101.23.5.5.1.3.1
-- 1.3.6.1.4.1.6296.101.23.5.5.5.3.33
		sleGponProfileVoIPDetailMgcSoftswitchChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlMgcSoftswitch
				 }
			STATUS current
			DESCRIPTION
				"Description."
			::= { sleGponProfileVoIPDetailNotification 33 }


--   1.3.6.1.4.1.6296.101.23.5.5.1.3.1
-- 1.3.6.1.4.1.6296.101.23.5.5.5.3.34
		sleGponProfileVoIPDetailVoicemailServerChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlVoicemailServer
				 }
			STATUS current
			DESCRIPTION
				"Description."
			::= { sleGponProfileVoIPDetailNotification 34 }


--   1.3.6.1.4.1.6296.101.23.5.5.1.3.1
-- 1.3.6.1.4.1.6296.101.23.5.5.5.3.35
		sleGponProfileVoIPDetailVoicemailExpireTimeChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlVoicemmailExpireTime
				 }
			STATUS current
			DESCRIPTION
				"Description."
			::= { sleGponProfileVoIPDetailNotification 35 }


--   1.3.6.1.4.1.6296.101.23.5.5.1.3.1
-- 1.3.6.1.4.1.6296.101.23.5.5.5.3.36
		sleGponProfileVoIPDetailReleaseTimeChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlReleaseTime
				 }
			STATUS current
			DESCRIPTION
				"Description."
			::= { sleGponProfileVoIPDetailNotification 36 }


--   1.3.6.1.4.1.6296.101.23.5.5.1.3.1
-- 1.3.6.1.4.1.6296.101.23.5.5.5.3.37
		sleGponProfileVoIPDetailRohTimerChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlRohTimer
				 }
			STATUS current
			DESCRIPTION
				"Description."
			::= { sleGponProfileVoIPDetailNotification 37 }


--   1.3.6.1.4.1.6296.101.23.5.5.1.3.1
-- 1.3.6.1.4.1.6296.101.23.5.5.5.3.38
		sleGponProfileVoIPDetailProxyServerChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlProxyServer
				 }
			STATUS current
			DESCRIPTION
				"Description."
			::= { sleGponProfileVoIPDetailNotification 38 }


--   1.3.6.1.4.1.6296.101.23.5.5.1.3.1
-- 1.3.6.1.4.1.6296.101.23.5.5.5.3.39
		sleGponProfileVoIPDetailOutboundProxyServerChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlOutboundProxyServer
				 }
			STATUS current
			DESCRIPTION
				"Description."
			::= { sleGponProfileVoIPDetailNotification 39 }


--   1.3.6.1.4.1.6296.101.23.5.5.1.3.1
-- 1.3.6.1.4.1.6296.101.23.5.5.5.3.40
		sleGponProfileVoIPDetailRegisterServerChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlRegisterServer
				 }
			STATUS current
			DESCRIPTION
				"Description."
			::= { sleGponProfileVoIPDetailNotification 40 }


--   1.3.6.1.4.1.6296.101.23.5.5.1.3.1
-- 1.3.6.1.4.1.6296.101.23.5.5.5.3.41
		sleGponProfileVoIPDetailHostpartServerChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlHostPartServer
				 }
			STATUS current
			DESCRIPTION
				"Description."
			::= { sleGponProfileVoIPDetailNotification 41 }


--   1.3.6.1.4.1.6296.101.23.5.5.1.3.1
-- 1.3.6.1.4.1.6296.101.23.5.5.5.3.42
		sleGponProfileVoIPDetailDnsChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlPriDns,
				sleGponProfileVoIPDetailControlSecDns }
			STATUS current
			DESCRIPTION
				"Description."
			::= { sleGponProfileVoIPDetailNotification 42 }


--   1.3.6.1.4.1.6296.101.23.5.5.1.3.1
-- 1.3.6.1.4.1.6296.101.23.5.5.5.3.43
		sleGponProfileVoIPDetailRegExpTimeChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlRegExpTime
				 }
			STATUS current
			DESCRIPTION
				"Description."
			::= { sleGponProfileVoIPDetailNotification 43 }


--   1.3.6.1.4.1.6296.101.23.5.5.1.3.1
-- 1.3.6.1.4.1.6296.101.23.5.5.5.3.44
		sleGponProfileVoIPDetailReregHeadStartTimeChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlReregHeadStartTime
				 }
			STATUS current
			DESCRIPTION
				"Description."
			::= { sleGponProfileVoIPDetailNotification 44 }


--   1.3.6.1.4.1.6296.101.23.5.5.1.3.1
-- 1.3.6.1.4.1.6296.101.23.5.5.5.3.45
		sleGponProfileVoIPDetailSoftSwitchChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlSoftSwitchVendor
				 }
			STATUS current
			DESCRIPTION
				"Description."
			::= { sleGponProfileVoIPDetailNotification 45 }


--   1.3.6.1.4.1.6296.101.23.5.5.1.3.1
-- 1.3.6.1.4.1.6296.101.23.5.5.5.3.46
		sleGponProfileVoIPDetailSipOptionTransmitCtlChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlSipOptionTransmitCtl
				 }
			STATUS current
			DESCRIPTION
				"Description."
			::= { sleGponProfileVoIPDetailNotification 46 }


--   1.3.6.1.4.1.6296.101.23.5.5.1.3.1
-- 1.3.6.1.4.1.6296.101.23.5.5.5.3.47
		sleGponProfileVoIPDetailSipUriFormatChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlSipUriFormat
				 }
			STATUS current
			DESCRIPTION
				"Description."
			::= { sleGponProfileVoIPDetailNotification 47 }


--   1.3.6.1.4.1.6296.101.23.5.5.1.3.1
-- 1.3.6.1.4.1.6296.101.23.5.5.5.3.48
		sleGponProfileVoIPDetailCallerIdChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlCallerId
				 }
			STATUS current
			DESCRIPTION
				"Description."
			::= { sleGponProfileVoIPDetailNotification 48 }


--   1.3.6.1.4.1.6296.101.23.5.5.1.3.1
-- 1.3.6.1.4.1.6296.101.23.5.5.5.3.49
		sleGponProfileVoIPDetailCallWaitingChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlCallWaiting
				 }
			STATUS current
			DESCRIPTION
				"Description."
			::= { sleGponProfileVoIPDetailNotification 49 }


--   1.3.6.1.4.1.6296.101.23.5.5.1.3.1
-- 1.3.6.1.4.1.6296.101.23.5.5.5.3.50
		sleGponProfileVoIPDetailCallProgressTransferChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlCallProgressTransfer
				 }
			STATUS current
			DESCRIPTION
				"Description."
			::= { sleGponProfileVoIPDetailNotification 50 }


--   1.3.6.1.4.1.6296.101.23.5.5.1.3.1
-- 1.3.6.1.4.1.6296.101.23.5.5.5.3.51
		sleGponProfileVoIPDetailCallPresentChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlCallProgressTransfer
				 }
			STATUS current
			DESCRIPTION
				"Description."
			::= { sleGponProfileVoIPDetailNotification 51 }


--   1.3.6.1.4.1.6296.101.23.5.5.1.3.1
-- 1.3.6.1.4.1.6296.101.23.5.5.5.3.52
		sleGponProfileVoIPDetailDirectConnectChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlDirectConnect
				 }
			STATUS current
			DESCRIPTION
				"Description."
			::= { sleGponProfileVoIPDetailNotification 52 }


--   1.3.6.1.4.1.6296.101.23.5.5.1.3.1
-- 1.3.6.1.4.1.6296.101.23.5.5.5.3.53
		sleGponProfileVoIPDetailDirectConnectUriChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlDirectConnectUri
				 }
			STATUS current
			DESCRIPTION
				"Description."
			::= { sleGponProfileVoIPDetailNotification 53 }


--   1.3.6.1.4.1.6296.101.23.5.5.1.3.1
-- 1.3.6.1.4.1.6296.101.23.5.5.5.3.54
		sleGponProfileVoIPDetailBridgedLineAgentUriChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlBridgedLineAgentUri
				 }
			STATUS current
			DESCRIPTION
				"Description."
			::= { sleGponProfileVoIPDetailNotification 54 }


--   1.3.6.1.4.1.6296.101.23.5.5.1.3.1
-- 1.3.6.1.4.1.6296.101.23.5.5.5.3.55
		sleGponProfileVoIPDetailConferenceFactoryUriChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlConferenceFactoryUri
				 }
			STATUS current
			DESCRIPTION
				"Description."
			::= { sleGponProfileVoIPDetailNotification 55 }


--   1.3.6.1.4.1.6296.101.23.5.5.1.3.1
-- 1.3.6.1.4.1.6296.101.23.5.5.5.3.56
		sleGponProfileVoIPDetailCancelCallWaitChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlCancelCallWait
				 }
			STATUS current
			DESCRIPTION
				"Description."
			::= { sleGponProfileVoIPDetailNotification 56 }


--   1.3.6.1.4.1.6296.101.23.5.5.1.3.1
-- 1.3.6.1.4.1.6296.101.23.5.5.5.3.57
		sleGponProfileVoIPDetailCallHoldChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlCallHold
				 }
			STATUS current
			DESCRIPTION
				"Description."
			::= { sleGponProfileVoIPDetailNotification 57 }


--   1.3.6.1.4.1.6296.101.23.5.5.1.3.1
-- 1.3.6.1.4.1.6296.101.23.5.5.5.3.58
		sleGponProfileVoIPDetailCallParkChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlCallPark
				 }
			STATUS current
			DESCRIPTION
				"Description."
			::= { sleGponProfileVoIPDetailNotification 58 }


--   1.3.6.1.4.1.6296.101.23.5.5.1.3.1
-- 1.3.6.1.4.1.6296.101.23.5.5.5.3.59
		sleGponProfileVoIPDetailCallerIdActChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlCallerIdAct
				 }
			STATUS current
			DESCRIPTION
				"Description."
			::= { sleGponProfileVoIPDetailNotification 59 }


--   1.3.6.1.4.1.6296.101.23.5.5.1.3.1
-- 1.3.6.1.4.1.6296.101.23.5.5.5.3.60
		sleGponProfileVoIPDetailCallerIdDeactChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlCallerIdDeact
				 }
			STATUS current
			DESCRIPTION
				"Description."
			::= { sleGponProfileVoIPDetailNotification 60 }


--   1.3.6.1.4.1.6296.101.23.5.5.1.3.1
-- 1.3.6.1.4.1.6296.101.23.5.5.5.3.61
		sleGponProfileVoIPDetailDoNotDisturbActChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlDoNotDisturbAct
				 }
			STATUS current
			DESCRIPTION
				"Description."
			::= { sleGponProfileVoIPDetailNotification 61 }


--   1.3.6.1.4.1.6296.101.23.5.5.1.3.1
-- 1.3.6.1.4.1.6296.101.23.5.5.5.3.62
		sleGponProfileVoIPDetailDoNotDisturbDeactChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlDoNotDisturbDeact
				 }
			STATUS current
			DESCRIPTION
				"Description."
			::= { sleGponProfileVoIPDetailNotification 62 }


--   1.3.6.1.4.1.6296.101.23.5.5.1.3.1
-- 1.3.6.1.4.1.6296.101.23.5.5.5.3.63
		sleGponProfileVoIPDetailDoNotDisturbPinChangeChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlDoNotDisturbPinChange
				 }
			STATUS current
			DESCRIPTION
				"Description."
			::= { sleGponProfileVoIPDetailNotification 63 }


--   1.3.6.1.4.1.6296.101.23.5.5.1.3.1
-- 1.3.6.1.4.1.6296.101.23.5.5.5.3.64
		sleGponProfileVoIPDetailEmergServiceNumberChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlEmergServiceNumber
				 }
			STATUS current
			DESCRIPTION
				"Description."
			::= { sleGponProfileVoIPDetailNotification 64 }


--   1.3.6.1.4.1.6296.101.23.5.5.1.3.1
-- 1.3.6.1.4.1.6296.101.23.5.5.5.3.65
		sleGponProfileVoIPDetailIntercomServiceChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlIntercomService
				 }
			STATUS current
			DESCRIPTION
				"Description."
			::= { sleGponProfileVoIPDetailNotification 65 }


--  1.3.6.1.4.1.6296.101.23.5.5.5.3.66
		sleGponProfileVoIPDetailDialPlanCritTimeOutChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlDialplanCritTimeout
				 }
			STATUS current
			DESCRIPTION
				"Description."
			::= { sleGponProfileVoIPDetailNotification 66 }


--  1.3.6.1.4.1.6296.101.23.5.5.5.3.67
		sleGponProfileVoIPDetailDialPlanPartTimeOutChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlDialplanPartTimeout
				 }
			STATUS current
			DESCRIPTION
				"Description."
			::= { sleGponProfileVoIPDetailNotification 67 }


--  1.3.6.1.4.1.6296.101.23.5.5.5.3.68
		sleGponProfileVoIPDetailDialPlanFormatChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlDialplanFormat
				 }
			STATUS current
			DESCRIPTION
				"Description."
			::= { sleGponProfileVoIPDetailNotification 68 }


--  1.3.6.1.4.1.6296.101.23.5.5.5.3.69
		sleGponProfileVoIPDetailSpecialLineServiceChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlSpecialLineService,
				sleGponProfileVoIPDetailControlWarmLineTimeout, sleGponProfileVoIPDetailControlLineNumber }
			STATUS current
			DESCRIPTION
				"setSpecialLineService"
			::= { sleGponProfileVoIPDetailNotification 69 }


--  1.3.6.1.4.1.6296.101.23.5.5.5.3.70
		sleGponProfileVoIPDetailThreeWaySSWMixingChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlThreeWaySSWMixing
				 }
			STATUS current
			DESCRIPTION
				"setThreeWaySSWMixing"
			::= { sleGponProfileVoIPDetailNotification 70 }


--  1.3.6.1.4.1.6296.101.23.5.5.5.3.71
		sleGponProfileVoIPDetailSIPDNSCacheChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlSIPDNSCache
				 }
			STATUS current
			DESCRIPTION
				"setDNSCachePolicy"
			::= { sleGponProfileVoIPDetailNotification 71 }


--  1.3.6.1.4.1.6296.101.23.5.5.5.3.72
		sleGponProfileVoIPDetailSIPTimerChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlSIPTimerT1,
				sleGponProfileVoIPDetailControlSIPTimerT2, sleGponProfileVoIPDetailControlSIPTimerTd }
			STATUS current
			DESCRIPTION
				"setSIPTimer"
			::= { sleGponProfileVoIPDetailNotification 72 }


--  1.3.6.1.4.1.6296.101.23.5.5.5.3.73
		sleGponProfileVoIPDetailSIPSessionTimerChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlSIPSessionTimer,
				sleGponProfileVoIPDetailControlSIPSessionTimeout }
			STATUS current
			DESCRIPTION
				"setSessionTimer"
			::= { sleGponProfileVoIPDetailNotification 73 }


--  1.3.6.1.4.1.6296.101.23.5.5.5.3.74
		sleGponProfileVoIPDetailSIPEndOfDigitChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlSIPEndOfDigit
				 }
			STATUS current
			DESCRIPTION
				"setEndOfDigit"
			::= { sleGponProfileVoIPDetailNotification 74 }


--  1.3.6.1.4.1.6296.101.23.5.5.5.3.75
		sleGponProfileVoIPDetailSIPEndSharpTokenChanged NOTIFICATION-TYPE
			OBJECTS { sleGponProfileVoIPDetailControlRequest, sleGponProfileVoIPDetailControlTimeStamp, sleGponProfileVoIPDetailControlReqResult, sleGponProfileVoIPDetailControlIndex, sleGponProfileVoIPDetailControlSIPEndSharpToken
				 }
			STATUS current
			DESCRIPTION
				"setEndSharpToken"
			::= { sleGponProfileVoIPDetailNotification 75 }


--  1.3.6.1.4.1.6296.101.23.5.5.6
		sleGponProfileVoIPDetailDialPlan OBJECT IDENTIFIER ::= { sleGponVoIP 6 }


--  1.3.6.1.4.1.6296.101.23.5.5.6.1
		sleGponProfileVoIPDetailDialPlanTable OBJECT-TYPE
			SYNTAX SEQUENCE OF SleGponProfileVoIPDetailDialPlanEntry
			MAX-ACCESS not-accessible
			STATUS current
			DESCRIPTION
				"sleGponProfileVoIPDetailDialPlanTable"
			::= { sleGponProfileVoIPDetailDialPlan 1 }


--  1.3.6.1.4.1.6296.101.23.5.5.6.1.1
		sleGponProfileVoIPDetailDialPlanEntry OBJECT-TYPE
			SYNTAX SleGponProfileVoIPDetailDialPlanEntry
			MAX-ACCESS not-accessible
			STATUS current
			DESCRIPTION
				"key: sleGponProfileVoIPDetailIndex, sleGponProfileVoIPDetailDialPlanTableIndex"
			INDEX { sleGponProfileVoIPDetailIndex, sleGponProfileVoIPDetailDialPlanTableIndex }
			::= { sleGponProfileVoIPDetailDialPlanTable 1 }


		SleGponProfileVoIPDetailDialPlanEntry ::=
			SEQUENCE {
				sleGponProfileVoIPDetailDialPlanTableIndex
					INTEGER,
				sleGponProfileVoIPDetailDialPlanTableToken
					OCTET STRING
			 }

--  1.3.6.1.4.1.6296.101.23.5.5.6.1.1.1
		sleGponProfileVoIPDetailDialPlanTableIndex OBJECT-TYPE
			SYNTAX INTEGER (1..65535)
			MAX-ACCESS read-only
			STATUS current
			DESCRIPTION
				"The Dial Plan Table Index."
			::= { sleGponProfileVoIPDetailDialPlanEntry 1 }


--  1.3.6.1.4.1.6296.101.23.5.5.6.1.1.2
		sleGponProfileVoIPDetailDialPlanTableToken OBJECT-TYPE
			SYNTAX OCTET STRING
			MAX-ACCESS read-only
			STATUS current
			DESCRIPTION
				"The Dial Plan Table Name."
			::= { sleGponProfileVoIPDetailDialPlanEntry 2 }


--  1.3.6.1.4.1.6296.101.23.5.5.6.2
		sleGponProfileVoIPDetailDialPlanControl OBJECT IDENTIFIER ::= { sleGponProfileVoIPDetailDialPlan 2 }


--  1.3.6.1.4.1.6296.101.23.5.5.6.2.1
		sleGponProfileVoIPDetailDialPlanControlRequest OBJECT-TYPE
			SYNTAX INTEGER
				{
				addDialPlanTable(1),
				delDialPlanTable(2)
				}
			MAX-ACCESS read-write
			STATUS current
			DESCRIPTION
				"The request of a user command"
			::= { sleGponProfileVoIPDetailDialPlanControl 1 }


--  1.3.6.1.4.1.6296.101.23.5.5.6.2.2
		sleGponProfileVoIPDetailDialPlanControlStatus OBJECT-TYPE
			SYNTAX SleControlStatusType
			MAX-ACCESS read-write
			STATUS current
			DESCRIPTION
				"The status of user command"
			::= { sleGponProfileVoIPDetailDialPlanControl 2 }


--  1.3.6.1.4.1.6296.101.23.5.5.6.2.3
		sleGponProfileVoIPDetailDialPlanControlTimer OBJECT-TYPE
			SYNTAX Gauge32
			MAX-ACCESS read-write
			STATUS current
			DESCRIPTION
				"The maximum time for the manager for a long running user command"
			::= { sleGponProfileVoIPDetailDialPlanControl 3 }


--  1.3.6.1.4.1.6296.101.23.5.5.6.2.4
		sleGponProfileVoIPDetailDialPlanControlTimeStamp OBJECT-TYPE
			SYNTAX TimeTicks
			MAX-ACCESS read-write
			STATUS current
			DESCRIPTION
				"The time stamp of the last command(end of command)"
			::= { sleGponProfileVoIPDetailDialPlanControl 4 }


--  1.3.6.1.4.1.6296.101.23.5.5.6.2.5
		sleGponProfileVoIPDetailDialPlanControlReqResult OBJECT-TYPE
			SYNTAX SleControlRequestResultType
			MAX-ACCESS read-write
			STATUS current
			DESCRIPTION
				"The result of the last user command"
			::= { sleGponProfileVoIPDetailDialPlanControl 5 }


--  1.3.6.1.4.1.6296.101.23.5.5.6.2.6
		sleGponProfileVoIPDetailDialPlanControlProfileIndex OBJECT-TYPE
			SYNTAX INTEGER (1..65535)
			MAX-ACCESS read-write
			STATUS current
			DESCRIPTION
				"sleGponProfileVoIPDetailIndex"
			::= { sleGponProfileVoIPDetailDialPlanControl 6 }


--  1.3.6.1.4.1.6296.101.23.5.5.6.2.7
		sleGponProfileVoIPDetailDialPlanControlTableIndex OBJECT-TYPE
			SYNTAX INTEGER (1..65535)
			MAX-ACCESS read-write
			STATUS current
			DESCRIPTION
				"The Dial Plan Table Index."
			::= { sleGponProfileVoIPDetailDialPlanControl 7 }


--  1.3.6.1.4.1.6296.101.23.5.5.6.2.8
		sleGponProfileVoIPDetailDialPlanControlTableToken OBJECT-TYPE
			SYNTAX OCTET STRING
			MAX-ACCESS read-write
			STATUS current
			DESCRIPTION
				"The Dial Plan Table Name."
			::= { sleGponProfileVoIPDetailDialPlanControl 8 }


--  1.3.6.1.4.1.6296.101.23.5.5.6.3
		sleGponProfileVoIPDetailDialPlanNotification OBJECT IDENTIFIER ::= { sleGponProfileVoIPDetailDialPlan 3 }


--  1.3.6.1.4.1.6296.101.23.5.5.6.3.1
		sleGponProfileVoIPDetailDialPlanTableCreated NOTIFICATION-TYPE
			OBJECTS { sleGponProfileVoIPDetailDialPlanControlRequest, sleGponProfileVoIPDetailDialPlanControlTimeStamp, sleGponProfileVoIPDetailDialPlanControlReqResult, sleGponProfileVoIPDetailDialPlanControlProfileIndex, sleGponProfileVoIPDetailDialPlanControlTableIndex,
				sleGponProfileVoIPDetailDialPlanControlTableToken }
			STATUS current
			DESCRIPTION
				"Description."
			::= { sleGponProfileVoIPDetailDialPlanNotification 1 }


--  1.3.6.1.4.1.6296.101.23.5.5.6.3.2
		sleGponProfileVoIPDetailDialPlanTableDeleted NOTIFICATION-TYPE
			OBJECTS { sleGponProfileVoIPDetailDialPlanControlRequest, sleGponProfileVoIPDetailDialPlanControlTimeStamp, sleGponProfileVoIPDetailDialPlanControlReqResult, sleGponProfileVoIPDetailDialPlanControlProfileIndex, sleGponProfileVoIPDetailDialPlanControlTableIndex
				 }
			STATUS current
			DESCRIPTION
				"Description."
			::= { sleGponProfileVoIPDetailDialPlanNotification 2 }


--  1.3.6.1.4.1.6296.101.23.5.5.7
		sleGponProfileVoIPService OBJECT IDENTIFIER ::= { sleGponVoIP 7 }


--  1.3.6.1.4.1.6296.101.23.5.5.7.1
		sleGponProfileVoIPServiceTable OBJECT-TYPE
			SYNTAX SEQUENCE OF SleGponProfileVoIPServiceEntry
			MAX-ACCESS not-accessible
			STATUS current
			DESCRIPTION
				"Description."
			::= { sleGponProfileVoIPService 1 }


--  1.3.6.1.4.1.6296.101.23.5.5.7.1.1
		sleGponProfileVoIPServiceEntry OBJECT-TYPE
			SYNTAX SleGponProfileVoIPServiceEntry
			MAX-ACCESS not-accessible
			STATUS current
			DESCRIPTION
				"Description."
			INDEX { sleGponOltId, sleGponOnuId, sleGponProfileVoIPServiceIndex }
			::= { sleGponProfileVoIPServiceTable 1 }


		SleGponProfileVoIPServiceEntry ::=
			SEQUENCE {
				sleGponProfileVoIPServiceIndex
					Integer32,
				sleGponProfileVoIPServiceMgcMessageId
					OCTET STRING
			 }

--  1.3.6.1.4.1.6296.101.23.5.5.7.1.1.1
		sleGponProfileVoIPServiceIndex OBJECT-TYPE
			SYNTAX Integer32 (1..65535)
			MAX-ACCESS read-only
			STATUS current
			DESCRIPTION
				"The VoIP service index"
			::= { sleGponProfileVoIPServiceEntry 1 }


--  1.3.6.1.4.1.6296.101.23.5.5.7.1.1.2
		sleGponProfileVoIPServiceMgcMessageId OBJECT-TYPE
			SYNTAX OCTET STRING
			MAX-ACCESS read-only
			STATUS current
			DESCRIPTION
				"The MGC message index."
			::= { sleGponProfileVoIPServiceEntry 2 }


--  1.3.6.1.4.1.6296.101.23.5.5.7.2
		sleGponProfileVoIPServiceControl OBJECT IDENTIFIER ::= { sleGponProfileVoIPService 2 }


--   1.3.6.1.4.1.6296.101.23.5.5.1.2.1
-- 1.3.6.1.4.1.6296.101.23.5.5.7.2.1
		sleGponProfileVoIPServiceControlRequest OBJECT-TYPE
			SYNTAX INTEGER { setMgcMessage(1) }
			MAX-ACCESS read-write
			STATUS current
			DESCRIPTION
				"The request of a user command"
			::= { sleGponProfileVoIPServiceControl 1 }


--   1.3.6.1.4.1.6296.101.23.5.5.1.2.2
-- 1.3.6.1.4.1.6296.101.23.5.5.7.2.2
		sleGponProfileVoIPServiceControlStatus OBJECT-TYPE
			SYNTAX SleControlStatusType
			MAX-ACCESS read-only
			STATUS current
			DESCRIPTION
				"The status of user command"
			::= { sleGponProfileVoIPServiceControl 2 }


--   1.3.6.1.4.1.6296.101.23.5.5.1.2.3
-- 1.3.6.1.4.1.6296.101.23.5.5.7.2.3
		sleGponProfileVoIPServiceControlTimer OBJECT-TYPE
			SYNTAX Gauge32
			MAX-ACCESS read-write
			STATUS current
			DESCRIPTION
				"The maximum time for the manager for a long running user command"
			::= { sleGponProfileVoIPServiceControl 3 }


--   1.3.6.1.4.1.6296.101.23.5.5.1.2.4
-- 1.3.6.1.4.1.6296.101.23.5.5.7.2.4
		sleGponProfileVoIPServiceControlTimeStamp OBJECT-TYPE
			SYNTAX TimeTicks
			MAX-ACCESS read-only
			STATUS current
			DESCRIPTION
				"The time stamp of the last command(end of command)"
			::= { sleGponProfileVoIPServiceControl 4 }


--   1.3.6.1.4.1.6296.101.23.5.5.1.2.5
-- 1.3.6.1.4.1.6296.101.23.5.5.7.2.5
		sleGponProfileVoIPServiceControlReqResult OBJECT-TYPE
			SYNTAX SleControlRequestResultType
			MAX-ACCESS read-only
			STATUS current
			DESCRIPTION
				"The result of the last user command"
			::= { sleGponProfileVoIPServiceControl 5 }


		sleGponProfileVoIPServiceControlOltId OBJECT-TYPE
			SYNTAX INTEGER (1..2147483647)
			MAX-ACCESS read-write
			STATUS current
			DESCRIPTION
				"The OLT index."
			::= { sleGponProfileVoIPServiceControl 6 }


--  1.3.6.1.4.1.6296.101.23.5.5.7.2.7
		sleGponProfileVoIPServiceControlOnuId OBJECT-TYPE
			SYNTAX INTEGER (1..65535)
			MAX-ACCESS read-write
			STATUS current
			DESCRIPTION
				"The ONU index."
			::= { sleGponProfileVoIPServiceControl 7 }


--  1.3.6.1.4.1.6296.101.23.5.5.7.2.8
		sleGponProfileVoIPServiceControlIndex OBJECT-TYPE
			SYNTAX Integer32 (1..65535)
			MAX-ACCESS read-write
			STATUS current
			DESCRIPTION
				"The VoIP service index"
			::= { sleGponProfileVoIPServiceControl 8 }


--  1.3.6.1.4.1.6296.101.23.5.5.7.2.9
		sleGponProfileVoIPServiceControlMgcMessageId OBJECT-TYPE
			SYNTAX OCTET STRING
			MAX-ACCESS read-write
			STATUS current
			DESCRIPTION
				"The MGC message index."
			::= { sleGponProfileVoIPServiceControl 9 }


--  1.3.6.1.4.1.6296.101.23.5.5.7.3
		sleGponProfileVoIPServiceNotification OBJECT IDENTIFIER ::= { sleGponProfileVoIPService 3 }


--  1.3.6.1.4.1.6296.101.23.5.5.7.3.1
		sleGponProfileVoIPServiceMgcMessageChanged NOTIFICATION-TYPE
			OBJECTS { sleGponProfileVoIPServiceControlRequest, sleGponProfileVoIPServiceControlTimeStamp, sleGponProfileVoIPServiceControlReqResult, sleGponProfileVoIPServiceControlOltId, sleGponProfileVoIPServiceControlOnuId,
				sleGponProfileVoIPServiceControlIndex, sleGponProfileVoIPServiceControlMgcMessageId }
			STATUS current
			DESCRIPTION
				"setMgcMessage"
			::= { sleGponProfileVoIPServiceNotification 1 }


--   1.3.6.1.4.1.6296.101.23.5.6
-- 1.3.6.1.4.1.6296.101.23.5.6
		sleGponServiceProfile OBJECT IDENTIFIER ::= { sleGponProfile 6 }


--   1.3.6.1.4.1.6296.101.23.5.6.1
-- 1.3.6.1.4.1.6296.101.23.5.6.1
		sleGponServiceProfileTable OBJECT-TYPE
			SYNTAX SEQUENCE OF SleGponServiceProfileEntry
			MAX-ACCESS not-accessible
			STATUS current
			DESCRIPTION
				"sleGponServiceProfileTable"
			::= { sleGponServiceProfile 1 }


--   1.3.6.1.4.1.6296.101.23.5.6.1.1
-- 1.3.6.1.4.1.6296.101.23.5.6.1.1
		sleGponServiceProfileEntry OBJECT-TYPE
			SYNTAX SleGponServiceProfileEntry
			MAX-ACCESS not-accessible
			STATUS current
			DESCRIPTION
				"key: sleGponServiceProfileIndex"
			INDEX { sleGponServiceProfileIndex }
			::= { sleGponServiceProfileTable 1 }


		SleGponServiceProfileEntry ::=
			SEQUENCE {
				sleGponServiceProfileIndex
					Integer32,
				sleGponServiceProfileModelName
					OCTET STRING,
				sleGponServiceProfileProfileName
					OCTET STRING
			 }

--   1.3.6.1.4.1.6296.101.23.5.6.1.1.1
-- 1.3.6.1.4.1.6296.101.23.5.6.1.1.1
		sleGponServiceProfileIndex OBJECT-TYPE
			SYNTAX Integer32 (1..65535)
			MAX-ACCESS read-write
			STATUS current
			DESCRIPTION
				"The profile index."
			::= { sleGponServiceProfileEntry 1 }


--   1.3.6.1.4.1.6296.101.23.5.6.1.1.2
-- 1.3.6.1.4.1.6296.101.23.5.6.1.1.2
		sleGponServiceProfileModelName OBJECT-TYPE
			SYNTAX OCTET STRING
			MAX-ACCESS read-only
			STATUS current
			DESCRIPTION
				"The Service Profile Model name."
			::= { sleGponServiceProfileEntry 2 }


--   1.3.6.1.4.1.6296.101.23.5.6.1.1.3
-- 1.3.6.1.4.1.6296.101.23.5.6.1.1.3
		sleGponServiceProfileProfileName OBJECT-TYPE
			SYNTAX OCTET STRING
			MAX-ACCESS read-only
			STATUS current
			DESCRIPTION
				"The Service Profile Name."
			::= { sleGponServiceProfileEntry 3 }


--   1.3.6.1.4.1.6296.101.23.5.6.2
-- 1.3.6.1.4.1.6296.101.23.5.6.2
		sleGponServiceProfileControl OBJECT IDENTIFIER ::= { sleGponServiceProfile 2 }


--   1.3.6.1.4.1.6296.101.23.5.6.2.1
-- 1.3.6.1.4.1.6296.101.23.5.6.2.1
		sleGponServiceProfileControlRequest OBJECT-TYPE
			SYNTAX INTEGER { setGponServiceProfileModel(1) }
			MAX-ACCESS read-write
			STATUS current
			DESCRIPTION
				"The request of a user command"
			::= { sleGponServiceProfileControl 1 }


--   1.3.6.1.4.1.6296.101.23.5.6.2.2
-- 1.3.6.1.4.1.6296.101.23.5.6.2.2
		sleGponServiceProfileControlStatus OBJECT-TYPE
			SYNTAX SleControlStatusType
			MAX-ACCESS read-write
			STATUS current
			DESCRIPTION
				"The status of user command"
			::= { sleGponServiceProfileControl 2 }


--   1.3.6.1.4.1.6296.101.23.5.6.2.3
-- 1.3.6.1.4.1.6296.101.23.5.6.2.3
		sleGponServiceProfileControlTimer OBJECT-TYPE
			SYNTAX Gauge32
			MAX-ACCESS read-write
			STATUS current
			DESCRIPTION
				"The maximum time for the manager for a long running user command"
			::= { sleGponServiceProfileControl 3 }


--   1.3.6.1.4.1.6296.101.23.5.6.2.4
-- 1.3.6.1.4.1.6296.101.23.5.6.2.4
		sleGponServiceProfileControlTimeStamp OBJECT-TYPE
			SYNTAX TimeTicks
			MAX-ACCESS read-write
			STATUS current
			DESCRIPTION
				"The time stamp of the last command(end of command)"
			::= { sleGponServiceProfileControl 4 }


--   1.3.6.1.4.1.6296.101.23.5.6.2.5
-- 1.3.6.1.4.1.6296.101.23.5.6.2.5
		sleGponServiceProfileControlReqResult OBJECT-TYPE
			SYNTAX SleControlRequestResultType
			MAX-ACCESS read-write
			STATUS current
			DESCRIPTION
				"The result of the last user command"
			::= { sleGponServiceProfileControl 5 }


--   1.3.6.1.4.1.6296.101.23.5.6.2.6
-- 1.3.6.1.4.1.6296.101.23.5.6.2.6
		sleGponServiceProfileControlModelName OBJECT-TYPE
			SYNTAX OCTET STRING
			MAX-ACCESS read-write
			STATUS current
			DESCRIPTION
				"The Service Profile Model name."
			::= { sleGponServiceProfileControl 6 }


--   1.3.6.1.4.1.6296.101.23.5.6.2.7
-- 1.3.6.1.4.1.6296.101.23.5.6.2.7
		sleGponServiceProfileControlProfileName OBJECT-TYPE
			SYNTAX OCTET STRING
			MAX-ACCESS read-write
			STATUS current
			DESCRIPTION
				"The Service Profile Name."
			::= { sleGponServiceProfileControl 7 }


--   1.3.6.1.4.1.6296.101.23.5.6.3
-- 1.3.6.1.4.1.6296.101.23.5.6.3
		sleGponServiceProfileNotification OBJECT IDENTIFIER ::= { sleGponServiceProfile 3 }


--   1.3.6.1.4.1.6296.101.23.5.6.3.1
-- 1.3.6.1.4.1.6296.101.23.5.6.3.1
		sleGponServiceProfileModelChanged NOTIFICATION-TYPE
			OBJECTS { sleGponServiceProfileControlRequest, sleGponServiceProfileControlTimeStamp, sleGponServiceProfileControlReqResult, sleGponServiceProfileControlModelName, sleGponServiceProfileControlProfileName
				 }
			STATUS current
			DESCRIPTION
				"Description."
			::= { sleGponServiceProfileNotification 1 }


--  1.3.6.1.4.1.6296.101.23.5.7
		sleGponProfileTdm OBJECT IDENTIFIER ::= { sleGponProfile 7 }


--  1.3.6.1.4.1.6296.101.23.5.7.1
		sleGponProfileTdmPwMt OBJECT IDENTIFIER ::= { sleGponProfileTdm 1 }


--  1.3.6.1.4.1.6296.101.23.5.7.1.1
		sleGponProfileTdmPwMtTable OBJECT-TYPE
			SYNTAX SEQUENCE OF SleGponProfileTdmPwMtEntry
			MAX-ACCESS not-accessible
			STATUS current
			DESCRIPTION
				"sleGponProfileTdmPwMtTable"
			::= { sleGponProfileTdmPwMt 1 }


--  1.3.6.1.4.1.6296.101.23.5.7.1.1.1
		sleGponProfileTdmPwMtEntry OBJECT-TYPE
			SYNTAX SleGponProfileTdmPwMtEntry
			MAX-ACCESS not-accessible
			STATUS current
			DESCRIPTION
				"key: sleGponProfileTdmPwMtIndex"
			INDEX { sleGponProfileTdmPwMtIndex }
			::= { sleGponProfileTdmPwMtTable 1 }


		SleGponProfileTdmPwMtEntry ::=
			SEQUENCE {
				sleGponProfileTdmPwMtIndex
					INTEGER,
				sleGponProfileTdmPwMtName
					OCTET STRING,
				sleGponProfileTdmPwMtMaxDepth
					INTEGER,
				sleGponProfileTdmPwMtDesiredDepth
					INTEGER,
				sleGponProfileTdmPwMtFillPolicy
					INTEGER,
				sleGponProfileTdmPwMtMisconnectDeclarePolicy
					INTEGER,
				sleGponProfileTdmPwMtMisconnectClearPolicy
					INTEGER,
				sleGponProfileTdmPwMtLossDeclarePolicy
					INTEGER,
				sleGponProfileTdmPwMtLossClearPolicy
					INTEGER,
				sleGponProfileTdmPwMtBuffUnderrunDeclarePolicy
					INTEGER,
				sleGponProfileTdmPwMtBuffUnderrunClearPolicy
					INTEGER,
				sleGponProfileTdmPwMtMalformedDeclarePolicy
					INTEGER,
				sleGponProfileTdmPwMtMalformedClearPolicy
					INTEGER,
				sleGponProfileTdmPwMtRBitTransmitPolicy
					INTEGER,
				sleGponProfileTdmPwMtRBitReceivePolicy
					INTEGER,
				sleGponProfileTdmPwMtLBitReceivePolicy
					INTEGER,
				sleGponProfileTdmPwMtSesThreshold
					INTEGER
			 }

--  1.3.6.1.4.1.6296.101.23.5.7.1.1.1.1
		sleGponProfileTdmPwMtIndex OBJECT-TYPE
			SYNTAX INTEGER (1..65535)
			MAX-ACCESS read-only
			STATUS current
			DESCRIPTION
				"PW Maintenance Profile Index"
			::= { sleGponProfileTdmPwMtEntry 1 }


--  1.3.6.1.4.1.6296.101.23.5.7.1.1.1.2
		sleGponProfileTdmPwMtName OBJECT-TYPE
			SYNTAX OCTET STRING
			MAX-ACCESS read-only
			STATUS current
			DESCRIPTION
				"PW Maintenance Profile Name"
			::= { sleGponProfileTdmPwMtEntry 2 }


--  1.3.6.1.4.1.6296.101.23.5.7.1.1.1.3
		sleGponProfileTdmPwMtMaxDepth OBJECT-TYPE
			SYNTAX INTEGER (1..65535)
			MAX-ACCESS read-only
			STATUS current
			DESCRIPTION
				"Configure Jitter buffer maximum depth"
			::= { sleGponProfileTdmPwMtEntry 3 }


--  1.3.6.1.4.1.6296.101.23.5.7.1.1.1.4
		sleGponProfileTdmPwMtDesiredDepth OBJECT-TYPE
			SYNTAX INTEGER (1..65535)
			MAX-ACCESS read-only
			STATUS current
			DESCRIPTION
				"Configure Jitter buffer desired depth"
			::= { sleGponProfileTdmPwMtEntry 4 }


--  1.3.6.1.4.1.6296.101.23.5.7.1.1.1.5
		sleGponProfileTdmPwMtFillPolicy OBJECT-TYPE
			SYNTAX INTEGER
				{
				vendorSpecific(0),
				playOutAis(1),
				playOutAll1S(2),
				playOutAll0S(3),
				repeatPrevData(4),
				playOutDs1Idle(5)
				}
			MAX-ACCESS read-only
			STATUS current
			DESCRIPTION
				"Configure Fill Payload Bit Pattern"
			::= { sleGponProfileTdmPwMtEntry 5 }


--  1.3.6.1.4.1.6296.101.23.5.7.1.1.1.6
		sleGponProfileTdmPwMtMisconnectDeclarePolicy OBJECT-TYPE
			SYNTAX INTEGER (0 | 1..100)
			MAX-ACCESS read-only
			STATUS current
			DESCRIPTION
				"Configure Misconnected packets declaration policy                                      "
			::= { sleGponProfileTdmPwMtEntry 6 }


--  1.3.6.1.4.1.6296.101.23.5.7.1.1.1.7
		sleGponProfileTdmPwMtMisconnectClearPolicy OBJECT-TYPE
			SYNTAX INTEGER (0..99 | 255)
			MAX-ACCESS read-only
			STATUS current
			DESCRIPTION
				"Configure Misconnected packets clear policy"
			::= { sleGponProfileTdmPwMtEntry 7 }


--  1.3.6.1.4.1.6296.101.23.5.7.1.1.1.8
		sleGponProfileTdmPwMtLossDeclarePolicy OBJECT-TYPE
			SYNTAX INTEGER (0 | 1..100)
			MAX-ACCESS read-only
			STATUS current
			DESCRIPTION
				"Configure Loss of packets declaration policy"
			::= { sleGponProfileTdmPwMtEntry 8 }


--  1.3.6.1.4.1.6296.101.23.5.7.1.1.1.9
		sleGponProfileTdmPwMtLossClearPolicy OBJECT-TYPE
			SYNTAX INTEGER (0..99 | 255)
			MAX-ACCESS read-only
			STATUS current
			DESCRIPTION
				"Configure Loss of packets clear policy"
			::= { sleGponProfileTdmPwMtEntry 9 }


--  1.3.6.1.4.1.6296.101.23.5.7.1.1.1.10
		sleGponProfileTdmPwMtBuffUnderrunDeclarePolicy OBJECT-TYPE
			SYNTAX INTEGER (0 | 1..100)
			MAX-ACCESS read-only
			STATUS current
			DESCRIPTION
				"Configure Buffer overrun/underrun declaration policy"
			::= { sleGponProfileTdmPwMtEntry 10 }


--  1.3.6.1.4.1.6296.101.23.5.7.1.1.1.11
		sleGponProfileTdmPwMtBuffUnderrunClearPolicy OBJECT-TYPE
			SYNTAX INTEGER (0..99 | 255)
			MAX-ACCESS read-only
			STATUS current
			DESCRIPTION
				"Configure Buffer overrun/underrun clear policy"
			::= { sleGponProfileTdmPwMtEntry 11 }


--  1.3.6.1.4.1.6296.101.23.5.7.1.1.1.12
		sleGponProfileTdmPwMtMalformedDeclarePolicy OBJECT-TYPE
			SYNTAX INTEGER (0 | 1..100)
			MAX-ACCESS read-only
			STATUS current
			DESCRIPTION
				"Configure Malformed packets declaration policy"
			::= { sleGponProfileTdmPwMtEntry 12 }


--  1.3.6.1.4.1.6296.101.23.5.7.1.1.1.13
		sleGponProfileTdmPwMtMalformedClearPolicy OBJECT-TYPE
			SYNTAX INTEGER (0..99 | 255)
			MAX-ACCESS read-only
			STATUS current
			DESCRIPTION
				"Configure Malformed packets clear policy"
			::= { sleGponProfileTdmPwMtEntry 13 }


--  1.3.6.1.4.1.6296.101.23.5.7.1.1.1.14
		sleGponProfileTdmPwMtRBitTransmitPolicy OBJECT-TYPE
			SYNTAX INTEGER (0 | 1..255)
			MAX-ACCESS read-only
			STATUS current
			DESCRIPTION
				"Configure R-bit transmit set policy"
			::= { sleGponProfileTdmPwMtEntry 14 }


--  1.3.6.1.4.1.6296.101.23.5.7.1.1.1.15
		sleGponProfileTdmPwMtRBitReceivePolicy OBJECT-TYPE
			SYNTAX INTEGER
				{
				none(0),
				playOut(1),
				sendIdle(2)
				}
			MAX-ACCESS read-only
			STATUS current
			DESCRIPTION
				"Configure R-bit receive policy"
			::= { sleGponProfileTdmPwMtEntry 15 }


--  1.3.6.1.4.1.6296.101.23.5.7.1.1.1.16
		sleGponProfileTdmPwMtLBitReceivePolicy OBJECT-TYPE
			SYNTAX INTEGER
				{
				playOut(0),
				repeatLastPacket(1),
				sendIdle(2)
				}
			MAX-ACCESS read-only
			STATUS current
			DESCRIPTION
				"Configure L-bit receive policy"
			::= { sleGponProfileTdmPwMtEntry 16 }


--  1.3.6.1.4.1.6296.101.23.5.7.1.1.1.17
		sleGponProfileTdmPwMtSesThreshold OBJECT-TYPE
			SYNTAX INTEGER (1..65535)
			MAX-ACCESS read-only
			STATUS current
			DESCRIPTION
				"Configure SES threshold"
			::= { sleGponProfileTdmPwMtEntry 17 }


--  1.3.6.1.4.1.6296.101.23.5.7.1.2
		sleGponProfileTdmPwMtControl OBJECT IDENTIFIER ::= { sleGponProfileTdmPwMt 2 }


--  1.3.6.1.4.1.6296.101.23.5.7.1.2.1
		sleGponProfileTdmPwMtControlRequest OBJECT-TYPE
			SYNTAX INTEGER
				{
				createProfile(1),
				destroyProfile(2),
				setMaxDepth(3),
				setDesiredDepth(4),
				setFillPolicy(5),
				setMisconnectDeclarePolicy(6),
				setMisconnectClearPolicy(7),
				setLossDeclarePolicy(8),
				setLossClearPolicy(9),
				setBuffUnderrunDeclarePolicy(10),
				setbuffUnderrunClearPolicy(11),
				setMalformedDeclarePolicy(12),
				setMalformedClearPolicy(13),
				setRBitTransmitPolicy(14),
				setRBitReceivePolicy(15),
				setLBitReceivePolicy(16),
				setSesThreshold(17)
				}
			MAX-ACCESS read-write
			STATUS current
			DESCRIPTION
				"The request of a user command"
			::= { sleGponProfileTdmPwMtControl 1 }


--  1.3.6.1.4.1.6296.101.23.5.7.1.2.2
		sleGponProfileTdmPwMtControlStatus OBJECT-TYPE
			SYNTAX SleControlStatusType
			MAX-ACCESS read-only
			STATUS current
			DESCRIPTION
				"The status of user command"
			::= { sleGponProfileTdmPwMtControl 2 }


--  1.3.6.1.4.1.6296.101.23.5.7.1.2.3
		sleGponProfileTdmPwMtControlTimer OBJECT-TYPE
			SYNTAX Gauge32
			MAX-ACCESS read-write
			STATUS current
			DESCRIPTION
				"The maximum time for the manager for a long running user command"
			::= { sleGponProfileTdmPwMtControl 3 }


--  1.3.6.1.4.1.6296.101.23.5.7.1.2.4
		sleGponProfileTdmPwMtControlTimeStamp OBJECT-TYPE
			SYNTAX TimeTicks
			MAX-ACCESS read-only
			STATUS current
			DESCRIPTION
				"The time stamp of the last command(end of command)"
			::= { sleGponProfileTdmPwMtControl 4 }


--  1.3.6.1.4.1.6296.101.23.5.7.1.2.5
		sleGponProfileTdmPwMtControlReqResult OBJECT-TYPE
			SYNTAX SleControlRequestResultType
			MAX-ACCESS read-only
			STATUS current
			DESCRIPTION
				"The result of the last user command"
			::= { sleGponProfileTdmPwMtControl 5 }


--  1.3.6.1.4.1.6296.101.23.5.7.1.2.6
		sleGponProfileTdmPwMtControlIndex OBJECT-TYPE
			SYNTAX INTEGER (1..65535)
			MAX-ACCESS read-write
			STATUS current
			DESCRIPTION
				"PW Maintenance Profile Index"
			::= { sleGponProfileTdmPwMtControl 6 }


--  1.3.6.1.4.1.6296.101.23.5.7.1.2.7
		sleGponProfileTdmPwMtControlName OBJECT-TYPE
			SYNTAX OCTET STRING
			MAX-ACCESS read-write
			STATUS current
			DESCRIPTION
				"PW Maintenance Profile Name"
			::= { sleGponProfileTdmPwMtControl 7 }


--  1.3.6.1.4.1.6296.101.23.5.7.1.2.8
		sleGponProfileTdmPwMtControlMaxDepth OBJECT-TYPE
			SYNTAX INTEGER (1..65535)
			MAX-ACCESS read-write
			STATUS current
			DESCRIPTION
				"Configure Jitter buffer maximum depth"
			::= { sleGponProfileTdmPwMtControl 8 }


--  1.3.6.1.4.1.6296.101.23.5.7.1.2.9
		sleGponProfileTdmPwMtControlDesiredDepth OBJECT-TYPE
			SYNTAX INTEGER (1..65535)
			MAX-ACCESS read-write
			STATUS current
			DESCRIPTION
				"Configure Jitter buffer desired depth"
			::= { sleGponProfileTdmPwMtControl 9 }


--  1.3.6.1.4.1.6296.101.23.5.7.1.2.10
		sleGponProfileTdmPwMtControlFillPolicy OBJECT-TYPE
			SYNTAX INTEGER
				{
				vendorSpecific(0),
				playOutAis(1),
				playOutAll1S(2),
				playOutAll0S(3),
				repeatPrevData(4),
				playOutDs1Idle(5)
				}
			MAX-ACCESS read-write
			STATUS current
			DESCRIPTION
				"Configure Fill Payload Bit Pattern"
			::= { sleGponProfileTdmPwMtControl 10 }


--  1.3.6.1.4.1.6296.101.23.5.7.1.2.11
		sleGponProfileTdmPwMtControlMisconnectDeclarePolicy OBJECT-TYPE
			SYNTAX INTEGER (0 | 1..100)
			MAX-ACCESS read-write
			STATUS current
			DESCRIPTION
				"Configure Misconnected packets declaration policy"
			::= { sleGponProfileTdmPwMtControl 11 }


--  1.3.6.1.4.1.6296.101.23.5.7.1.2.12
		sleGponProfileTdmPwMtControlMisconnectClearPolicy OBJECT-TYPE
			SYNTAX INTEGER (0..99 | 255)
			MAX-ACCESS read-write
			STATUS current
			DESCRIPTION
				"Configure Misconnected packets clear policy"
			::= { sleGponProfileTdmPwMtControl 12 }


--  1.3.6.1.4.1.6296.101.23.5.7.1.2.13
		sleGponProfileTdmPwMtControlLossDeclarePolicy OBJECT-TYPE
			SYNTAX INTEGER (0 | 1..100)
			MAX-ACCESS read-write
			STATUS current
			DESCRIPTION
				"Configure Loss of packets declaration policy"
			::= { sleGponProfileTdmPwMtControl 13 }


--  1.3.6.1.4.1.6296.101.23.5.7.1.2.14
		sleGponProfileTdmPwMtControlLossClearPolicy OBJECT-TYPE
			SYNTAX INTEGER (0..99 | 255)
			MAX-ACCESS read-write
			STATUS current
			DESCRIPTION
				"Configure Loss of packets clear policy"
			::= { sleGponProfileTdmPwMtControl 14 }


--  1.3.6.1.4.1.6296.101.23.5.7.1.2.15
		sleGponProfileTdmPwMtControlBuffUnderrunDeclarePolicy OBJECT-TYPE
			SYNTAX INTEGER (0 | 1..100)
			MAX-ACCESS read-write
			STATUS current
			DESCRIPTION
				"Configure Buffer overrun/underrun declaration policy"
			::= { sleGponProfileTdmPwMtControl 15 }


--  1.3.6.1.4.1.6296.101.23.5.7.1.2.16
		sleGponProfileTdmPwMtControlBuffUnderrunClearPolicy OBJECT-TYPE
			SYNTAX INTEGER (0..99 | 255)
			MAX-ACCESS read-write
			STATUS current
			DESCRIPTION
				"Configure Buffer overrun/underrun clear policy"
			::= { sleGponProfileTdmPwMtControl 16 }


--  1.3.6.1.4.1.6296.101.23.5.7.1.2.17
		sleGponProfileTdmPwMtControlMalformedDeclarePolicy OBJECT-TYPE
			SYNTAX INTEGER (0 | 1..100)
			MAX-ACCESS read-write
			STATUS current
			DESCRIPTION
				"Configure Malformed packets declaration policy"
			::= { sleGponProfileTdmPwMtControl 17 }


--  1.3.6.1.4.1.6296.101.23.5.7.1.2.18
		sleGponProfileTdmPwMtControlMalformedClearPolicy OBJECT-TYPE
			SYNTAX INTEGER (0..99 | 255)
			MAX-ACCESS read-write
			STATUS current
			DESCRIPTION
				"Configure Malformed packets clear policy"
			::= { sleGponProfileTdmPwMtControl 18 }


--  1.3.6.1.4.1.6296.101.23.5.7.1.2.19
		sleGponProfileTdmPwMtControlRBitTransmitPolicy OBJECT-TYPE
			SYNTAX INTEGER (0 | 1..255)
			MAX-ACCESS read-write
			STATUS current
			DESCRIPTION
				"Configure R-bit transmit set policy"
			::= { sleGponProfileTdmPwMtControl 19 }


--  1.3.6.1.4.1.6296.101.23.5.7.1.2.20
		sleGponProfileTdmPwMtControlRBitReceivePolicy OBJECT-TYPE
			SYNTAX INTEGER
				{
				none(0),
				playOut(1),
				sendIdle(2)
				}
			MAX-ACCESS read-write
			STATUS current
			DESCRIPTION
				"Configure R-bit receive policy"
			::= { sleGponProfileTdmPwMtControl 20 }


--  1.3.6.1.4.1.6296.101.23.5.7.1.2.21
		sleGponProfileTdmPwMtControlLBitReceivePolicy OBJECT-TYPE
			SYNTAX INTEGER
				{
				playOut(0),
				repeatLastPacket(1),
				sendIdle(2)
				}
			MAX-ACCESS read-write
			STATUS current
			DESCRIPTION
				"Configure L-bit receive policy"
			::= { sleGponProfileTdmPwMtControl 21 }


--  1.3.6.1.4.1.6296.101.23.5.7.1.2.22
		sleGponProfileTdmPwMtControlSesThreshold OBJECT-TYPE
			SYNTAX INTEGER (1..65535)
			MAX-ACCESS read-write
			STATUS current
			DESCRIPTION
				"Configure SES threshold"
			::= { sleGponProfileTdmPwMtControl 22 }


--  1.3.6.1.4.1.6296.101.23.5.7.1.3
		sleGponProfileTdmPwMtNotification OBJECT IDENTIFIER ::= { sleGponProfileTdmPwMt 3 }


--  1.3.6.1.4.1.6296.101.23.5.7.1.3.1
		sleGponProfileTdmPwMtProfileCreated NOTIFICATION-TYPE
			OBJECTS { sleGponProfileTdmPwMtControlName, sleGponProfileTdmPwMtControlRequest, sleGponProfileTdmPwMtControlTimeStamp, sleGponProfileTdmPwMtControlReqResult }
			STATUS current
			DESCRIPTION
				"Description."
			::= { sleGponProfileTdmPwMtNotification 1 }


--  1.3.6.1.4.1.6296.101.23.5.7.1.3.2
		sleGponProfileTdmPwMtProfileDeleted NOTIFICATION-TYPE
			OBJECTS { sleGponProfileTdmPwMtControlRequest, sleGponProfileTdmPwMtControlTimeStamp, sleGponProfileTdmPwMtControlReqResult, sleGponProfileTdmPwMtControlIndex }
			STATUS current
			DESCRIPTION
				"Description."
			::= { sleGponProfileTdmPwMtNotification 2 }


--  1.3.6.1.4.1.6296.101.23.5.7.1.3.3
		sleGponProfileTdmPwMtMaxDepthChanged NOTIFICATION-TYPE
			OBJECTS { sleGponProfileTdmPwMtControlRequest, sleGponProfileTdmPwMtControlTimeStamp, sleGponProfileTdmPwMtControlReqResult, sleGponProfileTdmPwMtControlIndex, sleGponProfileTdmPwMtControlMaxDepth
				 }
			STATUS current
			DESCRIPTION
				"Description."
			::= { sleGponProfileTdmPwMtNotification 3 }


--  1.3.6.1.4.1.6296.101.23.5.7.1.3.4
		sleGponProfileTdmDesiredDepthChanged NOTIFICATION-TYPE
			OBJECTS { sleGponProfileTdmPwMtControlRequest, sleGponProfileTdmPwMtControlTimeStamp, sleGponProfileTdmPwMtControlReqResult, sleGponProfileTdmPwMtControlIndex, sleGponProfileTdmPwMtControlDesiredDepth
				 }
			STATUS current
			DESCRIPTION
				"Description."
			::= { sleGponProfileTdmPwMtNotification 4 }


--  1.3.6.1.4.1.6296.101.23.5.7.1.3.5
		sleGponProfileTdmFillPolicyChanged NOTIFICATION-TYPE
			OBJECTS { sleGponProfileTdmPwMtControlRequest, sleGponProfileTdmPwMtControlTimeStamp, sleGponProfileTdmPwMtControlReqResult, sleGponProfileTdmPwMtControlIndex, sleGponProfileTdmPwMtControlFillPolicy
				 }
			STATUS current
			DESCRIPTION
				"Description."
			::= { sleGponProfileTdmPwMtNotification 5 }


--  1.3.6.1.4.1.6296.101.23.5.7.1.3.6
		sleGponProfileTdmMisconnectDeclarePolicyChanged NOTIFICATION-TYPE
			OBJECTS { sleGponProfileTdmPwMtControlRequest, sleGponProfileTdmPwMtControlTimeStamp, sleGponProfileTdmPwMtControlReqResult, sleGponProfileTdmPwMtControlIndex, sleGponProfileTdmPwMtControlMisconnectDeclarePolicy
				 }
			STATUS current
			DESCRIPTION
				"Description."
			::= { sleGponProfileTdmPwMtNotification 6 }


--  1.3.6.1.4.1.6296.101.23.5.7.1.3.7
		sleGponProfileTdmMisconnectClearPolicyChanged NOTIFICATION-TYPE
			OBJECTS { sleGponProfileTdmPwMtControlRequest, sleGponProfileTdmPwMtControlTimeStamp, sleGponProfileTdmPwMtControlReqResult, sleGponProfileTdmPwMtControlIndex, sleGponProfileTdmPwMtControlMisconnectClearPolicy
				 }
			STATUS current
			DESCRIPTION
				"Description."
			::= { sleGponProfileTdmPwMtNotification 7 }


--  1.3.6.1.4.1.6296.101.23.5.7.1.3.8
		sleGponProfileTdmLossDeclarePolicyChanged NOTIFICATION-TYPE
			OBJECTS { sleGponProfileTdmPwMtControlRequest, sleGponProfileTdmPwMtControlTimeStamp, sleGponProfileTdmPwMtControlReqResult, sleGponProfileTdmPwMtControlIndex, sleGponProfileTdmPwMtControlLossDeclarePolicy
				 }
			STATUS current
			DESCRIPTION
				"Description."
			::= { sleGponProfileTdmPwMtNotification 8 }


--  1.3.6.1.4.1.6296.101.23.5.7.1.3.9
		sleGponProfileTdmLossClearPolicyChanged NOTIFICATION-TYPE
			OBJECTS { sleGponProfileTdmPwMtControlRequest, sleGponProfileTdmPwMtControlTimeStamp, sleGponProfileTdmPwMtControlReqResult, sleGponProfileTdmPwMtControlIndex, sleGponProfileTdmPwMtControlLossClearPolicy
				 }
			STATUS current
			DESCRIPTION
				"Description."
			::= { sleGponProfileTdmPwMtNotification 9 }


--  1.3.6.1.4.1.6296.101.23.5.7.1.3.10
		sleGponProfileTdmBuffUnderrunDeclarePolicyChanged NOTIFICATION-TYPE
			OBJECTS { sleGponProfileTdmPwMtControlRequest, sleGponProfileTdmPwMtControlTimeStamp, sleGponProfileTdmPwMtControlReqResult, sleGponProfileTdmPwMtControlIndex, sleGponProfileTdmPwMtControlBuffUnderrunDeclarePolicy
				 }
			STATUS current
			DESCRIPTION
				"Description."
			::= { sleGponProfileTdmPwMtNotification 10 }


--  1.3.6.1.4.1.6296.101.23.5.7.1.3.11
		sleGponProfileTdmbuffUnderrunClearPolicyChanged NOTIFICATION-TYPE
			OBJECTS { sleGponProfileTdmPwMtControlRequest, sleGponProfileTdmPwMtControlTimeStamp, sleGponProfileTdmPwMtControlReqResult, sleGponProfileTdmPwMtControlIndex, sleGponProfileTdmPwMtControlBuffUnderrunClearPolicy
				 }
			STATUS current
			DESCRIPTION
				"Description."
			::= { sleGponProfileTdmPwMtNotification 11 }


--  1.3.6.1.4.1.6296.101.23.5.7.1.3.12
		sleGponProfileTdmMalformedDeclarePolicyChanged NOTIFICATION-TYPE
			OBJECTS { sleGponProfileTdmPwMtControlRequest, sleGponProfileTdmPwMtControlTimeStamp, sleGponProfileTdmPwMtControlReqResult, sleGponProfileTdmPwMtControlIndex, sleGponProfileTdmPwMtControlMalformedDeclarePolicy
				 }
			STATUS current
			DESCRIPTION
				"Description."
			::= { sleGponProfileTdmPwMtNotification 12 }


--  1.3.6.1.4.1.6296.101.23.5.7.1.3.13
		sleGponProfileTdmMalformedClearPolicyChanged NOTIFICATION-TYPE
			OBJECTS { sleGponProfileTdmPwMtControlRequest, sleGponProfileTdmPwMtControlTimeStamp, sleGponProfileTdmPwMtControlReqResult, sleGponProfileTdmPwMtControlIndex, sleGponProfileTdmPwMtControlMalformedClearPolicy
				 }
			STATUS current
			DESCRIPTION
				"Description."
			::= { sleGponProfileTdmPwMtNotification 13 }


--  1.3.6.1.4.1.6296.101.23.5.7.1.3.14
		sleGponProfileTdmRBitTransmitPolicyChanged NOTIFICATION-TYPE
			OBJECTS { sleGponProfileTdmPwMtControlRequest, sleGponProfileTdmPwMtControlTimeStamp, sleGponProfileTdmPwMtControlReqResult, sleGponProfileTdmPwMtControlIndex, sleGponProfileTdmPwMtControlRBitTransmitPolicy
				 }
			STATUS current
			DESCRIPTION
				"Description."
			::= { sleGponProfileTdmPwMtNotification 14 }


--  1.3.6.1.4.1.6296.101.23.5.7.1.3.15
		sleGponProfileTdmRBitReceivePolicyChanged NOTIFICATION-TYPE
			OBJECTS { sleGponProfileTdmPwMtControlRequest, sleGponProfileTdmPwMtControlTimeStamp, sleGponProfileTdmPwMtControlReqResult, sleGponProfileTdmPwMtControlIndex, sleGponProfileTdmPwMtControlRBitReceivePolicy
				 }
			STATUS current
			DESCRIPTION
				"Description."
			::= { sleGponProfileTdmPwMtNotification 15 }


--  1.3.6.1.4.1.6296.101.23.5.7.1.3.16
		sleGponProfileTdmLBitReceivePolicyChanged NOTIFICATION-TYPE
			OBJECTS { sleGponProfileTdmPwMtControlRequest, sleGponProfileTdmPwMtControlTimeStamp, sleGponProfileTdmPwMtControlReqResult, sleGponProfileTdmPwMtControlIndex, sleGponProfileTdmPwMtControlLBitReceivePolicy
				 }
			STATUS current
			DESCRIPTION
				"Description."
			::= { sleGponProfileTdmPwMtNotification 16 }


--  1.3.6.1.4.1.6296.101.23.5.7.1.3.17
		sleGponProfileTdmSesThresholdChanged NOTIFICATION-TYPE
			OBJECTS { sleGponProfileTdmPwMtControlRequest, sleGponProfileTdmPwMtControlTimeStamp, sleGponProfileTdmPwMtControlReqResult, sleGponProfileTdmPwMtControlIndex, sleGponProfileTdmPwMtControlSesThreshold
				 }
			STATUS current
			DESCRIPTION
				"Description."
			::= { sleGponProfileTdmPwMtNotification 17 }


--  1.3.6.1.4.1.6296.101.23.5.7.2
		sleGponProfileTdmPw OBJECT IDENTIFIER ::= { sleGponProfileTdm 2 }


--  1.3.6.1.4.1.6296.101.23.5.7.2.1
		sleGponProfileTdmPwTable OBJECT-TYPE
			SYNTAX SEQUENCE OF SleGponProfileTdmPwEntry
			MAX-ACCESS not-accessible
			STATUS current
			DESCRIPTION
				"sleGponProfileTdmPwTable"
			::= { sleGponProfileTdmPw 1 }


--  1.3.6.1.4.1.6296.101.23.5.7.2.1.1
		sleGponProfileTdmPwEntry OBJECT-TYPE
			SYNTAX SleGponProfileTdmPwEntry
			MAX-ACCESS not-accessible
			STATUS current
			DESCRIPTION
				"key: sleGponProfileTdmPwIndex"
			INDEX { sleGponProfileTdmPwIndex }
			::= { sleGponProfileTdmPwTable 1 }


		SleGponProfileTdmPwEntry ::=
			SEQUENCE {
				sleGponProfileTdmPwIndex
					INTEGER,
				sleGponProfileTdmPwName
					OCTET STRING,
				sleGponProfileTdmPwServiceType
					INTEGER,
				sleGponProfileTdmPwSignalling
					INTEGER,
				sleGponProfileTdmPwPayloadSize
					INTEGER,
				sleGponProfileTdmPwPayloadEncapulationDelay
					INTEGER,
				sleGponProfileTdmPwTimingMode
					INTEGER,
				sleGponProfileTdmPwRtpClockRefernce
					INTEGER,
				sleGponProfileTdmPwRtpTimeStampMode
					INTEGER,
				sleGponProfileTdmPwRtpPayloadChannel
					INTEGER,
				sleGponProfileTdmPwRtpPayloadSignalling
					INTEGER,
				sleGponProfileTdmPwRtpSyncSourceChannel
					INTEGER,
				sleGponProfileTdmPwRtpSyncSourceSignalling
					INTEGER,
				sleGponProfileTdmPwRtpExpectPayloadChannel
					INTEGER,
				sleGponProfileTdmPwRtpExpectPaloadSignalling
					INTEGER,
				sleGponProfileTdmPwRtpExpectSyncSourceChannel
					INTEGER,
				sleGponProfileTdmPwRtpExpectSyncSourceSignalling
					INTEGER,
				sleGponProfileTdmPwMtProfileName
					OCTET STRING
			 }

--  1.3.6.1.4.1.6296.101.23.5.7.2.1.1.1
		sleGponProfileTdmPwIndex OBJECT-TYPE
			SYNTAX INTEGER (1..65535)
			MAX-ACCESS read-only
			STATUS current
			DESCRIPTION
				"Tdm pw index"
			::= { sleGponProfileTdmPwEntry 1 }


--  1.3.6.1.4.1.6296.101.23.5.7.2.1.1.2
		sleGponProfileTdmPwName OBJECT-TYPE
			SYNTAX OCTET STRING
			MAX-ACCESS read-only
			STATUS current
			DESCRIPTION
				"TDM pw profile name"
			::= { sleGponProfileTdmPwEntry 2 }


--  1.3.6.1.4.1.6296.101.23.5.7.2.1.1.3
		sleGponProfileTdmPwServiceType OBJECT-TYPE
			SYNTAX INTEGER
				{
				unstructured(0),
				octetAlignedUnstructured(1),
				structured(2)
				}
			MAX-ACCESS read-only
			STATUS current
			DESCRIPTION
				"Configure Basic Service Type"
			::= { sleGponProfileTdmPwEntry 3 }


--  1.3.6.1.4.1.6296.101.23.5.7.2.1.1.4
		sleGponProfileTdmPwSignalling OBJECT-TYPE
			SYNTAX INTEGER
				{
				noSignalling(0),
				casCarryPacket(1),
				casCarryChannel(2)
				}
			MAX-ACCESS read-only
			STATUS current
			DESCRIPTION
				"Configure Signalling"
			::= { sleGponProfileTdmPwEntry 4 }


--  1.3.6.1.4.1.6296.101.23.5.7.2.1.1.5
		sleGponProfileTdmPwPayloadSize OBJECT-TYPE
			SYNTAX INTEGER (0..65535)
			MAX-ACCESS read-only
			STATUS current
			DESCRIPTION
				"Configure Payload bytes per packet"
			::= { sleGponProfileTdmPwEntry 5 }


--  1.3.6.1.4.1.6296.101.23.5.7.2.1.1.6
		sleGponProfileTdmPwPayloadEncapulationDelay OBJECT-TYPE
			SYNTAX INTEGER (0..65535)
			MAX-ACCESS read-only
			STATUS current
			DESCRIPTION
				"Configure Payload Encapsulation Delay (unit :ms)"
			::= { sleGponProfileTdmPwEntry 6 }


--  1.3.6.1.4.1.6296.101.23.5.7.2.1.1.7
		sleGponProfileTdmPwTimingMode OBJECT-TYPE
			SYNTAX INTEGER
				{
				network(0),
				differential(1),
				adaptive(2),
				loop(3)
				}
			MAX-ACCESS read-only
			STATUS current
			DESCRIPTION
				"Configure Timing Mode of the TDM service"
			::= { sleGponProfileTdmPwEntry 7 }


--  1.3.6.1.4.1.6296.101.23.5.7.2.1.1.8
		sleGponProfileTdmPwRtpClockRefernce OBJECT-TYPE
			SYNTAX INTEGER (0..65535)
			MAX-ACCESS read-only
			STATUS current
			DESCRIPTION
				"Configure RTP Clock Reference"
			::= { sleGponProfileTdmPwEntry 8 }


--  1.3.6.1.4.1.6296.101.23.5.7.2.1.1.9
		sleGponProfileTdmPwRtpTimeStampMode OBJECT-TYPE
			SYNTAX INTEGER
				{
				unknown(0),
				absolute(1),
				differential(2)
				}
			MAX-ACCESS read-only
			STATUS current
			DESCRIPTION
				"Configure RTP Time Stamp Mode"
			::= { sleGponProfileTdmPwEntry 9 }


--  1.3.6.1.4.1.6296.101.23.5.7.2.1.1.10
		sleGponProfileTdmPwRtpPayloadChannel OBJECT-TYPE
			SYNTAX INTEGER (0..65535)
			MAX-ACCESS read-only
			STATUS current
			DESCRIPTION
				"Configure RTP Payload Type"
			::= { sleGponProfileTdmPwEntry 10 }


--  1.3.6.1.4.1.6296.101.23.5.7.2.1.1.11
		sleGponProfileTdmPwRtpPayloadSignalling OBJECT-TYPE
			SYNTAX INTEGER (0..65535)
			MAX-ACCESS read-only
			STATUS current
			DESCRIPTION
				"Configure RTP Payload Signalling"
			::= { sleGponProfileTdmPwEntry 11 }


--  1.3.6.1.4.1.6296.101.23.5.7.2.1.1.12
		sleGponProfileTdmPwRtpSyncSourceChannel OBJECT-TYPE
			SYNTAX INTEGER (0..65535)
			MAX-ACCESS read-only
			STATUS current
			DESCRIPTION
				"Configure RTP Synchronization Source"
			::= { sleGponProfileTdmPwEntry 12 }


--  1.3.6.1.4.1.6296.101.23.5.7.2.1.1.13
		sleGponProfileTdmPwRtpSyncSourceSignalling OBJECT-TYPE
			SYNTAX INTEGER (0..65535)
			MAX-ACCESS read-only
			STATUS current
			DESCRIPTION
				"Configure RTP Synchronization Source Signalling"
			::= { sleGponProfileTdmPwEntry 13 }


--  1.3.6.1.4.1.6296.101.23.5.7.2.1.1.14
		sleGponProfileTdmPwRtpExpectPayloadChannel OBJECT-TYPE
			SYNTAX INTEGER (0..65535)
			MAX-ACCESS read-only
			STATUS current
			DESCRIPTION
				"Configure Expected RTP Payload Type"
			::= { sleGponProfileTdmPwEntry 14 }


--  1.3.6.1.4.1.6296.101.23.5.7.2.1.1.15
		sleGponProfileTdmPwRtpExpectPaloadSignalling OBJECT-TYPE
			SYNTAX INTEGER (0..65535)
			MAX-ACCESS read-only
			STATUS current
			DESCRIPTION
				"Configure Expected RTP Payload Signalling"
			::= { sleGponProfileTdmPwEntry 15 }


--  1.3.6.1.4.1.6296.101.23.5.7.2.1.1.16
		sleGponProfileTdmPwRtpExpectSyncSourceChannel OBJECT-TYPE
			SYNTAX INTEGER (0..65535)
			MAX-ACCESS read-only
			STATUS current
			DESCRIPTION
				"Configure Expected RTP Synchronization Source"
			::= { sleGponProfileTdmPwEntry 16 }


--  1.3.6.1.4.1.6296.101.23.5.7.2.1.1.17
		sleGponProfileTdmPwRtpExpectSyncSourceSignalling OBJECT-TYPE
			SYNTAX INTEGER (0..65535)
			MAX-ACCESS read-only
			STATUS current
			DESCRIPTION
				"Configure Expected RTP Synchronization Source Signalling"
			::= { sleGponProfileTdmPwEntry 17 }


--  1.3.6.1.4.1.6296.101.23.5.7.2.1.1.18
		sleGponProfileTdmPwMtProfileName OBJECT-TYPE
			SYNTAX OCTET STRING
			MAX-ACCESS read-only
			STATUS current
			DESCRIPTION
				"Configure PW Maintenance Profile"
			::= { sleGponProfileTdmPwEntry 18 }


--  1.3.6.1.4.1.6296.101.23.5.7.2.2
		sleGponProfileTdmPwControl OBJECT IDENTIFIER ::= { sleGponProfileTdmPw 2 }


--  1.3.6.1.4.1.6296.101.23.5.7.2.2.1
		sleGponProfileTdmPwControlRequest OBJECT-TYPE
			SYNTAX INTEGER
				{
				createProfile(1),
				destroyProfile(2),
				setServiceType(3),
				setSignalling(4),
				setPayloadSize(5),
				setPayloadEncapsulationDelay(6),
				setTimingMode(7),
				setRtpClockReference(8),
				setRtpTimeStampmode(9),
				setRtpPayloadType(10),
				setRtpSyncSource(11),
				setRtpExpectPayloadType(12),
				setRtpExpectSyncSource(13),
				setMtProfile(14)
				}
			MAX-ACCESS read-write
			STATUS current
			DESCRIPTION
				"The request of a user command"
			::= { sleGponProfileTdmPwControl 1 }


--  1.3.6.1.4.1.6296.101.23.5.7.2.2.2
		sleGponProfileTdmPwControlStatus OBJECT-TYPE
			SYNTAX SleControlStatusType
			MAX-ACCESS read-only
			STATUS current
			DESCRIPTION
				"The status of user command"
			::= { sleGponProfileTdmPwControl 2 }


--  1.3.6.1.4.1.6296.101.23.5.7.2.2.3
		sleGponProfileTdmPwControlTimer OBJECT-TYPE
			SYNTAX Gauge32
			MAX-ACCESS read-write
			STATUS current
			DESCRIPTION
				"The maximum time for the manager for a long running user command"
			::= { sleGponProfileTdmPwControl 3 }


--  1.3.6.1.4.1.6296.101.23.5.7.2.2.4
		sleGponProfileTdmPwControlTimeStamp OBJECT-TYPE
			SYNTAX TimeTicks
			MAX-ACCESS read-only
			STATUS current
			DESCRIPTION
				"The time stamp of the last command(end of command)"
			::= { sleGponProfileTdmPwControl 4 }


--  1.3.6.1.4.1.6296.101.23.5.7.2.2.5
		sleGponProfileTdmPwControlReqResult OBJECT-TYPE
			SYNTAX SleControlRequestResultType
			MAX-ACCESS read-only
			STATUS current
			DESCRIPTION
				"The result of the last user command"
			::= { sleGponProfileTdmPwControl 5 }


--  1.3.6.1.4.1.6296.101.23.5.7.2.2.6
		sleGponProfileTdmPwControlIndex OBJECT-TYPE
			SYNTAX INTEGER (0..65535)
			MAX-ACCESS read-write
			STATUS current
			DESCRIPTION
				"Tdm pw index"
			::= { sleGponProfileTdmPwControl 6 }


--  1.3.6.1.4.1.6296.101.23.5.7.2.2.7
		sleGponProfileTdmPwControlName OBJECT-TYPE
			SYNTAX OCTET STRING
			MAX-ACCESS read-write
			STATUS current
			DESCRIPTION
				"TDM pw profile name"
			::= { sleGponProfileTdmPwControl 7 }


--  1.3.6.1.4.1.6296.101.23.5.7.2.2.8
		sleGponProfileTdmPwControlServiceType OBJECT-TYPE
			SYNTAX INTEGER
				{
				unstructured(0),
				octetAlignedUnstructured(1),
				structured(2)
				}
			MAX-ACCESS read-write
			STATUS current
			DESCRIPTION
				"Configure Basic Service Type"
			::= { sleGponProfileTdmPwControl 8 }


--  1.3.6.1.4.1.6296.101.23.5.7.2.2.9
		sleGponProfileTdmPwControlSignalling OBJECT-TYPE
			SYNTAX INTEGER
				{
				noSignalling(0),
				casCarryPacket(1),
				casCarryChannel(2)
				}
			MAX-ACCESS read-write
			STATUS current
			DESCRIPTION
				"Configure Signalling"
			::= { sleGponProfileTdmPwControl 9 }


--  1.3.6.1.4.1.6296.101.23.5.7.2.2.10
		sleGponProfileTdmPwControlPayloadSize OBJECT-TYPE
			SYNTAX INTEGER (0..65535)
			MAX-ACCESS read-write
			STATUS current
			DESCRIPTION
				"Configure Payload bytes per packet"
			::= { sleGponProfileTdmPwControl 10 }


--  1.3.6.1.4.1.6296.101.23.5.7.2.2.11
		sleGponProfileTdmPwControlPayloadEncapulationDelay OBJECT-TYPE
			SYNTAX INTEGER (0..65535)
			MAX-ACCESS read-write
			STATUS current
			DESCRIPTION
				"Configure Payload Encapsulation Delay (unit :ms)"
			::= { sleGponProfileTdmPwControl 11 }


--  1.3.6.1.4.1.6296.101.23.5.7.2.2.12
		sleGponProfileTdmPwControlTimingMode OBJECT-TYPE
			SYNTAX INTEGER
				{
				network(0),
				absolute(1),
				differential(2)
				}
			MAX-ACCESS read-write
			STATUS current
			DESCRIPTION
				"Configure Timing Mode of the TDM service"
			::= { sleGponProfileTdmPwControl 12 }


--  1.3.6.1.4.1.6296.101.23.5.7.2.2.13
		sleGponProfileTdmPwControlRtpClockRefernce OBJECT-TYPE
			SYNTAX INTEGER (0..65535)
			MAX-ACCESS read-write
			STATUS current
			DESCRIPTION
				"Configure RTP Clock Reference"
			::= { sleGponProfileTdmPwControl 13 }


--  1.3.6.1.4.1.6296.101.23.5.7.2.2.14
		sleGponProfileTdmPwControlRtpTimeStampMode OBJECT-TYPE
			SYNTAX INTEGER
				{
				unknown(0),
				absolute(1),
				differential(2)
				}
			MAX-ACCESS read-write
			STATUS current
			DESCRIPTION
				"Configure RTP Time Stamp Mode"
			::= { sleGponProfileTdmPwControl 14 }


--  1.3.6.1.4.1.6296.101.23.5.7.2.2.15
		sleGponProfileTdmPwControlRtpPayloadChannel OBJECT-TYPE
			SYNTAX INTEGER (0..65535)
			MAX-ACCESS read-write
			STATUS current
			DESCRIPTION
				"Configure RTP Payload Type"
			::= { sleGponProfileTdmPwControl 15 }


--  1.3.6.1.4.1.6296.101.23.5.7.2.2.16
		sleGponProfileTdmPwControlRtpPayloadSignalling OBJECT-TYPE
			SYNTAX INTEGER (0..65535)
			MAX-ACCESS read-write
			STATUS current
			DESCRIPTION
				"Configure RTP Payload Signalling"
			::= { sleGponProfileTdmPwControl 16 }


--  1.3.6.1.4.1.6296.101.23.5.7.2.2.17
		sleGponProfileTdmPwControlRtpSyncSourceChannel OBJECT-TYPE
			SYNTAX INTEGER (0..65535)
			MAX-ACCESS read-write
			STATUS current
			DESCRIPTION
				"Configure RTP Synchronization Source"
			::= { sleGponProfileTdmPwControl 17 }


--  1.3.6.1.4.1.6296.101.23.5.7.2.2.18
		sleGponProfileTdmPwControlRtpSyncSourceSignalling OBJECT-TYPE
			SYNTAX INTEGER (0..65535)
			MAX-ACCESS read-write
			STATUS current
			DESCRIPTION
				"Configure RTP Synchronization Source Signalling"
			::= { sleGponProfileTdmPwControl 18 }


--  1.3.6.1.4.1.6296.101.23.5.7.2.2.19
		sleGponProfileTdmPwControlRtpExpectPayloadChannel OBJECT-TYPE
			SYNTAX INTEGER (0..65535)
			MAX-ACCESS read-write
			STATUS current
			DESCRIPTION
				"Configure Expected RTP Payload Type"
			::= { sleGponProfileTdmPwControl 19 }


--  1.3.6.1.4.1.6296.101.23.5.7.2.2.20
		sleGponProfileTdmPwControlRtpExpectPaloadSignalling OBJECT-TYPE
			SYNTAX INTEGER (0..65535)
			MAX-ACCESS read-write
			STATUS current
			DESCRIPTION
				"Configure Expected RTP Payload Signalling"
			::= { sleGponProfileTdmPwControl 20 }


--  1.3.6.1.4.1.6296.101.23.5.7.2.2.21
		sleGponProfileTdmPwControlRtpExpectSyncSourceChannel OBJECT-TYPE
			SYNTAX INTEGER (0..65535)
			MAX-ACCESS read-write
			STATUS current
			DESCRIPTION
				"Configure Expected RTP Synchronization Source"
			::= { sleGponProfileTdmPwControl 21 }


--  1.3.6.1.4.1.6296.101.23.5.7.2.2.22
		sleGponProfileTdmPwControlRtpExpectSyncSourceSignalling OBJECT-TYPE
			SYNTAX INTEGER (0..65535)
			MAX-ACCESS read-write
			STATUS current
			DESCRIPTION
				"Configure Expected RTP Synchronization Source Signalling"
			::= { sleGponProfileTdmPwControl 22 }


--  1.3.6.1.4.1.6296.101.23.5.7.2.2.23
		sleGponProfileTdmPwControlMtProfileName OBJECT-TYPE
			SYNTAX OCTET STRING
			MAX-ACCESS read-write
			STATUS current
			DESCRIPTION
				"Configure PW Maintenance Profile"
			::= { sleGponProfileTdmPwControl 23 }


--  1.3.6.1.4.1.6296.101.23.5.7.2.3
		sleGponProfileTdmPwNotification OBJECT IDENTIFIER ::= { sleGponProfileTdmPw 3 }


--  1.3.6.1.4.1.6296.101.23.5.7.2.3.1
		sleGponProfileTdmPwProfileCreated NOTIFICATION-TYPE
			OBJECTS { sleGponProfileTdmPwControlRequest, sleGponProfileTdmPwControlTimeStamp, sleGponProfileTdmPwControlReqResult, sleGponProfileTdmPwControlName }
			STATUS current
			DESCRIPTION
				"Description."
			::= { sleGponProfileTdmPwNotification 1 }


--  1.3.6.1.4.1.6296.101.23.5.7.2.3.2
		sleGponProfileTdmPwProfileDeleted NOTIFICATION-TYPE
			OBJECTS { sleGponProfileTdmPwControlRequest, sleGponProfileTdmPwControlTimeStamp, sleGponProfileTdmPwControlReqResult, sleGponProfileTdmPwControlIndex }
			STATUS current
			DESCRIPTION
				"Description."
			::= { sleGponProfileTdmPwNotification 2 }


--  1.3.6.1.4.1.6296.101.23.5.7.2.3.3
		sleGponProfileTdmPwServiceTypeChanged NOTIFICATION-TYPE
			OBJECTS { sleGponProfileTdmPwControlRequest, sleGponProfileTdmPwControlTimeStamp, sleGponProfileTdmPwControlReqResult, sleGponProfileTdmPwControlIndex, sleGponProfileTdmPwControlServiceType
				 }
			STATUS current
			DESCRIPTION
				"Description."
			::= { sleGponProfileTdmPwNotification 3 }


--  1.3.6.1.4.1.6296.101.23.5.7.2.3.4
		sleGponProfileTdmPwSignallingChanged NOTIFICATION-TYPE
			OBJECTS { sleGponProfileTdmPwControlRequest, sleGponProfileTdmPwControlTimeStamp, sleGponProfileTdmPwControlReqResult, sleGponProfileTdmPwControlIndex, sleGponProfileTdmPwControlSignalling
				 }
			STATUS current
			DESCRIPTION
				"Description."
			::= { sleGponProfileTdmPwNotification 4 }


--  1.3.6.1.4.1.6296.101.23.5.7.2.3.5
		sleGponProfileTdmPwPayloadSizeChanged NOTIFICATION-TYPE
			OBJECTS { sleGponProfileTdmPwControlRequest, sleGponProfileTdmPwControlTimeStamp, sleGponProfileTdmPwControlReqResult, sleGponProfileTdmPwControlIndex, sleGponProfileTdmPwControlPayloadSize
				 }
			STATUS current
			DESCRIPTION
				"Description."
			::= { sleGponProfileTdmPwNotification 5 }


--  1.3.6.1.4.1.6296.101.23.5.7.2.3.6
		sleGponProfileTdmPwPayloadEncapsulationDelayChanged NOTIFICATION-TYPE
			OBJECTS { sleGponProfileTdmPwControlRequest, sleGponProfileTdmPwControlTimeStamp, sleGponProfileTdmPwControlReqResult, sleGponProfileTdmPwControlIndex, sleGponProfileTdmPwControlPayloadEncapulationDelay
				 }
			STATUS current
			DESCRIPTION
				"Description."
			::= { sleGponProfileTdmPwNotification 6 }


--  1.3.6.1.4.1.6296.101.23.5.7.2.3.7
		sleGponProfileTdmPwTimingModeChanged NOTIFICATION-TYPE
			OBJECTS { sleGponProfileTdmPwControlRequest, sleGponProfileTdmPwControlTimeStamp, sleGponProfileTdmPwControlReqResult, sleGponProfileTdmPwControlIndex, sleGponProfileTdmPwControlTimingMode
				 }
			STATUS current
			DESCRIPTION
				"Description."
			::= { sleGponProfileTdmPwNotification 7 }


--  1.3.6.1.4.1.6296.101.23.5.7.2.3.8
		sleGponProfileTdmPwRtpClockReferenceChanged NOTIFICATION-TYPE
			OBJECTS { sleGponProfileTdmPwControlRequest, sleGponProfileTdmPwControlTimeStamp, sleGponProfileTdmPwControlReqResult, sleGponProfileTdmPwControlIndex, sleGponProfileTdmPwControlRtpClockRefernce
				 }
			STATUS current
			DESCRIPTION
				"Description."
			::= { sleGponProfileTdmPwNotification 8 }


--  1.3.6.1.4.1.6296.101.23.5.7.2.3.9
		sleGponProfileTdmPwRtpTimeStampmodeChanged NOTIFICATION-TYPE
			OBJECTS { sleGponProfileTdmPwControlRequest, sleGponProfileTdmPwControlTimeStamp, sleGponProfileTdmPwControlReqResult, sleGponProfileTdmPwControlIndex, sleGponProfileTdmPwControlRtpTimeStampMode
				 }
			STATUS current
			DESCRIPTION
				"Description."
			::= { sleGponProfileTdmPwNotification 9 }


--  1.3.6.1.4.1.6296.101.23.5.7.2.3.10
		sleGponProfileTdmPwRtpPayloadTypeChanged NOTIFICATION-TYPE
			OBJECTS { sleGponProfileTdmPwControlRequest, sleGponProfileTdmPwControlTimeStamp, sleGponProfileTdmPwControlReqResult, sleGponProfileTdmPwControlIndex, sleGponProfileTdmPwControlRtpPayloadChannel,
				sleGponProfileTdmPwControlRtpPayloadSignalling }
			STATUS current
			DESCRIPTION
				"Description."
			::= { sleGponProfileTdmPwNotification 10 }


--  1.3.6.1.4.1.6296.101.23.5.7.2.3.11
		sleGponProfileTdmPwRtpSyncSourceChanged NOTIFICATION-TYPE
			OBJECTS { sleGponProfileTdmPwControlRequest, sleGponProfileTdmPwControlTimeStamp, sleGponProfileTdmPwControlReqResult, sleGponProfileTdmPwControlIndex, sleGponProfileTdmPwControlRtpSyncSourceChannel,
				sleGponProfileTdmPwControlRtpSyncSourceSignalling }
			STATUS current
			DESCRIPTION
				"Description."
			::= { sleGponProfileTdmPwNotification 11 }


--  1.3.6.1.4.1.6296.101.23.5.7.2.3.12
		sleGponProfileTdmPwRtpExpectPayloadTypeChanged NOTIFICATION-TYPE
			OBJECTS { sleGponProfileTdmPwControlRequest, sleGponProfileTdmPwControlTimeStamp, sleGponProfileTdmPwControlReqResult, sleGponProfileTdmPwControlIndex, sleGponProfileTdmPwControlRtpExpectPayloadChannel,
				sleGponProfileTdmPwControlRtpExpectPaloadSignalling }
			STATUS current
			DESCRIPTION
				"Description."
			::= { sleGponProfileTdmPwNotification 12 }


--  1.3.6.1.4.1.6296.101.23.5.7.2.3.13
		sleGponProfileTdmPwRtpExpectSyncSourceChanged NOTIFICATION-TYPE
			OBJECTS { sleGponProfileTdmPwControlRequest, sleGponProfileTdmPwControlTimeStamp, sleGponProfileTdmPwControlReqResult, sleGponProfileTdmPwControlIndex, sleGponProfileTdmPwControlRtpExpectSyncSourceChannel,
				sleGponProfileTdmPwControlRtpExpectSyncSourceSignalling }
			STATUS current
			DESCRIPTION
				"Description."
			::= { sleGponProfileTdmPwNotification 13 }


--  1.3.6.1.4.1.6296.101.23.5.7.2.3.14
		sleGponProfileTdmPwMtProfileChanged NOTIFICATION-TYPE
			OBJECTS { sleGponProfileTdmPwControlRequest, sleGponProfileTdmPwControlTimeStamp, sleGponProfileTdmPwControlReqResult, sleGponProfileTdmPwControlIndex, sleGponProfileTdmPwControlMtProfileName
				 }
			STATUS current
			DESCRIPTION
				"Description."
			::= { sleGponProfileTdmPwNotification 14 }


--   1.3.6.1.4.1.6296.101.23.5.7.3
-- 1.3.6.1.4.1.6296.101.23.5.7.3
		sleGponProfileTdmSdh OBJECT IDENTIFIER ::= { sleGponProfileTdm 3 }


--   1.3.6.1.4.1.6296.101.23.5.7.3.1
-- 1.3.6.1.4.1.6296.101.23.5.7.3.1
		sleGponProfileTdmSdhTable OBJECT-TYPE
			SYNTAX SEQUENCE OF SleGponProfileTdmSdhEntry
			MAX-ACCESS not-accessible
			STATUS current
			DESCRIPTION
				"sleGponProfileTdmSdhTable"
			::= { sleGponProfileTdmSdh 1 }


--   1.3.6.1.4.1.6296.101.23.5.7.3.1.1
-- 1.3.6.1.4.1.6296.101.23.5.7.3.1.1
		sleGponProfileTdmSdhEntry OBJECT-TYPE
			SYNTAX SleGponProfileTdmSdhEntry
			MAX-ACCESS not-accessible
			STATUS current
			DESCRIPTION
				"key: sleGponProfileTdmSdhIndex"
			INDEX { sleGponProfileTdmSdhIndex }
			::= { sleGponProfileTdmSdhTable 1 }


		SleGponProfileTdmSdhEntry ::=
			SEQUENCE {
				sleGponProfileTdmSdhIndex
					INTEGER,
				sleGponProfileTdmSdhName
					OCTET STRING,
				sleGponProfileTdmSdhTuType
					INTEGER,
				sleGponProfileTdmSdhGemLossIntergrationPeriod
					INTEGER,
				sleGponProfileTdmSdhTransmitJ1J2
					INTEGER,
				sleGponProfileTdmSdhExpectJ1J2
					INTEGER,
				sleGponProfileTdmSdhReceiveJ1J2
					INTEGER,
				sleGponProfileTdmSdhTimMonitor
					INTEGER,
				sleGponProfileTdmSdhTimAis
					INTEGER
			 }

--   1.3.6.1.4.1.6296.101.23.5.7.3.1.1.1
-- 1.3.6.1.4.1.6296.101.23.5.7.3.1.1.1
		sleGponProfileTdmSdhIndex OBJECT-TYPE
			SYNTAX INTEGER (1..65535)
			MAX-ACCESS read-only
			STATUS current
			DESCRIPTION
				"sleGponProfileTdmSdhIndex (unused)"
			::= { sleGponProfileTdmSdhEntry 1 }


--   1.3.6.1.4.1.6296.101.23.5.7.3.1.1.2
-- 1.3.6.1.4.1.6296.101.23.5.7.3.1.1.2
		sleGponProfileTdmSdhName OBJECT-TYPE
			SYNTAX OCTET STRING
			MAX-ACCESS read-only
			STATUS current
			DESCRIPTION
				"sleGponProfileTdmSdhName (unused)"
			::= { sleGponProfileTdmSdhEntry 2 }


--   1.3.6.1.4.1.6296.101.23.5.7.3.1.1.3
-- 1.3.6.1.4.1.6296.101.23.5.7.3.1.1.3
		sleGponProfileTdmSdhTuType OBJECT-TYPE
			SYNTAX INTEGER
				{
				tu11(0),
				tu12(1),
				tu2(2),
				tu3(3)
				}
			MAX-ACCESS read-only
			STATUS current
			DESCRIPTION
				"sleGponProfileTdmSdhTuType (unused)"
			::= { sleGponProfileTdmSdhEntry 3 }


--   1.3.6.1.4.1.6296.101.23.5.7.3.1.1.4
-- 1.3.6.1.4.1.6296.101.23.5.7.3.1.1.4
		sleGponProfileTdmSdhGemLossIntergrationPeriod OBJECT-TYPE
			SYNTAX INTEGER (1..65535)
			MAX-ACCESS read-only
			STATUS current
			DESCRIPTION
				"sleGponProfileTdmSdhGemLossIntergrationPeriod (unused)"
			::= { sleGponProfileTdmSdhEntry 4 }


--   1.3.6.1.4.1.6296.101.23.5.7.3.1.1.5
-- 1.3.6.1.4.1.6296.101.23.5.7.3.1.1.5
		sleGponProfileTdmSdhTransmitJ1J2 OBJECT-TYPE
			SYNTAX INTEGER (1..65535)
			MAX-ACCESS read-only
			STATUS current
			DESCRIPTION
				"sleGponProfileTdmSdhTransmitJ1J2 (unused)"
			::= { sleGponProfileTdmSdhEntry 5 }


--   1.3.6.1.4.1.6296.101.23.5.7.3.1.1.6
-- 1.3.6.1.4.1.6296.101.23.5.7.3.1.1.6
		sleGponProfileTdmSdhExpectJ1J2 OBJECT-TYPE
			SYNTAX INTEGER (1..65535)
			MAX-ACCESS read-only
			STATUS current
			DESCRIPTION
				"sleGponProfileTdmSdhExpectJ1J2 (unused)"
			::= { sleGponProfileTdmSdhEntry 6 }


--   1.3.6.1.4.1.6296.101.23.5.7.3.1.1.7
-- 1.3.6.1.4.1.6296.101.23.5.7.3.1.1.7
		sleGponProfileTdmSdhReceiveJ1J2 OBJECT-TYPE
			SYNTAX INTEGER (1..65535)
			MAX-ACCESS read-only
			STATUS current
			DESCRIPTION
				"sleGponProfileTdmSdhReceiveJ1J2 (unused)"
			::= { sleGponProfileTdmSdhEntry 7 }


--   1.3.6.1.4.1.6296.101.23.5.7.3.1.1.8
-- 1.3.6.1.4.1.6296.101.23.5.7.3.1.1.8
		sleGponProfileTdmSdhTimMonitor OBJECT-TYPE
			SYNTAX INTEGER
				{
				disable(0),
				enable(1)
				}
			MAX-ACCESS read-only
			STATUS current
			DESCRIPTION
				"sleGponProfileTdmSdhTimMonitor (unused)"
			::= { sleGponProfileTdmSdhEntry 8 }


--   1.3.6.1.4.1.6296.101.23.5.7.3.1.1.9
-- 1.3.6.1.4.1.6296.101.23.5.7.3.1.1.9
		sleGponProfileTdmSdhTimAis OBJECT-TYPE
			SYNTAX INTEGER
				{
				disable(0),
				enable(1)
				}
			MAX-ACCESS read-only
			STATUS current
			DESCRIPTION
				"sleGponProfileTdmSdhTimAis (unused)"
			::= { sleGponProfileTdmSdhEntry 9 }


--   1.3.6.1.4.1.6296.101.23.5.7.3.2
-- 1.3.6.1.4.1.6296.101.23.5.7.3.2
		sleGponProfileTdmSdhControl OBJECT IDENTIFIER ::= { sleGponProfileTdmSdh 2 }


--   1.3.6.1.4.1.6296.101.23.5.7.3.2.1
-- 1.3.6.1.4.1.6296.101.23.5.7.3.2.1
		sleGponProfileTdmSdhControlRequest OBJECT-TYPE
			SYNTAX INTEGER
				{
				createProfile(1),
				destroyProfile(2),
				setTuType(3),
				setGemLossIntergrationPeriod(4),
				setTransmitJ1J2(5),
				setExpectJ1J2(6),
				setreceiveJ1J2(7),
				setTimMonitor(8),
				setTimAis(9)
				}
			MAX-ACCESS read-write
			STATUS current
			DESCRIPTION
				"The request of a user command"
			::= { sleGponProfileTdmSdhControl 1 }


--   1.3.6.1.4.1.6296.101.23.5.7.3.2.2
-- 1.3.6.1.4.1.6296.101.23.5.7.3.2.2
		sleGponProfileTdmSdhControlStatus OBJECT-TYPE
			SYNTAX SleControlStatusType
			MAX-ACCESS read-only
			STATUS current
			DESCRIPTION
				"The status of user command"
			::= { sleGponProfileTdmSdhControl 2 }


--   1.3.6.1.4.1.6296.101.23.5.7.3.2.3
-- 1.3.6.1.4.1.6296.101.23.5.7.3.2.3
		sleGponProfileTdmSdhControlTimer OBJECT-TYPE
			SYNTAX Gauge32
			MAX-ACCESS read-write
			STATUS current
			DESCRIPTION
				"The maximum time for the manager for a long running user command"
			::= { sleGponProfileTdmSdhControl 3 }


--   1.3.6.1.4.1.6296.101.23.5.7.3.2.4
-- 1.3.6.1.4.1.6296.101.23.5.7.3.2.4
		sleGponProfileTdmSdhControlTimeStamp OBJECT-TYPE
			SYNTAX TimeTicks
			MAX-ACCESS read-only
			STATUS current
			DESCRIPTION
				"The time stamp of the last command(end of command)"
			::= { sleGponProfileTdmSdhControl 4 }


--   1.3.6.1.4.1.6296.101.23.5.7.3.2.5
-- 1.3.6.1.4.1.6296.101.23.5.7.3.2.5
		sleGponProfileTdmSdhControlReqResult OBJECT-TYPE
			SYNTAX SleControlRequestResultType
			MAX-ACCESS read-only
			STATUS current
			DESCRIPTION
				"The result of the last user command"
			::= { sleGponProfileTdmSdhControl 5 }


--   1.3.6.1.4.1.6296.101.23.5.7.3.2.6
-- 1.3.6.1.4.1.6296.101.23.5.7.3.2.6
		sleGponProfileTdmSdhControlIndex OBJECT-TYPE
			SYNTAX INTEGER (1..65535)
			MAX-ACCESS read-write
			STATUS current
			DESCRIPTION
				"sleGponProfileTdmSdhControlIndex (unused)"
			::= { sleGponProfileTdmSdhControl 6 }


--   1.3.6.1.4.1.6296.101.23.5.7.3.2.7
-- 1.3.6.1.4.1.6296.101.23.5.7.3.2.7
		sleGponProfileTdmSdhControlName OBJECT-TYPE
			SYNTAX OCTET STRING
			MAX-ACCESS read-write
			STATUS current
			DESCRIPTION
				"sleGponProfileTdmSdhControlName (unused)"
			::= { sleGponProfileTdmSdhControl 7 }


--   1.3.6.1.4.1.6296.101.23.5.7.3.2.8
-- 1.3.6.1.4.1.6296.101.23.5.7.3.2.8
		sleGponProfileTdmSdhControlTuType OBJECT-TYPE
			SYNTAX INTEGER
				{
				tu11(0),
				tu12(1),
				tu2(2),
				tu3(3)
				}
			MAX-ACCESS read-write
			STATUS current
			DESCRIPTION
				"sleGponProfileTdmSdhControlTuType (unused)"
			::= { sleGponProfileTdmSdhControl 8 }


--   1.3.6.1.4.1.6296.101.23.5.7.3.2.9
-- 1.3.6.1.4.1.6296.101.23.5.7.3.2.9
		sleGponProfileTdmSdhControlGemLossIntergrationPeriod OBJECT-TYPE
			SYNTAX INTEGER (1..65535)
			MAX-ACCESS read-write
			STATUS current
			DESCRIPTION
				"sleGponProfileTdmSdhControlGemLossIntergrationPeriod (unused)"
			::= { sleGponProfileTdmSdhControl 9 }


--   1.3.6.1.4.1.6296.101.23.5.7.3.2.10
-- 1.3.6.1.4.1.6296.101.23.5.7.3.2.10
		sleGponProfileTdmSdhControlTransmitJ1J2 OBJECT-TYPE
			SYNTAX INTEGER (1..65535)
			MAX-ACCESS read-write
			STATUS current
			DESCRIPTION
				"sleGponProfileTdmSdhControlTransmitJ1J2 (unused)"
			::= { sleGponProfileTdmSdhControl 10 }


--   1.3.6.1.4.1.6296.101.23.5.7.3.2.11
-- 1.3.6.1.4.1.6296.101.23.5.7.3.2.11
		sleGponProfileTdmSdhControlExpectJ1J2 OBJECT-TYPE
			SYNTAX INTEGER (1..65535)
			MAX-ACCESS read-write
			STATUS current
			DESCRIPTION
				"sleGponProfileTdmSdhControlExpectJ1J2 (unused)"
			::= { sleGponProfileTdmSdhControl 11 }


--   1.3.6.1.4.1.6296.101.23.5.7.3.2.12
-- 1.3.6.1.4.1.6296.101.23.5.7.3.2.12
		sleGponProfileTdmSdhControlReceiveJ1J2 OBJECT-TYPE
			SYNTAX INTEGER (1..65535)
			MAX-ACCESS read-write
			STATUS current
			DESCRIPTION
				"sleGponProfileTdmSdhControlReceiveJ1J2 (unused)"
			::= { sleGponProfileTdmSdhControl 12 }


--   1.3.6.1.4.1.6296.101.23.5.7.3.2.13
-- 1.3.6.1.4.1.6296.101.23.5.7.3.2.13
		sleGponProfileTdmSdhControlTimMonitor OBJECT-TYPE
			SYNTAX INTEGER
				{
				disable(0),
				enable(1)
				}
			MAX-ACCESS read-write
			STATUS current
			DESCRIPTION
				"sleGponProfileTdmSdhControlTimMonitor (unused)"
			::= { sleGponProfileTdmSdhControl 13 }


--   1.3.6.1.4.1.6296.101.23.5.7.3.2.14
-- 1.3.6.1.4.1.6296.101.23.5.7.3.2.14
		sleGponProfileTdmSdhControlTimAis OBJECT-TYPE
			SYNTAX INTEGER
				{
				disable(0),
				enable(1)
				}
			MAX-ACCESS read-write
			STATUS current
			DESCRIPTION
				"sleGponProfileTdmSdhControlTimAis (unused)"
			::= { sleGponProfileTdmSdhControl 14 }


--   1.3.6.1.4.1.6296.101.23.5.7.3.3
-- 1.3.6.1.4.1.6296.101.23.5.7.3.3
		sleGponProfileTdmSdhNotification OBJECT IDENTIFIER ::= { sleGponProfileTdmSdh 3 }


--   1.3.6.1.4.1.6296.101.23.5.7.3.3.1
-- 1.3.6.1.4.1.6296.101.23.5.7.3.3.1
		sleGponProfileTdmSdhProfileCreated NOTIFICATION-TYPE
			OBJECTS { sleGponProfileTdmSdhControlRequest, sleGponProfileTdmSdhControlTimeStamp, sleGponProfileTdmSdhControlReqResult, sleGponProfileTdmSdhControlName }
			STATUS current
			DESCRIPTION
				"Description."
			::= { sleGponProfileTdmSdhNotification 1 }


--   1.3.6.1.4.1.6296.101.23.5.7.3.3.2
-- 1.3.6.1.4.1.6296.101.23.5.7.3.3.2
		sleGponProfileTdmSdhProfileDeleted NOTIFICATION-TYPE
			OBJECTS { sleGponProfileTdmSdhControlRequest, sleGponProfileTdmSdhControlTimeStamp, sleGponProfileTdmSdhControlReqResult, sleGponProfileTdmSdhControlIndex }
			STATUS current
			DESCRIPTION
				"Description."
			::= { sleGponProfileTdmSdhNotification 2 }


--   1.3.6.1.4.1.6296.101.23.5.7.3.3.3
-- 1.3.6.1.4.1.6296.101.23.5.7.3.3.3
		sleGponProfileTdmSdhTuTypeChanged NOTIFICATION-TYPE
			OBJECTS { sleGponProfileTdmSdhControlRequest, sleGponProfileTdmSdhControlTimeStamp, sleGponProfileTdmSdhControlReqResult, sleGponProfileTdmSdhControlIndex, sleGponProfileTdmSdhControlTuType
				 }
			STATUS current
			DESCRIPTION
				"Description."
			::= { sleGponProfileTdmSdhNotification 3 }


--   1.3.6.1.4.1.6296.101.23.5.7.3.3.4
-- 1.3.6.1.4.1.6296.101.23.5.7.3.3.4
		sleGponProfileTdmSdhGemLossIntergrationPeriodChanged NOTIFICATION-TYPE
			OBJECTS { sleGponProfileTdmSdhControlRequest, sleGponProfileTdmSdhControlTimeStamp, sleGponProfileTdmSdhControlReqResult, sleGponProfileTdmSdhControlIndex, sleGponProfileTdmSdhControlGemLossIntergrationPeriod
				 }
			STATUS current
			DESCRIPTION
				"Description."
			::= { sleGponProfileTdmSdhNotification 4 }


--   1.3.6.1.4.1.6296.101.23.5.7.3.3.5
-- 1.3.6.1.4.1.6296.101.23.5.7.3.3.5
		sleGponProfileTdmSdhTransmitJ1J2Changed NOTIFICATION-TYPE
			OBJECTS { sleGponProfileTdmSdhControlRequest, sleGponProfileTdmSdhControlTimeStamp, sleGponProfileTdmSdhControlReqResult, sleGponProfileTdmSdhControlIndex, sleGponProfileTdmSdhControlTransmitJ1J2
				 }
			STATUS current
			DESCRIPTION
				"Description."
			::= { sleGponProfileTdmSdhNotification 5 }


--   1.3.6.1.4.1.6296.101.23.5.7.3.3.6
-- 1.3.6.1.4.1.6296.101.23.5.7.3.3.6
		sleGponProfileTdmSdhExpectJ1J2Changed NOTIFICATION-TYPE
			OBJECTS { sleGponProfileTdmSdhControlRequest, sleGponProfileTdmSdhControlTimeStamp, sleGponProfileTdmSdhControlReqResult, sleGponProfileTdmSdhControlIndex, sleGponProfileTdmSdhControlExpectJ1J2
				 }
			STATUS current
			DESCRIPTION
				"Description."
			::= { sleGponProfileTdmSdhNotification 6 }


--   1.3.6.1.4.1.6296.101.23.5.7.3.3.7
-- 1.3.6.1.4.1.6296.101.23.5.7.3.3.7
		sleGponProfileTdmSdhreceiveJ1J2Changed NOTIFICATION-TYPE
			OBJECTS { sleGponProfileTdmSdhControlRequest, sleGponProfileTdmSdhControlTimeStamp, sleGponProfileTdmSdhControlReqResult, sleGponProfileTdmSdhControlIndex, sleGponProfileTdmSdhControlReceiveJ1J2
				 }
			STATUS current
			DESCRIPTION
				"Description."
			::= { sleGponProfileTdmSdhNotification 7 }


--   1.3.6.1.4.1.6296.101.23.5.7.3.3.8
-- 1.3.6.1.4.1.6296.101.23.5.7.3.3.8
		sleGponProfileTdmSdhTimMonitorChanged NOTIFICATION-TYPE
			OBJECTS { sleGponProfileTdmSdhControlRequest, sleGponProfileTdmSdhControlTimeStamp, sleGponProfileTdmSdhControlReqResult, sleGponProfileTdmSdhControlIndex, sleGponProfileTdmSdhControlTimMonitor
				 }
			STATUS current
			DESCRIPTION
				"Description."
			::= { sleGponProfileTdmSdhNotification 8 }


--   1.3.6.1.4.1.6296.101.23.5.7.3.3.9
-- 1.3.6.1.4.1.6296.101.23.5.7.3.3.9
		sleGponProfileTdmSdhTimAisChanged NOTIFICATION-TYPE
			OBJECTS { sleGponProfileTdmSdhControlRequest, sleGponProfileTdmSdhControlTimeStamp, sleGponProfileTdmSdhControlReqResult, sleGponProfileTdmSdhControlIndex, sleGponProfileTdmSdhControlTimAis
				 }
			STATUS current
			DESCRIPTION
				"Description."
			::= { sleGponProfileTdmSdhNotification 9 }


--  1.3.6.1.4.1.6296.101.23.5.7
		sleGponOltServiceProfile OBJECT IDENTIFIER ::= { sleGponProfile 8 }


--  1.3.6.1.4.1.6296.101.23.5.7.1.1
		sleGponOltServiceProfileTable OBJECT-TYPE
			SYNTAX SEQUENCE OF SleGponOltServiceProfileEntry
			MAX-ACCESS not-accessible
			STATUS current
			DESCRIPTION
				"sleGponProfileTdmPwMtTable"
			::= { sleGponOltServiceProfile 1 }


--  1.3.6.1.4.1.6296.101.23.5.7.1.1.1
		sleGponOltServiceProfileEntry OBJECT-TYPE
			SYNTAX SleGponOltServiceProfileEntry
			MAX-ACCESS not-accessible
			STATUS current
			DESCRIPTION
				"key: sleGponOltServiceOltIndex, sleGponOltServiceProfileIndex"
			INDEX { sleGponOltServiceOltIndex, sleGponOltServiceProfileIndex }
			::= { sleGponOltServiceProfileTable 1 }


		SleGponOltServiceProfileEntry ::=
			SEQUENCE {
				sleGponOltServiceOltIndex
					INTEGER,
				sleGponOltServiceProfileIndex
					Integer32,
				sleGponOltServiceProfileModelName
					OCTET STRING,
				sleGponOltServiceProfileProfileName
					OCTET STRING
			 }

		sleGponOltServiceOltIndex OBJECT-TYPE
			SYNTAX INTEGER (1..2147483647)
			MAX-ACCESS read-only
			STATUS current
			DESCRIPTION
				"The Olt index"
			::= { sleGponOltServiceProfileEntry 1 }


--  1.3.6.1.4.1.6296.101.23.5.7.1.1.1.2
		sleGponOltServiceProfileIndex OBJECT-TYPE
			SYNTAX Integer32 (1..65535)
			MAX-ACCESS read-only
			STATUS current
			DESCRIPTION
				"The profile index."
			::= { sleGponOltServiceProfileEntry 2 }


--  1.3.6.1.4.1.6296.101.23.5.7.1.1.1.3
		sleGponOltServiceProfileModelName OBJECT-TYPE
			SYNTAX OCTET STRING
			MAX-ACCESS read-only
			STATUS current
			DESCRIPTION
				"The Service Profile Model name."
			::= { sleGponOltServiceProfileEntry 3 }


--  1.3.6.1.4.1.6296.101.23.5.7.1.1.1.4
		sleGponOltServiceProfileProfileName OBJECT-TYPE
			SYNTAX OCTET STRING
			MAX-ACCESS read-only
			STATUS current
			DESCRIPTION
				"he Service Profile Name."
			::= { sleGponOltServiceProfileEntry 4 }


--  1.3.6.1.4.1.6296.101.23.5.7.1.2
		sleGponOltServiceProfileControl OBJECT IDENTIFIER ::= { sleGponOltServiceProfile 2 }


--  1.3.6.1.4.1.6296.101.23.5.7.1.2.1
		sleGponOltServiceProfileControlRequest OBJECT-TYPE
			SYNTAX INTEGER { setGponOltServiceProfileModel(1) }
			MAX-ACCESS read-write
			STATUS current
			DESCRIPTION
				"The request of a user command"
			::= { sleGponOltServiceProfileControl 1 }


--  1.3.6.1.4.1.6296.101.23.5.7.1.2.2
		sleGponOltServiceProfileControlStatus OBJECT-TYPE
			SYNTAX SleControlStatusType
			MAX-ACCESS read-only
			STATUS current
			DESCRIPTION
				"The status of user command"
			::= { sleGponOltServiceProfileControl 2 }


--  1.3.6.1.4.1.6296.101.23.5.7.1.2.3
		sleGponOltServiceProfileControlTimer OBJECT-TYPE
			SYNTAX Gauge32
			MAX-ACCESS read-write
			STATUS current
			DESCRIPTION
				"The maximum time for the manager for a long running user command"
			::= { sleGponOltServiceProfileControl 3 }


--  1.3.6.1.4.1.6296.101.23.5.7.1.2.4
		sleGponOltServiceProfileControlTimeStamp OBJECT-TYPE
			SYNTAX TimeTicks
			MAX-ACCESS read-only
			STATUS current
			DESCRIPTION
				"The time stamp of the last command(end of command)"
			::= { sleGponOltServiceProfileControl 4 }


--  1.3.6.1.4.1.6296.101.23.5.7.1.2.5
		sleGponOltServiceProfileControlReqResult OBJECT-TYPE
			SYNTAX SleControlRequestResultType
			MAX-ACCESS read-only
			STATUS current
			DESCRIPTION
				"The result of the last user command"
			::= { sleGponOltServiceProfileControl 5 }


		sleGponOltServiceProfileControlOltIndex OBJECT-TYPE
			SYNTAX INTEGER (1..2147483647)
			MAX-ACCESS read-write
			STATUS current
			DESCRIPTION
				"The Olt index"
			::= { sleGponOltServiceProfileControl 6 }


--  1.3.6.1.4.1.6296.101.23.5.7.1.2.7
		sleGponOltServiceProfileControlModelName OBJECT-TYPE
			SYNTAX OCTET STRING
			MAX-ACCESS read-write
			STATUS current
			DESCRIPTION
				"The Service Profile Model name."
			::= { sleGponOltServiceProfileControl 7 }


--  1.3.6.1.4.1.6296.101.23.5.7.1.2.8
		sleGponOltServiceProfileControlProfileName OBJECT-TYPE
			SYNTAX OCTET STRING
			MAX-ACCESS read-write
			STATUS current
			DESCRIPTION
				"The Service Profile Name."
			::= { sleGponOltServiceProfileControl 8 }


		sleGponOltServiceProfileNotification OBJECT IDENTIFIER ::= { sleGponOltServiceProfile 3 }


		sleGponOltServiceProfileModelChanged NOTIFICATION-TYPE
			OBJECTS { sleGponOltServiceProfileControlRequest, sleGponOltServiceProfileControlTimeStamp, sleGponOltServiceProfileControlReqResult, sleGponOltServiceProfileControlOltIndex, sleGponOltServiceProfileControlModelName,
				sleGponOltServiceProfileControlProfileName }
			STATUS current
			DESCRIPTION
				"setGponOltServiceProfileModel"
			::= { sleGponOltServiceProfileNotification 1 }


--   1.3.6.1.4.1.6296.101.23.6
-- 1.3.6.1.4.1.6296.101.23.6
		sleGponBridge OBJECT IDENTIFIER ::= { sleGpon 6 }


--   1.3.6.1.4.1.6296.101.23.6.1
-- 1.3.6.1.4.1.6296.101.23.6.1
		sleGponOnuPort OBJECT IDENTIFIER ::= { sleGponBridge 1 }


--   1.3.6.1.4.1.6296.101.23.6.1.1
-- 1.3.6.1.4.1.6296.101.23.6.1.1
		sleGponOnuPortTable OBJECT-TYPE
			SYNTAX SEQUENCE OF SleGponOnuPortEntry
			MAX-ACCESS not-accessible
			STATUS current
			DESCRIPTION
				"sleGponOnuPortTable"
			::= { sleGponOnuPort 1 }


--   1.3.6.1.4.1.6296.101.23.6.1.1.1
-- 1.3.6.1.4.1.6296.101.23.6.1.1.1
		sleGponOnuPortEntry OBJECT-TYPE
			SYNTAX SleGponOnuPortEntry
			MAX-ACCESS not-accessible
			STATUS current
			DESCRIPTION
				"key: sleGponOltId, sleGponOnuId, sleGponOnuPortSlotId, sleGponOnuPortId"
			INDEX { sleGponOltId, sleGponOnuId, sleGponOnuPortSlotId, sleGponOnuPortId }
			::= { sleGponOnuPortTable 1 }


		SleGponOnuPortEntry ::=
			SEQUENCE {
				sleGponOnuPortSlotId
					INTEGER,
				sleGponOnuPortId
					Integer32,
				sleGponOnuPortSlotType
					INTEGER,
				sleGponOnuPortAdminStatus
					INTEGER,
				sleGponOnuPortOperStatus
					INTEGER,
				sleGponOnuPortLinkUptime
					Counter64,
				sleGponOnuPortAutoNego
					INTEGER,
				sleGponOnuPortSpeed
					INTEGER,
				sleGponOnuPortDuplex
					INTEGER,
				sleGponOnuPortGemblockRx
					Counter64,
				sleGponOnuPortGemblockTx
					Counter64,
				sleGponOnuPortDiscardFrames
					Counter64,
				sleGponOnuPortElapsedTimeAfterClearStats
					Counter64,
				sleGponOnuPortHookState
					INTEGER,
				sleGponOnuPortSensedType
					INTEGER,
				sleGponOnuPortUniDescription
					OCTET STRING,
				sleGponOnuPortConfSpeed
					INTEGER,
				sleGponOnuPortConfDuplex
					INTEGER,
				sleGponOnuPortMediumMode
					INTEGER,
				sleGponOnuPortLoopbackStatus
					INTEGER,
				sleGponOnuPortOpticModuleInstall
					INTEGER,
				sleGponOnuPortOpticModuleTransceiverType
					INTEGER,
				sleGponOnuPortOpticModuleTransceiverDetailType
					INTEGER,
				sleGponOnuPortOpticModuleLengthMode
					INTEGER,
				sleGponOnuPortOpticModuleLength
					INTEGER,
				sleGponOnuPortOpticModuleSpeed
					INTEGER,
				sleGponOnuPortOpticModuleWavelength
					INTEGER,
				sleGponOnuPortOpticModuleConnecterType
					INTEGER,
				sleGponOnuPortOpticModuleVendorName
					OCTET STRING,
				sleGponOnuPortOpticModuleVendorPartName
					OCTET STRING,
				sleGponOnuPortOpticModuleVendorRevision
					OCTET STRING,
				sleGponOnuPortOpticModuleVendorSerialNumber
					OCTET STRING,
				sleGponOnuPortOpticModuleProductDate
					OCTET STRING,
				sleGponOnuPortLinkUpCount
					Integer32,
				sleGponOnuPortLinkDownCount
					Integer32,
				sleGponOnuPortOpticModuleTemper
					OCTET STRING,
				sleGponOnuPortOpticModuleVoltage
					OCTET STRING,
				sleGponOnuPortOpticModuleTxbias
					OCTET STRING,
				sleGponOnuPortOpticModuleTxPower
					OCTET STRING,
				sleGponOnuPortOpticModuleRxPower
					OCTET STRING,
				sleGponOnuPortMgmtAdminStatus
					INTEGER,
				sleGponOnuPortMgmtCapability
					INTEGER,
				sleGponOnuPortMgmtMethod
					INTEGER,
				sleGponOnuPortPowerControl
					INTEGER
			 }

--   1.3.6.1.4.1.6296.101.23.6.1.1.1.1
-- 1.3.6.1.4.1.6296.101.23.6.1.1.1.1
		sleGponOnuPortSlotId OBJECT-TYPE
			SYNTAX INTEGER
				{
				ethernet(1),
				pots(2),
				ces(3),
				video(4),
				virtualEthernet(5),
				wifi(6)
				}
			MAX-ACCESS read-only
			STATUS current
			DESCRIPTION
				"Slot Number of ONU Port"
			::= { sleGponOnuPortEntry 1 }


--   1.3.6.1.4.1.6296.101.23.6.1.1.1.2
-- 1.3.6.1.4.1.6296.101.23.6.1.1.1.2
		sleGponOnuPortId OBJECT-TYPE
			SYNTAX Integer32 (1..65535)
			MAX-ACCESS read-only
			STATUS current
			DESCRIPTION
				"ONU Port Number"
			::= { sleGponOnuPortEntry 2 }


--   1.3.6.1.4.1.6296.101.23.6.1.1.1.3
-- 1.3.6.1.4.1.6296.101.23.6.1.1.1.3
		sleGponOnuPortSlotType OBJECT-TYPE
			SYNTAX INTEGER
				{
				unknown(0),
				speed10M(1),
				speed100M(2),
				speed10Mspeed100M(3),
				speed10Mspeed100Mspeed1000M(4),
				pots(5),
				virtualEthernet(6),
				moca(7),
				video(8),
				ieee802dot11(9),
				ds1(10),
				e1(11),
				configurableDs1E1(12)
				}
			MAX-ACCESS read-only
			STATUS current
			DESCRIPTION
				"Slot type of ONU Port"
			::= { sleGponOnuPortEntry 3 }


--   1.3.6.1.4.1.6296.101.23.6.1.1.1.4
-- 1.3.6.1.4.1.6296.101.23.6.1.1.1.4
		sleGponOnuPortAdminStatus OBJECT-TYPE
			SYNTAX INTEGER
				{
				up(1),
				down(2)
				}
			MAX-ACCESS read-only
			STATUS current
			DESCRIPTION
				"State of ONU Port Administratoration"
			::= { sleGponOnuPortEntry 4 }


--   1.3.6.1.4.1.6296.101.23.6.1.1.1.5
-- 1.3.6.1.4.1.6296.101.23.6.1.1.1.5
		sleGponOnuPortOperStatus OBJECT-TYPE
			SYNTAX INTEGER
				{
				up(1),
				down(2)
				}
			MAX-ACCESS read-only
			STATUS current
			DESCRIPTION
				"State of ONU Port Operation"
			::= { sleGponOnuPortEntry 5 }


--   1.3.6.1.4.1.6296.101.23.6.1.1.1.6
-- 1.3.6.1.4.1.6296.101.23.6.1.1.1.6
		sleGponOnuPortLinkUptime OBJECT-TYPE
			SYNTAX Counter64
			UNITS "1 sec"
			MAX-ACCESS read-only
			STATUS current
			DESCRIPTION
				"The elapsed time after link-up event"
			::= { sleGponOnuPortEntry 6 }


--   1.3.6.1.4.1.6296.101.23.6.1.1.1.7
-- 1.3.6.1.4.1.6296.101.23.6.1.1.1.7
		sleGponOnuPortAutoNego OBJECT-TYPE
			SYNTAX INTEGER
				{
				on(1),
				off(2)
				}
			MAX-ACCESS read-only
			STATUS current
			DESCRIPTION
				"The port auto negotiation.
				(This OID is not available)"
			::= { sleGponOnuPortEntry 7 }


--   1.3.6.1.4.1.6296.101.23.6.1.1.1.8
-- 1.3.6.1.4.1.6296.101.23.6.1.1.1.8
		sleGponOnuPortSpeed OBJECT-TYPE
			SYNTAX INTEGER
				{
				speed10(1),
				speed100(2),
				speed1000(3),
				unknown(255)
				}
			MAX-ACCESS read-only
			STATUS current
			DESCRIPTION
				"The port speed.
				(This OID is not available)"
			::= { sleGponOnuPortEntry 8 }


--   1.3.6.1.4.1.6296.101.23.6.1.1.1.9
-- 1.3.6.1.4.1.6296.101.23.6.1.1.1.9
		sleGponOnuPortDuplex OBJECT-TYPE
			SYNTAX INTEGER
				{
				full(1),
				half(2),
				unknown(255)
				}
			MAX-ACCESS read-only
			STATUS current
			DESCRIPTION
				"The port duplex."
			::= { sleGponOnuPortEntry 9 }


--   1.3.6.1.4.1.6296.101.23.6.1.1.1.10
-- 1.3.6.1.4.1.6296.101.23.6.1.1.1.10
		sleGponOnuPortGemblockRx OBJECT-TYPE
			SYNTAX Counter64
			MAX-ACCESS read-only
			STATUS current
			DESCRIPTION
				"The gemblock port Rx count"
			::= { sleGponOnuPortEntry 10 }


--   1.3.6.1.4.1.6296.101.23.6.1.1.1.11
-- 1.3.6.1.4.1.6296.101.23.6.1.1.1.11
		sleGponOnuPortGemblockTx OBJECT-TYPE
			SYNTAX Counter64
			MAX-ACCESS read-only
			STATUS current
			DESCRIPTION
				"The gemblock port Tx count
				"
			::= { sleGponOnuPortEntry 11 }


--   1.3.6.1.4.1.6296.101.23.6.1.1.1.12
-- 1.3.6.1.4.1.6296.101.23.6.1.1.1.12
		sleGponOnuPortDiscardFrames OBJECT-TYPE
			SYNTAX Counter64
			MAX-ACCESS read-only
			STATUS current
			DESCRIPTION
				"The discard frames."
			::= { sleGponOnuPortEntry 12 }


--   1.3.6.1.4.1.6296.101.23.6.1.1.1.13
-- 1.3.6.1.4.1.6296.101.23.6.1.1.1.13
		sleGponOnuPortElapsedTimeAfterClearStats OBJECT-TYPE
			SYNTAX Counter64
			UNITS "1 sec"
			MAX-ACCESS read-only
			STATUS current
			DESCRIPTION
				"The elapsed time after clearing statistics."
			::= { sleGponOnuPortEntry 13 }


--  1.3.6.1.4.1.6296.101.23.6.1.1.1.14
		sleGponOnuPortHookState OBJECT-TYPE
			SYNTAX INTEGER
				{
				on(1),
				off(2),
				unused(255)
				}
			MAX-ACCESS read-only
			STATUS current
			DESCRIPTION
				"The port hook state"
			::= { sleGponOnuPortEntry 14 }


--  1.3.6.1.4.1.6296.101.23.6.1.1.1.15
		sleGponOnuPortSensedType OBJECT-TYPE
			SYNTAX INTEGER
				{
				ds1(10),
				e1(11),
				unknown(255)
				}
			MAX-ACCESS read-only
			STATUS current
			DESCRIPTION
				"The port sensed type"
			::= { sleGponOnuPortEntry 15 }


--  1.3.6.1.4.1.6296.101.23.6.1.1.1.16
		sleGponOnuPortUniDescription OBJECT-TYPE
			SYNTAX OCTET STRING
			MAX-ACCESS read-only
			STATUS current
			DESCRIPTION
				"The port description for UNI of ONT."
			::= { sleGponOnuPortEntry 16 }


--  1.3.6.1.4.1.6296.101.23.6.1.1.1.17
		sleGponOnuPortConfSpeed OBJECT-TYPE
			SYNTAX INTEGER
				{
				auto(0),
				speed10(1),
				speed100(2),
				speed1000(3)
				}
			MAX-ACCESS read-only
			STATUS current
			DESCRIPTION
				"The port speed configuration."
			::= { sleGponOnuPortEntry 17 }


--  1.3.6.1.4.1.6296.101.23.6.1.1.1.18
		sleGponOnuPortConfDuplex OBJECT-TYPE
			SYNTAX INTEGER
				{
				auto(0),
				full(1),
				half(2)
				}
			MAX-ACCESS read-only
			STATUS current
			DESCRIPTION
				"The port duplex configuration"
			::= { sleGponOnuPortEntry 18 }


--  1.3.6.1.4.1.6296.101.23.6.1.1.1.19
		sleGponOnuPortMediumMode OBJECT-TYPE
			SYNTAX INTEGER
				{
				mdiX(0),
				mdi(1),
				auto(2),
				unknown(255)
				}
			MAX-ACCESS read-only
			STATUS current
			DESCRIPTION
				"The port medium mode."
			::= { sleGponOnuPortEntry 19 }


--  1.3.6.1.4.1.6296.101.23.6.1.1.1.20
		sleGponOnuPortLoopbackStatus OBJECT-TYPE
			SYNTAX INTEGER
				{
				disable(0),
				enableType1(1),
				enableType2(2),
				enableType3(3),
				enableType4(4),
				enableType5(5),
				unknown(255)
				}
			MAX-ACCESS read-only
			STATUS current
			DESCRIPTION
				"The port loopback Status configuration."
			::= { sleGponOnuPortEntry 20 }


--  1.3.6.1.4.1.6296.101.23.6.1.1.1.21
		sleGponOnuPortOpticModuleInstall OBJECT-TYPE
			SYNTAX INTEGER
				{
				uninstall(0),
				install(1)
				}
			MAX-ACCESS read-only
			STATUS current
			DESCRIPTION
				"The module instatll status."
			::= { sleGponOnuPortEntry 21 }


--  1.3.6.1.4.1.6296.101.23.6.1.1.1.22
		sleGponOnuPortOpticModuleTransceiverType OBJECT-TYPE
			SYNTAX INTEGER
				{
				gbic(1),
				solderedToMotherboard(2),
				sfp(3),
				xbi300Pin(4),
				xenpak(5),
				xfp(6),
				xff(7),
				xfpE(8),
				spak(9),
				x2(10),
				unknown(255)
				}
			MAX-ACCESS read-only
			STATUS current
			DESCRIPTION
				"The module transceiver type.
				1: GBIC
				2 :Soldered to motherboard
				3: SFP
				4 :300 pin XBI
				5: XENPAK
				6: XFP
				7: XFF
				8: XFP-E
				9 :XPAK
				10: X2
				255:Unknown"
			::= { sleGponOnuPortEntry 22 }


--  1.3.6.1.4.1.6296.101.23.6.1.1.1.23
		sleGponOnuPortOpticModuleTransceiverDetailType OBJECT-TYPE
			SYNTAX INTEGER
				{
				base1000SX(1),
				base1000LX(2),
				base1000CX(3),
				base1000T(4),
				base1000LXorLX10(5),
				base1000FX(6),
				base1000BX10(7),
				base1000PX(8),
				oc3MultiShortReach(9),
				oc3SingleIntermediateReach(10),
				oc3SingleLongReach(11),
				unknown(255)
				}
			MAX-ACCESS read-only
			STATUS current
			DESCRIPTION
				"The module tranceiver detail type.
				1: 1000Base-SX
				2: 1000Base-LX
				3: 1000Base-CX
				4: 1000Base-T
				5: 1000Base-LX/LX10
				6: 100Base-FX
				7: 1000Base-BX10
				8: 1000Base-PX
				9: OC-3(155M) Multi Mode Short Reach
				10: OC-3(155M) Single Mode Intermediate Reach
				11: OC-3(155M) Single Mode Long Reach
				255: Unknown"
			::= { sleGponOnuPortEntry 23 }


--  1.3.6.1.4.1.6296.101.23.6.1.1.1.24
		sleGponOnuPortOpticModuleLengthMode OBJECT-TYPE
			SYNTAX INTEGER
				{
				singleMode(1),
				multiMode(2),
				unknown(255)
				}
			MAX-ACCESS read-only
			STATUS current
			DESCRIPTION
				"The module length mode.
				1: singleMode
				2: multiMode
				255 : unknown"
			::= { sleGponOnuPortEntry 24 }


--  1.3.6.1.4.1.6296.101.23.6.1.1.1.25
		sleGponOnuPortOpticModuleLength OBJECT-TYPE
			SYNTAX INTEGER (1..65535)
			MAX-ACCESS read-only
			STATUS current
			DESCRIPTION
				"the module length(m)."
			::= { sleGponOnuPortEntry 25 }


--  1.3.6.1.4.1.6296.101.23.6.1.1.1.26
		sleGponOnuPortOpticModuleSpeed OBJECT-TYPE
			SYNTAX INTEGER
				{
				speed155(1),
				speed200(2),
				speed622(3),
				speed1062dot5(4),
				speed1250(5),
				speed2125(6),
				speed4250(7),
				speed2488(8),
				unknown(255)
				}
			MAX-ACCESS read-only
			STATUS current
			DESCRIPTION
				"The module speed.
				1: 155 Mb/s
				2: 200 Mb/s
				3: 622 Mb/s
				4: 1062.5 Mb/s
				5: 1250 Mb/s
				6: 2125 Mb/s
				7: 4250 Mb/s
				8: 2488 Mb/s
				255: unknown"
			::= { sleGponOnuPortEntry 26 }


--  1.3.6.1.4.1.6296.101.23.6.1.1.1.27
		sleGponOnuPortOpticModuleWavelength OBJECT-TYPE
			SYNTAX INTEGER
				{
				length850(1),
				length1310(2),
				length1490(3),
				length1550(4),
				unknown(255)
				}
			MAX-ACCESS read-only
			STATUS current
			DESCRIPTION
				"The module wavelength
				1: 850 nm
				2: 1310 nm
				3: 1490 nm
				4: 1550 nm
				255: unknown"
			::= { sleGponOnuPortEntry 27 }


--  1.3.6.1.4.1.6296.101.23.6.1.1.1.28
		sleGponOnuPortOpticModuleConnecterType OBJECT-TYPE
			SYNTAX INTEGER
				{
				sc(1),
				fiberChannelStyle1(2),
				fiberChannelStyle2(3),
				bncTnc(4),
				fiberChannelCoaxialHeaders(5),
				fiberJack(6),
				lc(7),
				mtRj(8),
				mu(9),
				sg(10),
				opticalPigtail(11),
				hssdc2(12),
				copperPigtail(13),
				unknown(255)
				}
			MAX-ACCESS read-only
			STATUS current
			DESCRIPTION
				"The module connecter type.
				1: SC
				2: Fiber Channel Style 1 copper connector
				3: Fiber Channel Style 2 copper connector
				4: BNC/TNC
				5: Fiber Channel coaxial headers
				6: Fiber Jack
				7: LC
				8: MT-RJ
				9: MU
				10: SG
				11: Optical Pigtail
				12: HSSDC II
				13: Copper Pigtail
				255: unknown"
			::= { sleGponOnuPortEntry 28 }


--  1.3.6.1.4.1.6296.101.23.6.1.1.1.29
		sleGponOnuPortOpticModuleVendorName OBJECT-TYPE
			SYNTAX OCTET STRING
			MAX-ACCESS read-only
			STATUS current
			DESCRIPTION
				"The module vendor name."
			::= { sleGponOnuPortEntry 29 }


--  1.3.6.1.4.1.6296.101.23.6.1.1.1.30
		sleGponOnuPortOpticModuleVendorPartName OBJECT-TYPE
			SYNTAX OCTET STRING
			MAX-ACCESS read-only
			STATUS current
			DESCRIPTION
				"The module vendor part name."
			::= { sleGponOnuPortEntry 30 }


--  1.3.6.1.4.1.6296.101.23.6.1.1.1.31
		sleGponOnuPortOpticModuleVendorRevision OBJECT-TYPE
			SYNTAX OCTET STRING
			MAX-ACCESS read-only
			STATUS current
			DESCRIPTION
				"The module vendor revision."
			::= { sleGponOnuPortEntry 31 }


--  1.3.6.1.4.1.6296.101.23.6.1.1.1.32
		sleGponOnuPortOpticModuleVendorSerialNumber OBJECT-TYPE
			SYNTAX OCTET STRING
			MAX-ACCESS read-only
			STATUS current
			DESCRIPTION
				"the moduel vendor serial number."
			::= { sleGponOnuPortEntry 32 }


--  1.3.6.1.4.1.6296.101.23.6.1.1.1.33
		sleGponOnuPortOpticModuleProductDate OBJECT-TYPE
			SYNTAX OCTET STRING
			MAX-ACCESS read-only
			STATUS current
			DESCRIPTION
				"The module vendor product date."
			::= { sleGponOnuPortEntry 33 }


--  1.3.6.1.4.1.6296.101.23.6.1.1.1.34
		sleGponOnuPortLinkUpCount OBJECT-TYPE
			SYNTAX Integer32 (0..65535)
			MAX-ACCESS read-only
			STATUS current
			DESCRIPTION
				"The Link Up Count of ONU Port"
			::= { sleGponOnuPortEntry 34 }


--  1.3.6.1.4.1.6296.101.23.6.1.1.1.35
		sleGponOnuPortLinkDownCount OBJECT-TYPE
			SYNTAX Integer32 (0..65535)
			MAX-ACCESS read-only
			STATUS current
			DESCRIPTION
				"The Link Down Count of ONU Port"
			::= { sleGponOnuPortEntry 35 }


--  1.3.6.1.4.1.6296.101.23.6.1.1.1.36
		sleGponOnuPortOpticModuleTemper OBJECT-TYPE
			SYNTAX OCTET STRING
			MAX-ACCESS read-only
			STATUS current
			DESCRIPTION
				"Internally measured module temperature.(C)"
			::= { sleGponOnuPortEntry 36 }


--  1.3.6.1.4.1.6296.101.23.6.1.1.1.37
		sleGponOnuPortOpticModuleVoltage OBJECT-TYPE
			SYNTAX OCTET STRING
			MAX-ACCESS read-only
			STATUS current
			DESCRIPTION
				"Internally measured supply voltage in transceiver.(V)
				"
			::= { sleGponOnuPortEntry 37 }


--  1.3.6.1.4.1.6296.101.23.6.1.1.1.38
		sleGponOnuPortOpticModuleTxbias OBJECT-TYPE
			SYNTAX OCTET STRING
			MAX-ACCESS read-only
			STATUS current
			DESCRIPTION
				"Internally measured TX Bias Current.(mA)"
			::= { sleGponOnuPortEntry 38 }


--  1.3.6.1.4.1.6296.101.23.6.1.1.1.39
		sleGponOnuPortOpticModuleTxPower OBJECT-TYPE
			SYNTAX OCTET STRING
			MAX-ACCESS read-only
			STATUS current
			DESCRIPTION
				"Measured TX output power.(dBm)"
			::= { sleGponOnuPortEntry 39 }


--  1.3.6.1.4.1.6296.101.23.6.1.1.1.40
		sleGponOnuPortOpticModuleRxPower OBJECT-TYPE
			SYNTAX OCTET STRING
			MAX-ACCESS read-only
			STATUS current
			DESCRIPTION
				"Measured RX input power.(dBm)"
			::= { sleGponOnuPortEntry 40 }


--  1.3.6.1.4.1.6296.101.23.6.1.1.1.41
		sleGponOnuPortMgmtAdminStatus OBJECT-TYPE
			SYNTAX INTEGER
				{
				up(0),
				down(1),
				unknown(255)
				}
			MAX-ACCESS read-only
			STATUS current
			DESCRIPTION
				"State of ONU Port Administratoration"
			::= { sleGponOnuPortEntry 41 }


--  1.3.6.1.4.1.6296.101.23.6.1.1.1.42
		sleGponOnuPortMgmtCapability OBJECT-TYPE
			SYNTAX INTEGER
				{
				omci(0),
				nonOmci(1),
				both(2),
				unknown(255)
				}
			MAX-ACCESS read-only
			STATUS current
			DESCRIPTION
				"The port management capability"
			::= { sleGponOnuPortEntry 42 }


--  1.3.6.1.4.1.6296.101.23.6.1.1.1.43
		sleGponOnuPortMgmtMethod OBJECT-TYPE
			SYNTAX INTEGER
				{
				omci(0),
				nonOmci(1),
				unknown(255)
				}
			MAX-ACCESS read-only
			STATUS current
			DESCRIPTION
				"The port management method"
			::= { sleGponOnuPortEntry 43 }


		sleGponOnuPortPowerControl OBJECT-TYPE
			SYNTAX INTEGER
				{
				enable(1),
				disable(2),
				unknown(255)
				}
			MAX-ACCESS read-only
			STATUS current
			DESCRIPTION
				"The port power control"
			::= { sleGponOnuPortEntry 44 }


--   1.3.6.1.4.1.6296.101.23.6.1.2
-- 1.3.6.1.4.1.6296.101.23.6.1.2
		sleGponOnuPortControl OBJECT IDENTIFIER ::= { sleGponOnuPort 2 }


--   1.3.6.1.4.1.6296.101.23.6.1.2.1
-- 1.3.6.1.4.1.6296.101.23.6.1.2.1
		sleGponOnuPortControlRequest OBJECT-TYPE
			SYNTAX INTEGER
				{
				setOnuPortAdmin(1),
				setOnuPortAutoNego(2),
				setOnuPortSpeed(3),
				clearOnuPortStats(4),
				setUniDescription(5),
				setAutoDetection(6),
				setOnuPortMediumMode(7),
				setOnuPortLoopbackStatus(8),
				updateOnuPortOpticModuleInfo(9),
				updateOnuPortLinkStatisticsInfo(10),
				updateOnuPortMgmtData(11),
				setOnuPortPowerControl(12)
				}
			MAX-ACCESS read-write
			STATUS current
			DESCRIPTION
				"The request of a user command"
			::= { sleGponOnuPortControl 1 }


--   1.3.6.1.4.1.6296.101.23.6.1.2.2
-- 1.3.6.1.4.1.6296.101.23.6.1.2.2
		sleGponOnuPortControlStatus OBJECT-TYPE
			SYNTAX SleControlStatusType
			MAX-ACCESS read-only
			STATUS current
			DESCRIPTION
				"The status of user command"
			::= { sleGponOnuPortControl 2 }


--   1.3.6.1.4.1.6296.101.23.6.1.2.3
-- 1.3.6.1.4.1.6296.101.23.6.1.2.3
		sleGponOnuPortControlTimer OBJECT-TYPE
			SYNTAX Gauge32
			MAX-ACCESS read-write
			STATUS current
			DESCRIPTION
				"The maximum time for the manager for a long running user command"
			::= { sleGponOnuPortControl 3 }


--   1.3.6.1.4.1.6296.101.23.6.1.2.4
-- 1.3.6.1.4.1.6296.101.23.6.1.2.4
		sleGponOnuPortControlTimeStamp OBJECT-TYPE
			SYNTAX TimeTicks
			MAX-ACCESS read-only
			STATUS current
			DESCRIPTION
				"The time stamp of the last command(end of command)"
			::= { sleGponOnuPortControl 4 }


--   1.3.6.1.4.1.6296.101.23.6.1.2.5
-- 1.3.6.1.4.1.6296.101.23.6.1.2.5
		sleGponOnuPortControlReqResult OBJECT-TYPE
			SYNTAX SleControlRequestResultType
			MAX-ACCESS read-only
			STATUS current
			DESCRIPTION
				"The result of the last user command"
			::= { sleGponOnuPortControl 5 }


--   1.3.6.1.4.1.6296.101.23.6.1.2.6
-- 1.3.6.1.4.1.6296.101.23.6.1.2.6
		sleGponOnuPortControlOltId OBJECT-TYPE
			SYNTAX INTEGER (1..2147483647)
			MAX-ACCESS read-write
			STATUS current
			DESCRIPTION
				"Gpon Olt Index"
			::= { sleGponOnuPortControl 6 }


--   1.3.6.1.4.1.6296.101.23.6.1.2.7
-- 1.3.6.1.4.1.6296.101.23.6.1.2.7
		sleGponOnuPortControlOnuId OBJECT-TYPE
			SYNTAX INTEGER (1..65535)
			MAX-ACCESS read-write
			STATUS current
			DESCRIPTION
				"Gpon Onu Index"
			::= { sleGponOnuPortControl 7 }


--   1.3.6.1.4.1.6296.101.23.6.1.2.8
-- 1.3.6.1.4.1.6296.101.23.6.1.2.8
		sleGponOnuPortControlSlotId OBJECT-TYPE
			SYNTAX INTEGER
				{
				ethernet(1),
				pots(2),
				ces(3),
				video(4),
				virtualEthernet(5),
				wifi(6)
				}
			MAX-ACCESS read-write
			STATUS current
			DESCRIPTION
				"OSlot Number of ONU Port"
			::= { sleGponOnuPortControl 8 }


--   1.3.6.1.4.1.6296.101.23.6.1.2.9
-- 1.3.6.1.4.1.6296.101.23.6.1.2.9
		sleGponOnuPortControlPortId OBJECT-TYPE
			SYNTAX INTEGER (1..65535)
			MAX-ACCESS read-write
			STATUS current
			DESCRIPTION
				"ONU Port Number"
			::= { sleGponOnuPortControl 9 }


--   1.3.6.1.4.1.6296.101.23.6.1.2.10
-- 1.3.6.1.4.1.6296.101.23.6.1.2.10
		sleGponOnuPortControlAdminStatus OBJECT-TYPE
			SYNTAX INTEGER
				{
				up(1),
				down(2)
				}
			MAX-ACCESS read-write
			STATUS current
			DESCRIPTION
				"State of ONU Port Administratoration"
			::= { sleGponOnuPortControl 10 }


--   1.3.6.1.4.1.6296.101.23.6.1.2.11
-- 1.3.6.1.4.1.6296.101.23.6.1.2.11
		sleGponOnuPortControlOnuSerial OBJECT-TYPE
			SYNTAX OCTET STRING
			MAX-ACCESS read-write
			STATUS current
			DESCRIPTION
				"ONU Serial Number
				(This OID is not available.)"
			::= { sleGponOnuPortControl 11 }


--   1.3.6.1.4.1.6296.101.23.6.1.2.12
-- 1.3.6.1.4.1.6296.101.23.6.1.2.12
		sleGponOnuPortControlAutoNego OBJECT-TYPE
			SYNTAX INTEGER
				{
				on(1),
				off(2)
				}
			MAX-ACCESS read-write
			STATUS current
			DESCRIPTION
				"The port auto negotiation.
				(This OID is not available.)"
			::= { sleGponOnuPortControl 12 }


--   1.3.6.1.4.1.6296.101.23.6.1.2.13
-- 1.3.6.1.4.1.6296.101.23.6.1.2.13
		sleGponOnuPortControlSpeed OBJECT-TYPE
			SYNTAX INTEGER
				{
				auto(0),
				speed10(1),
				speed100(2),
				speed1000(3)
				}
			MAX-ACCESS read-write
			STATUS current
			DESCRIPTION
				"The port speed configuration.
				(This OID is not available.)"
			::= { sleGponOnuPortControl 13 }


--  1.3.6.1.4.1.6296.101.23.6.1.2.14
		sleGponOnuPortControlUniDescription OBJECT-TYPE
			SYNTAX OCTET STRING
			MAX-ACCESS read-write
			STATUS current
			DESCRIPTION
				"The port description for UNI of ONT."
			::= { sleGponOnuPortControl 14 }


--  1.3.6.1.4.1.6296.101.23.6.1.2.15
		sleGponOnuPortControlDuplex OBJECT-TYPE
			SYNTAX INTEGER
				{
				auto(0),
				full(1),
				half(2)
				}
			MAX-ACCESS read-write
			STATUS current
			DESCRIPTION
				"The port duplex configuration"
			::= { sleGponOnuPortControl 15 }


--  1.3.6.1.4.1.6296.101.23.6.1.2.16
		sleGponOnuPortControlMediumMode OBJECT-TYPE
			SYNTAX INTEGER
				{
				mdiX(0),
				mdi(1),
				auto(2),
				unknown(255)
				}
			MAX-ACCESS read-write
			STATUS current
			DESCRIPTION
				"The port medium mode."
			::= { sleGponOnuPortControl 16 }


--  1.3.6.1.4.1.6296.101.23.6.1.2.17
		sleGponOnuPortControlLoopbackStatus OBJECT-TYPE
			SYNTAX INTEGER
				{
				disable(0),
				enableType1(1),
				enableType2(2),
				enableType3(3),
				enableType4(4),
				enableType5(5),
				unknown(255)
				}
			MAX-ACCESS read-write
			STATUS current
			DESCRIPTION
				"The port loopback Status configuration."
			::= { sleGponOnuPortControl 17 }


		sleGponOnuPortControlPowerControl OBJECT-TYPE
			SYNTAX INTEGER
				{
				enable(1),
				disable(2)
				}
			MAX-ACCESS read-write
			STATUS current
			DESCRIPTION
				"The port power control"
			::= { sleGponOnuPortControl 18 }


--   1.3.6.1.4.1.6296.101.23.6.1.3
-- 1.3.6.1.4.1.6296.101.23.6.1.3
		sleGponOnuPortNotification OBJECT IDENTIFIER ::= { sleGponOnuPort 3 }


--   1.3.6.1.4.1.6296.101.23.6.1.3.1
-- 1.3.6.1.4.1.6296.101.23.6.1.3.1
		sleGponOnuPortAdminChanged NOTIFICATION-TYPE
			OBJECTS { sleGponOnuPortControlRequest, sleGponOnuPortControlTimeStamp, sleGponOnuPortControlReqResult, sleGponOnuPortControlOltId, sleGponOnuPortControlOnuId,
				sleGponOnuPortControlSlotId, sleGponOnuPortControlPortId, sleGponOnuPortControlAdminStatus, sleGponOnuPortControlOnuSerial }
			STATUS current
			DESCRIPTION
				"Description."
			::= { sleGponOnuPortNotification 1 }


--   1.3.6.1.4.1.6296.101.23.6.1.3.2
-- 1.3.6.1.4.1.6296.101.23.6.1.3.2
		sleGponOnuPortAutoNegoChanged NOTIFICATION-TYPE
			OBJECTS { sleGponOnuPortControlRequest, sleGponOnuPortControlTimeStamp, sleGponOnuPortControlReqResult, sleGponOnuPortControlOltId, sleGponOnuPortControlOnuId,
				sleGponOnuPortControlSlotId, sleGponOnuPortControlPortId, sleGponOnuPortControlOnuSerial, sleGponOnuPortControlAutoNego }
			STATUS current
			DESCRIPTION
				"setOnuPortAutoNego
				(This OID is not available)
				"
			::= { sleGponOnuPortNotification 2 }


--   1.3.6.1.4.1.6296.101.23.6.1.3.3
-- 1.3.6.1.4.1.6296.101.23.6.1.3.3
		sleGponOnuPortSpeedChanged NOTIFICATION-TYPE
			OBJECTS { sleGponOnuPortControlRequest, sleGponOnuPortControlTimeStamp, sleGponOnuPortControlReqResult, sleGponOnuPortControlOltId, sleGponOnuPortControlOnuId,
				sleGponOnuPortControlSlotId, sleGponOnuPortControlPortId, sleGponOnuPortControlOnuSerial, sleGponOnuPortControlSpeed }
			STATUS current
			DESCRIPTION
				"setOnuPortSpeed
				(This OID is not available)
				"
			::= { sleGponOnuPortNotification 3 }


--   1.3.6.1.4.1.6296.101.23.6.1.3.4
-- 1.3.6.1.4.1.6296.101.23.6.1.3.4
		sleGponOnuPortStatisticsCleared NOTIFICATION-TYPE
			OBJECTS { sleGponOnuPortControlRequest, sleGponOnuPortControlTimeStamp, sleGponOnuPortControlReqResult, sleGponOnuPortControlOltId, sleGponOnuPortControlOnuId,
				sleGponOnuPortControlSlotId, sleGponOnuPortControlPortId }
			STATUS current
			DESCRIPTION
				"clearOnuPortStats
				(This OID is not available)"
			::= { sleGponOnuPortNotification 4 }


--  1.3.6.1.4.1.6296.101.23.6.1.3.5
		sleGponOnuPortUniDescriptionChanged NOTIFICATION-TYPE
			OBJECTS { sleGponOnuPortControlRequest, sleGponOnuPortControlTimeStamp, sleGponOnuPortControlReqResult, sleGponOnuPortControlOltId, sleGponOnuPortControlOnuId,
				sleGponOnuPortControlSlotId, sleGponOnuPortControlPortId, sleGponOnuPortControlUniDescription }
			STATUS current
			DESCRIPTION
				"setUniDescription"
			::= { sleGponOnuPortNotification 5 }


--  1.3.6.1.4.1.6296.101.23.6.1.3.6
		sleGponOnuPortAutoDetectionChanged NOTIFICATION-TYPE
			OBJECTS { sleGponOnuPortControlRequest, sleGponOnuPortControlTimeStamp, sleGponOnuPortControlReqResult, sleGponOnuPortControlOltId, sleGponOnuPortControlOnuId,
				sleGponOnuPortControlSlotId, sleGponOnuPortControlPortId, sleGponOnuPortControlSpeed, sleGponOnuPortControlDuplex }
			STATUS current
			DESCRIPTION
				"setAutoDetection."
			::= { sleGponOnuPortNotification 6 }


--  1.3.6.1.4.1.6296.101.23.6.1.3.7
		sleGponOnuPortMediumModeChanged NOTIFICATION-TYPE
			OBJECTS { sleGponOnuPortControlRequest, sleGponOnuPortControlTimeStamp, sleGponOnuPortControlReqResult, sleGponOnuPortControlOltId, sleGponOnuPortControlOnuId,
				sleGponOnuPortControlSlotId, sleGponOnuPortControlPortId, sleGponOnuPortControlMediumMode }
			STATUS current
			DESCRIPTION
				"setOnuPortMediumMode"
			::= { sleGponOnuPortNotification 7 }


--  1.3.6.1.4.1.6296.101.23.6.1.3.8
		sleGponOnuPortLoopbackStatusChanged NOTIFICATION-TYPE
			OBJECTS { sleGponOnuPortControlRequest, sleGponOnuPortControlTimeStamp, sleGponOnuPortControlReqResult, sleGponOnuPortControlOltId, sleGponOnuPortControlOnuId,
				sleGponOnuPortControlSlotId, sleGponOnuPortControlPortId, sleGponOnuPortControlLoopbackStatus }
			STATUS current
			DESCRIPTION
				"setOnuPortLoopbackStatus"
			::= { sleGponOnuPortNotification 8 }


--  1.3.6.1.4.1.6296.101.23.6.1.3.9
		sleGponOnuPortOpticModuleInfoUpdated NOTIFICATION-TYPE
			OBJECTS { sleGponOnuPortControlRequest, sleGponOnuPortControlTimeStamp, sleGponOnuPortControlReqResult, sleGponOnuPortControlOltId, sleGponOnuPortControlOnuId,
				sleGponOnuPortControlSlotId, sleGponOnuPortControlPortId }
			STATUS current
			DESCRIPTION
				"updateOnuPortOpticModuleInfo."
			::= { sleGponOnuPortNotification 9 }


--  1.3.6.1.4.1.6296.101.23.6.1.3.10
		sleGponOnuPortLinkStatisticsUpdated NOTIFICATION-TYPE
			OBJECTS { sleGponOnuPortControlRequest, sleGponOnuPortControlTimeStamp, sleGponOnuPortControlReqResult, sleGponOnuPortControlOltId, sleGponOnuPortControlOnuId,
				sleGponOnuPortControlSlotId, sleGponOnuPortControlPortId }
			STATUS current
			DESCRIPTION
				"updateOnuPortLinkStatisticsInfo"
			::= { sleGponOnuPortNotification 10 }


--   1.3.6.1.4.1.6296.101.23.6.1.3.1
-- 1.3.6.1.4.1.6296.101.23.6.1.3.11
		sleGponOnuPortMgmtChanged NOTIFICATION-TYPE
			OBJECTS { sleGponOnuPortControlRequest, sleGponOnuPortControlTimeStamp, sleGponOnuPortControlReqResult, sleGponOnuPortControlOltId, sleGponOnuPortControlOnuId,
				sleGponOnuPortControlSlotId, sleGponOnuPortControlPortId }
			STATUS current
			DESCRIPTION
				"updateOnuPortMgmtData "
			::= { sleGponOnuPortNotification 11 }


		sleGponOnuPortPowrControlChanged NOTIFICATION-TYPE
			OBJECTS { sleGponOnuPortControlRequest, sleGponOnuPortControlTimeStamp, sleGponOnuPortControlReqResult, sleGponOnuPortControlOltId, sleGponOnuPortControlOnuId,
				sleGponOnuPortControlSlotId, sleGponOnuPortControlPortId, sleGponOnuPortControlPowerControl }
			STATUS current
			DESCRIPTION
				"setOnuPortPowerControl"
			::= { sleGponOnuPortNotification 12 }


--   1.3.6.1.4.1.6296.101.23.6.2
-- 1.3.6.1.4.1.6296.101.23.6.2
		sleGponOnuUserMac OBJECT IDENTIFIER ::= { sleGponBridge 2 }


--   1.3.6.1.4.1.6296.101.23.6.2.1
-- 1.3.6.1.4.1.6296.101.23.6.2.1
		sleGponOnuUserMacTable OBJECT-TYPE
			SYNTAX SEQUENCE OF SleGponOnuUserMacEntry
			MAX-ACCESS not-accessible
			STATUS current
			DESCRIPTION
				"sleGponOnuUserMacTable"
			::= { sleGponOnuUserMac 1 }


--   1.3.6.1.4.1.6296.101.23.6.2.1.1
-- 1.3.6.1.4.1.6296.101.23.6.2.1.1
		sleGponOnuUserMacEntry OBJECT-TYPE
			SYNTAX SleGponOnuUserMacEntry
			MAX-ACCESS not-accessible
			STATUS current
			DESCRIPTION
				"key: sleGponOltId, sleGponOnuId, sleGponOnuUserMacVlanId, sleGponOnuUserMacAddress"
			INDEX { sleGponOltId, sleGponOnuId, sleGponOnuUserMacVlanId, sleGponOnuUserMacAddress }
			::= { sleGponOnuUserMacTable 1 }


		SleGponOnuUserMacEntry ::=
			SEQUENCE {
				sleGponOnuUserMacAddress
					OCTET STRING,
				sleGponOnuUserMacVlanId
					INTEGER,
				sleGponOnuUserMacPortId
					INTEGER,
				sleGponOnuUserMacOltId
					INTEGER,
				sleGponOnuUserMacOnuId
					INTEGER,
				sleGponOnuUserMacStatus
					INTEGER
			 }

--   1.3.6.1.4.1.6296.101.23.6.2.1.1.1
-- 1.3.6.1.4.1.6296.101.23.6.2.1.1.1
		sleGponOnuUserMacAddress OBJECT-TYPE
			SYNTAX OCTET STRING (SIZE (0..6))
			MAX-ACCESS read-only
			STATUS current
			DESCRIPTION
				"The user MAC addresses that are leant at the running ONU."
			::= { sleGponOnuUserMacEntry 1 }


--   1.3.6.1.4.1.6296.101.23.6.2.1.1.2
-- 1.3.6.1.4.1.6296.101.23.6.2.1.1.2
		sleGponOnuUserMacVlanId OBJECT-TYPE
			SYNTAX INTEGER (1..4094)
			MAX-ACCESS read-only
			STATUS current
			DESCRIPTION
				"The user VLAN-ID that are leant at the running ONU."
			::= { sleGponOnuUserMacEntry 2 }


--   1.3.6.1.4.1.6296.101.23.6.2.1.1.3
-- 1.3.6.1.4.1.6296.101.23.6.2.1.1.3
		sleGponOnuUserMacPortId OBJECT-TYPE
			SYNTAX INTEGER (0..4096)
			MAX-ACCESS read-only
			STATUS current
			DESCRIPTION
				"The user GEM PORT-ID that are leant at the running ONU."
			::= { sleGponOnuUserMacEntry 3 }


		sleGponOnuUserMacOltId OBJECT-TYPE
			SYNTAX INTEGER (1..2147483647)
			MAX-ACCESS read-only
			STATUS current
			DESCRIPTION
				"Gpon Olt Index."
			::= { sleGponOnuUserMacEntry 4 }


--     1.3.6.1.4.1.6296.101.23.6.2.1.1.5
-- 1.3.6.1.4.1.6296.101.23.6.2.1.1.5
-- 1.3.6.1.4.1.6296.101.23.6.2.1.1.5
-- 1.3.6.1.4.1.6296.101.23.6.2.1.1.5
		sleGponOnuUserMacOnuId OBJECT-TYPE
			SYNTAX INTEGER (1..65535)
			MAX-ACCESS read-only
			STATUS current
			DESCRIPTION
				"Gpon Onu Index."
			::= { sleGponOnuUserMacEntry 5 }


--  1.3.6.1.4.1.6296.101.23.6.2.1.1.6
		sleGponOnuUserMacStatus OBJECT-TYPE
			SYNTAX INTEGER
				{
				dynamic(0),
				snoop(1),
				static(2),
				unknown(3)
				}
			MAX-ACCESS read-only
			STATUS current
			DESCRIPTION
				"The mac learning status."
			::= { sleGponOnuUserMacEntry 6 }


--   1.3.6.1.4.1.6296.101.23.6.2.2
-- 1.3.6.1.4.1.6296.101.23.6.2.2
		sleGponOnuUserMacControl OBJECT IDENTIFIER ::= { sleGponOnuUserMac 2 }


--   1.3.6.1.4.1.6296.101.23.6.2.2.1
-- 1.3.6.1.4.1.6296.101.23.6.2.2.1
		sleGponOnuUserMacControlRequest OBJECT-TYPE
			SYNTAX INTEGER
				{
				clearOltMacOne(1),
				clearOltMacOnu(2),
				clearOltMacAll(3),
				updateOltMac(4)
				}
			MAX-ACCESS read-write
			STATUS current
			DESCRIPTION
				"The request of a user command"
			::= { sleGponOnuUserMacControl 1 }


--   1.3.6.1.4.1.6296.101.23.6.2.2.2
-- 1.3.6.1.4.1.6296.101.23.6.2.2.2
		sleGponOnuUserMacControlStatus OBJECT-TYPE
			SYNTAX SleControlStatusType
			MAX-ACCESS read-write
			STATUS current
			DESCRIPTION
				"The status of user command"
			::= { sleGponOnuUserMacControl 2 }


--   1.3.6.1.4.1.6296.101.23.6.2.2.3
-- 1.3.6.1.4.1.6296.101.23.6.2.2.3
		sleGponOnuUserMacControlTimer OBJECT-TYPE
			SYNTAX Gauge32
			MAX-ACCESS read-write
			STATUS current
			DESCRIPTION
				"The maximum time for the manager for a long running user command"
			::= { sleGponOnuUserMacControl 3 }


--   1.3.6.1.4.1.6296.101.23.6.2.2.4
-- 1.3.6.1.4.1.6296.101.23.6.2.2.4
		sleGponOnuUserMacControlTimeStamp OBJECT-TYPE
			SYNTAX Integer32
			MAX-ACCESS read-write
			STATUS current
			DESCRIPTION
				"The time stamp of the last command(end of command)"
			::= { sleGponOnuUserMacControl 4 }


--   1.3.6.1.4.1.6296.101.23.6.2.2.5
-- 1.3.6.1.4.1.6296.101.23.6.2.2.5
		sleGponOnuUserMacControlReqResult OBJECT-TYPE
			SYNTAX SleControlRequestResultType
			MAX-ACCESS read-write
			STATUS current
			DESCRIPTION
				"The result of the last user command"
			::= { sleGponOnuUserMacControl 5 }


		sleGponOnuUserMacControlOltId OBJECT-TYPE
			SYNTAX INTEGER (1..2147483647)
			MAX-ACCESS read-write
			STATUS current
			DESCRIPTION
				"Gpon Olt Index"
			::= { sleGponOnuUserMacControl 6 }


--   1.3.6.1.4.1.6296.101.23.6.2.2.7
-- 1.3.6.1.4.1.6296.101.23.6.2.2.7
		sleGponOnuUserMacControlOnuId OBJECT-TYPE
			SYNTAX INTEGER (1..65535)
			MAX-ACCESS read-write
			STATUS current
			DESCRIPTION
				"Gpon Onu Index"
			::= { sleGponOnuUserMacControl 7 }


--   1.3.6.1.4.1.6296.101.23.6.2.2.8
-- 1.3.6.1.4.1.6296.101.23.6.2.2.8
		sleGponOnuUserMacControlAddress OBJECT-TYPE
			SYNTAX OCTET STRING
			MAX-ACCESS read-write
			STATUS current
			DESCRIPTION
				"The user MAC addresses that are leant at the running ONU."
			::= { sleGponOnuUserMacControl 8 }


--   1.3.6.1.4.1.6296.101.23.6.2.2.9
-- 1.3.6.1.4.1.6296.101.23.6.2.2.9
		sleGponOnuUserMacControlVlanId OBJECT-TYPE
			SYNTAX INTEGER (1..65535)
			MAX-ACCESS read-write
			STATUS current
			DESCRIPTION
				"GPON ONU Vlan Index"
			::= { sleGponOnuUserMacControl 9 }


--   1.3.6.1.4.1.6296.101.23.6.2.3
-- 1.3.6.1.4.1.6296.101.23.6.2.3
		sleGponOnuUserMacNotification OBJECT IDENTIFIER ::= { sleGponOnuUserMac 3 }


--   1.3.6.1.4.1.6296.101.23.6.2.3.1
-- 1.3.6.1.4.1.6296.101.23.6.2.3.1
		sleGponOnuUserMacOltMacChanged NOTIFICATION-TYPE
			OBJECTS { sleGponOnuUserMacControlRequest, sleGponOnuUserMacControlTimeStamp, sleGponOnuUserMacControlReqResult, sleGponOnuUserMacControlOltId, sleGponOnuUserMacControlOnuId,
				sleGponOnuUserMacControlAddress, sleGponOnuUserMacControlVlanId }
			STATUS current
			DESCRIPTION
				"clearOltMacOne"
			::= { sleGponOnuUserMacNotification 1 }


--   1.3.6.1.4.1.6296.101.23.6.2.3.2
-- 1.3.6.1.4.1.6296.101.23.6.2.3.2
		sleGponOnuUserMacOltMacOnuChanged NOTIFICATION-TYPE
			OBJECTS { sleGponOnuUserMacControlRequest, sleGponOnuUserMacControlTimeStamp, sleGponOnuUserMacControlReqResult, sleGponOnuUserMacControlOltId, sleGponOnuUserMacControlOnuId
				 }
			STATUS current
			DESCRIPTION
				"clearOltMacOnu"
			::= { sleGponOnuUserMacNotification 2 }


--   1.3.6.1.4.1.6296.101.23.6.2.3.3
-- 1.3.6.1.4.1.6296.101.23.6.2.3.3
		sleGponOnuUserMacOltMacAllChanged NOTIFICATION-TYPE
			OBJECTS { sleGponOnuUserMacControlRequest, sleGponOnuUserMacControlTimeStamp, sleGponOnuUserMacControlReqResult, sleGponOnuUserMacControlOltId }
			STATUS current
			DESCRIPTION
				"clearOltMacAll"
			::= { sleGponOnuUserMacNotification 3 }


--   1.3.6.1.4.1.6296.101.23.6.2.3.4
-- 1.3.6.1.4.1.6296.101.23.6.2.3.4
		sleGponOnuUserMacOltMacUpdated NOTIFICATION-TYPE
			OBJECTS { sleGponOnuUserMacControlRequest, sleGponOnuUserMacControlTimeStamp, sleGponOnuUserMacControlReqResult, sleGponOnuUserMacControlOltId, sleGponOnuUserMacControlOnuId
				 }
			STATUS current
			DESCRIPTION
				"updateOltMac"
			::= { sleGponOnuUserMacNotification 4 }


--   1.3.6.1.4.1.6296.101.23.6.3
-- 1.3.6.1.4.1.6296.101.23.6.3
		sleGponBridgeVoIP OBJECT IDENTIFIER ::= { sleGponBridge 3 }


--   1.3.6.1.4.1.6296.101.23.6.3.1
-- 1.3.6.1.4.1.6296.101.23.6.3.1
		sleGponBridgeVoIPInfoTable OBJECT-TYPE
			SYNTAX SEQUENCE OF SleGponBridgeVoIPInfoEntry
			MAX-ACCESS not-accessible
			STATUS current
			DESCRIPTION
				"sleGponBridgeVoIPInfoTable"
			::= { sleGponBridgeVoIP 1 }


--   1.3.6.1.4.1.6296.101.23.6.3.1.1
-- 1.3.6.1.4.1.6296.101.23.6.3.1.1
		sleGponBridgeVoIPInfoEntry OBJECT-TYPE
			SYNTAX SleGponBridgeVoIPInfoEntry
			MAX-ACCESS not-accessible
			STATUS current
			DESCRIPTION
				"key: sleGponBridgeVoIPInfoOltId, sleGponBridgeVoIPInfoOnuId"
			INDEX { sleGponBridgeVoIPInfoOltId, sleGponBridgeVoIPInfoOnuId }
			::= { sleGponBridgeVoIPInfoTable 1 }


		SleGponBridgeVoIPInfoEntry ::=
			SEQUENCE {
				sleGponBridgeVoIPInfoOltId
					Integer32,
				sleGponBridgeVoIPInfoOnuId
					Integer32,
				sleGponBridgeVoIPInfoDHCP
					INTEGER,
				sleGponBridgeVoIPInfoIpAddress
					IpAddress,
				sleGponBridgeVoIPInfoMethods
					BITS,
				sleGponBridgeVoIPInfoCurrMethods
					INTEGER,
				sleGponBridgeVoIPInfoProtocols
					BITS,
				sleGponBridgeVoIPInfoCurrProtocols
					INTEGER
			 }

--   1.3.6.1.4.1.6296.101.23.6.3.1.1.1
-- 1.3.6.1.4.1.6296.101.23.6.3.1.1.1
		sleGponBridgeVoIPInfoOltId OBJECT-TYPE
			SYNTAX Integer32 (1..2147483647)
			MAX-ACCESS read-only
			STATUS current
			DESCRIPTION
				"Olt Index."
			::= { sleGponBridgeVoIPInfoEntry 1 }


--   1.3.6.1.4.1.6296.101.23.6.3.1.1.2
-- 1.3.6.1.4.1.6296.101.23.6.3.1.1.2
		sleGponBridgeVoIPInfoOnuId OBJECT-TYPE
			SYNTAX Integer32 (1..65535)
			MAX-ACCESS read-only
			STATUS current
			DESCRIPTION
				"Onu Index."
			::= { sleGponBridgeVoIPInfoEntry 2 }


--   1.3.6.1.4.1.6296.101.23.6.3.1.1.3
-- 1.3.6.1.4.1.6296.101.23.6.3.1.1.3
		sleGponBridgeVoIPInfoDHCP OBJECT-TYPE
			SYNTAX INTEGER
				{
				auto(1),
				manual(2)
				}
			MAX-ACCESS read-only
			STATUS current
			DESCRIPTION
				"Indicate whether using DHCP or not."
			::= { sleGponBridgeVoIPInfoEntry 3 }


--   1.3.6.1.4.1.6296.101.23.6.3.1.1.4
-- 1.3.6.1.4.1.6296.101.23.6.3.1.1.4
		sleGponBridgeVoIPInfoIpAddress OBJECT-TYPE
			SYNTAX IpAddress
			MAX-ACCESS read-only
			STATUS current
			DESCRIPTION
				"IP Address."
			::= { sleGponBridgeVoIPInfoEntry 4 }


--   1.3.6.1.4.1.6296.101.23.6.3.1.1.5
-- 1.3.6.1.4.1.6296.101.23.6.3.1.1.5
		sleGponBridgeVoIPInfoMethods OBJECT-TYPE
			SYNTAX BITS
				{
				omci(0),
				file(1),
				tr69(2),
				ietf(3)
				}
			MAX-ACCESS read-only
			STATUS current
			DESCRIPTION
				"Supporting Methods."
			::= { sleGponBridgeVoIPInfoEntry 5 }


--
-- 1.3.6.1.4.1.6296.101.23.6.3.1.1.6
-- 1.3.6.1.4.1.6296.101.23.6.3.1.1.6
		sleGponBridgeVoIPInfoCurrMethods OBJECT-TYPE
			SYNTAX INTEGER
				{
				omci(1),
				file(2),
				tr69(3),
				ietf(4),
				unknown(255)
				}
			MAX-ACCESS read-only
			STATUS current
			DESCRIPTION
				"Current using method."
			::= { sleGponBridgeVoIPInfoEntry 6 }


--   1.3.6.1.4.1.6296.101.23.6.3.1.1.7
-- 1.3.6.1.4.1.6296.101.23.6.3.1.1.7
		sleGponBridgeVoIPInfoProtocols OBJECT-TYPE
			SYNTAX BITS
				{
				sip(0),
				h248(1),
				mgcp(2)
				}
			MAX-ACCESS read-only
			STATUS current
			DESCRIPTION
				"Supporting Protocols."
			::= { sleGponBridgeVoIPInfoEntry 7 }


--   1.3.6.1.4.1.6296.101.23.6.3.1.1.8
-- 1.3.6.1.4.1.6296.101.23.6.3.1.1.8
		sleGponBridgeVoIPInfoCurrProtocols OBJECT-TYPE
			SYNTAX INTEGER
				{
				sip(1),
				h248(2),
				mgcp(3),
				unknown(255)
				}
			MAX-ACCESS read-only
			STATUS current
			DESCRIPTION
				"Current using protocol."
			::= { sleGponBridgeVoIPInfoEntry 8 }


--   1.3.6.1.4.1.6296.101.23.6.3.2
-- 1.3.6.1.4.1.6296.101.23.6.3.2
		sleGponBridgeVoIPLineTable OBJECT-TYPE
			SYNTAX SEQUENCE OF SleGponBridgeVoIPLineEntry
			MAX-ACCESS not-accessible
			STATUS current
			DESCRIPTION
				"sleGponBridgeVoIPLineTable"
			::= { sleGponBridgeVoIP 2 }


--   1.3.6.1.4.1.6296.101.23.6.3.2.1
-- 1.3.6.1.4.1.6296.101.23.6.3.2.1
		sleGponBridgeVoIPLineEntry OBJECT-TYPE
			SYNTAX SleGponBridgeVoIPLineEntry
			MAX-ACCESS not-accessible
			STATUS current
			DESCRIPTION
				"sleGponBridgeVoIPLineOltId, sleGponBridgeVoIPLineOnuId, sleGponBridgeVoIPLinePots"
			INDEX { sleGponBridgeVoIPLineOltId, sleGponBridgeVoIPLineOnuId, sleGponBridgeVoIPLinePots }
			::= { sleGponBridgeVoIPLineTable 1 }


		SleGponBridgeVoIPLineEntry ::=
			SEQUENCE {
				sleGponBridgeVoIPLineOltId
					Integer32,
				sleGponBridgeVoIPLineOnuId
					Integer32,
				sleGponBridgeVoIPLinePots
					Integer32,
				sleGponBridgeVoIPLineAdminStatus
					INTEGER,
				sleGponBridgeVoIPLineOperStatus
					INTEGER,
				sleGponBridgeVoIPLineStatus
					INTEGER
			 }

--   1.3.6.1.4.1.6296.101.23.6.3.2.1.1
-- 1.3.6.1.4.1.6296.101.23.6.3.2.1.1
		sleGponBridgeVoIPLineOltId OBJECT-TYPE
			SYNTAX Integer32 (1..2147483647)
			MAX-ACCESS read-only
			STATUS current
			DESCRIPTION
				"Olt Index."
			::= { sleGponBridgeVoIPLineEntry 1 }


--   1.3.6.1.4.1.6296.101.23.6.3.2.1.2
-- 1.3.6.1.4.1.6296.101.23.6.3.2.1.2
		sleGponBridgeVoIPLineOnuId OBJECT-TYPE
			SYNTAX Integer32 (1..65535)
			MAX-ACCESS read-only
			STATUS current
			DESCRIPTION
				"Onu Index."
			::= { sleGponBridgeVoIPLineEntry 2 }


--   1.3.6.1.4.1.6296.101.23.6.3.2.1.3
-- 1.3.6.1.4.1.6296.101.23.6.3.2.1.3
		sleGponBridgeVoIPLinePots OBJECT-TYPE
			SYNTAX Integer32 (1..65535)
			MAX-ACCESS read-only
			STATUS current
			DESCRIPTION
				"The Outer Vlan-ID to tag for incoming packet with vlan index."
			::= { sleGponBridgeVoIPLineEntry 3 }


--   1.3.6.1.4.1.6296.101.23.6.3.2.1.4
-- 1.3.6.1.4.1.6296.101.23.6.3.2.1.4
		sleGponBridgeVoIPLineAdminStatus OBJECT-TYPE
			SYNTAX INTEGER
				{
				up(1),
				down(2)
				}
			MAX-ACCESS read-only
			STATUS current
			DESCRIPTION
				"Admin status."
			::= { sleGponBridgeVoIPLineEntry 4 }


--   1.3.6.1.4.1.6296.101.23.6.3.2.1.5
-- 1.3.6.1.4.1.6296.101.23.6.3.2.1.5
		sleGponBridgeVoIPLineOperStatus OBJECT-TYPE
			SYNTAX INTEGER
				{
				up(1),
				down(2)
				}
			MAX-ACCESS read-only
			STATUS current
			DESCRIPTION
				"Oper status."
			::= { sleGponBridgeVoIPLineEntry 5 }


--   1.3.6.1.4.1.6296.101.23.6.3.2.1.6
-- 1.3.6.1.4.1.6296.101.23.6.3.2.1.6
		sleGponBridgeVoIPLineStatus OBJECT-TYPE
			SYNTAX INTEGER
				{
				noneInitial(1),
				registered(2),
				inSession(3),
				failedRegistrationIcmpError(4),
				failedRegistrationFailedTcp(5),
				failedRegistrationFailedAuthentication(6),
				failedRegistrationTimeout(7),
				failedRegistrationServerFailCode(8),
				failedInviteIcmpError(9),
				failedInviteFailedTcp(10),
				failedInviteFailedAuthentication(11),
				failedInviteTimeout(12),
				failedInviteServerFailCode(13),
				portNotConfigured(14),
				configDone(15)
				}
			MAX-ACCESS read-only
			STATUS current
			DESCRIPTION
				"Line Status"
			::= { sleGponBridgeVoIPLineEntry 6 }


--   1.3.6.1.4.1.6296.101.23.6.4
-- 1.3.6.1.4.1.6296.101.23.6.4
		sleGponBridgeSlot OBJECT IDENTIFIER ::= { sleGponBridge 4 }


--   1.3.6.1.4.1.6296.101.23.6.4.1
-- 1.3.6.1.4.1.6296.101.23.6.4.1
		sleGponBridgeSlotStatusTable OBJECT-TYPE
			SYNTAX SEQUENCE OF SleGponBridgeSlotStatusEntry
			MAX-ACCESS not-accessible
			STATUS current
			DESCRIPTION
				"sleGponBridgeSlotStatusTable"
			::= { sleGponBridgeSlot 1 }


--   1.3.6.1.4.1.6296.101.23.6.4.1.1
-- 1.3.6.1.4.1.6296.101.23.6.4.1.1
		sleGponBridgeSlotStatusEntry OBJECT-TYPE
			SYNTAX SleGponBridgeSlotStatusEntry
			MAX-ACCESS not-accessible
			STATUS current
			DESCRIPTION
				"key: sleGponBridgeSlotIndex"
			INDEX { sleGponBridgeSlotIndex }
			::= { sleGponBridgeSlotStatusTable 1 }


		SleGponBridgeSlotStatusEntry ::=
			SEQUENCE {
				sleGponBridgeSlotIndex
					Integer32,
				sleGponBridgeSlotConnectionStatus
					INTEGER,
				sleGponBridgeSlotFlags
					INTEGER
			 }

--   1.3.6.1.4.1.6296.101.23.6.4.1.1.1
-- 1.3.6.1.4.1.6296.101.23.6.4.1.1.1
		sleGponBridgeSlotIndex OBJECT-TYPE
			SYNTAX Integer32 (1..65535)
			MAX-ACCESS read-only
			STATUS current
			DESCRIPTION
				"Gpon slot index."
			::= { sleGponBridgeSlotStatusEntry 1 }


--   1.3.6.1.4.1.6296.101.23.6.4.1.1.2
-- 1.3.6.1.4.1.6296.101.23.6.4.1.1.2
		sleGponBridgeSlotConnectionStatus OBJECT-TYPE
			SYNTAX INTEGER
				{
				nonCreate(1),
				disconnect(2),
				waiting(3),
				connect(4),
				monitoring(5),
				unknown(255)
				}
			MAX-ACCESS read-only
			STATUS current
			DESCRIPTION
				"Gpon slot connection status."
			::= { sleGponBridgeSlotStatusEntry 2 }


--   1.3.6.1.4.1.6296.101.23.6.4.1.1.3
-- 1.3.6.1.4.1.6296.101.23.6.4.1.1.3
		sleGponBridgeSlotFlags OBJECT-TYPE
			SYNTAX INTEGER
				{
				true(1),
				false(2)
				}
			MAX-ACCESS read-only
			STATUS current
			DESCRIPTION
				"Flags."
			::= { sleGponBridgeSlotStatusEntry 3 }


--  1.3.6.1.4.1.6296.101.23.6.5
		sleGponOnuVoipLine OBJECT IDENTIFIER ::= { sleGponBridge 5 }


--  1.3.6.1.4.1.6296.101.23.6.5.1
		sleGponOnuVoipLineTable OBJECT-TYPE
			SYNTAX SEQUENCE OF SleGponOnuVoipLineEntry
			MAX-ACCESS not-accessible
			STATUS current
			DESCRIPTION
				"sleGponOnuVoipLineTable"
			::= { sleGponOnuVoipLine 1 }


--  1.3.6.1.4.1.6296.101.23.6.5.1.1
		sleGponOnuVoipLineEntry OBJECT-TYPE
			SYNTAX SleGponOnuVoipLineEntry
			MAX-ACCESS not-accessible
			STATUS current
			DESCRIPTION
				"key: sleGponOnuVoipLineOltId, sleGponOnuVoipLineOnuId, sleGponOnuVoipLineId"
			INDEX { sleGponOnuVoipLineOltId, sleGponOnuVoipLineOnuId, sleGponOnuVoipLineId }
			::= { sleGponOnuVoipLineTable 1 }


		SleGponOnuVoipLineEntry ::=
			SEQUENCE {
				sleGponOnuVoipLineOltId
					Integer32,
				sleGponOnuVoipLineOnuId
					Integer32,
				sleGponOnuVoipLineId
					Integer32,
				sleGponOnuVoipLineStatus
					INTEGER,
				sleGponOnuVoipLineUsedCodec
					INTEGER,
				sleGponOnuVoipLineSessionType
					INTEGER,
				sleGponOnuVoipLine1stProtocolPeriod
					INTEGER,
				sleGponOnuVoipLine1stDestAddr
					OCTET STRING,
				sleGponOnuVoipLine2ndProtocolPeriod
					INTEGER,
				sleGponOnuVoipLine2ndDestAddr
					OCTET STRING
			 }

--  1.3.6.1.4.1.6296.101.23.6.5.1.1.1
		sleGponOnuVoipLineOltId OBJECT-TYPE
			SYNTAX Integer32 (1..2147483647)
			MAX-ACCESS read-only
			STATUS current
			DESCRIPTION
				"Olt Index."
			::= { sleGponOnuVoipLineEntry 1 }


--  1.3.6.1.4.1.6296.101.23.6.5.1.1.2
		sleGponOnuVoipLineOnuId OBJECT-TYPE
			SYNTAX Integer32 (1..65535)
			MAX-ACCESS read-only
			STATUS current
			DESCRIPTION
				"Onu Index."
			::= { sleGponOnuVoipLineEntry 2 }


--  1.3.6.1.4.1.6296.101.23.6.5.1.1.3
		sleGponOnuVoipLineId OBJECT-TYPE
			SYNTAX Integer32 (1..65535)
			MAX-ACCESS read-only
			STATUS current
			DESCRIPTION
				"The Outer Vlan-ID to tag for incoming packet with vlan index."
			::= { sleGponOnuVoipLineEntry 3 }


--  1.3.6.1.4.1.6296.101.23.6.5.1.1.4
		sleGponOnuVoipLineStatus OBJECT-TYPE
			SYNTAX INTEGER
				{
				noneInitial(1),
				registered(2),
				inSession(3),
				failedRegistrationIcmpError(4),
				failedRegistrationFailedTcp(5),
				failedRegistrationFailedAuthentication(6),
				failedRegistrationTimeout(7),
				failedRegistrationServerFailCode(8),
				failedInviteIcmpError(9),
				failedInviteFailedTcp(10),
				failedInviteFailedAuthentication(11),
				failedInviteTimeout(12),
				failedInviteServerFailCode(13),
				portNotConfigured(14),
				configDone(15)
				}
			MAX-ACCESS read-only
			STATUS current
			DESCRIPTION
				"The line status"
			::= { sleGponOnuVoipLineEntry 4 }


--  1.3.6.1.4.1.6296.101.23.6.5.1.1.5
		sleGponOnuVoipLineUsedCodec OBJECT-TYPE
			SYNTAX INTEGER
				{
				autoSelect(0),
				gDot711ALaw(1),
				gDot711MuLaw(2),
				gDot723(3),
				gDot722Dot1(4),
				gDot722Dot2(5),
				gDot723Dot1(6),
				gDot726(7),
				gDot728(8),
				gDot729A(9),
				gDot729B(10),
				gDot729D(11),
				gDot729E(12),
				melp(13),
				unknown(255)
				}
			MAX-ACCESS read-only
			STATUS current
			DESCRIPTION
				"The used codec configuration"
			::= { sleGponOnuVoipLineEntry 5 }


--  1.3.6.1.4.1.6296.101.23.6.5.1.1.6
		sleGponOnuVoipLineSessionType OBJECT-TYPE
			SYNTAX INTEGER
				{
				idle(0),
				twoWay(1),
				threeWay(2),
				fax(3),
				telem(4),
				conference(5),
				unknown(255)
				}
			MAX-ACCESS read-only
			STATUS current
			DESCRIPTION
				"The session type"
			::= { sleGponOnuVoipLineEntry 6 }


--  1.3.6.1.4.1.6296.101.23.6.5.1.1.7
		sleGponOnuVoipLine1stProtocolPeriod OBJECT-TYPE
			SYNTAX INTEGER (1..65535)
			MAX-ACCESS read-only
			STATUS current
			DESCRIPTION
				"1st protocol period"
			::= { sleGponOnuVoipLineEntry 7 }


--  1.3.6.1.4.1.6296.101.23.6.5.1.1.8
		sleGponOnuVoipLine1stDestAddr OBJECT-TYPE
			SYNTAX OCTET STRING
			MAX-ACCESS read-only
			STATUS current
			DESCRIPTION
				"1st destination address"
			::= { sleGponOnuVoipLineEntry 8 }


--  1.3.6.1.4.1.6296.101.23.6.5.1.1.9
		sleGponOnuVoipLine2ndProtocolPeriod OBJECT-TYPE
			SYNTAX INTEGER (1..65535)
			MAX-ACCESS read-only
			STATUS current
			DESCRIPTION
				"2nd protocol period"
			::= { sleGponOnuVoipLineEntry 9 }


--  1.3.6.1.4.1.6296.101.23.6.5.1.1.10
		sleGponOnuVoipLine2ndDestAddr OBJECT-TYPE
			SYNTAX OCTET STRING
			MAX-ACCESS read-only
			STATUS current
			DESCRIPTION
				"2nd destination address"
			::= { sleGponOnuVoipLineEntry 10 }


--  1.3.6.1.4.1.6296.101.23.6.5.2
		sleGponOnuVoipLineControl OBJECT IDENTIFIER ::= { sleGponOnuVoipLine 2 }


--  1.3.6.1.4.1.6296.101.23.6.5.2.1
		sleGponOnuVoipLineControlRequest OBJECT-TYPE
			SYNTAX INTEGER { updateVoipInfo(1) }
			MAX-ACCESS read-write
			STATUS current
			DESCRIPTION
				"The request of a user command"
			::= { sleGponOnuVoipLineControl 1 }


--  1.3.6.1.4.1.6296.101.23.6.5.2.2
		sleGponOnuVoipLineControlStatus OBJECT-TYPE
			SYNTAX SleControlStatusType
			MAX-ACCESS read-write
			STATUS current
			DESCRIPTION
				"The status of user command"
			::= { sleGponOnuVoipLineControl 2 }


--  1.3.6.1.4.1.6296.101.23.6.5.2.3
		sleGponOnuVoipLineControlTimer OBJECT-TYPE
			SYNTAX Gauge32
			MAX-ACCESS read-write
			STATUS current
			DESCRIPTION
				"The maximum time for the manager for a long running user command"
			::= { sleGponOnuVoipLineControl 3 }


--  1.3.6.1.4.1.6296.101.23.6.5.2.4
		sleGponOnuVoipLineControlTimeStamp OBJECT-TYPE
			SYNTAX TimeTicks
			MAX-ACCESS read-write
			STATUS current
			DESCRIPTION
				"The time stamp of the last command(end of command)"
			::= { sleGponOnuVoipLineControl 4 }


--  1.3.6.1.4.1.6296.101.23.6.5.2.5
		sleGponOnuVoipLineControlReqResult OBJECT-TYPE
			SYNTAX SleControlRequestResultType
			MAX-ACCESS read-write
			STATUS current
			DESCRIPTION
				"The result of the last user command"
			::= { sleGponOnuVoipLineControl 5 }


--  1.3.6.1.4.1.6296.101.23.6.5.2.6
		sleGponOnuVoipLineControlOltId OBJECT-TYPE
			SYNTAX Integer32 (1..2147483647)
			MAX-ACCESS read-write
			STATUS current
			DESCRIPTION
				"Olt Index."
			::= { sleGponOnuVoipLineControl 6 }


--  1.3.6.1.4.1.6296.101.23.6.5.2.7
		sleGponOnuVoipLineControlOnuId OBJECT-TYPE
			SYNTAX Integer32 (1..65535)
			MAX-ACCESS read-write
			STATUS current
			DESCRIPTION
				"Onu Index."
			::= { sleGponOnuVoipLineControl 7 }


--  1.3.6.1.4.1.6296.101.23.6.5.3
		sleGponOnuVoipLineNotification OBJECT IDENTIFIER ::= { sleGponOnuVoipLine 3 }


--  1.3.6.1.4.1.6296.101.23.6.5.3.1
		sleGponOnuVoipLineVoipInfoChanged NOTIFICATION-TYPE
			OBJECTS { sleGponOnuVoipLineControlRequest, sleGponOnuVoipLineControlTimeStamp, sleGponOnuVoipLineControlReqResult, sleGponOnuVoipLineControlOltId, sleGponOnuVoipLineControlOnuId
				 }
			STATUS current
			DESCRIPTION
				"Description."
			::= { sleGponOnuVoipLineNotification 1 }


--  1.3.6.1.4.1.6296.101.23.6.6
		sleGponOnuAni OBJECT IDENTIFIER ::= { sleGponBridge 6 }


--   1.3.6.1.4.1.6296.101.23.6.1.1
-- 1.3.6.1.4.1.6296.101.23.6.6.1
		sleGponOnuAniTable OBJECT-TYPE
			SYNTAX SEQUENCE OF SleGponOnuAniEntry
			MAX-ACCESS not-accessible
			STATUS current
			DESCRIPTION
				"sleGponOnuPortTable"
			::= { sleGponOnuAni 1 }


--   1.3.6.1.4.1.6296.101.23.6.1.1.1
-- 1.3.6.1.4.1.6296.101.23.6.6.1.1
		sleGponOnuAniEntry OBJECT-TYPE
			SYNTAX SleGponOnuAniEntry
			MAX-ACCESS not-accessible
			STATUS current
			DESCRIPTION
				"key: sleGponOltId, sleGponOnuId, sleGponOnuPortSlotId, sleGponOnuPortId"
			INDEX { sleGponOltId, sleGponOnuId, sleGponOnuAniId }
			::= { sleGponOnuAniTable 1 }


		SleGponOnuAniEntry ::=
			SEQUENCE {
				sleGponOnuAniId
					Integer32,
				sleGponOnuAniType
					INTEGER,
				sleGponOnuAniOpticModuleInstall
					INTEGER,
				sleGponOnuAniOpticModuleTransceiverType
					INTEGER,
				sleGponOnuAniOpticModuleTransceiverDetailType
					INTEGER,
				sleGponOnuAniOpticModuleLengthMode
					INTEGER,
				sleGponOnuAniOpticModuleLength
					INTEGER,
				sleGponOnuAniOpticModuleSpeed
					INTEGER,
				sleGponOnuAniOpticModuleWavelength
					INTEGER,
				sleGponOnuAniOpticModuleConnecterType
					INTEGER,
				sleGponOnuAniOpticModuleVendorName
					OCTET STRING,
				sleGponOnuAniOpticModuleVendorPartName
					OCTET STRING,
				sleGponOnuAniOpticModuleVendorRevision
					OCTET STRING,
				sleGponOnuAniOpticModuleVendorSerialNumber
					OCTET STRING,
				sleGponOnuAniOpticModuleProductDate
					OCTET STRING,
				sleGponOnuAniOpticModuleTemper
					OCTET STRING,
				sleGponOnuAniOpticModuleVoltage
					OCTET STRING,
				sleGponOnuAniOpticModuleTxbias
					OCTET STRING,
				sleGponOnuAniOpticModuleTxPower
					OCTET STRING,
				sleGponOnuAniOpticModuleRxPower
					OCTET STRING,
				sleGponOnuAniOpticModuleTemperHighThr
					Integer32,
				sleGponOnuAniOpticModuleTemperLowThr
					Integer32,
				sleGponOnuAniOpticModuleVoltageHighThr
					Integer32,
				sleGponOnuAniOpticModuleVoltageLowThr
					Integer32,
				sleGponOnuAniOpticModuleTxbiasHighThr
					Integer32,
				sleGponOnuAniOpticModuleTxbiasLowThr
					Integer32,
				sleGponOnuAniOpticModuleTxPowerHighThr
					Integer32,
				sleGponOnuAniOpticModuleTxPowerLowThr
					Integer32,
				sleGponOnuAniOpticModuleRxPowerHighThr
					Integer32,
				sleGponOnuAniOpticModuleRxPowerLowThr
					Integer32
			 }

--  1.3.6.1.4.1.6296.101.23.6.6.1.1.1
		sleGponOnuAniId OBJECT-TYPE
			SYNTAX Integer32 (1..65535)
			MAX-ACCESS read-only
			STATUS current
			DESCRIPTION
				"The ani index."
			::= { sleGponOnuAniEntry 1 }


--  1.3.6.1.4.1.6296.101.23.6.6.1.1.2
		sleGponOnuAniType OBJECT-TYPE
			SYNTAX INTEGER
				{
				gpon(1),
				video(2)
				}
			MAX-ACCESS read-only
			STATUS current
			DESCRIPTION
				"The ONU ANI type."
			::= { sleGponOnuAniEntry 2 }


--  1.3.6.1.4.1.6296.101.23.6.6.1.1.3
		sleGponOnuAniOpticModuleInstall OBJECT-TYPE
			SYNTAX INTEGER
				{
				uninstall(0),
				install(1)
				}
			MAX-ACCESS read-only
			STATUS current
			DESCRIPTION
				"The module instatll status."
			::= { sleGponOnuAniEntry 3 }


--  1.3.6.1.4.1.6296.101.23.6.6.1.1.4
		sleGponOnuAniOpticModuleTransceiverType OBJECT-TYPE
			SYNTAX INTEGER
				{
				gbic(1),
				solderedToMotherboard(2),
				sfp(3),
				xbi300Pin(4),
				xenpak(5),
				xfp(6),
				xff(7),
				xfpE(8),
				spak(9),
				x2(10),
				unknown(255)
				}
			MAX-ACCESS read-only
			STATUS current
			DESCRIPTION
				"The module transceiver type.
				1: GBIC
				2 :Soldered to motherboard
				3: SFP
				4 :300 pin XBI
				5: XENPAK
				6: XFP
				7: XFF
				8: XFP-E
				9 :XPAK
				10: X2
				255:Unknown"
			::= { sleGponOnuAniEntry 4 }


--  1.3.6.1.4.1.6296.101.23.6.6.1.1.5
		sleGponOnuAniOpticModuleTransceiverDetailType OBJECT-TYPE
			SYNTAX INTEGER
				{
				base1000SX(1),
				base1000LX(2),
				base1000CX(3),
				base1000T(4),
				base1000LXorLX10(5),
				base1000FX(6),
				base1000BX10(7),
				base1000PX(8),
				oc3MultiShortReach(9),
				oc3SingleIntermediateReach(10),
				oc3SingleLongReach(11),
				unknown(255)
				}
			MAX-ACCESS read-only
			STATUS current
			DESCRIPTION
				"The module tranceiver detail type.
				1: 1000Base-SX
				2: 1000Base-LX
				3: 1000Base-CX
				4: 1000Base-T
				5: 1000Base-LX/LX10
				6: 100Base-FX
				7: 1000Base-BX10
				8: 1000Base-PX
				9: OC-3(155M) Multi Mode Short Reach
				10: OC-3(155M) Single Mode Intermediate Reach
				11: OC-3(155M) Single Mode Long Reach
				255: Unknown"
			::= { sleGponOnuAniEntry 5 }


--  1.3.6.1.4.1.6296.101.23.6.6.1.1.6
		sleGponOnuAniOpticModuleLengthMode OBJECT-TYPE
			SYNTAX INTEGER
				{
				singleMode(1),
				multiMode(2),
				unknown(255)
				}
			MAX-ACCESS read-only
			STATUS current
			DESCRIPTION
				"The module length mode.
				1: singleMode
				2: multiMode
				255 : unknown"
			::= { sleGponOnuAniEntry 6 }


--  1.3.6.1.4.1.6296.101.23.6.6.1.1.7
		sleGponOnuAniOpticModuleLength OBJECT-TYPE
			SYNTAX INTEGER (1..65535)
			MAX-ACCESS read-only
			STATUS current
			DESCRIPTION
				"the module length(m)."
			::= { sleGponOnuAniEntry 7 }


--  1.3.6.1.4.1.6296.101.23.6.6.1.1.8
		sleGponOnuAniOpticModuleSpeed OBJECT-TYPE
			SYNTAX INTEGER
				{
				speed155(1),
				speed200(2),
				speed622(3),
				speed1062dot5(4),
				speed1250(5),
				speed2125(6),
				speed4250(7),
				speed2488(8),
				unknown(255)
				}
			MAX-ACCESS read-only
			STATUS current
			DESCRIPTION
				"The module speed.
				1: 155 Mb/s
				2: 200 Mb/s
				3: 622 Mb/s
				4: 1062.5 Mb/s
				5: 1250 Mb/s
				6: 2125 Mb/s
				7: 4250 Mb/s
				8: 2488 Mb/s
				255: unknown"
			::= { sleGponOnuAniEntry 8 }


--  1.3.6.1.4.1.6296.101.23.6.6.1.1.9
		sleGponOnuAniOpticModuleWavelength OBJECT-TYPE
			SYNTAX INTEGER
				{
				length850(1),
				length1310(2),
				length1490(3),
				length1550(4),
				unknown(255)
				}
			MAX-ACCESS read-only
			STATUS current
			DESCRIPTION
				"The module wavelength
				1: 850 nm
				2: 1310 nm
				3: 1490 nm
				4: 1550 nm
				255: unknown"
			::= { sleGponOnuAniEntry 9 }


--  1.3.6.1.4.1.6296.101.23.6.6.1.1.10
		sleGponOnuAniOpticModuleConnecterType OBJECT-TYPE
			SYNTAX INTEGER
				{
				sc(1),
				fiberChannelStyle1(2),
				fiberChannelStyle2(3),
				bncTnc(4),
				fiberChannelCoaxialHeaders(5),
				fiberJack(6),
				lc(7),
				mtRj(8),
				mu(9),
				sg(10),
				opticalPigtail(11),
				hssdc2(12),
				copperPigtail(13),
				unknown(255)
				}
			MAX-ACCESS read-only
			STATUS current
			DESCRIPTION
				"The module connecter type.
				1: SC
				2: Fiber Channel Style 1 copper connector
				3: Fiber Channel Style 2 copper connector
				4: BNC/TNC
				5: Fiber Channel coaxial headers
				6: Fiber Jack
				7: LC
				8: MT-RJ
				9: MU
				10: SG
				11: Optical Pigtail
				12: HSSDC II
				13: Copper Pigtail
				255: unknown"
			::= { sleGponOnuAniEntry 10 }


--  1.3.6.1.4.1.6296.101.23.6.6.1.1.11
		sleGponOnuAniOpticModuleVendorName OBJECT-TYPE
			SYNTAX OCTET STRING
			MAX-ACCESS read-only
			STATUS current
			DESCRIPTION
				"The module vendor name."
			::= { sleGponOnuAniEntry 11 }


--  1.3.6.1.4.1.6296.101.23.6.6.1.1.12
		sleGponOnuAniOpticModuleVendorPartName OBJECT-TYPE
			SYNTAX OCTET STRING
			MAX-ACCESS read-only
			STATUS current
			DESCRIPTION
				"The module vendor part name."
			::= { sleGponOnuAniEntry 12 }


--  1.3.6.1.4.1.6296.101.23.6.6.1.1.13
		sleGponOnuAniOpticModuleVendorRevision OBJECT-TYPE
			SYNTAX OCTET STRING
			MAX-ACCESS read-only
			STATUS current
			DESCRIPTION
				"The module vendor revision."
			::= { sleGponOnuAniEntry 13 }


--  1.3.6.1.4.1.6296.101.23.6.6.1.1.14
		sleGponOnuAniOpticModuleVendorSerialNumber OBJECT-TYPE
			SYNTAX OCTET STRING
			MAX-ACCESS read-only
			STATUS current
			DESCRIPTION
				"the moduel vendor serial number."
			::= { sleGponOnuAniEntry 14 }


--  1.3.6.1.4.1.6296.101.23.6.6.1.1.15
		sleGponOnuAniOpticModuleProductDate OBJECT-TYPE
			SYNTAX OCTET STRING
			MAX-ACCESS read-only
			STATUS current
			DESCRIPTION
				"The module vendor product date."
			::= { sleGponOnuAniEntry 15 }


--  1.3.6.1.4.1.6296.101.23.6.6.1.1.16
		sleGponOnuAniOpticModuleTemper OBJECT-TYPE
			SYNTAX OCTET STRING
			MAX-ACCESS read-only
			STATUS current
			DESCRIPTION
				"Internally measured module temperature.(C)"
			::= { sleGponOnuAniEntry 16 }


--  1.3.6.1.4.1.6296.101.23.6.6.1.1.17
		sleGponOnuAniOpticModuleVoltage OBJECT-TYPE
			SYNTAX OCTET STRING
			MAX-ACCESS read-only
			STATUS current
			DESCRIPTION
				"Internally measured supply voltage in transceiver.(V)
				"
			::= { sleGponOnuAniEntry 17 }


--  1.3.6.1.4.1.6296.101.23.6.6.1.1.18
		sleGponOnuAniOpticModuleTxbias OBJECT-TYPE
			SYNTAX OCTET STRING
			MAX-ACCESS read-only
			STATUS current
			DESCRIPTION
				"Internally measured TX Bias Current.(mA)"
			::= { sleGponOnuAniEntry 18 }


--  1.3.6.1.4.1.6296.101.23.6.6.1.1.19
		sleGponOnuAniOpticModuleTxPower OBJECT-TYPE
			SYNTAX OCTET STRING
			MAX-ACCESS read-only
			STATUS current
			DESCRIPTION
				"Measured TX output power.(dBm)"
			::= { sleGponOnuAniEntry 19 }


--  1.3.6.1.4.1.6296.101.23.6.6.1.1.20
		sleGponOnuAniOpticModuleRxPower OBJECT-TYPE
			SYNTAX OCTET STRING
			MAX-ACCESS read-only
			STATUS current
			DESCRIPTION
				"Measured RX input power.(dBm)"
			::= { sleGponOnuAniEntry 20 }


--  1.3.6.1.4.1.6296.101.23.6.6.1.1.21
		sleGponOnuAniOpticModuleTemperHighThr OBJECT-TYPE
			SYNTAX Integer32
			MAX-ACCESS read-only
			STATUS current
			DESCRIPTION
				"The temperature high threshold"
			::= { sleGponOnuAniEntry 21 }


--  1.3.6.1.4.1.6296.101.23.6.6.1.1.22
		sleGponOnuAniOpticModuleTemperLowThr OBJECT-TYPE
			SYNTAX Integer32
			MAX-ACCESS read-only
			STATUS current
			DESCRIPTION
				"The temperature low threshold"
			::= { sleGponOnuAniEntry 22 }


--  1.3.6.1.4.1.6296.101.23.6.6.1.1.23
		sleGponOnuAniOpticModuleVoltageHighThr OBJECT-TYPE
			SYNTAX Integer32
			MAX-ACCESS read-only
			STATUS current
			DESCRIPTION
				"The voltage high threshold (0.1 V)"
			::= { sleGponOnuAniEntry 23 }


--  1.3.6.1.4.1.6296.101.23.6.6.1.1.24
		sleGponOnuAniOpticModuleVoltageLowThr OBJECT-TYPE
			SYNTAX Integer32
			MAX-ACCESS read-only
			STATUS current
			DESCRIPTION
				"The voltage low threshold (0.1 V)"
			::= { sleGponOnuAniEntry 24 }


--  1.3.6.1.4.1.6296.101.23.6.6.1.1.25
		sleGponOnuAniOpticModuleTxbiasHighThr OBJECT-TYPE
			SYNTAX Integer32
			MAX-ACCESS read-only
			STATUS current
			DESCRIPTION
				"The TX bias high threshold"
			::= { sleGponOnuAniEntry 25 }


--  1.3.6.1.4.1.6296.101.23.6.6.1.1.26
		sleGponOnuAniOpticModuleTxbiasLowThr OBJECT-TYPE
			SYNTAX Integer32
			MAX-ACCESS read-only
			STATUS current
			DESCRIPTION
				"The TX bias low threshold"
			::= { sleGponOnuAniEntry 26 }


--  1.3.6.1.4.1.6296.101.23.6.6.1.1.27
		sleGponOnuAniOpticModuleTxPowerHighThr OBJECT-TYPE
			SYNTAX Integer32
			MAX-ACCESS read-only
			STATUS current
			DESCRIPTION
				"The TX power high threshold (0.1 dBm)"
			::= { sleGponOnuAniEntry 27 }


--  1.3.6.1.4.1.6296.101.23.6.6.1.1.28
		sleGponOnuAniOpticModuleTxPowerLowThr OBJECT-TYPE
			SYNTAX Integer32
			MAX-ACCESS read-only
			STATUS current
			DESCRIPTION
				"The TX power low threshold (0.1 dBm)"
			::= { sleGponOnuAniEntry 28 }


--  1.3.6.1.4.1.6296.101.23.6.6.1.1.29
		sleGponOnuAniOpticModuleRxPowerHighThr OBJECT-TYPE
			SYNTAX Integer32
			MAX-ACCESS read-only
			STATUS current
			DESCRIPTION
				"The RX power high threshold"
			::= { sleGponOnuAniEntry 29 }


--  1.3.6.1.4.1.6296.101.23.6.6.1.1.30
		sleGponOnuAniOpticModuleRxPowerLowThr OBJECT-TYPE
			SYNTAX Integer32
			MAX-ACCESS read-only
			STATUS current
			DESCRIPTION
				"The RX power low threshold"
			::= { sleGponOnuAniEntry 30 }


--   1.3.6.1.4.1.6296.101.23.6.1.2
-- 1.3.6.1.4.1.6296.101.23.6.6.2
		sleGponOnuAniControl OBJECT IDENTIFIER ::= { sleGponOnuAni 2 }


--   1.3.6.1.4.1.6296.101.23.6.1.2.1
-- 1.3.6.1.4.1.6296.101.23.6.6.2.1
		sleGponOnuAniControlRequest OBJECT-TYPE
			SYNTAX INTEGER
				{
				updateOnuAniOpticModuleInfo(1),
				updateOnuAniOpticModuleInfoTestAction(2)
				}
			MAX-ACCESS read-write
			STATUS current
			DESCRIPTION
				"The request of a user command"
			::= { sleGponOnuAniControl 1 }


--   1.3.6.1.4.1.6296.101.23.6.1.2.2
-- 1.3.6.1.4.1.6296.101.23.6.6.2.2
		sleGponOnuAniControlStatus OBJECT-TYPE
			SYNTAX SleControlStatusType
			MAX-ACCESS read-only
			STATUS current
			DESCRIPTION
				"The status of user command"
			::= { sleGponOnuAniControl 2 }


--   1.3.6.1.4.1.6296.101.23.6.1.2.3
-- 1.3.6.1.4.1.6296.101.23.6.6.2.3
		sleGponOnuAniControlTimer OBJECT-TYPE
			SYNTAX Gauge32
			MAX-ACCESS read-write
			STATUS current
			DESCRIPTION
				"The maximum time for the manager for a long running user command"
			::= { sleGponOnuAniControl 3 }


--   1.3.6.1.4.1.6296.101.23.6.1.2.4
-- 1.3.6.1.4.1.6296.101.23.6.6.2.4
		sleGponOnuAniControlTimeStamp OBJECT-TYPE
			SYNTAX TimeTicks
			MAX-ACCESS read-only
			STATUS current
			DESCRIPTION
				"The time stamp of the last command(end of command)"
			::= { sleGponOnuAniControl 4 }


--   1.3.6.1.4.1.6296.101.23.6.1.2.5
-- 1.3.6.1.4.1.6296.101.23.6.6.2.5
		sleGponOnuAniControlReqResult OBJECT-TYPE
			SYNTAX SleControlRequestResultType
			MAX-ACCESS read-only
			STATUS current
			DESCRIPTION
				"The result of the last user command"
			::= { sleGponOnuAniControl 5 }


--   1.3.6.1.4.1.6296.101.23.6.1.2.6
-- 1.3.6.1.4.1.6296.101.23.6.6.2.6
		sleGponOnuAniControlOltId OBJECT-TYPE
			SYNTAX INTEGER (1..2147483647)
			MAX-ACCESS read-write
			STATUS current
			DESCRIPTION
				"Gpon Olt Index"
			::= { sleGponOnuAniControl 6 }


--   1.3.6.1.4.1.6296.101.23.6.1.2.7
-- 1.3.6.1.4.1.6296.101.23.6.6.2.7
		sleGponOnuAniControlOnuId OBJECT-TYPE
			SYNTAX INTEGER (1..65535)
			MAX-ACCESS read-write
			STATUS current
			DESCRIPTION
				"Gpon Onu Index"
			::= { sleGponOnuAniControl 7 }


--  1.3.6.1.4.1.6296.101.23.6.6.2.8
		sleGponOnuAniControlAniId OBJECT-TYPE
			SYNTAX Integer32
			MAX-ACCESS read-write
			STATUS current
			DESCRIPTION
				"The ANI index."
			::= { sleGponOnuAniControl 8 }


--  1.3.6.1.4.1.6296.101.23.6.6.3
		sleGponOnuAniNotification OBJECT IDENTIFIER ::= { sleGponOnuAni 3 }


--  1.3.6.1.4.1.6296.101.23.6.6.3.1
		sleGponOnuAniOpticModuleInfoUpdated NOTIFICATION-TYPE
			OBJECTS { sleGponOnuAniControlRequest, sleGponOnuAniControlTimeStamp, sleGponOnuAniControlReqResult, sleGponOltId, sleGponOnuId,
				sleGponOnuAniId }
			STATUS current
			DESCRIPTION
				"updateOnuAniOpticModuleInfo"
			::= { sleGponOnuAniNotification 1 }


		sleGponOnuAniOpticModuleInfoTestActionUpdated NOTIFICATION-TYPE
			OBJECTS { sleGponOnuAniControlRequest, sleGponOnuAniControlTimeStamp, sleGponOnuAniControlReqResult, sleGponOnuAniControlOltId, sleGponOnuAniControlOnuId,
				sleGponOnuAniControlAniId }
			STATUS current
			DESCRIPTION
				"updateOnuAniOpticModuleInfoTestAction "
			::= { sleGponOnuAniNotification 2 }


--  1.3.6.1.4.1.6296.101.23.6.7
		sleGponStaticMac OBJECT IDENTIFIER ::= { sleGponBridge 7 }


--  1.3.6.1.4.1.6296.101.23.6.7.1
		sleGponStaticMacTable OBJECT-TYPE
			SYNTAX SEQUENCE OF SleGponStaticMacEntry
			MAX-ACCESS not-accessible
			STATUS current
			DESCRIPTION
				"Description."
			::= { sleGponStaticMac 1 }


--  1.3.6.1.4.1.6296.101.23.6.7.1.1
		sleGponStaticMacEntry OBJECT-TYPE
			SYNTAX SleGponStaticMacEntry
			MAX-ACCESS not-accessible
			STATUS current
			DESCRIPTION
				"Description."
			INDEX { sleGponOltId, sleGponStaticMacListId }
			::= { sleGponStaticMacTable 1 }


		SleGponStaticMacEntry ::=
			SEQUENCE {
				sleGponStaticMacListId
					Integer32,
				sleGponStaticMacStartAddr
					OCTET STRING,
				sleGponStaticMacEndAddr
					Integer32,
				sleGponStaticMacTrafficId
					INTEGER,
				sleGponStaticMacVlanId
					Integer32,
				sleGponStaticMacPortId
					Integer32,
				sleGponStaticMacCount
					Integer32
			 }

--  1.3.6.1.4.1.6296.101.23.6.7.1.1.1
		sleGponStaticMacListId OBJECT-TYPE
			SYNTAX Integer32 (1..65535)
			MAX-ACCESS read-only
			STATUS current
			DESCRIPTION
				"Gpon List Index. (only use for showing GET)"
			::= { sleGponStaticMacEntry 1 }


--  1.3.6.1.4.1.6296.101.23.6.7.1.1.2
		sleGponStaticMacStartAddr OBJECT-TYPE
			SYNTAX OCTET STRING
			MAX-ACCESS read-only
			STATUS current
			DESCRIPTION
				"The start static MAC address used by range of a multicast or broadcast stream."
			::= { sleGponStaticMacEntry 2 }


--  1.3.6.1.4.1.6296.101.23.6.7.1.1.3
		sleGponStaticMacEndAddr OBJECT-TYPE
			SYNTAX Integer32
			MAX-ACCESS read-only
			STATUS current
			DESCRIPTION
				"The end static MAC address used by range of multicast or broadcast stream"
			::= { sleGponStaticMacEntry 3 }


--  1.3.6.1.4.1.6296.101.23.6.7.1.1.4
		sleGponStaticMacTrafficId OBJECT-TYPE
			SYNTAX INTEGER
				{
				multicast(1),
				broadcast(2)
				}
			MAX-ACCESS read-only
			STATUS current
			DESCRIPTION
				"Traffic ID information
				1       Multicast
				2       Broadcast
				"
			::= { sleGponStaticMacEntry 4 }


--  1.3.6.1.4.1.6296.101.23.6.7.1.1.5
		sleGponStaticMacVlanId OBJECT-TYPE
			SYNTAX Integer32 (1..4094)
			MAX-ACCESS read-only
			STATUS current
			DESCRIPTION
				"VLAN ID information"
			::= { sleGponStaticMacEntry 5 }


--  1.3.6.1.4.1.6296.101.23.6.7.1.1.6
		sleGponStaticMacPortId OBJECT-TYPE
			SYNTAX Integer32 (1..4095)
			MAX-ACCESS read-only
			STATUS current
			DESCRIPTION
				"GEM Port ID information"
			::= { sleGponStaticMacEntry 6 }


--  1.3.6.1.4.1.6296.101.23.6.7.1.1.7
		sleGponStaticMacCount OBJECT-TYPE
			SYNTAX Integer32 (0..4096)
			MAX-ACCESS read-only
			STATUS current
			DESCRIPTION
				"The total range of static MAC address "
			::= { sleGponStaticMacEntry 7 }


--  1.3.6.1.4.1.6296.101.23.6.7.2
		sleGponStaticMacControl OBJECT IDENTIFIER ::= { sleGponStaticMac 2 }


--   1.3.6.1.4.1.6296.101.23.6.1.2.1
-- 1.3.6.1.4.1.6296.101.23.6.7.2.1
		sleGponStaticMacControlReqest OBJECT-TYPE
			SYNTAX INTEGER
				{
				setGponStaticMac(1),
				deleteGponStaticMac(2)
				}
			MAX-ACCESS read-write
			STATUS current
			DESCRIPTION
				"The request of a user command"
			::= { sleGponStaticMacControl 1 }


--   1.3.6.1.4.1.6296.101.23.6.1.2.2
-- 1.3.6.1.4.1.6296.101.23.6.7.2.2
		sleGponStaticMacControlStatus OBJECT-TYPE
			SYNTAX SleControlStatusType
			MAX-ACCESS read-only
			STATUS current
			DESCRIPTION
				"The status of user command"
			::= { sleGponStaticMacControl 2 }


--   1.3.6.1.4.1.6296.101.23.6.1.2.3
-- 1.3.6.1.4.1.6296.101.23.6.7.2.3
		sleGponStaticMacControlTimer OBJECT-TYPE
			SYNTAX Gauge32
			MAX-ACCESS read-write
			STATUS current
			DESCRIPTION
				"The maximum time for the manager for a long running user command"
			::= { sleGponStaticMacControl 3 }


--   1.3.6.1.4.1.6296.101.23.6.1.2.4
-- 1.3.6.1.4.1.6296.101.23.6.7.2.4
		sleGponStaticMacControlTimeStamp OBJECT-TYPE
			SYNTAX TimeTicks
			MAX-ACCESS read-only
			STATUS current
			DESCRIPTION
				"The time stamp of the last command(end of command)"
			::= { sleGponStaticMacControl 4 }


--   1.3.6.1.4.1.6296.101.23.6.1.2.5
-- 1.3.6.1.4.1.6296.101.23.6.7.2.5
		sleGponStaticMacControlReqResult OBJECT-TYPE
			SYNTAX SleControlRequestResultType
			MAX-ACCESS read-only
			STATUS current
			DESCRIPTION
				"The result of the last user command"
			::= { sleGponStaticMacControl 5 }


--  1.3.6.1.4.1.6296.101.23.6.7.2.6
		sleGponStaticMacControlOltId OBJECT-TYPE
			SYNTAX Integer32 (1..2147483647)
			MAX-ACCESS read-write
			STATUS current
			DESCRIPTION
				"OLT index."
			::= { sleGponStaticMacControl 6 }


--  1.3.6.1.4.1.6296.101.23.6.7.2.7
		sleGponStaticMacControlStartAddr OBJECT-TYPE
			SYNTAX OCTET STRING
			MAX-ACCESS read-write
			STATUS current
			DESCRIPTION
				"The start static MAC address used by range of a multicast or broadcast stream."
			::= { sleGponStaticMacControl 7 }


--  1.3.6.1.4.1.6296.101.23.6.7.2.8
		sleGponStaticMacControlEndAddr OBJECT-TYPE
			SYNTAX OCTET STRING
			MAX-ACCESS read-write
			STATUS current
			DESCRIPTION
				"The end static MAC address used by range of multicast or broadcast stream"
			::= { sleGponStaticMacControl 8 }


--  1.3.6.1.4.1.6296.101.23.6.7.2.9
		sleGponStaticMacControlTrafficId OBJECT-TYPE
			SYNTAX INTEGER
				{
				multicast(1),
				broadcast(2)
				}
			MAX-ACCESS read-write
			STATUS current
			DESCRIPTION
				"The traffic type method about the Static MAC address"
			::= { sleGponStaticMacControl 9 }


--  1.3.6.1.4.1.6296.101.23.6.7.2.10
		sleGponStaticMacControlVlanId OBJECT-TYPE
			SYNTAX Integer32 (0..4094)
			MAX-ACCESS read-write
			STATUS current
			DESCRIPTION
				"VLAN ID method"
			::= { sleGponStaticMacControl 10 }


--  1.3.6.1.4.1.6296.101.23.6.7.3
		sleGponStaticMacNotification OBJECT IDENTIFIER ::= { sleGponStaticMac 3 }


--  1.3.6.1.4.1.6296.101.23.6.7.3.1
		sleGponStaticMacCreated NOTIFICATION-TYPE
			OBJECTS { sleGponStaticMacControlReqest, sleGponStaticMacControlTimeStamp, sleGponStaticMacControlReqResult, sleGponStaticMacControlOltId, sleGponStaticMacControlStartAddr,
				sleGponStaticMacControlEndAddr, sleGponStaticMacControlTrafficId, sleGponStaticMacControlVlanId }
			STATUS current
			DESCRIPTION
				"setGponStaticMac"
			::= { sleGponStaticMacNotification 1 }


--  1.3.6.1.4.1.6296.101.23.6.7.3.2
		sleGponStaticMacDeleted NOTIFICATION-TYPE
			OBJECTS { sleGponStaticMacControlReqest, sleGponStaticMacControlTimeStamp, sleGponStaticMacControlReqResult, sleGponStaticMacControlOltId, sleGponStaticMacControlStartAddr,
				sleGponStaticMacControlEndAddr, sleGponStaticMacControlTrafficId, sleGponStaticMacControlVlanId }
			STATUS current
			DESCRIPTION
				"deleteGponStaticMac"
			::= { sleGponStaticMacNotification 2 }


--  1.3.6.1.4.1.6296.101.23.6.8
		sleGponOnuVideoAni OBJECT IDENTIFIER ::= { sleGponBridge 8 }


--  1.3.6.1.4.1.6296.101.23.6.8.1
		sleGponOnuVideoAniTable OBJECT-TYPE
			SYNTAX SEQUENCE OF SleGponOnuVideoAniEntry
			MAX-ACCESS not-accessible
			STATUS current
			DESCRIPTION
				"Description."
			::= { sleGponOnuVideoAni 1 }


--  1.3.6.1.4.1.6296.101.23.6.8.1.1
		sleGponOnuVideoAniEntry OBJECT-TYPE
			SYNTAX SleGponOnuVideoAniEntry
			MAX-ACCESS not-accessible
			STATUS current
			DESCRIPTION
				"Description."
			INDEX { sleGponOltId, sleGponOnuId, sleGponOnuVideoAniIndex }
			::= { sleGponOnuVideoAniTable 1 }


		SleGponOnuVideoAniEntry ::=
			SEQUENCE {
				sleGponOnuVideoAniIndex
					Integer32,
				sleGponOnuVideoAniAdminState
					INTEGER,
				sleGponOnuVideoAniOperState
					INTEGER,
				sleGponOnuVideoAniArc
					Integer32,
				sleGponOnuVideoAniArcInterval
					Integer32,
				sleGponOnuVideoAniFreqRangeLow
					INTEGER,
				sleGponOnuVideoAniFreqRangeHigh
					INTEGER,
				sleGponOnuVideoAniSignalCapability
					INTEGER,
				sleGponOnuVideoAniOpticalSignalLevel
					Integer32,
				sleGponOnuVideoAniPilotSignalLevel
					Integer32,
				sleGponOnuVideoAniSignalLevelMin
					Integer32,
				sleGponOnuVideoAniSignalLevelMax
					Integer32,
				sleGponOnuVideoAniPilotFreq
					Integer32,
				sleGponOnuVideoAniAgcMode
					INTEGER,
				sleGponOnuVideoAniAgcSetting
					Integer32,
				sleGponOnuVideoAniVideoLowerOpticalThr
					Integer32,
				sleGponOnuVideoAniVideoUpperOpticalThr
					Integer32,
				sleGponOnuVideoAniConfAgcSetting
					Integer32
			 }

--  1.3.6.1.4.1.6296.101.23.6.8.1.1.1
		sleGponOnuVideoAniIndex OBJECT-TYPE
			SYNTAX Integer32 (1..65535)
			MAX-ACCESS read-only
			STATUS current
			DESCRIPTION
				"The ANI index."
			::= { sleGponOnuVideoAniEntry 1 }


--  1.3.6.1.4.1.6296.101.23.6.8.1.1.2
		sleGponOnuVideoAniAdminState OBJECT-TYPE
			SYNTAX INTEGER
				{
				up(1),
				down(2)
				}
			MAX-ACCESS read-only
			STATUS current
			DESCRIPTION
				"This attribute up (1) and down (2) the functions performed by this
				managed entity. When the administrative state is set to lock, all user
				functions of this managed entity are blocked, and alarms, TCAs and AVCs
				for this managed entity and all dependent managed entities are no longer
				generated. Selection of a default value for this attribute is outside the scope
				of this Recommendation.
				"
			::= { sleGponOnuVideoAniEntry 2 }


--  1.3.6.1.4.1.6296.101.23.6.8.1.1.3
		sleGponOnuVideoAniOperState OBJECT-TYPE
			SYNTAX INTEGER
				{
				up(1),
				down(2)
				}
			MAX-ACCESS read-only
			STATUS current
			DESCRIPTION
				"This attribute indicates whether or not the managed entity is capable of
				performing its function. Valid values are up (1) and down (2).
				"
			::= { sleGponOnuVideoAniEntry 3 }


--  1.3.6.1.4.1.6296.101.23.6.8.1.1.4
		sleGponOnuVideoAniArc OBJECT-TYPE
			SYNTAX Integer32 (1..255)
			MAX-ACCESS read-only
			STATUS current
			DESCRIPTION
				"This attribute allows the activation of alarm reporting control (ARC) for this PPTP. The attribute
				works in concert with the ARC_interval attribute"
			::= { sleGponOnuVideoAniEntry 4 }


--  1.3.6.1.4.1.6296.101.23.6.8.1.1.5
		sleGponOnuVideoAniArcInterval OBJECT-TYPE
			SYNTAX Integer32 (1..255)
			MAX-ACCESS read-only
			STATUS current
			DESCRIPTION
				"This attribute defines the interval to be used with the ARC function for this PPTP. The values 0
				through 254 give the duration in minutes for the NALM-QI timer. The special value 255 means that
				the timer never expires. The default value is zero.
				Note that ARC suppresses the reporting of the alarms, and not the alarm conditions themselves.
				Therefore, if an alarm condition develops during an ARC interval, then the ONT should maintain
				the internal indication of the alarm, and if the OLT gets all the alarms, it should be reported. "
			::= { sleGponOnuVideoAniEntry 5 }


--  1.3.6.1.4.1.6296.101.23.6.8.1.1.6
		sleGponOnuVideoAniFreqRangeLow OBJECT-TYPE
			SYNTAX INTEGER
				{
				noLowBand(0),
				band50To550Mhz(1),
				band50To750Mhz(2),
				band50To870Mhz(3)
				}
			MAX-ACCESS read-only
			STATUS current
			DESCRIPTION
				"This attribute indicates the lower of the two possible frequency ranges
				supported. Different frequency ranges are indicated by code points:
				0 No low band.
				1 50..550 MHz.
				2 50..750 MHz.
				3 50..870 MHz.

				"
			::= { sleGponOnuVideoAniEntry 6 }


--  1.3.6.1.4.1.6296.101.23.6.8.1.1.7
		sleGponOnuVideoAniFreqRangeHigh OBJECT-TYPE
			SYNTAX INTEGER
				{
				noHighBand(0),
				band550To750(1),
				band550To870(2),
				band950To2050(3),
				band2150To3250(4),
				band950To3250(5)
				}
			MAX-ACCESS read-only
			STATUS current
			DESCRIPTION
				"This attribute indicates the higher of the two frequency ranges supported.
				Different frequency ranges are indicated by code points:
				0 No high band.
				1 550..750 MHz.
				2 550..870 MHz.
				3 950..2050 MHz.
				4 2150..3250 MHz.
				5 950..3250 MHz.
				"
			::= { sleGponOnuVideoAniEntry 7 }


--  1.3.6.1.4.1.6296.101.23.6.8.1.1.8
		sleGponOnuVideoAniSignalCapability OBJECT-TYPE
			SYNTAX INTEGER
				{
				noSignal(0),
				totalOptical(1),
				fixedFrequencyPilotTone(2),
				totalOpticalAndFixedFrequencyPilotTone(3),
				variableFrequencyPilotTone(4),
				totalOpticalAndVariableFrequencyPilotTone(5),
				broadbandRF(6),
				totalOpticalAndBroadbandRF(7)
				}
			MAX-ACCESS read-only
			STATUS current
			DESCRIPTION
				"This attribute indicates the capability of the ONT to measure the video
				signal level. Capabilities are indicated by code points:
				0 No signal level capability.
				1 Total optical power level.
				2 Fixed frequency pilot tone power level.
				3 Total optical power level and fixed frequency pilot tone power level.
				4 Variable frequency pilot tone power level.
				5 Total optical power level and variable frequency pilot tone power level.
				6 Broadband RF power level.
				7 Total optical power level and broadband RF power level.
				8..255 Reserved.
				"
			::= { sleGponOnuVideoAniEntry 8 }


--  1.3.6.1.4.1.6296.101.23.6.8.1.1.9
		sleGponOnuVideoAniOpticalSignalLevel OBJECT-TYPE
			SYNTAX Integer32 (1..255)
			MAX-ACCESS read-only
			STATUS current
			DESCRIPTION
				"This attribute is an unsigned integer that returns the current measurement
				of the total optical signal level. The unit of this attribute is dBm optical.
				If signal capability = 0, 2, 4 or 6, this attribute is undefined.
				If signal capability =1, 3, 5 or 7, this attribute describes the total
				optical power that is generating photocurrent on the receiver.
				"
			::= { sleGponOnuVideoAniEntry 9 }


--  1.3.6.1.4.1.6296.101.23.6.8.1.1.10
		sleGponOnuVideoAniPilotSignalLevel OBJECT-TYPE
			SYNTAX Integer32 (1..255)
			MAX-ACCESS read-only
			STATUS current
			DESCRIPTION
				"This attribute indicates the current measurement of the pilot signal level or
				broadband RF level. The unit of this attribute is dB⊥iV at the RF video
				service port.
				If signal capability = 0 or 1, then this attribute is undefined.
				If signal capability = 2, 3, 4 or 5, this attribute reports the pilot signal level
				at the out put of the video UNI.
				If signal capability = 6 or 7, this attribute reports the total RF power level at the out
				put of the video UNI.
				"
			::= { sleGponOnuVideoAniEntry 10 }


--  1.3.6.1.4.1.6296.101.23.6.8.1.1.11
		sleGponOnuVideoAniSignalLevelMin OBJECT-TYPE
			SYNTAX Integer32 (1..255)
			MAX-ACCESS read-only
			STATUS current
			DESCRIPTION
				"This attribute indicates the minimum optical RF power per channel that
				results in a CNR of 47 dBc for a channel of 4.5 MHz bandwidth at a
				receive optical power of -5 dBm. The unit of this attribute is dB⊥iW
				optical."
			::= { sleGponOnuVideoAniEntry 11 }


--  1.3.6.1.4.1.6296.101.23.6.8.1.1.12
		sleGponOnuVideoAniSignalLevelMax OBJECT-TYPE
			SYNTAX Integer32 (1..255)
			MAX-ACCESS read-only
			STATUS current
			DESCRIPTION
				"This attribute indicates the maximum optical RF power per channel that
				results in a CTB of -57 dBc for an 80-channel ensemble of carriers at a
				per-channel optical modulation index of 3.5%. The unit of this attribute is
				dB⊥iW optical. "
			::= { sleGponOnuVideoAniEntry 12 }


--  1.3.6.1.4.1.6296.101.23.6.8.1.1.13
		sleGponOnuVideoAniPilotFreq OBJECT-TYPE
			SYNTAX Integer32 (1..255)
			MAX-ACCESS read-only
			STATUS current
			DESCRIPTION
				"This attribute specifies the frequency of the pilot channel receiver. The unit of this attribute is Hz.
				If signal capability = 0, 1, 6 or 7, this attribute is undefined.
				If signal capability = 2 or 3, this tionally read only.
				If signal capability = 4 or 5, this attribute is read-write.
				"
			::= { sleGponOnuVideoAniEntry 13 }


--  1.3.6.1.4.1.6296.101.23.6.8.1.1.14
		sleGponOnuVideoAniAgcMode OBJECT-TYPE
			SYNTAX INTEGER
				{
				noAgc(0),
				broadbandRfAgc(1),
				opticalAgc(2)
				}
			MAX-ACCESS read-only
			STATUS current
			DESCRIPTION
				"This attribute allows the discovery and configuration of the ONT's AGC
				capabilities. The attribute contains a codepoint for several AGC types. The
				ONT displays the currently used AGC mode. The OLT can discover new
				modes via the set command; the ONT denies attempts to set an
				unsupported mode. The code points are:
				0  No AGC.
				1  Broadband RF AGC.
				2  Optical AGC.
				"
			::= { sleGponOnuVideoAniEntry 14 }


--  1.3.6.1.4.1.6296.101.23.6.8.1.1.15
		sleGponOnuVideoAniAgcSetting OBJECT-TYPE
			SYNTAX Integer32 (-128..127)
			MAX-ACCESS read-only
			STATUS current
			DESCRIPTION
				"This attribute indicates the measurement offset that the ONT should use in
				AGC. The attribute has a step size of 0.1 dB, represented as a signed integer.

				The theoretical nominal RF signal is 80 channels of NTSC video, each
				having a per-channel optical modulation index of 3.5%. An ONT
				presented with such a signal should produce its specified ou
				tput when this attribute is set to zero.

				If total optical power is used for AGC, this attribute provides the OMI
				offset for any NTSC carriers present from the theoretical 3.5% value. For
				example, if the actual signal uses an OMI of 7.0% per channel (3 dB
				higher), then the ONT should be given an AGC setting of 30
				(coded 0x1E).

				If broadband RF power is used for AGC, this attribute provides the total
				power offset for any NTSC carriers present from the theoretical 80 channel
				value. For example, if an actual signal contains 40 NTSC channels (3 dB
				lower), then the ONT should be given an AGC setting of <0096>30 (coded
				0xE2).
				"
			::= { sleGponOnuVideoAniEntry 15 }


--  1.3.6.1.4.1.6296.101.23.6.8.1.1.16
		sleGponOnuVideoAniVideoLowerOpticalThr OBJECT-TYPE
			SYNTAX Integer32 (1..255)
			MAX-ACCESS read-only
			STATUS current
			DESCRIPTION
				"This attribute specifies the optical level used to declare the video OOR low
				alarm. Valid values are <0096>12 to +6 dBm in 0.1 dB increments, represented
				as a 2s complement integer (coding -120 to +60, where 0x00 = 0 dBm,
				0x88 = -12.0 dBm, etc.). Upon ME instantiation, the ONT sets this
				attribute to 0xA1 (-9.5 dBm). (R, W) (optional) (1 byte)

				NOTE <0096> Because the power measurement returned in the optical signal level
				attribute has a resolution of 1 dB, it is possible that the measured value could
				appear to be in-range, even though an out-of-range alarm has been declared
				against a threshold with 0.1 dB resolution.
				"
			::= { sleGponOnuVideoAniEntry 16 }


--  1.3.6.1.4.1.6296.101.23.6.8.1.1.17
		sleGponOnuVideoAniVideoUpperOpticalThr OBJECT-TYPE
			SYNTAX Integer32 (1..255)
			MAX-ACCESS read-only
			STATUS current
			DESCRIPTION
				"This attribute specifies the optical level used to declare the video OOR
				high alarm. Valid values are -12 to +6 dBm in 0.1 dB increments,
				represented as a 2s complement integer (coding -120 to +60,
				0x00 = 0dBm, 0x88 = -12.0 dBm, etc.).
				Upon ME instantiation, the ONT sets this attribute to 0x19 (+2.5 dB
				m)."
			::= { sleGponOnuVideoAniEntry 17 }


--  1.3.6.1.4.1.6296.101.23.6.8.1.1.18
		sleGponOnuVideoAniConfAgcSetting OBJECT-TYPE
			SYNTAX Integer32 (-128..127)
			MAX-ACCESS read-only
			STATUS current
			DESCRIPTION
				"This attribute indicates the measurement offset that the ONT should use in
				AGC. The attribute has a step size of 0.1 dB, represented as a signed integer.

				The theoretical nominal RF signal is 80 channels of NTSC video, each
				having a per-channel optical modulation index of 3.5%. An ONT
				presented with such a signal should produce its specified ou
				tput when this attribute is set to zero.

				If total optical power is used for AGC, this attribute provides the OMI
				offset for any NTSC carriers present from the theoretical 3.5% value. For
				example, if the actual signal uses an OMI of 7.0% per channel (3 dB
				higher), then the ONT should be given an AGC setting of 30
				(coded 0x1E).

				If broadband RF power is used for AGC, this attribute provides the total
				power offset for any NTSC carriers present from the theoretical 80 channel
				value. For example, if an actual signal contains 40 NTSC channels (3 dB
				lower), then the ONT should be given an AGC setting of <0096>30 (coded
				0xE2).

				"
			::= { sleGponOnuVideoAniEntry 18 }


--  1.3.6.1.4.1.6296.101.23.6.8.2
		sleGponOnuVideoAniControl OBJECT IDENTIFIER ::= { sleGponOnuVideoAni 2 }


--   1.3.6.1.4.1.6296.101.23.6.1.2.1
-- 1.3.6.1.4.1.6296.101.23.6.8.2.1
		sleGponOnuVideoAniControlRequest OBJECT-TYPE
			SYNTAX INTEGER
				{
				updateVideoAniStatus(1),
				setVideoAniAgc(2)
				}
			MAX-ACCESS read-write
			STATUS current
			DESCRIPTION
				"The request of a user command"
			::= { sleGponOnuVideoAniControl 1 }


--   1.3.6.1.4.1.6296.101.23.6.1.2.2
-- 1.3.6.1.4.1.6296.101.23.6.8.2.2
		sleGponOnuVideoAniControlStatus OBJECT-TYPE
			SYNTAX SleControlStatusType
			MAX-ACCESS read-only
			STATUS current
			DESCRIPTION
				"The status of user command"
			::= { sleGponOnuVideoAniControl 2 }


--   1.3.6.1.4.1.6296.101.23.6.1.2.3
-- 1.3.6.1.4.1.6296.101.23.6.8.2.3
		sleGponOnuVideoAniControlTimer OBJECT-TYPE
			SYNTAX Gauge32
			MAX-ACCESS read-write
			STATUS current
			DESCRIPTION
				"The maximum time for the manager for a long running user command"
			::= { sleGponOnuVideoAniControl 3 }


--   1.3.6.1.4.1.6296.101.23.6.1.2.4
-- 1.3.6.1.4.1.6296.101.23.6.8.2.4
		sleGponOnuVideoAniControlTimeStamp OBJECT-TYPE
			SYNTAX TimeTicks
			MAX-ACCESS read-only
			STATUS current
			DESCRIPTION
				"The time stamp of the last command(end of command)"
			::= { sleGponOnuVideoAniControl 4 }


--   1.3.6.1.4.1.6296.101.23.6.1.2.5
-- 1.3.6.1.4.1.6296.101.23.6.8.2.5
		sleGponOnuVideoAniControlReqResult OBJECT-TYPE
			SYNTAX SleControlRequestResultType
			MAX-ACCESS read-only
			STATUS current
			DESCRIPTION
				"The result of the last user command"
			::= { sleGponOnuVideoAniControl 5 }


--  1.3.6.1.4.1.6296.101.23.6.8.2.6
		sleGponOnuVideoAniControlOltIndex OBJECT-TYPE
			SYNTAX Integer32 (1..2147483647)
			MAX-ACCESS read-write
			STATUS current
			DESCRIPTION
				"The OLT index."
			::= { sleGponOnuVideoAniControl 6 }


--  1.3.6.1.4.1.6296.101.23.6.8.2.7
		sleGponOnuVideoAniControlOnuIndex OBJECT-TYPE
			SYNTAX Integer32 (1..256)
			MAX-ACCESS read-write
			STATUS current
			DESCRIPTION
				"The ONU index."
			::= { sleGponOnuVideoAniControl 7 }


--  1.3.6.1.4.1.6296.101.23.6.8.2.8
		sleGponOnuVideoAniControlAniIndex OBJECT-TYPE
			SYNTAX Integer32 (1..65535)
			MAX-ACCESS read-write
			STATUS current
			DESCRIPTION
				"The ANI index."
			::= { sleGponOnuVideoAniControl 8 }


--  1.3.6.1.4.1.6296.101.23.6.8.2.9
		sleGponOnuVideoAniControlConfAgcSetting OBJECT-TYPE
			SYNTAX Integer32 (-128..127)
			MAX-ACCESS read-write
			STATUS current
			DESCRIPTION
				"This attribute indicates the measurement offset that the ONT should use in
				AGC. The attribute has a step size of 0.1 dB, represented as a signed integer.

				The theoretical nominal RF signal is 80 channels of NTSC video, each
				having a per-channel optical modulation index of 3.5%. An ONT
				presented with such a signal should produce its specified ou
				tput when this attribute is set to zero.

				If total optical power is used for AGC, this attribute provides the OMI
				offset for any NTSC carriers present from the theoretical 3.5% value. For
				example, if the actual signal uses an OMI of 7.0% per channel (3 dB
				higher), then the ONT should be given an AGC setting of 30
				(coded 0x1E).

				If broadband RF power is used for AGC, this attribute provides the total
				power offset for any NTSC carriers present from the theoretical 80 channel
				value. For example, if an actual signal contains 40 NTSC channels (3 dB
				lower), then the ONT should be given an AGC setting of <0096>30 (coded
				0xE2).

				"
			::= { sleGponOnuVideoAniControl 9 }


--  1.3.6.1.4.1.6296.101.23.6.8.3
		sleGponOnuVideoAniNotification OBJECT IDENTIFIER ::= { sleGponOnuVideoAni 3 }


--  1.3.6.1.4.1.6296.101.23.6.8.3.1
		sleGponOnuVideoAniupdateVideoAniStatusUpdated NOTIFICATION-TYPE
			OBJECTS { sleGponOnuVideoAniControlRequest, sleGponOnuVideoAniControlTimeStamp, sleGponOnuVideoAniControlReqResult, sleGponOnuVideoAniControlOltIndex, sleGponOnuVideoAniControlOnuIndex
				 }
			STATUS current
			DESCRIPTION
				"updateVideoAniStatus"
			::= { sleGponOnuVideoAniNotification 1 }


--  1.3.6.1.4.1.6296.101.23.6.8.3.2
		sleGponOnuVideoAniControlVideoAniArcChanged NOTIFICATION-TYPE
			OBJECTS { sleGponOnuVideoAniControlRequest, sleGponOnuVideoAniControlTimeStamp, sleGponOnuVideoAniControlReqResult, sleGponOnuVideoAniControlOltIndex, sleGponOnuVideoAniControlOnuIndex,
				sleGponOnuVideoAniControlAniIndex, sleGponOnuVideoAniControlConfAgcSetting }
			STATUS current
			DESCRIPTION
				"setVideoAniAgc"
			::= { sleGponOnuVideoAniNotification 2 }


		sleGponOnuPortMgmt OBJECT IDENTIFIER ::= { sleGponBridge 9 }


		sleGponOnuPppoe OBJECT IDENTIFIER ::= { sleGponBridge 10 }


		sleGponOnuPppoeTable OBJECT-TYPE
			SYNTAX SEQUENCE OF SleGponOnuPppoeEntry
			MAX-ACCESS not-accessible
			STATUS current
			DESCRIPTION
				"Description."
			::= { sleGponOnuPppoe 1 }


		sleGponOnuPppoeEntry OBJECT-TYPE
			SYNTAX SleGponOnuPppoeEntry
			MAX-ACCESS not-accessible
			STATUS current
			DESCRIPTION
				"Description."
			INDEX { sleGponOltId, sleGponOnuId, sleGponOnuPppoeIndex }
			::= { sleGponOnuPppoeTable 1 }


		SleGponOnuPppoeEntry ::=
			SEQUENCE {
				sleGponOnuPppoeIndex
					Integer32,
				sleGponOnuPppoeAdminState
					INTEGER,
				sleGponOnuPppoeStatus
					INTEGER,
				sleGponOnuPppoeAuthType
					INTEGER,
				sleGponOnuPppoeUsername
					OCTET STRING,
				sleGponOnuPppoePassword
					OCTET STRING,
				sleGponOnuPppoeMtu
					Integer32,
				sleGponOnuPppoeLCPInterval
					Integer32
			 }

		sleGponOnuPppoeIndex OBJECT-TYPE
			SYNTAX Integer32 (0..65535)
			MAX-ACCESS read-only
			STATUS current
			DESCRIPTION
				"The PPPoE Index."
			::= { sleGponOnuPppoeEntry 1 }


		sleGponOnuPppoeAdminState OBJECT-TYPE
			SYNTAX INTEGER
				{
				enable(1),
				disable(2)
				}
			MAX-ACCESS read-only
			STATUS current
			DESCRIPTION
				"This attribute specifies the type of Administrative State.
				Valid values are enable (1) and disable (2)."
			::= { sleGponOnuPppoeEntry 2 }


		sleGponOnuPppoeStatus OBJECT-TYPE
			SYNTAX INTEGER
				{
				nonConfigure(1),
				connectProgress(2),
				nonAuthenticated(3),
				authenticated(4)
				}
			MAX-ACCESS read-only
			STATUS current
			DESCRIPTION
				"This attribute specifies the type of PPPoE connection status.
				1 Non Configured : PPPoE mode is enable. but username, password, authentication type is not configured yet.
				2 Connect Progress : When try to connect PPPoE.
				3 Non Authenticated : PPPoE mode is enable, but PPPoE login is failed. (wrong username or password)
				4 Authenticated : When PPPoE client succeed to Login."
			::= { sleGponOnuPppoeEntry 3 }


		sleGponOnuPppoeAuthType OBJECT-TYPE
			SYNTAX INTEGER
				{
				chap(1),
				pap(2)
				}
			MAX-ACCESS read-only
			STATUS current
			DESCRIPTION
				"This attribute specifies the type of PPPoE Authentication."
			::= { sleGponOnuPppoeEntry 4 }


		sleGponOnuPppoeUsername OBJECT-TYPE
			SYNTAX OCTET STRING
			MAX-ACCESS read-only
			STATUS current
			DESCRIPTION
				"This attribute points a large string that contains the username of PPPoE authentication."
			::= { sleGponOnuPppoeEntry 5 }


		sleGponOnuPppoePassword OBJECT-TYPE
			SYNTAX OCTET STRING
			MAX-ACCESS read-only
			STATUS current
			DESCRIPTION
				"This attribute points a large string that contains the password of PPPoE authentication."
			::= { sleGponOnuPppoeEntry 6 }


		sleGponOnuPppoeMtu OBJECT-TYPE
			SYNTAX Integer32 (128..1500)
			MAX-ACCESS read-only
			STATUS current
			DESCRIPTION
				"This attribute specifies the value of MTU. Default value is 1492."
			::= { sleGponOnuPppoeEntry 7 }


		sleGponOnuPppoeLCPInterval OBJECT-TYPE
			SYNTAX Integer32 (10..3600)
			MAX-ACCESS read-only
			STATUS current
			DESCRIPTION
				"This attribute specifies the value of LCP Intervals between PPPoE server and client. Default value is 20."
			::= { sleGponOnuPppoeEntry 8 }


		sleGponOnuPppoeControl OBJECT IDENTIFIER ::= { sleGponOnuPppoe 2 }


		sleGponOnuPppoeControlRequest OBJECT-TYPE
			SYNTAX INTEGER { updatePppoeStatus(1) }
			MAX-ACCESS read-write
			STATUS current
			DESCRIPTION
				"The request of a user command
				"
			::= { sleGponOnuPppoeControl 1 }


		sleGponOnuPppoeControlStatus OBJECT-TYPE
			SYNTAX SleControlStatusType
			MAX-ACCESS read-only
			STATUS current
			DESCRIPTION
				"The status of user command"
			::= { sleGponOnuPppoeControl 2 }


		sleGponOnuPppoeControlTimer OBJECT-TYPE
			SYNTAX Gauge32
			MAX-ACCESS read-write
			STATUS current
			DESCRIPTION
				"The maximum time for the manager for a long running user command"
			::= { sleGponOnuPppoeControl 3 }


		sleGponOnuPppoeiControlTimeStamp OBJECT-TYPE
			SYNTAX TimeTicks
			MAX-ACCESS read-only
			STATUS current
			DESCRIPTION
				"The time stamp of the last command(end of command)"
			::= { sleGponOnuPppoeControl 4 }


		sleGponOnuPppoeControlReqResult OBJECT-TYPE
			SYNTAX SleControlRequestResultType
			MAX-ACCESS read-only
			STATUS current
			DESCRIPTION
				"The result of the last user command"
			::= { sleGponOnuPppoeControl 5 }


		sleGponOnuPppoeControlOltIndex OBJECT-TYPE
			SYNTAX Integer32 (1..2147483647)
			MAX-ACCESS read-write
			STATUS current
			DESCRIPTION
				"The OLT index."
			::= { sleGponOnuPppoeControl 6 }


		sleGponOnuPppoeControlOnuIndex OBJECT-TYPE
			SYNTAX Integer32 (1..256)
			MAX-ACCESS read-write
			STATUS current
			DESCRIPTION
				"The ONU index.."
			::= { sleGponOnuPppoeControl 7 }


		sleGponOnuPppoeControlIndex OBJECT-TYPE
			SYNTAX Integer32
			MAX-ACCESS read-write
			STATUS current
			DESCRIPTION
				"The PPPoE index."
			::= { sleGponOnuPppoeControl 8 }


		sleGponOnuPppoeNotification OBJECT IDENTIFIER ::= { sleGponOnuPppoe 3 }


		sleGponOnuPppoeStatusUpdated NOTIFICATION-TYPE
			OBJECTS { sleGponOnuPppoeControlRequest, sleGponOnuPppoeiControlTimeStamp, sleGponOnuPppoeControlReqResult, sleGponOnuPppoeControlOltIndex, sleGponOnuPppoeControlOnuIndex
				 }
			STATUS current
			DESCRIPTION
				"Description."
			::= { sleGponOnuPppoeNotification 1 }


--   1.3.6.1.4.1.6296.101.23.7
-- 1.3.6.1.4.1.6296.101.23.7
		sleGponStatistics OBJECT IDENTIFIER ::= { sleGpon 7 }


--   1.3.6.1.4.1.6296.101.23.7.1
-- 1.3.6.1.4.1.6296.101.23.7.1
		sleGponOltStatistics OBJECT IDENTIFIER ::= { sleGponStatistics 1 }


--   1.3.6.1.4.1.6296.101.23.7.1.1
-- 1.3.6.1.4.1.6296.101.23.7.1.1
		sleGponOltStatsTable OBJECT-TYPE
			SYNTAX SEQUENCE OF SleGponOltStatsEntry
			MAX-ACCESS not-accessible
			STATUS current
			DESCRIPTION
				"sleGponOltStatsTable"
			::= { sleGponOltStatistics 1 }


--   1.3.6.1.4.1.6296.101.23.7.1.1.1
-- 1.3.6.1.4.1.6296.101.23.7.1.1.1
		sleGponOltStatsEntry OBJECT-TYPE
			SYNTAX SleGponOltStatsEntry
			MAX-ACCESS not-accessible
			STATUS current
			DESCRIPTION
				"key: sleGponOltId"
			INDEX { sleGponOltId }
			::= { sleGponOltStatsTable 1 }


		SleGponOltStatsEntry ::=
			SEQUENCE {
				sleGponOltStatsPonValidEthPacketsRx
					Counter64,
				sleGponOltStatsPonCpuPacketsRx
					Counter64,
				sleGponOltStatsPonPloamsRx
					Counter64,
				sleGponOltStatsPonInvalidPacketsRx
					Counter64,
				sleGponOltStatsPonValidEthPacketsTx
					Counter64,
				sleGponOltStatsPonCpuPacketsTx
					Counter64,
				sleGponOltStatsPonPloamsTx
					Counter64,
				sleGponOltStatsPonInvalidPacketsTx
					Counter64,
				sleGponOltStatsPerfRxValidPackets
					Counter64,
				sleGponOltStatsPerfRxErroredPackets
					Counter64,
				sleGponOltStatsPerfCRCdroppedPackets
					Counter64
			 }

--   1.3.6.1.4.1.6296.101.23.7.1.1.1.1
-- 1.3.6.1.4.1.6296.101.23.7.1.1.1.1
		sleGponOltStatsPonValidEthPacketsRx OBJECT-TYPE
			SYNTAX Counter64
			MAX-ACCESS read-only
			STATUS current
			DESCRIPTION
				"UpStream(Rx), N/A"
			::= { sleGponOltStatsEntry 1 }


--   1.3.6.1.4.1.6296.101.23.7.1.1.1.2
-- 1.3.6.1.4.1.6296.101.23.7.1.1.1.2
		sleGponOltStatsPonCpuPacketsRx OBJECT-TYPE
			SYNTAX Counter64
			MAX-ACCESS read-only
			STATUS current
			DESCRIPTION
				"UpStream(Rx), N/A"
			::= { sleGponOltStatsEntry 2 }


--   1.3.6.1.4.1.6296.101.23.7.1.1.1.3
-- 1.3.6.1.4.1.6296.101.23.7.1.1.1.3
		sleGponOltStatsPonPloamsRx OBJECT-TYPE
			SYNTAX Counter64
			MAX-ACCESS read-only
			STATUS current
			DESCRIPTION
				"UpStream(Rx)"
			::= { sleGponOltStatsEntry 3 }


--   1.3.6.1.4.1.6296.101.23.7.1.1.1.4
-- 1.3.6.1.4.1.6296.101.23.7.1.1.1.4
		sleGponOltStatsPonInvalidPacketsRx OBJECT-TYPE
			SYNTAX Counter64
			MAX-ACCESS read-only
			STATUS current
			DESCRIPTION
				"UpStream(Rx)"
			::= { sleGponOltStatsEntry 4 }


--   1.3.6.1.4.1.6296.101.23.7.1.1.1.5
-- 1.3.6.1.4.1.6296.101.23.7.1.1.1.5
		sleGponOltStatsPonValidEthPacketsTx OBJECT-TYPE
			SYNTAX Counter64
			MAX-ACCESS read-only
			STATUS current
			DESCRIPTION
				"DownStream(Tx)"
			::= { sleGponOltStatsEntry 5 }


--   1.3.6.1.4.1.6296.101.23.7.1.1.1.6
-- 1.3.6.1.4.1.6296.101.23.7.1.1.1.6
		sleGponOltStatsPonCpuPacketsTx OBJECT-TYPE
			SYNTAX Counter64
			MAX-ACCESS read-only
			STATUS current
			DESCRIPTION
				"DownStream(Tx)"
			::= { sleGponOltStatsEntry 6 }


--   1.3.6.1.4.1.6296.101.23.7.1.1.1.7
-- 1.3.6.1.4.1.6296.101.23.7.1.1.1.7
		sleGponOltStatsPonPloamsTx OBJECT-TYPE
			SYNTAX Counter64
			MAX-ACCESS read-only
			STATUS current
			DESCRIPTION
				"DownStream(Tx)"
			::= { sleGponOltStatsEntry 7 }


--   1.3.6.1.4.1.6296.101.23.7.1.1.1.8
-- 1.3.6.1.4.1.6296.101.23.7.1.1.1.8
		sleGponOltStatsPonInvalidPacketsTx OBJECT-TYPE
			SYNTAX Counter64
			MAX-ACCESS read-only
			STATUS current
			DESCRIPTION
				"N/A"
			::= { sleGponOltStatsEntry 8 }


--   1.3.6.1.4.1.6296.101.23.7.1.1.1.9
-- 1.3.6.1.4.1.6296.101.23.7.1.1.1.9
		sleGponOltStatsPerfRxValidPackets OBJECT-TYPE
			SYNTAX Counter64
			MAX-ACCESS read-only
			STATUS current
			DESCRIPTION
				"UpStream(Rx)"
			::= { sleGponOltStatsEntry 9 }


--   1.3.6.1.4.1.6296.101.23.7.1.1.1.10
-- 1.3.6.1.4.1.6296.101.23.7.1.1.1.10
		sleGponOltStatsPerfRxErroredPackets OBJECT-TYPE
			SYNTAX Counter64
			MAX-ACCESS read-only
			STATUS current
			DESCRIPTION
				"UpStream(Rx)"
			::= { sleGponOltStatsEntry 10 }


--   1.3.6.1.4.1.6296.101.23.7.1.1.1.11
-- 1.3.6.1.4.1.6296.101.23.7.1.1.1.11
		sleGponOltStatsPerfCRCdroppedPackets OBJECT-TYPE
			SYNTAX Counter64
			MAX-ACCESS read-only
			STATUS current
			DESCRIPTION
				"UpStream(Rx)"
			::= { sleGponOltStatsEntry 11 }


--   1.3.6.1.4.1.6296.101.23.7.1.2
-- 1.3.6.1.4.1.6296.101.23.7.1.2
		sleGponOltStatsAllocTable OBJECT-TYPE
			SYNTAX SEQUENCE OF SleGponOltStatsAllocEntry
			MAX-ACCESS not-accessible
			STATUS current
			DESCRIPTION
				"sleGponOltStatsAllocTable"
			::= { sleGponOltStatistics 2 }


--   1.3.6.1.4.1.6296.101.23.7.1.2.1
-- 1.3.6.1.4.1.6296.101.23.7.1.2.1
		sleGponOltStatsAllocEntry OBJECT-TYPE
			SYNTAX SleGponOltStatsAllocEntry
			MAX-ACCESS not-accessible
			STATUS current
			DESCRIPTION
				"key: sleGponOltId, sleGponOltStatsAllocId"
			INDEX { sleGponOltId, sleGponOltStatsAllocId }
			::= { sleGponOltStatsAllocTable 1 }


		SleGponOltStatsAllocEntry ::=
			SEQUENCE {
				sleGponOltStatsAllocId
					INTEGER,
				sleGponOltStatsAllocDataRx
					Counter64
			 }

--   1.3.6.1.4.1.6296.101.23.7.1.2.1.1
-- 1.3.6.1.4.1.6296.101.23.7.1.2.1.1
		sleGponOltStatsAllocId OBJECT-TYPE
			SYNTAX INTEGER (256..1023)
			MAX-ACCESS read-only
			STATUS current
			DESCRIPTION
				"Alloc-Id"
			::= { sleGponOltStatsAllocEntry 1 }


--   1.3.6.1.4.1.6296.101.23.7.1.2.1.2
-- 1.3.6.1.4.1.6296.101.23.7.1.2.1.2
		sleGponOltStatsAllocDataRx OBJECT-TYPE
			SYNTAX Counter64
			MAX-ACCESS read-only
			STATUS current
			DESCRIPTION
				"The total value of received data in bytes per Alloc-Id."
			::= { sleGponOltStatsAllocEntry 2 }


--   1.3.6.1.4.1.6296.101.23.7.1.3
-- 1.3.6.1.4.1.6296.101.23.7.1.3
		sleGponOltStatsOnuTable OBJECT-TYPE
			SYNTAX SEQUENCE OF SleGponOltStatsOnuEntry
			MAX-ACCESS not-accessible
			STATUS current
			DESCRIPTION
				"sleGponOltStatsOnuTable"
			::= { sleGponOltStatistics 3 }


--   1.3.6.1.4.1.6296.101.23.7.1.3.1
-- 1.3.6.1.4.1.6296.101.23.7.1.3.1
		sleGponOltStatsOnuEntry OBJECT-TYPE
			SYNTAX SleGponOltStatsOnuEntry
			MAX-ACCESS not-accessible
			STATUS current
			DESCRIPTION
				"key: sleGponOltId, sleGponOnuId"
			INDEX { sleGponOltId, sleGponOnuId }
			::= { sleGponOltStatsOnuTable 1 }


		SleGponOltStatsOnuEntry ::=
			SEQUENCE {
				sleGponOltStatsOnuPonUnreceivedBursts
					Counter64,
				sleGponOltStatsOnuPonPositiveDrift
					Counter64,
				sleGponOltStatsOnuNegativeDrift
					Counter64,
				sleGponOltStatsOnuPonBip8Errors
					Counter64,
				sleGponOltStatsOnuPonFecCorrectedBytes
					Counter64,
				sleGponOltStatsOnuPonFecUncorrectedCodewords
					Counter64,
				sleGponOltStatsOnuPonFecCorrectedCodewords
					Counter64,
				sleGponOltStatsOnuPonFecReceivedCodewords
					Counter64,
				sleGponOltStatsOnuAlarmSf
					Counter32,
				sleGponOltStatsOnuAlarmSd
					Counter32,
				sleGponOltStatsOnuElapsedTimeAfterClear
					TimeTicks,
				sleGponOltStatsOnuBipReiErrors
					Counter64
			 }

--   1.3.6.1.4.1.6296.101.23.7.1.3.1.1
-- 1.3.6.1.4.1.6296.101.23.7.1.3.1.1
		sleGponOltStatsOnuPonUnreceivedBursts OBJECT-TYPE
			SYNTAX Counter64
			MAX-ACCESS read-only
			STATUS current
			DESCRIPTION
				"Returns the number of unreceived bursts per ONU-Id."
			::= { sleGponOltStatsOnuEntry 1 }


--   1.3.6.1.4.1.6296.101.23.7.1.3.1.2
-- 1.3.6.1.4.1.6296.101.23.7.1.3.1.2
		sleGponOltStatsOnuPonPositiveDrift OBJECT-TYPE
			SYNTAX Counter64
			MAX-ACCESS read-only
			STATUS current
			DESCRIPTION
				"Returns accumulated positive drifts value in bits."
			::= { sleGponOltStatsOnuEntry 2 }


--   1.3.6.1.4.1.6296.101.23.7.1.3.1.3
-- 1.3.6.1.4.1.6296.101.23.7.1.3.1.3
		sleGponOltStatsOnuNegativeDrift OBJECT-TYPE
			SYNTAX Counter64
			MAX-ACCESS read-only
			STATUS current
			DESCRIPTION
				"Returns accumulated negative drifts value in bits."
			::= { sleGponOltStatsOnuEntry 3 }


--   1.3.6.1.4.1.6296.101.23.7.1.3.1.4
-- 1.3.6.1.4.1.6296.101.23.7.1.3.1.4
		sleGponOltStatsOnuPonBip8Errors OBJECT-TYPE
			SYNTAX Counter64
			MAX-ACCESS read-only
			STATUS current
			DESCRIPTION
				"Returns the number of BIP8 errors."
			::= { sleGponOltStatsOnuEntry 4 }


--   1.3.6.1.4.1.6296.101.23.7.1.3.1.5
-- 1.3.6.1.4.1.6296.101.23.7.1.3.1.5
		sleGponOltStatsOnuPonFecCorrectedBytes OBJECT-TYPE
			SYNTAX Counter64
			MAX-ACCESS read-only
			STATUS current
			DESCRIPTION
				"Returns FEC Corrected Bytes statistics."
			::= { sleGponOltStatsOnuEntry 5 }


--   1.3.6.1.4.1.6296.101.23.7.1.3.1.6
-- 1.3.6.1.4.1.6296.101.23.7.1.3.1.6
		sleGponOltStatsOnuPonFecUncorrectedCodewords OBJECT-TYPE
			SYNTAX Counter64
			MAX-ACCESS read-only
			STATUS current
			DESCRIPTION
				"Returns FEC Corrected Codewords statistics."
			::= { sleGponOltStatsOnuEntry 6 }


--   1.3.6.1.4.1.6296.101.23.7.1.3.1.7
-- 1.3.6.1.4.1.6296.101.23.7.1.3.1.7
		sleGponOltStatsOnuPonFecCorrectedCodewords OBJECT-TYPE
			SYNTAX Counter64
			MAX-ACCESS read-only
			STATUS current
			DESCRIPTION
				"Returns FEC Uncorrectable Codewords statistics."
			::= { sleGponOltStatsOnuEntry 7 }


--   1.3.6.1.4.1.6296.101.23.7.1.3.1.8
-- 1.3.6.1.4.1.6296.101.23.7.1.3.1.8
		sleGponOltStatsOnuPonFecReceivedCodewords OBJECT-TYPE
			SYNTAX Counter64
			MAX-ACCESS read-only
			STATUS current
			DESCRIPTION
				"Returns FEC Total number of received Codewords statistics."
			::= { sleGponOltStatsOnuEntry 8 }


--  1.3.6.1.4.1.6296.101.23.7.1.3.1.9
		sleGponOltStatsOnuAlarmSf OBJECT-TYPE
			SYNTAX Counter32
			MAX-ACCESS read-only
			STATUS current
			DESCRIPTION
				"The OLT statistics alarm SF counter"
			::= { sleGponOltStatsOnuEntry 9 }


--  1.3.6.1.4.1.6296.101.23.7.1.3.1.10
		sleGponOltStatsOnuAlarmSd OBJECT-TYPE
			SYNTAX Counter32
			MAX-ACCESS read-only
			STATUS current
			DESCRIPTION
				"The OLT statistics alarm SD counter"
			::= { sleGponOltStatsOnuEntry 10 }


--  1.3.6.1.4.1.6296.101.23.7.1.3.1.11
		sleGponOltStatsOnuElapsedTimeAfterClear OBJECT-TYPE
			SYNTAX TimeTicks
			MAX-ACCESS read-only
			STATUS current
			DESCRIPTION
				"The OLT statistics alarm elapsed time"
			::= { sleGponOltStatsOnuEntry 11 }


--  1.3.6.1.4.1.6296.101.23.7.1.3.1.12
		sleGponOltStatsOnuBipReiErrors OBJECT-TYPE
			SYNTAX Counter64
			MAX-ACCESS read-only
			STATUS current
			DESCRIPTION
				"The ONU statistics alarm Bip REI errors"
			::= { sleGponOltStatsOnuEntry 12 }


--   1.3.6.1.4.1.6296.101.23.7.1.4
-- 1.3.6.1.4.1.6296.101.23.7.1.4
		sleGponOltStatsControl OBJECT IDENTIFIER ::= { sleGponOltStatistics 4 }


--   1.3.6.1.4.1.6296.101.23.7.1.4.1
-- 1.3.6.1.4.1.6296.101.23.7.1.4.1
		sleGponOltStatsControlRequest OBJECT-TYPE
			SYNTAX INTEGER
				{
				clearGponOltStatistics(1),
				clearGponOltActivationStatistics(2),
				clearGponOltOnuStatistics(3),
				clearGponOltAlarmStatistics(4)
				}
			MAX-ACCESS read-write
			STATUS current
			DESCRIPTION
				"The request of a user command"
			::= { sleGponOltStatsControl 1 }


--   1.3.6.1.4.1.6296.101.23.7.1.4.2
-- 1.3.6.1.4.1.6296.101.23.7.1.4.2
		sleGponOltStatsControlStatus OBJECT-TYPE
			SYNTAX SleControlStatusType
			MAX-ACCESS read-only
			STATUS current
			DESCRIPTION
				"The status of user command"
			::= { sleGponOltStatsControl 2 }


--   1.3.6.1.4.1.6296.101.23.7.1.4.3
-- 1.3.6.1.4.1.6296.101.23.7.1.4.3
		sleGponOltStatsControlTimer OBJECT-TYPE
			SYNTAX Gauge32
			MAX-ACCESS read-write
			STATUS current
			DESCRIPTION
				"The maximum time for the manager for a long running user command"
			::= { sleGponOltStatsControl 3 }


--   1.3.6.1.4.1.6296.101.23.7.1.4.4
-- 1.3.6.1.4.1.6296.101.23.7.1.4.4
		sleGponOltStatsControlTimeStamp OBJECT-TYPE
			SYNTAX TimeTicks
			MAX-ACCESS read-only
			STATUS current
			DESCRIPTION
				"The time stamp of the last command(end of command)"
			::= { sleGponOltStatsControl 4 }


--   1.3.6.1.4.1.6296.101.23.7.1.4.5
-- 1.3.6.1.4.1.6296.101.23.7.1.4.5
		sleGponOltStatsControlReqResult OBJECT-TYPE
			SYNTAX SleControlRequestResultType
			MAX-ACCESS read-only
			STATUS current
			DESCRIPTION
				"The result of the last user command"
			::= { sleGponOltStatsControl 5 }


		sleGponOltStatsControlOltIndex OBJECT-TYPE
			SYNTAX INTEGER (1..2147483647)
			MAX-ACCESS read-write
			STATUS current
			DESCRIPTION
				"Profile Id"
			::= { sleGponOltStatsControl 6 }


--   1.3.6.1.4.1.6296.101.23.7.1.4.7
-- 1.3.6.1.4.1.6296.101.23.7.1.4.7
		sleGponOltStatsControlOnuIndex OBJECT-TYPE
			SYNTAX INTEGER (1..65535)
			MAX-ACCESS read-write
			STATUS current
			DESCRIPTION
				"Profile Name"
			::= { sleGponOltStatsControl 7 }


--   1.3.6.1.4.1.6296.101.23.7.1.5
-- 1.3.6.1.4.1.6296.101.23.7.1.5
		sleGponOltStatsNotification OBJECT IDENTIFIER ::= { sleGponOltStatistics 5 }


--   1.3.6.1.4.1.6296.101.23.7.1.5.1
-- 1.3.6.1.4.1.6296.101.23.7.1.5.1
		sleGponOltStatsCleared NOTIFICATION-TYPE
			OBJECTS { sleGponOltStatsControlRequest, sleGponOltStatsControlTimeStamp, sleGponOltStatsControlReqResult, sleGponOltStatsControlOltIndex }
			STATUS current
			DESCRIPTION
				"Description."
			::= { sleGponOltStatsNotification 1 }


--   1.3.6.1.4.1.6296.101.23.7.1.5.1
-- 1.3.6.1.4.1.6296.101.23.7.1.5.1
		sleGponOltActivationStatsCleared NOTIFICATION-TYPE
			OBJECTS { sleGponOltStatsControlRequest, sleGponOltStatsControlTimeStamp, sleGponOltStatsControlReqResult, sleGponOltStatsControlOltIndex }
			STATUS current
			DESCRIPTION
				"clearGponOltActivationStatistics "
			::= { sleGponOltStatsNotification 2 }


--   1.3.6.1.4.1.6296.101.23.7.1.5.1
-- 1.3.6.1.4.1.6296.101.23.7.1.5.1
		sleGponOltOnuStatsCleared NOTIFICATION-TYPE
			OBJECTS { sleGponOltStatsControlRequest, sleGponOltStatsControlTimeStamp, sleGponOltStatsControlReqResult, sleGponOltStatsControlOltIndex, sleGponOltStatsControlOnuIndex
				 }
			STATUS current
			DESCRIPTION
				"clearGponOltOnuStatistics  "
			::= { sleGponOltStatsNotification 3 }


--   1.3.6.1.4.1.6296.101.23.7.1.5.1
-- 1.3.6.1.4.1.6296.101.23.7.1.5.1
		sleGponOltAlarmStatsCleared NOTIFICATION-TYPE
			OBJECTS { sleGponOltStatsControlRequest, sleGponOltStatsControlTimeStamp, sleGponOltStatsControlReqResult, sleGponOltStatsControlOltIndex, sleGponOltStatsControlOnuIndex
				 }
			STATUS current
			DESCRIPTION
				"clearGponOltAlarmStatistics "
			::= { sleGponOltStatsNotification 4 }


--   1.3.6.1.4.1.6296.101.23.7.2
-- 1.3.6.1.4.1.6296.101.23.7.2
		sleGponOnuPMStatistics OBJECT IDENTIFIER ::= { sleGponStatistics 2 }


--   1.3.6.1.4.1.6296.101.23.7.2.1
-- 1.3.6.1.4.1.6296.101.23.7.2.1
		sleGponOnuPMStatsTable OBJECT-TYPE
			SYNTAX SEQUENCE OF SleGponOnuPMStatsEntry
			MAX-ACCESS not-accessible
			STATUS current
			DESCRIPTION
				"sleGponOnuPMStatsTable"
			::= { sleGponOnuPMStatistics 1 }


--   1.3.6.1.4.1.6296.101.23.7.2.1.1
-- 1.3.6.1.4.1.6296.101.23.7.2.1.1
		sleGponOnuPMStatsEntry OBJECT-TYPE
			SYNTAX SleGponOnuPMStatsEntry
			MAX-ACCESS not-accessible
			STATUS current
			DESCRIPTION
				"key: sleGponOltId, sleGponOnuId"
			INDEX { sleGponOltId, sleGponOnuId }
			::= { sleGponOnuPMStatsTable 1 }


		SleGponOnuPMStatsEntry ::=
			SEQUENCE {
				sleGponOnuPMStatsPrev15mLostPackets
					Counter64,
				sleGponOnuPMStatsPrev15mMisInsertedPackets
					Counter64,
				sleGponOnuPMStatsPrev15mReceivedPackets
					Counter64,
				sleGponOnuPMStatsPrev15mReceivedBlocks
					Counter64,
				sleGponOnuPMStatsPrev15mTransmittedBlocks
					Counter64,
				sleGponOnuPMStatsPrev15mImpairedBlocks
					Counter64,
				sleGponOnuPMStatsPrev15mDiscardedFrames
					Counter64,
				sleGponOnuPMStatsPrev30mLostPackets
					Counter64,
				sleGponOnuPMStatsPrev30mMisInsertedPackets
					Counter64,
				sleGponOnuPMStatsPrev30mReceivedPackets
					Counter64,
				sleGponOnuPMStatsPrev30mReceivedBlocks
					Counter64,
				sleGponOnuPMStatsPrev30mTransmittedBlocks
					Counter64,
				sleGponOnuPMStatsPrev30mImpairedBlocks
					Counter64,
				sleGponOnuPMStatsPrev30mDiscardedFrames
					Counter64,
				sleGponOnuPMStatsTotalLostPackets
					Counter64,
				sleGponOnuPMStatsTotalMisInsertedPackets
					Counter64,
				sleGponOnuPMStatsTotalReceivedPackets
					Counter64,
				sleGponOnuPMStatsTotalReceivedBlocks
					Counter64,
				sleGponOnuPMStatsTotalTransmittedBlocks
					Counter64,
				sleGponOnuPMStatsTotalImpairedBlocks
					Counter64,
				sleGponOnuPMStatsTotalDiscardedFrames
					Counter64,
				sleGponOnuPMStatsElapsedTimeAfterClear
					TimeTicks,
				sleGponOnuPMStatsElapsedTimeAfterUpdate
					Counter64
			 }

--   1.3.6.1.4.1.6296.101.23.7.2.1.1.1
-- 1.3.6.1.4.1.6296.101.23.7.2.1.1.1
		sleGponOnuPMStatsPrev15mLostPackets OBJECT-TYPE
			SYNTAX Counter64
			MAX-ACCESS read-only
			STATUS current
			DESCRIPTION
				"This attribute counts background GEM frame loss."
			::= { sleGponOnuPMStatsEntry 1 }


--   1.3.6.1.4.1.6296.101.23.7.2.1.1.2
-- 1.3.6.1.4.1.6296.101.23.7.2.1.1.2
		sleGponOnuPMStatsPrev15mMisInsertedPackets OBJECT-TYPE
			SYNTAX Counter64
			MAX-ACCESS read-only
			STATUS current
			DESCRIPTION
				"This attribute counts GEM frames misrouted to this GEM port."
			::= { sleGponOnuPMStatsEntry 2 }


--   1.3.6.1.4.1.6296.101.23.7.2.1.1.3
-- 1.3.6.1.4.1.6296.101.23.7.2.1.1.3
		sleGponOnuPMStatsPrev15mReceivedPackets OBJECT-TYPE
			SYNTAX Counter64
			MAX-ACCESS read-only
			STATUS current
			DESCRIPTION
				"This attribute counts GEM frames that were received correctly at the monitored GEM port."
			::= { sleGponOnuPMStatsEntry 3 }


--   1.3.6.1.4.1.6296.101.23.7.2.1.1.4
-- 1.3.6.1.4.1.6296.101.23.7.2.1.1.4
		sleGponOnuPMStatsPrev15mReceivedBlocks OBJECT-TYPE
			SYNTAX Counter64
			MAX-ACCESS read-only
			STATUS current
			DESCRIPTION
				"This attribute counts GEM blocks that were received correctly at the monitored GEM port."
			::= { sleGponOnuPMStatsEntry 4 }


--   1.3.6.1.4.1.6296.101.23.7.2.1.1.5
-- 1.3.6.1.4.1.6296.101.23.7.2.1.1.5
		sleGponOnuPMStatsPrev15mTransmittedBlocks OBJECT-TYPE
			SYNTAX Counter64
			MAX-ACCESS read-only
			STATUS current
			DESCRIPTION
				"This attribute counts GEM blocks originated by the transmitting end point"
			::= { sleGponOnuPMStatsEntry 5 }


--   1.3.6.1.4.1.6296.101.23.7.2.1.1.6
-- 1.3.6.1.4.1.6296.101.23.7.2.1.1.6
		sleGponOnuPMStatsPrev15mImpairedBlocks OBJECT-TYPE
			SYNTAX Counter64
			MAX-ACCESS read-only
			STATUS current
			DESCRIPTION
				"This attribute counts GEM blocks originated by the number of misinserted packets reaches its threshold."
			::= { sleGponOnuPMStatsEntry 6 }


--   1.3.6.1.4.1.6296.101.23.7.2.1.1.7
-- 1.3.6.1.4.1.6296.101.23.7.2.1.1.7
		sleGponOnuPMStatsPrev15mDiscardedFrames OBJECT-TYPE
			SYNTAX Counter64
			MAX-ACCESS read-only
			STATUS current
			DESCRIPTION
				"This attribute counts the number of downstream GEM frames discarded for any reason (erroneous FCS, too long length, buffer overflow, etc)"
			::= { sleGponOnuPMStatsEntry 7 }


--   1.3.6.1.4.1.6296.101.23.7.2.1.1.8
-- 1.3.6.1.4.1.6296.101.23.7.2.1.1.8
		sleGponOnuPMStatsPrev30mLostPackets OBJECT-TYPE
			SYNTAX Counter64
			MAX-ACCESS read-only
			STATUS current
			DESCRIPTION
				"This attribute counts background GEM frame loss."
			::= { sleGponOnuPMStatsEntry 8 }


--   1.3.6.1.4.1.6296.101.23.7.2.1.1.9
-- 1.3.6.1.4.1.6296.101.23.7.2.1.1.9
		sleGponOnuPMStatsPrev30mMisInsertedPackets OBJECT-TYPE
			SYNTAX Counter64
			MAX-ACCESS read-only
			STATUS current
			DESCRIPTION
				"This attribute counts GEM frames misrouted to this GEM port."
			::= { sleGponOnuPMStatsEntry 9 }


--   1.3.6.1.4.1.6296.101.23.7.2.1.1.10
-- 1.3.6.1.4.1.6296.101.23.7.2.1.1.10
		sleGponOnuPMStatsPrev30mReceivedPackets OBJECT-TYPE
			SYNTAX Counter64
			MAX-ACCESS read-only
			STATUS current
			DESCRIPTION
				"This attribute counts GEM frames that were received correctly at the monitored GEM port."
			::= { sleGponOnuPMStatsEntry 10 }


--   1.3.6.1.4.1.6296.101.23.7.2.1.1.11
-- 1.3.6.1.4.1.6296.101.23.7.2.1.1.11
		sleGponOnuPMStatsPrev30mReceivedBlocks OBJECT-TYPE
			SYNTAX Counter64
			MAX-ACCESS read-only
			STATUS current
			DESCRIPTION
				"This attribute counts GEM blocks that were received correctly at the monitored GEM port."
			::= { sleGponOnuPMStatsEntry 11 }


--   1.3.6.1.4.1.6296.101.23.7.2.1.1.12
-- 1.3.6.1.4.1.6296.101.23.7.2.1.1.12
		sleGponOnuPMStatsPrev30mTransmittedBlocks OBJECT-TYPE
			SYNTAX Counter64
			MAX-ACCESS read-only
			STATUS current
			DESCRIPTION
				"This attribute counts GEM blocks originated by the transmitting end point"
			::= { sleGponOnuPMStatsEntry 12 }


--   1.3.6.1.4.1.6296.101.23.7.2.1.1.13
-- 1.3.6.1.4.1.6296.101.23.7.2.1.1.13
		sleGponOnuPMStatsPrev30mImpairedBlocks OBJECT-TYPE
			SYNTAX Counter64
			MAX-ACCESS read-only
			STATUS current
			DESCRIPTION
				"This attribute counts GEM blocks originated by the number of misinserted packets reaches its threshold."
			::= { sleGponOnuPMStatsEntry 13 }


--   1.3.6.1.4.1.6296.101.23.7.2.1.1.14
-- 1.3.6.1.4.1.6296.101.23.7.2.1.1.14
		sleGponOnuPMStatsPrev30mDiscardedFrames OBJECT-TYPE
			SYNTAX Counter64
			MAX-ACCESS read-only
			STATUS current
			DESCRIPTION
				"This attribute counts the number of downstream GEM frames discarded for any reason (erroneous FCS, too long length, buffer overflow, etc)"
			::= { sleGponOnuPMStatsEntry 14 }


--   1.3.6.1.4.1.6296.101.23.7.2.1.1.15
-- 1.3.6.1.4.1.6296.101.23.7.2.1.1.15
		sleGponOnuPMStatsTotalLostPackets OBJECT-TYPE
			SYNTAX Counter64
			MAX-ACCESS read-only
			STATUS current
			DESCRIPTION
				"This attribute counts background GEM frame loss."
			::= { sleGponOnuPMStatsEntry 15 }


--   1.3.6.1.4.1.6296.101.23.7.2.1.1.16
-- 1.3.6.1.4.1.6296.101.23.7.2.1.1.16
		sleGponOnuPMStatsTotalMisInsertedPackets OBJECT-TYPE
			SYNTAX Counter64
			MAX-ACCESS read-only
			STATUS current
			DESCRIPTION
				"This attribute counts GEM frames misrouted to this GEM port."
			::= { sleGponOnuPMStatsEntry 16 }


--   1.3.6.1.4.1.6296.101.23.7.2.1.1.17
-- 1.3.6.1.4.1.6296.101.23.7.2.1.1.17
		sleGponOnuPMStatsTotalReceivedPackets OBJECT-TYPE
			SYNTAX Counter64
			MAX-ACCESS read-only
			STATUS current
			DESCRIPTION
				"This attribute counts GEM frames that were received correctly at the monitored GEM port."
			::= { sleGponOnuPMStatsEntry 17 }


--   1.3.6.1.4.1.6296.101.23.7.2.1.1.18
-- 1.3.6.1.4.1.6296.101.23.7.2.1.1.18
		sleGponOnuPMStatsTotalReceivedBlocks OBJECT-TYPE
			SYNTAX Counter64
			MAX-ACCESS read-only
			STATUS current
			DESCRIPTION
				"This attribute counts GEM blocks that were received correctly at the monitored GEM port."
			::= { sleGponOnuPMStatsEntry 18 }


--   1.3.6.1.4.1.6296.101.23.7.2.1.1.19
-- 1.3.6.1.4.1.6296.101.23.7.2.1.1.19
		sleGponOnuPMStatsTotalTransmittedBlocks OBJECT-TYPE
			SYNTAX Counter64
			MAX-ACCESS read-only
			STATUS current
			DESCRIPTION
				"This attribute counts GEM blocks originated by the transmitting end point"
			::= { sleGponOnuPMStatsEntry 19 }


--   1.3.6.1.4.1.6296.101.23.7.2.1.1.20
-- 1.3.6.1.4.1.6296.101.23.7.2.1.1.20
		sleGponOnuPMStatsTotalImpairedBlocks OBJECT-TYPE
			SYNTAX Counter64
			MAX-ACCESS read-only
			STATUS current
			DESCRIPTION
				"This attribute counts GEM blocks originated by the number of misinserted packets reaches its threshold."
			::= { sleGponOnuPMStatsEntry 20 }


--   1.3.6.1.4.1.6296.101.23.7.2.1.1.21
-- 1.3.6.1.4.1.6296.101.23.7.2.1.1.21
		sleGponOnuPMStatsTotalDiscardedFrames OBJECT-TYPE
			SYNTAX Counter64
			MAX-ACCESS read-only
			STATUS current
			DESCRIPTION
				"This attribute counts the number of downstream GEM frames discarded for any reason (erroneous FCS, too long length, buffer overflow, etc)"
			::= { sleGponOnuPMStatsEntry 21 }


--   1.3.6.1.4.1.6296.101.23.7.2.1.1.22
-- 1.3.6.1.4.1.6296.101.23.7.2.1.1.22
		sleGponOnuPMStatsElapsedTimeAfterClear OBJECT-TYPE
			SYNTAX TimeTicks
			MAX-ACCESS read-only
			STATUS current
			DESCRIPTION
				"ONU PM counter  time after Clear "
			::= { sleGponOnuPMStatsEntry 22 }


--   1.3.6.1.4.1.6296.101.23.7.2.1.1.23
-- 1.3.6.1.4.1.6296.101.23.7.2.1.1.23
		sleGponOnuPMStatsElapsedTimeAfterUpdate OBJECT-TYPE
			SYNTAX Counter64
			MAX-ACCESS read-only
			STATUS current
			DESCRIPTION
				"ONU PM counter  time after update"
			::= { sleGponOnuPMStatsEntry 23 }


--   1.3.6.1.4.1.6296.101.23.7.2.2
-- 1.3.6.1.4.1.6296.101.23.7.2.2
		sleGponOnuPMStatsControl OBJECT IDENTIFIER ::= { sleGponOnuPMStatistics 2 }


--   1.3.6.1.4.1.6296.101.23.7.2.2.1
-- 1.3.6.1.4.1.6296.101.23.7.2.2.1
		sleGponOnuPMStatsControlRequest OBJECT-TYPE
			SYNTAX INTEGER
				{
				clearPmStats(1),
				setCurrentDetailStats(2)
				}
			MAX-ACCESS read-write
			STATUS current
			DESCRIPTION
				"The request of a user command"
			::= { sleGponOnuPMStatsControl 1 }


--   1.3.6.1.4.1.6296.101.23.7.2.2.2
-- 1.3.6.1.4.1.6296.101.23.7.2.2.2
		sleGponOnuPMStatsControlStatus OBJECT-TYPE
			SYNTAX SleControlStatusType
			MAX-ACCESS read-only
			STATUS current
			DESCRIPTION
				"The status of user command"
			::= { sleGponOnuPMStatsControl 2 }


--   1.3.6.1.4.1.6296.101.23.7.2.2.3
-- 1.3.6.1.4.1.6296.101.23.7.2.2.3
		sleGponOnuPMStatsControlTimer OBJECT-TYPE
			SYNTAX Gauge32
			MAX-ACCESS read-write
			STATUS current
			DESCRIPTION
				"The maximum time for the manager for a long running user command"
			::= { sleGponOnuPMStatsControl 3 }


--   1.3.6.1.4.1.6296.101.23.7.2.2.4
-- 1.3.6.1.4.1.6296.101.23.7.2.2.4
		sleGponOnuPMStatsControlTimeStamp OBJECT-TYPE
			SYNTAX TimeTicks
			MAX-ACCESS read-only
			STATUS current
			DESCRIPTION
				"The time stamp of the last command(end of command)"
			::= { sleGponOnuPMStatsControl 4 }


--   1.3.6.1.4.1.6296.101.23.7.2.2.5
-- 1.3.6.1.4.1.6296.101.23.7.2.2.5
		sleGponOnuPMStatsControlReqResult OBJECT-TYPE
			SYNTAX SleControlRequestResultType
			MAX-ACCESS read-only
			STATUS current
			DESCRIPTION
				"The result of the last user command"
			::= { sleGponOnuPMStatsControl 5 }


		sleGponOnuPMStatsControlOltIndex OBJECT-TYPE
			SYNTAX Integer32 (1..2147483647)
			MAX-ACCESS read-write
			STATUS current
			DESCRIPTION
				"The OLT index."
			::= { sleGponOnuPMStatsControl 6 }


--   1.3.6.1.4.1.6296.101.23.7.2.2.7
-- 1.3.6.1.4.1.6296.101.23.7.2.2.7
		sleGponOnuPMStatsControlOnuIndex OBJECT-TYPE
			SYNTAX Integer32
			MAX-ACCESS read-write
			STATUS current
			DESCRIPTION
				"The result of the last user command"
			::= { sleGponOnuPMStatsControl 7 }


--   1.3.6.1.4.1.6296.101.23.7.2.3
-- 1.3.6.1.4.1.6296.101.23.7.2.3
		sleGponOnuPMStatsNotification OBJECT IDENTIFIER ::= { sleGponOnuPMStatistics 3 }


--   1.3.6.1.4.1.6296.101.23.7.2.3.1
-- 1.3.6.1.4.1.6296.101.23.7.2.3.1
		sleGponOnuPMStatsCleared NOTIFICATION-TYPE
			OBJECTS { sleGponOnuPMStatsControlRequest, sleGponOnuPMStatsControlTimeStamp, sleGponOnuPMStatsControlReqResult, sleGponOnuPMStatsControlOltIndex, sleGponOnuPMStatsControlOnuIndex
				 }
			STATUS current
			DESCRIPTION
				"Description."
			::= { sleGponOnuPMStatsNotification 1 }


--   1.3.6.1.4.1.6296.101.23.7.2.3.1
-- 1.3.6.1.4.1.6296.101.23.7.2.3.2
		sleGponOnuPMStatsCurrentDetailChanged NOTIFICATION-TYPE
			OBJECTS { sleGponOnuPMStatsControlRequest, sleGponOnuPMStatsControlTimeStamp, sleGponOnuPMStatsControlReqResult, sleGponOnuPMStatsControlOltIndex, sleGponOnuPMStatsControlOnuIndex
				 }
			STATUS current
			DESCRIPTION
				"Description."
			::= { sleGponOnuPMStatsNotification 2 }


--   1.3.6.1.4.1.6296.101.23.7.3
-- 1.3.6.1.4.1.6296.101.23.7.3
		sleGponOnuPMStatisticsDetail OBJECT IDENTIFIER ::= { sleGponStatistics 3 }


--   1.3.6.1.4.1.6296.101.23.7.3.1
-- 1.3.6.1.4.1.6296.101.23.7.3.1
		sleGponOnuPMStatsDetailGEMTable OBJECT-TYPE
			SYNTAX SEQUENCE OF SleGponOnuPMStatsDetailGEMEntry
			MAX-ACCESS not-accessible
			STATUS current
			DESCRIPTION
				"sleGponOnuPMStatsDetailGEMTable"
			::= { sleGponOnuPMStatisticsDetail 1 }


--   1.3.6.1.4.1.6296.101.23.7.3.1.1
-- 1.3.6.1.4.1.6296.101.23.7.3.1.1
		sleGponOnuPMStatsDetailGEMEntry OBJECT-TYPE
			SYNTAX SleGponOnuPMStatsDetailGEMEntry
			MAX-ACCESS not-accessible
			STATUS current
			DESCRIPTION
				"key: sleGponOnuPMStatsDetailGEMPort, sleGponOltId, sleGponOnuId"
			INDEX { sleGponOltId, sleGponOnuId, sleGponOnuPMStatsDetailGEMPortIndex }
			::= { sleGponOnuPMStatsDetailGEMTable 1 }


		SleGponOnuPMStatsDetailGEMEntry ::=
			SEQUENCE {
				sleGponOnuPMStatsDetailGEMPortIndex
					INTEGER,
				sleGponOnuPMStatsDetailGEMPort
					INTEGER,
				sleGponOnuPMStatsDetailGEMPre15mLostPackets
					Counter64,
				sleGponOnuPMStatsDetailGEMPre15mMisInsertedPackets
					Counter64,
				sleGponOnuPMStatsDetailGEMPre15mReceivedPackets
					Counter64,
				sleGponOnuPMStatsDetailGEMPre15mReceivedBlocks
					Counter64,
				sleGponOnuPMStatsDetailGEMPre15mTransmittedBlocks
					Counter64,
				sleGponOnuPMStatsDetailGEMPre15mImpairedBlocks
					Counter64,
				sleGponOnuPMStatsDetailGEMHourLostPackets
					Counter64,
				sleGponOnuPMStatsDetailGEMHourMisInsertedPackets
					Counter64,
				sleGponOnuPMStatsDetailGEMHourReceivedPackets
					Counter64,
				sleGponOnuPMStatsDetailGEMHourReceivedBlocks
					Counter64,
				sleGponOnuPMStatsDetailGEMHourTransmittedBlocks
					Counter64,
				sleGponOnuPMStatsDetailGEMHourImpairedBlocks
					Counter64,
				sleGponOnuPMStatsDetailGEMDayLostPackets
					Counter64,
				sleGponOnuPMStatsDetailGEMDayMisInsertedPackets
					Counter64,
				sleGponOnuPMStatsDetailGEMDayReceivedPackets
					Counter64,
				sleGponOnuPMStatsDetailGEMDayReceivedBlocks
					Counter64,
				sleGponOnuPMStatsDetailGEMDayTransmittedBlocks
					Counter64,
				sleGponOnuPMStatsDetailGEMDayImpairedBlocks
					Counter64,
				sleGponOnuPMStatsDetailGEMTotalLostPackets
					Counter64,
				sleGponOnuPMStatsDetailGEMTotalMisInsertedPackets
					Counter64,
				sleGponOnuPMStatsDetailGEMTotalReceivedPackets
					Counter64,
				sleGponOnuPMStatsDetailGEMTotalReceivedBlocks
					Counter64,
				sleGponOnuPMStatsDetailGEMTotalTransmittedBlocks
					Counter64,
				sleGponOnuPMStatsDetailGEMTotalImpairedBlocks
					Counter64,
				sleGponOnuPMStatsDetailGEMElapsedTimeAfterClear
					TimeTicks,
				sleGponOnuPMStatsDetailGEMElapsedTimeAfterUpdate
					Counter64
			 }

--  1.3.6.1.4.1.6296.101.23.7.3.1.1.1
		sleGponOnuPMStatsDetailGEMPortIndex OBJECT-TYPE
			SYNTAX INTEGER (1..65535)
			MAX-ACCESS read-only
			STATUS current
			DESCRIPTION
				"The GEM port index."
			::= { sleGponOnuPMStatsDetailGEMEntry 1 }


--   1.3.6.1.4.1.6296.101.23.7.3.1.1.1
-- 1.3.6.1.4.1.6296.101.23.7.3.1.1.2
		sleGponOnuPMStatsDetailGEMPort OBJECT-TYPE
			SYNTAX INTEGER (1..65535)
			MAX-ACCESS read-only
			STATUS current
			DESCRIPTION
				"The GEM port information"
			::= { sleGponOnuPMStatsDetailGEMEntry 2 }


--   1.3.6.1.4.1.6296.101.23.7.3.1.1.2
-- 1.3.6.1.4.1.6296.101.23.7.3.1.1.3
		sleGponOnuPMStatsDetailGEMPre15mLostPackets OBJECT-TYPE
			SYNTAX Counter64
			MAX-ACCESS read-only
			STATUS current
			DESCRIPTION
				"The pre 15 minute number of lost packet "
			::= { sleGponOnuPMStatsDetailGEMEntry 3 }


--   1.3.6.1.4.1.6296.101.23.7.3.1.1.3
-- 1.3.6.1.4.1.6296.101.23.7.3.1.1.4
		sleGponOnuPMStatsDetailGEMPre15mMisInsertedPackets OBJECT-TYPE
			SYNTAX Counter64
			MAX-ACCESS read-only
			STATUS current
			DESCRIPTION
				"The pre 15 minute number of mis inserted packet "
			::= { sleGponOnuPMStatsDetailGEMEntry 4 }


--   1.3.6.1.4.1.6296.101.23.7.3.1.1.4
-- 1.3.6.1.4.1.6296.101.23.7.3.1.1.5
		sleGponOnuPMStatsDetailGEMPre15mReceivedPackets OBJECT-TYPE
			SYNTAX Counter64
			MAX-ACCESS read-only
			STATUS current
			DESCRIPTION
				"The pre 15 minute number of received packet"
			::= { sleGponOnuPMStatsDetailGEMEntry 5 }


--   1.3.6.1.4.1.6296.101.23.7.3.1.1.5
-- 1.3.6.1.4.1.6296.101.23.7.3.1.1.6
		sleGponOnuPMStatsDetailGEMPre15mReceivedBlocks OBJECT-TYPE
			SYNTAX Counter64
			MAX-ACCESS read-only
			STATUS current
			DESCRIPTION
				"The pre 15 minute number of received blocks"
			::= { sleGponOnuPMStatsDetailGEMEntry 6 }


--   1.3.6.1.4.1.6296.101.23.7.3.1.1.6
-- 1.3.6.1.4.1.6296.101.23.7.3.1.1.7
		sleGponOnuPMStatsDetailGEMPre15mTransmittedBlocks OBJECT-TYPE
			SYNTAX Counter64
			MAX-ACCESS read-only
			STATUS current
			DESCRIPTION
				"The pre 15 minute number of transmitted blocks"
			::= { sleGponOnuPMStatsDetailGEMEntry 7 }


--   1.3.6.1.4.1.6296.101.23.7.3.1.1.7
-- 1.3.6.1.4.1.6296.101.23.7.3.1.1.8
		sleGponOnuPMStatsDetailGEMPre15mImpairedBlocks OBJECT-TYPE
			SYNTAX Counter64
			MAX-ACCESS read-only
			STATUS current
			DESCRIPTION
				"The pre 15 minute number of impaired blocks"
			::= { sleGponOnuPMStatsDetailGEMEntry 8 }


--   1.3.6.1.4.1.6296.101.23.7.3.1.1.8
-- 1.3.6.1.4.1.6296.101.23.7.3.1.1.9
		sleGponOnuPMStatsDetailGEMHourLostPackets OBJECT-TYPE
			SYNTAX Counter64
			MAX-ACCESS read-only
			STATUS current
			DESCRIPTION
				"The hour number of lost packet "
			::= { sleGponOnuPMStatsDetailGEMEntry 9 }


--   1.3.6.1.4.1.6296.101.23.7.3.1.1.9
-- 1.3.6.1.4.1.6296.101.23.7.3.1.1.10
		sleGponOnuPMStatsDetailGEMHourMisInsertedPackets OBJECT-TYPE
			SYNTAX Counter64
			MAX-ACCESS read-only
			STATUS current
			DESCRIPTION
				"The hour number of mis inserted packet "
			::= { sleGponOnuPMStatsDetailGEMEntry 10 }


--   1.3.6.1.4.1.6296.101.23.7.3.1.1.10
-- 1.3.6.1.4.1.6296.101.23.7.3.1.1.11
		sleGponOnuPMStatsDetailGEMHourReceivedPackets OBJECT-TYPE
			SYNTAX Counter64
			MAX-ACCESS read-write
			STATUS current
			DESCRIPTION
				"The hour number of received packet"
			::= { sleGponOnuPMStatsDetailGEMEntry 11 }


--   1.3.6.1.4.1.6296.101.23.7.3.1.1.11
-- 1.3.6.1.4.1.6296.101.23.7.3.1.1.12
		sleGponOnuPMStatsDetailGEMHourReceivedBlocks OBJECT-TYPE
			SYNTAX Counter64
			MAX-ACCESS read-write
			STATUS current
			DESCRIPTION
				"The hour number of received blocks"
			::= { sleGponOnuPMStatsDetailGEMEntry 12 }


--   1.3.6.1.4.1.6296.101.23.7.3.1.1.12
-- 1.3.6.1.4.1.6296.101.23.7.3.1.1.13
		sleGponOnuPMStatsDetailGEMHourTransmittedBlocks OBJECT-TYPE
			SYNTAX Counter64
			MAX-ACCESS read-only
			STATUS current
			DESCRIPTION
				"The hour number of transmitted blocks"
			::= { sleGponOnuPMStatsDetailGEMEntry 13 }


--   1.3.6.1.4.1.6296.101.23.7.3.1.1.13
-- 1.3.6.1.4.1.6296.101.23.7.3.1.1.14
		sleGponOnuPMStatsDetailGEMHourImpairedBlocks OBJECT-TYPE
			SYNTAX Counter64
			MAX-ACCESS read-write
			STATUS current
			DESCRIPTION
				"The hour number of impaired blocks"
			::= { sleGponOnuPMStatsDetailGEMEntry 14 }


--   1.3.6.1.4.1.6296.101.23.7.3.1.1.14
-- 1.3.6.1.4.1.6296.101.23.7.3.1.1.15
		sleGponOnuPMStatsDetailGEMDayLostPackets OBJECT-TYPE
			SYNTAX Counter64
			MAX-ACCESS read-write
			STATUS current
			DESCRIPTION
				"The day number of lost packet "
			::= { sleGponOnuPMStatsDetailGEMEntry 15 }


--   1.3.6.1.4.1.6296.101.23.7.3.1.1.15
-- 1.3.6.1.4.1.6296.101.23.7.3.1.1.16
		sleGponOnuPMStatsDetailGEMDayMisInsertedPackets OBJECT-TYPE
			SYNTAX Counter64
			MAX-ACCESS read-write
			STATUS current
			DESCRIPTION
				"The day number of mis inserted packet "
			::= { sleGponOnuPMStatsDetailGEMEntry 16 }


--   1.3.6.1.4.1.6296.101.23.7.3.1.1.16
-- 1.3.6.1.4.1.6296.101.23.7.3.1.1.17
		sleGponOnuPMStatsDetailGEMDayReceivedPackets OBJECT-TYPE
			SYNTAX Counter64
			MAX-ACCESS read-write
			STATUS current
			DESCRIPTION
				"The day number of received packet"
			::= { sleGponOnuPMStatsDetailGEMEntry 17 }


--   1.3.6.1.4.1.6296.101.23.7.3.1.1.17
-- 1.3.6.1.4.1.6296.101.23.7.3.1.1.18
		sleGponOnuPMStatsDetailGEMDayReceivedBlocks OBJECT-TYPE
			SYNTAX Counter64
			MAX-ACCESS read-write
			STATUS current
			DESCRIPTION
				"The day number of received blocks"
			::= { sleGponOnuPMStatsDetailGEMEntry 18 }


--   1.3.6.1.4.1.6296.101.23.7.3.1.1.18
-- 1.3.6.1.4.1.6296.101.23.7.3.1.1.19
		sleGponOnuPMStatsDetailGEMDayTransmittedBlocks OBJECT-TYPE
			SYNTAX Counter64
			MAX-ACCESS read-write
			STATUS current
			DESCRIPTION
				"The day number of transmitted blocks"
			::= { sleGponOnuPMStatsDetailGEMEntry 19 }


--   1.3.6.1.4.1.6296.101.23.7.3.1.1.19
-- 1.3.6.1.4.1.6296.101.23.7.3.1.1.20
		sleGponOnuPMStatsDetailGEMDayImpairedBlocks OBJECT-TYPE
			SYNTAX Counter64
			MAX-ACCESS read-write
			STATUS current
			DESCRIPTION
				"The day number of impaired blocks"
			::= { sleGponOnuPMStatsDetailGEMEntry 20 }


--   1.3.6.1.4.1.6296.101.23.7.3.1.1.20
-- 1.3.6.1.4.1.6296.101.23.7.3.1.1.21
		sleGponOnuPMStatsDetailGEMTotalLostPackets OBJECT-TYPE
			SYNTAX Counter64
			MAX-ACCESS read-write
			STATUS current
			DESCRIPTION
				"The total number of lost packet "
			::= { sleGponOnuPMStatsDetailGEMEntry 21 }


--   1.3.6.1.4.1.6296.101.23.7.3.1.1.21
-- 1.3.6.1.4.1.6296.101.23.7.3.1.1.22
		sleGponOnuPMStatsDetailGEMTotalMisInsertedPackets OBJECT-TYPE
			SYNTAX Counter64
			MAX-ACCESS read-write
			STATUS current
			DESCRIPTION
				"The total number of mis inserted packet "
			::= { sleGponOnuPMStatsDetailGEMEntry 22 }


--   1.3.6.1.4.1.6296.101.23.7.3.1.1.22
-- 1.3.6.1.4.1.6296.101.23.7.3.1.1.23
		sleGponOnuPMStatsDetailGEMTotalReceivedPackets OBJECT-TYPE
			SYNTAX Counter64
			MAX-ACCESS read-write
			STATUS current
			DESCRIPTION
				"The total number of received packet"
			::= { sleGponOnuPMStatsDetailGEMEntry 23 }


--   1.3.6.1.4.1.6296.101.23.7.3.1.1.23
-- 1.3.6.1.4.1.6296.101.23.7.3.1.1.24
		sleGponOnuPMStatsDetailGEMTotalReceivedBlocks OBJECT-TYPE
			SYNTAX Counter64
			MAX-ACCESS read-write
			STATUS current
			DESCRIPTION
				"The total number of received blocks"
			::= { sleGponOnuPMStatsDetailGEMEntry 24 }


--   1.3.6.1.4.1.6296.101.23.7.3.1.1.24
-- 1.3.6.1.4.1.6296.101.23.7.3.1.1.25
		sleGponOnuPMStatsDetailGEMTotalTransmittedBlocks OBJECT-TYPE
			SYNTAX Counter64
			MAX-ACCESS read-write
			STATUS current
			DESCRIPTION
				"The total number of transmitted blocks"
			::= { sleGponOnuPMStatsDetailGEMEntry 25 }


--   1.3.6.1.4.1.6296.101.23.7.3.1.1.25
-- 1.3.6.1.4.1.6296.101.23.7.3.1.1.26
		sleGponOnuPMStatsDetailGEMTotalImpairedBlocks OBJECT-TYPE
			SYNTAX Counter64
			MAX-ACCESS read-write
			STATUS current
			DESCRIPTION
				"The total number of impaired blocks"
			::= { sleGponOnuPMStatsDetailGEMEntry 26 }


--   1.3.6.1.4.1.6296.101.23.7.3.1.1.26
-- 1.3.6.1.4.1.6296.101.23.7.3.1.1.27
		sleGponOnuPMStatsDetailGEMElapsedTimeAfterClear OBJECT-TYPE
			SYNTAX TimeTicks
			MAX-ACCESS read-only
			STATUS current
			DESCRIPTION
				"The number of packets for elapsed time after clear"
			::= { sleGponOnuPMStatsDetailGEMEntry 27 }


--   1.3.6.1.4.1.6296.101.23.7.3.1.1.27
-- 1.3.6.1.4.1.6296.101.23.7.3.1.1.28
		sleGponOnuPMStatsDetailGEMElapsedTimeAfterUpdate OBJECT-TYPE
			SYNTAX Counter64
			MAX-ACCESS read-write
			STATUS current
			DESCRIPTION
				"The number of packets for elapsed time after update"
			::= { sleGponOnuPMStatsDetailGEMEntry 28 }


--   1.3.6.1.4.1.6296.101.23.7.3.2
-- 1.3.6.1.4.1.6296.101.23.7.3.2
		sleGponOnuPMStatsDetailAniTable OBJECT-TYPE
			SYNTAX SEQUENCE OF SleGponOnuPMStatsDetailAniEntry
			MAX-ACCESS not-accessible
			STATUS current
			DESCRIPTION
				"sleGponOnuPMStatsDetailAniTable"
			::= { sleGponOnuPMStatisticsDetail 2 }


--   1.3.6.1.4.1.6296.101.23.7.3.2.1
-- 1.3.6.1.4.1.6296.101.23.7.3.2.1
		sleGponOnuPMStatsDetailAniEntry OBJECT-TYPE
			SYNTAX SleGponOnuPMStatsDetailAniEntry
			MAX-ACCESS not-accessible
			STATUS current
			DESCRIPTION
				"key: sleGponOnuPMStatsDetailAniPort, sleGponOltId, sleGponOnuId"
			INDEX { sleGponOltId, sleGponOnuId, sleGponOnuPMStatsDetailAniPortIndex }
			::= { sleGponOnuPMStatsDetailAniTable 1 }


		SleGponOnuPMStatsDetailAniEntry ::=
			SEQUENCE {
				sleGponOnuPMStatsDetailAniPortIndex
					INTEGER,
				sleGponOnuPMStatsDetailAniPort
					INTEGER,
				sleGponOnuPMStatsDetailAniPre15mDiscardedFrames
					Counter64,
				sleGponOnuPMStatsDetailAniHourDiscardedFrames
					Counter64,
				sleGponOnuPMStatsDetailAniDayDiscardedFrames
					Counter64,
				sleGponOnuPMStatsDetailAniTotalDiscardedFrames
					Counter64,
				sleGponOnuPMStatsDetailAniElapsedTimeAfterClear
					TimeTicks,
				sleGponOnuPMStatsDetailAniElapsedTimeAfterUpdate
					Counter64
			 }

--  1.3.6.1.4.1.6296.101.23.7.3.2.1.1
		sleGponOnuPMStatsDetailAniPortIndex OBJECT-TYPE
			SYNTAX INTEGER (1..65535)
			MAX-ACCESS read-only
			STATUS current
			DESCRIPTION
				"The ANI port index."
			::= { sleGponOnuPMStatsDetailAniEntry 1 }


--   1.3.6.1.4.1.6296.101.23.7.3.2.1.1
-- 1.3.6.1.4.1.6296.101.23.7.3.2.1.2
		sleGponOnuPMStatsDetailAniPort OBJECT-TYPE
			SYNTAX INTEGER (1..65535)
			MAX-ACCESS read-only
			STATUS current
			DESCRIPTION
				"The Ani port information"
			::= { sleGponOnuPMStatsDetailAniEntry 2 }


--   1.3.6.1.4.1.6296.101.23.7.3.2.1.2
-- 1.3.6.1.4.1.6296.101.23.7.3.2.1.3
		sleGponOnuPMStatsDetailAniPre15mDiscardedFrames OBJECT-TYPE
			SYNTAX Counter64
			MAX-ACCESS read-only
			STATUS current
			DESCRIPTION
				"The pre 15 minute number of lost discarded frames"
			::= { sleGponOnuPMStatsDetailAniEntry 3 }


--   1.3.6.1.4.1.6296.101.23.7.3.2.1.3
-- 1.3.6.1.4.1.6296.101.23.7.3.2.1.4
		sleGponOnuPMStatsDetailAniHourDiscardedFrames OBJECT-TYPE
			SYNTAX Counter64
			MAX-ACCESS read-only
			STATUS current
			DESCRIPTION
				"The hour number of lost discarded frames"
			::= { sleGponOnuPMStatsDetailAniEntry 4 }


--   1.3.6.1.4.1.6296.101.23.7.3.2.1.4
-- 1.3.6.1.4.1.6296.101.23.7.3.2.1.5
		sleGponOnuPMStatsDetailAniDayDiscardedFrames OBJECT-TYPE
			SYNTAX Counter64
			MAX-ACCESS read-only
			STATUS current
			DESCRIPTION
				"The day number of lost discarded frames"
			::= { sleGponOnuPMStatsDetailAniEntry 5 }


--   1.3.6.1.4.1.6296.101.23.7.3.2.1.5
-- 1.3.6.1.4.1.6296.101.23.7.3.2.1.6
		sleGponOnuPMStatsDetailAniTotalDiscardedFrames OBJECT-TYPE
			SYNTAX Counter64
			MAX-ACCESS read-only
			STATUS current
			DESCRIPTION
				"The total number of lost discarded frames"
			::= { sleGponOnuPMStatsDetailAniEntry 6 }


--   1.3.6.1.4.1.6296.101.23.7.3.2.1.6
-- 1.3.6.1.4.1.6296.101.23.7.3.2.1.7
		sleGponOnuPMStatsDetailAniElapsedTimeAfterClear OBJECT-TYPE
			SYNTAX TimeTicks
			MAX-ACCESS read-only
			STATUS current
			DESCRIPTION
				"The number of packets for elapsed time after clear"
			::= { sleGponOnuPMStatsDetailAniEntry 7 }


--   1.3.6.1.4.1.6296.101.23.7.3.2.1.7
-- 1.3.6.1.4.1.6296.101.23.7.3.2.1.8
		sleGponOnuPMStatsDetailAniElapsedTimeAfterUpdate OBJECT-TYPE
			SYNTAX Counter64
			MAX-ACCESS read-write
			STATUS current
			DESCRIPTION
				"The number of packets for elapsed time after update"
			::= { sleGponOnuPMStatsDetailAniEntry 8 }


--   1.3.6.1.4.1.6296.101.23.7.3.3
-- 1.3.6.1.4.1.6296.101.23.7.3.3
		sleGponOnuPMStatsDetailUniEthFrameUpTable OBJECT-TYPE
			SYNTAX SEQUENCE OF SleGponOnuPMStatsDetailUniEthFrameUpEntry
			MAX-ACCESS not-accessible
			STATUS current
			DESCRIPTION
				"sleGponOnuPMStatsDetailUniEthFrameUpTable"
			::= { sleGponOnuPMStatisticsDetail 3 }


--   1.3.6.1.4.1.6296.101.23.7.3.3.1
-- 1.3.6.1.4.1.6296.101.23.7.3.3.1
		sleGponOnuPMStatsDetailUniEthFrameUpEntry OBJECT-TYPE
			SYNTAX SleGponOnuPMStatsDetailUniEthFrameUpEntry
			MAX-ACCESS not-accessible
			STATUS current
			DESCRIPTION
				"key: sleGponOltId, sleGponOnuId, sleGponOnuPMStatsDetailUniEthFrameUpUniPort"
			INDEX { sleGponOltId, sleGponOnuId, sleGponOnuPMStatsDetailUniEthFrameUpUniPort }
			::= { sleGponOnuPMStatsDetailUniEthFrameUpTable 1 }


		SleGponOnuPMStatsDetailUniEthFrameUpEntry ::=
			SEQUENCE {
				sleGponOnuPMStatsDetailUniEthFrameUpUniPort
					INTEGER,
				sleGponOnuPMStatsDetailUniEthFrameUpPre15mDropEvents
					Counter64,
				sleGponOnuPMStatsDetailUniEthFrameUpPre15mOctets
					Counter64,
				sleGponOnuPMStatsDetailUniEthFrameUpPre15mPackets
					Counter64,
				sleGponOnuPMStatsDetailUniEthFrameUpPre15mBcastPackets
					Counter64,
				sleGponOnuPMStatsDetailUniEthFrameUpPre15mMcastPackets
					Counter64,
				sleGponOnuPMStatsDetailUniEthFrameUpPre15mUcastPackets
					Counter64,
				sleGponOnuPMStatsDetailUniEthFrameUpPre15mCRCErroredPackets
					Counter64,
				sleGponOnuPMStatsDetailUniEthFrameUpPre15mUndersizePackets
					Counter64,
				sleGponOnuPMStatsDetailUniEthFrameUpPre15mOversizePackets
					Counter64,
				sleGponOnuPMStatsDetailUniEthFrameUpPre15mPkt64Octets
					Counter64,
				sleGponOnuPMStatsDetailUniEthFrameUpPre15mPkt65To127Octets
					Counter64,
				sleGponOnuPMStatsDetailUniEthFrameUpPre15mPkt128To255Octets
					Counter64,
				sleGponOnuPMStatsDetailUniEthFrameUpPre15mPkt256To511Octets
					Counter64,
				sleGponOnuPMStatsDetailUniEthFrameUpPre15mPkt512To1023Octets
					Counter64,
				sleGponOnuPMStatsDetailUniEthFrameUpPre15mPkt1024To1518Octets
					Counter64,
				sleGponOnuPMStatsDetailUniEthFrameUpHourDropEvents
					Counter64,
				sleGponOnuPMStatsDetailUniEthFrameUpHourOctets
					Counter64,
				sleGponOnuPMStatsDetailUniEthFrameUpHourPackets
					Counter64,
				sleGponOnuPMStatsDetailUniEthFrameUpHourBcastPackets
					Counter64,
				sleGponOnuPMStatsDetailUniEthFrameUpHourMcastPackets
					Counter64,
				sleGponOnuPMStatsDetailUniEthFrameUpHourUcastPackets
					Counter64,
				sleGponOnuPMStatsDetailUniEthFrameUpHourCRCErroredPackets
					Counter64,
				sleGponOnuPMStatsDetailUniEthFrameUpHourUndersizePackets
					Counter64,
				sleGponOnuPMStatsDetailUniEthFrameUpHourOversizePackets
					Counter64,
				sleGponOnuPMStatsDetailUniEthFrameUpHourPkt64Octets
					Counter64,
				sleGponOnuPMStatsDetailUniEthFrameUpHourPkt65To127Octets
					Counter64,
				sleGponOnuPMStatsDetailUniEthFrameUpHourPkt128To255Octets
					Counter64,
				sleGponOnuPMStatsDetailUniEthFrameUpHourPkt256To511Octets
					Counter64,
				sleGponOnuPMStatsDetailUniEthFrameUpHourPkt512To1023Octets
					Counter64,
				sleGponOnuPMStatsDetailUniEthFrameUpHourPkt1024To1518Octets
					Counter64,
				sleGponOnuPMStatsDetailUniEthFrameUpDayDropEvents
					Counter64,
				sleGponOnuPMStatsDetailUniEthFrameUpDayOctets
					Counter64,
				sleGponOnuPMStatsDetailUniEthFrameUpDayPackets
					Counter64,
				sleGponOnuPMStatsDetailUniEthFrameUpDayBcastPackets
					Counter64,
				sleGponOnuPMStatsDetailUniEthFrameUpDayMcastPackets
					Counter64,
				sleGponOnuPMStatsDetailUniEthFrameUpDayUcastPackets
					Counter64,
				sleGponOnuPMStatsDetailUniEthFrameUpDayCRCErroredPackets
					Counter64,
				sleGponOnuPMStatsDetailUniEthFrameUpDayUndersizePackets
					Counter64,
				sleGponOnuPMStatsDetailUniEthFrameUpDayOversizePackets
					Counter64,
				sleGponOnuPMStatsDetailUniEthFrameUpDayPkt64Octets
					Counter64,
				sleGponOnuPMStatsDetailUniEthFrameUpDayPkt65To127Octets
					Counter64,
				sleGponOnuPMStatsDetailUniEthFrameUpDayPkt128To255Octets
					Counter64,
				sleGponOnuPMStatsDetailUniEthFrameUpDayPkt256To511Octets
					Counter64,
				sleGponOnuPMStatsDetailUniEthFrameUpDayPkt512To1023Octets
					Counter64,
				sleGponOnuPMStatsDetailUniEthFrameUpDayPkt1024To1518Octets
					Counter64,
				sleGponOnuPMStatsDetailUniEthFrameUpTotalDropEvents
					Counter64,
				sleGponOnuPMStatsDetailUniEthFrameUpTotalOctets
					Counter64,
				sleGponOnuPMStatsDetailUniEthFrameUpTotalPackets
					Counter64,
				sleGponOnuPMStatsDetailUniEthFrameUpTotalBcastPackets
					Counter64,
				sleGponOnuPMStatsDetailUniEthFrameUpTotalMcastPackets
					Counter64,
				sleGponOnuPMStatsDetailUniEthFrameUpTotalUcastPackets
					Counter64,
				sleGponOnuPMStatsDetailUniEthFrameUpTotalCRCErroredPackets
					Counter64,
				sleGponOnuPMStatsDetailUniEthFrameUpTotalUndersizePackets
					Counter64,
				sleGponOnuPMStatsDetailUniEthFrameUpTotalOversizePackets
					Counter64,
				sleGponOnuPMStatsDetailUniEthFrameUpTotalPkt64Octets
					Counter64,
				sleGponOnuPMStatsDetailUniEthFrameUpTotalPkt65To127Octets
					Counter64,
				sleGponOnuPMStatsDetailUniEthFrameUpTotalPkt128To255Octets
					Counter64,
				sleGponOnuPMStatsDetailUniEthFrameUpTotalPkt256To511Octets
					Counter64,
				sleGponOnuPMStatsDetailUniEthFrameUpTotalPkt512To1023Octets
					Counter64,
				sleGponOnuPMStatsDetailUniEthFrameUpTotalPkt1024To1518Octets
					Counter64,
				sleGponOnuPMStatsDetailUniEthFrameUpElapsedTimeAfterClear
					TimeTicks,
				sleGponOnuPMStatsDetailUniEthFrameUpElapsedTimeAfterUpdate
					Counter64
			 }

--   1.3.6.1.4.1.6296.101.23.7.3.3.1.1
-- 1.3.6.1.4.1.6296.101.23.7.3.3.1.1
		sleGponOnuPMStatsDetailUniEthFrameUpUniPort OBJECT-TYPE
			SYNTAX INTEGER (1..65535)
			MAX-ACCESS read-only
			STATUS current
			DESCRIPTION
				"The Uni port information"
			::= { sleGponOnuPMStatsDetailUniEthFrameUpEntry 1 }


--   1.3.6.1.4.1.6296.101.23.7.3.3.1.2
-- 1.3.6.1.4.1.6296.101.23.7.3.3.1.2
		sleGponOnuPMStatsDetailUniEthFrameUpPre15mDropEvents OBJECT-TYPE
			SYNTAX Counter64
			MAX-ACCESS read-only
			STATUS current
			DESCRIPTION
				"The pre 15 minute number of events in which packets were dropped due to lack
				of resources."
			::= { sleGponOnuPMStatsDetailUniEthFrameUpEntry 2 }


--   1.3.6.1.4.1.6296.101.23.7.3.3.1.3
-- 1.3.6.1.4.1.6296.101.23.7.3.3.1.3
		sleGponOnuPMStatsDetailUniEthFrameUpPre15mOctets OBJECT-TYPE
			SYNTAX Counter64
			MAX-ACCESS read-only
			STATUS current
			DESCRIPTION
				"The pre 15 minute number of octets received"
			::= { sleGponOnuPMStatsDetailUniEthFrameUpEntry 3 }


--   1.3.6.1.4.1.6296.101.23.7.3.3.1.4
-- 1.3.6.1.4.1.6296.101.23.7.3.3.1.4
		sleGponOnuPMStatsDetailUniEthFrameUpPre15mPackets OBJECT-TYPE
			SYNTAX Counter64
			MAX-ACCESS read-only
			STATUS current
			DESCRIPTION
				"The pre 15 minute number of packets received,"
			::= { sleGponOnuPMStatsDetailUniEthFrameUpEntry 4 }


--   1.3.6.1.4.1.6296.101.23.7.3.3.1.5
-- 1.3.6.1.4.1.6296.101.23.7.3.3.1.5
		sleGponOnuPMStatsDetailUniEthFrameUpPre15mBcastPackets OBJECT-TYPE
			SYNTAX Counter64
			MAX-ACCESS read-only
			STATUS current
			DESCRIPTION
				"The pre 15 minute number of received good packets directed to the broadcast address"
			::= { sleGponOnuPMStatsDetailUniEthFrameUpEntry 5 }


--   1.3.6.1.4.1.6296.101.23.7.3.3.1.6
-- 1.3.6.1.4.1.6296.101.23.7.3.3.1.6
		sleGponOnuPMStatsDetailUniEthFrameUpPre15mMcastPackets OBJECT-TYPE
			SYNTAX Counter64
			MAX-ACCESS read-only
			STATUS current
			DESCRIPTION
				"The pre 15 minute number of received good packets directed to a multicast address."
			::= { sleGponOnuPMStatsDetailUniEthFrameUpEntry 6 }


--   1.3.6.1.4.1.6296.101.23.7.3.3.1.7
-- 1.3.6.1.4.1.6296.101.23.7.3.3.1.7
		sleGponOnuPMStatsDetailUniEthFrameUpPre15mUcastPackets OBJECT-TYPE
			SYNTAX Counter64
			MAX-ACCESS read-only
			STATUS current
			DESCRIPTION
				"The pre 15 minute number of received good packets directed to the unicast address"
			::= { sleGponOnuPMStatsDetailUniEthFrameUpEntry 7 }


--   1.3.6.1.4.1.6296.101.23.7.3.3.1.8
-- 1.3.6.1.4.1.6296.101.23.7.3.3.1.8
		sleGponOnuPMStatsDetailUniEthFrameUpPre15mCRCErroredPackets OBJECT-TYPE
			SYNTAX Counter64
			MAX-ACCESS read-only
			STATUS current
			DESCRIPTION
				"The pre 15 minute number of packets received that had a length"
			::= { sleGponOnuPMStatsDetailUniEthFrameUpEntry 8 }


--   1.3.6.1.4.1.6296.101.23.7.3.3.1.9
-- 1.3.6.1.4.1.6296.101.23.7.3.3.1.9
		sleGponOnuPMStatsDetailUniEthFrameUpPre15mUndersizePackets OBJECT-TYPE
			SYNTAX Counter64
			MAX-ACCESS read-only
			STATUS current
			DESCRIPTION
				"The pre 15 minute number of packets received that were less than 64 octets long"
			::= { sleGponOnuPMStatsDetailUniEthFrameUpEntry 9 }


--   1.3.6.1.4.1.6296.101.23.7.3.3.1.10
-- 1.3.6.1.4.1.6296.101.23.7.3.3.1.10
		sleGponOnuPMStatsDetailUniEthFrameUpPre15mOversizePackets OBJECT-TYPE
			SYNTAX Counter64
			MAX-ACCESS read-only
			STATUS current
			DESCRIPTION
				"The pre 15 minute number of packets received that were longer than 1518 octets"
			::= { sleGponOnuPMStatsDetailUniEthFrameUpEntry 10 }


--   1.3.6.1.4.1.6296.101.23.7.3.3.1.11
-- 1.3.6.1.4.1.6296.101.23.7.3.3.1.11
		sleGponOnuPMStatsDetailUniEthFrameUpPre15mPkt64Octets OBJECT-TYPE
			SYNTAX Counter64
			MAX-ACCESS read-only
			STATUS current
			DESCRIPTION
				"The pre 15 minute number of received packets (including bad packets) that were
				64 octets long,
				"
			::= { sleGponOnuPMStatsDetailUniEthFrameUpEntry 11 }


--   1.3.6.1.4.1.6296.101.23.7.3.3.1.12
-- 1.3.6.1.4.1.6296.101.23.7.3.3.1.12
		sleGponOnuPMStatsDetailUniEthFrameUpPre15mPkt65To127Octets OBJECT-TYPE
			SYNTAX Counter64
			MAX-ACCESS read-only
			STATUS current
			DESCRIPTION
				"The pre 15 minute number of received packets (including bad packets) that were
				65..127 octets long,
				"
			::= { sleGponOnuPMStatsDetailUniEthFrameUpEntry 12 }


--   1.3.6.1.4.1.6296.101.23.7.3.3.1.13
-- 1.3.6.1.4.1.6296.101.23.7.3.3.1.13
		sleGponOnuPMStatsDetailUniEthFrameUpPre15mPkt128To255Octets OBJECT-TYPE
			SYNTAX Counter64
			MAX-ACCESS read-only
			STATUS current
			DESCRIPTION
				"The pre 15 minute number of packets (including bad packets) received that were
				128..255 octets long,
				"
			::= { sleGponOnuPMStatsDetailUniEthFrameUpEntry 13 }


--   1.3.6.1.4.1.6296.101.23.7.3.3.1.14
-- 1.3.6.1.4.1.6296.101.23.7.3.3.1.14
		sleGponOnuPMStatsDetailUniEthFrameUpPre15mPkt256To511Octets OBJECT-TYPE
			SYNTAX Counter64
			MAX-ACCESS read-only
			STATUS current
			DESCRIPTION
				"The pre 15 minute number of packets (including bad packets) received that were
				256..511 octets long,
				"
			::= { sleGponOnuPMStatsDetailUniEthFrameUpEntry 14 }


--   1.3.6.1.4.1.6296.101.23.7.3.3.1.15
-- 1.3.6.1.4.1.6296.101.23.7.3.3.1.15
		sleGponOnuPMStatsDetailUniEthFrameUpPre15mPkt512To1023Octets OBJECT-TYPE
			SYNTAX Counter64
			MAX-ACCESS read-only
			STATUS current
			DESCRIPTION
				"The pre 15 minute number of packets (including bad packets) received that were
				512..1023 octets long,
				"
			::= { sleGponOnuPMStatsDetailUniEthFrameUpEntry 15 }


--   1.3.6.1.4.1.6296.101.23.7.3.3.1.16
-- 1.3.6.1.4.1.6296.101.23.7.3.3.1.16
		sleGponOnuPMStatsDetailUniEthFrameUpPre15mPkt1024To1518Octets OBJECT-TYPE
			SYNTAX Counter64
			MAX-ACCESS read-only
			STATUS current
			DESCRIPTION
				"The pre 15 minute number of packets (including bad packets) received that were
				1024..1518 octets long,
				"
			::= { sleGponOnuPMStatsDetailUniEthFrameUpEntry 16 }


--   1.3.6.1.4.1.6296.101.23.7.3.3.1.17
-- 1.3.6.1.4.1.6296.101.23.7.3.3.1.17
		sleGponOnuPMStatsDetailUniEthFrameUpHourDropEvents OBJECT-TYPE
			SYNTAX Counter64
			MAX-ACCESS read-only
			STATUS current
			DESCRIPTION
				"The hour number of events in which packets were dropped due to lack
				of resources.
				"
			::= { sleGponOnuPMStatsDetailUniEthFrameUpEntry 17 }


--   1.3.6.1.4.1.6296.101.23.7.3.3.1.18
-- 1.3.6.1.4.1.6296.101.23.7.3.3.1.18
		sleGponOnuPMStatsDetailUniEthFrameUpHourOctets OBJECT-TYPE
			SYNTAX Counter64
			MAX-ACCESS read-only
			STATUS current
			DESCRIPTION
				"The hour number of octets received"
			::= { sleGponOnuPMStatsDetailUniEthFrameUpEntry 18 }


--   1.3.6.1.4.1.6296.101.23.7.3.3.1.19
-- 1.3.6.1.4.1.6296.101.23.7.3.3.1.19
		sleGponOnuPMStatsDetailUniEthFrameUpHourPackets OBJECT-TYPE
			SYNTAX Counter64
			MAX-ACCESS read-only
			STATUS current
			DESCRIPTION
				"The hour number of packets received,"
			::= { sleGponOnuPMStatsDetailUniEthFrameUpEntry 19 }


--   1.3.6.1.4.1.6296.101.23.7.3.3.1.20
-- 1.3.6.1.4.1.6296.101.23.7.3.3.1.20
		sleGponOnuPMStatsDetailUniEthFrameUpHourBcastPackets OBJECT-TYPE
			SYNTAX Counter64
			MAX-ACCESS read-write
			STATUS current
			DESCRIPTION
				"The hour number of received good packets directed to the broadcast address"
			::= { sleGponOnuPMStatsDetailUniEthFrameUpEntry 20 }


--   1.3.6.1.4.1.6296.101.23.7.3.3.1.21
-- 1.3.6.1.4.1.6296.101.23.7.3.3.1.21
		sleGponOnuPMStatsDetailUniEthFrameUpHourMcastPackets OBJECT-TYPE
			SYNTAX Counter64
			MAX-ACCESS read-only
			STATUS current
			DESCRIPTION
				"The hour number of received good packets directed to a multicast address."
			::= { sleGponOnuPMStatsDetailUniEthFrameUpEntry 21 }


--   1.3.6.1.4.1.6296.101.23.7.3.3.1.22
-- 1.3.6.1.4.1.6296.101.23.7.3.3.1.22
		sleGponOnuPMStatsDetailUniEthFrameUpHourUcastPackets OBJECT-TYPE
			SYNTAX Counter64
			MAX-ACCESS read-only
			STATUS current
			DESCRIPTION
				"The hour number of received good packets directed to the unicast address"
			::= { sleGponOnuPMStatsDetailUniEthFrameUpEntry 22 }


--   1.3.6.1.4.1.6296.101.23.7.3.3.1.23
-- 1.3.6.1.4.1.6296.101.23.7.3.3.1.23
		sleGponOnuPMStatsDetailUniEthFrameUpHourCRCErroredPackets OBJECT-TYPE
			SYNTAX Counter64
			MAX-ACCESS read-only
			STATUS current
			DESCRIPTION
				"The hour number of packets received that had a length"
			::= { sleGponOnuPMStatsDetailUniEthFrameUpEntry 23 }


--   1.3.6.1.4.1.6296.101.23.7.3.3.1.24
-- 1.3.6.1.4.1.6296.101.23.7.3.3.1.24
		sleGponOnuPMStatsDetailUniEthFrameUpHourUndersizePackets OBJECT-TYPE
			SYNTAX Counter64
			MAX-ACCESS read-only
			STATUS current
			DESCRIPTION
				"The hour number of packets received that were less than 64 octets long"
			::= { sleGponOnuPMStatsDetailUniEthFrameUpEntry 24 }


--   1.3.6.1.4.1.6296.101.23.7.3.3.1.25
-- 1.3.6.1.4.1.6296.101.23.7.3.3.1.25
		sleGponOnuPMStatsDetailUniEthFrameUpHourOversizePackets OBJECT-TYPE
			SYNTAX Counter64
			MAX-ACCESS read-only
			STATUS current
			DESCRIPTION
				"The hour number of packets received that were longer than 1518 octets"
			::= { sleGponOnuPMStatsDetailUniEthFrameUpEntry 25 }


--   1.3.6.1.4.1.6296.101.23.7.3.3.1.26
-- 1.3.6.1.4.1.6296.101.23.7.3.3.1.26
		sleGponOnuPMStatsDetailUniEthFrameUpHourPkt64Octets OBJECT-TYPE
			SYNTAX Counter64
			MAX-ACCESS read-only
			STATUS current
			DESCRIPTION
				"The hour number of received packets (including bad packets) that were
				64 octets long,
				"
			::= { sleGponOnuPMStatsDetailUniEthFrameUpEntry 26 }


--   1.3.6.1.4.1.6296.101.23.7.3.3.1.27
-- 1.3.6.1.4.1.6296.101.23.7.3.3.1.27
		sleGponOnuPMStatsDetailUniEthFrameUpHourPkt65To127Octets OBJECT-TYPE
			SYNTAX Counter64
			MAX-ACCESS read-only
			STATUS current
			DESCRIPTION
				"The hour number of received packets (including bad packets) that were
				65..127 octets long,
				"
			::= { sleGponOnuPMStatsDetailUniEthFrameUpEntry 27 }


--   1.3.6.1.4.1.6296.101.23.7.3.3.1.28
-- 1.3.6.1.4.1.6296.101.23.7.3.3.1.28
		sleGponOnuPMStatsDetailUniEthFrameUpHourPkt128To255Octets OBJECT-TYPE
			SYNTAX Counter64
			MAX-ACCESS read-write
			STATUS current
			DESCRIPTION
				"The hour number of packets (including bad packets) received that were
				128..255 octets long,
				"
			::= { sleGponOnuPMStatsDetailUniEthFrameUpEntry 28 }


--   1.3.6.1.4.1.6296.101.23.7.3.3.1.29
-- 1.3.6.1.4.1.6296.101.23.7.3.3.1.29
		sleGponOnuPMStatsDetailUniEthFrameUpHourPkt256To511Octets OBJECT-TYPE
			SYNTAX Counter64
			MAX-ACCESS read-only
			STATUS current
			DESCRIPTION
				"The hour number of packets (including bad packets) received that were
				256..511 octets long,
				"
			::= { sleGponOnuPMStatsDetailUniEthFrameUpEntry 29 }


--   1.3.6.1.4.1.6296.101.23.7.3.3.1.30
-- 1.3.6.1.4.1.6296.101.23.7.3.3.1.30
		sleGponOnuPMStatsDetailUniEthFrameUpHourPkt512To1023Octets OBJECT-TYPE
			SYNTAX Counter64
			MAX-ACCESS read-write
			STATUS current
			DESCRIPTION
				"The hour number of packets (including bad packets) received that were
				512..1023 octets long,
				"
			::= { sleGponOnuPMStatsDetailUniEthFrameUpEntry 30 }


--   1.3.6.1.4.1.6296.101.23.7.3.3.1.31
-- 1.3.6.1.4.1.6296.101.23.7.3.3.1.31
		sleGponOnuPMStatsDetailUniEthFrameUpHourPkt1024To1518Octets OBJECT-TYPE
			SYNTAX Counter64
			MAX-ACCESS read-only
			STATUS current
			DESCRIPTION
				"The hour number of packets (including bad packets) received that were
				1024..1518 octets long,

				"
			::= { sleGponOnuPMStatsDetailUniEthFrameUpEntry 31 }


--   1.3.6.1.4.1.6296.101.23.7.3.3.1.32
-- 1.3.6.1.4.1.6296.101.23.7.3.3.1.32
		sleGponOnuPMStatsDetailUniEthFrameUpDayDropEvents OBJECT-TYPE
			SYNTAX Counter64
			MAX-ACCESS read-only
			STATUS current
			DESCRIPTION
				"The day number of events in which packets were dropped due to lack of resources."
			::= { sleGponOnuPMStatsDetailUniEthFrameUpEntry 32 }


--   1.3.6.1.4.1.6296.101.23.7.3.3.1.33
-- 1.3.6.1.4.1.6296.101.23.7.3.3.1.33
		sleGponOnuPMStatsDetailUniEthFrameUpDayOctets OBJECT-TYPE
			SYNTAX Counter64
			MAX-ACCESS read-only
			STATUS current
			DESCRIPTION
				"The day number of octets received"
			::= { sleGponOnuPMStatsDetailUniEthFrameUpEntry 33 }


--   1.3.6.1.4.1.6296.101.23.7.3.3.1.34
-- 1.3.6.1.4.1.6296.101.23.7.3.3.1.34
		sleGponOnuPMStatsDetailUniEthFrameUpDayPackets OBJECT-TYPE
			SYNTAX Counter64
			MAX-ACCESS read-only
			STATUS current
			DESCRIPTION
				"The day number of packets received,"
			::= { sleGponOnuPMStatsDetailUniEthFrameUpEntry 34 }


--   1.3.6.1.4.1.6296.101.23.7.3.3.1.35
-- 1.3.6.1.4.1.6296.101.23.7.3.3.1.35
		sleGponOnuPMStatsDetailUniEthFrameUpDayBcastPackets OBJECT-TYPE
			SYNTAX Counter64
			MAX-ACCESS read-write
			STATUS current
			DESCRIPTION
				"The day number of received good packets directed to the broadcast address"
			::= { sleGponOnuPMStatsDetailUniEthFrameUpEntry 35 }


--   1.3.6.1.4.1.6296.101.23.7.3.3.1.36
-- 1.3.6.1.4.1.6296.101.23.7.3.3.1.36
		sleGponOnuPMStatsDetailUniEthFrameUpDayMcastPackets OBJECT-TYPE
			SYNTAX Counter64
			MAX-ACCESS read-only
			STATUS current
			DESCRIPTION
				"The day number of received good packets directed to a multicast address."
			::= { sleGponOnuPMStatsDetailUniEthFrameUpEntry 36 }


--   1.3.6.1.4.1.6296.101.23.7.3.3.1.37
-- 1.3.6.1.4.1.6296.101.23.7.3.3.1.37
		sleGponOnuPMStatsDetailUniEthFrameUpDayUcastPackets OBJECT-TYPE
			SYNTAX Counter64
			MAX-ACCESS read-only
			STATUS current
			DESCRIPTION
				"The day number of received good packets directed to the unicast address"
			::= { sleGponOnuPMStatsDetailUniEthFrameUpEntry 37 }


--   1.3.6.1.4.1.6296.101.23.7.3.3.1.38
-- 1.3.6.1.4.1.6296.101.23.7.3.3.1.38
		sleGponOnuPMStatsDetailUniEthFrameUpDayCRCErroredPackets OBJECT-TYPE
			SYNTAX Counter64
			MAX-ACCESS read-only
			STATUS current
			DESCRIPTION
				"The day number of packets received that had a length"
			::= { sleGponOnuPMStatsDetailUniEthFrameUpEntry 38 }


--   1.3.6.1.4.1.6296.101.23.7.3.3.1.39
-- 1.3.6.1.4.1.6296.101.23.7.3.3.1.39
		sleGponOnuPMStatsDetailUniEthFrameUpDayUndersizePackets OBJECT-TYPE
			SYNTAX Counter64
			MAX-ACCESS read-only
			STATUS current
			DESCRIPTION
				"The day number of packets received that were less than 64 octets long"
			::= { sleGponOnuPMStatsDetailUniEthFrameUpEntry 39 }


--   1.3.6.1.4.1.6296.101.23.7.3.3.1.40
-- 1.3.6.1.4.1.6296.101.23.7.3.3.1.40
		sleGponOnuPMStatsDetailUniEthFrameUpDayOversizePackets OBJECT-TYPE
			SYNTAX Counter64
			MAX-ACCESS read-only
			STATUS current
			DESCRIPTION
				"The day number of packets received that were longer than 1518 octets"
			::= { sleGponOnuPMStatsDetailUniEthFrameUpEntry 40 }


--   1.3.6.1.4.1.6296.101.23.7.3.3.1.41
-- 1.3.6.1.4.1.6296.101.23.7.3.3.1.41
		sleGponOnuPMStatsDetailUniEthFrameUpDayPkt64Octets OBJECT-TYPE
			SYNTAX Counter64
			MAX-ACCESS read-only
			STATUS current
			DESCRIPTION
				"The day number of received packets (including bad packets) that were
				64 octets long,
				"
			::= { sleGponOnuPMStatsDetailUniEthFrameUpEntry 41 }


--   1.3.6.1.4.1.6296.101.23.7.3.3.1.42
-- 1.3.6.1.4.1.6296.101.23.7.3.3.1.42
		sleGponOnuPMStatsDetailUniEthFrameUpDayPkt65To127Octets OBJECT-TYPE
			SYNTAX Counter64
			MAX-ACCESS read-only
			STATUS current
			DESCRIPTION
				"The day number of received packets (including bad packets) that were
				65..127 octets long,
				"
			::= { sleGponOnuPMStatsDetailUniEthFrameUpEntry 42 }


--   1.3.6.1.4.1.6296.101.23.7.3.3.1.43
-- 1.3.6.1.4.1.6296.101.23.7.3.3.1.43
		sleGponOnuPMStatsDetailUniEthFrameUpDayPkt128To255Octets OBJECT-TYPE
			SYNTAX Counter64
			MAX-ACCESS read-write
			STATUS current
			DESCRIPTION
				"The day number of received packets (including bad packets) that were
				128..255 octets long,
				"
			::= { sleGponOnuPMStatsDetailUniEthFrameUpEntry 43 }


--   1.3.6.1.4.1.6296.101.23.7.3.3.1.44
-- 1.3.6.1.4.1.6296.101.23.7.3.3.1.44
		sleGponOnuPMStatsDetailUniEthFrameUpDayPkt256To511Octets OBJECT-TYPE
			SYNTAX Counter64
			MAX-ACCESS read-only
			STATUS current
			DESCRIPTION
				"The day number of received packets (including bad packets) that were
				256..511 octets long,
				"
			::= { sleGponOnuPMStatsDetailUniEthFrameUpEntry 44 }


--   1.3.6.1.4.1.6296.101.23.7.3.3.1.45
-- 1.3.6.1.4.1.6296.101.23.7.3.3.1.45
		sleGponOnuPMStatsDetailUniEthFrameUpDayPkt512To1023Octets OBJECT-TYPE
			SYNTAX Counter64
			MAX-ACCESS read-write
			STATUS current
			DESCRIPTION
				"The day number of packets (including bad packets) received that were
				512..1023 octets long,
				"
			::= { sleGponOnuPMStatsDetailUniEthFrameUpEntry 45 }


--   1.3.6.1.4.1.6296.101.23.7.3.3.1.46
-- 1.3.6.1.4.1.6296.101.23.7.3.3.1.46
		sleGponOnuPMStatsDetailUniEthFrameUpDayPkt1024To1518Octets OBJECT-TYPE
			SYNTAX Counter64
			MAX-ACCESS read-only
			STATUS current
			DESCRIPTION
				"The day number of packets (including bad packets) received that were
				1024..1518 octets long,
				"
			::= { sleGponOnuPMStatsDetailUniEthFrameUpEntry 46 }


--   1.3.6.1.4.1.6296.101.23.7.3.3.1.47
-- 1.3.6.1.4.1.6296.101.23.7.3.3.1.47
		sleGponOnuPMStatsDetailUniEthFrameUpTotalDropEvents OBJECT-TYPE
			SYNTAX Counter64
			MAX-ACCESS read-only
			STATUS current
			DESCRIPTION
				"The total number of events in which packets were dropped due to lack
				of resources."
			::= { sleGponOnuPMStatsDetailUniEthFrameUpEntry 47 }


--   1.3.6.1.4.1.6296.101.23.7.3.3.1.48
-- 1.3.6.1.4.1.6296.101.23.7.3.3.1.48
		sleGponOnuPMStatsDetailUniEthFrameUpTotalOctets OBJECT-TYPE
			SYNTAX Counter64
			MAX-ACCESS read-only
			STATUS current
			DESCRIPTION
				"The total number of octets received"
			::= { sleGponOnuPMStatsDetailUniEthFrameUpEntry 48 }


--   1.3.6.1.4.1.6296.101.23.7.3.3.1.49
-- 1.3.6.1.4.1.6296.101.23.7.3.3.1.49
		sleGponOnuPMStatsDetailUniEthFrameUpTotalPackets OBJECT-TYPE
			SYNTAX Counter64
			MAX-ACCESS read-only
			STATUS current
			DESCRIPTION
				"The total number of packets received,"
			::= { sleGponOnuPMStatsDetailUniEthFrameUpEntry 49 }


--   1.3.6.1.4.1.6296.101.23.7.3.3.1.50
-- 1.3.6.1.4.1.6296.101.23.7.3.3.1.50
		sleGponOnuPMStatsDetailUniEthFrameUpTotalBcastPackets OBJECT-TYPE
			SYNTAX Counter64
			MAX-ACCESS read-write
			STATUS current
			DESCRIPTION
				"The total number of received good packets directed to a broadcast  address."
			::= { sleGponOnuPMStatsDetailUniEthFrameUpEntry 50 }


--   1.3.6.1.4.1.6296.101.23.7.3.3.1.51
-- 1.3.6.1.4.1.6296.101.23.7.3.3.1.51
		sleGponOnuPMStatsDetailUniEthFrameUpTotalMcastPackets OBJECT-TYPE
			SYNTAX Counter64
			MAX-ACCESS read-only
			STATUS current
			DESCRIPTION
				"The total number of received good packets directed to a multicast address."
			::= { sleGponOnuPMStatsDetailUniEthFrameUpEntry 51 }


--   1.3.6.1.4.1.6296.101.23.7.3.3.1.52
-- 1.3.6.1.4.1.6296.101.23.7.3.3.1.52
		sleGponOnuPMStatsDetailUniEthFrameUpTotalUcastPackets OBJECT-TYPE
			SYNTAX Counter64
			MAX-ACCESS read-only
			STATUS current
			DESCRIPTION
				"The total number of received good packets directed to a multicast address."
			::= { sleGponOnuPMStatsDetailUniEthFrameUpEntry 52 }


--   1.3.6.1.4.1.6296.101.23.7.3.3.1.53
-- 1.3.6.1.4.1.6296.101.23.7.3.3.1.53
		sleGponOnuPMStatsDetailUniEthFrameUpTotalCRCErroredPackets OBJECT-TYPE
			SYNTAX Counter64
			MAX-ACCESS read-only
			STATUS current
			DESCRIPTION
				"The total number of packets received that had a length"
			::= { sleGponOnuPMStatsDetailUniEthFrameUpEntry 53 }


--   1.3.6.1.4.1.6296.101.23.7.3.3.1.54
-- 1.3.6.1.4.1.6296.101.23.7.3.3.1.54
		sleGponOnuPMStatsDetailUniEthFrameUpTotalUndersizePackets OBJECT-TYPE
			SYNTAX Counter64
			MAX-ACCESS read-only
			STATUS current
			DESCRIPTION
				"The total number of packets received that were less than 64 octets long"
			::= { sleGponOnuPMStatsDetailUniEthFrameUpEntry 54 }


--   1.3.6.1.4.1.6296.101.23.7.3.3.1.55
-- 1.3.6.1.4.1.6296.101.23.7.3.3.1.55
		sleGponOnuPMStatsDetailUniEthFrameUpTotalOversizePackets OBJECT-TYPE
			SYNTAX Counter64
			MAX-ACCESS read-only
			STATUS current
			DESCRIPTION
				"The total number of packets received that were longer than 1518 octets"
			::= { sleGponOnuPMStatsDetailUniEthFrameUpEntry 55 }


--   1.3.6.1.4.1.6296.101.23.7.3.3.1.56
-- 1.3.6.1.4.1.6296.101.23.7.3.3.1.56
		sleGponOnuPMStatsDetailUniEthFrameUpTotalPkt64Octets OBJECT-TYPE
			SYNTAX Counter64
			MAX-ACCESS read-only
			STATUS current
			DESCRIPTION
				"The total number of received packets (including bad packets) that were
				64 octets long,"
			::= { sleGponOnuPMStatsDetailUniEthFrameUpEntry 56 }


--   1.3.6.1.4.1.6296.101.23.7.3.3.1.57
-- 1.3.6.1.4.1.6296.101.23.7.3.3.1.57
		sleGponOnuPMStatsDetailUniEthFrameUpTotalPkt65To127Octets OBJECT-TYPE
			SYNTAX Counter64
			MAX-ACCESS read-only
			STATUS current
			DESCRIPTION
				"The total number of received packets (including bad packets) that were
				65..127 octets long,"
			::= { sleGponOnuPMStatsDetailUniEthFrameUpEntry 57 }


--   1.3.6.1.4.1.6296.101.23.7.3.3.1.58
-- 1.3.6.1.4.1.6296.101.23.7.3.3.1.58
		sleGponOnuPMStatsDetailUniEthFrameUpTotalPkt128To255Octets OBJECT-TYPE
			SYNTAX Counter64
			MAX-ACCESS read-write
			STATUS current
			DESCRIPTION
				"The total number of packets (including bad packets) received that were
				128..255 octets long,"
			::= { sleGponOnuPMStatsDetailUniEthFrameUpEntry 58 }


--   1.3.6.1.4.1.6296.101.23.7.3.3.1.59
-- 1.3.6.1.4.1.6296.101.23.7.3.3.1.59
		sleGponOnuPMStatsDetailUniEthFrameUpTotalPkt256To511Octets OBJECT-TYPE
			SYNTAX Counter64
			MAX-ACCESS read-only
			STATUS current
			DESCRIPTION
				"The total number of packets (including bad packets) received that were
				256..511 octets long,"
			::= { sleGponOnuPMStatsDetailUniEthFrameUpEntry 59 }


--   1.3.6.1.4.1.6296.101.23.7.3.3.1.60
-- 1.3.6.1.4.1.6296.101.23.7.3.3.1.60
		sleGponOnuPMStatsDetailUniEthFrameUpTotalPkt512To1023Octets OBJECT-TYPE
			SYNTAX Counter64
			MAX-ACCESS read-write
			STATUS current
			DESCRIPTION
				"The total number of packets (including bad packets) received that were
				512..1023 octets long,"
			::= { sleGponOnuPMStatsDetailUniEthFrameUpEntry 60 }


--   1.3.6.1.4.1.6296.101.23.7.3.3.1.61
-- 1.3.6.1.4.1.6296.101.23.7.3.3.1.61
		sleGponOnuPMStatsDetailUniEthFrameUpTotalPkt1024To1518Octets OBJECT-TYPE
			SYNTAX Counter64
			MAX-ACCESS read-only
			STATUS current
			DESCRIPTION
				"The total number of packets (including bad packets) received that were
				1024..1518 octets long,"
			::= { sleGponOnuPMStatsDetailUniEthFrameUpEntry 61 }


--   1.3.6.1.4.1.6296.101.23.7.3.3.1.62
-- 1.3.6.1.4.1.6296.101.23.7.3.3.1.62
		sleGponOnuPMStatsDetailUniEthFrameUpElapsedTimeAfterClear OBJECT-TYPE
			SYNTAX TimeTicks
			MAX-ACCESS read-only
			STATUS current
			DESCRIPTION
				"The total number of packets for elapsed time after clear"
			::= { sleGponOnuPMStatsDetailUniEthFrameUpEntry 62 }


--   1.3.6.1.4.1.6296.101.23.7.3.3.1.63
-- 1.3.6.1.4.1.6296.101.23.7.3.3.1.63
		sleGponOnuPMStatsDetailUniEthFrameUpElapsedTimeAfterUpdate OBJECT-TYPE
			SYNTAX Counter64
			MAX-ACCESS read-only
			STATUS current
			DESCRIPTION
				"The total number of packets for elapsed time after update"
			::= { sleGponOnuPMStatsDetailUniEthFrameUpEntry 63 }


--   1.3.6.1.4.1.6296.101.23.7.3.4
-- 1.3.6.1.4.1.6296.101.23.7.3.4
		sleGponOnuPMStatsDetailUniEthFrameDownTable OBJECT-TYPE
			SYNTAX SEQUENCE OF SleGponOnuPMStatsDetailUniEthFrameDownEntry
			MAX-ACCESS not-accessible
			STATUS current
			DESCRIPTION
				"sleGponOnuPMStatsDetailUniEthFrameDownTable"
			::= { sleGponOnuPMStatisticsDetail 4 }


--   1.3.6.1.4.1.6296.101.23.7.3.4.1
-- 1.3.6.1.4.1.6296.101.23.7.3.4.1
		sleGponOnuPMStatsDetailUniEthFrameDownEntry OBJECT-TYPE
			SYNTAX SleGponOnuPMStatsDetailUniEthFrameDownEntry
			MAX-ACCESS not-accessible
			STATUS current
			DESCRIPTION
				"key: sleGponOltId, sleGponOnuId, sleGponOnuPMStatsDetailUniEthFrameUpUniPort"
			INDEX { sleGponOltId, sleGponOnuId, sleGponOnuPMStatsDetailUniEthFrameUpUniPort }
			::= { sleGponOnuPMStatsDetailUniEthFrameDownTable 1 }


		SleGponOnuPMStatsDetailUniEthFrameDownEntry ::=
			SEQUENCE {
				sleGponOnuPMStatsDetailUniEthFrameDownUniPort
					Integer32,
				sleGponOnuPMStatsDetailUniEthFrameDownPre15mDropEvents
					Counter64,
				sleGponOnuPMStatsDetailUniEthFrameDownPre15mOctets
					Counter64,
				sleGponOnuPMStatsDetailUniEthFrameDownPre15mPackets
					Counter64,
				sleGponOnuPMStatsDetailUniEthFrameDownPre15mBcastPackets
					Counter64,
				sleGponOnuPMStatsDetailUniEthFrameDownPre15mMcastPackets
					Counter64,
				sleGponOnuPMStatsDetailUniEthFrameDownPre15mUcastPackets
					Counter64,
				sleGponOnuPMStatsDetailUniEthFrameDownPre15mCRCErroredPackets
					Counter64,
				sleGponOnuPMStatsDetailUniEthFrameDownPre15mUndersizePackets
					Counter64,
				sleGponOnuPMStatsDetailUniEthFrameDownPre15mOversizePackets
					Counter64,
				sleGponOnuPMStatsDetailUniEthFrameDownPre15mPkt64Octets
					Counter64,
				sleGponOnuPMStatsDetailUniEthFrameDownPre15mPkt65To127Octets
					Counter64,
				sleGponOnuPMStatsDetailUniEthFrameDownPre15mPkt128To255Octets
					Counter64,
				sleGponOnuPMStatsDetailUniEthFrameDownPre15mPkt256To511Octets
					Counter64,
				sleGponOnuPMStatsDetailUniEthFrameDownPre15mPkt512To1023Octets
					Counter64,
				sleGponOnuPMStatsDetailUniEthFrameDownPre15mPkt1024To1518Octets
					Counter64,
				sleGponOnuPMStatsDetailUniEthFrameDownHourDropEvents
					Counter64,
				sleGponOnuPMStatsDetailUniEthFrameDownHourOctets
					Counter64,
				sleGponOnuPMStatsDetailUniEthFrameDownHourPackets
					Counter64,
				sleGponOnuPMStatsDetailUniEthFrameDownHourBcastPackets
					Counter64,
				sleGponOnuPMStatsDetailUniEthFrameDownHourMcastPackets
					Counter64,
				sleGponOnuPMStatsDetailUniEthFrameDownHourUcastPackets
					Counter64,
				sleGponOnuPMStatsDetailUniEthFrameDownHourCRCErroredPackets
					Counter64,
				sleGponOnuPMStatsDetailUniEthFrameDownHourUndersizePackets
					Counter64,
				sleGponOnuPMStatsDetailUniEthFrameDownHourOversizePackets
					Counter64,
				sleGponOnuPMStatsDetailUniEthFrameDownHourPkt64Octets
					Counter64,
				sleGponOnuPMStatsDetailUniEthFrameDownHourPkt65To127Octets
					Counter64,
				sleGponOnuPMStatsDetailUniEthFrameDownHourPkt128To255Octets
					Counter64,
				sleGponOnuPMStatsDetailUniEthFrameDownHourPkt256To511Octets
					Counter64,
				sleGponOnuPMStatsDetailUniEthFrameDownHourPkt512To1023Octets
					Counter64,
				sleGponOnuPMStatsDetailUniEthFrameDownHourPkt1024To1518Octets
					Counter64,
				sleGponOnuPMStatsDetailUniEthFrameDownDayDropEvents
					Counter64,
				sleGponOnuPMStatsDetailUniEthFrameDownDayOctets
					Counter64,
				sleGponOnuPMStatsDetailUniEthFrameDownDayPackets
					Counter64,
				sleGponOnuPMStatsDetailUniEthFrameDownDayBcastPackets
					Counter64,
				sleGponOnuPMStatsDetailUniEthFrameDownDayMcastPackets
					Counter64,
				sleGponOnuPMStatsDetailUniEthFrameDownDayUcastPackets
					Counter64,
				sleGponOnuPMStatsDetailUniEthFrameDownDayCRCErroredPackets
					Counter64,
				sleGponOnuPMStatsDetailUniEthFrameDownDayUndersizePackets
					Counter64,
				sleGponOnuPMStatsDetailUniEthFrameDownDayOversizePackets
					Counter64,
				sleGponOnuPMStatsDetailUniEthFrameDownDayPkt64Octets
					Counter64,
				sleGponOnuPMStatsDetailUniEthFrameDownDayPkt65To127Octets
					Counter64,
				sleGponOnuPMStatsDetailUniEthFrameDownDayPkt128To255Octets
					Counter64,
				sleGponOnuPMStatsDetailUniEthFrameDownDayPkt256To511Octets
					Counter64,
				sleGponOnuPMStatsDetailUniEthFrameDownDayPkt512To1023Octets
					Counter64,
				sleGponOnuPMStatsDetailUniEthFrameDownDayPkt1024To1518Octets
					Counter64,
				sleGponOnuPMStatsDetailUniEthFrameDownTotalDropEvents
					Counter64,
				sleGponOnuPMStatsDetailUniEthFrameDownTotalOctets
					Counter64,
				sleGponOnuPMStatsDetailUniEthFrameDownTotalPackets
					Counter64,
				sleGponOnuPMStatsDetailUniEthFrameDownTotalBcastPackets
					Counter64,
				sleGponOnuPMStatsDetailUniEthFrameDownTotalMcastPackets
					Counter64,
				sleGponOnuPMStatsDetailUniEthFrameDownTotalUcastPackets
					Counter64,
				sleGponOnuPMStatsDetailUniEthFrameDownTotalCRCErroredPackets
					Counter64,
				sleGponOnuPMStatsDetailUniEthFrameDownTotalUndersizePackets
					Counter64,
				sleGponOnuPMStatsDetailUniEthFrameDownTotalOversizePackets
					Counter64,
				sleGponOnuPMStatsDetailUniEthFrameDownTotalPkt64Octets
					Counter64,
				sleGponOnuPMStatsDetailUniEthFrameDownTotalPkt65To127Octets
					Counter64,
				sleGponOnuPMStatsDetailUniEthFrameDownTotalPkt128To255Octets
					Counter64,
				sleGponOnuPMStatsDetailUniEthFrameDownTotalPkt256To511Octets
					Counter64,
				sleGponOnuPMStatsDetailUniEthFrameDownTotalPkt512To1023Octets
					Counter64,
				sleGponOnuPMStatsDetailUniEthFrameDownTotalPkt1024To1518Octets
					Counter64,
				sleGponOnuPMStatsDetailUniEthFrameDownElapsedTimeAfterClear
					TimeTicks,
				sleGponOnuPMStatsDetailUniEthFrameDownElapsedTimeAfterUpdate
					Counter64
			 }

--   1.3.6.1.4.1.6296.101.23.7.3.4.1.1
-- 1.3.6.1.4.1.6296.101.23.7.3.4.1.1
		sleGponOnuPMStatsDetailUniEthFrameDownUniPort OBJECT-TYPE
			SYNTAX Integer32
			MAX-ACCESS read-only
			STATUS current
			DESCRIPTION
				"sleGponOltId, sleGponOnuId, sleGponOnuPMStatsDetailUniEthFrameUpUniPort"
			::= { sleGponOnuPMStatsDetailUniEthFrameDownEntry 1 }


--   1.3.6.1.4.1.6296.101.23.7.3.4.1.2
-- 1.3.6.1.4.1.6296.101.23.7.3.4.1.2
		sleGponOnuPMStatsDetailUniEthFrameDownPre15mDropEvents OBJECT-TYPE
			SYNTAX Counter64
			MAX-ACCESS read-only
			STATUS current
			DESCRIPTION
				"The pre 15 minute number of events in which packets were dropped due to lack of resources.
				"
			::= { sleGponOnuPMStatsDetailUniEthFrameDownEntry 2 }


--   1.3.6.1.4.1.6296.101.23.7.3.4.1.3
-- 1.3.6.1.4.1.6296.101.23.7.3.4.1.3
		sleGponOnuPMStatsDetailUniEthFrameDownPre15mOctets OBJECT-TYPE
			SYNTAX Counter64
			MAX-ACCESS read-only
			STATUS current
			DESCRIPTION
				"The pre 15 minute number of octets received"
			::= { sleGponOnuPMStatsDetailUniEthFrameDownEntry 3 }


--   1.3.6.1.4.1.6296.101.23.7.3.4.1.4
-- 1.3.6.1.4.1.6296.101.23.7.3.4.1.4
		sleGponOnuPMStatsDetailUniEthFrameDownPre15mPackets OBJECT-TYPE
			SYNTAX Counter64
			MAX-ACCESS read-only
			STATUS current
			DESCRIPTION
				"The pre 15 minute number of packets received,"
			::= { sleGponOnuPMStatsDetailUniEthFrameDownEntry 4 }


--   1.3.6.1.4.1.6296.101.23.7.3.4.1.5
-- 1.3.6.1.4.1.6296.101.23.7.3.4.1.5
		sleGponOnuPMStatsDetailUniEthFrameDownPre15mBcastPackets OBJECT-TYPE
			SYNTAX Counter64
			MAX-ACCESS read-only
			STATUS current
			DESCRIPTION
				"The pre 15 minute number of received good packets directed to the broadcast address"
			::= { sleGponOnuPMStatsDetailUniEthFrameDownEntry 5 }


--   1.3.6.1.4.1.6296.101.23.7.3.4.1.6
-- 1.3.6.1.4.1.6296.101.23.7.3.4.1.6
		sleGponOnuPMStatsDetailUniEthFrameDownPre15mMcastPackets OBJECT-TYPE
			SYNTAX Counter64
			MAX-ACCESS read-only
			STATUS current
			DESCRIPTION
				"The pre 15 minute number of received good packets directed to a multicast address."
			::= { sleGponOnuPMStatsDetailUniEthFrameDownEntry 6 }


--   1.3.6.1.4.1.6296.101.23.7.3.4.1.7
-- 1.3.6.1.4.1.6296.101.23.7.3.4.1.7
		sleGponOnuPMStatsDetailUniEthFrameDownPre15mUcastPackets OBJECT-TYPE
			SYNTAX Counter64
			MAX-ACCESS read-only
			STATUS current
			DESCRIPTION
				"The pre 15 minute number of received good packets directed to the unicast address"
			::= { sleGponOnuPMStatsDetailUniEthFrameDownEntry 7 }


--   1.3.6.1.4.1.6296.101.23.7.3.4.1.8
-- 1.3.6.1.4.1.6296.101.23.7.3.4.1.8
		sleGponOnuPMStatsDetailUniEthFrameDownPre15mCRCErroredPackets OBJECT-TYPE
			SYNTAX Counter64
			MAX-ACCESS read-only
			STATUS current
			DESCRIPTION
				"The pre 15 minute number of packets received that had a length"
			::= { sleGponOnuPMStatsDetailUniEthFrameDownEntry 8 }


--   1.3.6.1.4.1.6296.101.23.7.3.4.1.9
-- 1.3.6.1.4.1.6296.101.23.7.3.4.1.9
		sleGponOnuPMStatsDetailUniEthFrameDownPre15mUndersizePackets OBJECT-TYPE
			SYNTAX Counter64
			MAX-ACCESS read-only
			STATUS current
			DESCRIPTION
				"The pre 15 minute number of packets received that were less than 64 octets long"
			::= { sleGponOnuPMStatsDetailUniEthFrameDownEntry 9 }


--   1.3.6.1.4.1.6296.101.23.7.3.4.1.10
-- 1.3.6.1.4.1.6296.101.23.7.3.4.1.10
		sleGponOnuPMStatsDetailUniEthFrameDownPre15mOversizePackets OBJECT-TYPE
			SYNTAX Counter64
			MAX-ACCESS read-only
			STATUS current
			DESCRIPTION
				"The pre 15 minute number of packets received that were longer than 1518 octets"
			::= { sleGponOnuPMStatsDetailUniEthFrameDownEntry 10 }


--   1.3.6.1.4.1.6296.101.23.7.3.4.1.11
-- 1.3.6.1.4.1.6296.101.23.7.3.4.1.11
		sleGponOnuPMStatsDetailUniEthFrameDownPre15mPkt64Octets OBJECT-TYPE
			SYNTAX Counter64
			MAX-ACCESS read-only
			STATUS current
			DESCRIPTION
				"The pre 15 minute number of received packets (including bad packets) that were
				64 octets long,"
			::= { sleGponOnuPMStatsDetailUniEthFrameDownEntry 11 }


--   1.3.6.1.4.1.6296.101.23.7.3.4.1.12
-- 1.3.6.1.4.1.6296.101.23.7.3.4.1.12
		sleGponOnuPMStatsDetailUniEthFrameDownPre15mPkt65To127Octets OBJECT-TYPE
			SYNTAX Counter64
			MAX-ACCESS read-only
			STATUS current
			DESCRIPTION
				"The pre 15 minute number of received packets (including bad packets) that were
				65..127 octets long,"
			::= { sleGponOnuPMStatsDetailUniEthFrameDownEntry 12 }


--   1.3.6.1.4.1.6296.101.23.7.3.4.1.13
-- 1.3.6.1.4.1.6296.101.23.7.3.4.1.13
		sleGponOnuPMStatsDetailUniEthFrameDownPre15mPkt128To255Octets OBJECT-TYPE
			SYNTAX Counter64
			MAX-ACCESS read-only
			STATUS current
			DESCRIPTION
				"The pre 15 minute number of packets (including bad packets) received that were
				128..255 octets long,"
			::= { sleGponOnuPMStatsDetailUniEthFrameDownEntry 13 }


--   1.3.6.1.4.1.6296.101.23.7.3.4.1.14
-- 1.3.6.1.4.1.6296.101.23.7.3.4.1.14
		sleGponOnuPMStatsDetailUniEthFrameDownPre15mPkt256To511Octets OBJECT-TYPE
			SYNTAX Counter64
			MAX-ACCESS read-only
			STATUS current
			DESCRIPTION
				"The pre 15 minute number of packets (including bad packets) received that were
				256..511 octets long,"
			::= { sleGponOnuPMStatsDetailUniEthFrameDownEntry 14 }


--   1.3.6.1.4.1.6296.101.23.7.3.4.1.15
-- 1.3.6.1.4.1.6296.101.23.7.3.4.1.15
		sleGponOnuPMStatsDetailUniEthFrameDownPre15mPkt512To1023Octets OBJECT-TYPE
			SYNTAX Counter64
			MAX-ACCESS read-only
			STATUS current
			DESCRIPTION
				"The pre 15 minute number of packets (including bad packets) received that were
				512..1023 octets long,"
			::= { sleGponOnuPMStatsDetailUniEthFrameDownEntry 15 }


--   1.3.6.1.4.1.6296.101.23.7.3.4.1.16
-- 1.3.6.1.4.1.6296.101.23.7.3.4.1.16
		sleGponOnuPMStatsDetailUniEthFrameDownPre15mPkt1024To1518Octets OBJECT-TYPE
			SYNTAX Counter64
			MAX-ACCESS read-only
			STATUS current
			DESCRIPTION
				"The pre 15 minute number of packets (including bad packets) received that were
				1024..1518 octets long,"
			::= { sleGponOnuPMStatsDetailUniEthFrameDownEntry 16 }


--   1.3.6.1.4.1.6296.101.23.7.3.4.1.17
-- 1.3.6.1.4.1.6296.101.23.7.3.4.1.17
		sleGponOnuPMStatsDetailUniEthFrameDownHourDropEvents OBJECT-TYPE
			SYNTAX Counter64
			MAX-ACCESS read-only
			STATUS current
			DESCRIPTION
				"The hour number of events in which packets were dropped due to lack
				of resources."
			::= { sleGponOnuPMStatsDetailUniEthFrameDownEntry 17 }


--   1.3.6.1.4.1.6296.101.23.7.3.4.1.18
-- 1.3.6.1.4.1.6296.101.23.7.3.4.1.18
		sleGponOnuPMStatsDetailUniEthFrameDownHourOctets OBJECT-TYPE
			SYNTAX Counter64
			MAX-ACCESS read-only
			STATUS current
			DESCRIPTION
				"The hour number of octets received"
			::= { sleGponOnuPMStatsDetailUniEthFrameDownEntry 18 }


--   1.3.6.1.4.1.6296.101.23.7.3.4.1.19
-- 1.3.6.1.4.1.6296.101.23.7.3.4.1.19
		sleGponOnuPMStatsDetailUniEthFrameDownHourPackets OBJECT-TYPE
			SYNTAX Counter64
			MAX-ACCESS read-only
			STATUS current
			DESCRIPTION
				"The hour number of packets received,"
			::= { sleGponOnuPMStatsDetailUniEthFrameDownEntry 19 }


--   1.3.6.1.4.1.6296.101.23.7.3.4.1.20
-- 1.3.6.1.4.1.6296.101.23.7.3.4.1.20
		sleGponOnuPMStatsDetailUniEthFrameDownHourBcastPackets OBJECT-TYPE
			SYNTAX Counter64
			MAX-ACCESS read-write
			STATUS current
			DESCRIPTION
				"The hour number of received good packets directed to the broadcast address"
			::= { sleGponOnuPMStatsDetailUniEthFrameDownEntry 20 }


--   1.3.6.1.4.1.6296.101.23.7.3.4.1.21
-- 1.3.6.1.4.1.6296.101.23.7.3.4.1.21
		sleGponOnuPMStatsDetailUniEthFrameDownHourMcastPackets OBJECT-TYPE
			SYNTAX Counter64
			MAX-ACCESS read-only
			STATUS current
			DESCRIPTION
				"The hour number of received good packets directed to a multicast address."
			::= { sleGponOnuPMStatsDetailUniEthFrameDownEntry 21 }


--   1.3.6.1.4.1.6296.101.23.7.3.4.1.22
-- 1.3.6.1.4.1.6296.101.23.7.3.4.1.22
		sleGponOnuPMStatsDetailUniEthFrameDownHourUcastPackets OBJECT-TYPE
			SYNTAX Counter64
			MAX-ACCESS read-only
			STATUS current
			DESCRIPTION
				"The hour number of received good packets directed to the unicast address"
			::= { sleGponOnuPMStatsDetailUniEthFrameDownEntry 22 }


--   1.3.6.1.4.1.6296.101.23.7.3.4.1.23
-- 1.3.6.1.4.1.6296.101.23.7.3.4.1.23
		sleGponOnuPMStatsDetailUniEthFrameDownHourCRCErroredPackets OBJECT-TYPE
			SYNTAX Counter64
			MAX-ACCESS read-only
			STATUS current
			DESCRIPTION
				"The hour number of packets received that had a length"
			::= { sleGponOnuPMStatsDetailUniEthFrameDownEntry 23 }


--   1.3.6.1.4.1.6296.101.23.7.3.4.1.24
-- 1.3.6.1.4.1.6296.101.23.7.3.4.1.24
		sleGponOnuPMStatsDetailUniEthFrameDownHourUndersizePackets OBJECT-TYPE
			SYNTAX Counter64
			MAX-ACCESS read-only
			STATUS current
			DESCRIPTION
				"The hour number of packets received that were less than 64 octets long"
			::= { sleGponOnuPMStatsDetailUniEthFrameDownEntry 24 }


--   1.3.6.1.4.1.6296.101.23.7.3.4.1.25
-- 1.3.6.1.4.1.6296.101.23.7.3.4.1.25
		sleGponOnuPMStatsDetailUniEthFrameDownHourOversizePackets OBJECT-TYPE
			SYNTAX Counter64
			MAX-ACCESS read-only
			STATUS current
			DESCRIPTION
				"The hour number of received packets (including bad packets) that were
				64 octets long,
				"
			::= { sleGponOnuPMStatsDetailUniEthFrameDownEntry 25 }


--   1.3.6.1.4.1.6296.101.23.7.3.4.1.26
-- 1.3.6.1.4.1.6296.101.23.7.3.4.1.26
		sleGponOnuPMStatsDetailUniEthFrameDownHourPkt64Octets OBJECT-TYPE
			SYNTAX Counter64
			MAX-ACCESS read-only
			STATUS current
			DESCRIPTION
				"The hour number of received packets (including bad packets) that were
				64 octets long,
				"
			::= { sleGponOnuPMStatsDetailUniEthFrameDownEntry 26 }


--   1.3.6.1.4.1.6296.101.23.7.3.4.1.27
-- 1.3.6.1.4.1.6296.101.23.7.3.4.1.27
		sleGponOnuPMStatsDetailUniEthFrameDownHourPkt65To127Octets OBJECT-TYPE
			SYNTAX Counter64
			MAX-ACCESS read-only
			STATUS current
			DESCRIPTION
				"The hour number of received packets (including bad packets) that were
				65..127 octets long,"
			::= { sleGponOnuPMStatsDetailUniEthFrameDownEntry 27 }


--   1.3.6.1.4.1.6296.101.23.7.3.4.1.28
-- 1.3.6.1.4.1.6296.101.23.7.3.4.1.28
		sleGponOnuPMStatsDetailUniEthFrameDownHourPkt128To255Octets OBJECT-TYPE
			SYNTAX Counter64
			MAX-ACCESS read-write
			STATUS current
			DESCRIPTION
				"The hour number of packets (including bad packets) received that were
				128..255 octets long,"
			::= { sleGponOnuPMStatsDetailUniEthFrameDownEntry 28 }


--   1.3.6.1.4.1.6296.101.23.7.3.4.1.29
-- 1.3.6.1.4.1.6296.101.23.7.3.4.1.29
		sleGponOnuPMStatsDetailUniEthFrameDownHourPkt256To511Octets OBJECT-TYPE
			SYNTAX Counter64
			MAX-ACCESS read-only
			STATUS current
			DESCRIPTION
				"The hour number of packets (including bad packets) received that were
				256..511 octets long,"
			::= { sleGponOnuPMStatsDetailUniEthFrameDownEntry 29 }


--   1.3.6.1.4.1.6296.101.23.7.3.4.1.30
-- 1.3.6.1.4.1.6296.101.23.7.3.4.1.30
		sleGponOnuPMStatsDetailUniEthFrameDownHourPkt512To1023Octets OBJECT-TYPE
			SYNTAX Counter64
			MAX-ACCESS read-write
			STATUS current
			DESCRIPTION
				"The hour number of packets (including bad packets) received that were
				512..1023 octets long,
				"
			::= { sleGponOnuPMStatsDetailUniEthFrameDownEntry 30 }


--   1.3.6.1.4.1.6296.101.23.7.3.4.1.31
-- 1.3.6.1.4.1.6296.101.23.7.3.4.1.31
		sleGponOnuPMStatsDetailUniEthFrameDownHourPkt1024To1518Octets OBJECT-TYPE
			SYNTAX Counter64
			MAX-ACCESS read-only
			STATUS current
			DESCRIPTION
				"The hour number of packets (including bad packets) received that were
				1024..1518 octets long,
				"
			::= { sleGponOnuPMStatsDetailUniEthFrameDownEntry 31 }


--   1.3.6.1.4.1.6296.101.23.7.3.4.1.32
-- 1.3.6.1.4.1.6296.101.23.7.3.4.1.32
		sleGponOnuPMStatsDetailUniEthFrameDownDayDropEvents OBJECT-TYPE
			SYNTAX Counter64
			MAX-ACCESS read-only
			STATUS current
			DESCRIPTION
				"The day number of events in which packets were dropped due to lack of resources.
				"
			::= { sleGponOnuPMStatsDetailUniEthFrameDownEntry 32 }


--   1.3.6.1.4.1.6296.101.23.7.3.4.1.33
-- 1.3.6.1.4.1.6296.101.23.7.3.4.1.33
		sleGponOnuPMStatsDetailUniEthFrameDownDayOctets OBJECT-TYPE
			SYNTAX Counter64
			MAX-ACCESS read-only
			STATUS current
			DESCRIPTION
				"The day number of octets received"
			::= { sleGponOnuPMStatsDetailUniEthFrameDownEntry 33 }


--   1.3.6.1.4.1.6296.101.23.7.3.4.1.34
-- 1.3.6.1.4.1.6296.101.23.7.3.4.1.34
		sleGponOnuPMStatsDetailUniEthFrameDownDayPackets OBJECT-TYPE
			SYNTAX Counter64
			MAX-ACCESS read-only
			STATUS current
			DESCRIPTION
				"The day number of packets received,"
			::= { sleGponOnuPMStatsDetailUniEthFrameDownEntry 34 }


--   1.3.6.1.4.1.6296.101.23.7.3.4.1.35
-- 1.3.6.1.4.1.6296.101.23.7.3.4.1.35
		sleGponOnuPMStatsDetailUniEthFrameDownDayBcastPackets OBJECT-TYPE
			SYNTAX Counter64
			MAX-ACCESS read-write
			STATUS current
			DESCRIPTION
				"The day number of received good packets directed to a broadcast address."
			::= { sleGponOnuPMStatsDetailUniEthFrameDownEntry 35 }


--   1.3.6.1.4.1.6296.101.23.7.3.4.1.36
-- 1.3.6.1.4.1.6296.101.23.7.3.4.1.36
		sleGponOnuPMStatsDetailUniEthFrameDownDayMcastPackets OBJECT-TYPE
			SYNTAX Counter64
			MAX-ACCESS read-only
			STATUS current
			DESCRIPTION
				"The day number of received good packets directed to a multicast address."
			::= { sleGponOnuPMStatsDetailUniEthFrameDownEntry 36 }


--   1.3.6.1.4.1.6296.101.23.7.3.4.1.37
-- 1.3.6.1.4.1.6296.101.23.7.3.4.1.37
		sleGponOnuPMStatsDetailUniEthFrameDownDayUcastPackets OBJECT-TYPE
			SYNTAX Counter64
			MAX-ACCESS read-only
			STATUS current
			DESCRIPTION
				"The day number of received good packets directed to the unicast address"
			::= { sleGponOnuPMStatsDetailUniEthFrameDownEntry 37 }


--   1.3.6.1.4.1.6296.101.23.7.3.4.1.38
-- 1.3.6.1.4.1.6296.101.23.7.3.4.1.38
		sleGponOnuPMStatsDetailUniEthFrameDownDayCRCErroredPackets OBJECT-TYPE
			SYNTAX Counter64
			MAX-ACCESS read-only
			STATUS current
			DESCRIPTION
				"The day number of packets received that had a length"
			::= { sleGponOnuPMStatsDetailUniEthFrameDownEntry 38 }


--   1.3.6.1.4.1.6296.101.23.7.3.4.1.39
-- 1.3.6.1.4.1.6296.101.23.7.3.4.1.39
		sleGponOnuPMStatsDetailUniEthFrameDownDayUndersizePackets OBJECT-TYPE
			SYNTAX Counter64
			MAX-ACCESS read-only
			STATUS current
			DESCRIPTION
				"The day number of packets received that were less than 64 octets long"
			::= { sleGponOnuPMStatsDetailUniEthFrameDownEntry 39 }


--   1.3.6.1.4.1.6296.101.23.7.3.4.1.40
-- 1.3.6.1.4.1.6296.101.23.7.3.4.1.40
		sleGponOnuPMStatsDetailUniEthFrameDownDayOversizePackets OBJECT-TYPE
			SYNTAX Counter64
			MAX-ACCESS read-only
			STATUS current
			DESCRIPTION
				"The day number of packets received that were longer than 1518 octets"
			::= { sleGponOnuPMStatsDetailUniEthFrameDownEntry 40 }


--   1.3.6.1.4.1.6296.101.23.7.3.4.1.41
-- 1.3.6.1.4.1.6296.101.23.7.3.4.1.41
		sleGponOnuPMStatsDetailUniEthFrameDownDayPkt64Octets OBJECT-TYPE
			SYNTAX Counter64
			MAX-ACCESS read-only
			STATUS current
			DESCRIPTION
				"The day number of received packets (including bad packets) that were
				64 octets long,"
			::= { sleGponOnuPMStatsDetailUniEthFrameDownEntry 41 }


--   1.3.6.1.4.1.6296.101.23.7.3.4.1.42
-- 1.3.6.1.4.1.6296.101.23.7.3.4.1.42
		sleGponOnuPMStatsDetailUniEthFrameDownDayPkt65To127Octets OBJECT-TYPE
			SYNTAX Counter64
			MAX-ACCESS read-only
			STATUS current
			DESCRIPTION
				"The day number of received packets (including bad packets) that were
				65..127 octets long,"
			::= { sleGponOnuPMStatsDetailUniEthFrameDownEntry 42 }


--   1.3.6.1.4.1.6296.101.23.7.3.4.1.43
-- 1.3.6.1.4.1.6296.101.23.7.3.4.1.43
		sleGponOnuPMStatsDetailUniEthFrameDownDayPkt128To255Octets OBJECT-TYPE
			SYNTAX Counter64
			MAX-ACCESS read-write
			STATUS current
			DESCRIPTION
				"The day number of received packets (including bad packets) that were
				128..255 octets long,
				"
			::= { sleGponOnuPMStatsDetailUniEthFrameDownEntry 43 }


--   1.3.6.1.4.1.6296.101.23.7.3.4.1.44
-- 1.3.6.1.4.1.6296.101.23.7.3.4.1.44
		sleGponOnuPMStatsDetailUniEthFrameDownDayPkt256To511Octets OBJECT-TYPE
			SYNTAX Counter64
			MAX-ACCESS read-only
			STATUS current
			DESCRIPTION
				"The day number of packets (including bad packets) received that were
				256..511 octets long,"
			::= { sleGponOnuPMStatsDetailUniEthFrameDownEntry 44 }


--   1.3.6.1.4.1.6296.101.23.7.3.4.1.45
-- 1.3.6.1.4.1.6296.101.23.7.3.4.1.45
		sleGponOnuPMStatsDetailUniEthFrameDownDayPkt512To1023Octets OBJECT-TYPE
			SYNTAX Counter64
			MAX-ACCESS read-write
			STATUS current
			DESCRIPTION
				"The day number of packets (including bad packets) received that were
				512..1023 octets long,"
			::= { sleGponOnuPMStatsDetailUniEthFrameDownEntry 45 }


--   1.3.6.1.4.1.6296.101.23.7.3.4.1.46
-- 1.3.6.1.4.1.6296.101.23.7.3.4.1.46
		sleGponOnuPMStatsDetailUniEthFrameDownDayPkt1024To1518Octets OBJECT-TYPE
			SYNTAX Counter64
			MAX-ACCESS read-only
			STATUS current
			DESCRIPTION
				"The day number of packets (including bad packets) received that were
				1024..1518 octets long,"
			::= { sleGponOnuPMStatsDetailUniEthFrameDownEntry 46 }


--   1.3.6.1.4.1.6296.101.23.7.3.4.1.47
-- 1.3.6.1.4.1.6296.101.23.7.3.4.1.47
		sleGponOnuPMStatsDetailUniEthFrameDownTotalDropEvents OBJECT-TYPE
			SYNTAX Counter64
			MAX-ACCESS read-only
			STATUS current
			DESCRIPTION
				"The total number of events in which packets were dropped due to lack of resources."
			::= { sleGponOnuPMStatsDetailUniEthFrameDownEntry 47 }


--   1.3.6.1.4.1.6296.101.23.7.3.4.1.48
-- 1.3.6.1.4.1.6296.101.23.7.3.4.1.48
		sleGponOnuPMStatsDetailUniEthFrameDownTotalOctets OBJECT-TYPE
			SYNTAX Counter64
			MAX-ACCESS read-only
			STATUS current
			DESCRIPTION
				"The total number of octets received"
			::= { sleGponOnuPMStatsDetailUniEthFrameDownEntry 48 }


--   1.3.6.1.4.1.6296.101.23.7.3.4.1.49
-- 1.3.6.1.4.1.6296.101.23.7.3.4.1.49
		sleGponOnuPMStatsDetailUniEthFrameDownTotalPackets OBJECT-TYPE
			SYNTAX Counter64
			MAX-ACCESS read-only
			STATUS current
			DESCRIPTION
				"The total number of packets received,"
			::= { sleGponOnuPMStatsDetailUniEthFrameDownEntry 49 }


--   1.3.6.1.4.1.6296.101.23.7.3.4.1.50
-- 1.3.6.1.4.1.6296.101.23.7.3.4.1.50
		sleGponOnuPMStatsDetailUniEthFrameDownTotalBcastPackets OBJECT-TYPE
			SYNTAX Counter64
			MAX-ACCESS read-write
			STATUS current
			DESCRIPTION
				"The total number of received good packets directed to a broadcast address."
			::= { sleGponOnuPMStatsDetailUniEthFrameDownEntry 50 }


--   1.3.6.1.4.1.6296.101.23.7.3.4.1.51
-- 1.3.6.1.4.1.6296.101.23.7.3.4.1.51
		sleGponOnuPMStatsDetailUniEthFrameDownTotalMcastPackets OBJECT-TYPE
			SYNTAX Counter64
			MAX-ACCESS read-only
			STATUS current
			DESCRIPTION
				"The total number of received good packets directed to a multicast address."
			::= { sleGponOnuPMStatsDetailUniEthFrameDownEntry 51 }


--   1.3.6.1.4.1.6296.101.23.7.3.4.1.52
-- 1.3.6.1.4.1.6296.101.23.7.3.4.1.52
		sleGponOnuPMStatsDetailUniEthFrameDownTotalUcastPackets OBJECT-TYPE
			SYNTAX Counter64
			MAX-ACCESS read-only
			STATUS current
			DESCRIPTION
				"The total number of received good packets directed to the unicast address"
			::= { sleGponOnuPMStatsDetailUniEthFrameDownEntry 52 }


--   1.3.6.1.4.1.6296.101.23.7.3.4.1.53
-- 1.3.6.1.4.1.6296.101.23.7.3.4.1.53
		sleGponOnuPMStatsDetailUniEthFrameDownTotalCRCErroredPackets OBJECT-TYPE
			SYNTAX Counter64
			MAX-ACCESS read-only
			STATUS current
			DESCRIPTION
				"Description."
			::= { sleGponOnuPMStatsDetailUniEthFrameDownEntry 53 }


--   1.3.6.1.4.1.6296.101.23.7.3.4.1.54
-- 1.3.6.1.4.1.6296.101.23.7.3.4.1.54
		sleGponOnuPMStatsDetailUniEthFrameDownTotalUndersizePackets OBJECT-TYPE
			SYNTAX Counter64
			MAX-ACCESS read-only
			STATUS current
			DESCRIPTION
				"The total number of packets received that were less than 64 octets long"
			::= { sleGponOnuPMStatsDetailUniEthFrameDownEntry 54 }


--   1.3.6.1.4.1.6296.101.23.7.3.4.1.55
-- 1.3.6.1.4.1.6296.101.23.7.3.4.1.55
		sleGponOnuPMStatsDetailUniEthFrameDownTotalOversizePackets OBJECT-TYPE
			SYNTAX Counter64
			MAX-ACCESS read-only
			STATUS current
			DESCRIPTION
				"The total number of packets received that were longer than 1518 octets"
			::= { sleGponOnuPMStatsDetailUniEthFrameDownEntry 55 }


--   1.3.6.1.4.1.6296.101.23.7.3.4.1.56
-- 1.3.6.1.4.1.6296.101.23.7.3.4.1.56
		sleGponOnuPMStatsDetailUniEthFrameDownTotalPkt64Octets OBJECT-TYPE
			SYNTAX Counter64
			MAX-ACCESS read-only
			STATUS current
			DESCRIPTION
				"The total number of received packets (including bad packets) that were
				64 octets long,"
			::= { sleGponOnuPMStatsDetailUniEthFrameDownEntry 56 }


--   1.3.6.1.4.1.6296.101.23.7.3.4.1.57
-- 1.3.6.1.4.1.6296.101.23.7.3.4.1.57
		sleGponOnuPMStatsDetailUniEthFrameDownTotalPkt65To127Octets OBJECT-TYPE
			SYNTAX Counter64
			MAX-ACCESS read-only
			STATUS current
			DESCRIPTION
				"The total number of received packets (including bad packets) that were
				65..127 octets long,"
			::= { sleGponOnuPMStatsDetailUniEthFrameDownEntry 57 }


--   1.3.6.1.4.1.6296.101.23.7.3.4.1.58
-- 1.3.6.1.4.1.6296.101.23.7.3.4.1.58
		sleGponOnuPMStatsDetailUniEthFrameDownTotalPkt128To255Octets OBJECT-TYPE
			SYNTAX Counter64
			MAX-ACCESS read-write
			STATUS current
			DESCRIPTION
				"The total number of packets (including bad packets) received that were
				128..255 octets long,"
			::= { sleGponOnuPMStatsDetailUniEthFrameDownEntry 58 }


--   1.3.6.1.4.1.6296.101.23.7.3.4.1.59
-- 1.3.6.1.4.1.6296.101.23.7.3.4.1.59
		sleGponOnuPMStatsDetailUniEthFrameDownTotalPkt256To511Octets OBJECT-TYPE
			SYNTAX Counter64
			MAX-ACCESS read-only
			STATUS current
			DESCRIPTION
				"The total number of packets (including bad packets) received that were
				256..511 octets long,"
			::= { sleGponOnuPMStatsDetailUniEthFrameDownEntry 59 }


--   1.3.6.1.4.1.6296.101.23.7.3.4.1.60
-- 1.3.6.1.4.1.6296.101.23.7.3.4.1.60
		sleGponOnuPMStatsDetailUniEthFrameDownTotalPkt512To1023Octets OBJECT-TYPE
			SYNTAX Counter64
			MAX-ACCESS read-write
			STATUS current
			DESCRIPTION
				"The total number of packets (including bad packets) received that were
				512..1023 octets long,"
			::= { sleGponOnuPMStatsDetailUniEthFrameDownEntry 60 }


--   1.3.6.1.4.1.6296.101.23.7.3.4.1.61
-- 1.3.6.1.4.1.6296.101.23.7.3.4.1.61
		sleGponOnuPMStatsDetailUniEthFrameDownTotalPkt1024To1518Octets OBJECT-TYPE
			SYNTAX Counter64
			MAX-ACCESS read-only
			STATUS current
			DESCRIPTION
				"The total number of packets (including bad packets) received that were
				1024..1518 octets long,"
			::= { sleGponOnuPMStatsDetailUniEthFrameDownEntry 61 }


--   1.3.6.1.4.1.6296.101.23.7.3.4.1.62
-- 1.3.6.1.4.1.6296.101.23.7.3.4.1.62
		sleGponOnuPMStatsDetailUniEthFrameDownElapsedTimeAfterClear OBJECT-TYPE
			SYNTAX TimeTicks
			MAX-ACCESS read-only
			STATUS current
			DESCRIPTION
				"The total number of packets for elapsed time after clear"
			::= { sleGponOnuPMStatsDetailUniEthFrameDownEntry 62 }


--   1.3.6.1.4.1.6296.101.23.7.3.4.1.63
-- 1.3.6.1.4.1.6296.101.23.7.3.4.1.63
		sleGponOnuPMStatsDetailUniEthFrameDownElapsedTimeAfterUpdate OBJECT-TYPE
			SYNTAX Counter64
			MAX-ACCESS read-only
			STATUS current
			DESCRIPTION
				"The total number of packets for elapsed time after update"
			::= { sleGponOnuPMStatsDetailUniEthFrameDownEntry 63 }


--   1.3.6.1.4.1.6296.101.23.7.3.5
-- 1.3.6.1.4.1.6296.101.23.7.3.5
		sleGponOnuPMStatsDetailUniEth3Table OBJECT-TYPE
			SYNTAX SEQUENCE OF SleGponOnuPMStatsDetailUniEth3Entry
			MAX-ACCESS not-accessible
			STATUS current
			DESCRIPTION
				"sleGponOnuPMStatsDetailUniEth3Table"
			::= { sleGponOnuPMStatisticsDetail 5 }


--   1.3.6.1.4.1.6296.101.23.7.3.5.1
-- 1.3.6.1.4.1.6296.101.23.7.3.5.1
		sleGponOnuPMStatsDetailUniEth3Entry OBJECT-TYPE
			SYNTAX SleGponOnuPMStatsDetailUniEth3Entry
			MAX-ACCESS not-accessible
			STATUS current
			DESCRIPTION
				"key: sleGponOltId, sleGponOnuId, sleGponOnuPMStatsDetailUniEthFrameUpUniPort"
			INDEX { sleGponOltId, sleGponOnuId, sleGponOnuPMStatsDetailUniEthFrameUpUniPort }
			::= { sleGponOnuPMStatsDetailUniEth3Table 1 }


		SleGponOnuPMStatsDetailUniEth3Entry ::=
			SEQUENCE {
				sleGponOnuPMStatsDetailUniEth3UniPort
					Integer32,
				sleGponOnuPMStatsDetailUniEth3Pre15mDropEvents
					Counter64,
				sleGponOnuPMStatsDetailUniEth3Pre15mOctets
					Counter64,
				sleGponOnuPMStatsDetailUniEth3Pre15mPackets
					Counter64,
				sleGponOnuPMStatsDetailUniEth3Pre15mBcastPackets
					Counter64,
				sleGponOnuPMStatsDetailUniEth3Pre15mMcastPackets
					Counter64,
				sleGponOnuPMStatsDetailUniEth3Pre15mUcastPackets
					Counter64,
				sleGponOnuPMStatsDetailUniEth3Pre15mUndersizePackets
					Counter64,
				sleGponOnuPMStatsDetailUniEth3Pre15mFragments
					Counter64,
				sleGponOnuPMStatsDetailUniEth3Pre15mJabbers
					Counter64,
				sleGponOnuPMStatsDetailUniEth3Pre15mPkt64Octets
					Counter64,
				sleGponOnuPMStatsDetailUniEth3Pre15mPkt65To127Octets
					Counter64,
				sleGponOnuPMStatsDetailUniEth3Pre15mPkt128To255Octets
					Counter64,
				sleGponOnuPMStatsDetailUniEth3Pre15mPkt256To511Octets
					Counter64,
				sleGponOnuPMStatsDetailUniEth3Pre15mPkt512To1023Octets
					Counter64,
				sleGponOnuPMStatsDetailUniEth3Pre15mPkt1024To1518Octets
					Counter64,
				sleGponOnuPMStatsDetailUniEth3HourDropEvents
					Counter64,
				sleGponOnuPMStatsDetailUniEth3HourOctets
					Counter64,
				sleGponOnuPMStatsDetailUniEth3HourPackets
					Counter64,
				sleGponOnuPMStatsDetailUniEth3HourBcastPackets
					Counter64,
				sleGponOnuPMStatsDetailUniEth3HourMcastPackets
					Counter64,
				sleGponOnuPMStatsDetailUniEth3HourUcastPackets
					Counter64,
				sleGponOnuPMStatsDetailUniEth3HourUndersizePackets
					Counter64,
				sleGponOnuPMStatsDetailUniEth3HourFragments
					Counter64,
				sleGponOnuPMStatsDetailUniEth3HourJabbers
					Counter64,
				sleGponOnuPMStatsDetailUniEth3HourPkt64Octets
					Counter64,
				sleGponOnuPMStatsDetailUniEth3HourPkt65To127Octets
					Counter64,
				sleGponOnuPMStatsDetailUniEth3HourPkt128To255Octets
					Counter64,
				sleGponOnuPMStatsDetailUniEth3HourPkt256To511Octets
					Counter64,
				sleGponOnuPMStatsDetailUniEth3HourPkt512To1023Octets
					Counter64,
				sleGponOnuPMStatsDetailUniEth3HourPkt1024To1518Octets
					Counter64,
				sleGponOnuPMStatsDetailUniEth3DayDropEvents
					Counter64,
				sleGponOnuPMStatsDetailUniEth3DayOctets
					Counter64,
				sleGponOnuPMStatsDetailUniEth3DayPackets
					Counter64,
				sleGponOnuPMStatsDetailUniEth3DayBcastPackets
					Counter64,
				sleGponOnuPMStatsDetailUniEth3DayMcastPackets
					Counter64,
				sleGponOnuPMStatsDetailUniEth3DayUcastPackets
					Counter64,
				sleGponOnuPMStatsDetailUniEth3DayUndersizePackets
					Counter64,
				sleGponOnuPMStatsDetailUniEth3DayFragments
					Counter64,
				sleGponOnuPMStatsDetailUniEth3DayJabbers
					Counter64,
				sleGponOnuPMStatsDetailUniEth3DayPkt64Octets
					Counter64,
				sleGponOnuPMStatsDetailUniEth3DayPkt65To127Octets
					Counter64,
				sleGponOnuPMStatsDetailUniEth3DayPkt128To255Octets
					Counter64,
				sleGponOnuPMStatsDetailUniEth3DayPkt256To511Octets
					Counter64,
				sleGponOnuPMStatsDetailUniEth3DayPkt512To1023Octets
					Counter64,
				sleGponOnuPMStatsDetailUniEth3DayPkt1024To1518Octets
					Counter64,
				sleGponOnuPMStatsDetailUniEth3TotalDropEvents
					Counter64,
				sleGponOnuPMStatsDetailUniEth3TotalOctets
					Counter64,
				sleGponOnuPMStatsDetailUniEth3TotalPackets
					Counter64,
				sleGponOnuPMStatsDetailUniEth3TotalBcastPackets
					Counter64,
				sleGponOnuPMStatsDetailUniEth3TotalMcastPackets
					Counter64,
				sleGponOnuPMStatsDetailUniEth3TotalUcastPackets
					Counter64,
				sleGponOnuPMStatsDetailUniEth3TotalUndersizePackets
					Counter64,
				sleGponOnuPMStatsDetailUniEth3TotalFragments
					Counter64,
				sleGponOnuPMStatsDetailUniEth3TotalJabbers
					Counter64,
				sleGponOnuPMStatsDetailUniEth3TotalPkt64Octets
					Counter64,
				sleGponOnuPMStatsDetailUniEth3TotalPkt65To127Octets
					Counter64,
				sleGponOnuPMStatsDetailUniEth3TotalPkt128To255Octets
					Counter64,
				sleGponOnuPMStatsDetailUniEth3TotalPkt256To511Octets
					Counter64,
				sleGponOnuPMStatsDetailUniEth3TotalPkt512To1023Octets
					Counter64,
				sleGponOnuPMStatsDetailUniEth3TotalPkt1024To1518Octets
					Counter64,
				sleGponOnuPMStatsDetailUniEth3ElapsedTimeAfterClear
					TimeTicks,
				sleGponOnuPMStatsDetailUniEth3ElapsedTimeAfterUpdate
					Counter64
			 }

--   1.3.6.1.4.1.6296.101.23.7.3.5.1.1
-- 1.3.6.1.4.1.6296.101.23.7.3.5.1.1
		sleGponOnuPMStatsDetailUniEth3UniPort OBJECT-TYPE
			SYNTAX Integer32
			MAX-ACCESS read-only
			STATUS current
			DESCRIPTION
				"The Uni port information"
			::= { sleGponOnuPMStatsDetailUniEth3Entry 1 }


--   1.3.6.1.4.1.6296.101.23.7.3.5.1.2
-- 1.3.6.1.4.1.6296.101.23.7.3.5.1.2
		sleGponOnuPMStatsDetailUniEth3Pre15mDropEvents OBJECT-TYPE
			SYNTAX Counter64
			MAX-ACCESS read-only
			STATUS current
			DESCRIPTION
				"The pre 15 minute number of events in which packets were dropped due to lack of resources."
			::= { sleGponOnuPMStatsDetailUniEth3Entry 2 }


--   1.3.6.1.4.1.6296.101.23.7.3.5.1.3
-- 1.3.6.1.4.1.6296.101.23.7.3.5.1.3
		sleGponOnuPMStatsDetailUniEth3Pre15mOctets OBJECT-TYPE
			SYNTAX Counter64
			MAX-ACCESS read-only
			STATUS current
			DESCRIPTION
				"The pre 15 minute number of octets received"
			::= { sleGponOnuPMStatsDetailUniEth3Entry 3 }


--   1.3.6.1.4.1.6296.101.23.7.3.5.1.4
-- 1.3.6.1.4.1.6296.101.23.7.3.5.1.4
		sleGponOnuPMStatsDetailUniEth3Pre15mPackets OBJECT-TYPE
			SYNTAX Counter64
			MAX-ACCESS read-only
			STATUS current
			DESCRIPTION
				"The pre 15 minute number of packets received, including bad packets"
			::= { sleGponOnuPMStatsDetailUniEth3Entry 4 }


--   1.3.6.1.4.1.6296.101.23.7.3.5.1.5
-- 1.3.6.1.4.1.6296.101.23.7.3.5.1.5
		sleGponOnuPMStatsDetailUniEth3Pre15mBcastPackets OBJECT-TYPE
			SYNTAX Counter64
			MAX-ACCESS read-only
			STATUS current
			DESCRIPTION
				"The pre 15 minute number of received good packets directed to the broadcast address."
			::= { sleGponOnuPMStatsDetailUniEth3Entry 5 }


--   1.3.6.1.4.1.6296.101.23.7.3.5.1.6
-- 1.3.6.1.4.1.6296.101.23.7.3.5.1.6
		sleGponOnuPMStatsDetailUniEth3Pre15mMcastPackets OBJECT-TYPE
			SYNTAX Counter64
			MAX-ACCESS read-only
			STATUS current
			DESCRIPTION
				"The pre 15 minute number of received good packets directed to a multicast address."
			::= { sleGponOnuPMStatsDetailUniEth3Entry 6 }


--   1.3.6.1.4.1.6296.101.23.7.3.5.1.7
-- 1.3.6.1.4.1.6296.101.23.7.3.5.1.7
		sleGponOnuPMStatsDetailUniEth3Pre15mUcastPackets OBJECT-TYPE
			SYNTAX Counter64
			MAX-ACCESS read-only
			STATUS current
			DESCRIPTION
				"The pre 15 minute number of received good packets directed to a unicast address."
			::= { sleGponOnuPMStatsDetailUniEth3Entry 7 }


--   1.3.6.1.4.1.6296.101.23.7.3.5.1.8
-- 1.3.6.1.4.1.6296.101.23.7.3.5.1.8
		sleGponOnuPMStatsDetailUniEth3Pre15mUndersizePackets OBJECT-TYPE
			SYNTAX Counter64
			MAX-ACCESS read-only
			STATUS current
			DESCRIPTION
				"The pre 15 minute number of packets received that were less than 64 octets long"
			::= { sleGponOnuPMStatsDetailUniEth3Entry 8 }


--   1.3.6.1.4.1.6296.101.23.7.3.5.1.9
-- 1.3.6.1.4.1.6296.101.23.7.3.5.1.9
		sleGponOnuPMStatsDetailUniEth3Pre15mFragments OBJECT-TYPE
			SYNTAX Counter64
			MAX-ACCESS read-only
			STATUS current
			DESCRIPTION
				"The pre 15 minute number of packets received that were fragments"
			::= { sleGponOnuPMStatsDetailUniEth3Entry 9 }


--   1.3.6.1.4.1.6296.101.23.7.3.5.1.10
-- 1.3.6.1.4.1.6296.101.23.7.3.5.1.10
		sleGponOnuPMStatsDetailUniEth3Pre15mJabbers OBJECT-TYPE
			SYNTAX Counter64
			MAX-ACCESS read-only
			STATUS current
			DESCRIPTION
				"The pre 15 minute number of packets received that were jabbers"
			::= { sleGponOnuPMStatsDetailUniEth3Entry 10 }


--   1.3.6.1.4.1.6296.101.23.7.3.5.1.11
-- 1.3.6.1.4.1.6296.101.23.7.3.5.1.11
		sleGponOnuPMStatsDetailUniEth3Pre15mPkt64Octets OBJECT-TYPE
			SYNTAX Counter64
			MAX-ACCESS read-only
			STATUS current
			DESCRIPTION
				"The pre 15 minute number of received packets (including bad packets) that were 64 octets long"
			::= { sleGponOnuPMStatsDetailUniEth3Entry 11 }


--   1.3.6.1.4.1.6296.101.23.7.3.5.1.12
-- 1.3.6.1.4.1.6296.101.23.7.3.5.1.12
		sleGponOnuPMStatsDetailUniEth3Pre15mPkt65To127Octets OBJECT-TYPE
			SYNTAX Counter64
			MAX-ACCESS read-only
			STATUS current
			DESCRIPTION
				"The pre 15 minute number of received packets (including bad packets) that were 65..127 octets long"
			::= { sleGponOnuPMStatsDetailUniEth3Entry 12 }


--   1.3.6.1.4.1.6296.101.23.7.3.5.1.13
-- 1.3.6.1.4.1.6296.101.23.7.3.5.1.13
		sleGponOnuPMStatsDetailUniEth3Pre15mPkt128To255Octets OBJECT-TYPE
			SYNTAX Counter64
			MAX-ACCESS read-only
			STATUS current
			DESCRIPTION
				"The pre 15 minute number of packets (including bad packets) received that were 128..255 octets long"
			::= { sleGponOnuPMStatsDetailUniEth3Entry 13 }


--   1.3.6.1.4.1.6296.101.23.7.3.5.1.14
-- 1.3.6.1.4.1.6296.101.23.7.3.5.1.14
		sleGponOnuPMStatsDetailUniEth3Pre15mPkt256To511Octets OBJECT-TYPE
			SYNTAX Counter64
			MAX-ACCESS read-only
			STATUS current
			DESCRIPTION
				"The pre 15 minute number of packets (including bad packets) received that were 256..511 octets long"
			::= { sleGponOnuPMStatsDetailUniEth3Entry 14 }


--   1.3.6.1.4.1.6296.101.23.7.3.5.1.15
-- 1.3.6.1.4.1.6296.101.23.7.3.5.1.15
		sleGponOnuPMStatsDetailUniEth3Pre15mPkt512To1023Octets OBJECT-TYPE
			SYNTAX Counter64
			MAX-ACCESS read-only
			STATUS current
			DESCRIPTION
				"The pre 15 minute number of packets (including bad packets) received that were 512..1023 octets long"
			::= { sleGponOnuPMStatsDetailUniEth3Entry 15 }


--   1.3.6.1.4.1.6296.101.23.7.3.5.1.16
-- 1.3.6.1.4.1.6296.101.23.7.3.5.1.16
		sleGponOnuPMStatsDetailUniEth3Pre15mPkt1024To1518Octets OBJECT-TYPE
			SYNTAX Counter64
			MAX-ACCESS read-only
			STATUS current
			DESCRIPTION
				"The pre 15 minute number of packets (including bad packets) received that were 1024..1518 octets long"
			::= { sleGponOnuPMStatsDetailUniEth3Entry 16 }


--   1.3.6.1.4.1.6296.101.23.7.3.5.1.17
-- 1.3.6.1.4.1.6296.101.23.7.3.5.1.17
		sleGponOnuPMStatsDetailUniEth3HourDropEvents OBJECT-TYPE
			SYNTAX Counter64
			MAX-ACCESS read-only
			STATUS current
			DESCRIPTION
				"The hour number of events in which packets were dropped due to lack of resources."
			::= { sleGponOnuPMStatsDetailUniEth3Entry 17 }


--   1.3.6.1.4.1.6296.101.23.7.3.5.1.18
-- 1.3.6.1.4.1.6296.101.23.7.3.5.1.18
		sleGponOnuPMStatsDetailUniEth3HourOctets OBJECT-TYPE
			SYNTAX Counter64
			MAX-ACCESS read-only
			STATUS current
			DESCRIPTION
				"The hour number of octets received"
			::= { sleGponOnuPMStatsDetailUniEth3Entry 18 }


--   1.3.6.1.4.1.6296.101.23.7.3.5.1.19
-- 1.3.6.1.4.1.6296.101.23.7.3.5.1.19
		sleGponOnuPMStatsDetailUniEth3HourPackets OBJECT-TYPE
			SYNTAX Counter64
			MAX-ACCESS read-only
			STATUS current
			DESCRIPTION
				"The hour number of packets received,"
			::= { sleGponOnuPMStatsDetailUniEth3Entry 19 }


--   1.3.6.1.4.1.6296.101.23.7.3.5.1.20
-- 1.3.6.1.4.1.6296.101.23.7.3.5.1.20
		sleGponOnuPMStatsDetailUniEth3HourBcastPackets OBJECT-TYPE
			SYNTAX Counter64
			MAX-ACCESS read-write
			STATUS current
			DESCRIPTION
				"The hour number of received good packets directed to the broadcast address"
			::= { sleGponOnuPMStatsDetailUniEth3Entry 20 }


--   1.3.6.1.4.1.6296.101.23.7.3.5.1.21
-- 1.3.6.1.4.1.6296.101.23.7.3.5.1.21
		sleGponOnuPMStatsDetailUniEth3HourMcastPackets OBJECT-TYPE
			SYNTAX Counter64
			MAX-ACCESS read-only
			STATUS current
			DESCRIPTION
				"The hour number of received good packets directed to a multicast address."
			::= { sleGponOnuPMStatsDetailUniEth3Entry 21 }


--   1.3.6.1.4.1.6296.101.23.7.3.5.1.22
-- 1.3.6.1.4.1.6296.101.23.7.3.5.1.22
		sleGponOnuPMStatsDetailUniEth3HourUcastPackets OBJECT-TYPE
			SYNTAX Counter64
			MAX-ACCESS read-only
			STATUS current
			DESCRIPTION
				"The hour number of received good packets directed to the unicast address"
			::= { sleGponOnuPMStatsDetailUniEth3Entry 22 }


--   1.3.6.1.4.1.6296.101.23.7.3.5.1.23
-- 1.3.6.1.4.1.6296.101.23.7.3.5.1.23
		sleGponOnuPMStatsDetailUniEth3HourUndersizePackets OBJECT-TYPE
			SYNTAX Counter64
			MAX-ACCESS read-only
			STATUS current
			DESCRIPTION
				"The hour number of packets received that were less than 64 octets long"
			::= { sleGponOnuPMStatsDetailUniEth3Entry 23 }


--   1.3.6.1.4.1.6296.101.23.7.3.5.1.24
-- 1.3.6.1.4.1.6296.101.23.7.3.5.1.24
		sleGponOnuPMStatsDetailUniEth3HourFragments OBJECT-TYPE
			SYNTAX Counter64
			MAX-ACCESS read-only
			STATUS current
			DESCRIPTION
				"The hour number of packets received that were fragments"
			::= { sleGponOnuPMStatsDetailUniEth3Entry 24 }


--   1.3.6.1.4.1.6296.101.23.7.3.5.1.25
-- 1.3.6.1.4.1.6296.101.23.7.3.5.1.25
		sleGponOnuPMStatsDetailUniEth3HourJabbers OBJECT-TYPE
			SYNTAX Counter64
			MAX-ACCESS read-only
			STATUS current
			DESCRIPTION
				"The hour number of packets received that were jabbers"
			::= { sleGponOnuPMStatsDetailUniEth3Entry 25 }


--   1.3.6.1.4.1.6296.101.23.7.3.5.1.26
-- 1.3.6.1.4.1.6296.101.23.7.3.5.1.26
		sleGponOnuPMStatsDetailUniEth3HourPkt64Octets OBJECT-TYPE
			SYNTAX Counter64
			MAX-ACCESS read-only
			STATUS current
			DESCRIPTION
				"The hour number of received packets (including bad packets) that were
				64 octets long,"
			::= { sleGponOnuPMStatsDetailUniEth3Entry 26 }


--   1.3.6.1.4.1.6296.101.23.7.3.5.1.27
-- 1.3.6.1.4.1.6296.101.23.7.3.5.1.27
		sleGponOnuPMStatsDetailUniEth3HourPkt65To127Octets OBJECT-TYPE
			SYNTAX Counter64
			MAX-ACCESS read-only
			STATUS current
			DESCRIPTION
				"The hour number of received packets (including bad packets) that were
				65..127 octets long,"
			::= { sleGponOnuPMStatsDetailUniEth3Entry 27 }


--   1.3.6.1.4.1.6296.101.23.7.3.5.1.28
-- 1.3.6.1.4.1.6296.101.23.7.3.5.1.28
		sleGponOnuPMStatsDetailUniEth3HourPkt128To255Octets OBJECT-TYPE
			SYNTAX Counter64
			MAX-ACCESS read-write
			STATUS current
			DESCRIPTION
				"The hour number of packets (including bad packets) received that were
				128..255 octets long,"
			::= { sleGponOnuPMStatsDetailUniEth3Entry 28 }


--   1.3.6.1.4.1.6296.101.23.7.3.5.1.29
-- 1.3.6.1.4.1.6296.101.23.7.3.5.1.29
		sleGponOnuPMStatsDetailUniEth3HourPkt256To511Octets OBJECT-TYPE
			SYNTAX Counter64
			MAX-ACCESS read-only
			STATUS current
			DESCRIPTION
				"The hour number of packets (including bad packets) received that were
				256..511 octets long,"
			::= { sleGponOnuPMStatsDetailUniEth3Entry 29 }


--   1.3.6.1.4.1.6296.101.23.7.3.5.1.30
-- 1.3.6.1.4.1.6296.101.23.7.3.5.1.30
		sleGponOnuPMStatsDetailUniEth3HourPkt512To1023Octets OBJECT-TYPE
			SYNTAX Counter64
			MAX-ACCESS read-write
			STATUS current
			DESCRIPTION
				"The hour number of packets (including bad packets) received that were
				512..1023 octets long,"
			::= { sleGponOnuPMStatsDetailUniEth3Entry 30 }


--   1.3.6.1.4.1.6296.101.23.7.3.5.1.31
-- 1.3.6.1.4.1.6296.101.23.7.3.5.1.31
		sleGponOnuPMStatsDetailUniEth3HourPkt1024To1518Octets OBJECT-TYPE
			SYNTAX Counter64
			MAX-ACCESS read-only
			STATUS current
			DESCRIPTION
				"The hour number of packets (including bad packets) received that were
				1024..1518 octets long,"
			::= { sleGponOnuPMStatsDetailUniEth3Entry 31 }


--   1.3.6.1.4.1.6296.101.23.7.3.5.1.32
-- 1.3.6.1.4.1.6296.101.23.7.3.5.1.32
		sleGponOnuPMStatsDetailUniEth3DayDropEvents OBJECT-TYPE
			SYNTAX Counter64
			MAX-ACCESS read-only
			STATUS current
			DESCRIPTION
				"The day number of events in which packets were dropped due to lack of resources."
			::= { sleGponOnuPMStatsDetailUniEth3Entry 32 }


--   1.3.6.1.4.1.6296.101.23.7.3.5.1.33
-- 1.3.6.1.4.1.6296.101.23.7.3.5.1.33
		sleGponOnuPMStatsDetailUniEth3DayOctets OBJECT-TYPE
			SYNTAX Counter64
			MAX-ACCESS read-only
			STATUS current
			DESCRIPTION
				"The day number of events in which packets were dropped due to lack of resources.
				"
			::= { sleGponOnuPMStatsDetailUniEth3Entry 33 }


--   1.3.6.1.4.1.6296.101.23.7.3.5.1.34
-- 1.3.6.1.4.1.6296.101.23.7.3.5.1.34
		sleGponOnuPMStatsDetailUniEth3DayPackets OBJECT-TYPE
			SYNTAX Counter64
			MAX-ACCESS read-only
			STATUS current
			DESCRIPTION
				"The day number of octets received"
			::= { sleGponOnuPMStatsDetailUniEth3Entry 34 }


--   1.3.6.1.4.1.6296.101.23.7.3.5.1.35
-- 1.3.6.1.4.1.6296.101.23.7.3.5.1.35
		sleGponOnuPMStatsDetailUniEth3DayBcastPackets OBJECT-TYPE
			SYNTAX Counter64
			MAX-ACCESS read-write
			STATUS current
			DESCRIPTION
				"The day number of received good packets directed to the broadcast address"
			::= { sleGponOnuPMStatsDetailUniEth3Entry 35 }


--   1.3.6.1.4.1.6296.101.23.7.3.5.1.36
-- 1.3.6.1.4.1.6296.101.23.7.3.5.1.36
		sleGponOnuPMStatsDetailUniEth3DayMcastPackets OBJECT-TYPE
			SYNTAX Counter64
			MAX-ACCESS read-only
			STATUS current
			DESCRIPTION
				"The day number of received good packets directed to a multicast address."
			::= { sleGponOnuPMStatsDetailUniEth3Entry 36 }


--   1.3.6.1.4.1.6296.101.23.7.3.5.1.37
-- 1.3.6.1.4.1.6296.101.23.7.3.5.1.37
		sleGponOnuPMStatsDetailUniEth3DayUcastPackets OBJECT-TYPE
			SYNTAX Counter64
			MAX-ACCESS read-only
			STATUS current
			DESCRIPTION
				"The day number of received good packets directed to the unicast address"
			::= { sleGponOnuPMStatsDetailUniEth3Entry 37 }


--   1.3.6.1.4.1.6296.101.23.7.3.5.1.38
-- 1.3.6.1.4.1.6296.101.23.7.3.5.1.38
		sleGponOnuPMStatsDetailUniEth3DayUndersizePackets OBJECT-TYPE
			SYNTAX Counter64
			MAX-ACCESS read-only
			STATUS current
			DESCRIPTION
				"The day number of packets received that were less than 64 octets long"
			::= { sleGponOnuPMStatsDetailUniEth3Entry 38 }


--   1.3.6.1.4.1.6296.101.23.7.3.5.1.39
-- 1.3.6.1.4.1.6296.101.23.7.3.5.1.39
		sleGponOnuPMStatsDetailUniEth3DayFragments OBJECT-TYPE
			SYNTAX Counter64
			MAX-ACCESS read-only
			STATUS current
			DESCRIPTION
				"The day number of packets received that were fragments"
			::= { sleGponOnuPMStatsDetailUniEth3Entry 39 }


--   1.3.6.1.4.1.6296.101.23.7.3.5.1.40
-- 1.3.6.1.4.1.6296.101.23.7.3.5.1.40
		sleGponOnuPMStatsDetailUniEth3DayJabbers OBJECT-TYPE
			SYNTAX Counter64
			MAX-ACCESS read-only
			STATUS current
			DESCRIPTION
				"The day number of packets received that were jabbers"
			::= { sleGponOnuPMStatsDetailUniEth3Entry 40 }


--   1.3.6.1.4.1.6296.101.23.7.3.5.1.41
-- 1.3.6.1.4.1.6296.101.23.7.3.5.1.41
		sleGponOnuPMStatsDetailUniEth3DayPkt64Octets OBJECT-TYPE
			SYNTAX Counter64
			MAX-ACCESS read-only
			STATUS current
			DESCRIPTION
				"The day number of received packets (including bad packets) that were
				64 octets long,"
			::= { sleGponOnuPMStatsDetailUniEth3Entry 41 }


--   1.3.6.1.4.1.6296.101.23.7.3.5.1.42
-- 1.3.6.1.4.1.6296.101.23.7.3.5.1.42
		sleGponOnuPMStatsDetailUniEth3DayPkt65To127Octets OBJECT-TYPE
			SYNTAX Counter64
			MAX-ACCESS read-only
			STATUS current
			DESCRIPTION
				"The day number of received packets (including bad packets) that were
				65..127 octets long,"
			::= { sleGponOnuPMStatsDetailUniEth3Entry 42 }


--   1.3.6.1.4.1.6296.101.23.7.3.5.1.43
-- 1.3.6.1.4.1.6296.101.23.7.3.5.1.43
		sleGponOnuPMStatsDetailUniEth3DayPkt128To255Octets OBJECT-TYPE
			SYNTAX Counter64
			MAX-ACCESS read-write
			STATUS current
			DESCRIPTION
				"The day number of received packets (including bad packets) that were
				128..255 octets long,"
			::= { sleGponOnuPMStatsDetailUniEth3Entry 43 }


--   1.3.6.1.4.1.6296.101.23.7.3.5.1.44
-- 1.3.6.1.4.1.6296.101.23.7.3.5.1.44
		sleGponOnuPMStatsDetailUniEth3DayPkt256To511Octets OBJECT-TYPE
			SYNTAX Counter64
			MAX-ACCESS read-only
			STATUS current
			DESCRIPTION
				"The day number of received packets (including bad packets) that were
				256..511 octets long,"
			::= { sleGponOnuPMStatsDetailUniEth3Entry 44 }


--   1.3.6.1.4.1.6296.101.23.7.3.5.1.45
-- 1.3.6.1.4.1.6296.101.23.7.3.5.1.45
		sleGponOnuPMStatsDetailUniEth3DayPkt512To1023Octets OBJECT-TYPE
			SYNTAX Counter64
			MAX-ACCESS read-write
			STATUS current
			DESCRIPTION
				"The day number of packets (including bad packets) received that were
				512..1023 octets long,"
			::= { sleGponOnuPMStatsDetailUniEth3Entry 45 }


--   1.3.6.1.4.1.6296.101.23.7.3.5.1.46
-- 1.3.6.1.4.1.6296.101.23.7.3.5.1.46
		sleGponOnuPMStatsDetailUniEth3DayPkt1024To1518Octets OBJECT-TYPE
			SYNTAX Counter64
			MAX-ACCESS read-only
			STATUS current
			DESCRIPTION
				"The day number of packets (including bad packets) received that were
				1024..1518 octets long,"
			::= { sleGponOnuPMStatsDetailUniEth3Entry 46 }


--   1.3.6.1.4.1.6296.101.23.7.3.5.1.47
-- 1.3.6.1.4.1.6296.101.23.7.3.5.1.47
		sleGponOnuPMStatsDetailUniEth3TotalDropEvents OBJECT-TYPE
			SYNTAX Counter64
			MAX-ACCESS read-only
			STATUS current
			DESCRIPTION
				"The total number of events in which packets were dropped due to lack
				of resources."
			::= { sleGponOnuPMStatsDetailUniEth3Entry 47 }


--   1.3.6.1.4.1.6296.101.23.7.3.5.1.48
-- 1.3.6.1.4.1.6296.101.23.7.3.5.1.48
		sleGponOnuPMStatsDetailUniEth3TotalOctets OBJECT-TYPE
			SYNTAX Counter64
			MAX-ACCESS read-only
			STATUS current
			DESCRIPTION
				"The total number of octets received"
			::= { sleGponOnuPMStatsDetailUniEth3Entry 48 }


--   1.3.6.1.4.1.6296.101.23.7.3.5.1.49
-- 1.3.6.1.4.1.6296.101.23.7.3.5.1.49
		sleGponOnuPMStatsDetailUniEth3TotalPackets OBJECT-TYPE
			SYNTAX Counter64
			MAX-ACCESS read-only
			STATUS current
			DESCRIPTION
				"The total number of packets received,"
			::= { sleGponOnuPMStatsDetailUniEth3Entry 49 }


--   1.3.6.1.4.1.6296.101.23.7.3.5.1.50
-- 1.3.6.1.4.1.6296.101.23.7.3.5.1.50
		sleGponOnuPMStatsDetailUniEth3TotalBcastPackets OBJECT-TYPE
			SYNTAX Counter64
			MAX-ACCESS read-write
			STATUS current
			DESCRIPTION
				"The total number of received good packets directed to the broadcast address"
			::= { sleGponOnuPMStatsDetailUniEth3Entry 50 }


--   1.3.6.1.4.1.6296.101.23.7.3.5.1.51
-- 1.3.6.1.4.1.6296.101.23.7.3.5.1.51
		sleGponOnuPMStatsDetailUniEth3TotalMcastPackets OBJECT-TYPE
			SYNTAX Counter64
			MAX-ACCESS read-only
			STATUS current
			DESCRIPTION
				"The total number of received good packets directed to a multicast address."
			::= { sleGponOnuPMStatsDetailUniEth3Entry 51 }


--   1.3.6.1.4.1.6296.101.23.7.3.5.1.52
-- 1.3.6.1.4.1.6296.101.23.7.3.5.1.52
		sleGponOnuPMStatsDetailUniEth3TotalUcastPackets OBJECT-TYPE
			SYNTAX Counter64
			MAX-ACCESS read-only
			STATUS current
			DESCRIPTION
				"The total number of received good packets directed to the unicast address"
			::= { sleGponOnuPMStatsDetailUniEth3Entry 52 }


--   1.3.6.1.4.1.6296.101.23.7.3.5.1.53
-- 1.3.6.1.4.1.6296.101.23.7.3.5.1.53
		sleGponOnuPMStatsDetailUniEth3TotalUndersizePackets OBJECT-TYPE
			SYNTAX Counter64
			MAX-ACCESS read-only
			STATUS current
			DESCRIPTION
				"The total number of packets received that were less than 64 octets long"
			::= { sleGponOnuPMStatsDetailUniEth3Entry 53 }


--   1.3.6.1.4.1.6296.101.23.7.3.5.1.54
-- 1.3.6.1.4.1.6296.101.23.7.3.5.1.54
		sleGponOnuPMStatsDetailUniEth3TotalFragments OBJECT-TYPE
			SYNTAX Counter64
			MAX-ACCESS read-only
			STATUS current
			DESCRIPTION
				"The total number of packets received
				(fragments)"
			::= { sleGponOnuPMStatsDetailUniEth3Entry 54 }


--   1.3.6.1.4.1.6296.101.23.7.3.5.1.55
-- 1.3.6.1.4.1.6296.101.23.7.3.5.1.55
		sleGponOnuPMStatsDetailUniEth3TotalJabbers OBJECT-TYPE
			SYNTAX Counter64
			MAX-ACCESS read-only
			STATUS current
			DESCRIPTION
				"The total number of packets received
				(jabbers)"
			::= { sleGponOnuPMStatsDetailUniEth3Entry 55 }


--   1.3.6.1.4.1.6296.101.23.7.3.5.1.56
-- 1.3.6.1.4.1.6296.101.23.7.3.5.1.56
		sleGponOnuPMStatsDetailUniEth3TotalPkt64Octets OBJECT-TYPE
			SYNTAX Counter64
			MAX-ACCESS read-only
			STATUS current
			DESCRIPTION
				"The total number of received packets (including bad packets) that were
				64 octets long,"
			::= { sleGponOnuPMStatsDetailUniEth3Entry 56 }


--   1.3.6.1.4.1.6296.101.23.7.3.5.1.57
-- 1.3.6.1.4.1.6296.101.23.7.3.5.1.57
		sleGponOnuPMStatsDetailUniEth3TotalPkt65To127Octets OBJECT-TYPE
			SYNTAX Counter64
			MAX-ACCESS read-only
			STATUS current
			DESCRIPTION
				"The total number of received packets (including bad packets) that were
				65..127 octets long,"
			::= { sleGponOnuPMStatsDetailUniEth3Entry 57 }


--   1.3.6.1.4.1.6296.101.23.7.3.5.1.58
-- 1.3.6.1.4.1.6296.101.23.7.3.5.1.58
		sleGponOnuPMStatsDetailUniEth3TotalPkt128To255Octets OBJECT-TYPE
			SYNTAX Counter64
			MAX-ACCESS read-write
			STATUS current
			DESCRIPTION
				"The total number of packets (including bad packets) received that were
				128..255 octets long,"
			::= { sleGponOnuPMStatsDetailUniEth3Entry 58 }


--   1.3.6.1.4.1.6296.101.23.7.3.5.1.59
-- 1.3.6.1.4.1.6296.101.23.7.3.5.1.59
		sleGponOnuPMStatsDetailUniEth3TotalPkt256To511Octets OBJECT-TYPE
			SYNTAX Counter64
			MAX-ACCESS read-only
			STATUS current
			DESCRIPTION
				"The total number of packets (including bad packets) received that were
				256..511 octets long,"
			::= { sleGponOnuPMStatsDetailUniEth3Entry 59 }


--   1.3.6.1.4.1.6296.101.23.7.3.5.1.60
-- 1.3.6.1.4.1.6296.101.23.7.3.5.1.60
		sleGponOnuPMStatsDetailUniEth3TotalPkt512To1023Octets OBJECT-TYPE
			SYNTAX Counter64
			MAX-ACCESS read-write
			STATUS current
			DESCRIPTION
				"The total number of packets (including bad packets) received that were
				512..1023 octets long,"
			::= { sleGponOnuPMStatsDetailUniEth3Entry 60 }


--   1.3.6.1.4.1.6296.101.23.7.3.5.1.61
-- 1.3.6.1.4.1.6296.101.23.7.3.5.1.61
		sleGponOnuPMStatsDetailUniEth3TotalPkt1024To1518Octets OBJECT-TYPE
			SYNTAX Counter64
			MAX-ACCESS read-only
			STATUS current
			DESCRIPTION
				"The total number of packets (including bad packets) received that were
				1024..1518 octets long,"
			::= { sleGponOnuPMStatsDetailUniEth3Entry 61 }


--   1.3.6.1.4.1.6296.101.23.7.3.5.1.62
-- 1.3.6.1.4.1.6296.101.23.7.3.5.1.62
		sleGponOnuPMStatsDetailUniEth3ElapsedTimeAfterClear OBJECT-TYPE
			SYNTAX TimeTicks
			MAX-ACCESS read-only
			STATUS current
			DESCRIPTION
				"The number of packets for elapsed time after clear"
			::= { sleGponOnuPMStatsDetailUniEth3Entry 62 }


--   1.3.6.1.4.1.6296.101.23.7.3.5.1.63
-- 1.3.6.1.4.1.6296.101.23.7.3.5.1.63
		sleGponOnuPMStatsDetailUniEth3ElapsedTimeAfterUpdate OBJECT-TYPE
			SYNTAX Counter64
			MAX-ACCESS read-only
			STATUS current
			DESCRIPTION
				"The number of packets for elapsed time after update"
			::= { sleGponOnuPMStatsDetailUniEth3Entry 63 }


--   1.3.6.1.4.1.6296.101.23.7.3.5
-- 1.3.6.1.4.1.6296.101.23.7.3.6
		sleGponOnuPMStatsDetailGEMNCTPTable OBJECT-TYPE
			SYNTAX SEQUENCE OF SleGponOnuPMStatsDetailGEMNCTPEntry
			MAX-ACCESS not-accessible
			STATUS current
			DESCRIPTION
				"sleGponOnuPMStatsDetailUniEth3Table"
			::= { sleGponOnuPMStatisticsDetail 6 }


--   1.3.6.1.4.1.6296.101.23.7.3.5.1
-- 1.3.6.1.4.1.6296.101.23.7.3.6.1
		sleGponOnuPMStatsDetailGEMNCTPEntry OBJECT-TYPE
			SYNTAX SleGponOnuPMStatsDetailGEMNCTPEntry
			MAX-ACCESS not-accessible
			STATUS current
			DESCRIPTION
				"key: sleGponOltId, sleGponOnuId, sleGponOnuPMStatsDetailUniEthFrameUpUniPort"
			INDEX { sleGponOltId, sleGponOnuId, sleGponOnuPMStatsDetailGEMNCTPIndex }
			::= { sleGponOnuPMStatsDetailGEMNCTPTable 1 }


		SleGponOnuPMStatsDetailGEMNCTPEntry ::=
			SEQUENCE {
				sleGponOnuPMStatsDetailGEMNCTPIndex
					Integer32,
				sleGponOnuPMStatsDetailGEMNCTP
					Counter64,
				sleGponOnuPMStatsDetailGEMNCTPPre15mRxGemFrames
					Counter64,
				sleGponOnuPMStatsDetailGEMNCTPPre15mTxGemFrames
					Counter64,
				sleGponOnuPMStatsDetailGEMNCTPPre15mRxPayloadByte
					Counter64,
				sleGponOnuPMStatsDetailGEMNCTPPre15mTxPayloadByte
					Counter64,
				sleGponOnuPMStatsDetailGEMNCTPPre15mEncryptionKeyError
					Counter64,
				sleGponOnuPMStatsDetailGEMNCTPHourRxGemFrames
					Counter64,
				sleGponOnuPMStatsDetailGEMNCTPHourTxGemFrames
					Counter64,
				sleGponOnuPMStatsDetailGEMNCTPHourRxPayloadByte
					Counter64,
				sleGponOnuPMStatsDetailGEMNCTPHourTxPayloadByte
					Counter64,
				sleGponOnuPMStatsDetailGEMNCTPHourEncryptionKeyError
					Counter64,
				sleGponOnuPMStatsDetailGEMNCTPDayRxGemFrames
					Counter64,
				sleGponOnuPMStatsDetailGEMNCTPDayTxGemFrames
					Counter64,
				sleGponOnuPMStatsDetailGEMNCTPDayRxPayloadByte
					Counter64,
				sleGponOnuPMStatsDetailGEMNCTPDayTxPayloadByte
					Counter64,
				sleGponOnuPMStatsDetailGEMNCTPDayEncryptionKeyError
					Counter64,
				sleGponOnuPMStatsDetailGEMNCTPTotalRxGemFrames
					Counter64,
				sleGponOnuPMStatsDetailGEMNCTPTotalTxGemFrames
					Counter64,
				sleGponOnuPMStatsDetailGEMNCTPTotalRxPayloadByte
					Counter64,
				sleGponOnuPMStatsDetailGEMNCTPTotalTxPayloadByte
					Counter64,
				sleGponOnuPMStatsDetailGEMNCTPTotalEncryptionKeyError
					Counter64,
				sleGponOnuPMStatsDetailGEMNCTPElapsedTimeAfterClear
					TimeTicks,
				sleGponOnuPMStatsDetailGEMNCTPElapsedTimeAfterUpdate
					Counter64
			 }

--  1.3.6.1.4.1.6296.101.23.7.3.6.1.1
		sleGponOnuPMStatsDetailGEMNCTPIndex OBJECT-TYPE
			SYNTAX Integer32 (0..65535)
			MAX-ACCESS read-only
			STATUS current
			DESCRIPTION
				"The GEM Nctp index."
			::= { sleGponOnuPMStatsDetailGEMNCTPEntry 1 }


--  1.3.6.1.4.1.6296.101.23.7.3.6.1.2
		sleGponOnuPMStatsDetailGEMNCTP OBJECT-TYPE
			SYNTAX Counter64
			MAX-ACCESS read-only
			STATUS current
			DESCRIPTION
				"The GEM Nctp"
			::= { sleGponOnuPMStatsDetailGEMNCTPEntry 2 }


--  1.3.6.1.4.1.6296.101.23.7.3.6.1.3
		sleGponOnuPMStatsDetailGEMNCTPPre15mRxGemFrames OBJECT-TYPE
			SYNTAX Counter64
			MAX-ACCESS read-only
			STATUS current
			DESCRIPTION
				"The pre 15 minute number of Rx Gem Frames"
			::= { sleGponOnuPMStatsDetailGEMNCTPEntry 3 }


--  1.3.6.1.4.1.6296.101.23.7.3.6.1.4
		sleGponOnuPMStatsDetailGEMNCTPPre15mTxGemFrames OBJECT-TYPE
			SYNTAX Counter64
			MAX-ACCESS read-only
			STATUS current
			DESCRIPTION
				"The pre 15 minute number of Tx Gem Frames"
			::= { sleGponOnuPMStatsDetailGEMNCTPEntry 4 }


--  1.3.6.1.4.1.6296.101.23.7.3.6.1.5
		sleGponOnuPMStatsDetailGEMNCTPPre15mRxPayloadByte OBJECT-TYPE
			SYNTAX Counter64
			MAX-ACCESS read-only
			STATUS current
			DESCRIPTION
				"The pre 15 minute number of Rx Payload Byte"
			::= { sleGponOnuPMStatsDetailGEMNCTPEntry 5 }


--  1.3.6.1.4.1.6296.101.23.7.3.6.1.6
		sleGponOnuPMStatsDetailGEMNCTPPre15mTxPayloadByte OBJECT-TYPE
			SYNTAX Counter64
			MAX-ACCESS read-only
			STATUS current
			DESCRIPTION
				"The pre 15 minute number of Tx Payload Byte."
			::= { sleGponOnuPMStatsDetailGEMNCTPEntry 6 }


--  1.3.6.1.4.1.6296.101.23.7.3.6.1.7
		sleGponOnuPMStatsDetailGEMNCTPPre15mEncryptionKeyError OBJECT-TYPE
			SYNTAX Counter64
			MAX-ACCESS read-only
			STATUS current
			DESCRIPTION
				"The pre 15 minute number of Encryption Key Error"
			::= { sleGponOnuPMStatsDetailGEMNCTPEntry 7 }


--  1.3.6.1.4.1.6296.101.23.7.3.6.1.8
		sleGponOnuPMStatsDetailGEMNCTPHourRxGemFrames OBJECT-TYPE
			SYNTAX Counter64
			MAX-ACCESS read-only
			STATUS current
			DESCRIPTION
				"The hour number of Rx Gem Frames"
			::= { sleGponOnuPMStatsDetailGEMNCTPEntry 8 }


--  1.3.6.1.4.1.6296.101.23.7.3.6.1.9
		sleGponOnuPMStatsDetailGEMNCTPHourTxGemFrames OBJECT-TYPE
			SYNTAX Counter64
			MAX-ACCESS read-only
			STATUS current
			DESCRIPTION
				"The hour number of Tx Gem Frames"
			::= { sleGponOnuPMStatsDetailGEMNCTPEntry 9 }


--  1.3.6.1.4.1.6296.101.23.7.3.6.1.10
		sleGponOnuPMStatsDetailGEMNCTPHourRxPayloadByte OBJECT-TYPE
			SYNTAX Counter64
			MAX-ACCESS read-only
			STATUS current
			DESCRIPTION
				"The hour number of Rx Payload Byte"
			::= { sleGponOnuPMStatsDetailGEMNCTPEntry 10 }


--  1.3.6.1.4.1.6296.101.23.7.3.6.1.11
		sleGponOnuPMStatsDetailGEMNCTPHourTxPayloadByte OBJECT-TYPE
			SYNTAX Counter64
			MAX-ACCESS read-only
			STATUS current
			DESCRIPTION
				"The hour number of Tx Payload Byte"
			::= { sleGponOnuPMStatsDetailGEMNCTPEntry 11 }


--  1.3.6.1.4.1.6296.101.23.7.3.6.1.12
		sleGponOnuPMStatsDetailGEMNCTPHourEncryptionKeyError OBJECT-TYPE
			SYNTAX Counter64
			MAX-ACCESS read-only
			STATUS current
			DESCRIPTION
				"The hour number of Encryption Key Error"
			::= { sleGponOnuPMStatsDetailGEMNCTPEntry 12 }


--  1.3.6.1.4.1.6296.101.23.7.3.6.1.13
		sleGponOnuPMStatsDetailGEMNCTPDayRxGemFrames OBJECT-TYPE
			SYNTAX Counter64
			MAX-ACCESS read-only
			STATUS current
			DESCRIPTION
				"The day number of Rx Gem Frames"
			::= { sleGponOnuPMStatsDetailGEMNCTPEntry 13 }


--  1.3.6.1.4.1.6296.101.23.7.3.6.1.14
		sleGponOnuPMStatsDetailGEMNCTPDayTxGemFrames OBJECT-TYPE
			SYNTAX Counter64
			MAX-ACCESS read-only
			STATUS current
			DESCRIPTION
				"The day number of Tx Gem Frames"
			::= { sleGponOnuPMStatsDetailGEMNCTPEntry 14 }


--  1.3.6.1.4.1.6296.101.23.7.3.6.1.15
		sleGponOnuPMStatsDetailGEMNCTPDayRxPayloadByte OBJECT-TYPE
			SYNTAX Counter64
			MAX-ACCESS read-only
			STATUS current
			DESCRIPTION
				"The day number of Rx Payload Byte"
			::= { sleGponOnuPMStatsDetailGEMNCTPEntry 15 }


--  sleGponOnuPMStatsDetailGEMNCTPDayEncryptionKeyError
-- 1.3.6.1.4.1.6296.101.23.7.3.6.1.16
		sleGponOnuPMStatsDetailGEMNCTPDayTxPayloadByte OBJECT-TYPE
			SYNTAX Counter64
			MAX-ACCESS read-only
			STATUS current
			DESCRIPTION
				"The day number of Tx Payload Byte
				"
			::= { sleGponOnuPMStatsDetailGEMNCTPEntry 16 }


--  1.3.6.1.4.1.6296.101.23.7.3.6.1.17
		sleGponOnuPMStatsDetailGEMNCTPDayEncryptionKeyError OBJECT-TYPE
			SYNTAX Counter64
			MAX-ACCESS read-only
			STATUS current
			DESCRIPTION
				"The day number of Encryption Key Error"
			::= { sleGponOnuPMStatsDetailGEMNCTPEntry 17 }


--  1.3.6.1.4.1.6296.101.23.7.3.6.1.18
		sleGponOnuPMStatsDetailGEMNCTPTotalRxGemFrames OBJECT-TYPE
			SYNTAX Counter64
			MAX-ACCESS read-only
			STATUS current
			DESCRIPTION
				"The total number of Rx Gem Frames"
			::= { sleGponOnuPMStatsDetailGEMNCTPEntry 18 }


--  1.3.6.1.4.1.6296.101.23.7.3.6.1.19
		sleGponOnuPMStatsDetailGEMNCTPTotalTxGemFrames OBJECT-TYPE
			SYNTAX Counter64
			MAX-ACCESS read-only
			STATUS current
			DESCRIPTION
				"The total number of Tx Gem Frames"
			::= { sleGponOnuPMStatsDetailGEMNCTPEntry 19 }


--  1.3.6.1.4.1.6296.101.23.7.3.6.1.20
		sleGponOnuPMStatsDetailGEMNCTPTotalRxPayloadByte OBJECT-TYPE
			SYNTAX Counter64
			MAX-ACCESS read-write
			STATUS current
			DESCRIPTION
				"The total number of Rx Payload Byte"
			::= { sleGponOnuPMStatsDetailGEMNCTPEntry 20 }


--  1.3.6.1.4.1.6296.101.23.7.3.6.1.21
		sleGponOnuPMStatsDetailGEMNCTPTotalTxPayloadByte OBJECT-TYPE
			SYNTAX Counter64
			MAX-ACCESS read-only
			STATUS current
			DESCRIPTION
				"The total number of Tx Payload Byte"
			::= { sleGponOnuPMStatsDetailGEMNCTPEntry 21 }


--  1.3.6.1.4.1.6296.101.23.7.3.6.1.22
		sleGponOnuPMStatsDetailGEMNCTPTotalEncryptionKeyError OBJECT-TYPE
			SYNTAX Counter64
			MAX-ACCESS read-only
			STATUS current
			DESCRIPTION
				"The total number of Encryption Key Error"
			::= { sleGponOnuPMStatsDetailGEMNCTPEntry 22 }


--  1.3.6.1.4.1.6296.101.23.7.3.6.1.23
		sleGponOnuPMStatsDetailGEMNCTPElapsedTimeAfterClear OBJECT-TYPE
			SYNTAX TimeTicks
			MAX-ACCESS read-only
			STATUS current
			DESCRIPTION
				"The number of packets for elapsed time after clear"
			::= { sleGponOnuPMStatsDetailGEMNCTPEntry 23 }


--  1.3.6.1.4.1.6296.101.23.7.3.6.1.24
		sleGponOnuPMStatsDetailGEMNCTPElapsedTimeAfterUpdate OBJECT-TYPE
			SYNTAX Counter64
			MAX-ACCESS read-only
			STATUS current
			DESCRIPTION
				"The number of packets for elapsed time after update"
			::= { sleGponOnuPMStatsDetailGEMNCTPEntry 24 }


--  1.3.6.1.4.1.6296.101.23.7.4
		sleGponOnuPMStatsCurrentDetail OBJECT IDENTIFIER ::= { sleGponStatistics 4 }


--   1.3.6.1.4.1.6296.101.23.7.3.1
-- 1.3.6.1.4.1.6296.101.23.7.4.1
		sleGponOnuPMStatsCurrentDetailGEMTable OBJECT-TYPE
			SYNTAX SEQUENCE OF SleGponOnuPMStatsCurrentDetailGEMEntry
			MAX-ACCESS not-accessible
			STATUS current
			DESCRIPTION
				"sleGponOnuPMStatsCurrentDetailGEMTable"
			::= { sleGponOnuPMStatsCurrentDetail 1 }


--   1.3.6.1.4.1.6296.101.23.7.3.1.1
-- 1.3.6.1.4.1.6296.101.23.7.4.1.1
		sleGponOnuPMStatsCurrentDetailGEMEntry OBJECT-TYPE
			SYNTAX SleGponOnuPMStatsCurrentDetailGEMEntry
			MAX-ACCESS not-accessible
			STATUS current
			DESCRIPTION
				"key: sleGponOltId, sleGponOnuId, sleGponOnuPMStatsCurrentDetailGEMPortIndex"
			INDEX { sleGponOltId, sleGponOnuId, sleGponOnuPMStatsCurrentDetailGEMPortIndex }
			::= { sleGponOnuPMStatsCurrentDetailGEMTable 1 }


		SleGponOnuPMStatsCurrentDetailGEMEntry ::=
			SEQUENCE {
				sleGponOnuPMStatsCurrentDetailGEMPortIndex
					INTEGER,
				sleGponOnuPMStatsCurrentDetailGEMPort
					INTEGER,
				sleGponOnuPMStatsCurrentDetailGEMLostPackets
					Counter64,
				sleGponOnuPMStatsCurrentDetailGEMMisInsertedPackets
					Counter64,
				sleGponOnuPMStatsCurrentDetailGEMReceivedPackets
					Counter64,
				sleGponOnuPMStatsCurrentDetailGEMReceivedBlocks
					Counter64,
				sleGponOnuPMStatsCurrentDetailGEMTransmittedBlocks
					Counter64,
				sleGponOnuPMStatsCurrentDetailGEMImpairedBlocks
					Counter64
			 }

--  1.3.6.1.4.1.6296.101.23.7.4.1.1.1
		sleGponOnuPMStatsCurrentDetailGEMPortIndex OBJECT-TYPE
			SYNTAX INTEGER (1..65535)
			MAX-ACCESS read-only
			STATUS current
			DESCRIPTION
				"The GEM port index."
			::= { sleGponOnuPMStatsCurrentDetailGEMEntry 1 }


--   1.3.6.1.4.1.6296.101.23.7.3.1.1.1
-- 1.3.6.1.4.1.6296.101.23.7.4.1.1.2
		sleGponOnuPMStatsCurrentDetailGEMPort OBJECT-TYPE
			SYNTAX INTEGER (1..65535)
			MAX-ACCESS read-only
			STATUS current
			DESCRIPTION
				"The GEM port information"
			::= { sleGponOnuPMStatsCurrentDetailGEMEntry 2 }


--   1.3.6.1.4.1.6296.101.23.7.3.1.1.2
-- 1.3.6.1.4.1.6296.101.23.7.4.1.1.3
		sleGponOnuPMStatsCurrentDetailGEMLostPackets OBJECT-TYPE
			SYNTAX Counter64
			MAX-ACCESS read-only
			STATUS current
			DESCRIPTION
				"The number of lost packet "
			::= { sleGponOnuPMStatsCurrentDetailGEMEntry 3 }


--   1.3.6.1.4.1.6296.101.23.7.3.1.1.3
-- 1.3.6.1.4.1.6296.101.23.7.4.1.1.4
		sleGponOnuPMStatsCurrentDetailGEMMisInsertedPackets OBJECT-TYPE
			SYNTAX Counter64
			MAX-ACCESS read-only
			STATUS current
			DESCRIPTION
				"The number of mis inserted packet "
			::= { sleGponOnuPMStatsCurrentDetailGEMEntry 4 }


--   1.3.6.1.4.1.6296.101.23.7.3.1.1.4
-- 1.3.6.1.4.1.6296.101.23.7.4.1.1.5
		sleGponOnuPMStatsCurrentDetailGEMReceivedPackets OBJECT-TYPE
			SYNTAX Counter64
			MAX-ACCESS read-only
			STATUS current
			DESCRIPTION
				"The number of received packet"
			::= { sleGponOnuPMStatsCurrentDetailGEMEntry 5 }


--   1.3.6.1.4.1.6296.101.23.7.3.1.1.5
-- 1.3.6.1.4.1.6296.101.23.7.4.1.1.6
		sleGponOnuPMStatsCurrentDetailGEMReceivedBlocks OBJECT-TYPE
			SYNTAX Counter64
			MAX-ACCESS read-only
			STATUS current
			DESCRIPTION
				"The number of received blocks"
			::= { sleGponOnuPMStatsCurrentDetailGEMEntry 6 }


--   1.3.6.1.4.1.6296.101.23.7.3.1.1.6
-- 1.3.6.1.4.1.6296.101.23.7.4.1.1.7
		sleGponOnuPMStatsCurrentDetailGEMTransmittedBlocks OBJECT-TYPE
			SYNTAX Counter64
			MAX-ACCESS read-only
			STATUS current
			DESCRIPTION
				"The number of transmitted blocks"
			::= { sleGponOnuPMStatsCurrentDetailGEMEntry 7 }


--   1.3.6.1.4.1.6296.101.23.7.3.1.1.7
-- 1.3.6.1.4.1.6296.101.23.7.4.1.1.8
		sleGponOnuPMStatsCurrentDetailGEMImpairedBlocks OBJECT-TYPE
			SYNTAX Counter64
			MAX-ACCESS read-only
			STATUS current
			DESCRIPTION
				"The number of impaired blocks"
			::= { sleGponOnuPMStatsCurrentDetailGEMEntry 8 }


--   1.3.6.1.4.1.6296.101.23.7.3.2
-- 1.3.6.1.4.1.6296.101.23.7.4.2
		sleGponOnuPMStatsCurrentDetailAniTable OBJECT-TYPE
			SYNTAX SEQUENCE OF SleGponOnuPMStatsCurrentDetailAniEntry
			MAX-ACCESS not-accessible
			STATUS current
			DESCRIPTION
				"sleGponOnuPMStatsCurrentDetailAniTable"
			::= { sleGponOnuPMStatsCurrentDetail 2 }


--   1.3.6.1.4.1.6296.101.23.7.3.2.1
-- 1.3.6.1.4.1.6296.101.23.7.4.2.1
		sleGponOnuPMStatsCurrentDetailAniEntry OBJECT-TYPE
			SYNTAX SleGponOnuPMStatsCurrentDetailAniEntry
			MAX-ACCESS not-accessible
			STATUS current
			DESCRIPTION
				"key: sleGponOltId, sleGponOnuId, sleGponOnuPMStatsCurrentDetailAniPortIndex"
			INDEX { sleGponOltId, sleGponOnuId, sleGponOnuPMStatsCurrentDetailAniPortIndex }
			::= { sleGponOnuPMStatsCurrentDetailAniTable 1 }


		SleGponOnuPMStatsCurrentDetailAniEntry ::=
			SEQUENCE {
				sleGponOnuPMStatsCurrentDetailAniPortIndex
					INTEGER,
				sleGponOnuPMStatsCurrentDetailAniPort
					INTEGER,
				sleGponOnuPMStatsCurrentDetailAniDiscardedFrames
					Counter64
			 }

--  1.3.6.1.4.1.6296.101.23.7.4.2.1.1
		sleGponOnuPMStatsCurrentDetailAniPortIndex OBJECT-TYPE
			SYNTAX INTEGER (1..65535)
			MAX-ACCESS read-only
			STATUS current
			DESCRIPTION
				"The ANI port index."
			::= { sleGponOnuPMStatsCurrentDetailAniEntry 1 }


--   1.3.6.1.4.1.6296.101.23.7.3.2.1.1
-- 1.3.6.1.4.1.6296.101.23.7.4.2.1.2
		sleGponOnuPMStatsCurrentDetailAniPort OBJECT-TYPE
			SYNTAX INTEGER (1..65535)
			MAX-ACCESS read-only
			STATUS current
			DESCRIPTION
				"The Ani port information"
			::= { sleGponOnuPMStatsCurrentDetailAniEntry 2 }


--   1.3.6.1.4.1.6296.101.23.7.3.2.1.2
-- 1.3.6.1.4.1.6296.101.23.7.4.2.1.3
		sleGponOnuPMStatsCurrentDetailAniDiscardedFrames OBJECT-TYPE
			SYNTAX Counter64
			MAX-ACCESS read-only
			STATUS current
			DESCRIPTION
				"The number of lost discarded frames"
			::= { sleGponOnuPMStatsCurrentDetailAniEntry 3 }


--   1.3.6.1.4.1.6296.101.23.7.3.3
-- 1.3.6.1.4.1.6296.101.23.7.4.3
		sleGponOnuPMStatsCurrentDetailUniEthFrameUpTable OBJECT-TYPE
			SYNTAX SEQUENCE OF SleGponOnuPMStatsCurrentDetailUniEthFrameUpEntry
			MAX-ACCESS not-accessible
			STATUS current
			DESCRIPTION
				"sleGponOnuPMStatsCurrentDetailUniEthFrameUpTable"
			::= { sleGponOnuPMStatsCurrentDetail 3 }


--   1.3.6.1.4.1.6296.101.23.7.3.3.1
-- 1.3.6.1.4.1.6296.101.23.7.4.3.1
		sleGponOnuPMStatsCurrentDetailUniEthFrameUpEntry OBJECT-TYPE
			SYNTAX SleGponOnuPMStatsCurrentDetailUniEthFrameUpEntry
			MAX-ACCESS not-accessible
			STATUS current
			DESCRIPTION
				"key: sleGponOltId, sleGponOnuId, sleGponOnuPMStatsCurrentDetailUniEthFrameUpUniPort"
			INDEX { sleGponOltId, sleGponOnuId, sleGponOnuPMStatsCurrentDetailUniEthFrameUpUniPort }
			::= { sleGponOnuPMStatsCurrentDetailUniEthFrameUpTable 1 }


		SleGponOnuPMStatsCurrentDetailUniEthFrameUpEntry ::=
			SEQUENCE {
				sleGponOnuPMStatsCurrentDetailUniEthFrameUpUniPort
					INTEGER,
				sleGponOnuPMStatsCurrentDetailUniEthFrameUpDropEvents
					Counter64,
				sleGponOnuPMStatsCurrentDetailUniEthFrameUpOctets
					Counter64,
				sleGponOnuPMStatsCurrentDetailUniEthFrameUpPackets
					Counter64,
				sleGponOnuPMStatsCurrentDetailUniEthFrameUpBcastPackets
					Counter64,
				sleGponOnuPMStatsCurrentDetailUniEthFrameUpMcastPackets
					Counter64,
				sleGponOnuPMStatsCurrentDetailUniEthFrameUpUcastPackets
					Counter64,
				sleGponOnuPMStatsCurrentDetailUniEthFrameUpCRCErroredPackets
					Counter64,
				sleGponOnuPMStatsCurrentDetailUniEthFrameUpUndersizePackets
					Counter64,
				sleGponOnuPMStatsCurrentDetailUniEthFrameUpOversizePackets
					Counter64,
				sleGponOnuPMStatsCurrentDetailUniEthFrameUpPkt64Octets
					Counter64,
				sleGponOnuPMStatsCurrentDetailUniEthFrameUpPkt65To127Octets
					Counter64,
				sleGponOnuPMStatsCurrentDetailUniEthFrameUpPkt128To255
					Counter64,
				sleGponOnuPMStatsCurrentDetailUniEthFrameUpPkt256To511
					Counter64,
				sleGponOnuPMStatsCurrentDetailUniEthFrameUpPkt512To1023
					Counter64,
				sleGponOnuPMStatsCurrentDetailUniEthFrameUpPkt1024To1518
					Counter64,
				sleGponOnuPMStatsCurrentDetailUniEthFrameUpAvgPackets
					Counter64,
				sleGponOnuPMStatsCurrentDetailUniEthFrameUpAvgBits
					Counter64,
				sleGponOnuPMStatsCurrentDetailUniEthFrameTotalUpAvgPackets
					Counter64,
				sleGponOnuPMStatsCurrentDetailUniEthFrameTotalUpAvgBits
					Counter64
			 }

--   1.3.6.1.4.1.6296.101.23.7.3.3.1.1
-- 1.3.6.1.4.1.6296.101.23.7.4.3.1.1
		sleGponOnuPMStatsCurrentDetailUniEthFrameUpUniPort OBJECT-TYPE
			SYNTAX INTEGER (1..65535)
			MAX-ACCESS read-only
			STATUS current
			DESCRIPTION
				"The Uni port information"
			::= { sleGponOnuPMStatsCurrentDetailUniEthFrameUpEntry 1 }


--   1.3.6.1.4.1.6296.101.23.7.3.3.1.2
-- 1.3.6.1.4.1.6296.101.23.7.4.3.1.2
		sleGponOnuPMStatsCurrentDetailUniEthFrameUpDropEvents OBJECT-TYPE
			SYNTAX Counter64
			MAX-ACCESS read-only
			STATUS current
			DESCRIPTION
				"The number of events in which packets were dropped due to lack
				of resources."
			::= { sleGponOnuPMStatsCurrentDetailUniEthFrameUpEntry 2 }


--   1.3.6.1.4.1.6296.101.23.7.3.3.1.3
-- 1.3.6.1.4.1.6296.101.23.7.4.3.1.3
		sleGponOnuPMStatsCurrentDetailUniEthFrameUpOctets OBJECT-TYPE
			SYNTAX Counter64
			MAX-ACCESS read-only
			STATUS current
			DESCRIPTION
				"The number of octets received"
			::= { sleGponOnuPMStatsCurrentDetailUniEthFrameUpEntry 3 }


--   1.3.6.1.4.1.6296.101.23.7.3.3.1.4
-- 1.3.6.1.4.1.6296.101.23.7.4.3.1.4
		sleGponOnuPMStatsCurrentDetailUniEthFrameUpPackets OBJECT-TYPE
			SYNTAX Counter64
			MAX-ACCESS read-only
			STATUS current
			DESCRIPTION
				"The number of packets received,"
			::= { sleGponOnuPMStatsCurrentDetailUniEthFrameUpEntry 4 }


--   1.3.6.1.4.1.6296.101.23.7.3.3.1.5
-- 1.3.6.1.4.1.6296.101.23.7.4.3.1.5
		sleGponOnuPMStatsCurrentDetailUniEthFrameUpBcastPackets OBJECT-TYPE
			SYNTAX Counter64
			MAX-ACCESS read-only
			STATUS current
			DESCRIPTION
				"The number of received good packets directed to the broadcast address"
			::= { sleGponOnuPMStatsCurrentDetailUniEthFrameUpEntry 5 }


--   1.3.6.1.4.1.6296.101.23.7.3.3.1.6
-- 1.3.6.1.4.1.6296.101.23.7.4.3.1.6
		sleGponOnuPMStatsCurrentDetailUniEthFrameUpMcastPackets OBJECT-TYPE
			SYNTAX Counter64
			MAX-ACCESS read-only
			STATUS current
			DESCRIPTION
				"The number of received good packets directed to a multicast address."
			::= { sleGponOnuPMStatsCurrentDetailUniEthFrameUpEntry 6 }


--   1.3.6.1.4.1.6296.101.23.7.3.3.1.7
-- 1.3.6.1.4.1.6296.101.23.7.4.3.1.7
		sleGponOnuPMStatsCurrentDetailUniEthFrameUpUcastPackets OBJECT-TYPE
			SYNTAX Counter64
			MAX-ACCESS read-only
			STATUS current
			DESCRIPTION
				"The number of received good packets directed to the unicast address"
			::= { sleGponOnuPMStatsCurrentDetailUniEthFrameUpEntry 7 }


--   1.3.6.1.4.1.6296.101.23.7.3.3.1.8
-- 1.3.6.1.4.1.6296.101.23.7.4.3.1.8
		sleGponOnuPMStatsCurrentDetailUniEthFrameUpCRCErroredPackets OBJECT-TYPE
			SYNTAX Counter64
			MAX-ACCESS read-only
			STATUS current
			DESCRIPTION
				"The number of packets received that had a length"
			::= { sleGponOnuPMStatsCurrentDetailUniEthFrameUpEntry 8 }


--   1.3.6.1.4.1.6296.101.23.7.3.3.1.9
-- 1.3.6.1.4.1.6296.101.23.7.4.3.1.9
		sleGponOnuPMStatsCurrentDetailUniEthFrameUpUndersizePackets OBJECT-TYPE
			SYNTAX Counter64
			MAX-ACCESS read-only
			STATUS current
			DESCRIPTION
				"The number of packets received that were less than 64 octets long"
			::= { sleGponOnuPMStatsCurrentDetailUniEthFrameUpEntry 9 }


--   1.3.6.1.4.1.6296.101.23.7.3.3.1.10
-- 1.3.6.1.4.1.6296.101.23.7.4.3.1.10
		sleGponOnuPMStatsCurrentDetailUniEthFrameUpOversizePackets OBJECT-TYPE
			SYNTAX Counter64
			MAX-ACCESS read-only
			STATUS current
			DESCRIPTION
				"The number of packets received that were longer than 1518 octets"
			::= { sleGponOnuPMStatsCurrentDetailUniEthFrameUpEntry 10 }


--   1.3.6.1.4.1.6296.101.23.7.3.3.1.11
-- 1.3.6.1.4.1.6296.101.23.7.4.3.1.11
		sleGponOnuPMStatsCurrentDetailUniEthFrameUpPkt64Octets OBJECT-TYPE
			SYNTAX Counter64
			MAX-ACCESS read-only
			STATUS current
			DESCRIPTION
				"The number of received packets (including bad packets) that were
				64 octets long,
				"
			::= { sleGponOnuPMStatsCurrentDetailUniEthFrameUpEntry 11 }


--   1.3.6.1.4.1.6296.101.23.7.3.3.1.12
-- 1.3.6.1.4.1.6296.101.23.7.4.3.1.12
		sleGponOnuPMStatsCurrentDetailUniEthFrameUpPkt65To127Octets OBJECT-TYPE
			SYNTAX Counter64
			MAX-ACCESS read-only
			STATUS current
			DESCRIPTION
				"The number of received packets (including bad packets) that were
				65..127 octets long,
				"
			::= { sleGponOnuPMStatsCurrentDetailUniEthFrameUpEntry 12 }


--   1.3.6.1.4.1.6296.101.23.7.3.3.1.13
-- 1.3.6.1.4.1.6296.101.23.7.4.3.1.13
		sleGponOnuPMStatsCurrentDetailUniEthFrameUpPkt128To255 OBJECT-TYPE
			SYNTAX Counter64
			MAX-ACCESS read-only
			STATUS current
			DESCRIPTION
				"The number of packets (including bad packets) received that were
				128..255 octets long,
				"
			::= { sleGponOnuPMStatsCurrentDetailUniEthFrameUpEntry 13 }


--   1.3.6.1.4.1.6296.101.23.7.3.3.1.14
-- 1.3.6.1.4.1.6296.101.23.7.4.3.1.14
		sleGponOnuPMStatsCurrentDetailUniEthFrameUpPkt256To511 OBJECT-TYPE
			SYNTAX Counter64
			MAX-ACCESS read-only
			STATUS current
			DESCRIPTION
				"The number of packets (including bad packets) received that were
				256..511 octets long,
				"
			::= { sleGponOnuPMStatsCurrentDetailUniEthFrameUpEntry 14 }


--   1.3.6.1.4.1.6296.101.23.7.3.3.1.15
-- 1.3.6.1.4.1.6296.101.23.7.4.3.1.15
		sleGponOnuPMStatsCurrentDetailUniEthFrameUpPkt512To1023 OBJECT-TYPE
			SYNTAX Counter64
			MAX-ACCESS read-only
			STATUS current
			DESCRIPTION
				"The number of packets (including bad packets) received that were
				512..1023 octets long,
				"
			::= { sleGponOnuPMStatsCurrentDetailUniEthFrameUpEntry 15 }


--   1.3.6.1.4.1.6296.101.23.7.3.3.1.16
-- 1.3.6.1.4.1.6296.101.23.7.4.3.1.16
		sleGponOnuPMStatsCurrentDetailUniEthFrameUpPkt1024To1518 OBJECT-TYPE
			SYNTAX Counter64
			MAX-ACCESS read-only
			STATUS current
			DESCRIPTION
				"The number of packets (including bad packets) received that were
				1024..1518 octets long,
				"
			::= { sleGponOnuPMStatsCurrentDetailUniEthFrameUpEntry 16 }


--  1.3.6.1.4.1.6296.101.23.7.4.3.1.17
		sleGponOnuPMStatsCurrentDetailUniEthFrameUpAvgPackets OBJECT-TYPE
			SYNTAX Counter64
			MAX-ACCESS read-only
			STATUS current
			DESCRIPTION
				"1.3.6.1.4.1.6296.101.23.7.4.3.1.17"
			::= { sleGponOnuPMStatsCurrentDetailUniEthFrameUpEntry 17 }


--  1.3.6.1.4.1.6296.101.23.7.4.3.1.18
		sleGponOnuPMStatsCurrentDetailUniEthFrameUpAvgBits OBJECT-TYPE
			SYNTAX Counter64
			MAX-ACCESS read-only
			STATUS current
			DESCRIPTION
				"1.3.6.1.4.1.6296.101.23.7.4.3.1.18"
			::= { sleGponOnuPMStatsCurrentDetailUniEthFrameUpEntry 18 }


--  1.3.6.1.4.1.6296.101.23.7.4.3.1.19
		sleGponOnuPMStatsCurrentDetailUniEthFrameTotalUpAvgPackets OBJECT-TYPE
			SYNTAX Counter64
			MAX-ACCESS read-only
			STATUS current
			DESCRIPTION
				"1.3.6.1.4.1.6296.101.23.7.4.3.1.19"
			::= { sleGponOnuPMStatsCurrentDetailUniEthFrameUpEntry 19 }


--  1.3.6.1.4.1.6296.101.23.7.4.3.1.20
		sleGponOnuPMStatsCurrentDetailUniEthFrameTotalUpAvgBits OBJECT-TYPE
			SYNTAX Counter64
			MAX-ACCESS read-only
			STATUS current
			DESCRIPTION
				"1.3.6.1.4.1.6296.101.23.7.4.3.1.20"
			::= { sleGponOnuPMStatsCurrentDetailUniEthFrameUpEntry 20 }


--   1.3.6.1.4.1.6296.101.23.7.3.4
-- 1.3.6.1.4.1.6296.101.23.7.4.4
		sleGponOnuPMStatsCurrentDetailUniEthFrameDownTable OBJECT-TYPE
			SYNTAX SEQUENCE OF SleGponOnuPMStatsCurrentDetailUniEthFrameDownEntry
			MAX-ACCESS not-accessible
			STATUS current
			DESCRIPTION
				"sleGponOnuPMStatsCurrentDetailUniEthFrameDownTable"
			::= { sleGponOnuPMStatsCurrentDetail 4 }


--   1.3.6.1.4.1.6296.101.23.7.3.4.1
-- 1.3.6.1.4.1.6296.101.23.7.4.4.1
		sleGponOnuPMStatsCurrentDetailUniEthFrameDownEntry OBJECT-TYPE
			SYNTAX SleGponOnuPMStatsCurrentDetailUniEthFrameDownEntry
			MAX-ACCESS not-accessible
			STATUS current
			DESCRIPTION
				"key: sleGponOltId, sleGponOnuId, sleGponOnuPMStatsCurrentDetailUniEthFrameDownUniPort"
			INDEX { sleGponOltId, sleGponOnuId, sleGponOnuPMStatsCurrentDetailUniEthFrameDownUniPort }
			::= { sleGponOnuPMStatsCurrentDetailUniEthFrameDownTable 1 }


		SleGponOnuPMStatsCurrentDetailUniEthFrameDownEntry ::=
			SEQUENCE {
				sleGponOnuPMStatsCurrentDetailUniEthFrameDownUniPort
					Integer32,
				sleGponOnuPMStatsCurrentDetailUniEthFrameDownDropEvents
					Counter64,
				sleGponOnuPMStatsCurrentDetailUniEthFrameDownOctets
					Counter64,
				sleGponOnuPMStatsCurrentDetailUniEthFrameDownPackets
					Counter64,
				sleGponOnuPMStatsCurrentDetailUniEthFrameDownBcastPackets
					Counter64,
				sleGponOnuPMStatsCurrentDetailUniEthFrameDownMcastPackets
					Counter64,
				sleGponOnuPMStatsCurrentDetailUniEthFrameDownUcastPackets
					Counter64,
				sleGponOnuPMStatsCurrentDetailUniEthFrameDownCRCErroredPackets
					Counter64,
				sleGponOnuPMStatsCurrentDetailUniEthFrameDownUndersizePackets
					Counter64,
				sleGponOnuPMStatsCurrentDetailUniEthFrameDownOversizePackets
					Counter64,
				sleGponOnuPMStatsCurrentDetailUniEthFrameDownPkt64Octets
					Counter64,
				sleGponOnuPMStatsCurrentDetailUniEthFrameDownPkt65To127Octets
					Counter64,
				sleGponOnuPMStatsCurrentDetailUniEthFrameDownPkt128To255Octets
					Counter64,
				sleGponOnuPMStatsCurrentDetailUniEthFrameDownmPkt256To511Octets
					Counter64,
				sleGponOnuPMStatsCurrentDetailUniEthFrameDownmPkt512To1023Octets
					Counter64,
				sleGponOnuPMStatsCurrentDetailUniEthFrameDownPkt1024To1518Octets
					Counter64,
				sleGponOnuPMStatsCurrentDetailUniEthFrameDownAvgPackets
					Counter64,
				sleGponOnuPMStatsCurrentDetailUniEthFrameDownAvgBits
					Counter64,
				sleGponOnuPMStatsCurrentDetailUniEthFrameTotalDownAvgPackets
					Counter64,
				sleGponOnuPMStatsCurrentDetailUniEthFrameTotalDownAvgBits
					Counter64
			 }

--   1.3.6.1.4.1.6296.101.23.7.3.4.1.1
-- 1.3.6.1.4.1.6296.101.23.7.4.4.1.1
		sleGponOnuPMStatsCurrentDetailUniEthFrameDownUniPort OBJECT-TYPE
			SYNTAX Integer32 (1..65535)
			MAX-ACCESS read-only
			STATUS current
			DESCRIPTION
				"sleGponOltId, sleGponOnuId, sleGponOnuPMStatsDetailUniEthFrameUpUniPort"
			::= { sleGponOnuPMStatsCurrentDetailUniEthFrameDownEntry 1 }


--   1.3.6.1.4.1.6296.101.23.7.3.4.1.2
-- 1.3.6.1.4.1.6296.101.23.7.4.4.1.2
		sleGponOnuPMStatsCurrentDetailUniEthFrameDownDropEvents OBJECT-TYPE
			SYNTAX Counter64
			MAX-ACCESS read-only
			STATUS current
			DESCRIPTION
				"The pre 15 minute number of events in which packets were dropped due to lack of resources.
				"
			::= { sleGponOnuPMStatsCurrentDetailUniEthFrameDownEntry 2 }


--   1.3.6.1.4.1.6296.101.23.7.3.4.1.3
-- 1.3.6.1.4.1.6296.101.23.7.4.4.1.3
		sleGponOnuPMStatsCurrentDetailUniEthFrameDownOctets OBJECT-TYPE
			SYNTAX Counter64
			MAX-ACCESS read-only
			STATUS current
			DESCRIPTION
				"The pre 15 minute number of octets received"
			::= { sleGponOnuPMStatsCurrentDetailUniEthFrameDownEntry 3 }


--   1.3.6.1.4.1.6296.101.23.7.3.4.1.4
-- 1.3.6.1.4.1.6296.101.23.7.4.4.1.4
		sleGponOnuPMStatsCurrentDetailUniEthFrameDownPackets OBJECT-TYPE
			SYNTAX Counter64
			MAX-ACCESS read-only
			STATUS current
			DESCRIPTION
				"The pre 15 minute number of packets received,"
			::= { sleGponOnuPMStatsCurrentDetailUniEthFrameDownEntry 4 }


--   1.3.6.1.4.1.6296.101.23.7.3.4.1.5
-- 1.3.6.1.4.1.6296.101.23.7.4.4.1.5
		sleGponOnuPMStatsCurrentDetailUniEthFrameDownBcastPackets OBJECT-TYPE
			SYNTAX Counter64
			MAX-ACCESS read-only
			STATUS current
			DESCRIPTION
				"The pre 15 minute number of received good packets directed to the broadcast address"
			::= { sleGponOnuPMStatsCurrentDetailUniEthFrameDownEntry 5 }


--   1.3.6.1.4.1.6296.101.23.7.3.4.1.6
-- 1.3.6.1.4.1.6296.101.23.7.4.4.1.6
		sleGponOnuPMStatsCurrentDetailUniEthFrameDownMcastPackets OBJECT-TYPE
			SYNTAX Counter64
			MAX-ACCESS read-only
			STATUS current
			DESCRIPTION
				"The pre 15 minute number of received good packets directed to a multicast address."
			::= { sleGponOnuPMStatsCurrentDetailUniEthFrameDownEntry 6 }


--   1.3.6.1.4.1.6296.101.23.7.3.4.1.7
-- 1.3.6.1.4.1.6296.101.23.7.4.4.1.7
		sleGponOnuPMStatsCurrentDetailUniEthFrameDownUcastPackets OBJECT-TYPE
			SYNTAX Counter64
			MAX-ACCESS read-only
			STATUS current
			DESCRIPTION
				"The pre 15 minute number of received good packets directed to the unicast address"
			::= { sleGponOnuPMStatsCurrentDetailUniEthFrameDownEntry 7 }


--   1.3.6.1.4.1.6296.101.23.7.3.4.1.8
-- 1.3.6.1.4.1.6296.101.23.7.4.4.1.8
		sleGponOnuPMStatsCurrentDetailUniEthFrameDownCRCErroredPackets OBJECT-TYPE
			SYNTAX Counter64
			MAX-ACCESS read-only
			STATUS current
			DESCRIPTION
				"The pre 15 minute number of packets received that had a length"
			::= { sleGponOnuPMStatsCurrentDetailUniEthFrameDownEntry 8 }


--   1.3.6.1.4.1.6296.101.23.7.3.4.1.9
-- 1.3.6.1.4.1.6296.101.23.7.4.4.1.9
		sleGponOnuPMStatsCurrentDetailUniEthFrameDownUndersizePackets OBJECT-TYPE
			SYNTAX Counter64
			MAX-ACCESS read-only
			STATUS current
			DESCRIPTION
				"The pre 15 minute number of packets received that were less than 64 octets long"
			::= { sleGponOnuPMStatsCurrentDetailUniEthFrameDownEntry 9 }


--   1.3.6.1.4.1.6296.101.23.7.3.4.1.10
-- 1.3.6.1.4.1.6296.101.23.7.4.4.1.10
		sleGponOnuPMStatsCurrentDetailUniEthFrameDownOversizePackets OBJECT-TYPE
			SYNTAX Counter64
			MAX-ACCESS read-only
			STATUS current
			DESCRIPTION
				"The pre 15 minute number of packets received that were longer than 1518 octets"
			::= { sleGponOnuPMStatsCurrentDetailUniEthFrameDownEntry 10 }


--   1.3.6.1.4.1.6296.101.23.7.3.4.1.11
-- 1.3.6.1.4.1.6296.101.23.7.4.4.1.11
		sleGponOnuPMStatsCurrentDetailUniEthFrameDownPkt64Octets OBJECT-TYPE
			SYNTAX Counter64
			MAX-ACCESS read-only
			STATUS current
			DESCRIPTION
				"The pre 15 minute number of received packets (including bad packets) that were
				64 octets long,"
			::= { sleGponOnuPMStatsCurrentDetailUniEthFrameDownEntry 11 }


--   1.3.6.1.4.1.6296.101.23.7.3.4.1.12
-- 1.3.6.1.4.1.6296.101.23.7.4.4.1.12
		sleGponOnuPMStatsCurrentDetailUniEthFrameDownPkt65To127Octets OBJECT-TYPE
			SYNTAX Counter64
			MAX-ACCESS read-only
			STATUS current
			DESCRIPTION
				"The pre 15 minute number of received packets (including bad packets) that were
				65..127 octets long,"
			::= { sleGponOnuPMStatsCurrentDetailUniEthFrameDownEntry 12 }


--   1.3.6.1.4.1.6296.101.23.7.3.4.1.13
-- 1.3.6.1.4.1.6296.101.23.7.4.4.1.13
		sleGponOnuPMStatsCurrentDetailUniEthFrameDownPkt128To255Octets OBJECT-TYPE
			SYNTAX Counter64
			MAX-ACCESS read-only
			STATUS current
			DESCRIPTION
				"The pre 15 minute number of packets (including bad packets) received that were
				128..255 octets long,"
			::= { sleGponOnuPMStatsCurrentDetailUniEthFrameDownEntry 13 }


--   1.3.6.1.4.1.6296.101.23.7.3.4.1.14
-- 1.3.6.1.4.1.6296.101.23.7.4.4.1.14
		sleGponOnuPMStatsCurrentDetailUniEthFrameDownmPkt256To511Octets OBJECT-TYPE
			SYNTAX Counter64
			MAX-ACCESS read-only
			STATUS current
			DESCRIPTION
				"The pre 15 minute number of packets (including bad packets) received that were
				256..511 octets long,"
			::= { sleGponOnuPMStatsCurrentDetailUniEthFrameDownEntry 14 }


--   1.3.6.1.4.1.6296.101.23.7.3.4.1.15
-- 1.3.6.1.4.1.6296.101.23.7.4.4.1.15
		sleGponOnuPMStatsCurrentDetailUniEthFrameDownmPkt512To1023Octets OBJECT-TYPE
			SYNTAX Counter64
			MAX-ACCESS read-only
			STATUS current
			DESCRIPTION
				"The pre 15 minute number of packets (including bad packets) received that were
				512..1023 octets long,"
			::= { sleGponOnuPMStatsCurrentDetailUniEthFrameDownEntry 15 }


--   1.3.6.1.4.1.6296.101.23.7.3.4.1.16
-- 1.3.6.1.4.1.6296.101.23.7.4.4.1.16
		sleGponOnuPMStatsCurrentDetailUniEthFrameDownPkt1024To1518Octets OBJECT-TYPE
			SYNTAX Counter64
			MAX-ACCESS read-only
			STATUS current
			DESCRIPTION
				"The pre 15 minute number of packets (including bad packets) received that were
				1024..1518 octets long,"
			::= { sleGponOnuPMStatsCurrentDetailUniEthFrameDownEntry 16 }


--  1.3.6.1.4.1.6296.101.23.7.4.4.1.17
		sleGponOnuPMStatsCurrentDetailUniEthFrameDownAvgPackets OBJECT-TYPE
			SYNTAX Counter64
			MAX-ACCESS read-only
			STATUS current
			DESCRIPTION
				"1.3.6.1.4.1.6296.101.23.7.4.4.1.17"
			::= { sleGponOnuPMStatsCurrentDetailUniEthFrameDownEntry 17 }


--  1.3.6.1.4.1.6296.101.23.7.4.4.1.18
		sleGponOnuPMStatsCurrentDetailUniEthFrameDownAvgBits OBJECT-TYPE
			SYNTAX Counter64
			MAX-ACCESS read-only
			STATUS current
			DESCRIPTION
				"1.3.6.1.4.1.6296.101.23.7.4.4.1.18"
			::= { sleGponOnuPMStatsCurrentDetailUniEthFrameDownEntry 18 }


--  1.3.6.1.4.1.6296.101.23.7.4.4.1.19
		sleGponOnuPMStatsCurrentDetailUniEthFrameTotalDownAvgPackets OBJECT-TYPE
			SYNTAX Counter64
			MAX-ACCESS read-only
			STATUS current
			DESCRIPTION
				"1.3.6.1.4.1.6296.101.23.7.4.4.1.19"
			::= { sleGponOnuPMStatsCurrentDetailUniEthFrameDownEntry 19 }


--  1.3.6.1.4.1.6296.101.23.7.4.4.1.20
		sleGponOnuPMStatsCurrentDetailUniEthFrameTotalDownAvgBits OBJECT-TYPE
			SYNTAX Counter64
			MAX-ACCESS read-only
			STATUS current
			DESCRIPTION
				"1.3.6.1.4.1.6296.101.23.7.4.4.1.20"
			::= { sleGponOnuPMStatsCurrentDetailUniEthFrameDownEntry 20 }


--   1.3.6.1.4.1.6296.101.23.7.3.5
-- 1.3.6.1.4.1.6296.101.23.7.4.5
		sleGponOnuPMStatsCurrentDetailUniEth3Table OBJECT-TYPE
			SYNTAX SEQUENCE OF SleGponOnuPMStatsCurrentDetailUniEth3Entry
			MAX-ACCESS not-accessible
			STATUS current
			DESCRIPTION
				"sleGponOnuPMStatsCurrentDetailUniEth3Table"
			::= { sleGponOnuPMStatsCurrentDetail 5 }


--   1.3.6.1.4.1.6296.101.23.7.3.5.1
-- 1.3.6.1.4.1.6296.101.23.7.4.5.1
		sleGponOnuPMStatsCurrentDetailUniEth3Entry OBJECT-TYPE
			SYNTAX SleGponOnuPMStatsCurrentDetailUniEth3Entry
			MAX-ACCESS not-accessible
			STATUS current
			DESCRIPTION
				"key: sleGponOltId, sleGponOnuId, sleGponOnuPMStatsCurrentDetailUniEth3UniPort"
			INDEX { sleGponOltId, sleGponOnuId, sleGponOnuPMStatsCurrentDetailUniEth3UniPort }
			::= { sleGponOnuPMStatsCurrentDetailUniEth3Table 1 }


		SleGponOnuPMStatsCurrentDetailUniEth3Entry ::=
			SEQUENCE {
				sleGponOnuPMStatsCurrentDetailUniEth3UniPort
					Integer32,
				sleGponOnuPMStatsCurrentDetailUniEth3DropEvents
					Counter64,
				sleGponOnuPMStatsCurrentDetailUniEth3Octets
					Counter64,
				sleGponOnuPMStatsCurrentDetailUniEth3Packets
					Counter64,
				sleGponOnuPMStatsCurrentDetailUniEth3BcastPackets
					Counter64,
				sleGponOnuPMStatsCurrentDetailUniEth3McastPackets
					Counter64,
				sleGponOnuPMStatsCurrentDetailUniEth3UcastPackets
					Counter64,
				sleGponOnuPMStatsCurrentDetailUniEth3UndersizePackets
					Counter64,
				sleGponOnuPMStatsCurrentDetailUniEth3Fragments
					Counter64,
				sleGponOnuPMStatsCurrentDetailUniEth3Jabbers
					Counter64,
				sleGponOnuPMStatsCurrentDetailUniEth3Pkt64Octets
					Counter64,
				sleGponOnuPMStatsCurrentDetailUniEth3Pkt65To127Octets
					Counter64,
				sleGponOnuPMStatsCurrentDetailUniEth3Pkt128To255Octets
					Counter64,
				sleGponOnuPMStatsCurrentDetailUniEth3Pkt256To511Octets
					Counter64,
				sleGponOnuPMStatsCurrentDetailUniEth3Pkt512To1023Octets
					Counter64,
				sleGponOnuPMStatsCurrentDetailUniEth3Pkt1024To1518Octets
					Counter64
			 }

--   1.3.6.1.4.1.6296.101.23.7.3.5.1.1
-- 1.3.6.1.4.1.6296.101.23.7.4.5.1.1
		sleGponOnuPMStatsCurrentDetailUniEth3UniPort OBJECT-TYPE
			SYNTAX Integer32 (1..65535)
			MAX-ACCESS read-only
			STATUS current
			DESCRIPTION
				"The Uni port information"
			::= { sleGponOnuPMStatsCurrentDetailUniEth3Entry 1 }


--   1.3.6.1.4.1.6296.101.23.7.3.5.1.2
-- 1.3.6.1.4.1.6296.101.23.7.4.5.1.2
		sleGponOnuPMStatsCurrentDetailUniEth3DropEvents OBJECT-TYPE
			SYNTAX Counter64
			MAX-ACCESS read-only
			STATUS current
			DESCRIPTION
				"The number of events in which packets were dropped due to lack of resources."
			::= { sleGponOnuPMStatsCurrentDetailUniEth3Entry 2 }


--   1.3.6.1.4.1.6296.101.23.7.3.5.1.3
-- 1.3.6.1.4.1.6296.101.23.7.4.5.1.3
		sleGponOnuPMStatsCurrentDetailUniEth3Octets OBJECT-TYPE
			SYNTAX Counter64
			MAX-ACCESS read-only
			STATUS current
			DESCRIPTION
				"The number of octets received"
			::= { sleGponOnuPMStatsCurrentDetailUniEth3Entry 3 }


--   1.3.6.1.4.1.6296.101.23.7.3.5.1.4
-- 1.3.6.1.4.1.6296.101.23.7.4.5.1.4
		sleGponOnuPMStatsCurrentDetailUniEth3Packets OBJECT-TYPE
			SYNTAX Counter64
			MAX-ACCESS read-only
			STATUS current
			DESCRIPTION
				"The number of packets received, including bad packets"
			::= { sleGponOnuPMStatsCurrentDetailUniEth3Entry 4 }


--   1.3.6.1.4.1.6296.101.23.7.3.5.1.5
-- 1.3.6.1.4.1.6296.101.23.7.4.5.1.5
		sleGponOnuPMStatsCurrentDetailUniEth3BcastPackets OBJECT-TYPE
			SYNTAX Counter64
			MAX-ACCESS read-only
			STATUS current
			DESCRIPTION
				"The number of received good packets directed to the broadcast address."
			::= { sleGponOnuPMStatsCurrentDetailUniEth3Entry 5 }


--   1.3.6.1.4.1.6296.101.23.7.3.5.1.6
-- 1.3.6.1.4.1.6296.101.23.7.4.5.1.6
		sleGponOnuPMStatsCurrentDetailUniEth3McastPackets OBJECT-TYPE
			SYNTAX Counter64
			MAX-ACCESS read-only
			STATUS current
			DESCRIPTION
				"The number of received good packets directed to a multicast address."
			::= { sleGponOnuPMStatsCurrentDetailUniEth3Entry 6 }


--   1.3.6.1.4.1.6296.101.23.7.3.5.1.7
-- 1.3.6.1.4.1.6296.101.23.7.4.5.1.7
		sleGponOnuPMStatsCurrentDetailUniEth3UcastPackets OBJECT-TYPE
			SYNTAX Counter64
			MAX-ACCESS read-only
			STATUS current
			DESCRIPTION
				"The number of received good packets directed to a unicast address."
			::= { sleGponOnuPMStatsCurrentDetailUniEth3Entry 7 }


--   1.3.6.1.4.1.6296.101.23.7.3.5.1.8
-- 1.3.6.1.4.1.6296.101.23.7.4.5.1.8
		sleGponOnuPMStatsCurrentDetailUniEth3UndersizePackets OBJECT-TYPE
			SYNTAX Counter64
			MAX-ACCESS read-only
			STATUS current
			DESCRIPTION
				"The number of packets received that were less than 64 octets long"
			::= { sleGponOnuPMStatsCurrentDetailUniEth3Entry 8 }


--   1.3.6.1.4.1.6296.101.23.7.3.5.1.9
-- 1.3.6.1.4.1.6296.101.23.7.4.5.1.9
		sleGponOnuPMStatsCurrentDetailUniEth3Fragments OBJECT-TYPE
			SYNTAX Counter64
			MAX-ACCESS read-only
			STATUS current
			DESCRIPTION
				"The number of packets received that were fragments"
			::= { sleGponOnuPMStatsCurrentDetailUniEth3Entry 9 }


--   1.3.6.1.4.1.6296.101.23.7.3.5.1.10
-- 1.3.6.1.4.1.6296.101.23.7.4.5.1.10
		sleGponOnuPMStatsCurrentDetailUniEth3Jabbers OBJECT-TYPE
			SYNTAX Counter64
			MAX-ACCESS read-only
			STATUS current
			DESCRIPTION
				"The number of packets received that were jabbers"
			::= { sleGponOnuPMStatsCurrentDetailUniEth3Entry 10 }


--   1.3.6.1.4.1.6296.101.23.7.3.5.1.11
-- 1.3.6.1.4.1.6296.101.23.7.4.5.1.11
		sleGponOnuPMStatsCurrentDetailUniEth3Pkt64Octets OBJECT-TYPE
			SYNTAX Counter64
			MAX-ACCESS read-only
			STATUS current
			DESCRIPTION
				"The number of received packets (including bad packets) that were 64 octets long"
			::= { sleGponOnuPMStatsCurrentDetailUniEth3Entry 11 }


--   1.3.6.1.4.1.6296.101.23.7.3.5.1.12
-- 1.3.6.1.4.1.6296.101.23.7.4.5.1.12
		sleGponOnuPMStatsCurrentDetailUniEth3Pkt65To127Octets OBJECT-TYPE
			SYNTAX Counter64
			MAX-ACCESS read-only
			STATUS current
			DESCRIPTION
				"The number of received packets (including bad packets) that were 65..127 octets long"
			::= { sleGponOnuPMStatsCurrentDetailUniEth3Entry 12 }


--   1.3.6.1.4.1.6296.101.23.7.3.5.1.13
-- 1.3.6.1.4.1.6296.101.23.7.4.5.1.13
		sleGponOnuPMStatsCurrentDetailUniEth3Pkt128To255Octets OBJECT-TYPE
			SYNTAX Counter64
			MAX-ACCESS read-only
			STATUS current
			DESCRIPTION
				"The number of packets (including bad packets) received that were 128..255 octets long"
			::= { sleGponOnuPMStatsCurrentDetailUniEth3Entry 13 }


--   1.3.6.1.4.1.6296.101.23.7.3.5.1.14
-- 1.3.6.1.4.1.6296.101.23.7.4.5.1.14
		sleGponOnuPMStatsCurrentDetailUniEth3Pkt256To511Octets OBJECT-TYPE
			SYNTAX Counter64
			MAX-ACCESS read-only
			STATUS current
			DESCRIPTION
				"The number of packets (including bad packets) received that were 256..511 octets long"
			::= { sleGponOnuPMStatsCurrentDetailUniEth3Entry 14 }


--   1.3.6.1.4.1.6296.101.23.7.3.5.1.15
-- 1.3.6.1.4.1.6296.101.23.7.4.5.1.15
		sleGponOnuPMStatsCurrentDetailUniEth3Pkt512To1023Octets OBJECT-TYPE
			SYNTAX Counter64
			MAX-ACCESS read-only
			STATUS current
			DESCRIPTION
				"The number of packets (including bad packets) received that were 512..1023 octets long"
			::= { sleGponOnuPMStatsCurrentDetailUniEth3Entry 15 }


--   1.3.6.1.4.1.6296.101.23.7.3.5.1.16
-- 1.3.6.1.4.1.6296.101.23.7.4.5.1.16
		sleGponOnuPMStatsCurrentDetailUniEth3Pkt1024To1518Octets OBJECT-TYPE
			SYNTAX Counter64
			MAX-ACCESS read-only
			STATUS current
			DESCRIPTION
				"The number of packets (including bad packets) received that were 1024..1518 octets long"
			::= { sleGponOnuPMStatsCurrentDetailUniEth3Entry 16 }


--   1.3.6.1.4.1.6296.101.23.7.3.5
-- 1.3.6.1.4.1.6296.101.23.7.4.6
		sleGponOnuPMStatsCurrentDetailGEMNCTPTable OBJECT-TYPE
			SYNTAX SEQUENCE OF SleGponOnuPMStatsCurrentDetailGEMNCTPEntry
			MAX-ACCESS not-accessible
			STATUS current
			DESCRIPTION
				"sleGponOnuPMStatsCurrentDetailUniEth3Table"
			::= { sleGponOnuPMStatsCurrentDetail 6 }


--   1.3.6.1.4.1.6296.101.23.7.3.5.1
-- 1.3.6.1.4.1.6296.101.23.7.4.6.1
		sleGponOnuPMStatsCurrentDetailGEMNCTPEntry OBJECT-TYPE
			SYNTAX SleGponOnuPMStatsCurrentDetailGEMNCTPEntry
			MAX-ACCESS not-accessible
			STATUS current
			DESCRIPTION
				"key: sleGponOltId, sleGponOnuId, sleGponOnuPMStatsCurrentDetailUniEth3UniPort"
			INDEX { sleGponOltId, sleGponOnuId, sleGponOnuPMStatsCurrentDetailGEMNCTPIndex }
			::= { sleGponOnuPMStatsCurrentDetailGEMNCTPTable 1 }


		SleGponOnuPMStatsCurrentDetailGEMNCTPEntry ::=
			SEQUENCE {
				sleGponOnuPMStatsCurrentDetailGEMNCTPIndex
					Integer32,
				sleGponOnuPMStatsCurrentDetailGEMNCTP
					Counter64,
				sleGponOnuPMStatsCurrentDetailGEMNCTPRxGemFrames
					Counter64,
				sleGponOnuPMStatsCurrentDetailGEMNCTPTxGemFrames
					Counter64,
				sleGponOnuPMStatsCurrentDetailGEMNCTPRxPayloadByte
					Counter64,
				sleGponOnuPMStatsCurrentDetailGEMNCTPTxPayloadByte
					Counter64,
				sleGponOnuPMStatsCurrentDetailGEMNCTPEncryptionKeyError
					Counter64
			 }

--   1.3.6.1.4.1.6296.101.23.7.3.5.1.1
-- 1.3.6.1.4.1.6296.101.23.7.4.6.1.1
		sleGponOnuPMStatsCurrentDetailGEMNCTPIndex OBJECT-TYPE
			SYNTAX Integer32 (1..65535)
			MAX-ACCESS read-only
			STATUS current
			DESCRIPTION
				"The GEM NCTP index."
			::= { sleGponOnuPMStatsCurrentDetailGEMNCTPEntry 1 }


--  1.3.6.1.4.1.6296.101.23.7.4.6.1.2
		sleGponOnuPMStatsCurrentDetailGEMNCTP OBJECT-TYPE
			SYNTAX Counter64
			MAX-ACCESS read-only
			STATUS current
			DESCRIPTION
				"The GEM NCTP"
			::= { sleGponOnuPMStatsCurrentDetailGEMNCTPEntry 2 }


--  1.3.6.1.4.1.6296.101.23.7.4.6.1.3
		sleGponOnuPMStatsCurrentDetailGEMNCTPRxGemFrames OBJECT-TYPE
			SYNTAX Counter64
			MAX-ACCESS read-only
			STATUS current
			DESCRIPTION
				"The number of Rx Gem Frames"
			::= { sleGponOnuPMStatsCurrentDetailGEMNCTPEntry 3 }


--  1.3.6.1.4.1.6296.101.23.7.4.6.1.4
		sleGponOnuPMStatsCurrentDetailGEMNCTPTxGemFrames OBJECT-TYPE
			SYNTAX Counter64
			MAX-ACCESS read-only
			STATUS current
			DESCRIPTION
				"The number of Tx Gem Frames"
			::= { sleGponOnuPMStatsCurrentDetailGEMNCTPEntry 4 }


--  1.3.6.1.4.1.6296.101.23.7.4.6.1.5
		sleGponOnuPMStatsCurrentDetailGEMNCTPRxPayloadByte OBJECT-TYPE
			SYNTAX Counter64
			MAX-ACCESS read-only
			STATUS current
			DESCRIPTION
				"The number of Rx Payload Byte"
			::= { sleGponOnuPMStatsCurrentDetailGEMNCTPEntry 5 }


--  1.3.6.1.4.1.6296.101.23.7.4.6.1.6
		sleGponOnuPMStatsCurrentDetailGEMNCTPTxPayloadByte OBJECT-TYPE
			SYNTAX Counter64
			MAX-ACCESS read-only
			STATUS current
			DESCRIPTION
				"The number of Tx Payload Byte"
			::= { sleGponOnuPMStatsCurrentDetailGEMNCTPEntry 6 }


--  1.3.6.1.4.1.6296.101.23.7.4.6.1.7
		sleGponOnuPMStatsCurrentDetailGEMNCTPEncryptionKeyError OBJECT-TYPE
			SYNTAX Counter64
			MAX-ACCESS read-only
			STATUS current
			DESCRIPTION
				"The number of Encryption Key Error"
			::= { sleGponOnuPMStatsCurrentDetailGEMNCTPEntry 7 }


--  1.3.6.1.4.1.6296.101.23.7.5
		sleGponOnuIgmpPmStatistics OBJECT IDENTIFIER ::= { sleGponStatistics 5 }


--  1.3.6.1.4.1.6296.101.23.7.5.1
		sleGponOnuIgmpPmStatisticsTable OBJECT-TYPE
			SYNTAX SEQUENCE OF SleGponOnuIgmpPmStatisticsEntry
			MAX-ACCESS not-accessible
			STATUS current
			DESCRIPTION
				"Description."
			::= { sleGponOnuIgmpPmStatistics 1 }


--  1.3.6.1.4.1.6296.101.23.7.5.1.1
		sleGponOnuIgmpPmStatisticsEntry OBJECT-TYPE
			SYNTAX SleGponOnuIgmpPmStatisticsEntry
			MAX-ACCESS not-accessible
			STATUS current
			DESCRIPTION
				"Description."
			INDEX { sleGponOltId, sleGponOnuId, sleGponOnuIgmpPmStatisticsSlotType, sleGponOnuIgmpPmStatisticsPortIndex }
			::= { sleGponOnuIgmpPmStatisticsTable 1 }


		SleGponOnuIgmpPmStatisticsEntry ::=
			SEQUENCE {
				sleGponOnuIgmpPmStatisticsSlotType
					INTEGER,
				sleGponOnuIgmpPmStatisticsPortIndex
					Integer32,
				sleGponOnuIgmpPmStatisticsSuccessfulJoins
					Integer32,
				sleGponOnuIgmpPmStatisticsUnsuccessfulJoins
					Integer32,
				sleGponOnuIgmpPmStatisticsLeaveMessages
					Integer32,
				sleGponOnuIgmpPmStatisticsGeneralQueries
					Integer32,
				sleGponOnuIgmpPmStatisticsSpecificQueries
					Integer32,
				sleGponOnuIgmpPmStatisticsInvalidIGMPMessages
					Integer32
			 }

--  1.3.6.1.4.1.6296.101.23.7.5.1.1.1
		sleGponOnuIgmpPmStatisticsSlotType OBJECT-TYPE
			SYNTAX INTEGER
				{
				ethernet(1),
				pots(2),
				ces(3),
				video(4),
				virtualEthernet(5)
				}
			MAX-ACCESS read-only
			STATUS current
			DESCRIPTION
				"The slot type"
			::= { sleGponOnuIgmpPmStatisticsEntry 1 }


--  1.3.6.1.4.1.6296.101.23.7.5.1.1.2
		sleGponOnuIgmpPmStatisticsPortIndex OBJECT-TYPE
			SYNTAX Integer32 (1..65535)
			MAX-ACCESS read-only
			STATUS current
			DESCRIPTION
				"The port index."
			::= { sleGponOnuIgmpPmStatisticsEntry 2 }


--  1.3.6.1.4.1.6296.101.23.7.5.1.1.3
		sleGponOnuIgmpPmStatisticsSuccessfulJoins OBJECT-TYPE
			SYNTAX Integer32
			MAX-ACCESS read-only
			STATUS current
			DESCRIPTION
				"The successful Joins."
			::= { sleGponOnuIgmpPmStatisticsEntry 3 }


--  1.3.6.1.4.1.6296.101.23.7.5.1.1.4
		sleGponOnuIgmpPmStatisticsUnsuccessfulJoins OBJECT-TYPE
			SYNTAX Integer32
			MAX-ACCESS read-only
			STATUS current
			DESCRIPTION
				"The unsuccessful Joins."
			::= { sleGponOnuIgmpPmStatisticsEntry 4 }


--  1.3.6.1.4.1.6296.101.23.7.5.1.1.5
		sleGponOnuIgmpPmStatisticsLeaveMessages OBJECT-TYPE
			SYNTAX Integer32
			MAX-ACCESS read-only
			STATUS current
			DESCRIPTION
				"The leave messages."
			::= { sleGponOnuIgmpPmStatisticsEntry 5 }


--  1.3.6.1.4.1.6296.101.23.7.5.1.1.6
		sleGponOnuIgmpPmStatisticsGeneralQueries OBJECT-TYPE
			SYNTAX Integer32
			MAX-ACCESS read-only
			STATUS current
			DESCRIPTION
				"The General Queries "
			::= { sleGponOnuIgmpPmStatisticsEntry 6 }


--  1.3.6.1.4.1.6296.101.23.7.5.1.1.7
		sleGponOnuIgmpPmStatisticsSpecificQueries OBJECT-TYPE
			SYNTAX Integer32
			MAX-ACCESS read-only
			STATUS current
			DESCRIPTION
				"The Specific Queries"
			::= { sleGponOnuIgmpPmStatisticsEntry 7 }


--  1.3.6.1.4.1.6296.101.23.7.5.1.1.8
		sleGponOnuIgmpPmStatisticsInvalidIGMPMessages OBJECT-TYPE
			SYNTAX Integer32
			MAX-ACCESS read-only
			STATUS current
			DESCRIPTION
				"The Invalid IGMP Messages"
			::= { sleGponOnuIgmpPmStatisticsEntry 8 }


--  1.3.6.1.4.1.6296.101.23.7.5.2
		sleGponOnuIgmpPmStatisticsControl OBJECT IDENTIFIER ::= { sleGponOnuIgmpPmStatistics 2 }


--  1.3.6.1.4.1.6296.101.23.7.5.2.1
		sleGponOnuIgmpPmStatisticsControlRequest OBJECT-TYPE
			SYNTAX INTEGER
				{
				updateOnuIgmpPmData(1),
				clearOnuIgmpPmData(2)
				}
			MAX-ACCESS read-write
			STATUS current
			DESCRIPTION
				"The request of a user command"
			::= { sleGponOnuIgmpPmStatisticsControl 1 }


--  1.3.6.1.4.1.6296.101.23.7.5.2.2
		sleGponOnuIgmpPmStatisticsControlStatus OBJECT-TYPE
			SYNTAX SleControlStatusType
			MAX-ACCESS read-only
			STATUS current
			DESCRIPTION
				"The status of user command"
			::= { sleGponOnuIgmpPmStatisticsControl 2 }


--  1.3.6.1.4.1.6296.101.23.7.5.2.3
		sleGponOnuIgmpPmStatisticsControlTimer OBJECT-TYPE
			SYNTAX Gauge32
			MAX-ACCESS read-write
			STATUS current
			DESCRIPTION
				"The maximum time for the manager for a long running user command"
			::= { sleGponOnuIgmpPmStatisticsControl 3 }


--  1.3.6.1.4.1.6296.101.23.7.5.2.4
		sleGponOnuIgmpPmStatisticsControlTimeStamp OBJECT-TYPE
			SYNTAX TimeTicks
			MAX-ACCESS read-only
			STATUS current
			DESCRIPTION
				"The time stamp of the last command(end of command)"
			::= { sleGponOnuIgmpPmStatisticsControl 4 }


--  1.3.6.1.4.1.6296.101.23.7.5.2.5
		sleGponOnuIgmpPmStatisticsControlReqResult OBJECT-TYPE
			SYNTAX SleControlRequestResultType
			MAX-ACCESS read-only
			STATUS current
			DESCRIPTION
				"The result of the last user command"
			::= { sleGponOnuIgmpPmStatisticsControl 5 }


		sleGponOnuIgmpPmStatisticsControlOltIndex OBJECT-TYPE
			SYNTAX Integer32 (1..2147483647)
			MAX-ACCESS read-write
			STATUS current
			DESCRIPTION
				"The OLT index."
			::= { sleGponOnuIgmpPmStatisticsControl 6 }


--  1.3.6.1.4.1.6296.101.23.7.5.2.7
		sleGponOnuIgmpPmStatisticsControlOnuIndex OBJECT-TYPE
			SYNTAX Integer32
			MAX-ACCESS read-write
			STATUS current
			DESCRIPTION
				"The ONU index."
			::= { sleGponOnuIgmpPmStatisticsControl 7 }


--  1.3.6.1.4.1.6296.101.23.7.5.2.8
		sleGponOnuIgmpPmStatisticsControlSlotType OBJECT-TYPE
			SYNTAX INTEGER
				{
				ethernet(1),
				pots(2),
				ces(3),
				video(4),
				virtualEthernet(5)
				}
			MAX-ACCESS read-write
			STATUS current
			DESCRIPTION
				"The slot type."
			::= { sleGponOnuIgmpPmStatisticsControl 8 }


--  1.3.6.1.4.1.6296.101.23.7.5.2.9
		sleGponOnuIgmpPmStatisticsControlPortIndex OBJECT-TYPE
			SYNTAX Integer32
			MAX-ACCESS read-write
			STATUS current
			DESCRIPTION
				"The port index."
			::= { sleGponOnuIgmpPmStatisticsControl 9 }


--  1.3.6.1.4.1.6296.101.23.7.5.3
		sleGponOnuIgmpPmStatisticsNotification OBJECT IDENTIFIER ::= { sleGponOnuIgmpPmStatistics 3 }


--  1.3.6.1.4.1.6296.101.23.7.5.3.1
		sleGponOnuIgmpPmStatisticsPmDataChanged NOTIFICATION-TYPE
			OBJECTS { sleGponOnuIgmpPmStatisticsControlRequest, sleGponOnuIgmpPmStatisticsControlTimeStamp, sleGponOnuIgmpPmStatisticsControlReqResult, sleGponOnuIgmpPmStatisticsControlOltIndex, sleGponOnuIgmpPmStatisticsControlOnuIndex,
				sleGponOnuIgmpPmStatisticsControlSlotType, sleGponOnuIgmpPmStatisticsControlPortIndex }
			STATUS current
			DESCRIPTION
				"updateOnuIgmpPmData"
			::= { sleGponOnuIgmpPmStatisticsNotification 1 }


--  1.3.6.1.4.1.6296.101.23.7.5.3.2
		sleGponOnuIgmpPmStatisticsPmDataCleared NOTIFICATION-TYPE
			OBJECTS { sleGponOnuIgmpPmStatisticsControlRequest, sleGponOnuIgmpPmStatisticsControlTimeStamp, sleGponOnuIgmpPmStatisticsControlReqResult, sleGponOnuIgmpPmStatisticsControlOltIndex, sleGponOnuIgmpPmStatisticsControlOnuIndex,
				sleGponOnuIgmpPmStatisticsControlSlotType, sleGponOnuIgmpPmStatisticsControlPortIndex }
			STATUS current
			DESCRIPTION
				"clearOnuIgmpPmData"
			::= { sleGponOnuIgmpPmStatisticsNotification 2 }


--  1.3.6.1.4.1.6296.101.23.7.6
		sleGponOnuPmStatsUniAvg OBJECT IDENTIFIER ::= { sleGponStatistics 6 }


--  1.3.6.1.4.1.6296.101.23.7.6.1
		sleGponOnuPmStatsUniAvgTable OBJECT-TYPE
			SYNTAX SEQUENCE OF SleGponOnuPmStatsUniAvgEntry
			MAX-ACCESS not-accessible
			STATUS current
			DESCRIPTION
				"Description."
			::= { sleGponOnuPmStatsUniAvg 1 }


--  1.3.6.1.4.1.6296.101.23.7.6.1.1
		sleGponOnuPmStatsUniAvgEntry OBJECT-TYPE
			SYNTAX SleGponOnuPmStatsUniAvgEntry
			MAX-ACCESS not-accessible
			STATUS current
			DESCRIPTION
				"Description."
			INDEX { sleGponOltId, sleGponOnuId, sleGponOnuPmStatsUniAvgPort }
			::= { sleGponOnuPmStatsUniAvgTable 1 }


		SleGponOnuPmStatsUniAvgEntry ::=
			SEQUENCE {
				sleGponOnuPmStatsUniAvgPort
					Integer32,
				sleGponOnuPmStatsUniAvgEthFrameUpPackets
					Counter64,
				sleGponOnuPmStatsUniAvgEthFrameUpBits
					Counter64,
				sleGponOnuPmStatsUniAvgEthFrameDownPackets
					Counter64,
				sleGponOnuPmStatsUniAvgEthFrameDownBits
					Counter64
			 }

--  1.3.6.1.4.1.6296.101.23.7.6.1.1.1
		sleGponOnuPmStatsUniAvgPort OBJECT-TYPE
			SYNTAX Integer32 (1..65535)
			MAX-ACCESS read-only
			STATUS current
			DESCRIPTION
				"The port index."
			::= { sleGponOnuPmStatsUniAvgEntry 1 }


--  1.3.6.1.4.1.6296.101.23.7.6.1.1.2
		sleGponOnuPmStatsUniAvgEthFrameUpPackets OBJECT-TYPE
			SYNTAX Counter64
			MAX-ACCESS read-only
			STATUS current
			DESCRIPTION
				"The average frame up packets."
			::= { sleGponOnuPmStatsUniAvgEntry 2 }


--  1.3.6.1.4.1.6296.101.23.7.6.1.1.3
		sleGponOnuPmStatsUniAvgEthFrameUpBits OBJECT-TYPE
			SYNTAX Counter64
			MAX-ACCESS read-only
			STATUS current
			DESCRIPTION
				"The average frame up bits."
			::= { sleGponOnuPmStatsUniAvgEntry 3 }


--  1.3.6.1.4.1.6296.101.23.7.6.1.1.4
		sleGponOnuPmStatsUniAvgEthFrameDownPackets OBJECT-TYPE
			SYNTAX Counter64
			MAX-ACCESS read-only
			STATUS current
			DESCRIPTION
				"The average frame down packets."
			::= { sleGponOnuPmStatsUniAvgEntry 4 }


--  1.3.6.1.4.1.6296.101.23.7.6.1.1.5
		sleGponOnuPmStatsUniAvgEthFrameDownBits OBJECT-TYPE
			SYNTAX Counter64
			MAX-ACCESS read-only
			STATUS current
			DESCRIPTION
				"The average frame down bits."
			::= { sleGponOnuPmStatsUniAvgEntry 5 }


--  1.3.6.1.4.1.6296.101.23.7.6.2
		sleGponOnuPmStatsUniAvgControl OBJECT IDENTIFIER ::= { sleGponOnuPmStatsUniAvg 2 }


--  1.3.6.1.4.1.6296.101.23.7.6.2.1
		sleGponOnuPmStatsUniAvgControlRequest OBJECT-TYPE
			SYNTAX INTEGER { updateAvgStats(1) }
			MAX-ACCESS read-write
			STATUS current
			DESCRIPTION
				"The request of a user command"
			::= { sleGponOnuPmStatsUniAvgControl 1 }


--  1.3.6.1.4.1.6296.101.23.7.6.2.2
		sleGponOnuPmStatsUniAvgControlStatus OBJECT-TYPE
			SYNTAX SleControlStatusType
			MAX-ACCESS read-only
			STATUS current
			DESCRIPTION
				"The status of user command"
			::= { sleGponOnuPmStatsUniAvgControl 2 }


--  1.3.6.1.4.1.6296.101.23.7.6.2.3
		sleGponOnuPmStatsUniAvgControlTimer OBJECT-TYPE
			SYNTAX Gauge32
			MAX-ACCESS read-write
			STATUS current
			DESCRIPTION
				"The maximum time for the manager for a long running user command"
			::= { sleGponOnuPmStatsUniAvgControl 3 }


--  1.3.6.1.4.1.6296.101.23.7.6.2.4
		sleGponOnuPmStatsUniAvgControlTimeStamp OBJECT-TYPE
			SYNTAX TimeTicks
			MAX-ACCESS read-only
			STATUS current
			DESCRIPTION
				"The time stamp of the last command(end of command)"
			::= { sleGponOnuPmStatsUniAvgControl 4 }


--  1.3.6.1.4.1.6296.101.23.7.6.2.5
		sleGponOnuPmStatsUniAvgControlReqResult OBJECT-TYPE
			SYNTAX SleControlRequestResultType
			MAX-ACCESS read-only
			STATUS current
			DESCRIPTION
				"The result of the last user command"
			::= { sleGponOnuPmStatsUniAvgControl 5 }


		sleGponOnuPmStatsUniAvgControlOltindex OBJECT-TYPE
			SYNTAX Integer32 (1..2147483647)
			MAX-ACCESS read-write
			STATUS current
			DESCRIPTION
				"The OLT index."
			::= { sleGponOnuPmStatsUniAvgControl 6 }


--  1.3.6.1.4.1.6296.101.23.7.6.2.7
		sleGponOnuPmStatsUniAvgControlOnuIndex OBJECT-TYPE
			SYNTAX Integer32
			MAX-ACCESS read-write
			STATUS current
			DESCRIPTION
				"The ONU index."
			::= { sleGponOnuPmStatsUniAvgControl 7 }


--  1.3.6.1.4.1.6296.101.23.7.6.2.8
		sleGponOnuPmStatsUniAvgControlPort OBJECT-TYPE
			SYNTAX Integer32
			MAX-ACCESS read-write
			STATUS current
			DESCRIPTION
				"The port index."
			::= { sleGponOnuPmStatsUniAvgControl 8 }


--  1.3.6.1.4.1.6296.101.23.7.6.3
		sleGponOnuPmStatsUniAvgNotification OBJECT IDENTIFIER ::= { sleGponOnuPmStatsUniAvg 3 }


--  1.3.6.1.4.1.6296.101.23.7.6.3.1
		sleGponOnuPmStatsUniAvgUpdated NOTIFICATION-TYPE
			OBJECTS { sleGponOnuPmStatsUniAvgControlRequest, sleGponOnuPmStatsUniAvgControlTimeStamp, sleGponOnuPmStatsUniAvgControlReqResult, sleGponOnuPmStatsUniAvgControlOltindex, sleGponOnuPmStatsUniAvgControlOnuIndex,
				sleGponOnuPmStatsUniAvgControlPort }
			STATUS current
			DESCRIPTION
				"updateAvgStats"
			::= { sleGponOnuPmStatsUniAvgNotification 1 }


--   1.3.6.1.4.1.6296.101.23.7.3
-- 1.3.6.1.4.1.6296.101.23.7.7
		sleGponOnuPMStatatisticsSum OBJECT IDENTIFIER ::= { sleGponStatistics 7 }


--  1.3.6.1.4.1.6296.101.23.7.7.1
		sleGponOnuPMStatsSumAllOnuGemTable OBJECT-TYPE
			SYNTAX SEQUENCE OF SleGponOnuPMStatsSumAllOnuGemEntry
			MAX-ACCESS not-accessible
			STATUS current
			DESCRIPTION
				"Description."
			::= { sleGponOnuPMStatatisticsSum 1 }


--  1.3.6.1.4.1.6296.101.23.7.7.1.1
		sleGponOnuPMStatsSumAllOnuGemEntry OBJECT-TYPE
			SYNTAX SleGponOnuPMStatsSumAllOnuGemEntry
			MAX-ACCESS not-accessible
			STATUS current
			DESCRIPTION
				"Description."
			INDEX { sleGponOltId }
			::= { sleGponOnuPMStatsSumAllOnuGemTable 1 }


		SleGponOnuPMStatsSumAllOnuGemEntry ::=
			SEQUENCE {
				sleGponOnuPMStatsSumAllOnuGemLostPackets
					Counter64,
				sleGponOnuPMStatsSumAllOnuGemMisInsertedPackets
					Counter64,
				sleGponOnuPMStatsSumAllOnuGemReceivedPackets
					Counter64,
				sleGponOnuPMStatsSumAllOnuGemReceivedBlocks
					Counter64,
				sleGponOnuPMStatsSumAllOnuGemTransmittedBlocks
					Counter64,
				sleGponOnuPMStatsSumAllOnuGemImpairedBlocks
					Counter64
			 }

--  1.3.6.1.4.1.6296.101.23.7.7.1.1.1
		sleGponOnuPMStatsSumAllOnuGemLostPackets OBJECT-TYPE
			SYNTAX Counter64
			MAX-ACCESS read-only
			STATUS current
			DESCRIPTION
				"The sum total of all onu lost packet in olt"
			::= { sleGponOnuPMStatsSumAllOnuGemEntry 1 }


--  1.3.6.1.4.1.6296.101.23.7.7.1.1.2
		sleGponOnuPMStatsSumAllOnuGemMisInsertedPackets OBJECT-TYPE
			SYNTAX Counter64
			MAX-ACCESS read-only
			STATUS current
			DESCRIPTION
				"The sum total of all onu mis inserted packet in olt"
			::= { sleGponOnuPMStatsSumAllOnuGemEntry 2 }


--  1.3.6.1.4.1.6296.101.23.7.7.1.1.3
		sleGponOnuPMStatsSumAllOnuGemReceivedPackets OBJECT-TYPE
			SYNTAX Counter64
			MAX-ACCESS read-only
			STATUS current
			DESCRIPTION
				"The sum total of all onu received packet in olt"
			::= { sleGponOnuPMStatsSumAllOnuGemEntry 3 }


--  1.3.6.1.4.1.6296.101.23.7.7.1.1.4
		sleGponOnuPMStatsSumAllOnuGemReceivedBlocks OBJECT-TYPE
			SYNTAX Counter64
			MAX-ACCESS read-only
			STATUS current
			DESCRIPTION
				"The sum total of all onu received blocks in olt"
			::= { sleGponOnuPMStatsSumAllOnuGemEntry 4 }


--  1.3.6.1.4.1.6296.101.23.7.7.1.1.5
		sleGponOnuPMStatsSumAllOnuGemTransmittedBlocks OBJECT-TYPE
			SYNTAX Counter64
			MAX-ACCESS read-only
			STATUS current
			DESCRIPTION
				"The sum total of all onu transmitted blocks in olt"
			::= { sleGponOnuPMStatsSumAllOnuGemEntry 5 }


--  1.3.6.1.4.1.6296.101.23.7.7.1.1.6
		sleGponOnuPMStatsSumAllOnuGemImpairedBlocks OBJECT-TYPE
			SYNTAX Counter64
			MAX-ACCESS read-only
			STATUS current
			DESCRIPTION
				"The sum total of all onu impaired blocks in olt"
			::= { sleGponOnuPMStatsSumAllOnuGemEntry 6 }


--  1.3.6.1.4.1.6296.101.23.7.7.2
		sleGponOnuPMStatsSumAllOnuAniTable OBJECT-TYPE
			SYNTAX SEQUENCE OF SleGponOnuPMStatsSumAllOnuAniEntry
			MAX-ACCESS not-accessible
			STATUS current
			DESCRIPTION
				"Description."
			::= { sleGponOnuPMStatatisticsSum 2 }


--  1.3.6.1.4.1.6296.101.23.7.7.2.1
		sleGponOnuPMStatsSumAllOnuAniEntry OBJECT-TYPE
			SYNTAX SleGponOnuPMStatsSumAllOnuAniEntry
			MAX-ACCESS not-accessible
			STATUS current
			DESCRIPTION
				"Description."
			INDEX { sleGponOltId }
			::= { sleGponOnuPMStatsSumAllOnuAniTable 1 }


		SleGponOnuPMStatsSumAllOnuAniEntry ::=
			SEQUENCE {
				sleGponOnuPMStatsSumAllOnuAniDiscardedFrames
					Counter64
			 }

--  1.3.6.1.4.1.6296.101.23.7.7.2.1.1
		sleGponOnuPMStatsSumAllOnuAniDiscardedFrames OBJECT-TYPE
			SYNTAX Counter64
			MAX-ACCESS read-only
			STATUS current
			DESCRIPTION
				"The sum total of all onu lost discarded frames"
			::= { sleGponOnuPMStatsSumAllOnuAniEntry 1 }


--   1.3.6.1.4.1.6296.101.23.7.3.3
-- 1.3.6.1.4.1.6296.101.23.7.7.3
		sleGponOnuPMStatsSumAllOnuUniEthFrameUpTable OBJECT-TYPE
			SYNTAX SEQUENCE OF SleGponOnuPMStatsSumAllOnuUniEthFrameUpEntry
			MAX-ACCESS not-accessible
			STATUS current
			DESCRIPTION
				"sleGponOnuPMStatsDetailUniEthFrameUpTable"
			::= { sleGponOnuPMStatatisticsSum 3 }


--   1.3.6.1.4.1.6296.101.23.7.3.3.1
-- 1.3.6.1.4.1.6296.101.23.7.7.3.1
		sleGponOnuPMStatsSumAllOnuUniEthFrameUpEntry OBJECT-TYPE
			SYNTAX SleGponOnuPMStatsSumAllOnuUniEthFrameUpEntry
			MAX-ACCESS not-accessible
			STATUS current
			DESCRIPTION
				"key: sleGponOltId, sleGponOnuId, sleGponOnuPMStatsDetailUniEthFrameUpUniPort"
			INDEX { sleGponOltId }
			::= { sleGponOnuPMStatsSumAllOnuUniEthFrameUpTable 1 }


		SleGponOnuPMStatsSumAllOnuUniEthFrameUpEntry ::=
			SEQUENCE {
				sleGponOnuPMStatsSumAllOnuUniEthFrameUpDropEvents
					Counter64,
				sleGponOnuPMStatsSumAllOnuUniEthFrameUpOctets
					Counter64,
				sleGponOnuPMStatsSumAllOnuUniEthFrameUpPackets
					Counter64,
				sleGponOnuPMStatsSumAllOnuUniEthFrameUpBcastPackets
					Counter64,
				sleGponOnuPMStatsSumAllOnuUniEthFrameUpMcastPackets
					Counter64,
				sleGponOnuPMStatsSumAllOnuUniEthFrameUpUcastPackets
					Counter64,
				sleGponOnuPMStatsSumAllOnuUniEthFrameUpCRCErroredPackets
					Counter64,
				sleGponOnuPMStatsSumAllOnuUniEthFrameUpUndersizePackets
					Counter64,
				sleGponOnuPMStatsSumAllOnuUniEthFrameUpOversizePackets
					Counter64,
				sleGponOnuPMStatsSumAllOnuUniEthFrameUpPkt64Octets
					Counter64,
				sleGponOnuPMStatsSumAllOnuUniEthFrameUpPkt65To127Octets
					Counter64,
				sleGponOnuPMStatsSumAllOnuUniEthFrameUpPkt128To255Octets
					Counter64,
				sleGponOnuPMStatsSumAllOnuUniEthFrameUpPkt256To511Octets
					Counter64,
				sleGponOnuPMStatsSumAllOnuUniEthFrameUpPkt512To1023Octets
					Counter64,
				sleGponOnuPMStatsSumAllOnuUniEthFrameUpPkt1024To1518Octets
					Counter64
			 }

--   1.3.6.1.4.1.6296.101.23.7.3.3.1.1
-- 1.3.6.1.4.1.6296.101.23.7.7.3.1.1
		sleGponOnuPMStatsSumAllOnuUniEthFrameUpDropEvents OBJECT-TYPE
			SYNTAX Counter64
			MAX-ACCESS read-only
			STATUS current
			DESCRIPTION
				"The sum total of all onu events in which packets were dropped due to lack of resources."
			::= { sleGponOnuPMStatsSumAllOnuUniEthFrameUpEntry 1 }


--   1.3.6.1.4.1.6296.101.23.7.3.3.1.2
-- 1.3.6.1.4.1.6296.101.23.7.7.3.1.2
		sleGponOnuPMStatsSumAllOnuUniEthFrameUpOctets OBJECT-TYPE
			SYNTAX Counter64
			MAX-ACCESS read-only
			STATUS current
			DESCRIPTION
				"The sum total of all onu octets received"
			::= { sleGponOnuPMStatsSumAllOnuUniEthFrameUpEntry 2 }


--   1.3.6.1.4.1.6296.101.23.7.3.3.1.3
-- 1.3.6.1.4.1.6296.101.23.7.7.3.1.3
		sleGponOnuPMStatsSumAllOnuUniEthFrameUpPackets OBJECT-TYPE
			SYNTAX Counter64
			MAX-ACCESS read-only
			STATUS current
			DESCRIPTION
				"The sum total of all onu packets received,"
			::= { sleGponOnuPMStatsSumAllOnuUniEthFrameUpEntry 3 }


--   1.3.6.1.4.1.6296.101.23.7.3.3.1.4
-- 1.3.6.1.4.1.6296.101.23.7.7.3.1.4
		sleGponOnuPMStatsSumAllOnuUniEthFrameUpBcastPackets OBJECT-TYPE
			SYNTAX Counter64
			MAX-ACCESS read-only
			STATUS current
			DESCRIPTION
				"The sum total of all onu received good packets directed to a broadcast address."
			::= { sleGponOnuPMStatsSumAllOnuUniEthFrameUpEntry 4 }


--   1.3.6.1.4.1.6296.101.23.7.3.3.1.5
-- 1.3.6.1.4.1.6296.101.23.7.7.3.1.5
		sleGponOnuPMStatsSumAllOnuUniEthFrameUpMcastPackets OBJECT-TYPE
			SYNTAX Counter64
			MAX-ACCESS read-only
			STATUS current
			DESCRIPTION
				"The sum total of all onu received good packets directed to a multicast address."
			::= { sleGponOnuPMStatsSumAllOnuUniEthFrameUpEntry 5 }


--   1.3.6.1.4.1.6296.101.23.7.3.3.1.6
-- 1.3.6.1.4.1.6296.101.23.7.7.3.1.6
		sleGponOnuPMStatsSumAllOnuUniEthFrameUpUcastPackets OBJECT-TYPE
			SYNTAX Counter64
			MAX-ACCESS read-only
			STATUS current
			DESCRIPTION
				"The sum total of all onu received good packets directed to a multicast address."
			::= { sleGponOnuPMStatsSumAllOnuUniEthFrameUpEntry 6 }


--   1.3.6.1.4.1.6296.101.23.7.3.3.1.8
-- 1.3.6.1.4.1.6296.101.23.7.7.3.1.7
		sleGponOnuPMStatsSumAllOnuUniEthFrameUpCRCErroredPackets OBJECT-TYPE
			SYNTAX Counter64
			MAX-ACCESS read-only
			STATUS current
			DESCRIPTION
				"The sum total of all onu packets received that had a length"
			::= { sleGponOnuPMStatsSumAllOnuUniEthFrameUpEntry 7 }


--   1.3.6.1.4.1.6296.101.23.7.3.3.1.9
-- 1.3.6.1.4.1.6296.101.23.7.7.3.1.8
		sleGponOnuPMStatsSumAllOnuUniEthFrameUpUndersizePackets OBJECT-TYPE
			SYNTAX Counter64
			MAX-ACCESS read-only
			STATUS current
			DESCRIPTION
				"The sum total of all onu packets received that were less than 64 octets long"
			::= { sleGponOnuPMStatsSumAllOnuUniEthFrameUpEntry 8 }


--   1.3.6.1.4.1.6296.101.23.7.3.3.1.10
-- 1.3.6.1.4.1.6296.101.23.7.7.3.1.9
		sleGponOnuPMStatsSumAllOnuUniEthFrameUpOversizePackets OBJECT-TYPE
			SYNTAX Counter64
			MAX-ACCESS read-only
			STATUS current
			DESCRIPTION
				"The sum total of all onu packets received that were longer than 1518 octets"
			::= { sleGponOnuPMStatsSumAllOnuUniEthFrameUpEntry 9 }


--   1.3.6.1.4.1.6296.101.23.7.3.3.1.11
-- 1.3.6.1.4.1.6296.101.23.7.7.3.1.10
		sleGponOnuPMStatsSumAllOnuUniEthFrameUpPkt64Octets OBJECT-TYPE
			SYNTAX Counter64
			MAX-ACCESS read-only
			STATUS current
			DESCRIPTION
				"The sum total of all onu received packets (including bad packets) that were
				64 octets long,
				"
			::= { sleGponOnuPMStatsSumAllOnuUniEthFrameUpEntry 10 }


--   1.3.6.1.4.1.6296.101.23.7.3.3.1.12
-- 1.3.6.1.4.1.6296.101.23.7.7.3.1.11
		sleGponOnuPMStatsSumAllOnuUniEthFrameUpPkt65To127Octets OBJECT-TYPE
			SYNTAX Counter64
			MAX-ACCESS read-only
			STATUS current
			DESCRIPTION
				"The sum total of all onu received packets (including bad packets) that were
				65..127 octets long,
				"
			::= { sleGponOnuPMStatsSumAllOnuUniEthFrameUpEntry 11 }


--   1.3.6.1.4.1.6296.101.23.7.3.3.1.13
-- 1.3.6.1.4.1.6296.101.23.7.7.3.1.12
		sleGponOnuPMStatsSumAllOnuUniEthFrameUpPkt128To255Octets OBJECT-TYPE
			SYNTAX Counter64
			MAX-ACCESS read-only
			STATUS current
			DESCRIPTION
				"The sum total of all onu packets (including bad packets) received that were
				128..255 octets long,
				"
			::= { sleGponOnuPMStatsSumAllOnuUniEthFrameUpEntry 12 }


--   1.3.6.1.4.1.6296.101.23.7.3.3.1.14
-- 1.3.6.1.4.1.6296.101.23.7.7.3.1.13
		sleGponOnuPMStatsSumAllOnuUniEthFrameUpPkt256To511Octets OBJECT-TYPE
			SYNTAX Counter64
			MAX-ACCESS read-only
			STATUS current
			DESCRIPTION
				"The sum total of all onu packets (including bad packets) received that were
				256..511 octets long,
				"
			::= { sleGponOnuPMStatsSumAllOnuUniEthFrameUpEntry 13 }


--   1.3.6.1.4.1.6296.101.23.7.3.3.1.15
-- 1.3.6.1.4.1.6296.101.23.7.7.3.1.14
		sleGponOnuPMStatsSumAllOnuUniEthFrameUpPkt512To1023Octets OBJECT-TYPE
			SYNTAX Counter64
			MAX-ACCESS read-only
			STATUS current
			DESCRIPTION
				"The sum total of all onu packets (including bad packets) received that were
				512..1023 octets long,
				"
			::= { sleGponOnuPMStatsSumAllOnuUniEthFrameUpEntry 14 }


--   1.3.6.1.4.1.6296.101.23.7.3.3.1.16
-- 1.3.6.1.4.1.6296.101.23.7.7.3.1.15
		sleGponOnuPMStatsSumAllOnuUniEthFrameUpPkt1024To1518Octets OBJECT-TYPE
			SYNTAX Counter64
			MAX-ACCESS read-only
			STATUS current
			DESCRIPTION
				"The sum total of packets (including bad packets) received that were
				1024..1518 octets long,
				"
			::= { sleGponOnuPMStatsSumAllOnuUniEthFrameUpEntry 15 }


--   1.3.6.1.4.1.6296.101.23.7.3.3
-- 1.3.6.1.4.1.6296.101.23.7.7.4
		sleGponOnuPMStatsSumAllOnuUniEthFrameDownTable OBJECT-TYPE
			SYNTAX SEQUENCE OF SleGponOnuPMStatsSumAllOnuUniEthFrameDownEntry
			MAX-ACCESS not-accessible
			STATUS current
			DESCRIPTION
				"sleGponOnuPMStatsDetailUniEthFrameUpTable"
			::= { sleGponOnuPMStatatisticsSum 4 }


--   1.3.6.1.4.1.6296.101.23.7.3.3.1
-- 1.3.6.1.4.1.6296.101.23.7.7.4.1
		sleGponOnuPMStatsSumAllOnuUniEthFrameDownEntry OBJECT-TYPE
			SYNTAX SleGponOnuPMStatsSumAllOnuUniEthFrameDownEntry
			MAX-ACCESS not-accessible
			STATUS current
			DESCRIPTION
				"key: sleGponOltId, sleGponOnuId, sleGponOnuPMStatsDetailUniEthFrameUpUniPort"
			INDEX { sleGponOltId }
			::= { sleGponOnuPMStatsSumAllOnuUniEthFrameDownTable 1 }


		SleGponOnuPMStatsSumAllOnuUniEthFrameDownEntry ::=
			SEQUENCE {
				sleGponOnuPMStatsSumAllOnuUniEthFrameDownDropEvents
					Counter64,
				sleGponOnuPMStatsSumAllOnuUniEthFrameDownOctets
					Counter64,
				sleGponOnuPMStatsSumAllOnuUniEthFrameDownPackets
					Counter64,
				sleGponOnuPMStatsSumAllOnuUniEthFrameDownBcastPackets
					Counter64,
				sleGponOnuPMStatsSumAllOnuUniEthFrameDownMcastPackets
					Counter64,
				sleGponOnuPMStatsSumAllOnuUniEthFrameDownUcastPackets
					Counter64,
				sleGponOnuPMStatsSumAllOnuUniEthFrameDownCRCErroredPackets
					Counter64,
				sleGponOnuPMStatsSumAllOnuUniEthFrameDownUndersizePackets
					Counter64,
				sleGponOnuPMStatsSumAllOnuUniEthFrameDownOversizePackets
					Counter64,
				sleGponOnuPMStatsSumAllOnuUniEthFrameDownPkt64Octets
					Counter64,
				sleGponOnuPMStatsSumAllOnuUniEthFrameDownPkt65To127Octets
					Counter64,
				sleGponOnuPMStatsSumAllOnuUniEthFrameDownPkt128To255Octets
					Counter64,
				sleGponOnuPMStatsSumAllOnuUniEthFrameDownPkt256To511Octets
					Counter64,
				sleGponOnuPMStatsSumAllOnuUniEthFrameDownPkt512To1023Octets
					Counter64,
				sleGponOnuPMStatsSumAllOnuUniEthFrameDownPkt1024To1518Octets
					Counter64
			 }

--   1.3.6.1.4.1.6296.101.23.7.3.3.1.1
-- 1.3.6.1.4.1.6296.101.23.7.7.4.1.1
		sleGponOnuPMStatsSumAllOnuUniEthFrameDownDropEvents OBJECT-TYPE
			SYNTAX Counter64
			MAX-ACCESS read-only
			STATUS current
			DESCRIPTION
				"The sum total of all onu events in which packets were dropped due to lack of resources."
			::= { sleGponOnuPMStatsSumAllOnuUniEthFrameDownEntry 1 }


--   1.3.6.1.4.1.6296.101.23.7.3.3.1.2
-- 1.3.6.1.4.1.6296.101.23.7.7.4.1.2
		sleGponOnuPMStatsSumAllOnuUniEthFrameDownOctets OBJECT-TYPE
			SYNTAX Counter64
			MAX-ACCESS read-only
			STATUS current
			DESCRIPTION
				"The sum total of all onu octets received"
			::= { sleGponOnuPMStatsSumAllOnuUniEthFrameDownEntry 2 }


--   1.3.6.1.4.1.6296.101.23.7.3.3.1.3
-- 1.3.6.1.4.1.6296.101.23.7.7.4.1.3
		sleGponOnuPMStatsSumAllOnuUniEthFrameDownPackets OBJECT-TYPE
			SYNTAX Counter64
			MAX-ACCESS read-only
			STATUS current
			DESCRIPTION
				"The sum total of all onu packets received,"
			::= { sleGponOnuPMStatsSumAllOnuUniEthFrameDownEntry 3 }


--   1.3.6.1.4.1.6296.101.23.7.3.3.1.4
-- 1.3.6.1.4.1.6296.101.23.7.7.4.1.4
		sleGponOnuPMStatsSumAllOnuUniEthFrameDownBcastPackets OBJECT-TYPE
			SYNTAX Counter64
			MAX-ACCESS read-only
			STATUS current
			DESCRIPTION
				"The sum total of all onu received good packets directed to a broadcast address."
			::= { sleGponOnuPMStatsSumAllOnuUniEthFrameDownEntry 4 }


--   1.3.6.1.4.1.6296.101.23.7.3.3.1.5
-- 1.3.6.1.4.1.6296.101.23.7.7.4.1.5
		sleGponOnuPMStatsSumAllOnuUniEthFrameDownMcastPackets OBJECT-TYPE
			SYNTAX Counter64
			MAX-ACCESS read-only
			STATUS current
			DESCRIPTION
				"The sum total of all onu received good packets directed to a multicast address."
			::= { sleGponOnuPMStatsSumAllOnuUniEthFrameDownEntry 5 }


--   1.3.6.1.4.1.6296.101.23.7.3.3.1.6
-- 1.3.6.1.4.1.6296.101.23.7.7.4.1.6
		sleGponOnuPMStatsSumAllOnuUniEthFrameDownUcastPackets OBJECT-TYPE
			SYNTAX Counter64
			MAX-ACCESS read-only
			STATUS current
			DESCRIPTION
				"The sum total of all onu received good packets directed to a multicast address."
			::= { sleGponOnuPMStatsSumAllOnuUniEthFrameDownEntry 6 }


--   1.3.6.1.4.1.6296.101.23.7.3.3.1.9
-- 1.3.6.1.4.1.6296.101.23.7.7.4.1.7
		sleGponOnuPMStatsSumAllOnuUniEthFrameDownCRCErroredPackets OBJECT-TYPE
			SYNTAX Counter64
			MAX-ACCESS read-only
			STATUS current
			DESCRIPTION
				"The sum total of all onu packets received that had a length"
			::= { sleGponOnuPMStatsSumAllOnuUniEthFrameDownEntry 7 }


--   1.3.6.1.4.1.6296.101.23.7.3.3.1.10
-- 1.3.6.1.4.1.6296.101.23.7.7.4.1.8
		sleGponOnuPMStatsSumAllOnuUniEthFrameDownUndersizePackets OBJECT-TYPE
			SYNTAX Counter64
			MAX-ACCESS read-only
			STATUS current
			DESCRIPTION
				"The sum total of all onu packets received that were less than 64 octets long"
			::= { sleGponOnuPMStatsSumAllOnuUniEthFrameDownEntry 8 }


--   1.3.6.1.4.1.6296.101.23.7.3.3.1.11
-- 1.3.6.1.4.1.6296.101.23.7.7.4.1.9
		sleGponOnuPMStatsSumAllOnuUniEthFrameDownOversizePackets OBJECT-TYPE
			SYNTAX Counter64
			MAX-ACCESS read-only
			STATUS current
			DESCRIPTION
				"The sum total of all onu packets received that were longer than 1518 octets"
			::= { sleGponOnuPMStatsSumAllOnuUniEthFrameDownEntry 9 }


--   1.3.6.1.4.1.6296.101.23.7.3.3.1.12
-- 1.3.6.1.4.1.6296.101.23.7.7.4.1.10
		sleGponOnuPMStatsSumAllOnuUniEthFrameDownPkt64Octets OBJECT-TYPE
			SYNTAX Counter64
			MAX-ACCESS read-only
			STATUS current
			DESCRIPTION
				"The sum total of all onu received packets (including bad packets) that were
				64 octets long,

				"
			::= { sleGponOnuPMStatsSumAllOnuUniEthFrameDownEntry 10 }


--   1.3.6.1.4.1.6296.101.23.7.3.3.1.13
-- 1.3.6.1.4.1.6296.101.23.7.7.4.1.11
		sleGponOnuPMStatsSumAllOnuUniEthFrameDownPkt65To127Octets OBJECT-TYPE
			SYNTAX Counter64
			MAX-ACCESS read-only
			STATUS current
			DESCRIPTION
				"The sum total of all onu received packets (including bad packets) that were
				65..127 octets long,
				"
			::= { sleGponOnuPMStatsSumAllOnuUniEthFrameDownEntry 11 }


--   1.3.6.1.4.1.6296.101.23.7.3.3.1.14
-- 1.3.6.1.4.1.6296.101.23.7.7.4.1.12
		sleGponOnuPMStatsSumAllOnuUniEthFrameDownPkt128To255Octets OBJECT-TYPE
			SYNTAX Counter64
			MAX-ACCESS read-only
			STATUS current
			DESCRIPTION
				"The sum total of all onu packets (including bad packets) received that were
				128..255 octets long,
				"
			::= { sleGponOnuPMStatsSumAllOnuUniEthFrameDownEntry 12 }


--   1.3.6.1.4.1.6296.101.23.7.3.3.1.15
-- 1.3.6.1.4.1.6296.101.23.7.7.4.1.13
		sleGponOnuPMStatsSumAllOnuUniEthFrameDownPkt256To511Octets OBJECT-TYPE
			SYNTAX Counter64
			MAX-ACCESS read-only
			STATUS current
			DESCRIPTION
				"The sum total of all onu packets (including bad packets) received that were
				256..511 octets long,
				"
			::= { sleGponOnuPMStatsSumAllOnuUniEthFrameDownEntry 13 }


--   1.3.6.1.4.1.6296.101.23.7.3.3.1.16
-- 1.3.6.1.4.1.6296.101.23.7.7.4.1.14
		sleGponOnuPMStatsSumAllOnuUniEthFrameDownPkt512To1023Octets OBJECT-TYPE
			SYNTAX Counter64
			MAX-ACCESS read-only
			STATUS current
			DESCRIPTION
				"The sum total of all onu packets (including bad packets) received that were
				512..1023 octets long,
				"
			::= { sleGponOnuPMStatsSumAllOnuUniEthFrameDownEntry 14 }


--   1.3.6.1.4.1.6296.101.23.7.3.3.1.16
-- 1.3.6.1.4.1.6296.101.23.7.7.4.1.15
		sleGponOnuPMStatsSumAllOnuUniEthFrameDownPkt1024To1518Octets OBJECT-TYPE
			SYNTAX Counter64
			MAX-ACCESS read-only
			STATUS current
			DESCRIPTION
				"The sum total of packets (including bad packets) received that were
				1024..1518 octets long,
				"
			::= { sleGponOnuPMStatsSumAllOnuUniEthFrameDownEntry 15 }


--   1.3.6.1.4.1.6296.101.23.7.3.3
-- 1.3.6.1.4.1.6296.101.23.7.7.5
		sleGponOnuPMStatsSumAllOnuUniEth3Table OBJECT-TYPE
			SYNTAX SEQUENCE OF SleGponOnuPMStatsSumAllOnuUniEth3Entry
			MAX-ACCESS not-accessible
			STATUS current
			DESCRIPTION
				"sleGponOnuPMStatsDetailUniEthFrameUpTable"
			::= { sleGponOnuPMStatatisticsSum 5 }


--   1.3.6.1.4.1.6296.101.23.7.3.3.1
-- 1.3.6.1.4.1.6296.101.23.7.7.5.1
		sleGponOnuPMStatsSumAllOnuUniEth3Entry OBJECT-TYPE
			SYNTAX SleGponOnuPMStatsSumAllOnuUniEth3Entry
			MAX-ACCESS not-accessible
			STATUS current
			DESCRIPTION
				"key: sleGponOltId, sleGponOnuId, sleGponOnuPMStatsDetailUniEthFrameUpUniPort"
			INDEX { sleGponOltId }
			::= { sleGponOnuPMStatsSumAllOnuUniEth3Table 1 }


		SleGponOnuPMStatsSumAllOnuUniEth3Entry ::=
			SEQUENCE {
				sleGponOnuPMStatsSumAllOnuUniEth3DropEvents
					Counter64,
				sleGponOnuPMStatsSumAllOnuUniEth3Octets
					Counter64,
				sleGponOnuPMStatsSumAllOnuUniEth3Packets
					Counter64,
				sleGponOnuPMStatsSumAllOnuUniEth3BcastPackets
					Counter64,
				sleGponOnuPMStatsSumAllOnuUniEth3McastPackets
					Counter64,
				sleGponOnuPMStatsSumAllOnuUniEth3UcastPackets
					Counter64,
				sleGponOnuPMStatsSumAllOnuUniEth3Fragments
					Counter64,
				sleGponOnuPMStatsSumAllOnuUniEth3Jabbers
					Counter64,
				sleGponOnuPMStatsSumAllOnuUniEth3Pkt64Octets
					Counter64,
				sleGponOnuPMStatsSumAllOnuUniEth3Pkt65To127Octets
					Counter64,
				sleGponOnuPMStatsSumAllOnuUniEth3Pkt128To255Octets
					Counter64,
				sleGponOnuPMStatsSumAllOnuUniEth3Pkt256To511Octets
					Counter64,
				sleGponOnuPMStatsSumAllOnuUniEth3Pkt512To1023Octets
					Counter64,
				sleGponOnuPMStatsSumAllOnuUniEth3Pkt1024To1518Octets
					Counter64
			 }

--   1.3.6.1.4.1.6296.101.23.7.3.3.1.1
-- 1.3.6.1.4.1.6296.101.23.7.7.5.1.1
		sleGponOnuPMStatsSumAllOnuUniEth3DropEvents OBJECT-TYPE
			SYNTAX Counter64
			MAX-ACCESS read-only
			STATUS current
			DESCRIPTION
				"The sum total of all onu events in which packets were dropped due to lack of resources."
			::= { sleGponOnuPMStatsSumAllOnuUniEth3Entry 1 }


--   1.3.6.1.4.1.6296.101.23.7.3.3.1.2
-- 1.3.6.1.4.1.6296.101.23.7.7.5.1.2
		sleGponOnuPMStatsSumAllOnuUniEth3Octets OBJECT-TYPE
			SYNTAX Counter64
			MAX-ACCESS read-only
			STATUS current
			DESCRIPTION
				"The sum total of all onu octets received"
			::= { sleGponOnuPMStatsSumAllOnuUniEth3Entry 2 }


--   1.3.6.1.4.1.6296.101.23.7.3.3.1.3
-- 1.3.6.1.4.1.6296.101.23.7.7.5.1.3
		sleGponOnuPMStatsSumAllOnuUniEth3Packets OBJECT-TYPE
			SYNTAX Counter64
			MAX-ACCESS read-only
			STATUS current
			DESCRIPTION
				"The sum total of all onu packets received,"
			::= { sleGponOnuPMStatsSumAllOnuUniEth3Entry 3 }


--   1.3.6.1.4.1.6296.101.23.7.3.3.1.4
-- 1.3.6.1.4.1.6296.101.23.7.7.5.1.4
		sleGponOnuPMStatsSumAllOnuUniEth3BcastPackets OBJECT-TYPE
			SYNTAX Counter64
			MAX-ACCESS read-only
			STATUS current
			DESCRIPTION
				"The sum total of all onu received good packets directed to a broadcast address."
			::= { sleGponOnuPMStatsSumAllOnuUniEth3Entry 4 }


--   1.3.6.1.4.1.6296.101.23.7.3.3.1.5
-- 1.3.6.1.4.1.6296.101.23.7.7.5.1.5
		sleGponOnuPMStatsSumAllOnuUniEth3McastPackets OBJECT-TYPE
			SYNTAX Counter64
			MAX-ACCESS read-only
			STATUS current
			DESCRIPTION
				"The sum total of all onu received good packets directed to a multicast address."
			::= { sleGponOnuPMStatsSumAllOnuUniEth3Entry 5 }


--   1.3.6.1.4.1.6296.101.23.7.3.3.1.6
-- 1.3.6.1.4.1.6296.101.23.7.7.5.1.6
		sleGponOnuPMStatsSumAllOnuUniEth3UcastPackets OBJECT-TYPE
			SYNTAX Counter64
			MAX-ACCESS read-only
			STATUS current
			DESCRIPTION
				"The sum total of all onu received good packets directed to a multicast address."
			::= { sleGponOnuPMStatsSumAllOnuUniEth3Entry 6 }


--   1.3.6.1.4.1.6296.101.23.7.3.3.1.9
-- 1.3.6.1.4.1.6296.101.23.7.7.5.1.7
		sleGponOnuPMStatsSumAllOnuUniEth3Fragments OBJECT-TYPE
			SYNTAX Counter64
			MAX-ACCESS read-only
			STATUS current
			DESCRIPTION
				"The sum total of all onu packets received (fragments)"
			::= { sleGponOnuPMStatsSumAllOnuUniEth3Entry 7 }


--   1.3.6.1.4.1.6296.101.23.7.3.3.1.10
-- 1.3.6.1.4.1.6296.101.23.7.7.5.1.8
		sleGponOnuPMStatsSumAllOnuUniEth3Jabbers OBJECT-TYPE
			SYNTAX Counter64
			MAX-ACCESS read-only
			STATUS current
			DESCRIPTION
				"The sum total of all onu packets received (jabbers)"
			::= { sleGponOnuPMStatsSumAllOnuUniEth3Entry 8 }


--   1.3.6.1.4.1.6296.101.23.7.3.3.1.12
-- 1.3.6.1.4.1.6296.101.23.7.7.5.1.9
		sleGponOnuPMStatsSumAllOnuUniEth3Pkt64Octets OBJECT-TYPE
			SYNTAX Counter64
			MAX-ACCESS read-only
			STATUS current
			DESCRIPTION
				"The sum total of all onu received packets (including bad packets) that were
				64 octets long,

				"
			::= { sleGponOnuPMStatsSumAllOnuUniEth3Entry 9 }


--   1.3.6.1.4.1.6296.101.23.7.3.3.1.13
-- 1.3.6.1.4.1.6296.101.23.7.7.5.1.10
		sleGponOnuPMStatsSumAllOnuUniEth3Pkt65To127Octets OBJECT-TYPE
			SYNTAX Counter64
			MAX-ACCESS read-only
			STATUS current
			DESCRIPTION
				"The sum total of all onu received packets (including bad packets) that were
				65..127 octets long,
				"
			::= { sleGponOnuPMStatsSumAllOnuUniEth3Entry 10 }


--   1.3.6.1.4.1.6296.101.23.7.3.3.1.14
-- 1.3.6.1.4.1.6296.101.23.7.7.5.1.11
		sleGponOnuPMStatsSumAllOnuUniEth3Pkt128To255Octets OBJECT-TYPE
			SYNTAX Counter64
			MAX-ACCESS read-only
			STATUS current
			DESCRIPTION
				"The sum total of all onu packets (including bad packets) received that were
				128..255 octets long,
				"
			::= { sleGponOnuPMStatsSumAllOnuUniEth3Entry 11 }


--   1.3.6.1.4.1.6296.101.23.7.3.3.1.15
-- 1.3.6.1.4.1.6296.101.23.7.7.5.1.12
		sleGponOnuPMStatsSumAllOnuUniEth3Pkt256To511Octets OBJECT-TYPE
			SYNTAX Counter64
			MAX-ACCESS read-only
			STATUS current
			DESCRIPTION
				"The sum total of all onu packets (including bad packets) received that were
				256..511 octets long,
				"
			::= { sleGponOnuPMStatsSumAllOnuUniEth3Entry 12 }


--   1.3.6.1.4.1.6296.101.23.7.3.3.1.16
-- 1.3.6.1.4.1.6296.101.23.7.7.5.1.13
		sleGponOnuPMStatsSumAllOnuUniEth3Pkt512To1023Octets OBJECT-TYPE
			SYNTAX Counter64
			MAX-ACCESS read-only
			STATUS current
			DESCRIPTION
				"The sum total of all onu packets (including bad packets) received that were
				512..1023 octets long,
				"
			::= { sleGponOnuPMStatsSumAllOnuUniEth3Entry 13 }


--   1.3.6.1.4.1.6296.101.23.7.3.3.1.16
-- 1.3.6.1.4.1.6296.101.23.7.7.5.1.14
		sleGponOnuPMStatsSumAllOnuUniEth3Pkt1024To1518Octets OBJECT-TYPE
			SYNTAX Counter64
			MAX-ACCESS read-only
			STATUS current
			DESCRIPTION
				"The sum total of packets (including bad packets) received that were
				1024..1518 octets long,
				"
			::= { sleGponOnuPMStatsSumAllOnuUniEth3Entry 14 }


--  1.3.6.1.4.1.6296.101.23.7.7.6
		sleGponOnuPMStatsSumOnuGEMTable OBJECT-TYPE
			SYNTAX SEQUENCE OF SleGponOnuPMStatsSumOnuGEMEntry
			MAX-ACCESS not-accessible
			STATUS current
			DESCRIPTION
				"sleGponOnuPMStatsDetailGEMTable"
			::= { sleGponOnuPMStatatisticsSum 6 }


--  1.3.6.1.4.1.6296.101.23.7.7.6.1
		sleGponOnuPMStatsSumOnuGEMEntry OBJECT-TYPE
			SYNTAX SleGponOnuPMStatsSumOnuGEMEntry
			MAX-ACCESS not-accessible
			STATUS current
			DESCRIPTION
				"key: sleGponOnuPMStatsDetailGEMPort, sleGponOltId, sleGponOnuId"
			INDEX { sleGponOltId, sleGponOnuId }
			::= { sleGponOnuPMStatsSumOnuGEMTable 1 }


		SleGponOnuPMStatsSumOnuGEMEntry ::=
			SEQUENCE {
				sleGponOnuPMStatsSumOnuGEMPre15mLostPackets
					Counter64,
				sleGponOnuPMStatsSumOnuGEMPre15mMisInsertedPackets
					Counter64,
				sleGponOnuPMStatsSumOnuGEMPre15mReceivedPackets
					Counter64,
				sleGponOnuPMStatsSumOnuGEMPre15mReceivedBlocks
					Counter64,
				sleGponOnuPMStatsSumOnuGEMPre15mTransmittedBlocks
					Counter64,
				sleGponOnuPMStatsSumOnuGEMPre15mImpairedBlocks
					Counter64,
				sleGponOnuPMStatsSumOnuGEMHourLostPackets
					Counter64,
				sleGponOnuPMStatsSumOnuGEMHourMisInsertedPackets
					Counter64,
				sleGponOnuPMStatsSumOnuGEMHourReceivedPackets
					Counter64,
				sleGponOnuPMStatsSumOnuGEMHourReceivedBlocks
					Counter64,
				sleGponOnuPMStatsSumOnuGEMHourTransmittedBlocks
					Counter64,
				sleGponOnuPMStatsSumOnuGEMHourImpairedBlocks
					Counter64,
				sleGponOnuPMStatsSumOnuGEMDayLostPackets
					Counter64,
				sleGponOnuPMStatsSumOnuGEMDayMisInsertedPackets
					Counter64,
				sleGponOnuPMStatsSumOnuGEMDayReceivedPackets
					Counter64,
				sleGponOnuPMStatsSumOnuGEMDayReceivedBlocks
					Counter64,
				sleGponOnuPMStatsSumOnuGEMDayTransmittedBlocks
					Counter64,
				sleGponOnuPMStatsSumOnuGEMDayImpairedBlocks
					Counter64,
				sleGponOnuPMStatsSumOnuGEMTotalLostPackets
					Counter64,
				sleGponOnuPMStatsSumOnuGEMTotalMisInsertedPackets
					Counter64,
				sleGponOnuPMStatsSumOnuGEMTotalReceivedPackets
					Counter64,
				sleGponOnuPMStatsSumOnuGEMTotalReceivedBlocks
					Counter64,
				sleGponOnuPMStatsSumOnuGEMTotalTransmittedBlocks
					Counter64,
				sleGponOnuPMStatsSumOnuGEMTotalImpairedBlocks
					Counter64
			 }

--  1.3.6.1.4.1.6296.101.23.7.7.6.1.1
		sleGponOnuPMStatsSumOnuGEMPre15mLostPackets OBJECT-TYPE
			SYNTAX Counter64
			MAX-ACCESS read-only
			STATUS current
			DESCRIPTION
				"The pre 15 minute number of lost packet "
			::= { sleGponOnuPMStatsSumOnuGEMEntry 1 }


--  1.3.6.1.4.1.6296.101.23.7.7.6.1.2
		sleGponOnuPMStatsSumOnuGEMPre15mMisInsertedPackets OBJECT-TYPE
			SYNTAX Counter64
			MAX-ACCESS read-only
			STATUS current
			DESCRIPTION
				"The pre 15 minute number of mis inserted packet "
			::= { sleGponOnuPMStatsSumOnuGEMEntry 2 }


--  1.3.6.1.4.1.6296.101.23.7.7.6.1.3
		sleGponOnuPMStatsSumOnuGEMPre15mReceivedPackets OBJECT-TYPE
			SYNTAX Counter64
			MAX-ACCESS read-only
			STATUS current
			DESCRIPTION
				"The pre 15 minute number of received packet"
			::= { sleGponOnuPMStatsSumOnuGEMEntry 3 }


--  1.3.6.1.4.1.6296.101.23.7.7.6.1.4
		sleGponOnuPMStatsSumOnuGEMPre15mReceivedBlocks OBJECT-TYPE
			SYNTAX Counter64
			MAX-ACCESS read-only
			STATUS current
			DESCRIPTION
				"The pre 15 minute number of received blocks"
			::= { sleGponOnuPMStatsSumOnuGEMEntry 4 }


--  1.3.6.1.4.1.6296.101.23.7.7.6.1.5
		sleGponOnuPMStatsSumOnuGEMPre15mTransmittedBlocks OBJECT-TYPE
			SYNTAX Counter64
			MAX-ACCESS read-only
			STATUS current
			DESCRIPTION
				"The pre 15 minute number of transmitted blocks"
			::= { sleGponOnuPMStatsSumOnuGEMEntry 5 }


--  1.3.6.1.4.1.6296.101.23.7.7.6.1.6
		sleGponOnuPMStatsSumOnuGEMPre15mImpairedBlocks OBJECT-TYPE
			SYNTAX Counter64
			MAX-ACCESS read-only
			STATUS current
			DESCRIPTION
				"The pre 15 minute number of impaired blocks"
			::= { sleGponOnuPMStatsSumOnuGEMEntry 6 }


--  1.3.6.1.4.1.6296.101.23.7.7.6.1.7
		sleGponOnuPMStatsSumOnuGEMHourLostPackets OBJECT-TYPE
			SYNTAX Counter64
			MAX-ACCESS read-only
			STATUS current
			DESCRIPTION
				"The hour number of lost packet "
			::= { sleGponOnuPMStatsSumOnuGEMEntry 7 }


--  1.3.6.1.4.1.6296.101.23.7.7.6.1.8
		sleGponOnuPMStatsSumOnuGEMHourMisInsertedPackets OBJECT-TYPE
			SYNTAX Counter64
			MAX-ACCESS read-only
			STATUS current
			DESCRIPTION
				"The hour number of mis inserted packet "
			::= { sleGponOnuPMStatsSumOnuGEMEntry 8 }


--  1.3.6.1.4.1.6296.101.23.7.7.6.1.9
		sleGponOnuPMStatsSumOnuGEMHourReceivedPackets OBJECT-TYPE
			SYNTAX Counter64
			MAX-ACCESS read-write
			STATUS current
			DESCRIPTION
				"The hour number of received packet"
			::= { sleGponOnuPMStatsSumOnuGEMEntry 9 }


--  1.3.6.1.4.1.6296.101.23.7.7.6.1.10
		sleGponOnuPMStatsSumOnuGEMHourReceivedBlocks OBJECT-TYPE
			SYNTAX Counter64
			MAX-ACCESS read-write
			STATUS current
			DESCRIPTION
				"The hour number of received blocks"
			::= { sleGponOnuPMStatsSumOnuGEMEntry 10 }


--  1.3.6.1.4.1.6296.101.23.7.7.6.1.11
		sleGponOnuPMStatsSumOnuGEMHourTransmittedBlocks OBJECT-TYPE
			SYNTAX Counter64
			MAX-ACCESS read-only
			STATUS current
			DESCRIPTION
				"The hour number of transmitted blocks"
			::= { sleGponOnuPMStatsSumOnuGEMEntry 11 }


--  1.3.6.1.4.1.6296.101.23.7.7.6.1.12
		sleGponOnuPMStatsSumOnuGEMHourImpairedBlocks OBJECT-TYPE
			SYNTAX Counter64
			MAX-ACCESS read-write
			STATUS current
			DESCRIPTION
				"The hour number of impaired blocks"
			::= { sleGponOnuPMStatsSumOnuGEMEntry 12 }


--  1.3.6.1.4.1.6296.101.23.7.7.6.1.13
		sleGponOnuPMStatsSumOnuGEMDayLostPackets OBJECT-TYPE
			SYNTAX Counter64
			MAX-ACCESS read-write
			STATUS current
			DESCRIPTION
				"The day number of lost packet "
			::= { sleGponOnuPMStatsSumOnuGEMEntry 13 }


--  1.3.6.1.4.1.6296.101.23.7.7.6.1.14
		sleGponOnuPMStatsSumOnuGEMDayMisInsertedPackets OBJECT-TYPE
			SYNTAX Counter64
			MAX-ACCESS read-write
			STATUS current
			DESCRIPTION
				"The day number of mis inserted packet "
			::= { sleGponOnuPMStatsSumOnuGEMEntry 14 }


--  1.3.6.1.4.1.6296.101.23.7.7.6.1.15
		sleGponOnuPMStatsSumOnuGEMDayReceivedPackets OBJECT-TYPE
			SYNTAX Counter64
			MAX-ACCESS read-write
			STATUS current
			DESCRIPTION
				"The day number of received packet"
			::= { sleGponOnuPMStatsSumOnuGEMEntry 15 }


--  1.3.6.1.4.1.6296.101.23.7.7.6.1.16
		sleGponOnuPMStatsSumOnuGEMDayReceivedBlocks OBJECT-TYPE
			SYNTAX Counter64
			MAX-ACCESS read-write
			STATUS current
			DESCRIPTION
				"The day number of received blocks"
			::= { sleGponOnuPMStatsSumOnuGEMEntry 16 }


--  1.3.6.1.4.1.6296.101.23.7.7.6.1.17
		sleGponOnuPMStatsSumOnuGEMDayTransmittedBlocks OBJECT-TYPE
			SYNTAX Counter64
			MAX-ACCESS read-write
			STATUS current
			DESCRIPTION
				"The day number of transmitted blocks"
			::= { sleGponOnuPMStatsSumOnuGEMEntry 17 }


--  1.3.6.1.4.1.6296.101.23.7.7.6.1.18
		sleGponOnuPMStatsSumOnuGEMDayImpairedBlocks OBJECT-TYPE
			SYNTAX Counter64
			MAX-ACCESS read-write
			STATUS current
			DESCRIPTION
				"The day number of impaired blocks"
			::= { sleGponOnuPMStatsSumOnuGEMEntry 18 }


--  1.3.6.1.4.1.6296.101.23.7.7.6.1.19
		sleGponOnuPMStatsSumOnuGEMTotalLostPackets OBJECT-TYPE
			SYNTAX Counter64
			MAX-ACCESS read-write
			STATUS current
			DESCRIPTION
				"The total number of lost packet "
			::= { sleGponOnuPMStatsSumOnuGEMEntry 19 }


--  1.3.6.1.4.1.6296.101.23.7.7.6.1.20
		sleGponOnuPMStatsSumOnuGEMTotalMisInsertedPackets OBJECT-TYPE
			SYNTAX Counter64
			MAX-ACCESS read-write
			STATUS current
			DESCRIPTION
				"The total number of mis inserted packet "
			::= { sleGponOnuPMStatsSumOnuGEMEntry 20 }


--  1.3.6.1.4.1.6296.101.23.7.7.6.1.21
		sleGponOnuPMStatsSumOnuGEMTotalReceivedPackets OBJECT-TYPE
			SYNTAX Counter64
			MAX-ACCESS read-write
			STATUS current
			DESCRIPTION
				"The total number of received packet"
			::= { sleGponOnuPMStatsSumOnuGEMEntry 21 }


--  1.3.6.1.4.1.6296.101.23.7.7.6.1.22
		sleGponOnuPMStatsSumOnuGEMTotalReceivedBlocks OBJECT-TYPE
			SYNTAX Counter64
			MAX-ACCESS read-write
			STATUS current
			DESCRIPTION
				"The total number of received blocks"
			::= { sleGponOnuPMStatsSumOnuGEMEntry 22 }


--  1.3.6.1.4.1.6296.101.23.7.7.6.1.23
		sleGponOnuPMStatsSumOnuGEMTotalTransmittedBlocks OBJECT-TYPE
			SYNTAX Counter64
			MAX-ACCESS read-write
			STATUS current
			DESCRIPTION
				"The total number of transmitted blocks"
			::= { sleGponOnuPMStatsSumOnuGEMEntry 23 }


--  1.3.6.1.4.1.6296.101.23.7.7.6.1.24
		sleGponOnuPMStatsSumOnuGEMTotalImpairedBlocks OBJECT-TYPE
			SYNTAX Counter64
			MAX-ACCESS read-write
			STATUS current
			DESCRIPTION
				"The total number of impaired blocks"
			::= { sleGponOnuPMStatsSumOnuGEMEntry 24 }


--  1.3.6.1.4.1.6296.101.23.7.7.7
		sleGponOnuPMStatsSumOnuAniTable OBJECT-TYPE
			SYNTAX SEQUENCE OF SleGponOnuPMStatsSumOnuAniEntry
			MAX-ACCESS not-accessible
			STATUS current
			DESCRIPTION
				"sleGponOnuPMStatsDetailAniTable"
			::= { sleGponOnuPMStatatisticsSum 7 }


--  1.3.6.1.4.1.6296.101.23.7.7.7.1
		sleGponOnuPMStatsSumOnuAniEntry OBJECT-TYPE
			SYNTAX SleGponOnuPMStatsSumOnuAniEntry
			MAX-ACCESS not-accessible
			STATUS current
			DESCRIPTION
				"key: sleGponOnuPMStatsDetailAniPort, sleGponOltId, sleGponOnuId"
			INDEX { sleGponOltId, sleGponOnuId }
			::= { sleGponOnuPMStatsSumOnuAniTable 1 }


		SleGponOnuPMStatsSumOnuAniEntry ::=
			SEQUENCE {
				sleGponOnuPMStatsSumOnuAniPre15mDiscardedFrames
					Counter64,
				sleGponOnuPMStatsSumOnuAniHourDiscardedFrames
					Counter64,
				sleGponOnuPMStatsSumOnuAniDayDiscardedFrames
					Counter64,
				sleGponOnuPMStatsSumOnuAniTotalDiscardedFrames
					Counter64
			 }

--  1.3.6.1.4.1.6296.101.23.7.7.7.1.1
		sleGponOnuPMStatsSumOnuAniPre15mDiscardedFrames OBJECT-TYPE
			SYNTAX Counter64
			MAX-ACCESS read-only
			STATUS current
			DESCRIPTION
				"The pre 15 minute number of lost discarded frames"
			::= { sleGponOnuPMStatsSumOnuAniEntry 1 }


--  1.3.6.1.4.1.6296.101.23.7.7.7.1.2
		sleGponOnuPMStatsSumOnuAniHourDiscardedFrames OBJECT-TYPE
			SYNTAX Counter64
			MAX-ACCESS read-only
			STATUS current
			DESCRIPTION
				"The hour number of lost discarded frames"
			::= { sleGponOnuPMStatsSumOnuAniEntry 2 }


--  1.3.6.1.4.1.6296.101.23.7.7.7.1.3
		sleGponOnuPMStatsSumOnuAniDayDiscardedFrames OBJECT-TYPE
			SYNTAX Counter64
			MAX-ACCESS read-only
			STATUS current
			DESCRIPTION
				"The day number of lost discarded frames"
			::= { sleGponOnuPMStatsSumOnuAniEntry 3 }


--  1.3.6.1.4.1.6296.101.23.7.7.7.1.4
		sleGponOnuPMStatsSumOnuAniTotalDiscardedFrames OBJECT-TYPE
			SYNTAX Counter64
			MAX-ACCESS read-only
			STATUS current
			DESCRIPTION
				"The total number of lost discarded frames"
			::= { sleGponOnuPMStatsSumOnuAniEntry 4 }


--  1.3.6.1.4.1.6296.101.23.7.7.8
		sleGponOnuPMStatsSumOnuEthFrameUpTable OBJECT-TYPE
			SYNTAX SEQUENCE OF SleGponOnuPMStatsSumOnuEthFrameUpEntry
			MAX-ACCESS not-accessible
			STATUS current
			DESCRIPTION
				"sleGponOnuPMStatsDetailUniEthFrameUpTable"
			::= { sleGponOnuPMStatatisticsSum 8 }


--  1.3.6.1.4.1.6296.101.23.7.7.8.1
		sleGponOnuPMStatsSumOnuEthFrameUpEntry OBJECT-TYPE
			SYNTAX SleGponOnuPMStatsSumOnuEthFrameUpEntry
			MAX-ACCESS not-accessible
			STATUS current
			DESCRIPTION
				"key: sleGponOltId, sleGponOnuId, sleGponOnuPMStatsDetailUniEthFrameUpUniPort"
			INDEX { sleGponOltId, sleGponOnuId }
			::= { sleGponOnuPMStatsSumOnuEthFrameUpTable 1 }


		SleGponOnuPMStatsSumOnuEthFrameUpEntry ::=
			SEQUENCE {
				sleGponOnuPMStatsSumOnuEthFrameUpPre15mDropEvents
					Counter64,
				sleGponOnuPMStatsSumOnuEthFrameUpPre15mOctets
					Counter64,
				sleGponOnuPMStatsSumOnuEthFrameUpPre15mPackets
					Counter64,
				sleGponOnuPMStatsSumOnuEthFrameUpPre15mBcastPackets
					Counter64,
				sleGponOnuPMStatsSumOnuEthFrameUpPre15mMcastPackets
					Counter64,
				sleGponOnuPMStatsSumOnuEthFrameUpPre15mUcastPackets
					Counter64,
				sleGponOnuPMStatsSumOnuEthFrameUpPre15mCRCErroredPackets
					Counter64,
				sleGponOnuPMStatsSumOnuEthFrameUpPre15mUndersizePackets
					Counter64,
				sleGponOnuPMStatsSumOnuEthFrameUpPre15mOversizePackets
					Counter64,
				sleGponOnuPMStatsSumOnuEthFrameUpPre15mPkt64Octets
					Counter64,
				sleGponOnuPMStatsSumOnuEthFrameUpPre15mPkt65To127Octets
					Counter64,
				sleGponOnuPMStatsSumOnuEthFrameUpPre15mPkt128To255Octets
					Counter64,
				sleGponOnuPMStatsSumOnuEthFrameUpPre15mPkt256To511Octets
					Counter64,
				sleGponOnuPMStatsSumOnuEthFrameUpPre15mPkt512To1023Octets
					Counter64,
				sleGponOnuPMStatsSumOnuEthFrameUpPre15mPkt1024To1518Octets
					Counter64,
				sleGponOnuPMStatsSumOnuEthFrameUpHourDropEvents
					Counter64,
				sleGponOnuPMStatsSumOnuEthFrameUpHourOctets
					Counter64,
				sleGponOnuPMStatsSumOnuEthFrameUpHourPackets
					Counter64,
				sleGponOnuPMStatsSumOnuEthFrameUpHourBcastPackets
					Counter64,
				sleGponOnuPMStatsSumOnuEthFrameUpHourMcastPackets
					Counter64,
				sleGponOnuPMStatsSumOnuEthFrameUpHourUcastPackets
					Counter64,
				sleGponOnuPMStatsSumOnuEthFrameUpHourCRCErroredPackets
					Counter64,
				sleGponOnuPMStatsSumOnuEthFrameUpHourUndersizePackets
					Counter64,
				sleGponOnuPMStatsSumOnuEthFrameUpHourOversizePackets
					Counter64,
				sleGponOnuPMStatsSumOnuEthFrameUpHourPkt64Octets
					Counter64,
				sleGponOnuPMStatsSumOnuEthFrameUpHourPkt65To127Octets
					Counter64,
				sleGponOnuPMStatsSumOnuEthFrameUpHourPkt128To255Octets
					Counter64,
				sleGponOnuPMStatsSumOnuEthFrameUpHourPkt256To511Octets
					Counter64,
				sleGponOnuPMStatsSumOnuEthFrameUpHourPkt512To1023Octets
					Counter64,
				sleGponOnuPMStatsSumOnuEthFrameUpHourPkt1024To1518Octets
					Counter64,
				sleGponOnuPMStatsSumOnuEthFrameUpDayDropEvents
					Counter64,
				sleGponOnuPMStatsSumOnuEthFrameUpDayOctets
					Counter64,
				sleGponOnuPMStatsSumOnuEthFrameUpDayPackets
					Counter64,
				sleGponOnuPMStatsSumOnuEthFrameUpDayBcastPackets
					Counter64,
				sleGponOnuPMStatsSumOnuEthFrameUpDayMcastPackets
					Counter64,
				sleGponOnuPMStatsSumOnuEthFrameUpDayUcastPackets
					Counter64,
				sleGponOnuPMStatsSumOnuEthFrameUpDayCRCErroredPackets
					Counter64,
				sleGponOnuPMStatsSumOnuEthFrameUpDayUndersizePackets
					Counter64,
				sleGponOnuPMStatsSumOnuEthFrameUpDayOversizePackets
					Counter64,
				sleGponOnuPMStatsSumOnuEthFrameUpDayPkt64Octets
					Counter64,
				sleGponOnuPMStatsSumOnuEthFrameUpDayPkt65To127Octets
					Counter64,
				sleGponOnuPMStatsSumOnuEthFrameUpDayPkt128To255Octets
					Counter64,
				sleGponOnuPMStatsSumOnuEthFrameUpDayPkt256To511Octets
					Counter64,
				sleGponOnuPMStatsSumOnuEthFrameUpDayPkt512To1023Octets
					Counter64,
				sleGponOnuPMStatsSumOnuEthFrameUpDayPkt1024To1518Octets
					Counter64,
				sleGponOnuPMStatsSumOnuEthFrameUpTotalDropEvents
					Counter64,
				sleGponOnuPMStatsSumOnuEthFrameUpTotalOctets
					Counter64,
				sleGponOnuPMStatsSumOnuEthFrameUpTotalPackets
					Counter64,
				sleGponOnuPMStatsSumOnuEthFrameUpTotalBcastPackets
					Counter64,
				sleGponOnuPMStatsSumOnuEthFrameUpTotalMcastPackets
					Counter64,
				sleGponOnuPMStatsSumOnuEthFrameUpTotalUcastPackets
					Counter64,
				sleGponOnuPMStatsSumOnuEthFrameUpTotalCRCErroredPackets
					Counter64,
				sleGponOnuPMStatsSumOnuEthFrameUpTotalUndersizePackets
					Counter64,
				sleGponOnuPMStatsSumOnuEthFrameUpTotalOversizePackets
					Counter64,
				sleGponOnuPMStatsSumOnuEthFrameUpTotalPkt64Octets
					Counter64,
				sleGponOnuPMStatsSumOnuEthFrameUpTotalPkt65To127Octets
					Counter64,
				sleGponOnuPMStatsSumOnuEthFrameUpTotalPkt128To255Octets
					Counter64,
				sleGponOnuPMStatsSumOnuEthFrameUpTotalPkt256To511Octets
					Counter64,
				sleGponOnuPMStatsSumOnuEthFrameUpTotalPkt512To1023Octets
					Counter64,
				sleGponOnuPMStatsSumOnuEthFrameUpTotalPkt1024To1518Octets
					Counter64
			 }

--  1.3.6.1.4.1.6296.101.23.7.7.8.1.1
		sleGponOnuPMStatsSumOnuEthFrameUpPre15mDropEvents OBJECT-TYPE
			SYNTAX Counter64
			MAX-ACCESS read-only
			STATUS current
			DESCRIPTION
				"The pre 15 minute number of events in which packets were dropped due to lack
				of resources."
			::= { sleGponOnuPMStatsSumOnuEthFrameUpEntry 1 }


--  1.3.6.1.4.1.6296.101.23.7.7.8.1.2
		sleGponOnuPMStatsSumOnuEthFrameUpPre15mOctets OBJECT-TYPE
			SYNTAX Counter64
			MAX-ACCESS read-only
			STATUS current
			DESCRIPTION
				"The pre 15 minute number of octets received"
			::= { sleGponOnuPMStatsSumOnuEthFrameUpEntry 2 }


--  1.3.6.1.4.1.6296.101.23.7.7.8.1.3
		sleGponOnuPMStatsSumOnuEthFrameUpPre15mPackets OBJECT-TYPE
			SYNTAX Counter64
			MAX-ACCESS read-only
			STATUS current
			DESCRIPTION
				"The pre 15 minute number of packets received,"
			::= { sleGponOnuPMStatsSumOnuEthFrameUpEntry 3 }


--  1.3.6.1.4.1.6296.101.23.7.7.8.1.4
		sleGponOnuPMStatsSumOnuEthFrameUpPre15mBcastPackets OBJECT-TYPE
			SYNTAX Counter64
			MAX-ACCESS read-only
			STATUS current
			DESCRIPTION
				"The pre 15 minute number of received good packets directed to the broadcast address"
			::= { sleGponOnuPMStatsSumOnuEthFrameUpEntry 4 }


--  1.3.6.1.4.1.6296.101.23.7.7.8.1.5
		sleGponOnuPMStatsSumOnuEthFrameUpPre15mMcastPackets OBJECT-TYPE
			SYNTAX Counter64
			MAX-ACCESS read-only
			STATUS current
			DESCRIPTION
				"The pre 15 minute number of received good packets directed to a multicast address."
			::= { sleGponOnuPMStatsSumOnuEthFrameUpEntry 5 }


--  1.3.6.1.4.1.6296.101.23.7.7.8.1.6
		sleGponOnuPMStatsSumOnuEthFrameUpPre15mUcastPackets OBJECT-TYPE
			SYNTAX Counter64
			MAX-ACCESS read-only
			STATUS current
			DESCRIPTION
				"The pre 15 minute number of received good packets directed to the unicast address"
			::= { sleGponOnuPMStatsSumOnuEthFrameUpEntry 6 }


--  1.3.6.1.4.1.6296.101.23.7.7.8.1.7
		sleGponOnuPMStatsSumOnuEthFrameUpPre15mCRCErroredPackets OBJECT-TYPE
			SYNTAX Counter64
			MAX-ACCESS read-only
			STATUS current
			DESCRIPTION
				"The pre 15 minute number of packets received that had a length"
			::= { sleGponOnuPMStatsSumOnuEthFrameUpEntry 7 }


--  1.3.6.1.4.1.6296.101.23.7.7.8.1.8
		sleGponOnuPMStatsSumOnuEthFrameUpPre15mUndersizePackets OBJECT-TYPE
			SYNTAX Counter64
			MAX-ACCESS read-only
			STATUS current
			DESCRIPTION
				"The pre 15 minute number of packets received that were less than 64 octets long"
			::= { sleGponOnuPMStatsSumOnuEthFrameUpEntry 8 }


--  1.3.6.1.4.1.6296.101.23.7.7.8.1.9
		sleGponOnuPMStatsSumOnuEthFrameUpPre15mOversizePackets OBJECT-TYPE
			SYNTAX Counter64
			MAX-ACCESS read-only
			STATUS current
			DESCRIPTION
				"The pre 15 minute number of packets received that were longer than 1518 octets"
			::= { sleGponOnuPMStatsSumOnuEthFrameUpEntry 9 }


--  1.3.6.1.4.1.6296.101.23.7.7.8.1.10
		sleGponOnuPMStatsSumOnuEthFrameUpPre15mPkt64Octets OBJECT-TYPE
			SYNTAX Counter64
			MAX-ACCESS read-only
			STATUS current
			DESCRIPTION
				"The pre 15 minute number of received packets (including bad packets) that were
				64 octets long,
				"
			::= { sleGponOnuPMStatsSumOnuEthFrameUpEntry 10 }


--  1.3.6.1.4.1.6296.101.23.7.7.8.1.11
		sleGponOnuPMStatsSumOnuEthFrameUpPre15mPkt65To127Octets OBJECT-TYPE
			SYNTAX Counter64
			MAX-ACCESS read-only
			STATUS current
			DESCRIPTION
				"The pre 15 minute number of received packets (including bad packets) that were
				65..127 octets long,
				"
			::= { sleGponOnuPMStatsSumOnuEthFrameUpEntry 11 }


--  1.3.6.1.4.1.6296.101.23.7.7.8.1.12
		sleGponOnuPMStatsSumOnuEthFrameUpPre15mPkt128To255Octets OBJECT-TYPE
			SYNTAX Counter64
			MAX-ACCESS read-only
			STATUS current
			DESCRIPTION
				"The pre 15 minute number of packets (including bad packets) received that were
				128..255 octets long,
				"
			::= { sleGponOnuPMStatsSumOnuEthFrameUpEntry 12 }


--  1.3.6.1.4.1.6296.101.23.7.7.8.1.13
		sleGponOnuPMStatsSumOnuEthFrameUpPre15mPkt256To511Octets OBJECT-TYPE
			SYNTAX Counter64
			MAX-ACCESS read-only
			STATUS current
			DESCRIPTION
				"The pre 15 minute number of packets (including bad packets) received that were
				256..511 octets long,
				"
			::= { sleGponOnuPMStatsSumOnuEthFrameUpEntry 13 }


--  1.3.6.1.4.1.6296.101.23.7.7.8.1.14
		sleGponOnuPMStatsSumOnuEthFrameUpPre15mPkt512To1023Octets OBJECT-TYPE
			SYNTAX Counter64
			MAX-ACCESS read-only
			STATUS current
			DESCRIPTION
				"The pre 15 minute number of packets (including bad packets) received that were
				512..1023 octets long,
				"
			::= { sleGponOnuPMStatsSumOnuEthFrameUpEntry 14 }


--  1.3.6.1.4.1.6296.101.23.7.7.8.1.15
		sleGponOnuPMStatsSumOnuEthFrameUpPre15mPkt1024To1518Octets OBJECT-TYPE
			SYNTAX Counter64
			MAX-ACCESS read-only
			STATUS current
			DESCRIPTION
				"The pre 15 minute number of packets (including bad packets) received that were
				1024..1518 octets long,
				"
			::= { sleGponOnuPMStatsSumOnuEthFrameUpEntry 15 }


--  1.3.6.1.4.1.6296.101.23.7.7.8.1.16
		sleGponOnuPMStatsSumOnuEthFrameUpHourDropEvents OBJECT-TYPE
			SYNTAX Counter64
			MAX-ACCESS read-only
			STATUS current
			DESCRIPTION
				"The hour number of events in which packets were dropped due to lack
				of resources.
				"
			::= { sleGponOnuPMStatsSumOnuEthFrameUpEntry 16 }


--  1.3.6.1.4.1.6296.101.23.7.7.8.1.17
		sleGponOnuPMStatsSumOnuEthFrameUpHourOctets OBJECT-TYPE
			SYNTAX Counter64
			MAX-ACCESS read-only
			STATUS current
			DESCRIPTION
				"The hour number of octets received"
			::= { sleGponOnuPMStatsSumOnuEthFrameUpEntry 17 }


--  1.3.6.1.4.1.6296.101.23.7.7.8.1.18
		sleGponOnuPMStatsSumOnuEthFrameUpHourPackets OBJECT-TYPE
			SYNTAX Counter64
			MAX-ACCESS read-only
			STATUS current
			DESCRIPTION
				"The hour number of packets received,"
			::= { sleGponOnuPMStatsSumOnuEthFrameUpEntry 18 }


--  1.3.6.1.4.1.6296.101.23.7.7.8.1.19
		sleGponOnuPMStatsSumOnuEthFrameUpHourBcastPackets OBJECT-TYPE
			SYNTAX Counter64
			MAX-ACCESS read-write
			STATUS current
			DESCRIPTION
				"The hour number of received good packets directed to the broadcast address"
			::= { sleGponOnuPMStatsSumOnuEthFrameUpEntry 19 }


--  1.3.6.1.4.1.6296.101.23.7.7.8.1.20
		sleGponOnuPMStatsSumOnuEthFrameUpHourMcastPackets OBJECT-TYPE
			SYNTAX Counter64
			MAX-ACCESS read-only
			STATUS current
			DESCRIPTION
				"The hour number of received good packets directed to a multicast address."
			::= { sleGponOnuPMStatsSumOnuEthFrameUpEntry 20 }


--  1.3.6.1.4.1.6296.101.23.7.7.8.1.21
		sleGponOnuPMStatsSumOnuEthFrameUpHourUcastPackets OBJECT-TYPE
			SYNTAX Counter64
			MAX-ACCESS read-only
			STATUS current
			DESCRIPTION
				"The hour number of received good packets directed to the unicast address"
			::= { sleGponOnuPMStatsSumOnuEthFrameUpEntry 21 }


--  1.3.6.1.4.1.6296.101.23.7.7.8.1.22
		sleGponOnuPMStatsSumOnuEthFrameUpHourCRCErroredPackets OBJECT-TYPE
			SYNTAX Counter64
			MAX-ACCESS read-only
			STATUS current
			DESCRIPTION
				"The hour number of packets received that had a length"
			::= { sleGponOnuPMStatsSumOnuEthFrameUpEntry 22 }


--  1.3.6.1.4.1.6296.101.23.7.7.8.1.23
		sleGponOnuPMStatsSumOnuEthFrameUpHourUndersizePackets OBJECT-TYPE
			SYNTAX Counter64
			MAX-ACCESS read-only
			STATUS current
			DESCRIPTION
				"The hour number of packets received that were less than 64 octets long"
			::= { sleGponOnuPMStatsSumOnuEthFrameUpEntry 23 }


--  1.3.6.1.4.1.6296.101.23.7.7.8.1.24
		sleGponOnuPMStatsSumOnuEthFrameUpHourOversizePackets OBJECT-TYPE
			SYNTAX Counter64
			MAX-ACCESS read-only
			STATUS current
			DESCRIPTION
				"The hour number of packets received that were longer than 1518 octets"
			::= { sleGponOnuPMStatsSumOnuEthFrameUpEntry 24 }


--  1.3.6.1.4.1.6296.101.23.7.7.8.1.25
		sleGponOnuPMStatsSumOnuEthFrameUpHourPkt64Octets OBJECT-TYPE
			SYNTAX Counter64
			MAX-ACCESS read-only
			STATUS current
			DESCRIPTION
				"The hour number of received packets (including bad packets) that were
				64 octets long,
				"
			::= { sleGponOnuPMStatsSumOnuEthFrameUpEntry 25 }


--  1.3.6.1.4.1.6296.101.23.7.7.8.1.26
		sleGponOnuPMStatsSumOnuEthFrameUpHourPkt65To127Octets OBJECT-TYPE
			SYNTAX Counter64
			MAX-ACCESS read-only
			STATUS current
			DESCRIPTION
				"The hour number of received packets (including bad packets) that were
				65..127 octets long,
				"
			::= { sleGponOnuPMStatsSumOnuEthFrameUpEntry 26 }


--  1.3.6.1.4.1.6296.101.23.7.7.8.1.27
		sleGponOnuPMStatsSumOnuEthFrameUpHourPkt128To255Octets OBJECT-TYPE
			SYNTAX Counter64
			MAX-ACCESS read-write
			STATUS current
			DESCRIPTION
				"The hour number of packets (including bad packets) received that were
				128..255 octets long,
				"
			::= { sleGponOnuPMStatsSumOnuEthFrameUpEntry 27 }


--  1.3.6.1.4.1.6296.101.23.7.7.8.1.28
		sleGponOnuPMStatsSumOnuEthFrameUpHourPkt256To511Octets OBJECT-TYPE
			SYNTAX Counter64
			MAX-ACCESS read-only
			STATUS current
			DESCRIPTION
				"The hour number of packets (including bad packets) received that were
				256..511 octets long,
				"
			::= { sleGponOnuPMStatsSumOnuEthFrameUpEntry 28 }


--  1.3.6.1.4.1.6296.101.23.7.7.8.1.29
		sleGponOnuPMStatsSumOnuEthFrameUpHourPkt512To1023Octets OBJECT-TYPE
			SYNTAX Counter64
			MAX-ACCESS read-write
			STATUS current
			DESCRIPTION
				"The hour number of packets (including bad packets) received that were
				512..1023 octets long,
				"
			::= { sleGponOnuPMStatsSumOnuEthFrameUpEntry 29 }


--  1.3.6.1.4.1.6296.101.23.7.7.8.1.30
		sleGponOnuPMStatsSumOnuEthFrameUpHourPkt1024To1518Octets OBJECT-TYPE
			SYNTAX Counter64
			MAX-ACCESS read-only
			STATUS current
			DESCRIPTION
				"The hour number of packets (including bad packets) received that were
				1024..1518 octets long,

				"
			::= { sleGponOnuPMStatsSumOnuEthFrameUpEntry 30 }


--  1.3.6.1.4.1.6296.101.23.7.7.8.1.31
		sleGponOnuPMStatsSumOnuEthFrameUpDayDropEvents OBJECT-TYPE
			SYNTAX Counter64
			MAX-ACCESS read-only
			STATUS current
			DESCRIPTION
				"The day number of events in which packets were dropped due to lack of resources."
			::= { sleGponOnuPMStatsSumOnuEthFrameUpEntry 31 }


--  1.3.6.1.4.1.6296.101.23.7.7.8.1.32
		sleGponOnuPMStatsSumOnuEthFrameUpDayOctets OBJECT-TYPE
			SYNTAX Counter64
			MAX-ACCESS read-only
			STATUS current
			DESCRIPTION
				"The day number of octets received"
			::= { sleGponOnuPMStatsSumOnuEthFrameUpEntry 32 }


--  1.3.6.1.4.1.6296.101.23.7.7.8.1.33
		sleGponOnuPMStatsSumOnuEthFrameUpDayPackets OBJECT-TYPE
			SYNTAX Counter64
			MAX-ACCESS read-only
			STATUS current
			DESCRIPTION
				"The day number of packets received,"
			::= { sleGponOnuPMStatsSumOnuEthFrameUpEntry 33 }


--  1.3.6.1.4.1.6296.101.23.7.7.8.1.34
		sleGponOnuPMStatsSumOnuEthFrameUpDayBcastPackets OBJECT-TYPE
			SYNTAX Counter64
			MAX-ACCESS read-write
			STATUS current
			DESCRIPTION
				"The day number of received good packets directed to the broadcast address"
			::= { sleGponOnuPMStatsSumOnuEthFrameUpEntry 34 }


--  1.3.6.1.4.1.6296.101.23.7.7.8.1.35
		sleGponOnuPMStatsSumOnuEthFrameUpDayMcastPackets OBJECT-TYPE
			SYNTAX Counter64
			MAX-ACCESS read-only
			STATUS current
			DESCRIPTION
				"The day number of received good packets directed to a multicast address."
			::= { sleGponOnuPMStatsSumOnuEthFrameUpEntry 35 }


--  1.3.6.1.4.1.6296.101.23.7.7.8.1.36
		sleGponOnuPMStatsSumOnuEthFrameUpDayUcastPackets OBJECT-TYPE
			SYNTAX Counter64
			MAX-ACCESS read-only
			STATUS current
			DESCRIPTION
				"The day number of received good packets directed to the unicast address"
			::= { sleGponOnuPMStatsSumOnuEthFrameUpEntry 36 }


--  1.3.6.1.4.1.6296.101.23.7.7.8.1.37
		sleGponOnuPMStatsSumOnuEthFrameUpDayCRCErroredPackets OBJECT-TYPE
			SYNTAX Counter64
			MAX-ACCESS read-only
			STATUS current
			DESCRIPTION
				"The day number of packets received that had a length"
			::= { sleGponOnuPMStatsSumOnuEthFrameUpEntry 37 }


--  1.3.6.1.4.1.6296.101.23.7.7.8.1.38
		sleGponOnuPMStatsSumOnuEthFrameUpDayUndersizePackets OBJECT-TYPE
			SYNTAX Counter64
			MAX-ACCESS read-only
			STATUS current
			DESCRIPTION
				"The day number of packets received that were less than 64 octets long"
			::= { sleGponOnuPMStatsSumOnuEthFrameUpEntry 38 }


--  1.3.6.1.4.1.6296.101.23.7.7.8.1.39
		sleGponOnuPMStatsSumOnuEthFrameUpDayOversizePackets OBJECT-TYPE
			SYNTAX Counter64
			MAX-ACCESS read-only
			STATUS current
			DESCRIPTION
				"The day number of packets received that were longer than 1518 octets"
			::= { sleGponOnuPMStatsSumOnuEthFrameUpEntry 39 }


--  1.3.6.1.4.1.6296.101.23.7.7.8.1.40
		sleGponOnuPMStatsSumOnuEthFrameUpDayPkt64Octets OBJECT-TYPE
			SYNTAX Counter64
			MAX-ACCESS read-only
			STATUS current
			DESCRIPTION
				"The day number of received packets (including bad packets) that were
				64 octets long,
				"
			::= { sleGponOnuPMStatsSumOnuEthFrameUpEntry 40 }


--  1.3.6.1.4.1.6296.101.23.7.7.8.1.41
		sleGponOnuPMStatsSumOnuEthFrameUpDayPkt65To127Octets OBJECT-TYPE
			SYNTAX Counter64
			MAX-ACCESS read-only
			STATUS current
			DESCRIPTION
				"The day number of received packets (including bad packets) that were
				65..127 octets long,
				"
			::= { sleGponOnuPMStatsSumOnuEthFrameUpEntry 41 }


--  1.3.6.1.4.1.6296.101.23.7.7.8.1.42
		sleGponOnuPMStatsSumOnuEthFrameUpDayPkt128To255Octets OBJECT-TYPE
			SYNTAX Counter64
			MAX-ACCESS read-write
			STATUS current
			DESCRIPTION
				"The day number of received packets (including bad packets) that were
				128..255 octets long,
				"
			::= { sleGponOnuPMStatsSumOnuEthFrameUpEntry 42 }


--  1.3.6.1.4.1.6296.101.23.7.7.8.1.43
		sleGponOnuPMStatsSumOnuEthFrameUpDayPkt256To511Octets OBJECT-TYPE
			SYNTAX Counter64
			MAX-ACCESS read-only
			STATUS current
			DESCRIPTION
				"The day number of received packets (including bad packets) that were
				256..511 octets long,
				"
			::= { sleGponOnuPMStatsSumOnuEthFrameUpEntry 43 }


--  1.3.6.1.4.1.6296.101.23.7.7.8.1.44
		sleGponOnuPMStatsSumOnuEthFrameUpDayPkt512To1023Octets OBJECT-TYPE
			SYNTAX Counter64
			MAX-ACCESS read-write
			STATUS current
			DESCRIPTION
				"The day number of packets (including bad packets) received that were
				512..1023 octets long,
				"
			::= { sleGponOnuPMStatsSumOnuEthFrameUpEntry 44 }


--  1.3.6.1.4.1.6296.101.23.7.7.8.1.45
		sleGponOnuPMStatsSumOnuEthFrameUpDayPkt1024To1518Octets OBJECT-TYPE
			SYNTAX Counter64
			MAX-ACCESS read-only
			STATUS current
			DESCRIPTION
				"The day number of packets (including bad packets) received that were
				1024..1518 octets long,
				"
			::= { sleGponOnuPMStatsSumOnuEthFrameUpEntry 45 }


--  1.3.6.1.4.1.6296.101.23.7.7.8.1.46
		sleGponOnuPMStatsSumOnuEthFrameUpTotalDropEvents OBJECT-TYPE
			SYNTAX Counter64
			MAX-ACCESS read-only
			STATUS current
			DESCRIPTION
				"The total number of events in which packets were dropped due to lack
				of resources."
			::= { sleGponOnuPMStatsSumOnuEthFrameUpEntry 46 }


--  1.3.6.1.4.1.6296.101.23.7.7.8.1.47
		sleGponOnuPMStatsSumOnuEthFrameUpTotalOctets OBJECT-TYPE
			SYNTAX Counter64
			MAX-ACCESS read-only
			STATUS current
			DESCRIPTION
				"The total number of octets received"
			::= { sleGponOnuPMStatsSumOnuEthFrameUpEntry 47 }


--  1.3.6.1.4.1.6296.101.23.7.7.8.1.48
		sleGponOnuPMStatsSumOnuEthFrameUpTotalPackets OBJECT-TYPE
			SYNTAX Counter64
			MAX-ACCESS read-only
			STATUS current
			DESCRIPTION
				"The total number of packets received,"
			::= { sleGponOnuPMStatsSumOnuEthFrameUpEntry 48 }


--  1.3.6.1.4.1.6296.101.23.7.7.8.1.49
		sleGponOnuPMStatsSumOnuEthFrameUpTotalBcastPackets OBJECT-TYPE
			SYNTAX Counter64
			MAX-ACCESS read-write
			STATUS current
			DESCRIPTION
				"The total number of received good packets directed to a broadcast  address."
			::= { sleGponOnuPMStatsSumOnuEthFrameUpEntry 49 }


--  1.3.6.1.4.1.6296.101.23.7.7.8.1.50
		sleGponOnuPMStatsSumOnuEthFrameUpTotalMcastPackets OBJECT-TYPE
			SYNTAX Counter64
			MAX-ACCESS read-only
			STATUS current
			DESCRIPTION
				"The total number of received good packets directed to a multicast address."
			::= { sleGponOnuPMStatsSumOnuEthFrameUpEntry 50 }


--  1.3.6.1.4.1.6296.101.23.7.7.8.1.51
		sleGponOnuPMStatsSumOnuEthFrameUpTotalUcastPackets OBJECT-TYPE
			SYNTAX Counter64
			MAX-ACCESS read-only
			STATUS current
			DESCRIPTION
				"The total number of received good packets directed to a multicast address."
			::= { sleGponOnuPMStatsSumOnuEthFrameUpEntry 51 }


--  1.3.6.1.4.1.6296.101.23.7.7.8.1.52
		sleGponOnuPMStatsSumOnuEthFrameUpTotalCRCErroredPackets OBJECT-TYPE
			SYNTAX Counter64
			MAX-ACCESS read-only
			STATUS current
			DESCRIPTION
				"The total number of packets received that had a length"
			::= { sleGponOnuPMStatsSumOnuEthFrameUpEntry 52 }


--  1.3.6.1.4.1.6296.101.23.7.7.8.1.53
		sleGponOnuPMStatsSumOnuEthFrameUpTotalUndersizePackets OBJECT-TYPE
			SYNTAX Counter64
			MAX-ACCESS read-only
			STATUS current
			DESCRIPTION
				"The total number of packets received that were less than 64 octets long"
			::= { sleGponOnuPMStatsSumOnuEthFrameUpEntry 53 }


--  1.3.6.1.4.1.6296.101.23.7.7.8.1.54
		sleGponOnuPMStatsSumOnuEthFrameUpTotalOversizePackets OBJECT-TYPE
			SYNTAX Counter64
			MAX-ACCESS read-only
			STATUS current
			DESCRIPTION
				"The total number of packets received that were longer than 1518 octets"
			::= { sleGponOnuPMStatsSumOnuEthFrameUpEntry 54 }


--  1.3.6.1.4.1.6296.101.23.7.7.8.1.55
		sleGponOnuPMStatsSumOnuEthFrameUpTotalPkt64Octets OBJECT-TYPE
			SYNTAX Counter64
			MAX-ACCESS read-only
			STATUS current
			DESCRIPTION
				"The total number of received packets (including bad packets) that were
				64 octets long,"
			::= { sleGponOnuPMStatsSumOnuEthFrameUpEntry 55 }


--  1.3.6.1.4.1.6296.101.23.7.7.8.1.56
		sleGponOnuPMStatsSumOnuEthFrameUpTotalPkt65To127Octets OBJECT-TYPE
			SYNTAX Counter64
			MAX-ACCESS read-only
			STATUS current
			DESCRIPTION
				"The total number of received packets (including bad packets) that were
				65..127 octets long,"
			::= { sleGponOnuPMStatsSumOnuEthFrameUpEntry 56 }


--  1.3.6.1.4.1.6296.101.23.7.7.8.1.57
		sleGponOnuPMStatsSumOnuEthFrameUpTotalPkt128To255Octets OBJECT-TYPE
			SYNTAX Counter64
			MAX-ACCESS read-write
			STATUS current
			DESCRIPTION
				"The total number of packets (including bad packets) received that were
				128..255 octets long,"
			::= { sleGponOnuPMStatsSumOnuEthFrameUpEntry 57 }


--  1.3.6.1.4.1.6296.101.23.7.7.8.1.58
		sleGponOnuPMStatsSumOnuEthFrameUpTotalPkt256To511Octets OBJECT-TYPE
			SYNTAX Counter64
			MAX-ACCESS read-only
			STATUS current
			DESCRIPTION
				"The total number of packets (including bad packets) received that were
				256..511 octets long,"
			::= { sleGponOnuPMStatsSumOnuEthFrameUpEntry 58 }


--  1.3.6.1.4.1.6296.101.23.7.7.8.1.59
		sleGponOnuPMStatsSumOnuEthFrameUpTotalPkt512To1023Octets OBJECT-TYPE
			SYNTAX Counter64
			MAX-ACCESS read-write
			STATUS current
			DESCRIPTION
				"The total number of packets (including bad packets) received that were
				512..1023 octets long,"
			::= { sleGponOnuPMStatsSumOnuEthFrameUpEntry 59 }


--  1.3.6.1.4.1.6296.101.23.7.7.8.1.60
		sleGponOnuPMStatsSumOnuEthFrameUpTotalPkt1024To1518Octets OBJECT-TYPE
			SYNTAX Counter64
			MAX-ACCESS read-only
			STATUS current
			DESCRIPTION
				"The total number of packets (including bad packets) received that were
				1024..1518 octets long,"
			::= { sleGponOnuPMStatsSumOnuEthFrameUpEntry 60 }


--  1.3.6.1.4.1.6296.101.23.7.7.9
		sleGponOnuPMStatsSumOnuEthFrameDownTable OBJECT-TYPE
			SYNTAX SEQUENCE OF SleGponOnuPMStatsSumOnuEthFrameDownEntry
			MAX-ACCESS not-accessible
			STATUS current
			DESCRIPTION
				"sleGponOnuPMStatsDetailUniEthFrameDownTable"
			::= { sleGponOnuPMStatatisticsSum 9 }


--  1.3.6.1.4.1.6296.101.23.7.7.9.1
		sleGponOnuPMStatsSumOnuEthFrameDownEntry OBJECT-TYPE
			SYNTAX SleGponOnuPMStatsSumOnuEthFrameDownEntry
			MAX-ACCESS not-accessible
			STATUS current
			DESCRIPTION
				"key: sleGponOltId, sleGponOnuId, sleGponOnuPMStatsDetailUniEthFrameUpUniPort"
			INDEX { sleGponOltId, sleGponOnuId }
			::= { sleGponOnuPMStatsSumOnuEthFrameDownTable 1 }


		SleGponOnuPMStatsSumOnuEthFrameDownEntry ::=
			SEQUENCE {
				sleGponOnuPMStatsSumOnuEthFrameDownPre15mDropEvents
					Counter64,
				sleGponOnuPMStatsSumOnuEthFrameDownPre15mOctets
					Counter64,
				sleGponOnuPMStatsSumOnuEthFrameDownPre15mPackets
					Counter64,
				sleGponOnuPMStatsSumOnuEthFrameDownPre15mBcastPackets
					Counter64,
				sleGponOnuPMStatsSumOnuEthFrameDownPre15mMcastPackets
					Counter64,
				sleGponOnuPMStatsSumOnuEthFrameDownPre15mUcastPackets
					Counter64,
				sleGponOnuPMStatsSumOnuEthFrameDownPre15mCRCErroredPackets
					Counter64,
				sleGponOnuPMStatsSumOnuEthFrameDownPre15mUndersizePackets
					Counter64,
				sleGponOnuPMStatsSumOnuEthFrameDownPre15mOversizePackets
					Counter64,
				sleGponOnuPMStatsSumOnuEthFrameDownPre15mPkt64Octets
					Counter64,
				sleGponOnuPMStatsSumOnuEthFrameDownPre15mPkt65To127Octets
					Counter64,
				sleGponOnuPMStatsSumOnuEthFrameDownPre15mPkt128To255Octets
					Counter64,
				sleGponOnuPMStatsSumOnuEthFrameDownPre15mPkt256To511Octets
					Counter64,
				sleGponOnuPMStatsSumOnuEthFrameDownPre15mPkt512To1023Octets
					Counter64,
				sleGponOnuPMStatsSumOnuEthFrameDownPre15mPkt1024To1518Octets
					Counter64,
				sleGponOnuPMStatsSumOnuEthFrameDownHourDropEvents
					Counter64,
				sleGponOnuPMStatsSumOnuEthFrameDownHourOctets
					Counter64,
				sleGponOnuPMStatsSumOnuEthFrameDownHourPackets
					Counter64,
				sleGponOnuPMStatsSumOnuEthFrameDownHourBcastPackets
					Counter64,
				sleGponOnuPMStatsSumOnuEthFrameDownHourMcastPackets
					Counter64,
				sleGponOnuPMStatsSumOnuEthFrameDownHourUcastPackets
					Counter64,
				sleGponOnuPMStatsSumOnuEthFrameDownHourCRCErroredPackets
					Counter64,
				sleGponOnuPMStatsSumOnuEthFrameDownHourUndersizePackets
					Counter64,
				sleGponOnuPMStatsSumOnuEthFrameDownHourOversizePackets
					Counter64,
				sleGponOnuPMStatsSumOnuEthFrameDownHourPkt64Octets
					Counter64,
				sleGponOnuPMStatsSumOnuEthFrameDownHourPkt65To127Octets
					Counter64,
				sleGponOnuPMStatsSumOnuEthFrameDownHourPkt128To255Octets
					Counter64,
				sleGponOnuPMStatsSumOnuEthFrameDownHourPkt256To511Octets
					Counter64,
				sleGponOnuPMStatsSumOnuEthFrameDownHourPkt512To1023Octets
					Counter64,
				sleGponOnuPMStatsSumOnuEthFrameDownHourPkt1024To1518Octets
					Counter64,
				sleGponOnuPMStatsSumOnuEthFrameDownDayDropEvents
					Counter64,
				sleGponOnuPMStatsSumOnuEthFrameDownDayOctets
					Counter64,
				sleGponOnuPMStatsSumOnuEthFrameDownDayPackets
					Counter64,
				sleGponOnuPMStatsSumOnuEthFrameDownDayBcastPackets
					Counter64,
				sleGponOnuPMStatsSumOnuEthFrameDownDayMcastPackets
					Counter64,
				sleGponOnuPMStatsSumOnuEthFrameDownDayUcastPackets
					Counter64,
				sleGponOnuPMStatsSumOnuEthFrameDownDayCRCErroredPackets
					Counter64,
				sleGponOnuPMStatsSumOnuEthFrameDownDayUndersizePackets
					Counter64,
				sleGponOnuPMStatsSumOnuEthFrameDownDayOversizePackets
					Counter64,
				sleGponOnuPMStatsSumOnuEthFrameDownDayPkt64Octets
					Counter64,
				sleGponOnuPMStatsSumOnuEthFrameDownDayPkt65To127Octets
					Counter64,
				sleGponOnuPMStatsSumOnuEthFrameDownDayPkt128To255Octets
					Counter64,
				sleGponOnuPMStatsSumOnuEthFrameDownDayPkt256To511Octets
					Counter64,
				sleGponOnuPMStatsSumOnuEthFrameDownDayPkt512To1023Octets
					Counter64,
				sleGponOnuPMStatsSumOnuEthFrameDownDayPkt1024To1518Octets
					Counter64,
				sleGponOnuPMStatsSumOnuEthFrameDownTotalDropEvents
					Counter64,
				sleGponOnuPMStatsSumOnuEthFrameDownTotalOctets
					Counter64,
				sleGponOnuPMStatsSumOnuEthFrameDownTotalPackets
					Counter64,
				sleGponOnuPMStatsSumOnuEthFrameDownTotalBcastPackets
					Counter64,
				sleGponOnuPMStatsSumOnuEthFrameDownTotalMcastPackets
					Counter64,
				sleGponOnuPMStatsSumOnuEthFrameDownTotalUcastPackets
					Counter64,
				sleGponOnuPMStatsSumOnuEthFrameDownTotalCRCErroredPackets
					Counter64,
				sleGponOnuPMStatsSumOnuEthFrameDownTotalUndersizePackets
					Counter64,
				sleGponOnuPMStatsSumOnuEthFrameDownTotalOversizePackets
					Counter64,
				sleGponOnuPMStatsSumOnuEthFrameDownTotalPkt64Octets
					Counter64,
				sleGponOnuPMStatsSumOnuEthFrameDownTotalPkt65To127Octets
					Counter64,
				sleGponOnuPMStatsSumOnuEthFrameDownTotalPkt128To255Octets
					Counter64,
				sleGponOnuPMStatsSumOnuEthFrameDownTotalPkt256To511Octets
					Counter64,
				sleGponOnuPMStatsSumOnuEthFrameDownTotalPkt512To1023Octets
					Counter64,
				sleGponOnuPMStatsSumOnuEthFrameDownTotalPkt1024To1518Octets
					Counter64
			 }

--  1.3.6.1.4.1.6296.101.23.7.7.9.1.1
		sleGponOnuPMStatsSumOnuEthFrameDownPre15mDropEvents OBJECT-TYPE
			SYNTAX Counter64
			MAX-ACCESS read-only
			STATUS current
			DESCRIPTION
				"The pre 15 minute number of events in which packets were dropped due to lack of resources.
				"
			::= { sleGponOnuPMStatsSumOnuEthFrameDownEntry 1 }


--  1.3.6.1.4.1.6296.101.23.7.7.9.1.2
		sleGponOnuPMStatsSumOnuEthFrameDownPre15mOctets OBJECT-TYPE
			SYNTAX Counter64
			MAX-ACCESS read-only
			STATUS current
			DESCRIPTION
				"The pre 15 minute number of octets received"
			::= { sleGponOnuPMStatsSumOnuEthFrameDownEntry 2 }


--  1.3.6.1.4.1.6296.101.23.7.7.9.1.3
		sleGponOnuPMStatsSumOnuEthFrameDownPre15mPackets OBJECT-TYPE
			SYNTAX Counter64
			MAX-ACCESS read-only
			STATUS current
			DESCRIPTION
				"The pre 15 minute number of packets received,"
			::= { sleGponOnuPMStatsSumOnuEthFrameDownEntry 3 }


--  1.3.6.1.4.1.6296.101.23.7.7.9.1.4
		sleGponOnuPMStatsSumOnuEthFrameDownPre15mBcastPackets OBJECT-TYPE
			SYNTAX Counter64
			MAX-ACCESS read-only
			STATUS current
			DESCRIPTION
				"The pre 15 minute number of received good packets directed to the broadcast address"
			::= { sleGponOnuPMStatsSumOnuEthFrameDownEntry 4 }


--  1.3.6.1.4.1.6296.101.23.7.7.9.1.5
		sleGponOnuPMStatsSumOnuEthFrameDownPre15mMcastPackets OBJECT-TYPE
			SYNTAX Counter64
			MAX-ACCESS read-only
			STATUS current
			DESCRIPTION
				"The pre 15 minute number of received good packets directed to a multicast address."
			::= { sleGponOnuPMStatsSumOnuEthFrameDownEntry 5 }


--  1.3.6.1.4.1.6296.101.23.7.7.9.1.6
		sleGponOnuPMStatsSumOnuEthFrameDownPre15mUcastPackets OBJECT-TYPE
			SYNTAX Counter64
			MAX-ACCESS read-only
			STATUS current
			DESCRIPTION
				"The pre 15 minute number of received good packets directed to the unicast address"
			::= { sleGponOnuPMStatsSumOnuEthFrameDownEntry 6 }


--  1.3.6.1.4.1.6296.101.23.7.7.9.1.7
		sleGponOnuPMStatsSumOnuEthFrameDownPre15mCRCErroredPackets OBJECT-TYPE
			SYNTAX Counter64
			MAX-ACCESS read-only
			STATUS current
			DESCRIPTION
				"The pre 15 minute number of packets received that had a length"
			::= { sleGponOnuPMStatsSumOnuEthFrameDownEntry 7 }


--  1.3.6.1.4.1.6296.101.23.7.7.9.1.8
		sleGponOnuPMStatsSumOnuEthFrameDownPre15mUndersizePackets OBJECT-TYPE
			SYNTAX Counter64
			MAX-ACCESS read-only
			STATUS current
			DESCRIPTION
				"The pre 15 minute number of packets received that were less than 64 octets long"
			::= { sleGponOnuPMStatsSumOnuEthFrameDownEntry 8 }


--  1.3.6.1.4.1.6296.101.23.7.7.9.1.9
		sleGponOnuPMStatsSumOnuEthFrameDownPre15mOversizePackets OBJECT-TYPE
			SYNTAX Counter64
			MAX-ACCESS read-only
			STATUS current
			DESCRIPTION
				"The pre 15 minute number of packets received that were longer than 1518 octets"
			::= { sleGponOnuPMStatsSumOnuEthFrameDownEntry 9 }


--  1.3.6.1.4.1.6296.101.23.7.7.9.1.10
		sleGponOnuPMStatsSumOnuEthFrameDownPre15mPkt64Octets OBJECT-TYPE
			SYNTAX Counter64
			MAX-ACCESS read-only
			STATUS current
			DESCRIPTION
				"The pre 15 minute number of received packets (including bad packets) that were
				64 octets long,"
			::= { sleGponOnuPMStatsSumOnuEthFrameDownEntry 10 }


--  1.3.6.1.4.1.6296.101.23.7.7.9.1.11
		sleGponOnuPMStatsSumOnuEthFrameDownPre15mPkt65To127Octets OBJECT-TYPE
			SYNTAX Counter64
			MAX-ACCESS read-only
			STATUS current
			DESCRIPTION
				"The pre 15 minute number of received packets (including bad packets) that were
				65..127 octets long,"
			::= { sleGponOnuPMStatsSumOnuEthFrameDownEntry 11 }


--  1.3.6.1.4.1.6296.101.23.7.7.9.1.12
		sleGponOnuPMStatsSumOnuEthFrameDownPre15mPkt128To255Octets OBJECT-TYPE
			SYNTAX Counter64
			MAX-ACCESS read-only
			STATUS current
			DESCRIPTION
				"The pre 15 minute number of packets (including bad packets) received that were
				128..255 octets long,"
			::= { sleGponOnuPMStatsSumOnuEthFrameDownEntry 12 }


--  1.3.6.1.4.1.6296.101.23.7.7.9.1.13
		sleGponOnuPMStatsSumOnuEthFrameDownPre15mPkt256To511Octets OBJECT-TYPE
			SYNTAX Counter64
			MAX-ACCESS read-only
			STATUS current
			DESCRIPTION
				"The pre 15 minute number of packets (including bad packets) received that were
				256..511 octets long,"
			::= { sleGponOnuPMStatsSumOnuEthFrameDownEntry 13 }


--  1.3.6.1.4.1.6296.101.23.7.7.9.1.14
		sleGponOnuPMStatsSumOnuEthFrameDownPre15mPkt512To1023Octets OBJECT-TYPE
			SYNTAX Counter64
			MAX-ACCESS read-only
			STATUS current
			DESCRIPTION
				"The pre 15 minute number of packets (including bad packets) received that were
				512..1023 octets long."
			::= { sleGponOnuPMStatsSumOnuEthFrameDownEntry 14 }


--  1.3.6.1.4.1.6296.101.23.7.7.9.1.15
		sleGponOnuPMStatsSumOnuEthFrameDownPre15mPkt1024To1518Octets OBJECT-TYPE
			SYNTAX Counter64
			MAX-ACCESS read-only
			STATUS current
			DESCRIPTION
				"The pre 15 minute number of packets (including bad packets) received that were
				1024..1518 octets long,"
			::= { sleGponOnuPMStatsSumOnuEthFrameDownEntry 15 }


--  1.3.6.1.4.1.6296.101.23.7.7.9.1.16
		sleGponOnuPMStatsSumOnuEthFrameDownHourDropEvents OBJECT-TYPE
			SYNTAX Counter64
			MAX-ACCESS read-only
			STATUS current
			DESCRIPTION
				"The hour number of events in which packets were dropped due to lack
				of resources."
			::= { sleGponOnuPMStatsSumOnuEthFrameDownEntry 16 }


--  1.3.6.1.4.1.6296.101.23.7.7.9.1.17
		sleGponOnuPMStatsSumOnuEthFrameDownHourOctets OBJECT-TYPE
			SYNTAX Counter64
			MAX-ACCESS read-only
			STATUS current
			DESCRIPTION
				"The hour number of octets received"
			::= { sleGponOnuPMStatsSumOnuEthFrameDownEntry 17 }


--  1.3.6.1.4.1.6296.101.23.7.7.9.1.18
		sleGponOnuPMStatsSumOnuEthFrameDownHourPackets OBJECT-TYPE
			SYNTAX Counter64
			MAX-ACCESS read-only
			STATUS current
			DESCRIPTION
				"The hour number of packets received,"
			::= { sleGponOnuPMStatsSumOnuEthFrameDownEntry 18 }


--  1.3.6.1.4.1.6296.101.23.7.7.9.1.19
		sleGponOnuPMStatsSumOnuEthFrameDownHourBcastPackets OBJECT-TYPE
			SYNTAX Counter64
			MAX-ACCESS read-write
			STATUS current
			DESCRIPTION
				"The hour number of received good packets directed to the broadcast address"
			::= { sleGponOnuPMStatsSumOnuEthFrameDownEntry 19 }


--  1.3.6.1.4.1.6296.101.23.7.7.9.1.20
		sleGponOnuPMStatsSumOnuEthFrameDownHourMcastPackets OBJECT-TYPE
			SYNTAX Counter64
			MAX-ACCESS read-only
			STATUS current
			DESCRIPTION
				"The hour number of received good packets directed to a multicast address."
			::= { sleGponOnuPMStatsSumOnuEthFrameDownEntry 20 }


--  1.3.6.1.4.1.6296.101.23.7.7.9.1.21
		sleGponOnuPMStatsSumOnuEthFrameDownHourUcastPackets OBJECT-TYPE
			SYNTAX Counter64
			MAX-ACCESS read-only
			STATUS current
			DESCRIPTION
				"The hour number of received good packets directed to the unicast address"
			::= { sleGponOnuPMStatsSumOnuEthFrameDownEntry 21 }


--  1.3.6.1.4.1.6296.101.23.7.7.9.1.22
		sleGponOnuPMStatsSumOnuEthFrameDownHourCRCErroredPackets OBJECT-TYPE
			SYNTAX Counter64
			MAX-ACCESS read-only
			STATUS current
			DESCRIPTION
				"The hour number of packets received that had a length"
			::= { sleGponOnuPMStatsSumOnuEthFrameDownEntry 22 }


--  1.3.6.1.4.1.6296.101.23.7.7.9.1.23
		sleGponOnuPMStatsSumOnuEthFrameDownHourUndersizePackets OBJECT-TYPE
			SYNTAX Counter64
			MAX-ACCESS read-only
			STATUS current
			DESCRIPTION
				"The hour number of packets received that were less than 64 octets long"
			::= { sleGponOnuPMStatsSumOnuEthFrameDownEntry 23 }


--  1.3.6.1.4.1.6296.101.23.7.7.9.1.24
		sleGponOnuPMStatsSumOnuEthFrameDownHourOversizePackets OBJECT-TYPE
			SYNTAX Counter64
			MAX-ACCESS read-only
			STATUS current
			DESCRIPTION
				"The hour number of received packets (including bad packets) that were
				64 octets long,
				"
			::= { sleGponOnuPMStatsSumOnuEthFrameDownEntry 24 }


--  1.3.6.1.4.1.6296.101.23.7.7.9.1.25
		sleGponOnuPMStatsSumOnuEthFrameDownHourPkt64Octets OBJECT-TYPE
			SYNTAX Counter64
			MAX-ACCESS read-only
			STATUS current
			DESCRIPTION
				"The hour number of received packets (including bad packets) that were
				64 octets long,
				"
			::= { sleGponOnuPMStatsSumOnuEthFrameDownEntry 25 }


--  1.3.6.1.4.1.6296.101.23.7.7.9.1.26
		sleGponOnuPMStatsSumOnuEthFrameDownHourPkt65To127Octets OBJECT-TYPE
			SYNTAX Counter64
			MAX-ACCESS read-only
			STATUS current
			DESCRIPTION
				"The hour number of received packets (including bad packets) that were
				65..127 octets long,"
			::= { sleGponOnuPMStatsSumOnuEthFrameDownEntry 26 }


--  1.3.6.1.4.1.6296.101.23.7.7.9.1.27
		sleGponOnuPMStatsSumOnuEthFrameDownHourPkt128To255Octets OBJECT-TYPE
			SYNTAX Counter64
			MAX-ACCESS read-write
			STATUS current
			DESCRIPTION
				"The hour number of packets (including bad packets) received that were
				128..255 octets long,"
			::= { sleGponOnuPMStatsSumOnuEthFrameDownEntry 27 }


--  1.3.6.1.4.1.6296.101.23.7.7.9.1.28
		sleGponOnuPMStatsSumOnuEthFrameDownHourPkt256To511Octets OBJECT-TYPE
			SYNTAX Counter64
			MAX-ACCESS read-only
			STATUS current
			DESCRIPTION
				"The hour number of packets (including bad packets) received that were
				256..511 octets long,"
			::= { sleGponOnuPMStatsSumOnuEthFrameDownEntry 28 }


--  1.3.6.1.4.1.6296.101.23.7.7.9.1.29
		sleGponOnuPMStatsSumOnuEthFrameDownHourPkt512To1023Octets OBJECT-TYPE
			SYNTAX Counter64
			MAX-ACCESS read-write
			STATUS current
			DESCRIPTION
				"The hour number of packets (including bad packets) received that were
				512..1023 octets long,
				"
			::= { sleGponOnuPMStatsSumOnuEthFrameDownEntry 29 }


--  1.3.6.1.4.1.6296.101.23.7.7.9.1.30
		sleGponOnuPMStatsSumOnuEthFrameDownHourPkt1024To1518Octets OBJECT-TYPE
			SYNTAX Counter64
			MAX-ACCESS read-only
			STATUS current
			DESCRIPTION
				"The hour number of packets (including bad packets) received that were
				1024..1518 octets long,
				"
			::= { sleGponOnuPMStatsSumOnuEthFrameDownEntry 30 }


--  1.3.6.1.4.1.6296.101.23.7.7.9.1.31
		sleGponOnuPMStatsSumOnuEthFrameDownDayDropEvents OBJECT-TYPE
			SYNTAX Counter64
			MAX-ACCESS read-only
			STATUS current
			DESCRIPTION
				"The day number of events in which packets were dropped due to lack of resources.
				"
			::= { sleGponOnuPMStatsSumOnuEthFrameDownEntry 31 }


--  1.3.6.1.4.1.6296.101.23.7.7.9.1.32
		sleGponOnuPMStatsSumOnuEthFrameDownDayOctets OBJECT-TYPE
			SYNTAX Counter64
			MAX-ACCESS read-only
			STATUS current
			DESCRIPTION
				"The day number of octets received"
			::= { sleGponOnuPMStatsSumOnuEthFrameDownEntry 32 }


--  1.3.6.1.4.1.6296.101.23.7.7.9.1.33
		sleGponOnuPMStatsSumOnuEthFrameDownDayPackets OBJECT-TYPE
			SYNTAX Counter64
			MAX-ACCESS read-only
			STATUS current
			DESCRIPTION
				"The day number of packets received,"
			::= { sleGponOnuPMStatsSumOnuEthFrameDownEntry 33 }


--  1.3.6.1.4.1.6296.101.23.7.7.9.1.34
		sleGponOnuPMStatsSumOnuEthFrameDownDayBcastPackets OBJECT-TYPE
			SYNTAX Counter64
			MAX-ACCESS read-write
			STATUS current
			DESCRIPTION
				"The day number of received good packets directed to a broadcast address."
			::= { sleGponOnuPMStatsSumOnuEthFrameDownEntry 34 }


--  1.3.6.1.4.1.6296.101.23.7.7.9.1.35
		sleGponOnuPMStatsSumOnuEthFrameDownDayMcastPackets OBJECT-TYPE
			SYNTAX Counter64
			MAX-ACCESS read-only
			STATUS current
			DESCRIPTION
				"The day number of received good packets directed to a multicast address."
			::= { sleGponOnuPMStatsSumOnuEthFrameDownEntry 35 }


--  1.3.6.1.4.1.6296.101.23.7.7.9.1.36
		sleGponOnuPMStatsSumOnuEthFrameDownDayUcastPackets OBJECT-TYPE
			SYNTAX Counter64
			MAX-ACCESS read-only
			STATUS current
			DESCRIPTION
				"The day number of received good packets directed to the unicast address"
			::= { sleGponOnuPMStatsSumOnuEthFrameDownEntry 36 }


--  1.3.6.1.4.1.6296.101.23.7.7.9.1.37
		sleGponOnuPMStatsSumOnuEthFrameDownDayCRCErroredPackets OBJECT-TYPE
			SYNTAX Counter64
			MAX-ACCESS read-only
			STATUS current
			DESCRIPTION
				"The day number of packets received that had a length"
			::= { sleGponOnuPMStatsSumOnuEthFrameDownEntry 37 }


--  1.3.6.1.4.1.6296.101.23.7.7.9.1.38
		sleGponOnuPMStatsSumOnuEthFrameDownDayUndersizePackets OBJECT-TYPE
			SYNTAX Counter64
			MAX-ACCESS read-only
			STATUS current
			DESCRIPTION
				"The day number of packets received that were less than 64 octets long"
			::= { sleGponOnuPMStatsSumOnuEthFrameDownEntry 38 }


--  1.3.6.1.4.1.6296.101.23.7.7.9.1.39
		sleGponOnuPMStatsSumOnuEthFrameDownDayOversizePackets OBJECT-TYPE
			SYNTAX Counter64
			MAX-ACCESS read-only
			STATUS current
			DESCRIPTION
				"The day number of packets received that were longer than 1518 octets"
			::= { sleGponOnuPMStatsSumOnuEthFrameDownEntry 39 }


--  1.3.6.1.4.1.6296.101.23.7.7.9.1.40
		sleGponOnuPMStatsSumOnuEthFrameDownDayPkt64Octets OBJECT-TYPE
			SYNTAX Counter64
			MAX-ACCESS read-only
			STATUS current
			DESCRIPTION
				"The day number of received packets (including bad packets) that were
				64 octets long,"
			::= { sleGponOnuPMStatsSumOnuEthFrameDownEntry 40 }


--  1.3.6.1.4.1.6296.101.23.7.7.9.1.41
		sleGponOnuPMStatsSumOnuEthFrameDownDayPkt65To127Octets OBJECT-TYPE
			SYNTAX Counter64
			MAX-ACCESS read-only
			STATUS current
			DESCRIPTION
				"The day number of received packets (including bad packets) that were
				65..127 octets long,"
			::= { sleGponOnuPMStatsSumOnuEthFrameDownEntry 41 }


--  1.3.6.1.4.1.6296.101.23.7.7.9.1.42
		sleGponOnuPMStatsSumOnuEthFrameDownDayPkt128To255Octets OBJECT-TYPE
			SYNTAX Counter64
			MAX-ACCESS read-write
			STATUS current
			DESCRIPTION
				"The day number of received packets (including bad packets) that were
				128..255 octets long,
				"
			::= { sleGponOnuPMStatsSumOnuEthFrameDownEntry 42 }


--  1.3.6.1.4.1.6296.101.23.7.7.9.1.43
		sleGponOnuPMStatsSumOnuEthFrameDownDayPkt256To511Octets OBJECT-TYPE
			SYNTAX Counter64
			MAX-ACCESS read-only
			STATUS current
			DESCRIPTION
				"The day number of packets (including bad packets) received that were
				256..511 octets long,"
			::= { sleGponOnuPMStatsSumOnuEthFrameDownEntry 43 }


--  1.3.6.1.4.1.6296.101.23.7.7.9.1.44
		sleGponOnuPMStatsSumOnuEthFrameDownDayPkt512To1023Octets OBJECT-TYPE
			SYNTAX Counter64
			MAX-ACCESS read-write
			STATUS current
			DESCRIPTION
				"The day number of packets (including bad packets) received that were
				512..1023 octets long,"
			::= { sleGponOnuPMStatsSumOnuEthFrameDownEntry 44 }


--  1.3.6.1.4.1.6296.101.23.7.7.9.1.45
		sleGponOnuPMStatsSumOnuEthFrameDownDayPkt1024To1518Octets OBJECT-TYPE
			SYNTAX Counter64
			MAX-ACCESS read-only
			STATUS current
			DESCRIPTION
				"The day number of packets (including bad packets) received that were
				1024..1518 octets long,"
			::= { sleGponOnuPMStatsSumOnuEthFrameDownEntry 45 }


--  1.3.6.1.4.1.6296.101.23.7.7.9.1.46
		sleGponOnuPMStatsSumOnuEthFrameDownTotalDropEvents OBJECT-TYPE
			SYNTAX Counter64
			MAX-ACCESS read-only
			STATUS current
			DESCRIPTION
				"The total number of events in which packets were dropped due to lack of resources."
			::= { sleGponOnuPMStatsSumOnuEthFrameDownEntry 46 }


--  1.3.6.1.4.1.6296.101.23.7.7.9.1.47
		sleGponOnuPMStatsSumOnuEthFrameDownTotalOctets OBJECT-TYPE
			SYNTAX Counter64
			MAX-ACCESS read-only
			STATUS current
			DESCRIPTION
				"The total number of octets received"
			::= { sleGponOnuPMStatsSumOnuEthFrameDownEntry 47 }


--  1.3.6.1.4.1.6296.101.23.7.7.9.1.48
		sleGponOnuPMStatsSumOnuEthFrameDownTotalPackets OBJECT-TYPE
			SYNTAX Counter64
			MAX-ACCESS read-only
			STATUS current
			DESCRIPTION
				"The total number of packets received,"
			::= { sleGponOnuPMStatsSumOnuEthFrameDownEntry 48 }


--  1.3.6.1.4.1.6296.101.23.7.7.9.1.49
		sleGponOnuPMStatsSumOnuEthFrameDownTotalBcastPackets OBJECT-TYPE
			SYNTAX Counter64
			MAX-ACCESS read-write
			STATUS current
			DESCRIPTION
				"The total number of received good packets directed to a broadcast address."
			::= { sleGponOnuPMStatsSumOnuEthFrameDownEntry 49 }


--  1.3.6.1.4.1.6296.101.23.7.7.9.1.50
		sleGponOnuPMStatsSumOnuEthFrameDownTotalMcastPackets OBJECT-TYPE
			SYNTAX Counter64
			MAX-ACCESS read-only
			STATUS current
			DESCRIPTION
				"The total number of received good packets directed to a multicast address."
			::= { sleGponOnuPMStatsSumOnuEthFrameDownEntry 50 }


--  1.3.6.1.4.1.6296.101.23.7.7.9.1.51
		sleGponOnuPMStatsSumOnuEthFrameDownTotalUcastPackets OBJECT-TYPE
			SYNTAX Counter64
			MAX-ACCESS read-only
			STATUS current
			DESCRIPTION
				"The total number of received good packets directed to the unicast address"
			::= { sleGponOnuPMStatsSumOnuEthFrameDownEntry 51 }


--  1.3.6.1.4.1.6296.101.23.7.7.9.1.52
		sleGponOnuPMStatsSumOnuEthFrameDownTotalCRCErroredPackets OBJECT-TYPE
			SYNTAX Counter64
			MAX-ACCESS read-only
			STATUS current
			DESCRIPTION
				"Description."
			::= { sleGponOnuPMStatsSumOnuEthFrameDownEntry 52 }


--  1.3.6.1.4.1.6296.101.23.7.7.9.1.53
		sleGponOnuPMStatsSumOnuEthFrameDownTotalUndersizePackets OBJECT-TYPE
			SYNTAX Counter64
			MAX-ACCESS read-only
			STATUS current
			DESCRIPTION
				"The total number of packets received that were less than 64 octets long"
			::= { sleGponOnuPMStatsSumOnuEthFrameDownEntry 53 }


--  1.3.6.1.4.1.6296.101.23.7.7.9.1.54
		sleGponOnuPMStatsSumOnuEthFrameDownTotalOversizePackets OBJECT-TYPE
			SYNTAX Counter64
			MAX-ACCESS read-only
			STATUS current
			DESCRIPTION
				"The total number of packets received that were longer than 1518 octets"
			::= { sleGponOnuPMStatsSumOnuEthFrameDownEntry 54 }


--  1.3.6.1.4.1.6296.101.23.7.7.9.1.55
		sleGponOnuPMStatsSumOnuEthFrameDownTotalPkt64Octets OBJECT-TYPE
			SYNTAX Counter64
			MAX-ACCESS read-only
			STATUS current
			DESCRIPTION
				"The total number of received packets (including bad packets) that were
				64 octets long,"
			::= { sleGponOnuPMStatsSumOnuEthFrameDownEntry 55 }


--  1.3.6.1.4.1.6296.101.23.7.7.9.1.56
		sleGponOnuPMStatsSumOnuEthFrameDownTotalPkt65To127Octets OBJECT-TYPE
			SYNTAX Counter64
			MAX-ACCESS read-only
			STATUS current
			DESCRIPTION
				"The total number of received packets (including bad packets) that were
				65..127 octets long,"
			::= { sleGponOnuPMStatsSumOnuEthFrameDownEntry 56 }


--  1.3.6.1.4.1.6296.101.23.7.7.9.1.57
		sleGponOnuPMStatsSumOnuEthFrameDownTotalPkt128To255Octets OBJECT-TYPE
			SYNTAX Counter64
			MAX-ACCESS read-write
			STATUS current
			DESCRIPTION
				"The total number of packets (including bad packets) received that were
				128..255 octets long,"
			::= { sleGponOnuPMStatsSumOnuEthFrameDownEntry 57 }


--  1.3.6.1.4.1.6296.101.23.7.7.9.1.58
		sleGponOnuPMStatsSumOnuEthFrameDownTotalPkt256To511Octets OBJECT-TYPE
			SYNTAX Counter64
			MAX-ACCESS read-only
			STATUS current
			DESCRIPTION
				"The total number of packets (including bad packets) received that were
				256..511 octets long,"
			::= { sleGponOnuPMStatsSumOnuEthFrameDownEntry 58 }


--  1.3.6.1.4.1.6296.101.23.7.7.9.1.59
		sleGponOnuPMStatsSumOnuEthFrameDownTotalPkt512To1023Octets OBJECT-TYPE
			SYNTAX Counter64
			MAX-ACCESS read-write
			STATUS current
			DESCRIPTION
				"The total number of packets (including bad packets) received that were
				512..1023 octets long,"
			::= { sleGponOnuPMStatsSumOnuEthFrameDownEntry 59 }


--  1.3.6.1.4.1.6296.101.23.7.7.9.1.60
		sleGponOnuPMStatsSumOnuEthFrameDownTotalPkt1024To1518Octets OBJECT-TYPE
			SYNTAX Counter64
			MAX-ACCESS read-only
			STATUS current
			DESCRIPTION
				"The total number of packets (including bad packets) received that were
				1024..1518 octets long,"
			::= { sleGponOnuPMStatsSumOnuEthFrameDownEntry 60 }


--  1.3.6.1.4.1.6296.101.23.7.7.10
		sleGponOnuPMStatsSumOnuUniEth3Table OBJECT-TYPE
			SYNTAX SEQUENCE OF SleGponOnuPMStatsSumOnuUniEth3Entry
			MAX-ACCESS not-accessible
			STATUS current
			DESCRIPTION
				"sleGponOnuPMStatsDetailUniEth3Table"
			::= { sleGponOnuPMStatatisticsSum 10 }


--  1.3.6.1.4.1.6296.101.23.7.7.10.1
		sleGponOnuPMStatsSumOnuUniEth3Entry OBJECT-TYPE
			SYNTAX SleGponOnuPMStatsSumOnuUniEth3Entry
			MAX-ACCESS not-accessible
			STATUS current
			DESCRIPTION
				"key: sleGponOltId, sleGponOnuId, sleGponOnuPMStatsDetailUniEthFrameUpUniPort"
			INDEX { sleGponOltId, sleGponOnuId }
			::= { sleGponOnuPMStatsSumOnuUniEth3Table 1 }


		SleGponOnuPMStatsSumOnuUniEth3Entry ::=
			SEQUENCE {
				sleGponOnuPMStatsSumOnuUniEth3Pre15mDropEvents
					Counter64,
				sleGponOnuPMStatsSumOnuUniEth3Pre15mOctets
					Counter64,
				sleGponOnuPMStatsSumOnuUniEth3Pre15mPackets
					Counter64,
				sleGponOnuPMStatsSumOnuUniEth3Pre15mBcastPackets
					Counter64,
				sleGponOnuPMStatsSumOnuUniEth3Pre15mMcastPackets
					Counter64,
				sleGponOnuPMStatsSumOnuUniEth3Pre15mUcastPackets
					Counter64,
				sleGponOnuPMStatsSumOnuUniEth3Pre15mUndersizePackets
					Counter64,
				sleGponOnuPMStatsSumOnuUniEth3Pre15mFragments
					Counter64,
				sleGponOnuPMStatsSumOnuUniEth3Pre15mJabbers
					Counter64,
				sleGponOnuPMStatsSumOnuUniEth3Pre15mPkt64Octets
					Counter64,
				sleGponOnuPMStatsSumOnuUniEth3Pre15mPkt65To127Octets
					Counter64,
				sleGponOnuPMStatsSumOnuUniEth3Pre15mPkt128To255Octets
					Counter64,
				sleGponOnuPMStatsSumOnuUniEth3Pre15mPkt256To511Octets
					Counter64,
				sleGponOnuPMStatsSumOnuUniEth3Pre15mPkt512To1023Octets
					Counter64,
				sleGponOnuPMStatsSumOnuUniEth3Pre15mPkt1024To1518Octets
					Counter64,
				sleGponOnuPMStatsSumOnuUniEth3HourDropEvents
					Counter64,
				sleGponOnuPMStatsSumOnuUniEth3HourOctets
					Counter64,
				sleGponOnuPMStatsSumOnuUniEth3HourPackets
					Counter64,
				sleGponOnuPMStatsSumOnuUniEth3HourBcastPackets
					Counter64,
				sleGponOnuPMStatsSumOnuUniEth3HourMcastPackets
					Counter64,
				sleGponOnuPMStatsSumOnuUniEth3HourUcastPackets
					Counter64,
				sleGponOnuPMStatsSumOnuUniEth3HourUndersizePackets
					Counter64,
				sleGponOnuPMStatsSumOnuUniEth3HourFragments
					Counter64,
				sleGponOnuPMStatsSumOnuUniEth3HourJabbers
					Counter64,
				sleGponOnuPMStatsSumOnuUniEth3HourPkt64Octets
					Counter64,
				sleGponOnuPMStatsSumOnuUniEth3HourPkt65To127Octets
					Counter64,
				sleGponOnuPMStatsSumOnuUniEth3HourPkt128To255Octets
					Counter64,
				sleGponOnuPMStatsSumOnuUniEth3HourPkt256To511Octets
					Counter64,
				sleGponOnuPMStatsSumOnuUniEth3HourPkt512To1023Octets
					Counter64,
				sleGponOnuPMStatsSumOnuUniEth3HourPkt1024To1518Octets
					Counter64,
				sleGponOnuPMStatsSumOnuUniEth3DayDropEvents
					Counter64,
				sleGponOnuPMStatsSumOnuUniEth3DayOctets
					Counter64,
				sleGponOnuPMStatsSumOnuUniEth3DayPackets
					Counter64,
				sleGponOnuPMStatsSumOnuUniEth3DayBcastPackets
					Counter64,
				sleGponOnuPMStatsSumOnuUniEth3DayMcastPackets
					Counter64,
				sleGponOnuPMStatsSumOnuUniEth3DayUcastPackets
					Counter64,
				sleGponOnuPMStatsSumOnuUniEth3DayUndersizePackets
					Counter64,
				sleGponOnuPMStatsSumOnuUniEth3DayFragments
					Counter64,
				sleGponOnuPMStatsSumOnuUniEth3DayJabbers
					Counter64,
				sleGponOnuPMStatsSumOnuUniEth3DayPkt64Octets
					Counter64,
				sleGponOnuPMStatsSumOnuUniEth3DayPkt65To127Octets
					Counter64,
				sleGponOnuPMStatsSumOnuUniEth3DayPkt128To255Octets
					Counter64,
				sleGponOnuPMStatsSumOnuUniEth3DayPkt256To511Octets
					Counter64,
				sleGponOnuPMStatsSumOnuUniEth3DayPkt512To1023Octets
					Counter64,
				sleGponOnuPMStatsSumOnuUniEth3DayPkt1024To1518Octets
					Counter64,
				sleGponOnuPMStatsSumOnuUniEth3TotalDropEvents
					Counter64,
				sleGponOnuPMStatsSumOnuUniEth3TotalOctets
					Counter64,
				sleGponOnuPMStatsSumOnuUniEth3TotalPackets
					Counter64,
				sleGponOnuPMStatsSumOnuUniEth3TotalBcastPackets
					Counter64,
				sleGponOnuPMStatsSumOnuUniEth3TotalMcastPackets
					Counter64,
				sleGponOnuPMStatsSumOnuUniEth3TotalUcastPackets
					Counter64,
				sleGponOnuPMStatsSumOnuUniEth3TotalUndersizePackets
					Counter64,
				sleGponOnuPMStatsSumOnuUniEth3TotalFragments
					Counter64,
				sleGponOnuPMStatsSumOnuUniEth3TotalJabbers
					Counter64,
				sleGponOnuPMStatsSumOnuUniEth3TotalPkt64Octets
					Counter64,
				sleGponOnuPMStatsSumOnuUniEth3TotalPkt65To127Octets
					Counter64,
				sleGponOnuPMStatsSumOnuUniEth3TotalPkt128To255Octets
					Counter64,
				sleGponOnuPMStatsSumOnuUniEth3TotalPkt256To511Octets
					Counter64,
				sleGponOnuPMStatsSumOnuUniEth3TotalPkt512To1023Octets
					Counter64,
				sleGponOnuPMStatsSumOnuUniEth3TotalPkt1024To1518Octets
					Counter64
			 }

--  1.3.6.1.4.1.6296.101.23.7.7.10.1.1
		sleGponOnuPMStatsSumOnuUniEth3Pre15mDropEvents OBJECT-TYPE
			SYNTAX Counter64
			MAX-ACCESS read-only
			STATUS current
			DESCRIPTION
				"The pre 15 minute number of events in which packets were dropped due to lack of resources."
			::= { sleGponOnuPMStatsSumOnuUniEth3Entry 1 }


--  1.3.6.1.4.1.6296.101.23.7.7.10.1.2
		sleGponOnuPMStatsSumOnuUniEth3Pre15mOctets OBJECT-TYPE
			SYNTAX Counter64
			MAX-ACCESS read-only
			STATUS current
			DESCRIPTION
				"The pre 15 minute number of octets received"
			::= { sleGponOnuPMStatsSumOnuUniEth3Entry 2 }


--  1.3.6.1.4.1.6296.101.23.7.7.10.1.3
		sleGponOnuPMStatsSumOnuUniEth3Pre15mPackets OBJECT-TYPE
			SYNTAX Counter64
			MAX-ACCESS read-only
			STATUS current
			DESCRIPTION
				"The pre 15 minute number of packets received, including bad packets"
			::= { sleGponOnuPMStatsSumOnuUniEth3Entry 3 }


--  1.3.6.1.4.1.6296.101.23.7.7.10.1.4
		sleGponOnuPMStatsSumOnuUniEth3Pre15mBcastPackets OBJECT-TYPE
			SYNTAX Counter64
			MAX-ACCESS read-only
			STATUS current
			DESCRIPTION
				"The pre 15 minute number of received good packets directed to the broadcast address."
			::= { sleGponOnuPMStatsSumOnuUniEth3Entry 4 }


--  1.3.6.1.4.1.6296.101.23.7.7.10.1.5
		sleGponOnuPMStatsSumOnuUniEth3Pre15mMcastPackets OBJECT-TYPE
			SYNTAX Counter64
			MAX-ACCESS read-only
			STATUS current
			DESCRIPTION
				"The pre 15 minute number of received good packets directed to a multicast address."
			::= { sleGponOnuPMStatsSumOnuUniEth3Entry 5 }


--  1.3.6.1.4.1.6296.101.23.7.7.10.1.6
		sleGponOnuPMStatsSumOnuUniEth3Pre15mUcastPackets OBJECT-TYPE
			SYNTAX Counter64
			MAX-ACCESS read-only
			STATUS current
			DESCRIPTION
				"The pre 15 minute number of received good packets directed to a unicast address."
			::= { sleGponOnuPMStatsSumOnuUniEth3Entry 6 }


--  1.3.6.1.4.1.6296.101.23.7.7.10.1.7
		sleGponOnuPMStatsSumOnuUniEth3Pre15mUndersizePackets OBJECT-TYPE
			SYNTAX Counter64
			MAX-ACCESS read-only
			STATUS current
			DESCRIPTION
				"The pre 15 minute number of packets received that were less than 64 octets long"
			::= { sleGponOnuPMStatsSumOnuUniEth3Entry 7 }


--  1.3.6.1.4.1.6296.101.23.7.7.10.1.8
		sleGponOnuPMStatsSumOnuUniEth3Pre15mFragments OBJECT-TYPE
			SYNTAX Counter64
			MAX-ACCESS read-only
			STATUS current
			DESCRIPTION
				"The pre 15 minute number of packets received that were fragments"
			::= { sleGponOnuPMStatsSumOnuUniEth3Entry 8 }


--  1.3.6.1.4.1.6296.101.23.7.7.10.1.9
		sleGponOnuPMStatsSumOnuUniEth3Pre15mJabbers OBJECT-TYPE
			SYNTAX Counter64
			MAX-ACCESS read-only
			STATUS current
			DESCRIPTION
				"The pre 15 minute number of packets received that were jabbers"
			::= { sleGponOnuPMStatsSumOnuUniEth3Entry 9 }


--  1.3.6.1.4.1.6296.101.23.7.7.10.1.10
		sleGponOnuPMStatsSumOnuUniEth3Pre15mPkt64Octets OBJECT-TYPE
			SYNTAX Counter64
			MAX-ACCESS read-only
			STATUS current
			DESCRIPTION
				"The pre 15 minute number of received packets (including bad packets) that were 64 octets long"
			::= { sleGponOnuPMStatsSumOnuUniEth3Entry 10 }


--  1.3.6.1.4.1.6296.101.23.7.7.10.1.11
		sleGponOnuPMStatsSumOnuUniEth3Pre15mPkt65To127Octets OBJECT-TYPE
			SYNTAX Counter64
			MAX-ACCESS read-only
			STATUS current
			DESCRIPTION
				"The pre 15 minute number of received packets (including bad packets) that were 65..127 octets long"
			::= { sleGponOnuPMStatsSumOnuUniEth3Entry 11 }


--  1.3.6.1.4.1.6296.101.23.7.7.10.1.12
		sleGponOnuPMStatsSumOnuUniEth3Pre15mPkt128To255Octets OBJECT-TYPE
			SYNTAX Counter64
			MAX-ACCESS read-only
			STATUS current
			DESCRIPTION
				"The pre 15 minute number of packets (including bad packets) received that were 128..255 octets long"
			::= { sleGponOnuPMStatsSumOnuUniEth3Entry 12 }


--  1.3.6.1.4.1.6296.101.23.7.7.10.1.13
		sleGponOnuPMStatsSumOnuUniEth3Pre15mPkt256To511Octets OBJECT-TYPE
			SYNTAX Counter64
			MAX-ACCESS read-only
			STATUS current
			DESCRIPTION
				"The pre 15 minute number of packets (including bad packets) received that were 256..511 octets long"
			::= { sleGponOnuPMStatsSumOnuUniEth3Entry 13 }


--  1.3.6.1.4.1.6296.101.23.7.7.10.1.14
		sleGponOnuPMStatsSumOnuUniEth3Pre15mPkt512To1023Octets OBJECT-TYPE
			SYNTAX Counter64
			MAX-ACCESS read-only
			STATUS current
			DESCRIPTION
				"The pre 15 minute number of packets (including bad packets) received that were 512..1023 octets long"
			::= { sleGponOnuPMStatsSumOnuUniEth3Entry 14 }


--  1.3.6.1.4.1.6296.101.23.7.7.10.1.15
		sleGponOnuPMStatsSumOnuUniEth3Pre15mPkt1024To1518Octets OBJECT-TYPE
			SYNTAX Counter64
			MAX-ACCESS read-only
			STATUS current
			DESCRIPTION
				"The pre 15 minute number of packets (including bad packets) received that were 1024..1518 octets long"
			::= { sleGponOnuPMStatsSumOnuUniEth3Entry 15 }


--  1.3.6.1.4.1.6296.101.23.7.7.10.1.16
		sleGponOnuPMStatsSumOnuUniEth3HourDropEvents OBJECT-TYPE
			SYNTAX Counter64
			MAX-ACCESS read-only
			STATUS current
			DESCRIPTION
				"The hour number of events in which packets were dropped due to lack of resources."
			::= { sleGponOnuPMStatsSumOnuUniEth3Entry 16 }


--  1.3.6.1.4.1.6296.101.23.7.7.10.1.17
		sleGponOnuPMStatsSumOnuUniEth3HourOctets OBJECT-TYPE
			SYNTAX Counter64
			MAX-ACCESS read-only
			STATUS current
			DESCRIPTION
				"The hour number of octets received"
			::= { sleGponOnuPMStatsSumOnuUniEth3Entry 17 }


--  1.3.6.1.4.1.6296.101.23.7.7.10.1.18
		sleGponOnuPMStatsSumOnuUniEth3HourPackets OBJECT-TYPE
			SYNTAX Counter64
			MAX-ACCESS read-only
			STATUS current
			DESCRIPTION
				"The hour number of packets received,"
			::= { sleGponOnuPMStatsSumOnuUniEth3Entry 18 }


--  1.3.6.1.4.1.6296.101.23.7.7.10.1.19
		sleGponOnuPMStatsSumOnuUniEth3HourBcastPackets OBJECT-TYPE
			SYNTAX Counter64
			MAX-ACCESS read-write
			STATUS current
			DESCRIPTION
				"The hour number of received good packets directed to the broadcast address"
			::= { sleGponOnuPMStatsSumOnuUniEth3Entry 19 }


--  1.3.6.1.4.1.6296.101.23.7.7.10.1.20
		sleGponOnuPMStatsSumOnuUniEth3HourMcastPackets OBJECT-TYPE
			SYNTAX Counter64
			MAX-ACCESS read-only
			STATUS current
			DESCRIPTION
				"The hour number of received good packets directed to a multicast address."
			::= { sleGponOnuPMStatsSumOnuUniEth3Entry 20 }


--  1.3.6.1.4.1.6296.101.23.7.7.10.1.21
		sleGponOnuPMStatsSumOnuUniEth3HourUcastPackets OBJECT-TYPE
			SYNTAX Counter64
			MAX-ACCESS read-only
			STATUS current
			DESCRIPTION
				"The hour number of received good packets directed to the unicast address"
			::= { sleGponOnuPMStatsSumOnuUniEth3Entry 21 }


--  1.3.6.1.4.1.6296.101.23.7.7.10.1.22
		sleGponOnuPMStatsSumOnuUniEth3HourUndersizePackets OBJECT-TYPE
			SYNTAX Counter64
			MAX-ACCESS read-only
			STATUS current
			DESCRIPTION
				"The hour number of packets received that were less than 64 octets long"
			::= { sleGponOnuPMStatsSumOnuUniEth3Entry 22 }


--  1.3.6.1.4.1.6296.101.23.7.7.10.1.23
		sleGponOnuPMStatsSumOnuUniEth3HourFragments OBJECT-TYPE
			SYNTAX Counter64
			MAX-ACCESS read-only
			STATUS current
			DESCRIPTION
				"The hour number of packets received that were fragments"
			::= { sleGponOnuPMStatsSumOnuUniEth3Entry 23 }


--  1.3.6.1.4.1.6296.101.23.7.7.10.1.24
		sleGponOnuPMStatsSumOnuUniEth3HourJabbers OBJECT-TYPE
			SYNTAX Counter64
			MAX-ACCESS read-only
			STATUS current
			DESCRIPTION
				"The hour number of packets received that were jabbers"
			::= { sleGponOnuPMStatsSumOnuUniEth3Entry 24 }


--  1.3.6.1.4.1.6296.101.23.7.7.10.1.25
		sleGponOnuPMStatsSumOnuUniEth3HourPkt64Octets OBJECT-TYPE
			SYNTAX Counter64
			MAX-ACCESS read-only
			STATUS current
			DESCRIPTION
				"The hour number of received packets (including bad packets) that were
				64 octets long,"
			::= { sleGponOnuPMStatsSumOnuUniEth3Entry 25 }


--  1.3.6.1.4.1.6296.101.23.7.7.10.1.26
		sleGponOnuPMStatsSumOnuUniEth3HourPkt65To127Octets OBJECT-TYPE
			SYNTAX Counter64
			MAX-ACCESS read-only
			STATUS current
			DESCRIPTION
				"The hour number of received packets (including bad packets) that were
				65..127 octets long,"
			::= { sleGponOnuPMStatsSumOnuUniEth3Entry 26 }


--  1.3.6.1.4.1.6296.101.23.7.7.10.1.27
		sleGponOnuPMStatsSumOnuUniEth3HourPkt128To255Octets OBJECT-TYPE
			SYNTAX Counter64
			MAX-ACCESS read-write
			STATUS current
			DESCRIPTION
				"The hour number of packets (including bad packets) received that were
				128..255 octets long,"
			::= { sleGponOnuPMStatsSumOnuUniEth3Entry 27 }


--  1.3.6.1.4.1.6296.101.23.7.7.10.1.28
		sleGponOnuPMStatsSumOnuUniEth3HourPkt256To511Octets OBJECT-TYPE
			SYNTAX Counter64
			MAX-ACCESS read-only
			STATUS current
			DESCRIPTION
				"The hour number of packets (including bad packets) received that were
				256..511 octets long,"
			::= { sleGponOnuPMStatsSumOnuUniEth3Entry 28 }


--  1.3.6.1.4.1.6296.101.23.7.7.10.1.29
		sleGponOnuPMStatsSumOnuUniEth3HourPkt512To1023Octets OBJECT-TYPE
			SYNTAX Counter64
			MAX-ACCESS read-write
			STATUS current
			DESCRIPTION
				"The hour number of packets (including bad packets) received that were
				512..1023 octets long,"
			::= { sleGponOnuPMStatsSumOnuUniEth3Entry 29 }


--  1.3.6.1.4.1.6296.101.23.7.7.10.1.30
		sleGponOnuPMStatsSumOnuUniEth3HourPkt1024To1518Octets OBJECT-TYPE
			SYNTAX Counter64
			MAX-ACCESS read-only
			STATUS current
			DESCRIPTION
				"The hour number of packets (including bad packets) received that were
				1024..1518 octets long,"
			::= { sleGponOnuPMStatsSumOnuUniEth3Entry 30 }


--  1.3.6.1.4.1.6296.101.23.7.7.10.1.31
		sleGponOnuPMStatsSumOnuUniEth3DayDropEvents OBJECT-TYPE
			SYNTAX Counter64
			MAX-ACCESS read-only
			STATUS current
			DESCRIPTION
				"The day number of events in which packets were dropped due to lack of resources."
			::= { sleGponOnuPMStatsSumOnuUniEth3Entry 31 }


--  1.3.6.1.4.1.6296.101.23.7.7.10.1.32
		sleGponOnuPMStatsSumOnuUniEth3DayOctets OBJECT-TYPE
			SYNTAX Counter64
			MAX-ACCESS read-only
			STATUS current
			DESCRIPTION
				"The day number of events in which packets were dropped due to lack of resources.
				"
			::= { sleGponOnuPMStatsSumOnuUniEth3Entry 32 }


--  1.3.6.1.4.1.6296.101.23.7.7.10.1.33
		sleGponOnuPMStatsSumOnuUniEth3DayPackets OBJECT-TYPE
			SYNTAX Counter64
			MAX-ACCESS read-only
			STATUS current
			DESCRIPTION
				"The day number of octets received"
			::= { sleGponOnuPMStatsSumOnuUniEth3Entry 33 }


--  1.3.6.1.4.1.6296.101.23.7.7.10.1.34
		sleGponOnuPMStatsSumOnuUniEth3DayBcastPackets OBJECT-TYPE
			SYNTAX Counter64
			MAX-ACCESS read-write
			STATUS current
			DESCRIPTION
				"The day number of received good packets directed to the broadcast address"
			::= { sleGponOnuPMStatsSumOnuUniEth3Entry 34 }


--  1.3.6.1.4.1.6296.101.23.7.7.10.1.35
		sleGponOnuPMStatsSumOnuUniEth3DayMcastPackets OBJECT-TYPE
			SYNTAX Counter64
			MAX-ACCESS read-only
			STATUS current
			DESCRIPTION
				"The day number of received good packets directed to a multicast address."
			::= { sleGponOnuPMStatsSumOnuUniEth3Entry 35 }


--  1.3.6.1.4.1.6296.101.23.7.7.10.1.36
		sleGponOnuPMStatsSumOnuUniEth3DayUcastPackets OBJECT-TYPE
			SYNTAX Counter64
			MAX-ACCESS read-only
			STATUS current
			DESCRIPTION
				"The day number of received good packets directed to the unicast address"
			::= { sleGponOnuPMStatsSumOnuUniEth3Entry 36 }


--  1.3.6.1.4.1.6296.101.23.7.7.10.1.37
		sleGponOnuPMStatsSumOnuUniEth3DayUndersizePackets OBJECT-TYPE
			SYNTAX Counter64
			MAX-ACCESS read-only
			STATUS current
			DESCRIPTION
				"The day number of packets received that were less than 64 octets long"
			::= { sleGponOnuPMStatsSumOnuUniEth3Entry 37 }


--  1.3.6.1.4.1.6296.101.23.7.7.10.1.38
		sleGponOnuPMStatsSumOnuUniEth3DayFragments OBJECT-TYPE
			SYNTAX Counter64
			MAX-ACCESS read-only
			STATUS current
			DESCRIPTION
				"The day number of packets received that were fragments"
			::= { sleGponOnuPMStatsSumOnuUniEth3Entry 38 }


--  1.3.6.1.4.1.6296.101.23.7.7.10.1.39
		sleGponOnuPMStatsSumOnuUniEth3DayJabbers OBJECT-TYPE
			SYNTAX Counter64
			MAX-ACCESS read-only
			STATUS current
			DESCRIPTION
				"The day number of packets received that were jabbers"
			::= { sleGponOnuPMStatsSumOnuUniEth3Entry 39 }


--  1.3.6.1.4.1.6296.101.23.7.7.10.1.40
		sleGponOnuPMStatsSumOnuUniEth3DayPkt64Octets OBJECT-TYPE
			SYNTAX Counter64
			MAX-ACCESS read-only
			STATUS current
			DESCRIPTION
				"The day number of received packets (including bad packets) that were
				64 octets long,"
			::= { sleGponOnuPMStatsSumOnuUniEth3Entry 40 }


--  1.3.6.1.4.1.6296.101.23.7.7.10.1.41
		sleGponOnuPMStatsSumOnuUniEth3DayPkt65To127Octets OBJECT-TYPE
			SYNTAX Counter64
			MAX-ACCESS read-only
			STATUS current
			DESCRIPTION
				"The day number of received packets (including bad packets) that were
				65..127 octets long,"
			::= { sleGponOnuPMStatsSumOnuUniEth3Entry 41 }


--  1.3.6.1.4.1.6296.101.23.7.7.10.1.42
		sleGponOnuPMStatsSumOnuUniEth3DayPkt128To255Octets OBJECT-TYPE
			SYNTAX Counter64
			MAX-ACCESS read-write
			STATUS current
			DESCRIPTION
				"The day number of received packets (including bad packets) that were
				128..255 octets long,"
			::= { sleGponOnuPMStatsSumOnuUniEth3Entry 42 }


--  1.3.6.1.4.1.6296.101.23.7.7.10.1.43
		sleGponOnuPMStatsSumOnuUniEth3DayPkt256To511Octets OBJECT-TYPE
			SYNTAX Counter64
			MAX-ACCESS read-only
			STATUS current
			DESCRIPTION
				"The day number of received packets (including bad packets) that were
				256..511 octets long,"
			::= { sleGponOnuPMStatsSumOnuUniEth3Entry 43 }


--  1.3.6.1.4.1.6296.101.23.7.7.10.1.44
		sleGponOnuPMStatsSumOnuUniEth3DayPkt512To1023Octets OBJECT-TYPE
			SYNTAX Counter64
			MAX-ACCESS read-write
			STATUS current
			DESCRIPTION
				"The day number of packets (including bad packets) received that were
				512..1023 octets long,"
			::= { sleGponOnuPMStatsSumOnuUniEth3Entry 44 }


--  1.3.6.1.4.1.6296.101.23.7.7.10.1.45
		sleGponOnuPMStatsSumOnuUniEth3DayPkt1024To1518Octets OBJECT-TYPE
			SYNTAX Counter64
			MAX-ACCESS read-only
			STATUS current
			DESCRIPTION
				"The day number of packets (including bad packets) received that were
				1024..1518 octets long,"
			::= { sleGponOnuPMStatsSumOnuUniEth3Entry 45 }


--  1.3.6.1.4.1.6296.101.23.7.7.10.1.46
		sleGponOnuPMStatsSumOnuUniEth3TotalDropEvents OBJECT-TYPE
			SYNTAX Counter64
			MAX-ACCESS read-only
			STATUS current
			DESCRIPTION
				"The total number of events in which packets were dropped due to lack
				of resources."
			::= { sleGponOnuPMStatsSumOnuUniEth3Entry 46 }


--  1.3.6.1.4.1.6296.101.23.7.7.10.1.47
		sleGponOnuPMStatsSumOnuUniEth3TotalOctets OBJECT-TYPE
			SYNTAX Counter64
			MAX-ACCESS read-only
			STATUS current
			DESCRIPTION
				"The total number of octets received"
			::= { sleGponOnuPMStatsSumOnuUniEth3Entry 47 }


--  1.3.6.1.4.1.6296.101.23.7.7.10.1.48
		sleGponOnuPMStatsSumOnuUniEth3TotalPackets OBJECT-TYPE
			SYNTAX Counter64
			MAX-ACCESS read-only
			STATUS current
			DESCRIPTION
				"The total number of packets received,"
			::= { sleGponOnuPMStatsSumOnuUniEth3Entry 48 }


--  1.3.6.1.4.1.6296.101.23.7.7.10.1.49
		sleGponOnuPMStatsSumOnuUniEth3TotalBcastPackets OBJECT-TYPE
			SYNTAX Counter64
			MAX-ACCESS read-write
			STATUS current
			DESCRIPTION
				"The total number of received good packets directed to the broadcast address"
			::= { sleGponOnuPMStatsSumOnuUniEth3Entry 49 }


--  1.3.6.1.4.1.6296.101.23.7.7.10.1.50
		sleGponOnuPMStatsSumOnuUniEth3TotalMcastPackets OBJECT-TYPE
			SYNTAX Counter64
			MAX-ACCESS read-only
			STATUS current
			DESCRIPTION
				"The total number of received good packets directed to a multicast address."
			::= { sleGponOnuPMStatsSumOnuUniEth3Entry 50 }


--  1.3.6.1.4.1.6296.101.23.7.7.10.1.51
		sleGponOnuPMStatsSumOnuUniEth3TotalUcastPackets OBJECT-TYPE
			SYNTAX Counter64
			MAX-ACCESS read-only
			STATUS current
			DESCRIPTION
				"The total number of received good packets directed to the unicast address"
			::= { sleGponOnuPMStatsSumOnuUniEth3Entry 51 }


--  1.3.6.1.4.1.6296.101.23.7.7.10.1.52
		sleGponOnuPMStatsSumOnuUniEth3TotalUndersizePackets OBJECT-TYPE
			SYNTAX Counter64
			MAX-ACCESS read-only
			STATUS current
			DESCRIPTION
				"The total number of packets received that were less than 64 octets long"
			::= { sleGponOnuPMStatsSumOnuUniEth3Entry 52 }


--  1.3.6.1.4.1.6296.101.23.7.7.10.1.53
		sleGponOnuPMStatsSumOnuUniEth3TotalFragments OBJECT-TYPE
			SYNTAX Counter64
			MAX-ACCESS read-only
			STATUS current
			DESCRIPTION
				"The total number of packets received
				(fragments)"
			::= { sleGponOnuPMStatsSumOnuUniEth3Entry 53 }


--  1.3.6.1.4.1.6296.101.23.7.7.10.1.54
		sleGponOnuPMStatsSumOnuUniEth3TotalJabbers OBJECT-TYPE
			SYNTAX Counter64
			MAX-ACCESS read-only
			STATUS current
			DESCRIPTION
				"The total number of packets received
				(jabbers)"
			::= { sleGponOnuPMStatsSumOnuUniEth3Entry 54 }


--  1.3.6.1.4.1.6296.101.23.7.7.10.1.55
		sleGponOnuPMStatsSumOnuUniEth3TotalPkt64Octets OBJECT-TYPE
			SYNTAX Counter64
			MAX-ACCESS read-only
			STATUS current
			DESCRIPTION
				"The total number of received packets (including bad packets) that were
				64 octets long,"
			::= { sleGponOnuPMStatsSumOnuUniEth3Entry 55 }


--  1.3.6.1.4.1.6296.101.23.7.7.10.1.56
		sleGponOnuPMStatsSumOnuUniEth3TotalPkt65To127Octets OBJECT-TYPE
			SYNTAX Counter64
			MAX-ACCESS read-only
			STATUS current
			DESCRIPTION
				"The total number of received packets (including bad packets) that were
				65..127 octets long,"
			::= { sleGponOnuPMStatsSumOnuUniEth3Entry 56 }


--  1.3.6.1.4.1.6296.101.23.7.7.10.1.57
		sleGponOnuPMStatsSumOnuUniEth3TotalPkt128To255Octets OBJECT-TYPE
			SYNTAX Counter64
			MAX-ACCESS read-write
			STATUS current
			DESCRIPTION
				"The total number of packets (including bad packets) received that were
				128..255 octets long,"
			::= { sleGponOnuPMStatsSumOnuUniEth3Entry 57 }


--  1.3.6.1.4.1.6296.101.23.7.7.10.1.58
		sleGponOnuPMStatsSumOnuUniEth3TotalPkt256To511Octets OBJECT-TYPE
			SYNTAX Counter64
			MAX-ACCESS read-only
			STATUS current
			DESCRIPTION
				"The total number of packets (including bad packets) received that were
				256..511 octets long,"
			::= { sleGponOnuPMStatsSumOnuUniEth3Entry 58 }


--  1.3.6.1.4.1.6296.101.23.7.7.10.1.59
		sleGponOnuPMStatsSumOnuUniEth3TotalPkt512To1023Octets OBJECT-TYPE
			SYNTAX Counter64
			MAX-ACCESS read-write
			STATUS current
			DESCRIPTION
				"The total number of packets (including bad packets) received that were
				512..1023 octets long,"
			::= { sleGponOnuPMStatsSumOnuUniEth3Entry 59 }


--  1.3.6.1.4.1.6296.101.23.7.7.10.1.60
		sleGponOnuPMStatsSumOnuUniEth3TotalPkt1024To1518Octets OBJECT-TYPE
			SYNTAX Counter64
			MAX-ACCESS read-only
			STATUS current
			DESCRIPTION
				"The total number of packets (including bad packets) received that were
				1024..1518 octets long,"
			::= { sleGponOnuPMStatsSumOnuUniEth3Entry 60 }


--  1.3.6.1.4.1.6296.101.23.7.7.11
		sleGponOnuPMStatsSumAllOnuGemNctpTable OBJECT-TYPE
			SYNTAX SEQUENCE OF SleGponOnuPMStatsSumAllOnuGemNctpEntry
			MAX-ACCESS not-accessible
			STATUS current
			DESCRIPTION
				" "
			::= { sleGponOnuPMStatatisticsSum 11 }


--  1.3.6.1.4.1.6296.101.23.7.7.11.1
		sleGponOnuPMStatsSumAllOnuGemNctpEntry OBJECT-TYPE
			SYNTAX SleGponOnuPMStatsSumAllOnuGemNctpEntry
			MAX-ACCESS not-accessible
			STATUS current
			DESCRIPTION
				" "
			INDEX { sleGponOltId }
			::= { sleGponOnuPMStatsSumAllOnuGemNctpTable 1 }


		SleGponOnuPMStatsSumAllOnuGemNctpEntry ::=
			SEQUENCE {
				sleGponOnuPMStatsSumAllOnuGemNctpRxGemFrames
					Counter64,
				sleGponOnuPMStatsSumAllOnuGemNctpTxGemFrames
					Counter64,
				sleGponOnuPMStatsSumAllOnuGemNctpRxPayloadByte
					Counter64,
				sleGponOnuPMStatsSumAllOnuGemNctpTxPayloadByte
					Counter64,
				sleGponOnuPMStatsSumAllOnuGemNctpEncryptionKeyError
					Counter64
			 }

--  1.3.6.1.4.1.6296.101.23.7.7.11.1.1
		sleGponOnuPMStatsSumAllOnuGemNctpRxGemFrames OBJECT-TYPE
			SYNTAX Counter64
			MAX-ACCESS read-only
			STATUS current
			DESCRIPTION
				"The sum total of all onu Rx Gem Frames"
			::= { sleGponOnuPMStatsSumAllOnuGemNctpEntry 1 }


--  1.3.6.1.4.1.6296.101.23.7.7.11.1.2
		sleGponOnuPMStatsSumAllOnuGemNctpTxGemFrames OBJECT-TYPE
			SYNTAX Counter64
			MAX-ACCESS read-only
			STATUS current
			DESCRIPTION
				"The sum total of all onu Tx Gem Frames"
			::= { sleGponOnuPMStatsSumAllOnuGemNctpEntry 2 }


--  1.3.6.1.4.1.6296.101.23.7.7.11.1.3
		sleGponOnuPMStatsSumAllOnuGemNctpRxPayloadByte OBJECT-TYPE
			SYNTAX Counter64
			MAX-ACCESS read-only
			STATUS current
			DESCRIPTION
				"The sum total of all onu Rx Payload Byte"
			::= { sleGponOnuPMStatsSumAllOnuGemNctpEntry 3 }


--  1.3.6.1.4.1.6296.101.23.7.7.11.1.4
		sleGponOnuPMStatsSumAllOnuGemNctpTxPayloadByte OBJECT-TYPE
			SYNTAX Counter64
			MAX-ACCESS read-only
			STATUS current
			DESCRIPTION
				"The sum total of all onu Tx Payload Byte"
			::= { sleGponOnuPMStatsSumAllOnuGemNctpEntry 4 }


--  1.3.6.1.4.1.6296.101.23.7.7.11.1.5
		sleGponOnuPMStatsSumAllOnuGemNctpEncryptionKeyError OBJECT-TYPE
			SYNTAX Counter64
			MAX-ACCESS read-only
			STATUS current
			DESCRIPTION
				"The sum total of all onu Encryption Key Error"
			::= { sleGponOnuPMStatsSumAllOnuGemNctpEntry 5 }


--  1.3.6.1.4.1.6296.101.23.7.7.12
		sleGponOnuPMStatsSumOnuGEMNCTPTable OBJECT-TYPE
			SYNTAX SEQUENCE OF SleGponOnuPMStatsSumOnuGEMNCTPEntry
			MAX-ACCESS not-accessible
			STATUS current
			DESCRIPTION
				" "
			::= { sleGponOnuPMStatatisticsSum 12 }


--  1.3.6.1.4.1.6296.101.23.7.7.12.1
		sleGponOnuPMStatsSumOnuGEMNCTPEntry OBJECT-TYPE
			SYNTAX SleGponOnuPMStatsSumOnuGEMNCTPEntry
			MAX-ACCESS not-accessible
			STATUS current
			DESCRIPTION
				" "
			INDEX { sleGponOltId, sleGponOnuId }
			::= { sleGponOnuPMStatsSumOnuGEMNCTPTable 1 }


		SleGponOnuPMStatsSumOnuGEMNCTPEntry ::=
			SEQUENCE {
				sleGponOnuPMStatsSumOnuGEMNCTPPre15mRxGemFrames
					Counter64,
				sleGponOnuPMStatsSumOnuGEMNCTPPre15mTxGemFrames
					Counter64,
				sleGponOnuPMStatsSumOnuGEMNCTPPre15mRxPayloadByte
					Counter64,
				sleGponOnuPMStatsSumOnuGEMNCTPPre15mTxPayloadByte
					Counter64,
				sleGponOnuPMStatsSumOnuGEMNCTPPre15mEncryptionKeyError
					Counter64,
				sleGponOnuPMStatsSumOnuGEMNCTPHourRxGemFrames
					Counter64,
				sleGponOnuPMStatsSumOnuGEMNCTPHourTxGemFrames
					Counter64,
				sleGponOnuPMStatsSumOnuGEMNCTPHourRxPayloadByte
					Counter64,
				sleGponOnuPMStatsSumOnuGEMNCTPHourTxPayloadByte
					Counter64,
				sleGponOnuPMStatsSumOnuGEMNCTPHourEncryptionKeyError
					Counter64,
				sleGponOnuPMStatsSumOnuGEMNCTPDayRxGemFrames
					Counter64,
				sleGponOnuPMStatsSumOnuGEMNCTPDayTxGemFrames
					Counter64,
				sleGponOnuPMStatsSumOnuGEMNCTPDayRxPayloadByte
					Counter64,
				sleGponOnuPMStatsSumOnuGEMNCTPDayTxPayloadByte
					Counter64,
				sleGponOnuPMStatsSumOnuGEMNCTPDayEncryptionKeyError
					Counter64,
				sleGponOnuPMStatsSumOnuGEMNCTPTotalRxGemFrames
					Counter64,
				sleGponOnuPMStatsSumOnuGEMNCTPTotalTxGemFrames
					Counter64,
				sleGponOnuPMStatsSumOnuGEMNCTPTotalRxPayloadByte
					Counter64,
				sleGponOnuPMStatsSumOnuGEMNCTPTotalTxPayloadByte
					Counter64,
				sleGponOnuPMStatsSumOnuGEMNCTPTotalEncryptionKeyError
					Counter64,
				sleGponOnuPMStatsSumOnuGEMNCTPElapsedTimeAfterClear
					TimeTicks,
				sleGponOnuPMStatsSumOnuGEMNCTPElapsedTimeAfterUpdate
					Counter64
			 }

--  1.3.6.1.4.1.6296.101.23.7.7.12.1.1
		sleGponOnuPMStatsSumOnuGEMNCTPPre15mRxGemFrames OBJECT-TYPE
			SYNTAX Counter64
			MAX-ACCESS read-only
			STATUS current
			DESCRIPTION
				"The pre 15 minute number of Rx Gem Frames"
			::= { sleGponOnuPMStatsSumOnuGEMNCTPEntry 1 }


--  1.3.6.1.4.1.6296.101.23.7.7.12.1.2
		sleGponOnuPMStatsSumOnuGEMNCTPPre15mTxGemFrames OBJECT-TYPE
			SYNTAX Counter64
			MAX-ACCESS read-only
			STATUS current
			DESCRIPTION
				"The pre 15 minute number of Tx Gem Frames"
			::= { sleGponOnuPMStatsSumOnuGEMNCTPEntry 2 }


--  1.3.6.1.4.1.6296.101.23.7.7.12.1.3
		sleGponOnuPMStatsSumOnuGEMNCTPPre15mRxPayloadByte OBJECT-TYPE
			SYNTAX Counter64
			MAX-ACCESS read-only
			STATUS current
			DESCRIPTION
				"The pre 15 minute number of Rx Payload Byte"
			::= { sleGponOnuPMStatsSumOnuGEMNCTPEntry 3 }


--  1.3.6.1.4.1.6296.101.23.7.7.12.1.4
		sleGponOnuPMStatsSumOnuGEMNCTPPre15mTxPayloadByte OBJECT-TYPE
			SYNTAX Counter64
			MAX-ACCESS read-only
			STATUS current
			DESCRIPTION
				"The pre 15 minute number of Tx Payload Byte"
			::= { sleGponOnuPMStatsSumOnuGEMNCTPEntry 4 }


--  1.3.6.1.4.1.6296.101.23.7.7.12.1.5
		sleGponOnuPMStatsSumOnuGEMNCTPPre15mEncryptionKeyError OBJECT-TYPE
			SYNTAX Counter64
			MAX-ACCESS read-only
			STATUS current
			DESCRIPTION
				"The pre 15 minute number of Encryption Key Error"
			::= { sleGponOnuPMStatsSumOnuGEMNCTPEntry 5 }


--  1.3.6.1.4.1.6296.101.23.7.7.12.1.6
		sleGponOnuPMStatsSumOnuGEMNCTPHourRxGemFrames OBJECT-TYPE
			SYNTAX Counter64
			MAX-ACCESS read-only
			STATUS current
			DESCRIPTION
				"The hour number of Rx Gem Frames"
			::= { sleGponOnuPMStatsSumOnuGEMNCTPEntry 6 }


--  1.3.6.1.4.1.6296.101.23.7.7.12.1.7
		sleGponOnuPMStatsSumOnuGEMNCTPHourTxGemFrames OBJECT-TYPE
			SYNTAX Counter64
			MAX-ACCESS read-only
			STATUS current
			DESCRIPTION
				"The hour number of Tx Gem Frames"
			::= { sleGponOnuPMStatsSumOnuGEMNCTPEntry 7 }


--  1.3.6.1.4.1.6296.101.23.7.7.12.1.8
		sleGponOnuPMStatsSumOnuGEMNCTPHourRxPayloadByte OBJECT-TYPE
			SYNTAX Counter64
			MAX-ACCESS read-only
			STATUS current
			DESCRIPTION
				"The hour number of Rx Payload Byte"
			::= { sleGponOnuPMStatsSumOnuGEMNCTPEntry 8 }


--  1.3.6.1.4.1.6296.101.23.7.7.12.1.9
		sleGponOnuPMStatsSumOnuGEMNCTPHourTxPayloadByte OBJECT-TYPE
			SYNTAX Counter64
			MAX-ACCESS read-only
			STATUS current
			DESCRIPTION
				"The hour number of Tx Payload Byte"
			::= { sleGponOnuPMStatsSumOnuGEMNCTPEntry 9 }


--  1.3.6.1.4.1.6296.101.23.7.7.12.1.10
		sleGponOnuPMStatsSumOnuGEMNCTPHourEncryptionKeyError OBJECT-TYPE
			SYNTAX Counter64
			MAX-ACCESS read-only
			STATUS current
			DESCRIPTION
				"The hour number of Encryption Key Error"
			::= { sleGponOnuPMStatsSumOnuGEMNCTPEntry 10 }


--  1.3.6.1.4.1.6296.101.23.7.7.12.1.11
		sleGponOnuPMStatsSumOnuGEMNCTPDayRxGemFrames OBJECT-TYPE
			SYNTAX Counter64
			MAX-ACCESS read-only
			STATUS current
			DESCRIPTION
				"The day number of Rx Gem Frames"
			::= { sleGponOnuPMStatsSumOnuGEMNCTPEntry 11 }


--  1.3.6.1.4.1.6296.101.23.7.7.12.1.12
		sleGponOnuPMStatsSumOnuGEMNCTPDayTxGemFrames OBJECT-TYPE
			SYNTAX Counter64
			MAX-ACCESS read-only
			STATUS current
			DESCRIPTION
				"The day number of Tx Gem Frames"
			::= { sleGponOnuPMStatsSumOnuGEMNCTPEntry 12 }


--  1.3.6.1.4.1.6296.101.23.7.7.12.1.13
		sleGponOnuPMStatsSumOnuGEMNCTPDayRxPayloadByte OBJECT-TYPE
			SYNTAX Counter64
			MAX-ACCESS read-only
			STATUS current
			DESCRIPTION
				"The day number of Rx Payload Byte"
			::= { sleGponOnuPMStatsSumOnuGEMNCTPEntry 13 }


--  1.3.6.1.4.1.6296.101.23.7.7.12.1.14
		sleGponOnuPMStatsSumOnuGEMNCTPDayTxPayloadByte OBJECT-TYPE
			SYNTAX Counter64
			MAX-ACCESS read-only
			STATUS current
			DESCRIPTION
				"The day number of Tx Payload Byte"
			::= { sleGponOnuPMStatsSumOnuGEMNCTPEntry 14 }


--  1.3.6.1.4.1.6296.101.23.7.7.12.1.15
		sleGponOnuPMStatsSumOnuGEMNCTPDayEncryptionKeyError OBJECT-TYPE
			SYNTAX Counter64
			MAX-ACCESS read-only
			STATUS current
			DESCRIPTION
				"The day number of Encryption Key Error"
			::= { sleGponOnuPMStatsSumOnuGEMNCTPEntry 15 }


--  1.3.6.1.4.1.6296.101.23.7.7.12.1.16
		sleGponOnuPMStatsSumOnuGEMNCTPTotalRxGemFrames OBJECT-TYPE
			SYNTAX Counter64
			MAX-ACCESS read-only
			STATUS current
			DESCRIPTION
				"The total number of Rx Gem Frames"
			::= { sleGponOnuPMStatsSumOnuGEMNCTPEntry 16 }


--  1.3.6.1.4.1.6296.101.23.7.7.12.1.17
		sleGponOnuPMStatsSumOnuGEMNCTPTotalTxGemFrames OBJECT-TYPE
			SYNTAX Counter64
			MAX-ACCESS read-only
			STATUS current
			DESCRIPTION
				"The total number of Tx Gem Frames"
			::= { sleGponOnuPMStatsSumOnuGEMNCTPEntry 17 }


--  1.3.6.1.4.1.6296.101.23.7.7.12.1.18
		sleGponOnuPMStatsSumOnuGEMNCTPTotalRxPayloadByte OBJECT-TYPE
			SYNTAX Counter64
			MAX-ACCESS read-only
			STATUS current
			DESCRIPTION
				"The total number of Rx Payload Byte"
			::= { sleGponOnuPMStatsSumOnuGEMNCTPEntry 18 }


--  1.3.6.1.4.1.6296.101.23.7.7.12.1.19
		sleGponOnuPMStatsSumOnuGEMNCTPTotalTxPayloadByte OBJECT-TYPE
			SYNTAX Counter64
			MAX-ACCESS read-write
			STATUS current
			DESCRIPTION
				"The total number of Tx Payload Byte"
			::= { sleGponOnuPMStatsSumOnuGEMNCTPEntry 19 }


--  1.3.6.1.4.1.6296.101.23.7.7.12.1.20
		sleGponOnuPMStatsSumOnuGEMNCTPTotalEncryptionKeyError OBJECT-TYPE
			SYNTAX Counter64
			MAX-ACCESS read-only
			STATUS current
			DESCRIPTION
				"The total number of Encryption Key Error"
			::= { sleGponOnuPMStatsSumOnuGEMNCTPEntry 20 }


--  1.3.6.1.4.1.6296.101.23.7.7.12.1.21
		sleGponOnuPMStatsSumOnuGEMNCTPElapsedTimeAfterClear OBJECT-TYPE
			SYNTAX TimeTicks
			MAX-ACCESS read-only
			STATUS current
			DESCRIPTION
				"The number of packets for elapsed time after clear"
			::= { sleGponOnuPMStatsSumOnuGEMNCTPEntry 21 }


--  1.3.6.1.4.1.6296.101.23.7.7.12.1.22
		sleGponOnuPMStatsSumOnuGEMNCTPElapsedTimeAfterUpdate OBJECT-TYPE
			SYNTAX Counter64
			MAX-ACCESS read-only
			STATUS current
			DESCRIPTION
				"The number of packets for elapsed time after update"
			::= { sleGponOnuPMStatsSumOnuGEMNCTPEntry 22 }


--   1.3.6.1.4.1.6296.101.23.8
-- 1.3.6.1.4.1.6296.101.23.8
		sleGponFirmwareMgmt OBJECT IDENTIFIER ::= { sleGpon 8 }


--   1.3.6.1.4.1.6296.101.23.8.1
-- 1.3.6.1.4.1.6296.101.23.8.1
		sleGponFirmwareTable OBJECT-TYPE
			SYNTAX SEQUENCE OF SleGponFirmwareEntry
			MAX-ACCESS not-accessible
			STATUS current
			DESCRIPTION
				"sleGponFirmwareTable"
			::= { sleGponFirmwareMgmt 1 }


--   1.3.6.1.4.1.6296.101.23.8.1.1
-- 1.3.6.1.4.1.6296.101.23.8.1.1
		sleGponFirmwareEntry OBJECT-TYPE
			SYNTAX SleGponFirmwareEntry
			MAX-ACCESS not-accessible
			STATUS current
			DESCRIPTION
				"key: sleGponFirmwareType, sleGponFirmwareName"
			INDEX { sleGponFirmwareType, sleGponFirmwareName }
			::= { sleGponFirmwareTable 1 }


		SleGponFirmwareEntry ::=
			SEQUENCE {
				sleGponFirmwareType
					INTEGER,
				sleGponFirmwareName
					OCTET STRING
			 }

--   1.3.6.1.4.1.6296.101.23.8.1.1.1
-- 1.3.6.1.4.1.6296.101.23.8.1.1.1
		sleGponFirmwareType OBJECT-TYPE
			SYNTAX INTEGER
				{
				olt(1),
				onu(2)
				}
			MAX-ACCESS read-only
			STATUS current
			DESCRIPTION
				"Firmware type."
			::= { sleGponFirmwareEntry 1 }


--   1.3.6.1.4.1.6296.101.23.8.1.1.2
-- 1.3.6.1.4.1.6296.101.23.8.1.1.2
		sleGponFirmwareName OBJECT-TYPE
			SYNTAX OCTET STRING (SIZE (1..64))
			MAX-ACCESS read-only
			STATUS current
			DESCRIPTION
				"Firmware name."
			::= { sleGponFirmwareEntry 2 }


--   1.3.6.1.4.1.6296.101.23.8.2
-- 1.3.6.1.4.1.6296.101.23.8.2
		sleGponFirmwareControl OBJECT IDENTIFIER ::= { sleGponFirmwareMgmt 2 }


--   1.3.6.1.4.1.6296.101.23.8.2.1
-- 1.3.6.1.4.1.6296.101.23.8.2.1
		sleGponFirmwareControlRequest OBJECT-TYPE
			SYNTAX INTEGER
				{
				setGponFirmwareUpgradeProfile(1),
				deleteGponFirmware(2),
				setGponFirmwareDownload(3)
				}
			MAX-ACCESS read-write
			STATUS current
			DESCRIPTION
				"The request of a user command"
			::= { sleGponFirmwareControl 1 }


--   1.3.6.1.4.1.6296.101.23.8.2.2
-- 1.3.6.1.4.1.6296.101.23.8.2.2
		sleGponFirmwareControlStatus OBJECT-TYPE
			SYNTAX SleControlStatusType
			MAX-ACCESS read-only
			STATUS current
			DESCRIPTION
				"The status of user command"
			::= { sleGponFirmwareControl 2 }


--   1.3.6.1.4.1.6296.101.23.8.2.3
-- 1.3.6.1.4.1.6296.101.23.8.2.3
		sleGponFirmwareControlTimer OBJECT-TYPE
			SYNTAX Gauge32
			MAX-ACCESS read-write
			STATUS current
			DESCRIPTION
				"The maximum time for the manager for a long running user command"
			::= { sleGponFirmwareControl 3 }


--   1.3.6.1.4.1.6296.101.23.8.2.4
-- 1.3.6.1.4.1.6296.101.23.8.2.4
		sleGponFirmwareControlTimeStamp OBJECT-TYPE
			SYNTAX TimeTicks
			MAX-ACCESS read-only
			STATUS current
			DESCRIPTION
				"The time stamp of the last command(end of command)"
			::= { sleGponFirmwareControl 4 }


--   1.3.6.1.4.1.6296.101.23.8.2.5
-- 1.3.6.1.4.1.6296.101.23.8.2.5
		sleGponFirmwareControlReqResult OBJECT-TYPE
			SYNTAX SleControlRequestResultType
			MAX-ACCESS read-only
			STATUS current
			DESCRIPTION
				"The result of the last user command"
			::= { sleGponFirmwareControl 5 }


--   1.3.6.1.4.1.6296.101.23.8.2.6
-- 1.3.6.1.4.1.6296.101.23.8.2.6
		sleGponFirmwareControlName OBJECT-TYPE
			SYNTAX OCTET STRING (SIZE (1..128))
			MAX-ACCESS read-write
			STATUS current
			DESCRIPTION
				"Firmware filename."
			::= { sleGponFirmwareControl 6 }


--   1.3.6.1.4.1.6296.101.23.8.2.7
-- 1.3.6.1.4.1.6296.101.23.8.2.7
		sleGponFirmwareControlUpgradeMethod OBJECT-TYPE
			SYNTAX INTEGER
				{
				ftp(1),
				tftp(2)
				}
			MAX-ACCESS read-write
			STATUS current
			DESCRIPTION
				"1: using FTP
				2: using TFTP"
			::= { sleGponFirmwareControl 7 }


--   1.3.6.1.4.1.6296.101.23.8.2.8
-- 1.3.6.1.4.1.6296.101.23.8.2.8
		sleGponFirmwareControlUpgradeMode OBJECT-TYPE
			SYNTAX INTEGER
				{
				upload(1),
				download(2)
				}
			MAX-ACCESS read-write
			STATUS current
			DESCRIPTION
				"1. Uploading firmware to the remote-host
				2. Downloading firmware from the remote-host."
			::= { sleGponFirmwareControl 8 }


--   1.3.6.1.4.1.6296.101.23.8.2.9
-- 1.3.6.1.4.1.6296.101.23.8.2.9
		sleGponFirmwareControlServerAddress OBJECT-TYPE
			SYNTAX IpAddress
			MAX-ACCESS read-write
			STATUS current
			DESCRIPTION
				"The remote-host's IP address"
			::= { sleGponFirmwareControl 9 }


--   1.3.6.1.4.1.6296.101.23.8.2.10
-- 1.3.6.1.4.1.6296.101.23.8.2.10
		sleGponFirmwareControlUser OBJECT-TYPE
			SYNTAX OCTET STRING
			MAX-ACCESS read-write
			STATUS current
			DESCRIPTION
				"Account-name"
			::= { sleGponFirmwareControl 10 }


--   1.3.6.1.4.1.6296.101.23.8.2.11
-- 1.3.6.1.4.1.6296.101.23.8.2.11
		sleGponFirmwareControlPasswd OBJECT-TYPE
			SYNTAX OCTET STRING
			MAX-ACCESS read-write
			STATUS current
			DESCRIPTION
				"Account-password"
			::= { sleGponFirmwareControl 11 }


--   1.3.6.1.4.1.6296.101.23.8.3
-- 1.3.6.1.4.1.6296.101.23.8.3
		sleGponFirmwareNotification OBJECT IDENTIFIER ::= { sleGponFirmwareMgmt 3 }


--   1.3.6.1.4.1.6296.101.23.8.3.1
-- 1.3.6.1.4.1.6296.101.23.8.3.1
		sleGponFirmwareUpgradeProfileChanged NOTIFICATION-TYPE
			OBJECTS { sleGponFirmwareControlRequest, sleGponFirmwareControlTimeStamp, sleGponFirmwareControlReqResult, sleGponFirmwareControlName, sleGponFirmwareControlUpgradeMethod,
				sleGponFirmwareControlUpgradeMode, sleGponFirmwareControlServerAddress, sleGponFirmwareControlUser, sleGponFirmwareControlPasswd }
			STATUS current
			DESCRIPTION
				"Description."
			::= { sleGponFirmwareNotification 1 }


--   1.3.6.1.4.1.6296.101.23.8.3.2
-- 1.3.6.1.4.1.6296.101.23.8.3.2
		sleGponFirmwareDeleted NOTIFICATION-TYPE
			OBJECTS { sleGponFirmwareControlRequest, sleGponFirmwareControlTimeStamp, sleGponFirmwareControlReqResult, sleGponFirmwareControlName }
			STATUS current
			DESCRIPTION
				"Description."
			::= { sleGponFirmwareNotification 2 }


--   1.3.6.1.4.1.6296.101.23.8.3.3
-- 1.3.6.1.4.1.6296.101.23.8.3.3
		sleGponFirmwareDownloadChanged NOTIFICATION-TYPE
			OBJECTS { sleGponFirmwareControlRequest, sleGponFirmwareControlTimeStamp, sleGponFirmwareControlReqResult, sleGponFirmwareControlName, sleGponFirmwareControlServerAddress,
				sleGponFirmwareControlUser, sleGponFirmwareControlPasswd }
			STATUS current
			DESCRIPTION
				"Description."
			::= { sleGponFirmwareNotification 3 }


--   1.3.6.1.4.1.6296.101.23.9
-- 1.3.6.1.4.1.6296.101.23.9
		sleGponOnuFirmwareAutoUpgradeMgmt OBJECT IDENTIFIER ::= { sleGpon 9 }


--   1.3.6.1.4.1.6296.101.23.9.1
-- 1.3.6.1.4.1.6296.101.23.9.1
		sleGponOnuFWAutoUpgrade OBJECT IDENTIFIER ::= { sleGponOnuFirmwareAutoUpgradeMgmt 1 }


--   1.3.6.1.4.1.6296.101.23.9.1.1
-- 1.3.6.1.4.1.6296.101.23.9.1.1
		sleGponOnuFWAutoUpgradeTable OBJECT-TYPE
			SYNTAX SEQUENCE OF SleGponOnuFWAutoUpgradeEntry
			MAX-ACCESS not-accessible
			STATUS current
			DESCRIPTION
				"sleGponOnuFWAutoUpgradeTable"
			::= { sleGponOnuFWAutoUpgrade 1 }


--   1.3.6.1.4.1.6296.101.23.9.1.1.1
-- 1.3.6.1.4.1.6296.101.23.9.1.1.1
		sleGponOnuFWAutoUpgradeEntry OBJECT-TYPE
			SYNTAX SleGponOnuFWAutoUpgradeEntry
			MAX-ACCESS not-accessible
			STATUS current
			DESCRIPTION
				"key: sleGponOltId"
			INDEX { sleGponOltId }
			::= { sleGponOnuFWAutoUpgradeTable 1 }


		SleGponOnuFWAutoUpgradeEntry ::=
			SEQUENCE {
				sleGponOnuFWAutoUpgradeMode
					INTEGER,
				sleGponOnuFWAutoUpgradeVersionMatch
					INTEGER,
				sleGponOnuFWAutoUpgradeInvalidVersionMatch
					INTEGER,
				sleGponOnuFWAutoUpgradeStatus
					INTEGER,
				sleGponOnuFWAutoUpgradeCurrentUgradingFWName
					OCTET STRING
			 }

--   1.3.6.1.4.1.6296.101.23.9.1.1.1.1
-- 1.3.6.1.4.1.6296.101.23.9.1.1.1.1
		sleGponOnuFWAutoUpgradeMode OBJECT-TYPE
			SYNTAX INTEGER
				{
				enable(1),
				disable(2)
				}
			MAX-ACCESS read-only
			STATUS current
			DESCRIPTION
				"Auto upgrade configuration."
			::= { sleGponOnuFWAutoUpgradeEntry 1 }


--   1.3.6.1.4.1.6296.101.23.9.1.1.1.2
-- 1.3.6.1.4.1.6296.101.23.9.1.1.1.2
		sleGponOnuFWAutoUpgradeVersionMatch OBJECT-TYPE
			SYNTAX INTEGER
				{
				enable(1),
				disable(2)
				}
			MAX-ACCESS read-only
			STATUS current
			DESCRIPTION
				"Upgrade if ONU's version is upper than auto-upgrade-fw."
			::= { sleGponOnuFWAutoUpgradeEntry 2 }


--   1.3.6.1.4.1.6296.101.23.9.1.1.1.3
-- 1.3.6.1.4.1.6296.101.23.9.1.1.1.3
		sleGponOnuFWAutoUpgradeInvalidVersionMatch OBJECT-TYPE
			SYNTAX INTEGER
				{
				enable(1),
				disable(2)
				}
			MAX-ACCESS read-only
			STATUS current
			DESCRIPTION
				"Upgrade if ONU's version is invalid."
			::= { sleGponOnuFWAutoUpgradeEntry 3 }


--   1.3.6.1.4.1.6296.101.23.9.1.1.1.4
-- 1.3.6.1.4.1.6296.101.23.9.1.1.1.4
		sleGponOnuFWAutoUpgradeStatus OBJECT-TYPE
			SYNTAX INTEGER
				{
				none(0),
				downloadFirmware(1),
				uploadFirmwareToGPIU(2),
				upgradeOnuProgress(3),
				upgradeOnuWating(4),
				unknown(5)
				}
			MAX-ACCESS read-only
			STATUS current
			DESCRIPTION
				"Auto upgrade status."
			::= { sleGponOnuFWAutoUpgradeEntry 4 }


--   1.3.6.1.4.1.6296.101.23.9.1.1.1.5
-- 1.3.6.1.4.1.6296.101.23.9.1.1.1.5
		sleGponOnuFWAutoUpgradeCurrentUgradingFWName OBJECT-TYPE
			SYNTAX OCTET STRING (SIZE (1..128))
			MAX-ACCESS read-only
			STATUS current
			DESCRIPTION
				"Firmware of current upgrading."
			::= { sleGponOnuFWAutoUpgradeEntry 5 }


--   1.3.6.1.4.1.6296.101.23.9.1.2
-- 1.3.6.1.4.1.6296.101.23.9.1.2
		sleGponOnuFWAutoUpgradeControl OBJECT IDENTIFIER ::= { sleGponOnuFWAutoUpgrade 2 }


--   1.3.6.1.4.1.6296.101.23.9.1.2.1
-- 1.3.6.1.4.1.6296.101.23.9.1.2.1
		sleGponOnuFWAutoUpgradeControlRequest OBJECT-TYPE
			SYNTAX INTEGER
				{
				setAutoUpgradeMode(1),
				setVersionMatch(2),
				setInvalidVersionMatch(3)
				}
			MAX-ACCESS read-write
			STATUS current
			DESCRIPTION
				"The request of a user command"
			::= { sleGponOnuFWAutoUpgradeControl 1 }


--   1.3.6.1.4.1.6296.101.23.9.1.2.2
-- 1.3.6.1.4.1.6296.101.23.9.1.2.2
		sleGponOnuFWAutoUpgradeControlStatus OBJECT-TYPE
			SYNTAX SleControlStatusType
			MAX-ACCESS read-only
			STATUS current
			DESCRIPTION
				"The status of user command"
			::= { sleGponOnuFWAutoUpgradeControl 2 }


--   1.3.6.1.4.1.6296.101.23.9.1.2.3
-- 1.3.6.1.4.1.6296.101.23.9.1.2.3
		sleGponOnuFWAutoUpgradeControlTimer OBJECT-TYPE
			SYNTAX Gauge32
			MAX-ACCESS read-write
			STATUS current
			DESCRIPTION
				"The maximum time for the manager for a long running user command"
			::= { sleGponOnuFWAutoUpgradeControl 3 }


--   1.3.6.1.4.1.6296.101.23.9.1.2.4
-- 1.3.6.1.4.1.6296.101.23.9.1.2.4
		sleGponOnuFWAutoUpgradeControlTimeStamp OBJECT-TYPE
			SYNTAX TimeTicks
			MAX-ACCESS read-only
			STATUS current
			DESCRIPTION
				"The time stamp of the last command(end of command)"
			::= { sleGponOnuFWAutoUpgradeControl 4 }


--   1.3.6.1.4.1.6296.101.23.9.1.2.5
-- 1.3.6.1.4.1.6296.101.23.9.1.2.5
		sleGponOnuFWAutoUpgradeControlReqResult OBJECT-TYPE
			SYNTAX SleControlRequestResultType
			MAX-ACCESS read-only
			STATUS current
			DESCRIPTION
				"The result of the last user command"
			::= { sleGponOnuFWAutoUpgradeControl 5 }


		sleGponOnuFWAutoUpgradeControlOltId OBJECT-TYPE
			SYNTAX INTEGER (1..2147483647)
			MAX-ACCESS read-write
			STATUS current
			DESCRIPTION
				"Gpon Olt Index."
			::= { sleGponOnuFWAutoUpgradeControl 6 }


--   1.3.6.1.4.1.6296.101.23.9.1.2.7
-- 1.3.6.1.4.1.6296.101.23.9.1.2.7
		sleGponOnuFWAutoUpgradeControlMode OBJECT-TYPE
			SYNTAX INTEGER
				{
				enable(1),
				disable(2)
				}
			MAX-ACCESS read-write
			STATUS current
			DESCRIPTION
				"Auto upgrade configuration."
			::= { sleGponOnuFWAutoUpgradeControl 7 }


--   1.3.6.1.4.1.6296.101.23.9.1.2.8
-- 1.3.6.1.4.1.6296.101.23.9.1.2.8
		sleGponOnuFWAutoUpgradeControlVersionMatch OBJECT-TYPE
			SYNTAX INTEGER
				{
				enable(1),
				disable(2)
				}
			MAX-ACCESS read-write
			STATUS current
			DESCRIPTION
				"Upgrade if ONU's version is upper than auto-upgrade-fw."
			::= { sleGponOnuFWAutoUpgradeControl 8 }


--   1.3.6.1.4.1.6296.101.23.9.1.2.9
-- 1.3.6.1.4.1.6296.101.23.9.1.2.9
		sleGponOnuFWAutoUpgradeControlInvalidVersionMatch OBJECT-TYPE
			SYNTAX INTEGER
				{
				enable(1),
				disable(2)
				}
			MAX-ACCESS read-write
			STATUS current
			DESCRIPTION
				"Upgrade if ONU's version is invalid."
			::= { sleGponOnuFWAutoUpgradeControl 9 }


--   1.3.6.1.4.1.6296.101.23.9.1.3
-- 1.3.6.1.4.1.6296.101.23.9.1.3
		sleGponOnuFWAutoUpgradeNotification OBJECT IDENTIFIER ::= { sleGponOnuFWAutoUpgrade 3 }


--   1.3.6.1.4.1.6296.101.23.9.1.3.1
-- 1.3.6.1.4.1.6296.101.23.9.1.3.1
		sleGponOnuFWAutoUpgradeModeChanged NOTIFICATION-TYPE
			OBJECTS { sleGponOnuFWAutoUpgradeControlRequest, sleGponOnuFWAutoUpgradeControlTimeStamp, sleGponOnuFWAutoUpgradeControlReqResult, sleGponOnuFWAutoUpgradeControlOltId, sleGponOnuFWAutoUpgradeControlMode
				 }
			STATUS current
			DESCRIPTION
				"Description."
			::= { sleGponOnuFWAutoUpgradeNotification 1 }


--   1.3.6.1.4.1.6296.101.23.9.1.3.2
-- 1.3.6.1.4.1.6296.101.23.9.1.3.2
		sleGponOnuFWAutoUpgradeVersionMatchChanged NOTIFICATION-TYPE
			OBJECTS { sleGponOnuFWAutoUpgradeControlRequest, sleGponOnuFWAutoUpgradeControlTimeStamp, sleGponOnuFWAutoUpgradeControlReqResult, sleGponOnuFWAutoUpgradeControlOltId, sleGponOnuFWAutoUpgradeControlVersionMatch
				 }
			STATUS current
			DESCRIPTION
				"Description."
			::= { sleGponOnuFWAutoUpgradeNotification 2 }


--   1.3.6.1.4.1.6296.101.23.9.1.3.3
-- 1.3.6.1.4.1.6296.101.23.9.1.3.3
		sleGponOnuFWAutoUpgradeInvalidVersionMatchChanged NOTIFICATION-TYPE
			OBJECTS { sleGponOnuFWAutoUpgradeControlRequest, sleGponOnuFWAutoUpgradeControlTimeStamp, sleGponOnuFWAutoUpgradeControlReqResult, sleGponOnuFWAutoUpgradeControlOltId, sleGponOnuFWAutoUpgradeControlInvalidVersionMatch
				 }
			STATUS current
			DESCRIPTION
				"Description."
			::= { sleGponOnuFWAutoUpgradeNotification 3 }


--   1.3.6.1.4.1.6296.101.23.9.2
-- 1.3.6.1.4.1.6296.101.23.9.2
		sleGponOnuFWAutoUpgradeTime OBJECT IDENTIFIER ::= { sleGponOnuFirmwareAutoUpgradeMgmt 2 }


--   1.3.6.1.4.1.6296.101.23.9.2.1
-- 1.3.6.1.4.1.6296.101.23.9.2.1
		sleGponOnuFWAutoUpgradeTimeInfo OBJECT IDENTIFIER ::= { sleGponOnuFWAutoUpgradeTime 1 }


--   1.3.6.1.4.1.6296.101.23.9.2.1.1
-- 1.3.6.1.4.1.6296.101.23.9.2.1.1
		sleGponOnuFWAutoUpgradeStartTime OBJECT-TYPE
			SYNTAX INTEGER (-1 | 0..23)
			UNITS "1 hour"
			MAX-ACCESS read-only
			STATUS current
			DESCRIPTION
				"ONU upgrade start time. (-1 is none-time : disable)"
			::= { sleGponOnuFWAutoUpgradeTimeInfo 1 }


--   1.3.6.1.4.1.6296.101.23.9.2.1.2
-- 1.3.6.1.4.1.6296.101.23.9.2.1.2
		sleGponOnuFWAutoUpgradeEndTime OBJECT-TYPE
			SYNTAX INTEGER (-1 | 0..23)
			UNITS "1 hour"
			MAX-ACCESS read-only
			STATUS current
			DESCRIPTION
				"ONU upgrade end time. (-1 is none-time : disable)"
			::= { sleGponOnuFWAutoUpgradeTimeInfo 2 }


--   1.3.6.1.4.1.6296.101.23.9.2.1.3
-- 1.3.6.1.4.1.6296.101.23.9.2.1.3
		sleGponOnuFWAutoUpgradeRebootTime OBJECT-TYPE
			SYNTAX INTEGER (-1 | 0..23 | 24)
			UNITS "1 hour"
			MAX-ACCESS read-only
			STATUS current
			DESCRIPTION
				"ONU rebooting time. (-1 is none-time : disable / 24 is immediately)"
			::= { sleGponOnuFWAutoUpgradeTimeInfo 3 }


--   1.3.6.1.4.1.6296.101.23.9.2.2
-- 1.3.6.1.4.1.6296.101.23.9.2.2
		sleGponOnuFWAutoUpgradeTimeControl OBJECT IDENTIFIER ::= { sleGponOnuFWAutoUpgradeTime 2 }


--   1.3.6.1.4.1.6296.101.23.9.2.2.1
-- 1.3.6.1.4.1.6296.101.23.9.2.2.1
		sleGponOnuFWAutoUpgradeTimeControlRequest OBJECT-TYPE
			SYNTAX INTEGER
				{
				setOnuFWAutoUpgradeStartEndTime(1),
				setOnuFWAutoUpgradeRebootTime(2)
				}
			MAX-ACCESS read-write
			STATUS current
			DESCRIPTION
				"The request of a user command"
			::= { sleGponOnuFWAutoUpgradeTimeControl 1 }


--   1.3.6.1.4.1.6296.101.23.9.2.2.2
-- 1.3.6.1.4.1.6296.101.23.9.2.2.2
		sleGponOnuFWAutoUpgradeTimeControlStatus OBJECT-TYPE
			SYNTAX SleControlStatusType
			MAX-ACCESS read-only
			STATUS current
			DESCRIPTION
				"The status of user command"
			::= { sleGponOnuFWAutoUpgradeTimeControl 2 }


--   1.3.6.1.4.1.6296.101.23.9.2.2.3
-- 1.3.6.1.4.1.6296.101.23.9.2.2.3
		sleGponOnuFWAutoUpgradeTimeControlTimer OBJECT-TYPE
			SYNTAX Gauge32
			MAX-ACCESS read-write
			STATUS current
			DESCRIPTION
				"The maximum time for the manager for a long running user command"
			::= { sleGponOnuFWAutoUpgradeTimeControl 3 }


--   1.3.6.1.4.1.6296.101.23.9.2.2.4
-- 1.3.6.1.4.1.6296.101.23.9.2.2.4
		sleGponOnuFWAutoUpgradeTimeControlTimeStamp OBJECT-TYPE
			SYNTAX TimeTicks
			MAX-ACCESS read-only
			STATUS current
			DESCRIPTION
				"The time stamp of the last command(end of command)"
			::= { sleGponOnuFWAutoUpgradeTimeControl 4 }


--   1.3.6.1.4.1.6296.101.23.9.2.2.5
-- 1.3.6.1.4.1.6296.101.23.9.2.2.5
		sleGponOnuFWAutoUpgradeTimeControlReqResult OBJECT-TYPE
			SYNTAX SleControlRequestResultType
			MAX-ACCESS read-only
			STATUS current
			DESCRIPTION
				"The result of the last user command"
			::= { sleGponOnuFWAutoUpgradeTimeControl 5 }


--   1.3.6.1.4.1.6296.101.23.9.2.2.6
-- 1.3.6.1.4.1.6296.101.23.9.2.2.6
		sleGponOnuFWAutoUpgradeTimeControlStartTime OBJECT-TYPE
			SYNTAX INTEGER (-1 | 0..23)
			UNITS "1 hour"
			MAX-ACCESS read-write
			STATUS current
			DESCRIPTION
				"ONU upgrade start time. (-1 is none-time : disable)"
			::= { sleGponOnuFWAutoUpgradeTimeControl 6 }


--   1.3.6.1.4.1.6296.101.23.9.2.2.7
-- 1.3.6.1.4.1.6296.101.23.9.2.2.7
		sleGponOnuFWAutoUpgradeTimeControlEndTime OBJECT-TYPE
			SYNTAX INTEGER (-1 | 0..23)
			UNITS "1 hour"
			MAX-ACCESS read-write
			STATUS current
			DESCRIPTION
				"ONU upgrade end time. (-1 is none-time : disable)"
			::= { sleGponOnuFWAutoUpgradeTimeControl 7 }


--   1.3.6.1.4.1.6296.101.23.9.2.2.8
-- 1.3.6.1.4.1.6296.101.23.9.2.2.8
		sleGponOnuFWAutoUpgradeTimeControlRebootTime OBJECT-TYPE
			SYNTAX INTEGER (-1 | 0..23 | 24)
			UNITS "1 hour"
			MAX-ACCESS read-write
			STATUS current
			DESCRIPTION
				"ONU rebooting time. (-1 is none-time : disable / 24 is immediately)"
			::= { sleGponOnuFWAutoUpgradeTimeControl 8 }


--   1.3.6.1.4.1.6296.101.23.9.2.3
-- 1.3.6.1.4.1.6296.101.23.9.2.3
		sleGponOnuFWAutoUpgradeTimeNotification OBJECT IDENTIFIER ::= { sleGponOnuFWAutoUpgradeTime 3 }


--   1.3.6.1.4.1.6296.101.23.9.2.3.1
-- 1.3.6.1.4.1.6296.101.23.9.2.3.1
		sleGponOnuFWAutoUpgradeStartEndTimeChanged NOTIFICATION-TYPE
			OBJECTS { sleGponOnuFWAutoUpgradeTimeControlRequest, sleGponOnuFWAutoUpgradeTimeControlTimeStamp, sleGponOnuFWAutoUpgradeTimeControlReqResult, sleGponOnuFWAutoUpgradeTimeControlStartTime, sleGponOnuFWAutoUpgradeTimeControlEndTime
				 }
			STATUS current
			DESCRIPTION
				"Description."
			::= { sleGponOnuFWAutoUpgradeTimeNotification 1 }


--   1.3.6.1.4.1.6296.101.23.9.2.3.2
-- 1.3.6.1.4.1.6296.101.23.9.2.3.2
		sleGponOnuFWAutoUpgradeRebootTimeChanged NOTIFICATION-TYPE
			OBJECTS { sleGponOnuFWAutoUpgradeTimeControlRequest, sleGponOnuFWAutoUpgradeTimeControlTimeStamp, sleGponOnuFWAutoUpgradeTimeControlReqResult, sleGponOnuFWAutoUpgradeTimeControlRebootTime }
			STATUS current
			DESCRIPTION
				"Description."
			::= { sleGponOnuFWAutoUpgradeTimeNotification 2 }


--   1.3.6.1.4.1.6296.101.23.9.3
-- 1.3.6.1.4.1.6296.101.23.9.3
		sleGponOnuFWAutoUpgradeModel OBJECT IDENTIFIER ::= { sleGponOnuFirmwareAutoUpgradeMgmt 3 }


--   1.3.6.1.4.1.6296.101.23.9.3.1
-- 1.3.6.1.4.1.6296.101.23.9.3.1
		sleGponOnuFWAutoUpgradeModelTable OBJECT-TYPE
			SYNTAX SEQUENCE OF SleGponOnuFWAutoUpgradeModelEntry
			MAX-ACCESS not-accessible
			STATUS current
			DESCRIPTION
				"sleGponOnuFWAutoUpgradeModelTable"
			::= { sleGponOnuFWAutoUpgradeModel 1 }


--   1.3.6.1.4.1.6296.101.23.9.3.1.1
-- 1.3.6.1.4.1.6296.101.23.9.3.1.1
		sleGponOnuFWAutoUpgradeModelEntry OBJECT-TYPE
			SYNTAX SleGponOnuFWAutoUpgradeModelEntry
			MAX-ACCESS not-accessible
			STATUS current
			DESCRIPTION
				"key: sleGponOnuFWAutoUpgradeModelId"
			INDEX { sleGponOnuFWAutoUpgradeModelId }
			::= { sleGponOnuFWAutoUpgradeModelTable 1 }


		SleGponOnuFWAutoUpgradeModelEntry ::=
			SEQUENCE {
				sleGponOnuFWAutoUpgradeModelId
					INTEGER,
				sleGponOnuFWAutoUpgradeModelName
					OCTET STRING,
				sleGponOnuFWAutoUpgradeModelFWName
					OCTET STRING,
				sleGponOnuFWAutoUpgradeModelFWVersion
					OCTET STRING,
				sleGponOnuFWAutoUpgradeModelStatus
					INTEGER,
				sleGponOnuFWAutoUpgradeModelMethod
					INTEGER,
				sleGponOnuFWAutoUpgradeModelServerAddress
					IpAddress,
				sleGponOnuFWAutoUpgradeModelUser
					OCTET STRING,
				sleGponOnuFWAutoUpgradeModelPasswd
					OCTET STRING,
				sleGponOnuFWAutoUpgradeModelFWTargetVersion
					OCTET STRING,
				sleGponOnuFWAutoUpgradeModelExclude
					INTEGER
			 }

--   1.3.6.1.4.1.6296.101.23.9.3.1.1.1
-- 1.3.6.1.4.1.6296.101.23.9.3.1.1.1
		sleGponOnuFWAutoUpgradeModelId OBJECT-TYPE
			SYNTAX INTEGER (1..65535)
			MAX-ACCESS read-only
			STATUS current
			DESCRIPTION
				"Onu modle index."
			::= { sleGponOnuFWAutoUpgradeModelEntry 1 }


--   1.3.6.1.4.1.6296.101.23.9.3.1.1.2
-- 1.3.6.1.4.1.6296.101.23.9.3.1.1.2
		sleGponOnuFWAutoUpgradeModelName OBJECT-TYPE
			SYNTAX OCTET STRING (SIZE (1..128))
			MAX-ACCESS read-only
			STATUS current
			DESCRIPTION
				"Onu model name."
			::= { sleGponOnuFWAutoUpgradeModelEntry 2 }


--   1.3.6.1.4.1.6296.101.23.9.3.1.1.3
-- 1.3.6.1.4.1.6296.101.23.9.3.1.1.3
		sleGponOnuFWAutoUpgradeModelFWName OBJECT-TYPE
			SYNTAX OCTET STRING (SIZE (1..128))
			MAX-ACCESS read-only
			STATUS current
			DESCRIPTION
				"Firmware name of onu model."
			::= { sleGponOnuFWAutoUpgradeModelEntry 3 }


--   1.3.6.1.4.1.6296.101.23.9.3.1.1.4
-- 1.3.6.1.4.1.6296.101.23.9.3.1.1.4
		sleGponOnuFWAutoUpgradeModelFWVersion OBJECT-TYPE
			SYNTAX OCTET STRING (SIZE (1..20))
			MAX-ACCESS read-only
			STATUS current
			DESCRIPTION
				"Firmware version of onu model."
			::= { sleGponOnuFWAutoUpgradeModelEntry 4 }


--   1.3.6.1.4.1.6296.101.23.9.3.1.1.5
-- 1.3.6.1.4.1.6296.101.23.9.3.1.1.5
		sleGponOnuFWAutoUpgradeModelStatus OBJECT-TYPE
			SYNTAX INTEGER
				{
				none(0),
				downloading(1),
				uploadingToGPIU(2),
				noFirmware(3),
				downloadComplete(4)
				}
			MAX-ACCESS read-only
			STATUS current
			DESCRIPTION
				"Firmware status of onu model."
			::= { sleGponOnuFWAutoUpgradeModelEntry 5 }


--   1.3.6.1.4.1.6296.101.23.9.3.1.1.6
-- 1.3.6.1.4.1.6296.101.23.9.3.1.1.6
		sleGponOnuFWAutoUpgradeModelMethod OBJECT-TYPE
			SYNTAX INTEGER
				{
				local(0),
				ftp(1),
				tftp(2)
				}
			MAX-ACCESS read-only
			STATUS current
			DESCRIPTION
				"0: using image in local
				1: using FTP
				2: using TFTP"
			::= { sleGponOnuFWAutoUpgradeModelEntry 6 }


--   1.3.6.1.4.1.6296.101.23.9.3.1.1.7
-- 1.3.6.1.4.1.6296.101.23.9.3.1.1.7
		sleGponOnuFWAutoUpgradeModelServerAddress OBJECT-TYPE
			SYNTAX IpAddress
			MAX-ACCESS read-only
			STATUS current
			DESCRIPTION
				"FTP/TFTP server IP address."
			::= { sleGponOnuFWAutoUpgradeModelEntry 7 }


--   1.3.6.1.4.1.6296.101.23.9.3.1.1.8
-- 1.3.6.1.4.1.6296.101.23.9.3.1.1.8
		sleGponOnuFWAutoUpgradeModelUser OBJECT-TYPE
			SYNTAX OCTET STRING (SIZE (1..20))
			MAX-ACCESS read-only
			STATUS current
			DESCRIPTION
				"Account-name"
			::= { sleGponOnuFWAutoUpgradeModelEntry 8 }


--   1.3.6.1.4.1.6296.101.23.9.3.1.1.9
-- 1.3.6.1.4.1.6296.101.23.9.3.1.1.9
		sleGponOnuFWAutoUpgradeModelPasswd OBJECT-TYPE
			SYNTAX OCTET STRING (SIZE (1..20))
			MAX-ACCESS read-only
			STATUS current
			DESCRIPTION
				"Account-password"
			::= { sleGponOnuFWAutoUpgradeModelEntry 9 }


--   1.3.6.1.4.1.6296.101.23.9.3.1.1.10
-- 1.3.6.1.4.1.6296.101.23.9.3.1.1.10
		sleGponOnuFWAutoUpgradeModelFWTargetVersion OBJECT-TYPE
			SYNTAX OCTET STRING (SIZE (1..20))
			MAX-ACCESS read-only
			STATUS current
			DESCRIPTION
				"Upgrade target onu's version."
			::= { sleGponOnuFWAutoUpgradeModelEntry 10 }


--  1.3.6.1.4.1.6296.101.23.9.3.1.1.11
		sleGponOnuFWAutoUpgradeModelExclude OBJECT-TYPE
			SYNTAX INTEGER
				{
				enable(1),
				disable(2)
				}
			MAX-ACCESS read-only
			STATUS current
			DESCRIPTION
				"The upgrade model excluding status"
			::= { sleGponOnuFWAutoUpgradeModelEntry 11 }


--   1.3.6.1.4.1.6296.101.23.9.3.2
-- 1.3.6.1.4.1.6296.101.23.9.3.2
		sleGponOnuFWAutoUpgradeModelControl OBJECT IDENTIFIER ::= { sleGponOnuFWAutoUpgradeModel 2 }


--
-- 1.3.6.1.4.1.6296.101.23.9.3.2.1
-- 1.3.6.1.4.1.6296.101.23.9.3.2.1
		sleGponOnuFWAutoUpgradeModelControlRequest OBJECT-TYPE
			SYNTAX INTEGER
				{
				setOnuFWAutoUpgradeModelProfile(1),
				destroyOnuAutoUpgradeFirmware(2),
				modifyOnuAutoUpgradeTargetVer(3),
				delGponOnuFWAutoUpgradeModelTargetVer(4)
				}
			MAX-ACCESS read-write
			STATUS current
			DESCRIPTION
				"The request of a user command"
			::= { sleGponOnuFWAutoUpgradeModelControl 1 }


--   1.3.6.1.4.1.6296.101.23.9.3.2.2
-- 1.3.6.1.4.1.6296.101.23.9.3.2.2
		sleGponOnuFWAutoUpgradeModelControlStatus OBJECT-TYPE
			SYNTAX SleControlStatusType
			MAX-ACCESS read-only
			STATUS current
			DESCRIPTION
				"The status of user command"
			::= { sleGponOnuFWAutoUpgradeModelControl 2 }


--   1.3.6.1.4.1.6296.101.23.9.3.2.3
-- 1.3.6.1.4.1.6296.101.23.9.3.2.3
		sleGponOnuFWAutoUpgradeModelControlTimer OBJECT-TYPE
			SYNTAX Gauge32
			MAX-ACCESS read-write
			STATUS current
			DESCRIPTION
				"The maximum time for the manager for a long running user command"
			::= { sleGponOnuFWAutoUpgradeModelControl 3 }


--   1.3.6.1.4.1.6296.101.23.9.3.2.4
-- 1.3.6.1.4.1.6296.101.23.9.3.2.4
		sleGponOnuFWAutoUpgradeModelControlTimeStamp OBJECT-TYPE
			SYNTAX TimeTicks
			MAX-ACCESS read-only
			STATUS current
			DESCRIPTION
				"The time stamp of the last command(end of command)"
			::= { sleGponOnuFWAutoUpgradeModelControl 4 }


--   1.3.6.1.4.1.6296.101.23.9.3.2.5
-- 1.3.6.1.4.1.6296.101.23.9.3.2.5
		sleGponOnuFWAutoUpgradeModelControlReqResult OBJECT-TYPE
			SYNTAX SleControlRequestResultType
			MAX-ACCESS read-only
			STATUS current
			DESCRIPTION
				"The result of the last user command"
			::= { sleGponOnuFWAutoUpgradeModelControl 5 }


--   1.3.6.1.4.1.6296.101.23.9.3.2.6
-- 1.3.6.1.4.1.6296.101.23.9.3.2.6
		sleGponOnuFWAutoUpgradeModelControlName OBJECT-TYPE
			SYNTAX OCTET STRING (SIZE (1..128))
			MAX-ACCESS read-write
			STATUS current
			DESCRIPTION
				"Onu model name."
			::= { sleGponOnuFWAutoUpgradeModelControl 6 }


--   1.3.6.1.4.1.6296.101.23.9.3.2.7
-- 1.3.6.1.4.1.6296.101.23.9.3.2.7
		sleGponOnuFWAutoUpgradeModelControlFWName OBJECT-TYPE
			SYNTAX OCTET STRING (SIZE (1..128))
			MAX-ACCESS read-write
			STATUS current
			DESCRIPTION
				"Firmware name of onu model."
			::= { sleGponOnuFWAutoUpgradeModelControl 7 }


--   1.3.6.1.4.1.6296.101.23.9.3.2.8
-- 1.3.6.1.4.1.6296.101.23.9.3.2.8
		sleGponOnuFWAutoUpgradeModelControlMethod OBJECT-TYPE
			SYNTAX INTEGER
				{
				local(0),
				ftp(1),
				tftp(2)
				}
			MAX-ACCESS read-write
			STATUS current
			DESCRIPTION
				"0: using image in local
				1: using FTP
				2: using TFTP"
			::= { sleGponOnuFWAutoUpgradeModelControl 8 }


--   1.3.6.1.4.1.6296.101.23.9.3.2.9
-- 1.3.6.1.4.1.6296.101.23.9.3.2.9
		sleGponOnuFWAutoUpgradeModelControlServerAddress OBJECT-TYPE
			SYNTAX IpAddress
			MAX-ACCESS read-write
			STATUS current
			DESCRIPTION
				"FTP/TFTP server IP address."
			::= { sleGponOnuFWAutoUpgradeModelControl 9 }


--   1.3.6.1.4.1.6296.101.23.9.3.2.10
-- 1.3.6.1.4.1.6296.101.23.9.3.2.10
		sleGponOnuFWAutoUpgradeModelControlUser OBJECT-TYPE
			SYNTAX OCTET STRING (SIZE (1..20))
			MAX-ACCESS read-write
			STATUS current
			DESCRIPTION
				"Account-name"
			::= { sleGponOnuFWAutoUpgradeModelControl 10 }


--   1.3.6.1.4.1.6296.101.23.9.3.2.11
-- 1.3.6.1.4.1.6296.101.23.9.3.2.11
		sleGponOnuFWAutoUpgradeModelControlPasswd OBJECT-TYPE
			SYNTAX OCTET STRING (SIZE (1..20))
			MAX-ACCESS read-write
			STATUS current
			DESCRIPTION
				"Account-password"
			::= { sleGponOnuFWAutoUpgradeModelControl 11 }


--   1.3.6.1.4.1.6296.101.23.9.3.2.12
-- 1.3.6.1.4.1.6296.101.23.9.3.2.12
		sleGponOnuFWAutoUpgradeModelControlFWTargetVersion OBJECT-TYPE
			SYNTAX OCTET STRING (SIZE (1..20))
			MAX-ACCESS read-write
			STATUS current
			DESCRIPTION
				"Upgrade target onu's version."
			::= { sleGponOnuFWAutoUpgradeModelControl 12 }


--  1.3.6.1.4.1.6296.101.23.9.3.2.13
		sleGponOnuFWAutoUpgradeModelControlExclude OBJECT-TYPE
			SYNTAX INTEGER
				{
				enable(1),
				disable(2)
				}
			MAX-ACCESS read-write
			STATUS current
			DESCRIPTION
				"The upgrade model excluding status"
			::= { sleGponOnuFWAutoUpgradeModelControl 13 }


--   1.3.6.1.4.1.6296.101.23.9.3.3
-- 1.3.6.1.4.1.6296.101.23.9.3.3
		sleGponOnuFWAutoUpgradeModelNotification OBJECT IDENTIFIER ::= { sleGponOnuFWAutoUpgradeModel 3 }


--   1.3.6.1.4.1.6296.101.23.9.3.3.1
-- 1.3.6.1.4.1.6296.101.23.9.3.3.1
		sleGponOnuFWAutoUpgradeModelProfileChanged NOTIFICATION-TYPE
			OBJECTS { sleGponOnuFWAutoUpgradeModelControlRequest, sleGponOnuFWAutoUpgradeModelControlTimeStamp, sleGponOnuFWAutoUpgradeModelControlReqResult, sleGponOnuFWAutoUpgradeModelControlName, sleGponOnuFWAutoUpgradeModelControlFWName,
				sleGponOnuFWAutoUpgradeModelControlMethod, sleGponOnuFWAutoUpgradeModelControlServerAddress, sleGponOnuFWAutoUpgradeModelControlUser, sleGponOnuFWAutoUpgradeModelControlPasswd, sleGponOnuFWAutoUpgradeModelControlFWTargetVersion
				 }
			STATUS current
			DESCRIPTION
				"Description."
			::= { sleGponOnuFWAutoUpgradeModelNotification 1 }


--   1.3.6.1.4.1.6296.101.23.9.3.3.2
-- 1.3.6.1.4.1.6296.101.23.9.3.3.2
		sleGponOnuFWAutoUpgradeModelDeleted NOTIFICATION-TYPE
			OBJECTS { sleGponOnuFWAutoUpgradeModelControlRequest, sleGponOnuFWAutoUpgradeModelControlTimeStamp, sleGponOnuFWAutoUpgradeModelControlReqResult, sleGponOnuFWAutoUpgradeModelControlName }
			STATUS current
			DESCRIPTION
				"Description."
			::= { sleGponOnuFWAutoUpgradeModelNotification 2 }


--   1.3.6.1.4.1.6296.101.23.9.3.3.3
-- 1.3.6.1.4.1.6296.101.23.9.3.3.3
		sleGponOnuFWAutoUpgradeModelModifyTargetVer NOTIFICATION-TYPE
			OBJECTS { sleGponOnuFWAutoUpgradeModelControlRequest, sleGponOnuFWAutoUpgradeModelControlTimeStamp, sleGponOnuFWAutoUpgradeModelControlReqResult, sleGponOnuFWAutoUpgradeModelControlName, sleGponOnuFWAutoUpgradeModelControlFWTargetVersion,
				sleGponOnuFWAutoUpgradeModelControlExclude }
			STATUS current
			DESCRIPTION
				"Description."
			::= { sleGponOnuFWAutoUpgradeModelNotification 3 }


--   1.3.6.1.4.1.6296.101.23.9.3.3.4
-- 1.3.6.1.4.1.6296.101.23.9.3.3.4
		sleGponOnuFWAutoUpgradeModelTargetVerDeleted NOTIFICATION-TYPE
			OBJECTS { sleGponOnuFWAutoUpgradeModelControlRequest, sleGponOnuFWAutoUpgradeModelControlTimeStamp, sleGponOnuFWAutoUpgradeModelControlReqResult, sleGponOnuFWAutoUpgradeModelControlName, sleGponOnuFWAutoUpgradeModelControlFWTargetVersion
				 }
			STATUS current
			DESCRIPTION
				"Description."
			::= { sleGponOnuFWAutoUpgradeModelNotification 4 }


--   1.3.6.1.4.1.6296.101.23.9.4
-- 1.3.6.1.4.1.6296.101.23.9.4
		sleGponOnuFWAutoUpgradeMTime OBJECT IDENTIFIER ::= { sleGponOnuFirmwareAutoUpgradeMgmt 4 }


--   1.3.6.1.4.1.6296.101.23.9.4.1
-- 1.3.6.1.4.1.6296.101.23.9.4.1
		sleGponOnuFWAutoUpgradeMTimeTable OBJECT-TYPE
			SYNTAX SEQUENCE OF SleGponOnuFWAutoUpgradeMTimeEntry
			MAX-ACCESS not-accessible
			STATUS current
			DESCRIPTION
				"sleGponOnuFWAutoUpgradeMTimeTable"
			::= { sleGponOnuFWAutoUpgradeMTime 1 }


--   1.3.6.1.4.1.6296.101.23.9.4.1.1
-- 1.3.6.1.4.1.6296.101.23.9.4.1.1
		sleGponOnuFWAutoUpgradeMTimeEntry OBJECT-TYPE
			SYNTAX SleGponOnuFWAutoUpgradeMTimeEntry
			MAX-ACCESS not-accessible
			STATUS current
			DESCRIPTION
				"key: sleGponOnuFWAutoUpgradeMTimeIndex"
			INDEX { sleGponOnuFWAutoUpgradeMTimeIndex }
			::= { sleGponOnuFWAutoUpgradeMTimeTable 1 }


		SleGponOnuFWAutoUpgradeMTimeEntry ::=
			SEQUENCE {
				sleGponOnuFWAutoUpgradeMTimeIndex
					Integer32,
				sleGponOnuFWAutoUpgradeMTimeStartTime
					INTEGER,
				sleGponOnuFWAutoUpgradeMTimeEndTime
					INTEGER,
				sleGponOnuFWAutoUpgradeMTimeModelName
					OCTET STRING,
				sleGponOnuFWAutoUpgradeMTimeRebootTime
					Integer32
			 }

--   1.3.6.1.4.1.6296.101.23.9.4.1.1.1
-- 1.3.6.1.4.1.6296.101.23.9.4.1.1.1
		sleGponOnuFWAutoUpgradeMTimeIndex OBJECT-TYPE
			SYNTAX Integer32 (1..65535)
			MAX-ACCESS read-only
			STATUS current
			DESCRIPTION
				"index"
			::= { sleGponOnuFWAutoUpgradeMTimeEntry 1 }


--   1.3.6.1.4.1.6296.101.23.9.4.1.1.2
-- 1.3.6.1.4.1.6296.101.23.9.4.1.1.2
		sleGponOnuFWAutoUpgradeMTimeStartTime OBJECT-TYPE
			SYNTAX INTEGER (-1 | 0..23)
			UNITS "1 hour"
			MAX-ACCESS read-only
			STATUS current
			DESCRIPTION
				"upgrade start time for model.
				(-1 is none-time : disable)"
			::= { sleGponOnuFWAutoUpgradeMTimeEntry 2 }


--   1.3.6.1.4.1.6296.101.23.9.4.1.1.3
-- 1.3.6.1.4.1.6296.101.23.9.4.1.1.3
		sleGponOnuFWAutoUpgradeMTimeEndTime OBJECT-TYPE
			SYNTAX INTEGER (-1 | 0..23)
			UNITS "1 hour"
			MAX-ACCESS read-only
			STATUS current
			DESCRIPTION
				"upgrade end time for model.
				(-1 is none-time : disable)"
			::= { sleGponOnuFWAutoUpgradeMTimeEntry 3 }


--   1.3.6.1.4.1.6296.101.23.9.4.1.1.4
-- 1.3.6.1.4.1.6296.101.23.9.4.1.1.4
		sleGponOnuFWAutoUpgradeMTimeModelName OBJECT-TYPE
			SYNTAX OCTET STRING (SIZE (1..128))
			MAX-ACCESS read-only
			STATUS current
			DESCRIPTION
				"Onu model name."
			::= { sleGponOnuFWAutoUpgradeMTimeEntry 4 }


--  1.3.6.1.4.1.6296.101.23.9.4.1.1.5
		sleGponOnuFWAutoUpgradeMTimeRebootTime OBJECT-TYPE
			SYNTAX Integer32 (-1 | 0..24)
			MAX-ACCESS read-only
			STATUS current
			DESCRIPTION
				"The reboot time (hour)
				-1: unused
				0~23: available values
				24: immediately"
			::= { sleGponOnuFWAutoUpgradeMTimeEntry 5 }


--   1.3.6.1.4.1.6296.101.23.9.4.2
-- 1.3.6.1.4.1.6296.101.23.9.4.2
		sleGponOnuFWAutoUpgradeMTimeControl OBJECT IDENTIFIER ::= { sleGponOnuFWAutoUpgradeMTime 2 }


--   1.3.6.1.4.1.6296.101.23.9.4.2.1
-- 1.3.6.1.4.1.6296.101.23.9.4.2.1
		sleGponOnuFWAutoUpgradeMTimeControlRequest OBJECT-TYPE
			SYNTAX INTEGER
				{
				setOnuFWAutoUpgradeMTime(1),
				destroyOnuAutoUpgradeMTime(2),
				setRebootTime(3)
				}
			MAX-ACCESS read-write
			STATUS current
			DESCRIPTION
				"The request of a user command"
			::= { sleGponOnuFWAutoUpgradeMTimeControl 1 }


--   1.3.6.1.4.1.6296.101.23.9.4.2.2
-- 1.3.6.1.4.1.6296.101.23.9.4.2.2
		sleGponOnuFWAutoUpgradeMTimeControlStatus OBJECT-TYPE
			SYNTAX SleControlStatusType
			MAX-ACCESS read-only
			STATUS current
			DESCRIPTION
				"The status of user command"
			::= { sleGponOnuFWAutoUpgradeMTimeControl 2 }


--   1.3.6.1.4.1.6296.101.23.9.4.2.3
-- 1.3.6.1.4.1.6296.101.23.9.4.2.3
		sleGponOnuFWAutoUpgradeMTimeControlTimer OBJECT-TYPE
			SYNTAX Gauge32
			MAX-ACCESS read-write
			STATUS current
			DESCRIPTION
				"The maximum time for the manager for a long running user command"
			::= { sleGponOnuFWAutoUpgradeMTimeControl 3 }


--   1.3.6.1.4.1.6296.101.23.9.4.2.4
-- 1.3.6.1.4.1.6296.101.23.9.4.2.4
		sleGponOnuFWAutoUpgradeMTimeControlTimeStamp OBJECT-TYPE
			SYNTAX TimeTicks
			MAX-ACCESS read-only
			STATUS current
			DESCRIPTION
				"The time stamp of the last command(end of command)"
			::= { sleGponOnuFWAutoUpgradeMTimeControl 4 }


--   1.3.6.1.4.1.6296.101.23.9.4.2.5
-- 1.3.6.1.4.1.6296.101.23.9.4.2.5
		sleGponOnuFWAutoUpgradeMTimeControlReqResult OBJECT-TYPE
			SYNTAX SleControlRequestResultType
			MAX-ACCESS read-only
			STATUS current
			DESCRIPTION
				"The result of the last user command"
			::= { sleGponOnuFWAutoUpgradeMTimeControl 5 }


--   1.3.6.1.4.1.6296.101.23.9.4.2.6
-- 1.3.6.1.4.1.6296.101.23.9.4.2.6
		sleGponOnuFWAutoUpgradeMTimeControlStartTime OBJECT-TYPE
			SYNTAX INTEGER (-1 | 0..23)
			UNITS "1 hour"
			MAX-ACCESS read-write
			STATUS current
			DESCRIPTION
				"Upgrade start time for model
				(-1 is none-time : disable)"
			::= { sleGponOnuFWAutoUpgradeMTimeControl 6 }


--   1.3.6.1.4.1.6296.101.23.9.4.2.7
-- 1.3.6.1.4.1.6296.101.23.9.4.2.7
		sleGponOnuFWAutoUpgradeMTimeControlEndTime OBJECT-TYPE
			SYNTAX INTEGER (-1 | 0..23)
			UNITS "1 hour"
			MAX-ACCESS read-write
			STATUS current
			DESCRIPTION
				"upgrade end time for model.
				(-1 is none-time : disable)"
			::= { sleGponOnuFWAutoUpgradeMTimeControl 7 }


--   1.3.6.1.4.1.6296.101.23.9.4.2.8
-- 1.3.6.1.4.1.6296.101.23.9.4.2.8
		sleGponOnuFWAutoUpgradeMTimeControlModelName OBJECT-TYPE
			SYNTAX OCTET STRING (SIZE (1..128))
			MAX-ACCESS read-write
			STATUS current
			DESCRIPTION
				"Onu model name."
			::= { sleGponOnuFWAutoUpgradeMTimeControl 8 }


--  1.3.6.1.4.1.6296.101.23.9.4.2.9
		sleGponOnuFWAutoUpgradeMTimeControlRebootTime OBJECT-TYPE
			SYNTAX Integer32 (-1 | 0..24)
			MAX-ACCESS read-write
			STATUS current
			DESCRIPTION
				"The reboot time (hour)
				-1: unused
				0~23: available values
				24: immediately
				"
			::= { sleGponOnuFWAutoUpgradeMTimeControl 9 }


--   1.3.6.1.4.1.6296.101.23.9.4.3
-- 1.3.6.1.4.1.6296.101.23.9.4.3
		sleGponOnuFWAutoUpgradeMTimeNotification OBJECT IDENTIFIER ::= { sleGponOnuFWAutoUpgradeMTime 3 }


--   1.3.6.1.4.1.6296.101.23.9.4.3.1
-- 1.3.6.1.4.1.6296.101.23.9.4.3.1
		sleGponOnuFWAutoUpgradeMTimeChanged NOTIFICATION-TYPE
			OBJECTS { sleGponOnuFWAutoUpgradeMTimeControlRequest, sleGponOnuFWAutoUpgradeMTimeControlTimeStamp, sleGponOnuFWAutoUpgradeMTimeControlReqResult, sleGponOnuFWAutoUpgradeMTimeControlStartTime, sleGponOnuFWAutoUpgradeMTimeControlEndTime,
				sleGponOnuFWAutoUpgradeMTimeControlModelName }
			STATUS current
			DESCRIPTION
				"Description."
			::= { sleGponOnuFWAutoUpgradeMTimeNotification 1 }


--   1.3.6.1.4.1.6296.101.23.9.4.3.2
-- 1.3.6.1.4.1.6296.101.23.9.4.3.2
		sleGponOnuFWAutoUpgradeMTimeDeleted NOTIFICATION-TYPE
			OBJECTS { sleGponOnuFWAutoUpgradeMTimeControlRequest, sleGponOnuFWAutoUpgradeMTimeControlTimeStamp, sleGponOnuFWAutoUpgradeMTimeControlReqResult, sleGponOnuFWAutoUpgradeMTimeControlModelName }
			STATUS current
			DESCRIPTION
				"Description."
			::= { sleGponOnuFWAutoUpgradeMTimeNotification 2 }


--  1.3.6.1.4.1.6296.101.23.9.4.3.3
		sleGponOnuFWAutoUpgradeMTimeRebootTimeChanged NOTIFICATION-TYPE
			OBJECTS { sleGponOnuFWAutoUpgradeMTimeControlRequest, sleGponOnuFWAutoUpgradeMTimeControlTimeStamp, sleGponOnuFWAutoUpgradeMTimeControlReqResult, sleGponOnuFWAutoUpgradeMTimeIndex, sleGponOnuFWAutoUpgradeMTimeControlRebootTime
				 }
			STATUS current
			DESCRIPTION
				"setRebootTime"
			::= { sleGponOnuFWAutoUpgradeMTimeNotification 3 }


--   1.3.6.1.4.1.6296.101.23.9.5
-- 1.3.6.1.4.1.6296.101.23.9.5
		sleGponOnuFWAutoUpgradeState OBJECT IDENTIFIER ::= { sleGponOnuFirmwareAutoUpgradeMgmt 5 }


--   1.3.6.1.4.1.6296.101.23.9.5.1
-- 1.3.6.1.4.1.6296.101.23.9.5.1
		sleGponOnuFWAutoUpgradeStateTable OBJECT-TYPE
			SYNTAX SEQUENCE OF SleGponOnuFWAutoUpgradeStateEntry
			MAX-ACCESS not-accessible
			STATUS current
			DESCRIPTION
				"sleGponOnuFWAutoUpgradeStateTable"
			::= { sleGponOnuFWAutoUpgradeState 1 }


--   1.3.6.1.4.1.6296.101.23.9.5.1.1
-- 1.3.6.1.4.1.6296.101.23.9.5.1.1
		sleGponOnuFWAutoUpgradeStateEntry OBJECT-TYPE
			SYNTAX SleGponOnuFWAutoUpgradeStateEntry
			MAX-ACCESS not-accessible
			STATUS current
			DESCRIPTION
				"key: sleGponOnuFWAutoUpgradeSIndex"
			INDEX { sleGponOnuFWAutoUpgradeSIndex }
			::= { sleGponOnuFWAutoUpgradeStateTable 1 }


		SleGponOnuFWAutoUpgradeStateEntry ::=
			SEQUENCE {
				sleGponOnuFWAutoUpgradeSIndex
					INTEGER,
				sleGponOnuFWAutoUpgradeSOltID
					INTEGER,
				sleGponOnuFWAutoUpgradeSOnuID
					INTEGER,
				sleGponOnuFWAutoUpgradeSModelName
					OCTET STRING,
				sleGponOnuFWAutoUpgradeSStatus
					INTEGER,
				sleGponOnuFWAutoUpgradeSFailCnt
					INTEGER,
				sleGponOnuFWAutoUpgradeSActiveVer
					OCTET STRING
			 }

--   1.3.6.1.4.1.6296.101.23.9.5.1.1.1
-- 1.3.6.1.4.1.6296.101.23.9.5.1.1.1
		sleGponOnuFWAutoUpgradeSIndex OBJECT-TYPE
			SYNTAX INTEGER (1..65535)
			MAX-ACCESS read-only
			STATUS current
			DESCRIPTION
				"Index."
			::= { sleGponOnuFWAutoUpgradeStateEntry 1 }


--   1.3.6.1.4.1.6296.101.23.9.5.1.1.2
-- 1.3.6.1.4.1.6296.101.23.9.5.1.1.2
		sleGponOnuFWAutoUpgradeSOltID OBJECT-TYPE
			SYNTAX INTEGER (1..65535)
			MAX-ACCESS read-only
			STATUS current
			DESCRIPTION
				"OLT ID."
			::= { sleGponOnuFWAutoUpgradeStateEntry 2 }


--   1.3.6.1.4.1.6296.101.23.9.5.1.1.3
-- 1.3.6.1.4.1.6296.101.23.9.5.1.1.3
		sleGponOnuFWAutoUpgradeSOnuID OBJECT-TYPE
			SYNTAX INTEGER (1..65535)
			MAX-ACCESS read-only
			STATUS current
			DESCRIPTION
				"ONU ID."
			::= { sleGponOnuFWAutoUpgradeStateEntry 3 }


--   1.3.6.1.4.1.6296.101.23.9.5.1.1.4
-- 1.3.6.1.4.1.6296.101.23.9.5.1.1.4
		sleGponOnuFWAutoUpgradeSModelName OBJECT-TYPE
			SYNTAX OCTET STRING (SIZE (1..128))
			MAX-ACCESS read-only
			STATUS current
			DESCRIPTION
				"Onu model name."
			::= { sleGponOnuFWAutoUpgradeStateEntry 4 }


--   1.3.6.1.4.1.6296.101.23.9.5.1.1.5
-- 1.3.6.1.4.1.6296.101.23.9.5.1.1.5
		sleGponOnuFWAutoUpgradeSStatus OBJECT-TYPE
			SYNTAX INTEGER
				{
				none(0),
				downloadProgress(1),
				downloadProgressforDevBusy(2),
				endDownloadForDevBusy(3),
				downloadComplete(4),
				downloadFail(5),
				commitWaitValid(6),
				commitProgress(7),
				commitProgressforDevBusy(8),
				commitFailForDevBusy(9),
				commitComplete(10),
				commitFail(11),
				changeActiveComplete(12),
				changeActiveFailforDevBusy(13),
				changeActiveFail(14),
				autoUpgradeResetWaiting(15),
				autoUpgradeFail(16),
				endDownloadSend(17),
				endDownloadComplete(18),
				bootloaderDownloadProgress(19),
				bootloaderDownloadDevBusy(20),
				bootloaderEndDownloadDevBusy(21),
				bootloaderDownloadComplete(22),
				bootloaderDownloadFail(23),
				bootloaderEndDownloadRequest(24),
				bootloaderEndDownloadComplete(25),
				autoUpgradeComplete(26),
				downloadWait(27),
				unknown(255)
				}
			MAX-ACCESS read-only
			STATUS current
			DESCRIPTION
				"Onu auto upgrade status."
			::= { sleGponOnuFWAutoUpgradeStateEntry 5 }


--   1.3.6.1.4.1.6296.101.23.9.5.1.1.6
-- 1.3.6.1.4.1.6296.101.23.9.5.1.1.6
		sleGponOnuFWAutoUpgradeSFailCnt OBJECT-TYPE
			SYNTAX INTEGER (1..65535)
			MAX-ACCESS read-only
			STATUS current
			DESCRIPTION
				"Auto upgrade fail count"
			::= { sleGponOnuFWAutoUpgradeStateEntry 6 }


--   1.3.6.1.4.1.6296.101.23.9.5.1.1.7
-- 1.3.6.1.4.1.6296.101.23.9.5.1.1.7
		sleGponOnuFWAutoUpgradeSActiveVer OBJECT-TYPE
			SYNTAX OCTET STRING (SIZE (1..20))
			MAX-ACCESS read-only
			STATUS current
			DESCRIPTION
				"Active version of onu."
			::= { sleGponOnuFWAutoUpgradeStateEntry 7 }


--   1.3.6.1.4.1.6296.101.23.9.6
-- 1.3.6.1.4.1.6296.101.23.9.6
		sleGponOnuFWAutoUpgradeBase OBJECT IDENTIFIER ::= { sleGponOnuFirmwareAutoUpgradeMgmt 6 }


--   1.3.6.1.4.1.6296.101.23.9.6.1
-- 1.3.6.1.4.1.6296.101.23.9.6.1
		sleGponOnuFWAutoUpgradeBaseInfo OBJECT IDENTIFIER ::= { sleGponOnuFWAutoUpgradeBase 1 }


--   1.3.6.1.4.1.6296.101.23.9.6.1.1
-- 1.3.6.1.4.1.6296.101.23.9.6.1.1
		sleGponOnuFWAutoUpgradeBaseRetryCounts OBJECT-TYPE
			SYNTAX Integer32
			MAX-ACCESS read-only
			STATUS current
			DESCRIPTION
				"The retry count."
			::= { sleGponOnuFWAutoUpgradeBaseInfo 1 }


--   1.3.6.1.4.1.6296.101.23.9.6.2
-- 1.3.6.1.4.1.6296.101.23.9.6.2
		sleGponOnuFWAutoUpgradeBaseControl OBJECT IDENTIFIER ::= { sleGponOnuFWAutoUpgradeBase 2 }


--   1.3.6.1.4.1.6296.101.23.9.6.2.1
-- 1.3.6.1.4.1.6296.101.23.9.6.2.1
		sleGponOnuFWAutoUpgradeControlBaseRequest OBJECT-TYPE
			SYNTAX INTEGER { setRetryCount(1) }
			MAX-ACCESS read-write
			STATUS current
			DESCRIPTION
				"The request of a user command"
			::= { sleGponOnuFWAutoUpgradeBaseControl 1 }


--   1.3.6.1.4.1.6296.101.23.9.6.2.2
-- 1.3.6.1.4.1.6296.101.23.9.6.2.2
		sleGponOnuFWAutoUpgradeControlBaseStatus OBJECT-TYPE
			SYNTAX SleControlStatusType
			MAX-ACCESS read-write
			STATUS current
			DESCRIPTION
				"The status of user command"
			::= { sleGponOnuFWAutoUpgradeBaseControl 2 }


--   1.3.6.1.4.1.6296.101.23.9.6.2.3
-- 1.3.6.1.4.1.6296.101.23.9.6.2.3
		sleGponOnuFWAutoUpgradeControlBaseTimer OBJECT-TYPE
			SYNTAX Gauge32
			MAX-ACCESS read-only
			STATUS current
			DESCRIPTION
				"The maximum time for the manager for a long running user command"
			::= { sleGponOnuFWAutoUpgradeBaseControl 3 }


--   1.3.6.1.4.1.6296.101.23.9.6.2.4
-- 1.3.6.1.4.1.6296.101.23.9.6.2.4
		sleGponOnuFWAutoUpgradeControlBaseTimeStamp OBJECT-TYPE
			SYNTAX TimeTicks
			MAX-ACCESS read-write
			STATUS current
			DESCRIPTION
				"The time stamp of the last command(end of command)"
			::= { sleGponOnuFWAutoUpgradeBaseControl 4 }


--   1.3.6.1.4.1.6296.101.23.9.6.2.5
-- 1.3.6.1.4.1.6296.101.23.9.6.2.5
		sleGponOnuFWAutoUpgradeControlBaseReqResult OBJECT-TYPE
			SYNTAX SleControlRequestResultType
			MAX-ACCESS read-only
			STATUS current
			DESCRIPTION
				"The result of the last user command"
			::= { sleGponOnuFWAutoUpgradeBaseControl 5 }


--
-- 1.3.6.1.4.1.6296.101.23.9.6.2.6
-- 1.3.6.1.4.1.6296.101.23.9.6.2.6
		sleGponOnuFWAutoUpgradeControlBaseCount OBJECT-TYPE
			SYNTAX INTEGER (3..10)
			MAX-ACCESS read-write
			STATUS current
			DESCRIPTION
				"The retry count."
			::= { sleGponOnuFWAutoUpgradeBaseControl 6 }


--   1.3.6.1.4.1.6296.101.23.9.6.3
-- 1.3.6.1.4.1.6296.101.23.9.6.3
		sleGponOnuFWAutoUpgradeBaseNotification OBJECT IDENTIFIER ::= { sleGponOnuFWAutoUpgradeBase 3 }


--   1.3.6.1.4.1.6296.101.23.9.6.3.1
-- 1.3.6.1.4.1.6296.101.23.9.6.3.1
		sleGponOnuFWAutoUpgradeBaseRetryCountChanged NOTIFICATION-TYPE
			OBJECTS { sleGponOnuFWAutoUpgradeControlBaseRequest, sleGponOnuFWAutoUpgradeControlBaseTimeStamp, sleGponOnuFWAutoUpgradeControlBaseReqResult, sleGponOnuFWAutoUpgradeControlBaseCount }
			STATUS current
			DESCRIPTION
				"Description."
			::= { sleGponOnuFWAutoUpgradeBaseNotification 1 }


--   1.3.6.1.4.1.6296.101.23.10
-- 1.3.6.1.4.1.6296.101.23.10
		sleGponOntFirmware OBJECT IDENTIFIER ::= { sleGpon 10 }


--   1.3.6.1.4.1.6296.101.23.10.1
-- 1.3.6.1.4.1.6296.101.23.10.1
		sleGponOntFirmwareTable OBJECT-TYPE
			SYNTAX SEQUENCE OF SleGponOntFirmwareEntry
			MAX-ACCESS not-accessible
			STATUS current
			DESCRIPTION
				"sleGponOntFirmwareTable"
			::= { sleGponOntFirmware 1 }


--   1.3.6.1.4.1.6296.101.23.10.1.1
-- 1.3.6.1.4.1.6296.101.23.10.1.1
		sleGponOntFirmwareEntry OBJECT-TYPE
			SYNTAX SleGponOntFirmwareEntry
			MAX-ACCESS not-accessible
			STATUS current
			DESCRIPTION
				"key: sleGponOntFirmwareIndex"
			INDEX { sleGponOntFirmwareIndex }
			::= { sleGponOntFirmwareTable 1 }


		SleGponOntFirmwareEntry ::=
			SEQUENCE {
				sleGponOntFirmwareIndex
					Integer32,
				sleGponOntFirmwareType
					INTEGER,
				sleGponOntFirmwareName
					OCTET STRING,
				sleGponOntiFirmwareSize
					Integer32,
				sleGponOntFirmwareMd5
					OCTET STRING
			 }

--   1.3.6.1.4.1.6296.101.23.10.1.1.1
-- 1.3.6.1.4.1.6296.101.23.10.1.1.1
		sleGponOntFirmwareIndex OBJECT-TYPE
			SYNTAX Integer32 (1..65535)
			MAX-ACCESS read-only
			STATUS current
			DESCRIPTION
				"Ont Firmware Index."
			::= { sleGponOntFirmwareEntry 1 }


--   1.3.6.1.4.1.6296.101.23.10.1.1.2
-- 1.3.6.1.4.1.6296.101.23.10.1.1.2
		sleGponOntFirmwareType OBJECT-TYPE
			SYNTAX INTEGER
				{
				os(1),
				bootloader(2),
				unknown(255)
				}
			MAX-ACCESS read-only
			STATUS current
			DESCRIPTION
				"Ont Firmware type."
			::= { sleGponOntFirmwareEntry 2 }


--   1.3.6.1.4.1.6296.101.23.10.1.1.3
-- 1.3.6.1.4.1.6296.101.23.10.1.1.3
		sleGponOntFirmwareName OBJECT-TYPE
			SYNTAX OCTET STRING
			MAX-ACCESS read-only
			STATUS current
			DESCRIPTION
				"Ont Firmware name."
			::= { sleGponOntFirmwareEntry 3 }


--   1.3.6.1.4.1.6296.101.23.10.1.1.4
-- 1.3.6.1.4.1.6296.101.23.10.1.1.4
		sleGponOntiFirmwareSize OBJECT-TYPE
			SYNTAX Integer32
			MAX-ACCESS read-only
			STATUS current
			DESCRIPTION
				"Ont Firmware size."
			::= { sleGponOntFirmwareEntry 4 }


--   1.3.6.1.4.1.6296.101.23.10.1.1.5
-- 1.3.6.1.4.1.6296.101.23.10.1.1.5
		sleGponOntFirmwareMd5 OBJECT-TYPE
			SYNTAX OCTET STRING
			MAX-ACCESS read-only
			STATUS current
			DESCRIPTION
				"Ont Firmware md5 sum."
			::= { sleGponOntFirmwareEntry 5 }


--   1.3.6.1.4.1.6296.101.23.10.2
-- 1.3.6.1.4.1.6296.101.23.10.2
		sleGponOntFirmwareOntTable OBJECT-TYPE
			SYNTAX SEQUENCE OF SleGponOntFirmwareOntEntry
			MAX-ACCESS not-accessible
			STATUS current
			DESCRIPTION
				"sleGponOntFirmwareOntTable"
			::= { sleGponOntFirmware 2 }


--   1.3.6.1.4.1.6296.101.23.10.2.1
-- 1.3.6.1.4.1.6296.101.23.10.2.1
		sleGponOntFirmwareOntEntry OBJECT-TYPE
			SYNTAX SleGponOntFirmwareOntEntry
			MAX-ACCESS not-accessible
			STATUS current
			DESCRIPTION
				"key: sleGponOntFirmwareOltId, sleGponOntFirmwareOntId"
			INDEX { sleGponOntFirmwareOltId, sleGponOntFirmwareOntId }
			::= { sleGponOntFirmwareOntTable 1 }


		SleGponOntFirmwareOntEntry ::=
			SEQUENCE {
				sleGponOntFirmwareOltId
					Integer32,
				sleGponOntFirmwareOntId
					Integer32,
				sleGponOntFirmwareOntOs1Ver
					OCTET STRING,
				sleGponOntFirmwareOntOs2Ver
					OCTET STRING,
				sleGponOntFirmwareOntBLVer
					OCTET STRING,
				sleGponOntFirmeareOntDefaultOS
					INTEGER,
				sleGponOntFirmeareOntRunningOS
					INTEGER,
				sleGponOntFirmwareOntGponOs1Ver
					OCTET STRING,
				sleGponOntFirmwareOntGponOs2Ver
					OCTET STRING,
				sleGponOntFirmwareOntOsStatus
					INTEGER,
				sleGponOntFirmwareOntBLStatus
					INTEGER,
				sleGponOntFirmwareOsUpgrdStatus
					INTEGER,
				sleGponOntFirmwareOsUpgrdResult
					INTEGER,
				sleGponOntFirmwareBLUpgrdStatus
					INTEGER,
				sleGponOntFirmwareBLUpgrdResult
					INTEGER
			 }

--   1.3.6.1.4.1.6296.101.23.10.2.1.1
-- 1.3.6.1.4.1.6296.101.23.10.2.1.1
		sleGponOntFirmwareOltId OBJECT-TYPE
			SYNTAX Integer32 (1..2147483647)
			MAX-ACCESS read-only
			STATUS current
			DESCRIPTION
				"Ont-Firmware OLT Index."
			::= { sleGponOntFirmwareOntEntry 1 }


--   1.3.6.1.4.1.6296.101.23.10.2.1.2
-- 1.3.6.1.4.1.6296.101.23.10.2.1.2
		sleGponOntFirmwareOntId OBJECT-TYPE
			SYNTAX Integer32 (1..65535)
			MAX-ACCESS read-only
			STATUS current
			DESCRIPTION
				"Ont-Firmware ONT Index."
			::= { sleGponOntFirmwareOntEntry 2 }


--   1.3.6.1.4.1.6296.101.23.10.2.1.3
-- 1.3.6.1.4.1.6296.101.23.10.2.1.3
		sleGponOntFirmwareOntOs1Ver OBJECT-TYPE
			SYNTAX OCTET STRING
			MAX-ACCESS read-only
			STATUS current
			DESCRIPTION
				"Ont-Firmware OS1 version."
			::= { sleGponOntFirmwareOntEntry 3 }


--   1.3.6.1.4.1.6296.101.23.10.2.1.4
-- 1.3.6.1.4.1.6296.101.23.10.2.1.4
		sleGponOntFirmwareOntOs2Ver OBJECT-TYPE
			SYNTAX OCTET STRING
			MAX-ACCESS read-only
			STATUS current
			DESCRIPTION
				"Ont-Firmware OS2 version."
			::= { sleGponOntFirmwareOntEntry 4 }


--   1.3.6.1.4.1.6296.101.23.10.2.1.5
-- 1.3.6.1.4.1.6296.101.23.10.2.1.5
		sleGponOntFirmwareOntBLVer OBJECT-TYPE
			SYNTAX OCTET STRING
			MAX-ACCESS read-only
			STATUS current
			DESCRIPTION
				"Ont-Firmware ONT bootloader name."
			::= { sleGponOntFirmwareOntEntry 5 }


--   1.3.6.1.4.1.6296.101.23.10.2.1.6
-- 1.3.6.1.4.1.6296.101.23.10.2.1.6
		sleGponOntFirmeareOntDefaultOS OBJECT-TYPE
			SYNTAX INTEGER
				{
				os1(1),
				os2(2)
				}
			MAX-ACCESS read-only
			STATUS current
			DESCRIPTION
				"Ont-Firmware ONT default-os."
			::= { sleGponOntFirmwareOntEntry 6 }


--   1.3.6.1.4.1.6296.101.23.10.2.1.7
-- 1.3.6.1.4.1.6296.101.23.10.2.1.7
		sleGponOntFirmeareOntRunningOS OBJECT-TYPE
			SYNTAX INTEGER
				{
				os1(1),
				os2(2)
				}
			MAX-ACCESS read-only
			STATUS current
			DESCRIPTION
				"Ont-Firmware ONT running-os."
			::= { sleGponOntFirmwareOntEntry 7 }


--   1.3.6.1.4.1.6296.101.23.10.2.1.8
-- 1.3.6.1.4.1.6296.101.23.10.2.1.8
		sleGponOntFirmwareOntGponOs1Ver OBJECT-TYPE
			SYNTAX OCTET STRING
			MAX-ACCESS read-only
			STATUS current
			DESCRIPTION
				"Ont-Firmware GPON OS1 version."
			::= { sleGponOntFirmwareOntEntry 8 }


--   1.3.6.1.4.1.6296.101.23.10.2.1.9
-- 1.3.6.1.4.1.6296.101.23.10.2.1.9
		sleGponOntFirmwareOntGponOs2Ver OBJECT-TYPE
			SYNTAX OCTET STRING
			MAX-ACCESS read-only
			STATUS current
			DESCRIPTION
				"Ont-Firmware GPON OS2 version."
			::= { sleGponOntFirmwareOntEntry 9 }


--   1.3.6.1.4.1.6296.101.23.10.2.1.10
-- 1.3.6.1.4.1.6296.101.23.10.2.1.10
		sleGponOntFirmwareOntOsStatus OBJECT-TYPE
			SYNTAX INTEGER
				{
				notupdatable(1),
				updatable(2),
				updating(3),
				updated(4)
				}
			MAX-ACCESS read-only
			STATUS current
			DESCRIPTION
				"Ont-Firmware OS status."
			::= { sleGponOntFirmwareOntEntry 10 }


--   1.3.6.1.4.1.6296.101.23.10.2.1.11
-- 1.3.6.1.4.1.6296.101.23.10.2.1.11
		sleGponOntFirmwareOntBLStatus OBJECT-TYPE
			SYNTAX INTEGER
				{
				notupdatable(1),
				updatable(2),
				updating(3),
				updated(4)
				}
			MAX-ACCESS read-only
			STATUS current
			DESCRIPTION
				"Ont-Firmware BL status."
			::= { sleGponOntFirmwareOntEntry 11 }


--   1.3.6.1.4.1.6296.101.23.10.2.1.12
-- 1.3.6.1.4.1.6296.101.23.10.2.1.12
		sleGponOntFirmwareOsUpgrdStatus OBJECT-TYPE
			SYNTAX INTEGER
				{
				none(1),
				idle(2),
				downloadImage(3),
				uncompress(4),
				downloadBL(5),
				updating(6),
				abort(7),
				rollback(8)
				}
			MAX-ACCESS read-only
			STATUS current
			DESCRIPTION
				"Ont-Firmware Upgrade status."
			::= { sleGponOntFirmwareOntEntry 12 }


--   1.3.6.1.4.1.6296.101.23.10.2.1.13
-- 1.3.6.1.4.1.6296.101.23.10.2.1.13
		sleGponOntFirmwareOsUpgrdResult OBJECT-TYPE
			SYNTAX INTEGER (1..65535)
			MAX-ACCESS read-only
			STATUS current
			DESCRIPTION
				"Ont-Firmware Upgrade result.
				Value   Meaning
				------------------
				100	Success
				101	Upgrade process aborted
				102	Transfer fail on Bootloader
				103	Transfer fail on AG
				104	Transfer fail on BL
				105	Cannot find a file
				106	ERROR_ONT_FTP_CON_FAIL_AG
				107	ERROR_ONT_FTP_CON_FAIL_BL
				108	ERROR_ONT_CANNOT_OPEN_FILE_AG
				109	ERROR_ONT_INSUFFICIENT_MEM_AG
				110	Image checksum error
				111	ERROR_ONT_INSUFFICIENT_MEM_AG
				112	ERROR_ONT_INSUFFICIENT_MEM_BL
				113	Image is corrupted
				114	Image is corrupted on AG
				115	Image is corrupted on BL
				116	ERROR_ONT_TWO_FILES_NO_EXIST
				117	Write image is fail on Bootloader
				118	Write image is fail on AG
				119	Write image is fail on BL
				120	Rollback image is fail
				121	ERROR_ONT_ROLLBACK
				122	ERROR_ONT_TIMEOUT
				123	Download timeout on Bootloader
				124	Donwload timeout on AG
				125	Download timeout on BL
				126	Uncompress timeout
				127	Write timeout on Bootloader
				128	Write timeout on AG
				129	Write timeout on BL
				130	Rollback timeout on BL
				131	Unknown error on Bootloader
				132	Unknown error on AG
				133	Unknown error on BL"
			::= { sleGponOntFirmwareOntEntry 13 }


--   1.3.6.1.4.1.6296.101.23.10.2.1.14
-- 1.3.6.1.4.1.6296.101.23.10.2.1.14
		sleGponOntFirmwareBLUpgrdStatus OBJECT-TYPE
			SYNTAX INTEGER
				{
				none(1),
				idle(2),
				downloadImage(3),
				uncompress(4),
				downloadBL(5),
				updating(6),
				abort(7),
				rollback(8)
				}
			MAX-ACCESS read-only
			STATUS current
			DESCRIPTION
				"Ont-Firmware BL Upgrade status."
			::= { sleGponOntFirmwareOntEntry 14 }


--   1.3.6.1.4.1.6296.101.23.10.2.1.15
-- 1.3.6.1.4.1.6296.101.23.10.2.1.15
		sleGponOntFirmwareBLUpgrdResult OBJECT-TYPE
			SYNTAX INTEGER (1..65535)
			MAX-ACCESS read-only
			STATUS current
			DESCRIPTION
				"Ont-Firmware Upgrade result.
				Value   Meaning
				------------------
				100	Success
				101	Upgrade process aborted
				102	Transfer fail on Bootloader
				103	Transfer fail on AG
				104	Transfer fail on BL
				105	Cannot find a file
				106	ERROR_ONT_FTP_CON_FAIL_AG
				107	ERROR_ONT_FTP_CON_FAIL_BL
				108	ERROR_ONT_CANNOT_OPEN_FILE_AG
				109	ERROR_ONT_INSUFFICIENT_MEM_AG
				110	Image checksum error
				111	ERROR_ONT_INSUFFICIENT_MEM_AG
				112	ERROR_ONT_INSUFFICIENT_MEM_BL
				113	Image is corrupted
				114	Image is corrupted on AG
				115	Image is corrupted on BL
				116	ERROR_ONT_TWO_FILES_NO_EXIST
				117	Write image is fail on Bootloader
				118	Write image is fail on AG
				119	Write image is fail on BL
				120	Rollback image is fail
				121	ERROR_ONT_ROLLBACK
				122	ERROR_ONT_TIMEOUT
				123	Download timeout on Bootloader
				124	Donwload timeout on AG
				125	Download timeout on BL
				126	Uncompress timeout
				127	Write timeout on Bootloader
				128	Write timeout on AG
				129	Write timeout on BL
				130	Rollback timeout on BL
				131	Unknown error on Bootloader
				132	Unknown error on AG
				133	Unknown error on BL"
			::= { sleGponOntFirmwareOntEntry 15 }


--   1.3.6.1.4.1.6296.101.23.10.3
-- 1.3.6.1.4.1.6296.101.23.10.3
		sleGponOntFirmwareControl OBJECT IDENTIFIER ::= { sleGponOntFirmware 3 }


--   1.3.6.1.4.1.6296.101.23.10.3.1
-- 1.3.6.1.4.1.6296.101.23.10.3.1
		sleGponOntFirmwareControlReqest OBJECT-TYPE
			SYNTAX INTEGER
				{
				setGponOntFwDownload(1),
				setGponOntFwUpgrade(2),
				setGponOntReset(3),
				deleteGponOntFw(4),
				deleteGponOntFwAll(5)
				}
			MAX-ACCESS read-write
			STATUS current
			DESCRIPTION
				"The request of a user command"
			::= { sleGponOntFirmwareControl 1 }


--   1.3.6.1.4.1.6296.101.23.10.3.2
-- 1.3.6.1.4.1.6296.101.23.10.3.2
		sleGponOntFirmwareControlStatus OBJECT-TYPE
			SYNTAX SleControlStatusType
			MAX-ACCESS read-only
			STATUS current
			DESCRIPTION
				"The status of user command"
			::= { sleGponOntFirmwareControl 2 }


--   1.3.6.1.4.1.6296.101.23.10.3.3
-- 1.3.6.1.4.1.6296.101.23.10.3.3
		sleGponOntFirmwareControlTimer OBJECT-TYPE
			SYNTAX Gauge32
			MAX-ACCESS read-write
			STATUS current
			DESCRIPTION
				"The maximum time for the manager for a long running user command"
			::= { sleGponOntFirmwareControl 3 }


--   1.3.6.1.4.1.6296.101.23.10.3.4
-- 1.3.6.1.4.1.6296.101.23.10.3.4
		sleGponOntFirmwareControlTimeStamp OBJECT-TYPE
			SYNTAX TimeTicks
			MAX-ACCESS read-only
			STATUS current
			DESCRIPTION
				"The time stamp of the last command(end of command)"
			::= { sleGponOntFirmwareControl 4 }


--   1.3.6.1.4.1.6296.101.23.10.3.5
-- 1.3.6.1.4.1.6296.101.23.10.3.5
		sleGponOntFirmwareControlReqResult OBJECT-TYPE
			SYNTAX SleControlRequestResultType
			MAX-ACCESS read-only
			STATUS current
			DESCRIPTION
				"The result of the last user command"
			::= { sleGponOntFirmwareControl 5 }


		sleGponOntFirmwareControlOltId OBJECT-TYPE
			SYNTAX INTEGER (1..2147483647)
			MAX-ACCESS read-write
			STATUS current
			DESCRIPTION
				"Ont-Firmware OLT index."
			::= { sleGponOntFirmwareControl 6 }


--   1.3.6.1.4.1.6296.101.23.10.3.7
-- 1.3.6.1.4.1.6296.101.23.10.3.7
		sleGponOntFirmwareControlOntId OBJECT-TYPE
			SYNTAX INTEGER (1..65535)
			MAX-ACCESS read-write
			STATUS current
			DESCRIPTION
				"Ont-Firmware ONT index."
			::= { sleGponOntFirmwareControl 7 }


--   1.3.6.1.4.1.6296.101.23.10.3.8
-- 1.3.6.1.4.1.6296.101.23.10.3.8
		sleGponOntFirmwareControlType OBJECT-TYPE
			SYNTAX INTEGER
				{
				os(1),
				bootloader(2)
				}
			MAX-ACCESS read-write
			STATUS current
			DESCRIPTION
				"Ont Firmware type."
			::= { sleGponOntFirmwareControl 8 }


--   1.3.6.1.4.1.6296.101.23.10.3.9
-- 1.3.6.1.4.1.6296.101.23.10.3.9
		sleGponOntFirmwareControlFwName OBJECT-TYPE
			SYNTAX OCTET STRING
			MAX-ACCESS read-write
			STATUS current
			DESCRIPTION
				"Ont-Firmware Firmware name."
			::= { sleGponOntFirmwareControl 9 }


--   1.3.6.1.4.1.6296.101.23.10.3.10
-- 1.3.6.1.4.1.6296.101.23.10.3.10
		sleGponOntFirmwareControlMethod OBJECT-TYPE
			SYNTAX INTEGER
				{
				ftp(1),
				tftp(2)
				}
			MAX-ACCESS read-write
			STATUS current
			DESCRIPTION
				"Ont-Firmware transmission method."
			::= { sleGponOntFirmwareControl 10 }


--   1.3.6.1.4.1.6296.101.23.10.3.11
-- 1.3.6.1.4.1.6296.101.23.10.3.11
		sleGponOntFirmwareControlServer OBJECT-TYPE
			SYNTAX IpAddress
			MAX-ACCESS read-write
			STATUS current
			DESCRIPTION
				"Ont-Firmware server address."
			::= { sleGponOntFirmwareControl 11 }


--   1.3.6.1.4.1.6296.101.23.10.3.12
-- 1.3.6.1.4.1.6296.101.23.10.3.12
		sleGponOntFirmwareControlUser OBJECT-TYPE
			SYNTAX OCTET STRING
			MAX-ACCESS read-write
			STATUS current
			DESCRIPTION
				"Ont-Firmware user name."
			::= { sleGponOntFirmwareControl 12 }


--   1.3.6.1.4.1.6296.101.23.10.3.13
-- 1.3.6.1.4.1.6296.101.23.10.3.13
		sleGponOntFirmwareControlPasswd OBJECT-TYPE
			SYNTAX OCTET STRING
			MAX-ACCESS read-write
			STATUS current
			DESCRIPTION
				"Ont-Firmware user password."
			::= { sleGponOntFirmwareControl 13 }


--   1.3.6.1.4.1.6296.101.23.10.3.14
-- 1.3.6.1.4.1.6296.101.23.10.3.14
		sleGponOntFirmwareControlOnuId OBJECT-TYPE
			SYNTAX Integer32
			MAX-ACCESS read-only
			STATUS current
			DESCRIPTION
				"The ONU id"
			::= { sleGponOntFirmwareControl 14 }


--   1.3.6.1.4.1.6296.101.23.10.4
-- 1.3.6.1.4.1.6296.101.23.10.4
		sleGponOntFirmwareNotification OBJECT IDENTIFIER ::= { sleGponOntFirmware 4 }


--   1.3.6.1.4.1.6296.101.23.10.4.1
-- 1.3.6.1.4.1.6296.101.23.10.4.1
		gponOntFwDownloaded NOTIFICATION-TYPE
			OBJECTS { sleGponOntFirmwareControlReqest, sleGponOntFirmwareControlTimeStamp, sleGponOntFirmwareControlReqResult, sleGponOntFirmwareControlType, sleGponOntFirmwareControlFwName,
				sleGponOntFirmwareControlMethod, sleGponOntFirmwareControlServer, sleGponOntFirmwareControlUser, sleGponOntFirmwareControlPasswd }
			STATUS current
			DESCRIPTION
				"Description."
			::= { sleGponOntFirmwareNotification 1 }


--
-- 1.3.6.1.4.1.6296.101.23.10.4.2
-- 1.3.6.1.4.1.6296.101.23.10.4.2
		gponOntFwUpgraded NOTIFICATION-TYPE
			OBJECTS { sleGponOntFirmwareControlReqest, sleGponOntFirmwareControlTimeStamp, sleGponOntFirmwareControlReqResult, sleGponOntFirmwareControlOltId, sleGponOntFirmwareControlOntId,
				sleGponOntFirmwareControlFwName }
			STATUS current
			DESCRIPTION
				"Description."
			::= { sleGponOntFirmwareNotification 2 }


--   1.3.6.1.4.1.6296.101.23.10.4.3
-- 1.3.6.1.4.1.6296.101.23.10.4.3
		gponOntFwOntReseted NOTIFICATION-TYPE
			OBJECTS { sleGponOntFirmwareControlReqest, sleGponOntFirmwareControlTimeStamp, sleGponOntFirmwareControlReqResult, sleGponOntFirmwareControlOltId, sleGponOntFirmwareControlOntId
				 }
			STATUS current
			DESCRIPTION
				"Description."
			::= { sleGponOntFirmwareNotification 3 }


--   1.3.6.1.4.1.6296.101.23.10.4.4
-- 1.3.6.1.4.1.6296.101.23.10.4.4
		gponOntFwDeleted NOTIFICATION-TYPE
			OBJECTS { sleGponOntFirmwareControlReqest, sleGponOntFirmwareControlTimeStamp, sleGponOntFirmwareControlReqResult, sleGponOntFirmwareControlFwName }
			STATUS current
			DESCRIPTION
				"Description."
			::= { sleGponOntFirmwareNotification 4 }


--   1.3.6.1.4.1.6296.101.23.10.4.5
-- 1.3.6.1.4.1.6296.101.23.10.4.5
		gponOntFwDeleteAll NOTIFICATION-TYPE
			OBJECTS { sleGponOntFirmwareControlReqest, sleGponOntFirmwareControlTimeStamp, sleGponOntFirmwareControlReqResult }
			STATUS current
			DESCRIPTION
				"Description."
			::= { sleGponOntFirmwareNotification 5 }


--   1.3.6.1.4.1.6296.101.23.11
-- 1.3.6.1.4.1.6296.101.23.11
		sleGponRedundancy OBJECT IDENTIFIER ::= { sleGpon 11 }


--   1.3.6.1.4.1.6296.101.23.11.1
-- 1.3.6.1.4.1.6296.101.23.11.1
		sleGponRedGroupTable OBJECT-TYPE
			SYNTAX SEQUENCE OF SleGponRedGroupEntry
			MAX-ACCESS not-accessible
			STATUS current
			DESCRIPTION
				"sleGponRedGroupTable"
			::= { sleGponRedundancy 1 }


--   1.3.6.1.4.1.6296.101.23.11.1.1
-- 1.3.6.1.4.1.6296.101.23.11.1.1
		sleGponRedGroupEntry OBJECT-TYPE
			SYNTAX SleGponRedGroupEntry
			MAX-ACCESS not-accessible
			STATUS current
			DESCRIPTION
				"key: sleGponRedGroupIndex"
			INDEX { sleGponRedGroupIndex }
			::= { sleGponRedGroupTable 1 }


		SleGponRedGroupEntry ::=
			SEQUENCE {
				sleGponRedGroupIndex
					Integer32,
				sleGponRedGroupOltAIndex
					Integer32,
				sleGponRedGroupOltAStatus
					INTEGER,
				sleGponRedGroupOltBIndex
					Integer32,
				sleGponRedGroupOltBStatus
					INTEGER,
				sleGponRedLastReason
					INTEGER,
				sleGponRedGroupStandbyLinkStatus
					INTEGER,
				sleGponRedGroupSlaveOltAdminStatus
					INTEGER,
				sleGponRedGroupTrigger
					BITS,
				sleGponRedGroupDbSyncStatus
					INTEGER,
				sleGponRedGroupStandbyActTriggerTime
					Integer32
			 }

--   1.3.6.1.4.1.6296.101.23.11.1.1.1
-- 1.3.6.1.4.1.6296.101.23.11.1.1.1
		sleGponRedGroupIndex OBJECT-TYPE
			SYNTAX Integer32 (1..65535)
			MAX-ACCESS read-only
			STATUS current
			DESCRIPTION
				"Gpon redundancy group-id."
			::= { sleGponRedGroupEntry 1 }


		sleGponRedGroupOltAIndex OBJECT-TYPE
			SYNTAX Integer32 (1..2147483647)
			MAX-ACCESS read-only
			STATUS current
			DESCRIPTION
				"Gpon redundancy Olt-A index."
			::= { sleGponRedGroupEntry 2 }


--   1.3.6.1.4.1.6296.101.23.11.1.1.3
-- 1.3.6.1.4.1.6296.101.23.11.1.1.3
		sleGponRedGroupOltAStatus OBJECT-TYPE
			SYNTAX INTEGER
				{
				working(1),
				standby(2),
				progress(3),
				waiting(4),
				workingPending(5),
				standbyPending(6),
				unknown(255)
				}
			MAX-ACCESS read-only
			STATUS current
			DESCRIPTION
				"Gpon redundancy Olt-A status."
			::= { sleGponRedGroupEntry 3 }


		sleGponRedGroupOltBIndex OBJECT-TYPE
			SYNTAX Integer32 (1..2147483647)
			MAX-ACCESS read-only
			STATUS current
			DESCRIPTION
				"Gpon redundancy Olt-B index."
			::= { sleGponRedGroupEntry 4 }


--   1.3.6.1.4.1.6296.101.23.11.1.1.5
-- 1.3.6.1.4.1.6296.101.23.11.1.1.5
		sleGponRedGroupOltBStatus OBJECT-TYPE
			SYNTAX INTEGER
				{
				working(1),
				standby(2),
				progress(3),
				waiting(4),
				workingPending(5),
				standbyPending(6),
				unknown(255)
				}
			MAX-ACCESS read-only
			STATUS current
			DESCRIPTION
				"Gpon redundancy Olt-B status."
			::= { sleGponRedGroupEntry 5 }


--   1.3.6.1.4.1.6296.101.23.11.1.1.6
-- 1.3.6.1.4.1.6296.101.23.11.1.1.6
		sleGponRedLastReason OBJECT-TYPE
			SYNTAX INTEGER
				{
				none(0),
				force(1),
				los(2),
				slotRemove(3),
				slotLock(4),
				slotRestart(5),
				slotDisable(6),
				slotReset(7),
				slotPowerDown(8),
				gponMacCrash(9),
				daemonCrash(10),
				unknown(255)
				}
			MAX-ACCESS read-only
			STATUS current
			DESCRIPTION
				"The Last gpon-redundancy reason."
			::= { sleGponRedGroupEntry 6 }


--  1.3.6.1.4.1.6296.101.23.11.1.1.7
		sleGponRedGroupStandbyLinkStatus OBJECT-TYPE
			SYNTAX INTEGER
				{
				none(0),
				rxDetect(1),
				txEnable(2)
				}
			MAX-ACCESS read-only
			STATUS current
			DESCRIPTION
				"The Standby Link Status."
			::= { sleGponRedGroupEntry 7 }


--  1.3.6.1.4.1.6296.101.23.11.1.1.8
		sleGponRedGroupSlaveOltAdminStatus OBJECT-TYPE
			SYNTAX INTEGER
				{
				activation(1),
				inActivation(2)
				}
			MAX-ACCESS read-only
			STATUS current
			DESCRIPTION
				"The Slave OLT Admin Status."
			::= { sleGponRedGroupEntry 8 }


--  1.3.6.1.4.1.6296.101.23.11.1.1.9
		sleGponRedGroupTrigger OBJECT-TYPE
			SYNTAX BITS
				{
				los(0),
				manual(1),
				slotStatus(2),
				gponMac(3),
				standbyAct(4)
				}
			MAX-ACCESS read-only
			STATUS current
			DESCRIPTION
				"olt redundancy trigger (los|manual|slot|gpon-mac) (on|off) group GROUP_ID"
			::= { sleGponRedGroupEntry 9 }


--  1.3.6.1.4.1.6296.101.23.11.1.1.10
		sleGponRedGroupDbSyncStatus OBJECT-TYPE
			SYNTAX INTEGER
				{
				init(0),
				same(1),
				checkDifferent(2),
				updateSuccess(3),
				updateFail(4)
				}
			MAX-ACCESS read-only
			STATUS current
			DESCRIPTION
				"The DB sync status"
			::= { sleGponRedGroupEntry 10 }


--  1.3.6.1.4.1.6296.101.23.11.1.1.11
		sleGponRedGroupStandbyActTriggerTime OBJECT-TYPE
			SYNTAX Integer32 (0 | 5..30)
			MAX-ACCESS read-only
			STATUS current
			DESCRIPTION
				"The Standby Active Trigger Time ( Unit : Sec ) "
			::= { sleGponRedGroupEntry 11 }


--   1.3.6.1.4.1.6296.101.23.11.2
-- 1.3.6.1.4.1.6296.101.23.11.2
		sleGponRedGroupControl OBJECT IDENTIFIER ::= { sleGponRedundancy 2 }


--   1.3.6.1.4.1.6296.101.23.11.2.1
-- 1.3.6.1.4.1.6296.101.23.11.2.1
		sleGponRedGroupControlRequest OBJECT-TYPE
			SYNTAX INTEGER
				{
				setGponRedGroup(1),
				clearGponRedGroup(2),
				setGponRedForceSwitchover(3),
				setGponRedStandbyOptic(4),
				setGponRedSlaveAdminStatus(5),
				setGponRedTrigger(6),
				setGponRedSafeSwitchover(7),
				setGponRedDbSyncCheck(8),
				setGponRedDbResync(9),
				setGponRedStandbyActTriggerTime(10)
				}
			MAX-ACCESS read-write
			STATUS current
			DESCRIPTION
				"The request of a user command"
			::= { sleGponRedGroupControl 1 }


--   1.3.6.1.4.1.6296.101.23.11.2.2
-- 1.3.6.1.4.1.6296.101.23.11.2.2
		sleGponRedGroupControlStatus OBJECT-TYPE
			SYNTAX SleControlStatusType
			MAX-ACCESS read-only
			STATUS current
			DESCRIPTION
				"The status of user command"
			::= { sleGponRedGroupControl 2 }


--   1.3.6.1.4.1.6296.101.23.11.2.3
-- 1.3.6.1.4.1.6296.101.23.11.2.3
		sleGponRedGroupControlTimer OBJECT-TYPE
			SYNTAX Gauge32
			MAX-ACCESS read-write
			STATUS current
			DESCRIPTION
				"The maximum time for the manager for a long running user command"
			::= { sleGponRedGroupControl 3 }


--
-- 1.3.6.1.4.1.6296.101.23.11.2.4
-- 1.3.6.1.4.1.6296.101.23.11.2.4
		sleGponRedGroupControlTimeStamp OBJECT-TYPE
			SYNTAX TimeTicks
			MAX-ACCESS read-only
			STATUS current
			DESCRIPTION
				"The time stamp of the last command(end of command)"
			::= { sleGponRedGroupControl 4 }


--   1.3.6.1.4.1.6296.101.23.11.2.5
-- 1.3.6.1.4.1.6296.101.23.11.2.5
		sleGponRedGroupControlReqResult OBJECT-TYPE
			SYNTAX SleControlRequestResultType
			MAX-ACCESS read-only
			STATUS current
			DESCRIPTION
				"The result of the last user command"
			::= { sleGponRedGroupControl 5 }


--   1.3.6.1.4.1.6296.101.23.11.2.6
-- 1.3.6.1.4.1.6296.101.23.11.2.6
		sleGponRedGroupControlGroupIndex OBJECT-TYPE
			SYNTAX Integer32
			MAX-ACCESS read-write
			STATUS current
			DESCRIPTION
				"Gpon red group Index."
			::= { sleGponRedGroupControl 6 }


		sleGponRedGroupControlOltAIndex OBJECT-TYPE
			SYNTAX Integer32 (1..2147483647)
			MAX-ACCESS read-write
			STATUS current
			DESCRIPTION
				"Gpon red Olt-A index."
			::= { sleGponRedGroupControl 7 }


		sleGponRedGroupControlOltBIndex OBJECT-TYPE
			SYNTAX Integer32 (1..2147483647)
			MAX-ACCESS read-write
			STATUS current
			DESCRIPTION
				"Gpon red Olt-B index."
			::= { sleGponRedGroupControl 8 }


--  1.3.6.1.4.1.6296.101.23.11.2.9
		sleGponRedGroupControlStandbyOptic OBJECT-TYPE
			SYNTAX INTEGER
				{
				enable(1),
				disable(2)
				}
			MAX-ACCESS read-write
			STATUS current
			DESCRIPTION
				"olt redundancy standby-optic (enable|disable) group GROUP_ID"
			::= { sleGponRedGroupControl 9 }


--  1.3.6.1.4.1.6296.101.23.11.2.10
		sleGponRedGroupControlStandbyOpticEnableTime OBJECT-TYPE
			SYNTAX INTEGER (0 | 1..600)
			MAX-ACCESS read-write
			STATUS current
			DESCRIPTION
				"olt redundancy standby-optic (enable|disable) group GROUP_ID (0:permanent|<1-600>)
				"
			::= { sleGponRedGroupControl 10 }


--  1.3.6.1.4.1.6296.101.23.11.2.11
		sleGponRedGroupControlSlaveAdminStatus OBJECT-TYPE
			SYNTAX INTEGER
				{
				activation(1),
				inActivation(2)
				}
			MAX-ACCESS read-write
			STATUS current
			DESCRIPTION
				"olt redundancy slave (activate|deactivate) group GROUP_ID"
			::= { sleGponRedGroupControl 11 }


--  1.3.6.1.4.1.6296.101.23.11.2.12
		sleGponRedGroupControlTrigger OBJECT-TYPE
			SYNTAX BITS
				{
				los(0),
				manual(1),
				slotStatus(2),
				gponMac(3),
				standbyAct(4)
				}
			MAX-ACCESS read-write
			STATUS current
			DESCRIPTION
				"olt redundancy trigger (los|manual|slot|gpon-mac) (on|off) group GROUP_ID"
			::= { sleGponRedGroupControl 12 }


--  1.3.6.1.4.1.6296.101.23.11.2.13
		sleGponRedGroupControlStandbyActTriggerTime OBJECT-TYPE
			SYNTAX Integer32 (5..30)
			MAX-ACCESS read-write
			STATUS current
			DESCRIPTION
				"The Standby Active Trigger Time ( Unit : Sec )"
			::= { sleGponRedGroupControl 13 }


--   1.3.6.1.4.1.6296.101.23.11.3
-- 1.3.6.1.4.1.6296.101.23.11.3
		sleGponRedGroupNotification OBJECT IDENTIFIER ::= { sleGponRedundancy 3 }


--   1.3.6.1.4.1.6296.101.23.11.3.1
-- 1.3.6.1.4.1.6296.101.23.11.3.1
		sleGponRedGroupChanged NOTIFICATION-TYPE
			OBJECTS { sleGponRedGroupControlRequest, sleGponRedGroupControlTimeStamp, sleGponRedGroupControlReqResult, sleGponRedGroupControlGroupIndex, sleGponRedGroupControlOltAIndex,
				sleGponRedGroupControlOltBIndex }
			STATUS current
			DESCRIPTION
				"Description."
			::= { sleGponRedGroupNotification 1 }


--   1.3.6.1.4.1.6296.101.23.11.3.2
-- 1.3.6.1.4.1.6296.101.23.11.3.2
		sleGponRedGroupCleared NOTIFICATION-TYPE
			OBJECTS { sleGponRedGroupControlRequest, sleGponRedGroupControlTimeStamp, sleGponRedGroupControlReqResult, sleGponRedGroupControlGroupIndex }
			STATUS current
			DESCRIPTION
				"Description."
			::= { sleGponRedGroupNotification 2 }


--   1.3.6.1.4.1.6296.101.23.11.3.3
-- 1.3.6.1.4.1.6296.101.23.11.3.3
		sleGponRedGroupForceSwitchovered NOTIFICATION-TYPE
			OBJECTS { sleGponRedGroupControlRequest, sleGponRedGroupControlTimeStamp, sleGponRedGroupControlReqResult, sleGponRedGroupControlGroupIndex }
			STATUS current
			DESCRIPTION
				"Description."
			::= { sleGponRedGroupNotification 3 }


--  1.3.6.1.4.1.6296.101.23.11.3.4
		sleGponRedGroupStandbyOpticChanged NOTIFICATION-TYPE
			OBJECTS { sleGponRedGroupControlRequest, sleGponRedGroupControlTimeStamp, sleGponRedGroupControlReqResult, sleGponRedGroupControlGroupIndex, sleGponRedGroupControlStandbyOptic,
				sleGponRedGroupControlStandbyOpticEnableTime }
			STATUS current
			DESCRIPTION
				"Description."
			::= { sleGponRedGroupNotification 4 }


--  1.3.6.1.4.1.6296.101.23.11.3.5
		sleGponRedGroupSlaveAdminStatusChanged NOTIFICATION-TYPE
			OBJECTS { sleGponRedGroupControlRequest, sleGponRedGroupControlTimeStamp, sleGponRedGroupControlReqResult, sleGponRedGroupControlGroupIndex, sleGponRedGroupControlSlaveAdminStatus
				 }
			STATUS current
			DESCRIPTION
				"Description."
			::= { sleGponRedGroupNotification 5 }


--  1.3.6.1.4.1.6296.101.23.11.3.6
		sleGponRedGroupTriggerChanged NOTIFICATION-TYPE
			OBJECTS { sleGponRedGroupControlRequest, sleGponRedGroupControlTimeStamp, sleGponRedGroupControlReqResult, sleGponRedGroupControlGroupIndex, sleGponRedGroupControlTrigger
				 }
			STATUS current
			DESCRIPTION
				"Description."
			::= { sleGponRedGroupNotification 6 }


--  1.3.6.1.4.1.6296.101.23.11.3.7
		sleGponRedGroupSafeSwitchOverChanged NOTIFICATION-TYPE
			OBJECTS { sleGponRedGroupControlRequest, sleGponRedGroupControlTimeStamp, sleGponRedGroupControlReqResult, sleGponRedGroupControlGroupIndex }
			STATUS current
			DESCRIPTION
				"setGponRedSafeSwitchover"
			::= { sleGponRedGroupNotification 7 }


--  1.3.6.1.4.1.6296.101.23.11.3.8
		sleGponRedGroupDbSyncCheckChanged NOTIFICATION-TYPE
			OBJECTS { sleGponRedGroupControlRequest, sleGponRedGroupControlTimeStamp, sleGponRedGroupControlReqResult, sleGponRedGroupControlGroupIndex, sleGponRedGroupDbSyncStatus
				 }
			STATUS current
			DESCRIPTION
				"setGponRedDbSyncCheck"
			::= { sleGponRedGroupNotification 8 }


--  1.3.6.1.4.1.6296.101.23.11.3.9
		sleGponRedGroupDbResyncChanged NOTIFICATION-TYPE
			OBJECTS { sleGponRedGroupControlRequest, sleGponRedGroupControlTimeStamp, sleGponRedGroupControlReqResult, sleGponRedGroupControlGroupIndex, sleGponRedGroupDbSyncStatus
				 }
			STATUS current
			DESCRIPTION
				"setGponRedDbResync"
			::= { sleGponRedGroupNotification 9 }


--  1.3.6.1.4.1.6296.101.23.11.3.10
		sleGponRedGroupStandbyActTriggerTimeChanged NOTIFICATION-TYPE
			OBJECTS { sleGponRedGroupControlRequest, sleGponRedGroupControlTimeStamp, sleGponRedGroupControlReqResult, sleGponRedGroupControlGroupIndex, sleGponRedGroupControlStandbyActTriggerTime
				 }
			STATUS current
			DESCRIPTION
				"setGponRedStandbyActTriggerTime "
			::= { sleGponRedGroupNotification 10 }


--   1.3.6.1.4.1.6296.101.23.12
-- 1.3.6.1.4.1.6296.101.23.12
		sleGponOnuHost OBJECT IDENTIFIER ::= { sleGpon 12 }


--   1.3.6.1.4.1.6296.101.23.12.1
-- 1.3.6.1.4.1.6296.101.23.12.1
		sleGponOnuHostTable OBJECT-TYPE
			SYNTAX SEQUENCE OF SleGponOnuHostEntry
			MAX-ACCESS not-accessible
			STATUS current
			DESCRIPTION
				"sleGponOnuHostTable"
			::= { sleGponOnuHost 1 }


--   1.3.6.1.4.1.6296.101.23.12.1.1
-- 1.3.6.1.4.1.6296.101.23.12.1.1
		sleGponOnuHostEntry OBJECT-TYPE
			SYNTAX SleGponOnuHostEntry
			MAX-ACCESS not-accessible
			STATUS current
			DESCRIPTION
				"key: sleGponOnuHostOltId, sleGponOnuHostOnuId, sleGponOnuHostId"
			INDEX { sleGponOnuHostOltId, sleGponOnuHostOnuId, sleGponOnuHostId }
			::= { sleGponOnuHostTable 1 }


		SleGponOnuHostEntry ::=
			SEQUENCE {
				sleGponOnuHostOltId
					INTEGER,
				sleGponOnuHostOnuId
					INTEGER,
				sleGponOnuHostId
					INTEGER,
				sleGponOnuHostIPAddr
					IpAddress,
				sleGponOnuHostMask
					IpAddress,
				sleGponOnuHostGW
					IpAddress,
				sleGponOnuHostPriDns
					IpAddress,
				sleGponOnuHostSecDns
					IpAddress,
				sleGponOnuHostIpOption
					BITS,
				sleGponOnuHostMacAddress
					OCTET STRING,
				sleGponOnuHostDomainName
					OCTET STRING,
				sleGponOnuHostHostName
					OCTET STRING,
				sleGponOnuHostCurIpAddr
					IpAddress,
				sleGponOnuHostCurMask
					IpAddress,
				sleGponOnuHostCurGW
					IpAddress,
				sleGponOnuHostCurPriDns
					IpAddress,
				sleGponOnuHostCurSecDns
					IpAddress,
				sleGponOnuHostType
					InetAddressType,
				sleGponOnuHostIPv6LinkLocalAddr
					InetAddress,
				sleGponOnuHostIPv6Addr
					InetAddress,
				sleGponOnuHostIPv6DefaultRouter
					InetAddress,
				sleGponOnuHostIPv6PriDns
					InetAddress,
				sleGponOnuHostIPv6SecDns
					InetAddress,
				sleGponOnuHostIPv6PrefixLen
					InetAddressPrefixLength,
				sleGponOnuHostIPv6CurDefaultRouter
					InetAddress,
				sleGponOnuHostIPv6CurPriDns
					InetAddress,
				sleGponOnuHostIPv6CurSecDns
					InetAddress,
				sleGponOnuHostPppoeAccountUser
					OCTET STRING,
				sleGponOnuHostPppoeAccountPassword
					OCTET STRING
			 }

		sleGponOnuHostOltId OBJECT-TYPE
			SYNTAX INTEGER (1..2147483647)
			MAX-ACCESS read-only
			STATUS current
			DESCRIPTION
				"Gpon Olt Index"
			::= { sleGponOnuHostEntry 1 }


--   1.3.6.1.4.1.6296.101.23.12.1.1.2
-- 1.3.6.1.4.1.6296.101.23.12.1.1.2
		sleGponOnuHostOnuId OBJECT-TYPE
			SYNTAX INTEGER (1..256)
			MAX-ACCESS read-only
			STATUS current
			DESCRIPTION
				"Gpon Onu Index"
			::= { sleGponOnuHostEntry 2 }


--   1.3.6.1.4.1.6296.101.23.12.1.1.3
-- 1.3.6.1.4.1.6296.101.23.12.1.1.3
		sleGponOnuHostId OBJECT-TYPE
			SYNTAX INTEGER (1..8)
			MAX-ACCESS read-only
			STATUS current
			DESCRIPTION
				"Onu Ip Host Config data Index"
			::= { sleGponOnuHostEntry 3 }


--   1.3.6.1.4.1.6296.101.23.12.1.1.4
-- 1.3.6.1.4.1.6296.101.23.12.1.1.4
		sleGponOnuHostIPAddr OBJECT-TYPE
			SYNTAX IpAddress
			MAX-ACCESS read-only
			STATUS current
			DESCRIPTION
				"Onu IP address"
			::= { sleGponOnuHostEntry 4 }


--   1.3.6.1.4.1.6296.101.23.12.1.1.5
-- 1.3.6.1.4.1.6296.101.23.12.1.1.5
		sleGponOnuHostMask OBJECT-TYPE
			SYNTAX IpAddress
			MAX-ACCESS read-only
			STATUS current
			DESCRIPTION
				"Onu IP Netmask"
			::= { sleGponOnuHostEntry 5 }


--   1.3.6.1.4.1.6296.101.23.12.1.1.6
-- 1.3.6.1.4.1.6296.101.23.12.1.1.6
		sleGponOnuHostGW OBJECT-TYPE
			SYNTAX IpAddress
			MAX-ACCESS read-only
			STATUS current
			DESCRIPTION
				"Onu Gateway"
			::= { sleGponOnuHostEntry 6 }


--  1.3.6.1.4.1.6296.101.23.12.1.1.7
		sleGponOnuHostPriDns OBJECT-TYPE
			SYNTAX IpAddress
			MAX-ACCESS read-only
			STATUS current
			DESCRIPTION
				"The Primary DNS address."
			::= { sleGponOnuHostEntry 7 }


--  1.3.6.1.4.1.6296.101.23.12.1.1.8
		sleGponOnuHostSecDns OBJECT-TYPE
			SYNTAX IpAddress
			MAX-ACCESS read-only
			STATUS current
			DESCRIPTION
				"The secondary DNS address"
			::= { sleGponOnuHostEntry 8 }


--  1.3.6.1.4.1.6296.101.23.12.1.1.9
		sleGponOnuHostIpOption OBJECT-TYPE
			SYNTAX BITS
				{
				enableDhcp(0),
				respondPings(1),
				respondTraceroute(2)
				}
			MAX-ACCESS read-only
			STATUS current
			DESCRIPTION
				"The IP option.
				1:enableDhcp, 2, respondPings 4, respondTraceroute"
			::= { sleGponOnuHostEntry 9 }


--  1.3.6.1.4.1.6296.101.23.12.1.1.10
		sleGponOnuHostMacAddress OBJECT-TYPE
			SYNTAX OCTET STRING
			MAX-ACCESS read-only
			STATUS current
			DESCRIPTION
				"The Mac address."
			::= { sleGponOnuHostEntry 10 }


--  1.3.6.1.4.1.6296.101.23.12.1.1.11
		sleGponOnuHostDomainName OBJECT-TYPE
			SYNTAX OCTET STRING
			MAX-ACCESS read-only
			STATUS current
			DESCRIPTION
				"The Domain name"
			::= { sleGponOnuHostEntry 11 }


--  1.3.6.1.4.1.6296.101.23.12.1.1.12
		sleGponOnuHostHostName OBJECT-TYPE
			SYNTAX OCTET STRING
			MAX-ACCESS read-only
			STATUS current
			DESCRIPTION
				"The host name."
			::= { sleGponOnuHostEntry 12 }


--  1.3.6.1.4.1.6296.101.23.12.1.1.13
		sleGponOnuHostCurIpAddr OBJECT-TYPE
			SYNTAX IpAddress
			MAX-ACCESS read-only
			STATUS current
			DESCRIPTION
				"The Current IP address."
			::= { sleGponOnuHostEntry 13 }


--  1.3.6.1.4.1.6296.101.23.12.1.1.14
		sleGponOnuHostCurMask OBJECT-TYPE
			SYNTAX IpAddress
			MAX-ACCESS read-only
			STATUS current
			DESCRIPTION
				"The Currest Mask."
			::= { sleGponOnuHostEntry 14 }


--  1.3.6.1.4.1.6296.101.23.12.1.1.15
		sleGponOnuHostCurGW OBJECT-TYPE
			SYNTAX IpAddress
			MAX-ACCESS read-only
			STATUS current
			DESCRIPTION
				"The current gate way."
			::= { sleGponOnuHostEntry 15 }


--  1.3.6.1.4.1.6296.101.23.12.1.1.16
		sleGponOnuHostCurPriDns OBJECT-TYPE
			SYNTAX IpAddress
			MAX-ACCESS read-only
			STATUS current
			DESCRIPTION
				"The current primary DNS address."
			::= { sleGponOnuHostEntry 16 }


--  1.3.6.1.4.1.6296.101.23.12.1.1.17
		sleGponOnuHostCurSecDns OBJECT-TYPE
			SYNTAX IpAddress
			MAX-ACCESS read-only
			STATUS current
			DESCRIPTION
				"The current secondary DNS address."
			::= { sleGponOnuHostEntry 17 }


		sleGponOnuHostType OBJECT-TYPE
			SYNTAX InetAddressType
			MAX-ACCESS read-only
			STATUS current
			DESCRIPTION
				"IP Host version Type"
			::= { sleGponOnuHostEntry 18 }


		sleGponOnuHostIPv6LinkLocalAddr OBJECT-TYPE
			SYNTAX InetAddress
			MAX-ACCESS read-only
			STATUS current
			DESCRIPTION
				"IPv6 link local address"
			::= { sleGponOnuHostEntry 19 }


		sleGponOnuHostIPv6Addr OBJECT-TYPE
			SYNTAX InetAddress
			MAX-ACCESS read-only
			STATUS current
			DESCRIPTION
				"IPv6 address"
			::= { sleGponOnuHostEntry 20 }


		sleGponOnuHostIPv6DefaultRouter OBJECT-TYPE
			SYNTAX InetAddress
			MAX-ACCESS read-only
			STATUS current
			DESCRIPTION
				"IPv6 Default Router"
			::= { sleGponOnuHostEntry 21 }


		sleGponOnuHostIPv6PriDns OBJECT-TYPE
			SYNTAX InetAddress
			MAX-ACCESS read-only
			STATUS current
			DESCRIPTION
				"IPv6 Primary DNS"
			::= { sleGponOnuHostEntry 22 }


		sleGponOnuHostIPv6SecDns OBJECT-TYPE
			SYNTAX InetAddress
			MAX-ACCESS read-only
			STATUS current
			DESCRIPTION
				"IPv6 Secondary DNS"
			::= { sleGponOnuHostEntry 23 }


		sleGponOnuHostIPv6PrefixLen OBJECT-TYPE
			SYNTAX InetAddressPrefixLength
			MAX-ACCESS read-only
			STATUS current
			DESCRIPTION
				"On-link Prefix Length"
			::= { sleGponOnuHostEntry 24 }


		sleGponOnuHostIPv6CurDefaultRouter OBJECT-TYPE
			SYNTAX InetAddress
			MAX-ACCESS read-only
			STATUS current
			DESCRIPTION
				"Current IPv6 Default Router"
			::= { sleGponOnuHostEntry 25 }


		sleGponOnuHostIPv6CurPriDns OBJECT-TYPE
			SYNTAX InetAddress
			MAX-ACCESS read-only
			STATUS current
			DESCRIPTION
				"Current IPv6 Primary DNS"
			::= { sleGponOnuHostEntry 26 }


		sleGponOnuHostIPv6CurSecDns OBJECT-TYPE
			SYNTAX InetAddress
			MAX-ACCESS read-only
			STATUS current
			DESCRIPTION
				"Current IPv6 Secondary DNS"
			::= { sleGponOnuHostEntry 27 }


		sleGponOnuHostPppoeAccountUser OBJECT-TYPE
			SYNTAX OCTET STRING
			MAX-ACCESS read-only
			STATUS current
			DESCRIPTION
				"Pppoe User Name"
			::= { sleGponOnuHostEntry 28 }


		sleGponOnuHostPppoeAccountPassword OBJECT-TYPE
			SYNTAX OCTET STRING
			MAX-ACCESS read-only
			STATUS current
			DESCRIPTION
				"OCTET STRING	Pppoe Password"
			::= { sleGponOnuHostEntry 29 }


--   1.3.6.1.4.1.6296.101.23.12.2
-- 1.3.6.1.4.1.6296.101.23.12.2
		sleGponOnuHostControl OBJECT IDENTIFIER ::= { sleGponOnuHost 2 }


--   1.3.6.1.4.1.6296.101.23.12.2.1
-- 1.3.6.1.4.1.6296.101.23.12.2.1
		sleGponOnuHostControlRequest OBJECT-TYPE
			SYNTAX INTEGER
				{
				setOnuHostIpInfo(1),
				updateOnuHostInfo(2),
				setOnuHostIpv6Info(3),
				setOnuHostPppoeAccount(4)
				}
			MAX-ACCESS read-write
			STATUS current
			DESCRIPTION
				"The request of a user command"
			::= { sleGponOnuHostControl 1 }


--   1.3.6.1.4.1.6296.101.23.12.2.2
-- 1.3.6.1.4.1.6296.101.23.12.2.2
		sleGponOnuHostControlStatus OBJECT-TYPE
			SYNTAX SleControlStatusType
			MAX-ACCESS read-only
			STATUS current
			DESCRIPTION
				"The status of user command"
			::= { sleGponOnuHostControl 2 }


--   1.3.6.1.4.1.6296.101.23.12.2.3
-- 1.3.6.1.4.1.6296.101.23.12.2.3
		sleGponOnuHostControlTimer OBJECT-TYPE
			SYNTAX Gauge32
			MAX-ACCESS read-write
			STATUS current
			DESCRIPTION
				"The maximum time for the manager for a long running user command"
			::= { sleGponOnuHostControl 3 }


--   1.3.6.1.4.1.6296.101.23.12.2.4
-- 1.3.6.1.4.1.6296.101.23.12.2.4
		sleGponOnuHostControlTimeStamp OBJECT-TYPE
			SYNTAX TimeTicks
			MAX-ACCESS read-only
			STATUS current
			DESCRIPTION
				"The time stamp of the last command(end of command)"
			::= { sleGponOnuHostControl 4 }


--   1.3.6.1.4.1.6296.101.23.12.2.5
-- 1.3.6.1.4.1.6296.101.23.12.2.5
		sleGponOnuHostControlReqResult OBJECT-TYPE
			SYNTAX SleControlRequestResultType
			MAX-ACCESS read-only
			STATUS current
			DESCRIPTION
				"The result of the last user command"
			::= { sleGponOnuHostControl 5 }


		sleGponOnuHostControlOltId OBJECT-TYPE
			SYNTAX INTEGER (1..2147483647)
			MAX-ACCESS read-write
			STATUS current
			DESCRIPTION
				"The OLT id."
			::= { sleGponOnuHostControl 6 }


--   1.3.6.1.4.1.6296.101.23.12.2.7
-- 1.3.6.1.4.1.6296.101.23.12.2.7
		sleGponOnuHostControlOnuId OBJECT-TYPE
			SYNTAX INTEGER (1..256)
			MAX-ACCESS read-write
			STATUS current
			DESCRIPTION
				"The ONU id"
			::= { sleGponOnuHostControl 7 }


--   1.3.6.1.4.1.6296.101.23.12.2.8
-- 1.3.6.1.4.1.6296.101.23.12.2.8
		sleGponOnuHostControlId OBJECT-TYPE
			SYNTAX INTEGER (1..8)
			MAX-ACCESS read-write
			STATUS current
			DESCRIPTION
				"Onu Ip Host Config data Index"
			::= { sleGponOnuHostControl 8 }


--   1.3.6.1.4.1.6296.101.23.12.2.9
-- 1.3.6.1.4.1.6296.101.23.12.2.9
		sleGponOnuHostControlIPAddr OBJECT-TYPE
			SYNTAX IpAddress
			MAX-ACCESS read-write
			STATUS current
			DESCRIPTION
				"Onu IP address"
			::= { sleGponOnuHostControl 9 }


--   1.3.6.1.4.1.6296.101.23.12.2.10
-- 1.3.6.1.4.1.6296.101.23.12.2.10
		sleGponOnuHostControlMask OBJECT-TYPE
			SYNTAX IpAddress
			MAX-ACCESS read-write
			STATUS current
			DESCRIPTION
				"Onu IP Netmask"
			::= { sleGponOnuHostControl 10 }


--   1.3.6.1.4.1.6296.101.23.12.2.11
-- 1.3.6.1.4.1.6296.101.23.12.2.11
		sleGponOnuHostControlGW OBJECT-TYPE
			SYNTAX IpAddress
			MAX-ACCESS read-write
			STATUS current
			DESCRIPTION
				"Onu Gateway"
			::= { sleGponOnuHostControl 11 }


--  1.3.6.1.4.1.6296.101.23.12.2.11
		sleGponOnuHostControlIPv6Addr OBJECT-TYPE
			SYNTAX InetAddress
			MAX-ACCESS read-write
			STATUS current
			DESCRIPTION
				"Onu IPv6 address"
			::= { sleGponOnuHostControl 12 }


--  1.3.6.1.4.1.6296.101.23.12.2.11
		sleGponOnuHostControlIPv6PrefixLen OBJECT-TYPE
			SYNTAX InetAddressPrefixLength
			MAX-ACCESS read-write
			STATUS current
			DESCRIPTION
				"ONU IPv6 Prefix Length"
			::= { sleGponOnuHostControl 13 }


--  1.3.6.1.4.1.6296.101.23.12.2.11
		sleGponOnuHostControlIPv6DefaultRouter OBJECT-TYPE
			SYNTAX InetAddress
			MAX-ACCESS read-write
			STATUS current
			DESCRIPTION
				"Onu IPv6 default router"
			::= { sleGponOnuHostControl 14 }


--  1.3.6.1.4.1.6296.101.23.12.2.11
		sleGponOnuHostControlIPppoeAccountUser OBJECT-TYPE
			SYNTAX OCTET STRING
			MAX-ACCESS read-write
			STATUS current
			DESCRIPTION
				"Pppoe User Name"
			::= { sleGponOnuHostControl 15 }


--  1.3.6.1.4.1.6296.101.23.12.2.11
		sleGponOnuHostControlIPppoeAccountPassword OBJECT-TYPE
			SYNTAX OCTET STRING
			MAX-ACCESS read-write
			STATUS current
			DESCRIPTION
				"Pppoe Password"
			::= { sleGponOnuHostControl 16 }


--   1.3.6.1.4.1.6296.101.23.12.3
-- 1.3.6.1.4.1.6296.101.23.12.3
		sleGponOnuHostNotification OBJECT IDENTIFIER ::= { sleGponOnuHost 3 }


--   1.3.6.1.4.1.6296.101.23.12.3.1
-- 1.3.6.1.4.1.6296.101.23.12.3.1
		sleGponOnuHostIPInfoChanged NOTIFICATION-TYPE
			OBJECTS { sleGponOnuHostControlRequest, sleGponOnuHostControlTimeStamp, sleGponOnuHostControlReqResult, sleGponOnuHostControlOltId, sleGponOnuHostControlOnuId,
				sleGponOnuHostControlId, sleGponOnuHostControlIPAddr, sleGponOnuHostControlMask, sleGponOnuHostControlGW }
			STATUS current
			DESCRIPTION
				"Description."
			::= { sleGponOnuHostNotification 1 }


--  1.3.6.1.4.1.6296.101.23.12.3.2
		sleGponOnuHostInfoChanged NOTIFICATION-TYPE
			OBJECTS { sleGponOnuHostControlRequest, sleGponOnuHostControlTimeStamp, sleGponOnuHostControlReqResult, sleGponOnuHostControlOltId, sleGponOnuHostControlOnuId
				 }
			STATUS current
			DESCRIPTION
				"Description."
			::= { sleGponOnuHostNotification 2 }


		sleGponOnuHostIpv6InfoChanged NOTIFICATION-TYPE
			OBJECTS { sleGponOnuHostControlRequest, sleGponOnuHostControlTimeStamp, sleGponOnuHostControlReqResult, sleGponOnuHostControlOltId, sleGponOnuHostControlOnuId,
				sleGponOnuHostControlId, sleGponOnuHostControlIPv6Addr, sleGponOnuHostControlIPv6PrefixLen, sleGponOnuHostControlIPv6DefaultRouter }
			STATUS current
			DESCRIPTION
				"Description."
			::= { sleGponOnuHostNotification 3 }


		sleGponOnuHostPppoeAccountChanged NOTIFICATION-TYPE
			OBJECTS { sleGponOnuHostControlRequest, sleGponOnuHostControlTimeStamp, sleGponOnuHostControlReqResult, sleGponOnuHostControlOltId, sleGponOnuHostControlOnuId,
				sleGponOnuHostControlId, sleGponOnuHostControlIPppoeAccountUser, sleGponOnuHostControlIPppoeAccountPassword }
			STATUS current
			DESCRIPTION
				"Description."
			::= { sleGponOnuHostNotification 4 }


		sleGponOnuIPv6HostCurAddrTable OBJECT-TYPE
			SYNTAX SEQUENCE OF SleGponOnuIPv6HostCurAddrEntry
			MAX-ACCESS not-accessible
			STATUS current
			DESCRIPTION
				"sleGponOnuHostTable"
			::= { sleGponOnuHost 4 }


--  1.3.6.1.4.1.6296.101.23.12.1.1
		sleGponOnuIPv6HostCurAddrEntry OBJECT-TYPE
			SYNTAX SleGponOnuIPv6HostCurAddrEntry
			MAX-ACCESS not-accessible
			STATUS current
			DESCRIPTION
				"key: sleGponOnuHostOltId, sleGponOnuHostOnuId, sleGponOnuHostId"
			INDEX { sleGponOnuIPv6HostCurAddrOltId, sleGponOnuIPv6HostCurAddrOnuId, sleGponOnuIPv6HostCurAddrId, sleGponOnuIPv6HostCurAddrHostId }
			::= { sleGponOnuIPv6HostCurAddrTable 1 }


		SleGponOnuIPv6HostCurAddrEntry ::=
			SEQUENCE {
				sleGponOnuIPv6HostCurAddrOltId
					INTEGER,
				sleGponOnuIPv6HostCurAddrOnuId
					INTEGER,
				sleGponOnuIPv6HostCurAddrHostId
					INTEGER,
				sleGponOnuIPv6HostCurAddrId
					Integer32,
				sleGponOnuIPv6HostCurAddr
					InetAddress
			 }

		sleGponOnuIPv6HostCurAddrOltId OBJECT-TYPE
			SYNTAX INTEGER (1..2147483647)
			MAX-ACCESS read-only
			STATUS current
			DESCRIPTION
				"Gpon Olt Index"
			::= { sleGponOnuIPv6HostCurAddrEntry 1 }


		sleGponOnuIPv6HostCurAddrOnuId OBJECT-TYPE
			SYNTAX INTEGER (1..256)
			MAX-ACCESS read-only
			STATUS current
			DESCRIPTION
				"Gpon Onu Index"
			::= { sleGponOnuIPv6HostCurAddrEntry 2 }


		sleGponOnuIPv6HostCurAddrHostId OBJECT-TYPE
			SYNTAX INTEGER (1..8)
			MAX-ACCESS read-only
			STATUS current
			DESCRIPTION
				"Onu Ip Host Config data Index"
			::= { sleGponOnuIPv6HostCurAddrEntry 3 }


		sleGponOnuIPv6HostCurAddrId OBJECT-TYPE
			SYNTAX Integer32 (0..65535)
			MAX-ACCESS read-only
			STATUS current
			DESCRIPTION
				"IPv6 Host Current Address Index"
			::= { sleGponOnuIPv6HostCurAddrEntry 4 }


		sleGponOnuIPv6HostCurAddr OBJECT-TYPE
			SYNTAX InetAddress
			MAX-ACCESS read-only
			STATUS current
			DESCRIPTION
				"IPv6 Host Current Address"
			::= { sleGponOnuIPv6HostCurAddrEntry 5 }


		sleGponOnuIPv6HostCurDefaultRouterTable OBJECT-TYPE
			SYNTAX SEQUENCE OF SleGponOnuIPv6HostCurDefaultRouterEntry
			MAX-ACCESS not-accessible
			STATUS current
			DESCRIPTION
				"sleGponOnuHostTable"
			::= { sleGponOnuHost 5 }


		sleGponOnuIPv6HostCurDefaultRouterEntry OBJECT-TYPE
			SYNTAX SleGponOnuIPv6HostCurDefaultRouterEntry
			MAX-ACCESS not-accessible
			STATUS current
			DESCRIPTION
				"key: sleGponOnuHostOltId, sleGponOnuHostOnuId, sleGponOnuHostId"
			INDEX { sleGponOnuIPv6HostCurDefaultRouterOltId, sleGponOnuIPv6HostCurDefaultRouterOnuId, sleGponOnuIPv6HostCurDefaultRouterId, sleGponOnuIPv6HostCurDefaultRouterHostId }
			::= { sleGponOnuIPv6HostCurDefaultRouterTable 1 }


		SleGponOnuIPv6HostCurDefaultRouterEntry ::=
			SEQUENCE {
				sleGponOnuIPv6HostCurDefaultRouterOltId
					INTEGER,
				sleGponOnuIPv6HostCurDefaultRouterOnuId
					INTEGER,
				sleGponOnuIPv6HostCurDefaultRouterHostId
					INTEGER,
				sleGponOnuIPv6HostCurDefaultRouterId
					Integer32,
				sleGponOnuIPv6HostCurDefaultRouter
					InetAddress
			 }

		sleGponOnuIPv6HostCurDefaultRouterOltId OBJECT-TYPE
			SYNTAX INTEGER (1..2147483647)
			MAX-ACCESS read-only
			STATUS current
			DESCRIPTION
				"Gpon Olt Index"
			::= { sleGponOnuIPv6HostCurDefaultRouterEntry 1 }


		sleGponOnuIPv6HostCurDefaultRouterOnuId OBJECT-TYPE
			SYNTAX INTEGER (1..256)
			MAX-ACCESS read-only
			STATUS current
			DESCRIPTION
				"Gpon Onu Index"
			::= { sleGponOnuIPv6HostCurDefaultRouterEntry 2 }


		sleGponOnuIPv6HostCurDefaultRouterHostId OBJECT-TYPE
			SYNTAX INTEGER (1..8)
			MAX-ACCESS read-only
			STATUS current
			DESCRIPTION
				"Onu Ip Host Config data Index"
			::= { sleGponOnuIPv6HostCurDefaultRouterEntry 3 }


		sleGponOnuIPv6HostCurDefaultRouterId OBJECT-TYPE
			SYNTAX Integer32 (0..65535)
			MAX-ACCESS read-only
			STATUS current
			DESCRIPTION
				"IPv6 Host Current Address Index"
			::= { sleGponOnuIPv6HostCurDefaultRouterEntry 4 }


		sleGponOnuIPv6HostCurDefaultRouter OBJECT-TYPE
			SYNTAX InetAddress
			MAX-ACCESS read-only
			STATUS current
			DESCRIPTION
				"IPv6 Host Current Address"
			::= { sleGponOnuIPv6HostCurDefaultRouterEntry 5 }


		sleGponOnuIPv6HostCurDnsTable OBJECT-TYPE
			SYNTAX SEQUENCE OF SleGponOnuIPv6HostCurDnsEntry
			MAX-ACCESS not-accessible
			STATUS current
			DESCRIPTION
				"sleGponOnuHostTable"
			::= { sleGponOnuHost 6 }


		sleGponOnuIPv6HostCurDnsEntry OBJECT-TYPE
			SYNTAX SleGponOnuIPv6HostCurDnsEntry
			MAX-ACCESS not-accessible
			STATUS current
			DESCRIPTION
				"key: sleGponOnuHostOltId, sleGponOnuHostOnuId, sleGponOnuHostId"
			INDEX { sleGponOnuIPv6HostCurDnsOltId, sleGponOnuIPv6HostCurDnsOnuId, sleGponOnuIPv6HostCurDnsHostId, sleGponOnuIPv6HostCurDnsId }
			::= { sleGponOnuIPv6HostCurDnsTable 1 }


		SleGponOnuIPv6HostCurDnsEntry ::=
			SEQUENCE {
				sleGponOnuIPv6HostCurDnsOltId
					INTEGER,
				sleGponOnuIPv6HostCurDnsOnuId
					INTEGER,
				sleGponOnuIPv6HostCurDnsHostId
					INTEGER,
				sleGponOnuIPv6HostCurDnsId
					Integer32,
				sleGponOnuIPv6HostCurDns
					InetAddress
			 }

		sleGponOnuIPv6HostCurDnsOltId OBJECT-TYPE
			SYNTAX INTEGER (1..2147483647)
			MAX-ACCESS read-only
			STATUS current
			DESCRIPTION
				"Gpon Olt Index"
			::= { sleGponOnuIPv6HostCurDnsEntry 1 }


		sleGponOnuIPv6HostCurDnsOnuId OBJECT-TYPE
			SYNTAX INTEGER (1..256)
			MAX-ACCESS read-only
			STATUS current
			DESCRIPTION
				"Gpon Onu Index"
			::= { sleGponOnuIPv6HostCurDnsEntry 2 }


		sleGponOnuIPv6HostCurDnsHostId OBJECT-TYPE
			SYNTAX INTEGER (1..8)
			MAX-ACCESS read-only
			STATUS current
			DESCRIPTION
				"Onu Ip Host Config data Index"
			::= { sleGponOnuIPv6HostCurDnsEntry 3 }


		sleGponOnuIPv6HostCurDnsId OBJECT-TYPE
			SYNTAX Integer32 (0..65535)
			MAX-ACCESS read-only
			STATUS current
			DESCRIPTION
				"IPv6 Host Current Address Index"
			::= { sleGponOnuIPv6HostCurDnsEntry 4 }


		sleGponOnuIPv6HostCurDns OBJECT-TYPE
			SYNTAX InetAddress
			MAX-ACCESS read-only
			STATUS current
			DESCRIPTION
				"IPv6 Host Current Address"
			::= { sleGponOnuIPv6HostCurDnsEntry 5 }


--   1.3.6.1.4.1.6296.101.23.13
-- 1.3.6.1.4.1.6296.101.23.13
		sleGponIgmpGroup OBJECT IDENTIFIER ::= { sleGpon 13 }


--
-- 1.3.6.1.4.1.6296.101.23.13.1
-- 1.3.6.1.4.1.6296.101.23.13.1
		sleGponIgmpGroupTable OBJECT-TYPE
			SYNTAX SEQUENCE OF SleGponIgmpGroupEntry
			MAX-ACCESS not-accessible
			STATUS current
			DESCRIPTION
				"sleGponIgmpGroupTable"
			::= { sleGponIgmpGroup 1 }


--   1.3.6.1.4.1.6296.101.23.13.1.1
-- 1.3.6.1.4.1.6296.101.23.13.1.1
		sleGponIgmpGroupEntry OBJECT-TYPE
			SYNTAX SleGponIgmpGroupEntry
			MAX-ACCESS not-accessible
			STATUS current
			DESCRIPTION
				"key: sleGponIgmpGroupOltId, sleGponIgmpGroupOnuId, sleGponIgmpGroupIndex"
			INDEX { sleGponIgmpGroupOltId, sleGponIgmpGroupOnuId, sleGponIgmpGroupIndex }
			::= { sleGponIgmpGroupTable 1 }


		SleGponIgmpGroupEntry ::=
			SEQUENCE {
				sleGponIgmpGroupOltId
					INTEGER,
				sleGponIgmpGroupOnuId
					INTEGER,
				sleGponIgmpGroupUniId
					INTEGER,
				sleGponIgmpGroupUniType
					INTEGER,
				sleGponIgmpGroupIndex
					INTEGER,
				sleGponIgmpGroupSrcIPAddr
					IpAddress,
				sleGponIgmpGroupDstIPAddr
					IpAddress,
				sleGponIgmpGroupRptIPAddr
					IpAddress,
				sleGponIgmpGroupJoinTime
					INTEGER,
				sleGponIgmpGroupVlanId
					INTEGER
			 }

		sleGponIgmpGroupOltId OBJECT-TYPE
			SYNTAX INTEGER (1..2147483647)
			MAX-ACCESS read-only
			STATUS current
			DESCRIPTION
				"The OLT id."
			::= { sleGponIgmpGroupEntry 1 }


--   1.3.6.1.4.1.6296.101.23.13.1.1.2
-- 1.3.6.1.4.1.6296.101.23.13.1.1.2
		sleGponIgmpGroupOnuId OBJECT-TYPE
			SYNTAX INTEGER (1..256)
			MAX-ACCESS read-only
			STATUS current
			DESCRIPTION
				"The ONU id."
			::= { sleGponIgmpGroupEntry 2 }


--   1.3.6.1.4.1.6296.101.23.13.1.1.3
-- 1.3.6.1.4.1.6296.101.23.13.1.1.3
		sleGponIgmpGroupUniId OBJECT-TYPE
			SYNTAX INTEGER (1..65535)
			MAX-ACCESS read-only
			STATUS current
			DESCRIPTION
				"The UNI id"
			::= { sleGponIgmpGroupEntry 3 }


--   1.3.6.1.4.1.6296.101.23.13.1.1.4
-- 1.3.6.1.4.1.6296.101.23.13.1.1.4
		sleGponIgmpGroupUniType OBJECT-TYPE
			SYNTAX INTEGER
				{
				ethernet(1),
				pots(2),
				ces(3),
				video(4),
				virtualEthernet(5),
				wifi(6),
				unknown(255)
				}
			MAX-ACCESS read-only
			STATUS current
			DESCRIPTION
				"The UNI type."
			::= { sleGponIgmpGroupEntry 4 }


--   1.3.6.1.4.1.6296.101.23.13.1.1.5
-- 1.3.6.1.4.1.6296.101.23.13.1.1.5
		sleGponIgmpGroupIndex OBJECT-TYPE
			SYNTAX INTEGER (1..65535)
			MAX-ACCESS read-only
			STATUS current
			DESCRIPTION
				"The IGMP group index."
			::= { sleGponIgmpGroupEntry 5 }


--   1.3.6.1.4.1.6296.101.23.13.1.1.6
-- 1.3.6.1.4.1.6296.101.23.13.1.1.6
		sleGponIgmpGroupSrcIPAddr OBJECT-TYPE
			SYNTAX IpAddress
			MAX-ACCESS read-only
			STATUS current
			DESCRIPTION
				"The source IP address"
			::= { sleGponIgmpGroupEntry 6 }


--
-- 1.3.6.1.4.1.6296.101.23.13.1.1.7
-- 1.3.6.1.4.1.6296.101.23.13.1.1.7
		sleGponIgmpGroupDstIPAddr OBJECT-TYPE
			SYNTAX IpAddress
			MAX-ACCESS read-only
			STATUS current
			DESCRIPTION
				"The destination IP address"
			::= { sleGponIgmpGroupEntry 7 }


--   1.3.6.1.4.1.6296.101.23.13.1.1.8
-- 1.3.6.1.4.1.6296.101.23.13.1.1.8
		sleGponIgmpGroupRptIPAddr OBJECT-TYPE
			SYNTAX IpAddress
			MAX-ACCESS read-only
			STATUS current
			DESCRIPTION
				"The  IP address"
			::= { sleGponIgmpGroupEntry 8 }


--
-- 1.3.6.1.4.1.6296.101.23.13.1.1.9
-- 1.3.6.1.4.1.6296.101.23.13.1.1.9
		sleGponIgmpGroupJoinTime OBJECT-TYPE
			SYNTAX INTEGER (1..65535)
			MAX-ACCESS read-only
			STATUS current
			DESCRIPTION
				"The join time."
			::= { sleGponIgmpGroupEntry 9 }


--  1.3.6.1.4.1.6296.101.23.13.1.1.10
		sleGponIgmpGroupVlanId OBJECT-TYPE
			SYNTAX INTEGER (1..4094)
			MAX-ACCESS read-only
			STATUS current
			DESCRIPTION
				"The Vlan Id."
			::= { sleGponIgmpGroupEntry 10 }


--  1.3.6.1.4.1.6296.101.23.13.2
		sleGponIgmpGroupControl OBJECT IDENTIFIER ::= { sleGponIgmpGroup 2 }


--  1.3.6.1.4.1.6296.101.23.13.2.1
		sleGponIgmpGroupControlRequest OBJECT-TYPE
			SYNTAX INTEGER { setGponIgmpGroup(1) }
			MAX-ACCESS read-write
			STATUS current
			DESCRIPTION
				"The request of a user command"
			::= { sleGponIgmpGroupControl 1 }


--  1.3.6.1.4.1.6296.101.23.13.2.2
		sleGponIgmpGroupControlStatus OBJECT-TYPE
			SYNTAX SleControlStatusType
			MAX-ACCESS read-write
			STATUS current
			DESCRIPTION
				"The status of user command"
			::= { sleGponIgmpGroupControl 2 }


--  1.3.6.1.4.1.6296.101.23.13.2.3
		sleGponIgmpGroupControlTimer OBJECT-TYPE
			SYNTAX Gauge32
			MAX-ACCESS read-write
			STATUS current
			DESCRIPTION
				"The maximum time for the manager for a long running user command"
			::= { sleGponIgmpGroupControl 3 }


--  1.3.6.1.4.1.6296.101.23.13.2.4
		sleGponIgmpGroupControlTimeStamp OBJECT-TYPE
			SYNTAX TimeTicks
			MAX-ACCESS read-write
			STATUS current
			DESCRIPTION
				"The time stamp of the last command(end of command)"
			::= { sleGponIgmpGroupControl 4 }


--  1.3.6.1.4.1.6296.101.23.13.2.5
		sleGponIgmpGroupControlReqResult OBJECT-TYPE
			SYNTAX SleControlRequestResultType
			MAX-ACCESS read-write
			STATUS current
			DESCRIPTION
				"The result of the last user command"
			::= { sleGponIgmpGroupControl 5 }


		sleGponIgmpGroupControlOltId OBJECT-TYPE
			SYNTAX Integer32 (1..2147483647)
			MAX-ACCESS read-write
			STATUS current
			DESCRIPTION
				"The OLT id."
			::= { sleGponIgmpGroupControl 6 }


--  1.3.6.1.4.1.6296.101.23.13.2.7
		sleGponIgmpGroupControlOnuId OBJECT-TYPE
			SYNTAX Integer32 (1..65535)
			MAX-ACCESS read-write
			STATUS current
			DESCRIPTION
				"The ONU id."
			::= { sleGponIgmpGroupControl 7 }


--  1.3.6.1.4.1.6296.101.23.13.3
		sleGponIgmpGroupNotification OBJECT IDENTIFIER ::= { sleGponIgmpGroup 3 }


--  1.3.6.1.4.1.6296.101.23.13.3.1
		sleGponIgmpGroupChanged NOTIFICATION-TYPE
			OBJECTS { sleGponIgmpGroupControlRequest, sleGponIgmpGroupControlTimeStamp, sleGponIgmpGroupControlReqResult, sleGponIgmpGroupControlOltId, sleGponIgmpGroupControlOnuId
				 }
			STATUS current
			DESCRIPTION
				"Description."
			::= { sleGponIgmpGroupNotification 1 }


--  1.3.6.1.4.1.6296.101.23.14
		sleGponAntiSpoofing OBJECT IDENTIFIER ::= { sleGpon 14 }


--  1.3.6.1.4.1.6296.101.23.14.1
		sleGponAntiSpoofingTable OBJECT-TYPE
			SYNTAX SEQUENCE OF SleGponAntiSpoofingEntry
			MAX-ACCESS not-accessible
			STATUS current
			DESCRIPTION
				"sleGponAntiSpoofingTable"
			::= { sleGponAntiSpoofing 1 }


--  1.3.6.1.4.1.6296.101.23.14.1.1
		sleGponAntiSpoofingEntry OBJECT-TYPE
			SYNTAX SleGponAntiSpoofingEntry
			MAX-ACCESS not-accessible
			STATUS current
			DESCRIPTION
				"key: sleGponAntiSpoofingOltId, sleGponAntiSpoofingOnuId, sleGponAntiSpoofingVlanId, sleGponAntiSpoofingMacIndex"
			INDEX { sleGponAntiSpoofingOltId, sleGponAntiSpoofingOnuId, sleGponAntiSpoofingVlanId, sleGponAntiSpoofingMacIndex }
			::= { sleGponAntiSpoofingTable 1 }


		SleGponAntiSpoofingEntry ::=
			SEQUENCE {
				sleGponAntiSpoofingOltId
					INTEGER,
				sleGponAntiSpoofingOnuId
					INTEGER,
				sleGponAntiSpoofingVlanId
					Integer32,
				sleGponAntiSpoofingMacIndex
					INTEGER,
				sleGponAntiSpoofingMac
					OCTET STRING,
				sleGponAntiSpoofingPortId
					INTEGER,
				sleGponAntiSpoofingDupPortId
					INTEGER,
				sleGponAntiSpoofingTimerStatus
					INTEGER,
				sleGponAntiSpoofingFilterStatus
					INTEGER
			 }

--  1.3.6.1.4.1.6296.101.23.14.1.1.1
		sleGponAntiSpoofingOltId OBJECT-TYPE
			SYNTAX INTEGER (1..2147483647)
			MAX-ACCESS read-only
			STATUS current
			DESCRIPTION
				"The OLT index."
			::= { sleGponAntiSpoofingEntry 1 }


--  1.3.6.1.4.1.6296.101.23.14.1.1.2
		sleGponAntiSpoofingOnuId OBJECT-TYPE
			SYNTAX INTEGER (1..256)
			MAX-ACCESS read-only
			STATUS current
			DESCRIPTION
				"The ONU index."
			::= { sleGponAntiSpoofingEntry 2 }


--  1.3.6.1.4.1.6296.101.23.14.1.1.3
		sleGponAntiSpoofingVlanId OBJECT-TYPE
			SYNTAX Integer32 (1..4094)
			MAX-ACCESS read-only
			STATUS current
			DESCRIPTION
				"The VLAN index."
			::= { sleGponAntiSpoofingEntry 3 }


--  1.3.6.1.4.1.6296.101.23.14.1.1.4
		sleGponAntiSpoofingMacIndex OBJECT-TYPE
			SYNTAX INTEGER (1..65535)
			MAX-ACCESS read-only
			STATUS current
			DESCRIPTION
				"The MAC index is only used at 'Get'. "
			::= { sleGponAntiSpoofingEntry 4 }


--  1.3.6.1.4.1.6296.101.23.14.1.1.5
		sleGponAntiSpoofingMac OBJECT-TYPE
			SYNTAX OCTET STRING
			MAX-ACCESS read-only
			STATUS current
			DESCRIPTION
				"The OLT mac address."
			::= { sleGponAntiSpoofingEntry 5 }


--  1.3.6.1.4.1.6296.101.23.14.1.1.6
		sleGponAntiSpoofingPortId OBJECT-TYPE
			SYNTAX INTEGER (1..65535)
			MAX-ACCESS read-only
			STATUS current
			DESCRIPTION
				"The Port index."
			::= { sleGponAntiSpoofingEntry 6 }


--  1.3.6.1.4.1.6296.101.23.14.1.1.7
		sleGponAntiSpoofingDupPortId OBJECT-TYPE
			SYNTAX INTEGER (1..65535)
			MAX-ACCESS read-only
			STATUS current
			DESCRIPTION
				"The Duplicated Port index."
			::= { sleGponAntiSpoofingEntry 7 }


--  1.3.6.1.4.1.6296.101.23.14.1.1.8
		sleGponAntiSpoofingTimerStatus OBJECT-TYPE
			SYNTAX INTEGER (1..65535)
			MAX-ACCESS read-only
			STATUS current
			DESCRIPTION
				"The Anti-Spoofing Timer."
			::= { sleGponAntiSpoofingEntry 8 }


--  1.3.6.1.4.1.6296.101.23.14.1.1.9
		sleGponAntiSpoofingFilterStatus OBJECT-TYPE
			SYNTAX INTEGER
				{
				filtering(0),
				notSupport(1)
				}
			MAX-ACCESS read-only
			STATUS current
			DESCRIPTION
				"The filter status."
			::= { sleGponAntiSpoofingEntry 9 }


--  1.3.6.1.4.1.6296.101.23.14.2
		sleGponAntiSpoofingControl OBJECT IDENTIFIER ::= { sleGponAntiSpoofing 2 }


--  1.3.6.1.4.1.6296.101.23.14.2.1
		sleGponAntiSpoofingControlRequest OBJECT-TYPE
			SYNTAX INTEGER
				{
				updateAntiSpoofingStatus(1),
				clearAntiSpoofingOlt(2),
				clearAntiSpoofingOnu(3),
				clearAntiSpoofingOne(4)
				}
			MAX-ACCESS read-write
			STATUS current
			DESCRIPTION
				"The request of a user command"
			::= { sleGponAntiSpoofingControl 1 }


--  1.3.6.1.4.1.6296.101.23.14.2.2
		sleGponAntiSpoofingControlStatus OBJECT-TYPE
			SYNTAX SleControlStatusType
			MAX-ACCESS read-write
			STATUS current
			DESCRIPTION
				"The status of user command"
			::= { sleGponAntiSpoofingControl 2 }


--  1.3.6.1.4.1.6296.101.23.14.2.3
		sleGponAntiSpoofingControlTimer OBJECT-TYPE
			SYNTAX Gauge32
			MAX-ACCESS read-write
			STATUS current
			DESCRIPTION
				"The maximum time for the manager for a long running user command"
			::= { sleGponAntiSpoofingControl 3 }


--  1.3.6.1.4.1.6296.101.23.14.2.4
		sleGponAntiSpoofingControlTimeStamp OBJECT-TYPE
			SYNTAX TimeTicks
			MAX-ACCESS read-write
			STATUS current
			DESCRIPTION
				"The time stamp of the last command(end of command)"
			::= { sleGponAntiSpoofingControl 4 }


--  1.3.6.1.4.1.6296.101.23.14.2.5
		sleGponAntiSpoofingControlReqResult OBJECT-TYPE
			SYNTAX SleControlRequestResultType
			MAX-ACCESS read-write
			STATUS current
			DESCRIPTION
				"The result of the last user command"
			::= { sleGponAntiSpoofingControl 5 }


--  1.3.6.1.4.1.6296.101.23.14.2.6
		sleGponAntiSpoofingControlOltId OBJECT-TYPE
			SYNTAX INTEGER (1..2147483647)
			MAX-ACCESS read-write
			STATUS current
			DESCRIPTION
				"The OLT index."
			::= { sleGponAntiSpoofingControl 6 }


--  1.3.6.1.4.1.6296.101.23.14.2.7
		sleGponAntiSpoofingControlOnuId OBJECT-TYPE
			SYNTAX INTEGER (1..256)
			MAX-ACCESS read-write
			STATUS current
			DESCRIPTION
				"The ONU index."
			::= { sleGponAntiSpoofingControl 7 }


--  1.3.6.1.4.1.6296.101.23.14.2.8
		sleGponAntiSpoofingControlVlanId OBJECT-TYPE
			SYNTAX Integer32 (1..4094)
			MAX-ACCESS read-write
			STATUS current
			DESCRIPTION
				"The VLAN index."
			::= { sleGponAntiSpoofingControl 8 }


--  1.3.6.1.4.1.6296.101.23.14.2.9
		sleGponAntiSpoofingControlMac OBJECT-TYPE
			SYNTAX OCTET STRING
			MAX-ACCESS read-write
			STATUS current
			DESCRIPTION
				"The OLT mac address."
			::= { sleGponAntiSpoofingControl 9 }


--  1.3.6.1.4.1.6296.101.23.14.2.10
		sleGponAntiSpoofingControlPortId OBJECT-TYPE
			SYNTAX INTEGER (1..65535)
			MAX-ACCESS read-write
			STATUS current
			DESCRIPTION
				"The Port index."
			::= { sleGponAntiSpoofingControl 10 }


--  1.3.6.1.4.1.6296.101.23.14.2.11
		sleGponAntiSpoofingControlTimerStatus OBJECT-TYPE
			SYNTAX INTEGER (1..65535)
			MAX-ACCESS read-write
			STATUS current
			DESCRIPTION
				"The Anti-Spoofing Timer."
			::= { sleGponAntiSpoofingControl 11 }


--  1.3.6.1.4.1.6296.101.23.14.3
		sleGponAntiSpoofingNotification OBJECT IDENTIFIER ::= { sleGponAntiSpoofing 3 }


--  1.3.6.1.4.1.6296.101.23.14.3.1
		sleGponAntiSpoofingAntiSpoofingStatusChanged NOTIFICATION-TYPE
			OBJECTS { sleGponAntiSpoofingControlRequest, sleGponAntiSpoofingControlTimeStamp, sleGponAntiSpoofingControlReqResult, sleGponAntiSpoofingControlOltId }
			STATUS current
			DESCRIPTION
				"Description."
			::= { sleGponAntiSpoofingNotification 1 }


--  1.3.6.1.4.1.6296.101.23.14.3.2
		sleGponAntiSpoofingAntiSpoofingOltCleared NOTIFICATION-TYPE
			OBJECTS { sleGponAntiSpoofingControlRequest, sleGponAntiSpoofingControlTimeStamp, sleGponAntiSpoofingControlReqResult, sleGponAntiSpoofingControlOltId }
			STATUS current
			DESCRIPTION
				"Description."
			::= { sleGponAntiSpoofingNotification 2 }


--  1.3.6.1.4.1.6296.101.23.14.3.3
		sleGponAntiSpoofingAntiSpoofingOnuCleared NOTIFICATION-TYPE
			OBJECTS { sleGponAntiSpoofingControlRequest, sleGponAntiSpoofingControlTimeStamp, sleGponAntiSpoofingControlReqResult, sleGponAntiSpoofingControlOltId, sleGponAntiSpoofingControlOnuId
				 }
			STATUS current
			DESCRIPTION
				"Description."
			::= { sleGponAntiSpoofingNotification 3 }


--  1.3.6.1.4.1.6296.101.23.14.3.4
		sleGponAntiSpoofingAntiSpoofingOneCleared NOTIFICATION-TYPE
			OBJECTS { sleGponAntiSpoofingControlRequest, sleGponAntiSpoofingControlTimeStamp, sleGponAntiSpoofingControlReqResult, sleGponAntiSpoofingControlOltId, sleGponAntiSpoofingControlOnuId,
				sleGponAntiSpoofingControlVlanId, sleGponAntiSpoofingControlMac }
			STATUS current
			DESCRIPTION
				"Description."
			::= { sleGponAntiSpoofingNotification 4 }


--  1.3.6.1.4.1.6296.101.23.15
		sleGponVlanGemMapping OBJECT IDENTIFIER ::= { sleGpon 15 }


--  1.3.6.1.4.1.6296.101.23.15.1
		sleGponVlanGemMappingTable OBJECT-TYPE
			SYNTAX SEQUENCE OF SleGponVlanGemMappingEntry
			MAX-ACCESS not-accessible
			STATUS current
			DESCRIPTION
				"sleGpoVlanGemMappingTable"
			::= { sleGponVlanGemMapping 1 }


--  1.3.6.1.4.1.6296.101.23.15.1.1
		sleGponVlanGemMappingEntry OBJECT-TYPE
			SYNTAX SleGponVlanGemMappingEntry
			MAX-ACCESS not-accessible
			STATUS current
			DESCRIPTION
				"key: sleGponOltId, sleGponOnuId, sleGponVlanGemMappingVid"
			INDEX { sleGponOltId, sleGponVlanGemMappingVid }
			::= { sleGponVlanGemMappingTable 1 }


		SleGponVlanGemMappingEntry ::=
			SEQUENCE {
				sleGponVlanGemMappingVid
					INTEGER,
				sleGponVlanGemMappingOnuid
					INTEGER,
				sleGponVlanGemMappingMapperId
					INTEGER,
				sleGponVlanGemMappingGemPort
					INTEGER
			 }

--  1.3.6.1.4.1.6296.101.23.15.1.1.1
		sleGponVlanGemMappingVid OBJECT-TYPE
			SYNTAX INTEGER (1..4094)
			MAX-ACCESS read-only
			STATUS current
			DESCRIPTION
				"The Vlan ID."
			::= { sleGponVlanGemMappingEntry 1 }


--  1.3.6.1.4.1.6296.101.23.15.1.1.2
		sleGponVlanGemMappingOnuid OBJECT-TYPE
			SYNTAX INTEGER (1..256)
			MAX-ACCESS read-only
			STATUS current
			DESCRIPTION
				"The ONU index. (255 is all onu)"
			::= { sleGponVlanGemMappingEntry 2 }


--  1.3.6.1.4.1.6296.101.23.15.1.1.3
		sleGponVlanGemMappingMapperId OBJECT-TYPE
			SYNTAX INTEGER (1..65535)
			MAX-ACCESS read-only
			STATUS current
			DESCRIPTION
				"The mapper ID. (4095 is multicast gem)"
			::= { sleGponVlanGemMappingEntry 3 }


--  1.3.6.1.4.1.6296.101.23.15.1.1.4
		sleGponVlanGemMappingGemPort OBJECT-TYPE
			SYNTAX INTEGER (1..65535)
			MAX-ACCESS read-only
			STATUS current
			DESCRIPTION
				"The GEM port."
			::= { sleGponVlanGemMappingEntry 4 }


--  1.3.6.1.4.1.6296.101.23.15.2
		sleGponVlanGemMappingControl OBJECT IDENTIFIER ::= { sleGponVlanGemMapping 2 }


--  1.3.6.1.4.1.6296.101.23.15.2.1
		sleGponVlanGemMappingControlRequest OBJECT-TYPE
			SYNTAX INTEGER
				{
				setVlanGemMapping(1),
				clearVlanGemMapping(2),
				clearOnuVlanGemMapping(3),
				clearOltVlanGemMapping(4)
				}
			MAX-ACCESS read-write
			STATUS current
			DESCRIPTION
				"The request of a user command"
			::= { sleGponVlanGemMappingControl 1 }


--  1.3.6.1.4.1.6296.101.23.15.2.2
		sleGponVlanGemMappingControlStatus OBJECT-TYPE
			SYNTAX SleControlStatusType
			MAX-ACCESS read-only
			STATUS current
			DESCRIPTION
				"The status of user command"
			::= { sleGponVlanGemMappingControl 2 }


--  1.3.6.1.4.1.6296.101.23.15.2.3
		sleGponVlanGemMappingControlTimer OBJECT-TYPE
			SYNTAX Gauge32
			MAX-ACCESS read-write
			STATUS current
			DESCRIPTION
				"The maximum time for the manager for a long running user command"
			::= { sleGponVlanGemMappingControl 3 }


--  1.3.6.1.4.1.6296.101.23.15.2.4
		sleGponVlanGemMappingControlTimeStamp OBJECT-TYPE
			SYNTAX TimeTicks
			MAX-ACCESS read-only
			STATUS current
			DESCRIPTION
				"The time stamp of the last command(end of command)"
			::= { sleGponVlanGemMappingControl 4 }


--  1.3.6.1.4.1.6296.101.23.15.2.5
		sleGponVlanGemMappingControlReqResult OBJECT-TYPE
			SYNTAX SleControlRequestResultType
			MAX-ACCESS read-only
			STATUS current
			DESCRIPTION
				"The result of the last user command"
			::= { sleGponVlanGemMappingControl 5 }


		sleGponVlanGemMappingControlOltId OBJECT-TYPE
			SYNTAX INTEGER (1..2147483647)
			MAX-ACCESS read-write
			STATUS current
			DESCRIPTION
				"The OLT ID."
			::= { sleGponVlanGemMappingControl 6 }


--  1.3.6.1.4.1.6296.101.23.15.2.7
		sleGponVlanGemMappingControlOnuId OBJECT-TYPE
			SYNTAX INTEGER (1..256)
			MAX-ACCESS read-write
			STATUS current
			DESCRIPTION
				"The ONU index. (255 is all onu)"
			::= { sleGponVlanGemMappingControl 7 }


--  1.3.6.1.4.1.6296.101.23.15.2.8
		sleGponVlanGemMappingControlVid OBJECT-TYPE
			SYNTAX INTEGER (1..4094)
			MAX-ACCESS read-write
			STATUS current
			DESCRIPTION
				"The Vlan ID."
			::= { sleGponVlanGemMappingControl 8 }


--  1.3.6.1.4.1.6296.101.23.15.2.9
		sleGponVlanGemMappingControlMapperId OBJECT-TYPE
			SYNTAX INTEGER (1..65535)
			MAX-ACCESS read-write
			STATUS current
			DESCRIPTION
				"The mapper ID. (4095 is multicast gem)"
			::= { sleGponVlanGemMappingControl 9 }


--   1.3.6.1.4.1.6296.101.23.15.2.10
-- 1.3.6.1.4.1.6296.101.23.15.2.10
		sleGponVlanGemMappingControlVidTo OBJECT-TYPE
			SYNTAX INTEGER (1..4094)
			MAX-ACCESS read-write
			STATUS current
			DESCRIPTION
				"The Vlan ID."
			::= { sleGponVlanGemMappingControl 10 }


--   1.3.6.1.4.1.6296.101.23.15.3
-- 1.3.6.1.4.1.6296.101.23.15.3
		sleGpoVlanGemMappingNotification OBJECT IDENTIFIER ::= { sleGponVlanGemMapping 3 }


--   1.3.6.1.4.1.6296.101.23.15.3.1
-- 1.3.6.1.4.1.6296.101.23.15.3.1
		sleGponVlanGemMappingChagned NOTIFICATION-TYPE
			OBJECTS { sleGponVlanGemMappingControlRequest, sleGponVlanGemMappingControlTimeStamp, sleGponVlanGemMappingControlReqResult, sleGponVlanGemMappingControlOltId, sleGponVlanGemMappingControlOnuId,
				sleGponVlanGemMappingControlVid, sleGponVlanGemMappingControlMapperId, sleGponVlanGemMappingControlVidTo }
			STATUS current
			DESCRIPTION
				"sleGponVlanGemMappingControlRequest, sleGponVlanGemMappingControlTimeStamp, sleGponVlanGemMappingControlReqResult, sleGponVlanGemMappingControlOltId, sleGponVlanGemMappingControlOnuId, sleGponVlanGemMappingControlVid, sleGponVlanGemMappingControlMapperId, sleGponVlanGemMappingControlVidTo"
			::= { sleGpoVlanGemMappingNotification 1 }


--   1.3.6.1.4.1.6296.101.23.15.3.2
-- 1.3.6.1.4.1.6296.101.23.15.3.2
		sleGponVlanGemMappingCleared NOTIFICATION-TYPE
			OBJECTS { sleGponVlanGemMappingControlRequest, sleGponVlanGemMappingControlTimeStamp, sleGponVlanGemMappingControlReqResult, sleGponVlanGemMappingControlOltId, sleGponVlanGemMappingControlOnuId,
				sleGponVlanGemMappingControlVid, sleGponVlanGemMappingControlVidTo }
			STATUS current
			DESCRIPTION
				"sleGponVlanGemMappingControlRequest, sleGponVlanGemMappingControlTimeStamp, sleGponVlanGemMappingControlReqResult, sleGponVlanGemMappingControlOltId, sleGponVlanGemMappingControlOnuId, sleGponVlanGemMappingControlVid, sleGponVlanGemMappingControlMapperId, sleGponVlanGemMappingControlVidTo"
			::= { sleGpoVlanGemMappingNotification 2 }


--   1.3.6.1.4.1.6296.101.23.15.3.3
-- 1.3.6.1.4.1.6296.101.23.15.3.3
		sleGponOnuVlanGemMappingCleared NOTIFICATION-TYPE
			OBJECTS { sleGponVlanGemMappingControlRequest, sleGponVlanGemMappingControlTimeStamp, sleGponVlanGemMappingControlReqResult, sleGponVlanGemMappingControlOltId, sleGponVlanGemMappingControlOnuId
				 }
			STATUS current
			DESCRIPTION
				"clearOnuVlanGemMapping"
			::= { sleGpoVlanGemMappingNotification 3 }


--   1.3.6.1.4.1.6296.101.23.15.3.4
-- 1.3.6.1.4.1.6296.101.23.15.3.4
		sleGponOltVlanGemMappingCleared NOTIFICATION-TYPE
			OBJECTS { sleGponVlanGemMappingControlRequest, sleGponVlanGemMappingControlTimeStamp, sleGponVlanGemMappingControlReqResult, sleGponVlanGemMappingControlOltId }
			STATUS current
			DESCRIPTION
				"clearOltVlanGemMapping"
			::= { sleGpoVlanGemMappingNotification 4 }


--  1.3.6.1.4.1.6296.101.23.16
		sleGponGemPort OBJECT IDENTIFIER ::= { sleGpon 16 }


--  1.3.6.1.4.1.6296.101.23.16.1
		sleGponGemPortTable OBJECT-TYPE
			SYNTAX SEQUENCE OF SleGponGemPortEntry
			MAX-ACCESS not-accessible
			STATUS current
			DESCRIPTION
				"sleGponGemPortTable"
			::= { sleGponGemPort 1 }


--  1.3.6.1.4.1.6296.101.23.16.1.1
		sleGponGemPortEntry OBJECT-TYPE
			SYNTAX SleGponGemPortEntry
			MAX-ACCESS not-accessible
			STATUS current
			DESCRIPTION
				"key : sleGponOltId, sleGponOnuId, sleGponGemPortId"
			INDEX { sleGponOltId, sleGponOnuId, sleGponGemPortId }
			::= { sleGponGemPortTable 1 }


		SleGponGemPortEntry ::=
			SEQUENCE {
				sleGponGemPortId
					INTEGER,
				sleGponGemPortNum
					INTEGER,
				sleGponGemPortMapperId
					INTEGER,
				sleGponGemPortCos
					BITS
			 }

--  1.3.6.1.4.1.6296.101.23.16.1.1.1
		sleGponGemPortId OBJECT-TYPE
			SYNTAX INTEGER (1..65535)
			MAX-ACCESS read-only
			STATUS current
			DESCRIPTION
				"the GEM port index."
			::= { sleGponGemPortEntry 1 }


--  1.3.6.1.4.1.6296.101.23.16.1.1.2
		sleGponGemPortNum OBJECT-TYPE
			SYNTAX INTEGER (128..4096)
			MAX-ACCESS read-only
			STATUS current
			DESCRIPTION
				"The GEM Port number."
			::= { sleGponGemPortEntry 2 }


--  1.3.6.1.4.1.6296.101.23.16.1.1.3
		sleGponGemPortMapperId OBJECT-TYPE
			SYNTAX INTEGER (1..65535)
			MAX-ACCESS read-only
			STATUS current
			DESCRIPTION
				"The mapper index."
			::= { sleGponGemPortEntry 3 }


--  1.3.6.1.4.1.6296.101.23.16.1.1.4
		sleGponGemPortCos OBJECT-TYPE
			SYNTAX BITS
				{
				cos0(0),
				cos1(1),
				cos2(2),
				cos3(3),
				cos4(4),
				cos5(5),
				cos6(6),
				cos7(7)
				}
			MAX-ACCESS read-only
			STATUS current
			DESCRIPTION
				"The CoS value."
			::= { sleGponGemPortEntry 4 }


--  1.3.6.1.4.1.6296.101.23.17
		sleGponOnuMcast OBJECT IDENTIFIER ::= { sleGpon 17 }


--  1.3.6.1.4.1.6296.101.23.17.1
		sleGponOnuMcastAcl OBJECT IDENTIFIER ::= { sleGponOnuMcast 1 }


--  1.3.6.1.4.1.6296.101.23.17.1.1
		sleGponOnuMcastAclTable OBJECT-TYPE
			SYNTAX SEQUENCE OF SleGponOnuMcastAclEntry
			MAX-ACCESS not-accessible
			STATUS current
			DESCRIPTION
				"Description."
			::= { sleGponOnuMcastAcl 1 }


--  1.3.6.1.4.1.6296.101.23.17.1.1.1
		sleGponOnuMcastAclEntry OBJECT-TYPE
			SYNTAX SleGponOnuMcastAclEntry
			MAX-ACCESS not-accessible
			STATUS current
			DESCRIPTION
				"Description."
			INDEX { sleGponOltId, sleGponOnuId, sleGponOnuMcastAclMcastIndex, sleGponOnuMcastAclTableIndex }
			::= { sleGponOnuMcastAclTable 1 }


		SleGponOnuMcastAclEntry ::=
			SEQUENCE {
				sleGponOnuMcastAclOltId
					Integer32,
				sleGponOnuMcastAclOnuId
					Integer32,
				sleGponOnuMcastAclMcastIndex
					Integer32,
				sleGponOnuMcastAclMcastName
					OCTET STRING,
				sleGponOnuMcastAclTableIndex
					Integer32,
				sleGponOnuMcastAclVid
					Integer32,
				sleGponOnuMcastAclDstIpStart
					IpAddress,
				sleGponOnuMcastAclDstIpEnd
					IpAddress,
				sleGponOnuMcastAclSrcIp
					IpAddress,
				sleGponOnuMcastAclBandwidth
					Integer32,
				sleGponOnuMcastAclGem
					Integer32
			 }

		sleGponOnuMcastAclOltId OBJECT-TYPE
			SYNTAX Integer32 (1..2147483647)
			MAX-ACCESS read-only
			STATUS current
			DESCRIPTION
				"The OLT index."
			::= { sleGponOnuMcastAclEntry 1 }


--  1.3.6.1.4.1.6296.101.23.17.1.1.1.2
		sleGponOnuMcastAclOnuId OBJECT-TYPE
			SYNTAX Integer32 (1..256)
			MAX-ACCESS read-only
			STATUS current
			DESCRIPTION
				"The ONU index."
			::= { sleGponOnuMcastAclEntry 2 }


--  1.3.6.1.4.1.6296.101.23.17.1.1.1.3
		sleGponOnuMcastAclMcastIndex OBJECT-TYPE
			SYNTAX Integer32 (1..65535)
			MAX-ACCESS read-only
			STATUS current
			DESCRIPTION
				"The Mcast Index."
			::= { sleGponOnuMcastAclEntry 3 }


--  1.3.6.1.4.1.6296.101.23.17.1.1.1.4
		sleGponOnuMcastAclMcastName OBJECT-TYPE
			SYNTAX OCTET STRING
			MAX-ACCESS read-only
			STATUS current
			DESCRIPTION
				"The Mcast name."
			::= { sleGponOnuMcastAclEntry 4 }


--  1.3.6.1.4.1.6296.101.23.17.1.1.1.5
		sleGponOnuMcastAclTableIndex OBJECT-TYPE
			SYNTAX Integer32 (1..65535)
			MAX-ACCESS read-only
			STATUS current
			DESCRIPTION
				"The table index."
			::= { sleGponOnuMcastAclEntry 5 }


--  1.3.6.1.4.1.6296.101.23.17.1.1.1.6
		sleGponOnuMcastAclVid OBJECT-TYPE
			SYNTAX Integer32 (1..4094)
			MAX-ACCESS read-only
			STATUS current
			DESCRIPTION
				"The vlan index."
			::= { sleGponOnuMcastAclEntry 6 }


--  1.3.6.1.4.1.6296.101.23.17.1.1.1.7
		sleGponOnuMcastAclDstIpStart OBJECT-TYPE
			SYNTAX IpAddress
			MAX-ACCESS read-only
			STATUS current
			DESCRIPTION
				"The destination start ip-address."
			::= { sleGponOnuMcastAclEntry 7 }


--  1.3.6.1.4.1.6296.101.23.17.1.1.1.8
		sleGponOnuMcastAclDstIpEnd OBJECT-TYPE
			SYNTAX IpAddress
			MAX-ACCESS read-only
			STATUS current
			DESCRIPTION
				"The destination end ip-address."
			::= { sleGponOnuMcastAclEntry 8 }


--  1.3.6.1.4.1.6296.101.23.17.1.1.1.9
		sleGponOnuMcastAclSrcIp OBJECT-TYPE
			SYNTAX IpAddress
			MAX-ACCESS read-only
			STATUS current
			DESCRIPTION
				"The source ip-address."
			::= { sleGponOnuMcastAclEntry 9 }


--  1.3.6.1.4.1.6296.101.23.17.1.1.1.10
		sleGponOnuMcastAclBandwidth OBJECT-TYPE
			SYNTAX Integer32
			MAX-ACCESS read-only
			STATUS current
			DESCRIPTION
				"The bandwidth"
			::= { sleGponOnuMcastAclEntry 10 }


--  1.3.6.1.4.1.6296.101.23.17.1.1.1.11
		sleGponOnuMcastAclGem OBJECT-TYPE
			SYNTAX Integer32 (1..65535)
			MAX-ACCESS read-only
			STATUS current
			DESCRIPTION
				"The Gem port index."
			::= { sleGponOnuMcastAclEntry 11 }


--  1.3.6.1.4.1.6296.101.23.17.1.2
		sleGponOnuMcastAclControl OBJECT IDENTIFIER ::= { sleGponOnuMcastAcl 2 }


--  1.3.6.1.4.1.6296.101.23.17.1.2.1
		sleGponOnuMcastAclControlRequest OBJECT-TYPE
			SYNTAX INTEGER
				{
				createMcastAcl(1),
				clearMcastAcl(2),
				clearMcastAclOnu(3),
				clearMcastAclOlt(4)
				}
			MAX-ACCESS read-write
			STATUS current
			DESCRIPTION
				"The request of a user command"
			::= { sleGponOnuMcastAclControl 1 }


--  1.3.6.1.4.1.6296.101.23.17.1.2.2
		sleGponOnuMcastAclControlStatus OBJECT-TYPE
			SYNTAX SleControlStatusType
			MAX-ACCESS read-only
			STATUS current
			DESCRIPTION
				"The status of user command"
			::= { sleGponOnuMcastAclControl 2 }


--  1.3.6.1.4.1.6296.101.23.17.1.2.3
		sleGponOnuMcastAclControlTimer OBJECT-TYPE
			SYNTAX Gauge32
			MAX-ACCESS read-write
			STATUS current
			DESCRIPTION
				"The maximum time for the manager for a long running user command"
			::= { sleGponOnuMcastAclControl 3 }


--  1.3.6.1.4.1.6296.101.23.17.1.2.4
		sleGponOnuMcastAclControlTimeStamp OBJECT-TYPE
			SYNTAX TimeTicks
			MAX-ACCESS read-only
			STATUS current
			DESCRIPTION
				"The time stamp of the last command(end of command)"
			::= { sleGponOnuMcastAclControl 4 }


--  1.3.6.1.4.1.6296.101.23.17.1.2.5
		sleGponOnuMcastAclControlReqResult OBJECT-TYPE
			SYNTAX SleControlRequestResultType
			MAX-ACCESS read-only
			STATUS current
			DESCRIPTION
				"The result of the last user command"
			::= { sleGponOnuMcastAclControl 5 }


		sleGponOnuMcastAclControlOltId OBJECT-TYPE
			SYNTAX Integer32 (1..2147483647)
			MAX-ACCESS read-write
			STATUS current
			DESCRIPTION
				"The OLT index."
			::= { sleGponOnuMcastAclControl 6 }


--  1.3.6.1.4.1.6296.101.23.17.1.2.7
		sleGponOnuMcastAclControlOnuId OBJECT-TYPE
			SYNTAX Integer32 (1..256)
			MAX-ACCESS read-write
			STATUS current
			DESCRIPTION
				"The ONU index."
			::= { sleGponOnuMcastAclControl 7 }


--  1.3.6.1.4.1.6296.101.23.17.1.2.8
		sleGponOnuMcastAclControlMcastName OBJECT-TYPE
			SYNTAX OCTET STRING
			MAX-ACCESS read-write
			STATUS current
			DESCRIPTION
				"The Mcase name."
			::= { sleGponOnuMcastAclControl 8 }


--  1.3.6.1.4.1.6296.101.23.17.1.2.9
		sleGponOnuMcastAclControlTableIndex OBJECT-TYPE
			SYNTAX Integer32 (1..65535)
			MAX-ACCESS read-write
			STATUS current
			DESCRIPTION
				"The table index."
			::= { sleGponOnuMcastAclControl 9 }


--  1.3.6.1.4.1.6296.101.23.17.1.2.10
		sleGponOnuMcastAclControlVid OBJECT-TYPE
			SYNTAX Integer32 (1..4094)
			MAX-ACCESS read-write
			STATUS current
			DESCRIPTION
				"The vlan index."
			::= { sleGponOnuMcastAclControl 10 }


--  1.3.6.1.4.1.6296.101.23.17.1.2.11
		sleGponOnuMcastAclControlDstIpStart OBJECT-TYPE
			SYNTAX IpAddress
			MAX-ACCESS read-write
			STATUS current
			DESCRIPTION
				"The destination start ip-address."
			::= { sleGponOnuMcastAclControl 11 }


--  1.3.6.1.4.1.6296.101.23.17.1.2.12
		sleGponOnuMcastAclControlDstIpEnd OBJECT-TYPE
			SYNTAX IpAddress
			MAX-ACCESS read-write
			STATUS current
			DESCRIPTION
				"The destination end ip-address."
			::= { sleGponOnuMcastAclControl 12 }


--  1.3.6.1.4.1.6296.101.23.17.1.2.13
		sleGponOnuMcastAclControlSrcIp OBJECT-TYPE
			SYNTAX IpAddress
			MAX-ACCESS read-write
			STATUS current
			DESCRIPTION
				"The source ip-address."
			::= { sleGponOnuMcastAclControl 13 }


--  1.3.6.1.4.1.6296.101.23.17.1.2.14
		sleGponOnuMcastAclControlBandwidth OBJECT-TYPE
			SYNTAX Integer32
			MAX-ACCESS read-write
			STATUS current
			DESCRIPTION
				"The bandwidth"
			::= { sleGponOnuMcastAclControl 14 }


--  1.3.6.1.4.1.6296.101.23.17.1.2.15
		sleGponOnuMcastAclControlGem OBJECT-TYPE
			SYNTAX Integer32 (1..65535)
			MAX-ACCESS read-write
			STATUS current
			DESCRIPTION
				"The Gem port index."
			::= { sleGponOnuMcastAclControl 15 }


--  1.3.6.1.4.1.6296.101.23.17.1.3
		sleGponOnuMcastAclNotification OBJECT IDENTIFIER ::= { sleGponOnuMcastAcl 3 }


--  1.3.6.1.4.1.6296.101.23.17.1.3.1
		sleGponOnuMcastAclCreated NOTIFICATION-TYPE
			OBJECTS { sleGponOnuMcastAclControlRequest, sleGponOnuMcastAclControlTimeStamp, sleGponOnuMcastAclControlReqResult, sleGponOnuMcastAclControlOltId, sleGponOnuMcastAclControlOnuId,
				sleGponOnuMcastAclControlMcastName, sleGponOnuMcastAclControlTableIndex, sleGponOnuMcastAclControlVid, sleGponOnuMcastAclControlDstIpStart, sleGponOnuMcastAclControlDstIpEnd,
				sleGponOnuMcastAclControlSrcIp, sleGponOnuMcastAclControlBandwidth, sleGponOnuMcastAclControlGem }
			STATUS current
			DESCRIPTION
				"createMcastAcl"
			::= { sleGponOnuMcastAclNotification 1 }


--  1.3.6.1.4.1.6296.101.23.17.1.3.2
		sleGponOnuMcastAclCleared NOTIFICATION-TYPE
			OBJECTS { sleGponOnuMcastAclControlRequest, sleGponOnuMcastAclControlTimeStamp, sleGponOnuMcastAclControlReqResult, sleGponOnuMcastAclControlOltId, sleGponOnuMcastAclControlOnuId,
				sleGponOnuMcastAclControlMcastName, sleGponOnuMcastAclControlTableIndex }
			STATUS current
			DESCRIPTION
				"clearMcastAcl"
			::= { sleGponOnuMcastAclNotification 2 }


--  1.3.6.1.4.1.6296.101.23.17.1.3.3
		sleGponOnuMcastAclOnuCleared NOTIFICATION-TYPE
			OBJECTS { sleGponOnuMcastAclControlRequest, sleGponOnuMcastAclControlTimeStamp, sleGponOnuMcastAclControlReqResult, sleGponOnuMcastAclControlOltId, sleGponOnuMcastAclControlOnuId
				 }
			STATUS current
			DESCRIPTION
				"clearMcastAclOnu"
			::= { sleGponOnuMcastAclNotification 3 }


--  1.3.6.1.4.1.6296.101.23.17.1.3.4
		sleGponOnuMcastAclOltCleared NOTIFICATION-TYPE
			OBJECTS { sleGponOnuMcastAclControlRequest, sleGponOnuMcastAclControlTimeStamp, sleGponOnuMcastAclControlReqResult, sleGponOnuMcastAclControlOltId }
			STATUS current
			DESCRIPTION
				"Description."
			::= { sleGponOnuMcastAclNotification 4 }


--  1.3.6.1.4.1.6296.101.23.18
		sleGponFlowMapping OBJECT IDENTIFIER ::= { sleGpon 18 }


--  1.3.6.1.4.1.6296.101.23.18.1
		sleGponFlowMappingMethod OBJECT IDENTIFIER ::= { sleGponFlowMapping 1 }


--  1.3.6.1.4.1.6296.101.23.18.1.1
		sleGponFlowMappingMethodTable OBJECT-TYPE
			SYNTAX SEQUENCE OF SleGponFlowMappingMethodEntry
			MAX-ACCESS not-accessible
			STATUS current
			DESCRIPTION
				"Description."
			::= { sleGponFlowMappingMethod 1 }


--  1.3.6.1.4.1.6296.101.23.18.1.1.1
		sleGponFlowMappingMethodEntry OBJECT-TYPE
			SYNTAX SleGponFlowMappingMethodEntry
			MAX-ACCESS not-accessible
			STATUS current
			DESCRIPTION
				"Description."
			INDEX { sleGponOltId, sleGponFlowMappingMethodVid }
			::= { sleGponFlowMappingMethodTable 1 }


		SleGponFlowMappingMethodEntry ::=
			SEQUENCE {
				sleGponFlowMappingMethodVid
					Integer32,
				sleGponFlowMappingMethodType
					INTEGER
			 }

--  1.3.6.1.4.1.6296.101.23.18.1.1.1.1
		sleGponFlowMappingMethodVid OBJECT-TYPE
			SYNTAX Integer32 (1..4094)
			MAX-ACCESS read-only
			STATUS current
			DESCRIPTION
				"The VLAN index."
			::= { sleGponFlowMappingMethodEntry 1 }


--  1.3.6.1.4.1.6296.101.23.18.1.1.1.2
		sleGponFlowMappingMethodType OBJECT-TYPE
			SYNTAX INTEGER
				{
				vid(1),
				mac(2),
				macVid(3)
				}
			MAX-ACCESS read-only
			STATUS current
			DESCRIPTION
				"The method type."
			::= { sleGponFlowMappingMethodEntry 2 }


--  1.3.6.1.4.1.6296.101.23.18.1.2
		sleGponFlowMappingMethodControl OBJECT IDENTIFIER ::= { sleGponFlowMappingMethod 2 }


--  1.3.6.1.4.1.6296.101.23.18.1.2.1
		sleGponFlowMappingMethodControlRequest OBJECT-TYPE
			SYNTAX INTEGER
				{
				setFlowMappingMethod(1),
				clearFlowMappingMethod(2),
				clearFlowMappingMethodOlt(3)
				}
			MAX-ACCESS read-write
			STATUS current
			DESCRIPTION
				"The request of a user command"
			::= { sleGponFlowMappingMethodControl 1 }


--  1.3.6.1.4.1.6296.101.23.18.1.2.2
		sleGponFlowMappingMethodControlStatus OBJECT-TYPE
			SYNTAX SleControlStatusType
			MAX-ACCESS read-only
			STATUS current
			DESCRIPTION
				"The status of user command"
			::= { sleGponFlowMappingMethodControl 2 }


--  1.3.6.1.4.1.6296.101.23.18.1.2.3
		sleGponFlowMappingMethodControlTimer OBJECT-TYPE
			SYNTAX Gauge32
			MAX-ACCESS read-write
			STATUS current
			DESCRIPTION
				"The maximum time for the manager for a long running user command"
			::= { sleGponFlowMappingMethodControl 3 }


--  1.3.6.1.4.1.6296.101.23.18.1.2.4
		sleGponFlowMappingMethodControlTimeStamp OBJECT-TYPE
			SYNTAX TimeTicks
			MAX-ACCESS read-only
			STATUS current
			DESCRIPTION
				"The time stamp of the last command(end of command)"
			::= { sleGponFlowMappingMethodControl 4 }


--  1.3.6.1.4.1.6296.101.23.18.1.2.5
		sleGponFlowMappingMethodControlReqResult OBJECT-TYPE
			SYNTAX SleControlRequestResultType
			MAX-ACCESS read-only
			STATUS current
			DESCRIPTION
				"The result of the last user command"
			::= { sleGponFlowMappingMethodControl 5 }


		sleGponFlowMappingMethodControlOltId OBJECT-TYPE
			SYNTAX Integer32 (1..2147483647)
			MAX-ACCESS read-write
			STATUS current
			DESCRIPTION
				"The OLT ID."
			::= { sleGponFlowMappingMethodControl 6 }


--  1.3.6.1.4.1.6296.101.23.18.1.2.7
		sleGponFlowMappingMethodControlVid OBJECT-TYPE
			SYNTAX INTEGER (1..4094)
			MAX-ACCESS read-write
			STATUS current
			DESCRIPTION
				"The Vlan ID."
			::= { sleGponFlowMappingMethodControl 7 }


--  1.3.6.1.4.1.6296.101.23.18.1.2.8
		sleGponFlowMappingMethodControlType OBJECT-TYPE
			SYNTAX INTEGER
				{
				vid(1),
				mac(2),
				macVid(3)
				}
			MAX-ACCESS read-write
			STATUS current
			DESCRIPTION
				"The method type."
			::= { sleGponFlowMappingMethodControl 8 }


--  1.3.6.1.4.1.6296.101.23.18.1.3
		sleGponFlowMappingMethodNotification OBJECT IDENTIFIER ::= { sleGponFlowMappingMethod 3 }


--  1.3.6.1.4.1.6296.101.23.18.1.3.1
		sleGponFlowMappingMethodChanged NOTIFICATION-TYPE
			OBJECTS { sleGponFlowMappingMethodControlRequest, sleGponFlowMappingMethodControlTimeStamp, sleGponFlowMappingMethodControlReqResult, sleGponFlowMappingMethodControlOltId, sleGponFlowMappingMethodControlVid,
				sleGponFlowMappingMethodControlType }
			STATUS current
			DESCRIPTION
				"setFlowMappingMethod"
			::= { sleGponFlowMappingMethodNotification 1 }


--  1.3.6.1.4.1.6296.101.23.18.1.3.2
		sleGponFlowMappingMethodCleared NOTIFICATION-TYPE
			OBJECTS { sleGponFlowMappingMethodControlRequest, sleGponFlowMappingMethodControlTimeStamp, sleGponFlowMappingMethodControlReqResult, sleGponFlowMappingMethodControlOltId, sleGponFlowMappingMethodControlVid
				 }
			STATUS current
			DESCRIPTION
				"clearFlowMappingMethod"
			::= { sleGponFlowMappingMethodNotification 2 }


--  1.3.6.1.4.1.6296.101.23.18.1.3.3
		sleGponFlowMappingMethodOltCleared NOTIFICATION-TYPE
			OBJECTS { sleGponFlowMappingMethodControlRequest, sleGponFlowMappingMethodControlTimeStamp, sleGponFlowMappingMethodControlReqResult, sleGponFlowMappingMethodControlOltId }
			STATUS current
			DESCRIPTION
				"clearFlowMappingMethodOlt"
			::= { sleGponFlowMappingMethodNotification 3 }


--  1.3.6.1.4.1.6296.101.23.19
		sleGponOnuMac OBJECT IDENTIFIER ::= { sleGpon 19 }


--  1.3.6.1.4.1.6296.101.23.19.1
		sleGponOnuMacTable OBJECT-TYPE
			SYNTAX SEQUENCE OF SleGponOnuMacEntry
			MAX-ACCESS not-accessible
			STATUS current
			DESCRIPTION
				"Description."
			::= { sleGponOnuMac 1 }


--  1.3.6.1.4.1.6296.101.23.19.1.1
		sleGponOnuMacEntry OBJECT-TYPE
			SYNTAX SleGponOnuMacEntry
			MAX-ACCESS not-accessible
			STATUS current
			DESCRIPTION
				"Description."
			INDEX { sleGponOltId, sleGponOnuId, sleGponOnuMacSlotIndex, sleGponOnuMacPortIndex, sleGponOnuMacIndex
				 }
			::= { sleGponOnuMacTable 1 }


		SleGponOnuMacEntry ::=
			SEQUENCE {
				sleGponOnuMacSlotIndex
					INTEGER,
				sleGponOnuMacPortIndex
					Integer32,
				sleGponOnuMacIndex
					Integer32,
				sleGponOnuMacAddress
					OCTET STRING,
				sleGponOnuMacPolicy
					INTEGER,
				sleGponOnuMacStatus
					INTEGER,
				sleGponOnuMacAge
					Integer32
			 }

--   1.3.6.1.4.1.6296.101.23.6.1.1.1.1
-- 1.3.6.1.4.1.6296.101.23.19.1.1.1
		sleGponOnuMacSlotIndex OBJECT-TYPE
			SYNTAX INTEGER
				{
				ethernet(1),
				pots(2),
				ces(3),
				video(4),
				virtualEthernet(5)
				}
			MAX-ACCESS read-only
			STATUS current
			DESCRIPTION
				"The slot index."
			::= { sleGponOnuMacEntry 1 }


--  1.3.6.1.4.1.6296.101.23.19.1.1.2
		sleGponOnuMacPortIndex OBJECT-TYPE
			SYNTAX Integer32 (1..65523)
			MAX-ACCESS read-only
			STATUS current
			DESCRIPTION
				"The port index."
			::= { sleGponOnuMacEntry 2 }


--  1.3.6.1.4.1.6296.101.23.19.1.1.3
		sleGponOnuMacIndex OBJECT-TYPE
			SYNTAX Integer32 (1..8000)
			MAX-ACCESS read-only
			STATUS current
			DESCRIPTION
				"The MAC index."
			::= { sleGponOnuMacEntry 3 }


--  1.3.6.1.4.1.6296.101.23.19.1.1.4
		sleGponOnuMacAddress OBJECT-TYPE
			SYNTAX OCTET STRING
			MAX-ACCESS read-only
			STATUS current
			DESCRIPTION
				"The MAC address."
			::= { sleGponOnuMacEntry 4 }


--  1.3.6.1.4.1.6296.101.23.19.1.1.5
		sleGponOnuMacPolicy OBJECT-TYPE
			SYNTAX INTEGER
				{
				forward(1),
				filter(2)
				}
			MAX-ACCESS read-only
			STATUS current
			DESCRIPTION
				"The MAC policy"
			::= { sleGponOnuMacEntry 5 }


--  1.3.6.1.4.1.6296.101.23.19.1.1.6
		sleGponOnuMacStatus OBJECT-TYPE
			SYNTAX INTEGER
				{
				static(1),
				dynamic(2)
				}
			MAX-ACCESS read-only
			STATUS current
			DESCRIPTION
				"The MAC status."
			::= { sleGponOnuMacEntry 6 }


--  1.3.6.1.4.1.6296.101.23.19.1.1.7
		sleGponOnuMacAge OBJECT-TYPE
			SYNTAX Integer32
			MAX-ACCESS read-only
			STATUS current
			DESCRIPTION
				"the MAC age"
			::= { sleGponOnuMacEntry 7 }


--  1.3.6.1.4.1.6296.101.23.19.2
		sleGponOnuMacControl OBJECT IDENTIFIER ::= { sleGponOnuMac 2 }


--  1.3.6.1.4.1.6296.101.23.19.2.1
		sleGponOnuMacControlRequest OBJECT-TYPE
			SYNTAX INTEGER { updateOnuMac(1) }
			MAX-ACCESS read-write
			STATUS current
			DESCRIPTION
				"The request of a user command"
			::= { sleGponOnuMacControl 1 }


--  1.3.6.1.4.1.6296.101.23.19.2.2
		sleGponOnuMacControlStatus OBJECT-TYPE
			SYNTAX SleControlStatusType
			MAX-ACCESS read-only
			STATUS current
			DESCRIPTION
				"The status of user command"
			::= { sleGponOnuMacControl 2 }


--  1.3.6.1.4.1.6296.101.23.19.2.3
		sleGponOnuMacControlTimer OBJECT-TYPE
			SYNTAX Gauge32
			MAX-ACCESS read-write
			STATUS current
			DESCRIPTION
				"The maximum time for the manager for a long running user command"
			::= { sleGponOnuMacControl 3 }


--  1.3.6.1.4.1.6296.101.23.19.2.4
		sleGponOnuMacControlTimeStamp OBJECT-TYPE
			SYNTAX TimeTicks
			MAX-ACCESS read-only
			STATUS current
			DESCRIPTION
				"The time stamp of the last command(end of command)"
			::= { sleGponOnuMacControl 4 }


--  1.3.6.1.4.1.6296.101.23.19.2.5
		sleGponOnuMacControlReqResult OBJECT-TYPE
			SYNTAX SleControlRequestResultType
			MAX-ACCESS read-only
			STATUS current
			DESCRIPTION
				"The result of the last user command"
			::= { sleGponOnuMacControl 5 }


		sleGponOnuMacControlOltIndex OBJECT-TYPE
			SYNTAX Integer32 (1..2147483647)
			MAX-ACCESS read-write
			STATUS current
			DESCRIPTION
				"The OLT index."
			::= { sleGponOnuMacControl 6 }


--  1.3.6.1.4.1.6296.101.23.19.2.7
		sleGponOnuMacControlOnuIndex OBJECT-TYPE
			SYNTAX Integer32
			MAX-ACCESS read-write
			STATUS current
			DESCRIPTION
				"The ONU index."
			::= { sleGponOnuMacControl 7 }


--  1.3.6.1.4.1.6296.101.23.19.2.8
		sleGponOnuMacControlSlotIndex OBJECT-TYPE
			SYNTAX INTEGER
				{
				ethernet(1),
				pots(2),
				ces(3),
				video(4),
				virtualEthernet(5)
				}
			MAX-ACCESS read-write
			STATUS current
			DESCRIPTION
				"The slot index."
			::= { sleGponOnuMacControl 8 }


--  1.3.6.1.4.1.6296.101.23.19.2.9
		sleGponOnuMacControlPortIndex OBJECT-TYPE
			SYNTAX Integer32
			MAX-ACCESS read-write
			STATUS current
			DESCRIPTION
				"The port index."
			::= { sleGponOnuMacControl 9 }


--  1.3.6.1.4.1.6296.101.23.19.3
		sleGponOnuMacNotification OBJECT IDENTIFIER ::= { sleGponOnuMac 3 }


--  1.3.6.1.4.1.6296.101.23.19.3.1
		sleGponOnuMacUpdated NOTIFICATION-TYPE
			OBJECTS { sleGponOnuMacControlRequest, sleGponOnuMacControlTimeStamp, sleGponOnuMacControlReqResult, sleGponOnuMacControlOltIndex, sleGponOnuMacControlOnuIndex,
				sleGponOnuMacControlSlotIndex, sleGponOnuMacControlPortIndex }
			STATUS current
			DESCRIPTION
				"updateOnuMac"
			::= { sleGponOnuMacNotification 1 }


--  1.3.6.1.4.1.6296.101.23.20
		sleGponOnuMacFilter OBJECT IDENTIFIER ::= { sleGpon 20 }


--  1.3.6.1.4.1.6296.101.23.20.1
		sleGponOnuMacFilterTable OBJECT-TYPE
			SYNTAX SEQUENCE OF SleGponOnuMacFilterEntry
			MAX-ACCESS not-accessible
			STATUS current
			DESCRIPTION
				"Description."
			::= { sleGponOnuMacFilter 1 }


--  1.3.6.1.4.1.6296.101.23.20.1.1
		sleGponOnuMacFilterEntry OBJECT-TYPE
			SYNTAX SleGponOnuMacFilterEntry
			MAX-ACCESS not-accessible
			STATUS current
			DESCRIPTION
				"Description."
			INDEX { sleGponOltId, sleGponOnuId, sleGponOnuMacFilterSlotType, sleGponOnuMacFilterPortId, sleGponOnuMacFilterMac
				 }
			::= { sleGponOnuMacFilterTable 1 }


		SleGponOnuMacFilterEntry ::=
			SEQUENCE {
				sleGponOnuMacFilterOltId
					Integer32,
				sleGponOnuMacFilterOnuId
					Integer32,
				sleGponOnuMacFilterSlotType
					INTEGER,
				sleGponOnuMacFilterPortId
					Integer32,
				sleGponOnuMacFilterMac
					OCTET STRING,
				sleGponOnuMacFilterType
					INTEGER
			 }

--
		sleGponOnuMacFilterOltId OBJECT-TYPE
			SYNTAX Integer32 (1..2147483647)
			MAX-ACCESS read-only
			STATUS current
			DESCRIPTION
				"The OLT index."
			::= { sleGponOnuMacFilterEntry 1 }


--  1.3.6.1.4.1.6296.101.23.20.1.1.2
		sleGponOnuMacFilterOnuId OBJECT-TYPE
			SYNTAX Integer32
			MAX-ACCESS read-only
			STATUS current
			DESCRIPTION
				"The ONU index."
			::= { sleGponOnuMacFilterEntry 2 }


--  1.3.6.1.4.1.6296.101.23.20.1.1.3
		sleGponOnuMacFilterSlotType OBJECT-TYPE
			SYNTAX INTEGER
				{
				ethernet(1),
				iphost(2),
				ces(3),
				virtualEthernet(4),
				mapper(5),
				gem(6)
				}
			MAX-ACCESS read-only
			STATUS current
			DESCRIPTION
				"The slot type."
			::= { sleGponOnuMacFilterEntry 3 }


--  1.3.6.1.4.1.6296.101.23.20.1.1.4
		sleGponOnuMacFilterPortId OBJECT-TYPE
			SYNTAX Integer32 (1..65535)
			MAX-ACCESS read-only
			STATUS current
			DESCRIPTION
				"The port  index"
			::= { sleGponOnuMacFilterEntry 4 }


--  1.3.6.1.4.1.6296.101.23.20.1.1.5
		sleGponOnuMacFilterMac OBJECT-TYPE
			SYNTAX OCTET STRING
			MAX-ACCESS read-only
			STATUS current
			DESCRIPTION
				"The MAC address."
			::= { sleGponOnuMacFilterEntry 5 }


--  1.3.6.1.4.1.6296.101.23.20.1.1.6
		sleGponOnuMacFilterType OBJECT-TYPE
			SYNTAX INTEGER
				{
				filter(1),
				forward(2)
				}
			MAX-ACCESS read-only
			STATUS current
			DESCRIPTION
				"The MAC filter type.
				filter mode       1
				forward mode    2
				"
			::= { sleGponOnuMacFilterEntry 6 }


--  1.3.6.1.4.1.6296.101.23.20.2
		sleGponOnuMacFilterControl OBJECT IDENTIFIER ::= { sleGponOnuMacFilter 2 }


--  1.3.6.1.4.1.6296.101.23.20.2.1
		sleGponOnuMacFilterControlRequest OBJECT-TYPE
			SYNTAX INTEGER
				{
				setOnuMacFilter(1),
				delOnuMacFilter(2)
				}
			MAX-ACCESS read-write
			STATUS current
			DESCRIPTION
				"The request of a user command"
			::= { sleGponOnuMacFilterControl 1 }


--  1.3.6.1.4.1.6296.101.23.20.2.2
		sleGponOnuMacFilterControlStatus OBJECT-TYPE
			SYNTAX SleControlStatusType
			MAX-ACCESS read-only
			STATUS current
			DESCRIPTION
				"The status of user command"
			::= { sleGponOnuMacFilterControl 2 }


--  1.3.6.1.4.1.6296.101.23.20.2.3
		sleGponOnuMacFilterControlTimer OBJECT-TYPE
			SYNTAX Gauge32
			MAX-ACCESS read-write
			STATUS current
			DESCRIPTION
				"The maximum time for the manager for a long running user command"
			::= { sleGponOnuMacFilterControl 3 }


--  1.3.6.1.4.1.6296.101.23.20.2.4
		sleGponOnuMacFilterControlTimeStamp OBJECT-TYPE
			SYNTAX TimeTicks
			MAX-ACCESS read-only
			STATUS current
			DESCRIPTION
				"The time stamp of the last command(end of command)"
			::= { sleGponOnuMacFilterControl 4 }


--  1.3.6.1.4.1.6296.101.23.20.2.5
		sleGponOnuMacFilterControlReqResult OBJECT-TYPE
			SYNTAX SleControlRequestResultType
			MAX-ACCESS read-only
			STATUS current
			DESCRIPTION
				"The result of the last user command"
			::= { sleGponOnuMacFilterControl 5 }


		sleGponOnuMacFilterControlOltIndex OBJECT-TYPE
			SYNTAX Integer32 (1..2147483647)
			MAX-ACCESS read-write
			STATUS current
			DESCRIPTION
				"The OLT index."
			::= { sleGponOnuMacFilterControl 6 }


--  1.3.6.1.4.1.6296.101.23.20.2.7
		sleGponOnuMacFilterControlOnuIndex OBJECT-TYPE
			SYNTAX Integer32
			MAX-ACCESS read-write
			STATUS current
			DESCRIPTION
				"The ONU index."
			::= { sleGponOnuMacFilterControl 7 }


--  1.3.6.1.4.1.6296.101.23.20.2.8
		sleGponOnuMacFilterControlSlotType OBJECT-TYPE
			SYNTAX INTEGER
				{
				ethernet(1),
				iphost(2),
				ces(3),
				virtualEthernet(4),
				mapper(5),
				gem(6)
				}
			MAX-ACCESS read-write
			STATUS current
			DESCRIPTION
				"The slot index."
			::= { sleGponOnuMacFilterControl 8 }


--  1.3.6.1.4.1.6296.101.23.20.2.9
		sleGponOnuMacFilterControlPortIndex OBJECT-TYPE
			SYNTAX Integer32
			MAX-ACCESS read-write
			STATUS current
			DESCRIPTION
				"The port index."
			::= { sleGponOnuMacFilterControl 9 }


--  1.3.6.1.4.1.6296.101.23.20.2.10
		sleGponOnuMacFilterControlMac OBJECT-TYPE
			SYNTAX OCTET STRING
			MAX-ACCESS read-write
			STATUS current
			DESCRIPTION
				"The mac address"
			::= { sleGponOnuMacFilterControl 10 }


--  1.3.6.1.4.1.6296.101.23.20.2.11
		sleGponOnuMacFilterControlType OBJECT-TYPE
			SYNTAX INTEGER
				{
				filter(1),
				forward(2)
				}
			MAX-ACCESS read-write
			STATUS current
			DESCRIPTION
				"The MAC filter type.
				filter mode       1
				forward mode    2"
			::= { sleGponOnuMacFilterControl 11 }


--  1.3.6.1.4.1.6296.101.23.20.3
		sleGponOnuMacFilterNotification OBJECT IDENTIFIER ::= { sleGponOnuMacFilter 3 }


--  1.3.6.1.4.1.6296.101.23.20.3.1
		sleGponOnuMacFilterChanged NOTIFICATION-TYPE
			OBJECTS { sleGponOnuMacFilterControlRequest, sleGponOnuMacFilterControlTimeStamp, sleGponOnuMacFilterControlReqResult, sleGponOnuMacFilterControlOltIndex, sleGponOnuMacFilterControlOnuIndex,
				sleGponOnuMacFilterControlSlotType, sleGponOnuMacFilterControlPortIndex, sleGponOnuMacFilterControlMac, sleGponOnuMacFilterControlType }
			STATUS current
			DESCRIPTION
				"setOnuMacFilter"
			::= { sleGponOnuMacFilterNotification 1 }


--  1.3.6.1.4.1.6296.101.23.20.3.2
		sleGponOnuMacFilterDeleted NOTIFICATION-TYPE
			OBJECTS { sleGponOnuMacFilterControlRequest, sleGponOnuMacFilterControlTimeStamp, sleGponOnuMacFilterControlReqResult, sleGponOnuMacFilterControlOltIndex, sleGponOnuMacFilterControlOnuIndex,
				sleGponOnuMacFilterControlSlotType, sleGponOnuMacFilterControlPortIndex, sleGponOnuMacFilterControlMac, sleGponOnuMacFilterControlType }
			STATUS current
			DESCRIPTION
				"setOnuMacFilter"
			::= { sleGponOnuMacFilterNotification 2 }


--  1.3.6.1.4.1.6296.101.23.21
		sleGponOnuMcastAccessList OBJECT IDENTIFIER ::= { sleGpon 21 }


--  1.3.6.1.4.1.6296.101.23.21.1
		sleGponOnuMcastAccessListTable OBJECT-TYPE
			SYNTAX SEQUENCE OF SleGponOnuMcastAccessListEntry
			MAX-ACCESS not-accessible
			STATUS current
			DESCRIPTION
				"Description."
			::= { sleGponOnuMcastAccessList 1 }


--  1.3.6.1.4.1.6296.101.23.21.1.1
		sleGponOnuMcastAccessListEntry OBJECT-TYPE
			SYNTAX SleGponOnuMcastAccessListEntry
			MAX-ACCESS not-accessible
			STATUS current
			DESCRIPTION
				"Description."
			INDEX { sleGponOltId, sleGponOnuId, sleGponOnuMcastAccessListIndex, sleGponOnuMcastAccessListProfileIndex }
			::= { sleGponOnuMcastAccessListTable 1 }


		SleGponOnuMcastAccessListEntry ::=
			SEQUENCE {
				sleGponOnuMcastAccessListOltId
					Integer32,
				sleGponOnuMcastAccessListOnuId
					Integer32,
				sleGponOnuMcastAccessListIndex
					Integer32,
				sleGponOnuMcastAccessListName
					OCTET STRING,
				sleGponOnuMcastAccessListProfileName
					OCTET STRING,
				sleGponOnuMcastAccessListProfileIndex
					Integer32
			 }

		sleGponOnuMcastAccessListOltId OBJECT-TYPE
			SYNTAX Integer32 (1..2147483647)
			MAX-ACCESS read-only
			STATUS current
			DESCRIPTION
				"The OLT index."
			::= { sleGponOnuMcastAccessListEntry 1 }


--  1.3.6.1.4.1.6296.101.23.21.1.1.2
		sleGponOnuMcastAccessListOnuId OBJECT-TYPE
			SYNTAX Integer32 (1..65523)
			MAX-ACCESS read-only
			STATUS current
			DESCRIPTION
				"The ONU index."
			::= { sleGponOnuMcastAccessListEntry 2 }


--  1.3.6.1.4.1.6296.101.23.21.1.1.3
		sleGponOnuMcastAccessListIndex OBJECT-TYPE
			SYNTAX Integer32 (0..65535)
			MAX-ACCESS read-write
			STATUS current
			DESCRIPTION
				"The Multicast ACL index."
			::= { sleGponOnuMcastAccessListEntry 3 }


--  1.3.6.1.4.1.6296.101.23.21.1.1.4
		sleGponOnuMcastAccessListName OBJECT-TYPE
			SYNTAX OCTET STRING
			MAX-ACCESS read-only
			STATUS current
			DESCRIPTION
				"The Mcast ACL name."
			::= { sleGponOnuMcastAccessListEntry 4 }


--  1.3.6.1.4.1.6296.101.23.21.1.1.5
		sleGponOnuMcastAccessListProfileName OBJECT-TYPE
			SYNTAX OCTET STRING
			MAX-ACCESS read-only
			STATUS current
			DESCRIPTION
				"The multicast-profile NAME"
			::= { sleGponOnuMcastAccessListEntry 5 }


--  1.3.6.1.4.1.6296.101.23.21.1.1.6
		sleGponOnuMcastAccessListProfileIndex OBJECT-TYPE
			SYNTAX Integer32 (0..65535)
			MAX-ACCESS read-only
			STATUS current
			DESCRIPTION
				"Description."
			::= { sleGponOnuMcastAccessListEntry 6 }


--  1.3.6.1.4.1.6296.101.23.21.2
		sleGponOnuMcastAccessListControl OBJECT IDENTIFIER ::= { sleGponOnuMcastAccessList 2 }


--  1.3.6.1.4.1.6296.101.23.21.2.1
		sleGponOnuMcastAccessListControlRequest OBJECT-TYPE
			SYNTAX INTEGER
				{
				addMcastACL(1),
				delMcastACL(2),
				delMcastACLOnu(3),
				delMcastACLOlt(4)
				}
			MAX-ACCESS read-write
			STATUS current
			DESCRIPTION
				"The request of a user command"
			::= { sleGponOnuMcastAccessListControl 1 }


--  1.3.6.1.4.1.6296.101.23.21.2.2
		sleGponOnuMcastAccessListControlStatus OBJECT-TYPE
			SYNTAX SleControlStatusType
			MAX-ACCESS read-only
			STATUS current
			DESCRIPTION
				"The status of user command"
			::= { sleGponOnuMcastAccessListControl 2 }


--  1.3.6.1.4.1.6296.101.23.21.2.3
		sleGponOnuMcastAccessListControlTimer OBJECT-TYPE
			SYNTAX Gauge32
			MAX-ACCESS read-write
			STATUS current
			DESCRIPTION
				"The maximum time for the manager for a long running user command"
			::= { sleGponOnuMcastAccessListControl 3 }


--  1.3.6.1.4.1.6296.101.23.21.2.4
		sleGponOnuMcastAccessListControlTimeStamp OBJECT-TYPE
			SYNTAX TimeTicks
			MAX-ACCESS read-only
			STATUS current
			DESCRIPTION
				"The time stamp of the last command(end of command)"
			::= { sleGponOnuMcastAccessListControl 4 }


--  1.3.6.1.4.1.6296.101.23.21.2.5
		sleGponOnuMcastAccessListControlReqResult OBJECT-TYPE
			SYNTAX SleControlRequestResultType
			MAX-ACCESS read-only
			STATUS current
			DESCRIPTION
				"The result of the last user command"
			::= { sleGponOnuMcastAccessListControl 5 }


		sleGponOnuMcastAccessListControlOltIndex OBJECT-TYPE
			SYNTAX Integer32 (1..2147483647)
			MAX-ACCESS read-write
			STATUS current
			DESCRIPTION
				"The OLT index."
			::= { sleGponOnuMcastAccessListControl 6 }


--  1.3.6.1.4.1.6296.101.23.21.2.7
		sleGponOnuMcastAccessListControlOnuIndex OBJECT-TYPE
			SYNTAX Integer32
			MAX-ACCESS read-write
			STATUS current
			DESCRIPTION
				"The ONU index."
			::= { sleGponOnuMcastAccessListControl 7 }


--  1.3.6.1.4.1.6296.101.23.21.2.8
		sleGponOnuMcastAccessListControlName OBJECT-TYPE
			SYNTAX OCTET STRING
			MAX-ACCESS read-write
			STATUS current
			DESCRIPTION
				"The Mcast ACL name."
			::= { sleGponOnuMcastAccessListControl 8 }


--  1.3.6.1.4.1.6296.101.23.21.2.9
		sleGponOnuMcastAccessListControlProfileName OBJECT-TYPE
			SYNTAX OCTET STRING
			MAX-ACCESS read-write
			STATUS current
			DESCRIPTION
				"The multicast-profile NAME"
			::= { sleGponOnuMcastAccessListControl 9 }


--  1.3.6.1.4.1.6296.101.23.21.3
		sleGponOnuMcastAccessListNotification OBJECT IDENTIFIER ::= { sleGponOnuMcastAccessList 3 }


--  1.3.6.1.4.1.6296.101.23.21.3.1
		sleGponOnuMcastAccessListAdded NOTIFICATION-TYPE
			OBJECTS { sleGponOnuMcastAccessListControlRequest, sleGponOnuMcastAccessListControlTimeStamp, sleGponOnuMcastAccessListControlReqResult, sleGponOnuMcastAccessListControlOltIndex, sleGponOnuMcastAccessListControlOnuIndex,
				sleGponOnuMcastAccessListControlName }
			STATUS current
			DESCRIPTION
				"addMcastACL"
			::= { sleGponOnuMcastAccessListNotification 1 }


--  1.3.6.1.4.1.6296.101.23.21.3.2
		sleGponOnuMcastAccessListDeleted NOTIFICATION-TYPE
			OBJECTS { sleGponOnuMcastAccessListControlRequest, sleGponOnuMcastAccessListControlTimeStamp, sleGponOnuMcastAccessListControlReqResult, sleGponOnuMcastAccessListControlOltIndex, sleGponOnuMcastAccessListControlOnuIndex,
				sleGponOnuMcastAccessListControlName }
			STATUS current
			DESCRIPTION
				"delMcastACL"
			::= { sleGponOnuMcastAccessListNotification 2 }


--  1.3.6.1.4.1.6296.101.23.21.3.3
		sleGponOnuMcastAccessListOnuDeleted NOTIFICATION-TYPE
			OBJECTS { sleGponOnuMcastAccessListControlRequest, sleGponOnuMcastAccessListControlTimeStamp, sleGponOnuMcastAccessListControlReqResult, sleGponOnuMcastAccessListControlOltIndex, sleGponOnuMcastAccessListControlOnuIndex
				 }
			STATUS current
			DESCRIPTION
				"addMcastACL"
			::= { sleGponOnuMcastAccessListNotification 3 }


--  1.3.6.1.4.1.6296.101.23.21.3.4
		sleGponOnuMcastAccessListOltDeleted NOTIFICATION-TYPE
			OBJECTS { sleGponOnuMcastAccessListControlRequest, sleGponOnuMcastAccessListControlTimeStamp, sleGponOnuMcastAccessListControlReqResult, sleGponOnuMcastAccessListControlOltIndex }
			STATUS current
			DESCRIPTION
				"addMcastACL"
			::= { sleGponOnuMcastAccessListNotification 4 }


--  1.3.6.1.4.1.6296.101.23.22
		sleGponOnuAuth OBJECT IDENTIFIER ::= { sleGpon 22 }


--  1.3.6.1.4.1.6296.101.23.22.1
		sleGponOnuAuthTable OBJECT-TYPE
			SYNTAX SEQUENCE OF SleGponOnuAuthEntry
			MAX-ACCESS not-accessible
			STATUS current
			DESCRIPTION
				"Description."
			::= { sleGponOnuAuth 1 }


--  1.3.6.1.4.1.6296.101.23.22.1.1
		sleGponOnuAuthEntry OBJECT-TYPE
			SYNTAX SleGponOnuAuthEntry
			MAX-ACCESS not-accessible
			STATUS current
			DESCRIPTION
				"Description."
			INDEX { sleGponOnuAuthIndex }
			::= { sleGponOnuAuthTable 1 }


		SleGponOnuAuthEntry ::=
			SEQUENCE {
				sleGponOnuAuthIndex
					Integer32,
				sleGponOnuAuthAddress
					IpAddress,
				sleGponOnuAuthKey
					OCTET STRING,
				sleGponOnuAuthPort
					Integer32
			 }

--  The ONU auth index
-- 1.3.6.1.4.1.6296.101.23.22.1.1.1
		sleGponOnuAuthIndex OBJECT-TYPE
			SYNTAX Integer32 (0..65535)
			MAX-ACCESS read-only
			STATUS current
			DESCRIPTION
				"Description."
			::= { sleGponOnuAuthEntry 1 }


--  The IP address of Radius server
--
-- 1.3.6.1.4.1.6296.101.23.22.1.1.2
		sleGponOnuAuthAddress OBJECT-TYPE
			SYNTAX IpAddress
			MAX-ACCESS read-only
			STATUS current
			DESCRIPTION
				"Description."
			::= { sleGponOnuAuthEntry 2 }


--  1.3.6.1.4.1.6296.101.23.22.1.1.3
		sleGponOnuAuthKey OBJECT-TYPE
			SYNTAX OCTET STRING
			MAX-ACCESS read-only
			STATUS current
			DESCRIPTION
				"Per Server encryption key
				"
			::= { sleGponOnuAuthEntry 3 }


--  1.3.6.1.4.1.6296.101.23.22.1.1.4
		sleGponOnuAuthPort OBJECT-TYPE
			SYNTAX Integer32 (0..65535)
			MAX-ACCESS read-only
			STATUS current
			DESCRIPTION
				"UDP port for Radius authentication server
				(Default 1812) "
			::= { sleGponOnuAuthEntry 4 }


--  1.3.6.1.4.1.6296.101.23.22.2
		sleGponOnuAuthControl OBJECT IDENTIFIER ::= { sleGponOnuAuth 2 }


--  1.3.6.1.4.1.6296.101.23.22.2.1
		sleGponOnuAuthControlRequest OBJECT-TYPE
			SYNTAX INTEGER
				{
				setOnuAuthServer(1),
				delOnuAuthServer(2)
				}
			MAX-ACCESS read-write
			STATUS current
			DESCRIPTION
				"The request of a user command"
			::= { sleGponOnuAuthControl 1 }


--  1.3.6.1.4.1.6296.101.23.22.2.2
		sleGponOnuAuthControlStatus OBJECT-TYPE
			SYNTAX SleControlStatusType
			MAX-ACCESS read-only
			STATUS current
			DESCRIPTION
				"The status of user command"
			::= { sleGponOnuAuthControl 2 }


--  1.3.6.1.4.1.6296.101.23.22.2.3
		sleGponOnuAuthControlTimer OBJECT-TYPE
			SYNTAX Gauge32
			MAX-ACCESS read-write
			STATUS current
			DESCRIPTION
				"The maximum time for the manager for a long running user command"
			::= { sleGponOnuAuthControl 3 }


--  1.3.6.1.4.1.6296.101.23.22.2.4
		sleGponOnuAuthControlTimeStamp OBJECT-TYPE
			SYNTAX TimeTicks
			MAX-ACCESS read-only
			STATUS current
			DESCRIPTION
				"The time stamp of the last command(end of command)"
			::= { sleGponOnuAuthControl 4 }


--  1.3.6.1.4.1.6296.101.23.22.2.5
		sleGponOnuAuthControlReqResult OBJECT-TYPE
			SYNTAX SleControlRequestResultType
			MAX-ACCESS read-only
			STATUS current
			DESCRIPTION
				"The result of the last user command"
			::= { sleGponOnuAuthControl 5 }


--  1.3.6.1.4.1.6296.101.23.22.2.6
		sleGponOnuAuthControlAddress OBJECT-TYPE
			SYNTAX IpAddress
			MAX-ACCESS read-write
			STATUS current
			DESCRIPTION
				"The IP address of Radius server"
			::= { sleGponOnuAuthControl 6 }


--  1.3.6.1.4.1.6296.101.23.22.2.7
		sleGponOnuAuthControlKey OBJECT-TYPE
			SYNTAX OCTET STRING
			MAX-ACCESS read-write
			STATUS current
			DESCRIPTION
				"Per Server encryption key
				"
			::= { sleGponOnuAuthControl 7 }


--  1.3.6.1.4.1.6296.101.23.22.2.8
		sleGponOnuAuthControlPort OBJECT-TYPE
			SYNTAX Integer32 (0..65535)
			MAX-ACCESS read-write
			STATUS current
			DESCRIPTION
				"UDP port for Radius authentication server
				(Default 1812)"
			::= { sleGponOnuAuthControl 8 }


--  1.3.6.1.4.1.6296.101.23.22.3
		sleGponOnuAuthNotification OBJECT IDENTIFIER ::= { sleGponOnuAuth 3 }


--  1.3.6.1.4.1.6296.101.23.22.3.1
		sleGponOnuAuthServerChanged NOTIFICATION-TYPE
			OBJECTS { sleGponOnuAuthControlRequest, sleGponOnuAuthControlTimeStamp, sleGponOnuAuthControlReqResult, sleGponOnuAuthControlAddress, sleGponOnuAuthControlKey,
				sleGponOnuAuthControlPort }
			STATUS current
			DESCRIPTION
				"addMcastACL"
			::= { sleGponOnuAuthNotification 1 }


--  1.3.6.1.4.1.6296.101.23.22.3.2
		sleGponOnuAuthServerDeleted NOTIFICATION-TYPE
			OBJECTS { sleGponOnuAuthControlRequest, sleGponOnuAuthControlTimeStamp, sleGponOnuAuthControlReqResult, sleGponOnuAuthControlAddress }
			STATUS current
			DESCRIPTION
				"addMcastACL"
			::= { sleGponOnuAuthNotification 2 }


--  1.3.6.1.4.1.6296.101.23.23
		sleGponOnuExtVlanTag OBJECT IDENTIFIER ::= { sleGpon 23 }


--  1.3.6.1.4.1.6296.101.23.23.1
		sleGponOnuExtVlanTagTable OBJECT-TYPE
			SYNTAX SEQUENCE OF SleGponOnuExtVlanTagEntry
			MAX-ACCESS not-accessible
			STATUS current
			DESCRIPTION
				"Description."
			::= { sleGponOnuExtVlanTag 1 }


--  1.3.6.1.4.1.6296.101.23.23.1.1
		sleGponOnuExtVlanTagEntry OBJECT-TYPE
			SYNTAX SleGponOnuExtVlanTagEntry
			MAX-ACCESS not-accessible
			STATUS current
			DESCRIPTION
				"Description."
			INDEX { sleGponOltId, sleGponOnuId, sleGponProfile2ExtVlanIndex, sleGponProfile2ExtVlanTagType, sleGponProfile2ExtVlanTagIndex
				 }
			::= { sleGponOnuExtVlanTagTable 1 }


		SleGponOnuExtVlanTagEntry ::=
			SEQUENCE {
				sleGponOnuExtVlanTagTreatInnerCopyVid
					Integer32,
				sleGponOnuExtVlanTagTreatInnerCopyCos
					INTEGER
			 }

--  1.3.6.1.4.1.6296.101.23.23.1.1.1
		sleGponOnuExtVlanTagTreatInnerCopyVid OBJECT-TYPE
			SYNTAX Integer32 (0..4094)
			MAX-ACCESS read-only
			STATUS current
			DESCRIPTION
				"The Treatment inner VID rule"
			::= { sleGponOnuExtVlanTagEntry 1 }


--  1.3.6.1.4.1.6296.101.23.23.1.1.2
		sleGponOnuExtVlanTagTreatInnerCopyCos OBJECT-TYPE
			SYNTAX INTEGER
			MAX-ACCESS read-only
			STATUS current
			DESCRIPTION
				"The Treatment inner Cos rule
				(0..7)
				8: copyInnerPriority
				9: copyOuterPriority
				10: dscpToPbit"
			::= { sleGponOnuExtVlanTagEntry 2 }


--  1.3.6.1.4.1.6296.101.23.23.2
		sleGponOnuExtVlanTagControl OBJECT IDENTIFIER ::= { sleGponOnuExtVlanTag 2 }


--  1.3.6.1.4.1.6296.101.23.23.2.1
		sleGponOnuExtVlanTagControlRequest OBJECT-TYPE
			SYNTAX INTEGER
				{
				addOnuExtendedVlanFrameTreatInner(1),
				delOnuExtendVlanFrameTreatInner(2)
				}
			MAX-ACCESS read-write
			STATUS current
			DESCRIPTION
				"The request of a user command"
			::= { sleGponOnuExtVlanTagControl 1 }


--  1.3.6.1.4.1.6296.101.23.23.2.2
		sleGponOnuExtVlanTagControlStatus OBJECT-TYPE
			SYNTAX SleControlStatusType
			MAX-ACCESS read-only
			STATUS current
			DESCRIPTION
				"The status of user command"
			::= { sleGponOnuExtVlanTagControl 2 }


--  1.3.6.1.4.1.6296.101.23.23.2.3
		sleGponOnuExtVlanTagControlTimer OBJECT-TYPE
			SYNTAX Gauge32
			MAX-ACCESS read-write
			STATUS current
			DESCRIPTION
				"The maximum time for the manager for a long running user command"
			::= { sleGponOnuExtVlanTagControl 3 }


--  1.3.6.1.4.1.6296.101.23.23.2.4
		sleGponOnuExtVlanTagControlTimeStamp OBJECT-TYPE
			SYNTAX TimeTicks
			MAX-ACCESS read-only
			STATUS current
			DESCRIPTION
				"The time stamp of the last command(end of command)"
			::= { sleGponOnuExtVlanTagControl 4 }


--  1.3.6.1.4.1.6296.101.23.23.2.5
		sleGponOnuExtVlanTagControlReqResult OBJECT-TYPE
			SYNTAX SleControlRequestResultType
			MAX-ACCESS read-only
			STATUS current
			DESCRIPTION
				"The result of the last user command"
			::= { sleGponOnuExtVlanTagControl 5 }


		sleGponOnuExtVlanTagControlOltIndex OBJECT-TYPE
			SYNTAX Integer32 (1..2147483647)
			MAX-ACCESS read-write
			STATUS current
			DESCRIPTION
				"The OLT index."
			::= { sleGponOnuExtVlanTagControl 6 }


--  1.3.6.1.4.1.6296.101.23.23.2.7
		sleGponOnuExtVlanTagControlOnuIndex OBJECT-TYPE
			SYNTAX Integer32
			MAX-ACCESS read-write
			STATUS current
			DESCRIPTION
				"The ONU index."
			::= { sleGponOnuExtVlanTagControl 7 }


--  1.3.6.1.4.1.6296.101.23.23.2.8
		sleGponOnuExtVlanTagControlProfileName OBJECT-TYPE
			SYNTAX OCTET STRING
			MAX-ACCESS read-write
			STATUS current
			DESCRIPTION
				"The Extended Vlan Tagging Operation profile Name"
			::= { sleGponOnuExtVlanTagControl 8 }


--  1.3.6.1.4.1.6296.101.23.23.2.9
		sleGponOnuExtVlanTagControlFrameType OBJECT-TYPE
			SYNTAX INTEGER
				{
				unTaggedFrame(1),
				singleTaggedFrame(2),
				doubleTaggedFrame(3)
				}
			MAX-ACCESS read-write
			STATUS current
			DESCRIPTION
				"The tag frame type"
			::= { sleGponOnuExtVlanTagControl 9 }


--  1.3.6.1.4.1.6296.101.23.23.2.10
		sleGponOnuExtVlanTagControlFrameIndex OBJECT-TYPE
			SYNTAX Integer32
			MAX-ACCESS read-write
			STATUS current
			DESCRIPTION
				"The tag frame table index"
			::= { sleGponOnuExtVlanTagControl 10 }


--  1.3.6.1.4.1.6296.101.23.23.2.11
		sleGponOnuExtVlanTagControlTreatInnerCopyVid OBJECT-TYPE
			SYNTAX INTEGER
			MAX-ACCESS read-write
			STATUS current
			DESCRIPTION
				"(0..4094)
				4096 : copyInnerVid
				4097 : copyOuter Vid"
			::= { sleGponOnuExtVlanTagControl 11 }


--  1.3.6.1.4.1.6296.101.23.23.2.12
		sleGponOnuExtVlanTagControlTreatInnerCopyCos OBJECT-TYPE
			SYNTAX INTEGER
			MAX-ACCESS read-write
			STATUS current
			DESCRIPTION
				"(0..7)
				8: copyInnerPriority
				9: copyOuterPriority
				10: dscpToPbit"
			::= { sleGponOnuExtVlanTagControl 12 }


--  1.3.6.1.4.1.6296.101.23.23.3
		sleGponOnuMExtVlanTagNotification OBJECT IDENTIFIER ::= { sleGponOnuExtVlanTag 3 }


--  1.3.6.1.4.1.6296.101.23.23.3.1
		sleGponOnuExtVlanTagFrameTreatInnerAdded NOTIFICATION-TYPE
			OBJECTS { sleGponOnuExtVlanTagControlRequest, sleGponOnuExtVlanTagControlTimeStamp, sleGponOnuExtVlanTagControlReqResult, sleGponOnuExtVlanTagControlOltIndex, sleGponOnuExtVlanTagControlOnuIndex,
				sleGponOnuExtVlanTagControlProfileName, sleGponOnuExtVlanTagControlFrameType, sleGponOnuExtVlanTagControlFrameIndex, sleGponOnuExtVlanTagControlTreatInnerCopyVid, sleGponOnuExtVlanTagControlTreatInnerCopyCos
				 }
			STATUS current
			DESCRIPTION
				"addMcastACL"
			::= { sleGponOnuMExtVlanTagNotification 1 }


--  1.3.6.1.4.1.6296.101.23.23.3.2
		sleGponOnuExtVlanTagFrameTreatInnerDeleted NOTIFICATION-TYPE
			OBJECTS { sleGponOnuExtVlanTagControlRequest, sleGponOnuExtVlanTagControlTimeStamp, sleGponOnuExtVlanTagControlReqResult, sleGponOnuExtVlanTagControlOltIndex, sleGponOnuExtVlanTagControlOnuIndex,
				sleGponOnuExtVlanTagControlProfileName, sleGponOnuExtVlanTagControlFrameType }
			STATUS current
			DESCRIPTION
				"addMcastACL"
			::= { sleGponOnuMExtVlanTagNotification 2 }


--  1.3.6.1.4.1.6296.101.23.24
		sleGponCfm OBJECT IDENTIFIER ::= { sleGpon 24 }


--  1.3.6.1.4.1.6296.101.23.24.1
		sleGponCfmMd OBJECT IDENTIFIER ::= { sleGponCfm 1 }


--  1.3.6.1.4.1.6296.101.23.24.1.1
		sleGponCfmMdTable OBJECT-TYPE
			SYNTAX SEQUENCE OF SleGponCfmMdEntry
			MAX-ACCESS not-accessible
			STATUS current
			DESCRIPTION
				"Description."
			::= { sleGponCfmMd 1 }


--  1.3.6.1.4.1.6296.101.23.24.1.1.1
		sleGponCfmMdEntry OBJECT-TYPE
			SYNTAX SleGponCfmMdEntry
			MAX-ACCESS not-accessible
			STATUS current
			DESCRIPTION
				"Description."
			INDEX { sleGponCmfMdIndex }
			::= { sleGponCfmMdTable 1 }


		SleGponCfmMdEntry ::=
			SEQUENCE {
				sleGponCmfMdIndex
					Integer32,
				sleGponCfmMdName
					OCTET STRING,
				sleGponCfmMdLevel
					INTEGER
			 }

--  1.3.6.1.4.1.6296.101.23.24.1.1.1.1
		sleGponCmfMdIndex OBJECT-TYPE
			SYNTAX Integer32 (0..65535)
			MAX-ACCESS read-only
			STATUS current
			DESCRIPTION
				"Description."
			::= { sleGponCfmMdEntry 1 }


--  1.3.6.1.4.1.6296.101.23.24.1.1.1.2
		sleGponCfmMdName OBJECT-TYPE
			SYNTAX OCTET STRING
			MAX-ACCESS read-only
			STATUS current
			DESCRIPTION
				"The Maintenance Domain Name"
			::= { sleGponCfmMdEntry 2 }


--  1.3.6.1.4.1.6296.101.23.24.1.1.1.3
		sleGponCfmMdLevel OBJECT-TYPE
			SYNTAX INTEGER (0..7)
			MAX-ACCESS read-write
			STATUS current
			DESCRIPTION
				"The Maintenance Domain level"
			::= { sleGponCfmMdEntry 3 }


--  1.3.6.1.4.1.6296.101.23.24.1.2
		sleGponCfmMdControl OBJECT IDENTIFIER ::= { sleGponCfmMd 2 }


--  1.3.6.1.4.1.6296.101.23.24.1.2.1
		sleGponCfmMdControlRequest OBJECT-TYPE
			SYNTAX INTEGER
				{
				setCfmMd(1),
				delCfmMd(2)
				}
			MAX-ACCESS read-write
			STATUS current
			DESCRIPTION
				"The request of a user command"
			::= { sleGponCfmMdControl 1 }


--  1.3.6.1.4.1.6296.101.23.24.1.2.2
		sleGponCfmMdControlStatus OBJECT-TYPE
			SYNTAX SleControlStatusType
			MAX-ACCESS read-only
			STATUS current
			DESCRIPTION
				"The status of user command"
			::= { sleGponCfmMdControl 2 }


--  1.3.6.1.4.1.6296.101.23.24.1.2.3
		sleGponCfmMdControlTimer OBJECT-TYPE
			SYNTAX Gauge32
			MAX-ACCESS read-write
			STATUS current
			DESCRIPTION
				"The maximum time for the manager for a long running user command"
			::= { sleGponCfmMdControl 3 }


--  1.3.6.1.4.1.6296.101.23.24.1.2.4
		sleGponCfmMdControlTimeStamp OBJECT-TYPE
			SYNTAX TimeTicks
			MAX-ACCESS read-only
			STATUS current
			DESCRIPTION
				"The time stamp of the last command(end of command)"
			::= { sleGponCfmMdControl 4 }


--  1.3.6.1.4.1.6296.101.23.24.1.2.5
		sleGponCfmMdControlReqResult OBJECT-TYPE
			SYNTAX SleControlRequestResultType
			MAX-ACCESS read-only
			STATUS current
			DESCRIPTION
				"The result of the last user command"
			::= { sleGponCfmMdControl 5 }


--  1.3.6.1.4.1.6296.101.23.24.1.2.6
		sleGponCfmMdControlName OBJECT-TYPE
			SYNTAX OCTET STRING
			MAX-ACCESS read-write
			STATUS current
			DESCRIPTION
				"The Maintenance Domain Name"
			::= { sleGponCfmMdControl 6 }


--  1.3.6.1.4.1.6296.101.23.24.1.2.7
		sleGponCfmMdControlLevel OBJECT-TYPE
			SYNTAX INTEGER (0..7)
			MAX-ACCESS read-write
			STATUS current
			DESCRIPTION
				"The Maintenance Domain level"
			::= { sleGponCfmMdControl 7 }


--  1.3.6.1.4.1.6296.101.23.24.1.3
		sleGponCfmMdNotification OBJECT IDENTIFIER ::= { sleGponCfmMd 3 }


--  1.3.6.1.4.1.6296.101.23.24.1.3.1
		sleGponCfmMdChanged NOTIFICATION-TYPE
			OBJECTS { sleGponCfmMdControlRequest, sleGponCfmMdControlTimeStamp, sleGponCfmMdControlReqResult, sleGponCfmMdControlName, sleGponCfmMdControlLevel
				 }
			STATUS current
			DESCRIPTION
				" "
			::= { sleGponCfmMdNotification 1 }


--  1.3.6.1.4.1.6296.101.23.24.1.3.2
		sleGponCfmMdDeleted NOTIFICATION-TYPE
			OBJECTS { sleGponCfmMdControlRequest, sleGponCfmMdControlTimeStamp, sleGponCfmMdControlReqResult, sleGponCfmMdControlName, sleGponCfmMdControlLevel
				 }
			STATUS current
			DESCRIPTION
				" "
			::= { sleGponCfmMdNotification 2 }


--  1.3.6.1.4.1.6296.101.23.24.2
		sleGponCfmMa OBJECT IDENTIFIER ::= { sleGponCfm 2 }


--  1.3.6.1.4.1.6296.101.23.24.2.1
		sleGponCfmMaTable OBJECT-TYPE
			SYNTAX SEQUENCE OF SleGponCfmMaEntry
			MAX-ACCESS not-accessible
			STATUS current
			DESCRIPTION
				"Description."
			::= { sleGponCfmMa 1 }


--  1.3.6.1.4.1.6296.101.23.24.2.1.1
		sleGponCfmMaEntry OBJECT-TYPE
			SYNTAX SleGponCfmMaEntry
			MAX-ACCESS not-accessible
			STATUS current
			DESCRIPTION
				"Description."
			INDEX { sleGponCmfMaKey }
			::= { sleGponCfmMaTable 1 }


		SleGponCfmMaEntry ::=
			SEQUENCE {
				sleGponCmfMaKey
					Integer32,
				sleGponCfmMaNameFormat
					INTEGER,
				sleGponCfmMaName
					OCTET STRING,
				sleGponCfmMaCcmInterval
					INTEGER,
				sleGponCfmMaMdName
					OCTET STRING
			 }

--  1.3.6.1.4.1.6296.101.23.24.2.1.1.1
		sleGponCmfMaKey OBJECT-TYPE
			SYNTAX Integer32 (0..65535)
			MAX-ACCESS read-only
			STATUS current
			DESCRIPTION
				"The maintenance association Index."
			::= { sleGponCfmMaEntry 1 }


--  1.3.6.1.4.1.6296.101.23.24.2.1.1.2
		sleGponCfmMaNameFormat OBJECT-TYPE
			SYNTAX INTEGER
				{
				primaryVID(1),
				characterString(2),
				twoOctetInteger(3),
				vpnId(4),
				unknown(255)
				}
			MAX-ACCESS read-only
			STATUS current
			DESCRIPTION
				"The maintenance association format of name"
			::= { sleGponCfmMaEntry 2 }


--  1.3.6.1.4.1.6296.101.23.24.2.1.1.3
		sleGponCfmMaName OBJECT-TYPE
			SYNTAX OCTET STRING
			MAX-ACCESS read-only
			STATUS current
			DESCRIPTION
				"The maintenance association name."
			::= { sleGponCfmMaEntry 3 }


--  1.3.6.1.4.1.6296.101.23.24.2.1.1.4
		sleGponCfmMaCcmInterval OBJECT-TYPE
			SYNTAX INTEGER
				{
				disable(0),
				interval3dot33msec(1),
				inteval10msec(2),
				interval100msec(3),
				itnerval1sec(4),
				interval10sec(5),
				inteval1min(6),
				interval10min(7),
				unknown(255)
				}
			MAX-ACCESS read-only
			STATUS current
			DESCRIPTION
				"The maintenance association CCMs interval..
				If CCMs are enabled on an MEP, the CCM interval attribute specifies the
				rate at which they are generated. The MEP also expects to receive CCMs
				from each of the other MEPs in its CC database at this rate."
			::= { sleGponCfmMaEntry 4 }


--  1.3.6.1.4.1.6296.101.23.24.2.1.1.5
		sleGponCfmMaMdName OBJECT-TYPE
			SYNTAX OCTET STRING
			MAX-ACCESS read-only
			STATUS current
			DESCRIPTION
				"This Name specifies the dot1ag maintenance domain with which this MA is associated."
			::= { sleGponCfmMaEntry 5 }


--  1.3.6.1.4.1.6296.101.23.24.2.2
		sleGponCfmMaControl OBJECT IDENTIFIER ::= { sleGponCfmMa 2 }


--  1.3.6.1.4.1.6296.101.23.24.2.2.1
		sleGponCfmMaControlRequest OBJECT-TYPE
			SYNTAX INTEGER
				{
				setCfmMa(1),
				delCfmMa(2)
				}
			MAX-ACCESS read-write
			STATUS current
			DESCRIPTION
				"The request of a user command"
			::= { sleGponCfmMaControl 1 }


--  1.3.6.1.4.1.6296.101.23.24.2.2.2
		sleGponCfmMaControlStatus OBJECT-TYPE
			SYNTAX SleControlStatusType
			MAX-ACCESS read-only
			STATUS current
			DESCRIPTION
				"The status of user command"
			::= { sleGponCfmMaControl 2 }


--  1.3.6.1.4.1.6296.101.23.24.2.2.3
		sleGponCfmMaControlTimer OBJECT-TYPE
			SYNTAX Gauge32
			MAX-ACCESS read-write
			STATUS current
			DESCRIPTION
				"The maximum time for the manager for a long running user command"
			::= { sleGponCfmMaControl 3 }


--  1.3.6.1.4.1.6296.101.23.24.2.2.4
		sleGponCfmMaControlTimeStamp OBJECT-TYPE
			SYNTAX TimeTicks
			MAX-ACCESS read-only
			STATUS current
			DESCRIPTION
				"The time stamp of the last command(end of command)"
			::= { sleGponCfmMaControl 4 }


--  1.3.6.1.4.1.6296.101.23.24.2.2.5
		sleGponCfmMaControlReqResult OBJECT-TYPE
			SYNTAX SleControlRequestResultType
			MAX-ACCESS read-only
			STATUS current
			DESCRIPTION
				"The result of the last user command"
			::= { sleGponCfmMaControl 5 }


--  1.3.6.1.4.1.6296.101.23.24.2.2.6
		sleGponCfmMaControlKey OBJECT-TYPE
			SYNTAX Integer32
			MAX-ACCESS read-write
			STATUS current
			DESCRIPTION
				"The maintenance association Index"
			::= { sleGponCfmMaControl 6 }


--  1.3.6.1.4.1.6296.101.23.24.2.2.7
		sleGponCfmMaControlNameFormat OBJECT-TYPE
			SYNTAX INTEGER
				{
				primaryVID(1),
				characterString(2),
				twoOctetInteger(3),
				vpnId(4),
				unknown(255)
				}
			MAX-ACCESS read-write
			STATUS current
			DESCRIPTION
				"The maintenance association format of name"
			::= { sleGponCfmMaControl 7 }


--  1.3.6.1.4.1.6296.101.23.24.2.2.8
		sleGponCfmMaControlName OBJECT-TYPE
			SYNTAX OCTET STRING
			MAX-ACCESS read-write
			STATUS current
			DESCRIPTION
				"The maintenance association name."
			::= { sleGponCfmMaControl 8 }


--  1.3.6.1.4.1.6296.101.23.24.2.2.9
		sleGponCfmMaControlCcmInterval OBJECT-TYPE
			SYNTAX INTEGER
				{
				disable(0),
				interval3dot33msec(1),
				interval10msec(2),
				interval100msec(3),
				interval1sec(4),
				interval10sec(5),
				interval1min(6),
				interval10min(7),
				unknown(255)
				}
			MAX-ACCESS read-write
			STATUS current
			DESCRIPTION
				"The maintenance association CCMs interval..
				If CCMs are enabled on an MEP, the CCM interval attribute specifies the
				rate at which they are generated. The MEP also expects to receive CCMs
				from each of the other MEPs in its CC database at this rate."
			::= { sleGponCfmMaControl 9 }


--  1.3.6.1.4.1.6296.101.23.24.2.2.10
		sleGponCfmMaControlMdName OBJECT-TYPE
			SYNTAX OCTET STRING
			MAX-ACCESS read-write
			STATUS current
			DESCRIPTION
				"This Name specifies the dot1ag maintenance domain with which this MA is associated.
				"
			::= { sleGponCfmMaControl 10 }


--  1.3.6.1.4.1.6296.101.23.24.2.3
		sleGponCfmMaNotification OBJECT IDENTIFIER ::= { sleGponCfmMa 3 }


--  1.3.6.1.4.1.6296.101.23.24.2.3.1
		sleGponCfmMaChanged NOTIFICATION-TYPE
			OBJECTS { sleGponCfmMaControlNameFormat, sleGponCfmMaControlName, sleGponCfmMaControlCcmInterval, sleGponCfmMaControlMdName, sleGponCfmMaControlTimeStamp,
				sleGponCfmMaControlKey, sleGponCfmMaControlReqResult, sleGponCfmMaControlRequest }
			STATUS current
			DESCRIPTION
				" "
			::= { sleGponCfmMaNotification 1 }


--  1.3.6.1.4.1.6296.101.23.24.2.3.2
		sleGponCfmMaDeleted NOTIFICATION-TYPE
			OBJECTS { sleGponCfmMaControlTimeStamp, sleGponCfmMaControlReqResult, sleGponCfmMaControlRequest, sleGponCfmMaControlKey }
			STATUS current
			DESCRIPTION
				" "
			::= { sleGponCfmMaNotification 2 }


--  1.3.6.1.4.1.6296.101.23.24.3
		sleGponCfmMep OBJECT IDENTIFIER ::= { sleGponCfm 3 }


--  1.3.6.1.4.1.6296.101.23.24.3.1
		sleGponCfmMepTable OBJECT-TYPE
			SYNTAX SEQUENCE OF SleGponCfmMepEntry
			MAX-ACCESS not-accessible
			STATUS current
			DESCRIPTION
				"Description."
			::= { sleGponCfmMep 1 }


--  1.3.6.1.4.1.6296.101.23.24.3.1.1
		sleGponCfmMepEntry OBJECT-TYPE
			SYNTAX SleGponCfmMepEntry
			MAX-ACCESS not-accessible
			STATUS current
			DESCRIPTION
				"Description."
			INDEX { sleGponOltId, sleGponOnuId, sleGponCfmMepSlotType, sleGponCfmMepPortIndex, sleGponCfmMepMepid
				 }
			::= { sleGponCfmMepTable 1 }


		SleGponCfmMepEntry ::=
			SEQUENCE {
				sleGponCfmMepSlotType
					INTEGER,
				sleGponCfmMepPortIndex
					Integer32,
				sleGponCfmMepMepid
					INTEGER,
				sleGponCfmMepPriVlanid
					INTEGER,
				sleGponCfmMepPeerMepid
					INTEGER,
				sleGponCfmMepMaKey
					Integer32,
				sleGponCfmMepCcm
					INTEGER
			 }

--  1.3.6.1.4.1.6296.101.23.24.3.1.1.1
		sleGponCfmMepSlotType OBJECT-TYPE
			SYNTAX INTEGER
				{
				ethernet(1),
				iphost(2),
				ces(3),
				virtualEthernet(4),
				mapper(5),
				gem(6),
				bridgeAni(7)
				}
			MAX-ACCESS read-only
			STATUS current
			DESCRIPTION
				"The slot Type"
			::= { sleGponCfmMepEntry 1 }


--  1.3.6.1.4.1.6296.101.23.24.3.1.1.2
		sleGponCfmMepPortIndex OBJECT-TYPE
			SYNTAX Integer32 (0..65535)
			MAX-ACCESS read-only
			STATUS current
			DESCRIPTION
				"The port index."
			::= { sleGponCfmMepEntry 2 }


--  1.3.6.1.4.1.6296.101.23.24.3.1.1.3
		sleGponCfmMepMepid OBJECT-TYPE
			SYNTAX INTEGER (1..8191)
			MAX-ACCESS read-only
			STATUS current
			DESCRIPTION
				"This attribute specifies the MEP's own identity in the MA. For a given MA,
				the MEP ID must be unique throughout the network defined by the MD. The
				MEP ID is defined in the range 1..8191."
			::= { sleGponCfmMepEntry 3 }


--  1.3.6.1.4.1.6296.101.23.24.3.1.1.4
		sleGponCfmMepPriVlanid OBJECT-TYPE
			SYNTAX INTEGER (1..4095)
			MAX-ACCESS read-only
			STATUS current
			DESCRIPTION
				"The MEP's Vlan ID"
			::= { sleGponCfmMepEntry 4 }


--  1.3.6.1.4.1.6296.101.23.24.3.1.1.5
		sleGponCfmMepPeerMepid OBJECT-TYPE
			SYNTAX INTEGER (1..8191)
			MAX-ACCESS read-only
			STATUS current
			DESCRIPTION
				"The MEP's peer identity in th MA."
			::= { sleGponCfmMepEntry 5 }


--  1.3.6.1.4.1.6296.101.23.24.3.1.1.6
		sleGponCfmMepMaKey OBJECT-TYPE
			SYNTAX Integer32
			MAX-ACCESS read-only
			STATUS current
			DESCRIPTION
				"The maintenance association Index."
			::= { sleGponCfmMepEntry 6 }


--  1.3.6.1.4.1.6296.101.23.24.3.1.1.7
		sleGponCfmMepCcm OBJECT-TYPE
			SYNTAX INTEGER
				{
				enable(1),
				disable(2)
				}
			MAX-ACCESS read-only
			STATUS current
			DESCRIPTION
				"MEP generates continuity check messages"
			::= { sleGponCfmMepEntry 7 }


--  1.3.6.1.4.1.6296.101.23.24.3.2
		sleGponCfmMepControl OBJECT IDENTIFIER ::= { sleGponCfmMep 2 }


--  1.3.6.1.4.1.6296.101.23.24.3.2.1
		sleGponCfmMepControlRequest OBJECT-TYPE
			SYNTAX INTEGER
				{
				setCfmMep(1),
				delCfmMep(2),
				clearCfmMep(3),
				setCfmMepCcm(4)
				}
			MAX-ACCESS read-write
			STATUS current
			DESCRIPTION
				"The request of a user command"
			::= { sleGponCfmMepControl 1 }


--  1.3.6.1.4.1.6296.101.23.24.3.2.2
		sleGponCfmMepControlStatus OBJECT-TYPE
			SYNTAX SleControlStatusType
			MAX-ACCESS read-only
			STATUS current
			DESCRIPTION
				"The status of user command"
			::= { sleGponCfmMepControl 2 }


--  1.3.6.1.4.1.6296.101.23.24.3.2.3
		sleGponCfmMepControlTimer OBJECT-TYPE
			SYNTAX Gauge32
			MAX-ACCESS read-write
			STATUS current
			DESCRIPTION
				"The maximum time for the manager for a long running user command"
			::= { sleGponCfmMepControl 3 }


--  1.3.6.1.4.1.6296.101.23.24.3.2.4
		sleGponCfmMepControlTimeStamp OBJECT-TYPE
			SYNTAX TimeTicks
			MAX-ACCESS read-only
			STATUS current
			DESCRIPTION
				"The time stamp of the last command(end of command)"
			::= { sleGponCfmMepControl 4 }


--  1.3.6.1.4.1.6296.101.23.24.3.2.5
		sleGponCfmMepControlReqResult OBJECT-TYPE
			SYNTAX SleControlRequestResultType
			MAX-ACCESS read-only
			STATUS current
			DESCRIPTION
				"The result of the last user command"
			::= { sleGponCfmMepControl 5 }


		sleGponCfmMepControlOltId OBJECT-TYPE
			SYNTAX Integer32 (1..2147483647)
			MAX-ACCESS read-write
			STATUS current
			DESCRIPTION
				"Gpon Olt Index"
			::= { sleGponCfmMepControl 6 }


--  1.3.6.1.4.1.6296.101.23.24.3.2.7
		sleGponCfmMepControlOnuId OBJECT-TYPE
			SYNTAX Integer32
			MAX-ACCESS read-write
			STATUS current
			DESCRIPTION
				"Gpon Onu Index"
			::= { sleGponCfmMepControl 7 }


--  1.3.6.1.4.1.6296.101.23.24.3.2.8
		sleGponCfmMepControlSlotType OBJECT-TYPE
			SYNTAX INTEGER
				{
				ethernet(1),
				iphost(2),
				ces(3),
				virtualEthernet(4),
				mapper(5),
				gem(6),
				bridgeAni(7)
				}
			MAX-ACCESS read-write
			STATUS current
			DESCRIPTION
				"The slot Type"
			::= { sleGponCfmMepControl 8 }


--  1.3.6.1.4.1.6296.101.23.24.3.2.9
		sleGponCfmMepControlPortIndex OBJECT-TYPE
			SYNTAX Integer32
			MAX-ACCESS read-write
			STATUS current
			DESCRIPTION
				"The port index."
			::= { sleGponCfmMepControl 9 }


--  1.3.6.1.4.1.6296.101.23.24.3.2.10
		sleGponCfmMepControlMepid OBJECT-TYPE
			SYNTAX INTEGER (1..8196)
			MAX-ACCESS read-write
			STATUS current
			DESCRIPTION
				"This attribute specifies the MEP's own identity in the MA. For a given MA,
				the MEP ID must be unique throughout the network defined by the MD. The
				MEP ID is defined in the range 1..8191."
			::= { sleGponCfmMepControl 10 }


--  1.3.6.1.4.1.6296.101.23.24.3.2.11
		sleGponCfmMepControlPriVlanid OBJECT-TYPE
			SYNTAX INTEGER (1..4095)
			MAX-ACCESS read-write
			STATUS current
			DESCRIPTION
				"The MEP's Vlan ID"
			::= { sleGponCfmMepControl 11 }


--  1.3.6.1.4.1.6296.101.23.24.3.2.12
		sleGponCfmMepControlPeerMepid OBJECT-TYPE
			SYNTAX INTEGER (1..8196)
			MAX-ACCESS read-write
			STATUS current
			DESCRIPTION
				"The MEP's peer identity in th MA."
			::= { sleGponCfmMepControl 12 }


--  1.3.6.1.4.1.6296.101.23.24.3.2.13
		sleGponCfmMepControlMaKey OBJECT-TYPE
			SYNTAX Integer32
			MAX-ACCESS read-write
			STATUS current
			DESCRIPTION
				"The maintenance association Index."
			::= { sleGponCfmMepControl 13 }


--  1.3.6.1.4.1.6296.101.23.24.3.2.14
		sleGponCfmMepControlCcm OBJECT-TYPE
			SYNTAX INTEGER
				{
				enable(1),
				disable(2)
				}
			MAX-ACCESS read-write
			STATUS current
			DESCRIPTION
				"MEP generates continuity check messages."
			::= { sleGponCfmMepControl 14 }


--  1.3.6.1.4.1.6296.101.23.24.3.3
		sleGponCfmMepNotification OBJECT IDENTIFIER ::= { sleGponCfmMep 3 }


--  1.3.6.1.4.1.6296.101.23.24.3.3.1
		sleGponCfmMepChanged NOTIFICATION-TYPE
			OBJECTS { sleGponCfmMepControlRequest, sleGponCfmMepControlReqResult, sleGponCfmMepControlOltId, sleGponCfmMepControlOnuId, sleGponCfmMepControlSlotType,
				sleGponCfmMepControlPortIndex, sleGponCfmMepControlMepid, sleGponCfmMepControlPriVlanid, sleGponCfmMepControlPeerMepid, sleGponCfmMepControlMaKey
				 }
			STATUS current
			DESCRIPTION
				" "
			::= { sleGponCfmMepNotification 1 }


--  1.3.6.1.4.1.6296.101.23.24.3.3.2
		sleGponCfmMepDeleted NOTIFICATION-TYPE
			OBJECTS { sleGponCfmMepControlRequest, sleGponCfmMepControlReqResult, sleGponCfmMepControlOltId, sleGponCfmMepControlOnuId, sleGponCfmMepControlSlotType,
				sleGponCfmMepControlPortIndex, sleGponCfmMepControlMepid }
			STATUS current
			DESCRIPTION
				" "
			::= { sleGponCfmMepNotification 2 }


--  1.3.6.1.4.1.6296.101.23.24.3.3.3
		sleGponCfmMepCleared NOTIFICATION-TYPE
			OBJECTS { sleGponCfmMepControlRequest, sleGponCfmMepControlReqResult, sleGponCfmMepControlOltId, sleGponCfmMepControlOnuId, sleGponCfmMepControlPortIndex
				 }
			STATUS current
			DESCRIPTION
				" "
			::= { sleGponCfmMepNotification 3 }


--  1.3.6.1.4.1.6296.101.23.24.3.3.4
		sleGponCfmMepCcmChanged NOTIFICATION-TYPE
			OBJECTS { sleGponCfmMepControlRequest, sleGponCfmMepControlReqResult, sleGponCfmMepControlOltId, sleGponCfmMepControlOnuId, sleGponCfmMepMepid,
				sleGponCfmMepControlPortIndex, sleGponCfmMepControlSlotType, sleGponCfmMepControlCcm }
			STATUS current
			DESCRIPTION
				" "
			::= { sleGponCfmMepNotification 4 }


--  1.3.6.1.4.1.6296.101.23.24.4
		sleGponCfmMip OBJECT IDENTIFIER ::= { sleGponCfm 4 }


--  1.3.6.1.4.1.6296.101.23.24.4.1
		sleGponCfmMipTable OBJECT-TYPE
			SYNTAX SEQUENCE OF SleGponCfmMipEntry
			MAX-ACCESS not-accessible
			STATUS current
			DESCRIPTION
				"Description."
			::= { sleGponCfmMip 1 }


--  1.3.6.1.4.1.6296.101.23.24.4.1.1
		sleGponCfmMipEntry OBJECT-TYPE
			SYNTAX SleGponCfmMipEntry
			MAX-ACCESS not-accessible
			STATUS current
			DESCRIPTION
				"Description."
			INDEX { sleGponOltId, sleGponOnuId, sleGponCfmMipLevel }
			::= { sleGponCfmMipTable 1 }


		SleGponCfmMipEntry ::=
			SEQUENCE {
				sleGponCfmMipLevel
					INTEGER,
				sleGponCfmMipVlan
					OCTET STRING
			 }

--  1.3.6.1.4.1.6296.101.23.24.4.1.1.1
		sleGponCfmMipLevel OBJECT-TYPE
			SYNTAX INTEGER (0..7)
			MAX-ACCESS read-only
			STATUS current
			DESCRIPTION
				"The CFM MIP Level."
			::= { sleGponCfmMipEntry 1 }


--  1.3.6.1.4.1.6296.101.23.24.4.1.1.2
		sleGponCfmMipVlan OBJECT-TYPE
			SYNTAX OCTET STRING
			MAX-ACCESS read-only
			STATUS current
			DESCRIPTION
				"The CFM MIP VID list."
			::= { sleGponCfmMipEntry 2 }


--  1.3.6.1.4.1.6296.101.23.24.4.2
		sleGponCfmMipControl OBJECT IDENTIFIER ::= { sleGponCfmMip 2 }


--  1.3.6.1.4.1.6296.101.23.24.4.2.1
		sleGponCfmMipControlRequest OBJECT-TYPE
			SYNTAX INTEGER
				{
				setCfmMip(1),
				delCfmMip(2)
				}
			MAX-ACCESS read-write
			STATUS current
			DESCRIPTION
				"The request of a user command"
			::= { sleGponCfmMipControl 1 }


--  1.3.6.1.4.1.6296.101.23.24.4.2.2
		sleGponCfmMipControlStatus OBJECT-TYPE
			SYNTAX SleControlStatusType
			MAX-ACCESS read-only
			STATUS current
			DESCRIPTION
				"The status of user command"
			::= { sleGponCfmMipControl 2 }


--  1.3.6.1.4.1.6296.101.23.24.4.2.3
		sleGponCfmMipControlTimer OBJECT-TYPE
			SYNTAX Gauge32
			MAX-ACCESS read-write
			STATUS current
			DESCRIPTION
				"The maximum time for the manager for a long running user command"
			::= { sleGponCfmMipControl 3 }


--  1.3.6.1.4.1.6296.101.23.24.4.2.4
		sleGponCfmMipControlTimeStamp OBJECT-TYPE
			SYNTAX TimeTicks
			MAX-ACCESS read-only
			STATUS current
			DESCRIPTION
				"The time stamp of the last command(end of command)"
			::= { sleGponCfmMipControl 4 }


--  1.3.6.1.4.1.6296.101.23.24.4.2.5
		sleGponCfmMipControlReqResult OBJECT-TYPE
			SYNTAX SleControlRequestResultType
			MAX-ACCESS read-only
			STATUS current
			DESCRIPTION
				"The result of the last user command"
			::= { sleGponCfmMipControl 5 }


		sleGponCfmMipControlOltId OBJECT-TYPE
			SYNTAX Integer32 (1..2147483647)
			MAX-ACCESS read-write
			STATUS current
			DESCRIPTION
				"Gpon Olt Index"
			::= { sleGponCfmMipControl 6 }


--  1.3.6.1.4.1.6296.101.23.24.4.2.7
		sleGponCfmMipControlOnuId OBJECT-TYPE
			SYNTAX Integer32
			MAX-ACCESS read-write
			STATUS current
			DESCRIPTION
				"Gpon Onu Index"
			::= { sleGponCfmMipControl 7 }


--  1.3.6.1.4.1.6296.101.23.24.4.2.8
		sleGponCfmMipControlLevel OBJECT-TYPE
			SYNTAX INTEGER (0..7)
			MAX-ACCESS read-write
			STATUS current
			DESCRIPTION
				"The CFM MIP Level."
			::= { sleGponCfmMipControl 8 }


--  1.3.6.1.4.1.6296.101.23.24.4.2.9
		sleGponCfmMipControlVlan OBJECT-TYPE
			SYNTAX OCTET STRING
			MAX-ACCESS read-write
			STATUS current
			DESCRIPTION
				"The CFM MIP VID list."
			::= { sleGponCfmMipControl 9 }


--  1.3.6.1.4.1.6296.101.23.24.4.3
		sleGponCfmMipNotification OBJECT IDENTIFIER ::= { sleGponCfmMip 3 }


--  1.3.6.1.4.1.6296.101.23.24.4.3.1
		sleGponCfmMipChanged NOTIFICATION-TYPE
			OBJECTS { sleGponCfmMipControlLevel, sleGponCfmMipControlVlan, sleGponCfmMipControlRequest, sleGponCfmMipControlTimeStamp, sleGponCfmMipControlReqResult,
				sleGponCfmMipControlOltId, sleGponCfmMipControlOnuId }
			STATUS current
			DESCRIPTION
				" "
			::= { sleGponCfmMipNotification 1 }


--  1.3.6.1.4.1.6296.101.23.24.4.3.2
		sleGponCfmMipDeleted NOTIFICATION-TYPE
			OBJECTS { sleGponCfmMipControlRequest, sleGponCfmMipControlTimeStamp, sleGponCfmMipControlReqResult, sleGponCfmMipControlOltId, sleGponCfmMipControlOnuId,
				sleGponCfmMipControlLevel }
			STATUS current
			DESCRIPTION
				" "
			::= { sleGponCfmMipNotification 2 }


--  1.3.6.1.4.1.6296.101.23.24.5
		sleGponCfmTest OBJECT IDENTIFIER ::= { sleGponCfm 5 }


--  1.3.6.1.4.1.6296.101.23.24.5.1
		sleGponCfmTestLbResultTable OBJECT-TYPE
			SYNTAX SEQUENCE OF SleGponCfmTestLbResultEntry
			MAX-ACCESS not-accessible
			STATUS current
			DESCRIPTION
				"Description."
			::= { sleGponCfmTest 1 }


--  1.3.6.1.4.1.6296.101.23.24.5.1.1
		sleGponCfmTestLbResultEntry OBJECT-TYPE
			SYNTAX SleGponCfmTestLbResultEntry
			MAX-ACCESS not-accessible
			STATUS current
			DESCRIPTION
				"Description."
			INDEX { sleGponOltId, sleGponOnuId, sleGponCfmTestLbResultSlotType, sleGponCfmTestLbResultPortIndex, sleGponCfmTestLbResultMepId
				 }
			::= { sleGponCfmTestLbResultTable 1 }


		SleGponCfmTestLbResultEntry ::=
			SEQUENCE {
				sleGponCfmTestLbResultSlotType
					INTEGER,
				sleGponCfmTestLbResultPortIndex
					Integer32,
				sleGponCfmTestLbResultMepId
					INTEGER,
				sleGponCfmTestLbResultRate
					Integer32,
				sleGponCfmTestLbResultAvg
					Integer32,
				sleGponCfmTestLbResultValidCount
					Integer32
			 }

--  1.3.6.1.4.1.6296.101.23.24.5.1.1.1
		sleGponCfmTestLbResultSlotType OBJECT-TYPE
			SYNTAX INTEGER
				{
				ethernet(1),
				iphost(2),
				ces(3),
				virtualEthernet(4),
				mapper(5),
				gem(6),
				bridgeAni(7)
				}
			MAX-ACCESS read-only
			STATUS current
			DESCRIPTION
				"The slot Type"
			::= { sleGponCfmTestLbResultEntry 1 }


--  1.3.6.1.4.1.6296.101.23.24.5.1.1.2
		sleGponCfmTestLbResultPortIndex OBJECT-TYPE
			SYNTAX Integer32 (0..65535)
			MAX-ACCESS read-only
			STATUS current
			DESCRIPTION
				"The port index."
			::= { sleGponCfmTestLbResultEntry 2 }


--  1.3.6.1.4.1.6296.101.23.24.5.1.1.3
		sleGponCfmTestLbResultMepId OBJECT-TYPE
			SYNTAX INTEGER (1..8196)
			MAX-ACCESS read-only
			STATUS current
			DESCRIPTION
				"This attribute specifies the MEP's own identity in the MA. For a given MA,
				the MEP ID must be unique throughout the network defined by the MD. The
				MEP ID is defined in the range 1..8191."
			::= { sleGponCfmTestLbResultEntry 3 }


--  1.3.6.1.4.1.6296.101.23.24.5.1.1.4
		sleGponCfmTestLbResultRate OBJECT-TYPE
			SYNTAX Integer32
			MAX-ACCESS read-only
			STATUS current
			DESCRIPTION
				"Loopback Success rate"
			::= { sleGponCfmTestLbResultEntry 4 }


--  1.3.6.1.4.1.6296.101.23.24.5.1.1.5
		sleGponCfmTestLbResultAvg OBJECT-TYPE
			SYNTAX Integer32
			MAX-ACCESS read-only
			STATUS current
			DESCRIPTION
				"The average round trip time of Loopback message"
			::= { sleGponCfmTestLbResultEntry 5 }


		sleGponCfmTestLbResultValidCount OBJECT-TYPE
			SYNTAX Integer32
			MAX-ACCESS read-only
			STATUS current
			DESCRIPTION
				"Loopback Success counter."
			::= { sleGponCfmTestLbResultEntry 6 }


--  1.3.6.1.4.1.6296.101.23.24.5.2
		sleGponCfmTestTrResultTable OBJECT-TYPE
			SYNTAX SEQUENCE OF SleGponCfmTestTrResultEntry
			MAX-ACCESS not-accessible
			STATUS current
			DESCRIPTION
				"Description."
			::= { sleGponCfmTest 2 }


--  1.3.6.1.4.1.6296.101.23.24.5.2.1
		sleGponCfmTestTrResultEntry OBJECT-TYPE
			SYNTAX SleGponCfmTestTrResultEntry
			MAX-ACCESS not-accessible
			STATUS current
			DESCRIPTION
				"Description."
			INDEX { sleGponOltId, sleGponOnuId, sleGponCfmTestTrResultSlotType, sleGponCfmTestTrResultPortIndex, sleGponCfmTestTrResultMepId,
				sleGponCfmTestTrResultReceiveOrder }
			::= { sleGponCfmTestTrResultTable 1 }


		SleGponCfmTestTrResultEntry ::=
			SEQUENCE {
				sleGponCfmTestTrResultSlotType
					INTEGER,
				sleGponCfmTestTrResultPortIndex
					Integer32,
				sleGponCfmTestTrResultMepId
					INTEGER,
				sleGponCfmTestTrResultReceiveOrder
					Integer32,
				sleGponCfmTestTrResultInfo
					OCTET STRING
			 }

--  1.3.6.1.4.1.6296.101.23.24.5.2.1.1
		sleGponCfmTestTrResultSlotType OBJECT-TYPE
			SYNTAX INTEGER
				{
				ethernet(1),
				iphost(2),
				ces(3),
				virtualEthernet(4),
				mapper(5),
				gem(6),
				bridgeAni(7)
				}
			MAX-ACCESS read-only
			STATUS current
			DESCRIPTION
				"The slot Type"
			::= { sleGponCfmTestTrResultEntry 1 }


--  1.3.6.1.4.1.6296.101.23.24.5.2.1.2
		sleGponCfmTestTrResultPortIndex OBJECT-TYPE
			SYNTAX Integer32 (0..65535)
			MAX-ACCESS read-only
			STATUS current
			DESCRIPTION
				"The port index."
			::= { sleGponCfmTestTrResultEntry 2 }


--  1.3.6.1.4.1.6296.101.23.24.5.2.1.3
		sleGponCfmTestTrResultMepId OBJECT-TYPE
			SYNTAX INTEGER (1..8196)
			MAX-ACCESS read-only
			STATUS current
			DESCRIPTION
				"This attribute specifies the MEP's own identity in the MA. For a given MA,
				the MEP ID must be unique throughout the network defined by the MD. The
				MEP ID is defined in the range 1..8191."
			::= { sleGponCfmTestTrResultEntry 3 }


--  1.3.6.1.4.1.6296.101.23.24.5.2.1.4
		sleGponCfmTestTrResultReceiveOrder OBJECT-TYPE
			SYNTAX Integer32 (0..65535)
			MAX-ACCESS read-only
			STATUS current
			DESCRIPTION
				"Indicates an index to distinguish among multiple LTRs with the same LTR Transaction Identifier field value"
			::= { sleGponCfmTestTrResultEntry 4 }


--  1.3.6.1.4.1.6296.101.23.24.5.2.1.5
		sleGponCfmTestTrResultInfo OBJECT-TYPE
			SYNTAX OCTET STRING
			MAX-ACCESS read-only
			STATUS current
			DESCRIPTION
				"The result of trace route"
			::= { sleGponCfmTestTrResultEntry 5 }


--  1.3.6.1.4.1.6296.101.23.24.5.3
		sleGponCfmTestControl OBJECT IDENTIFIER ::= { sleGponCfmTest 3 }


--  1.3.6.1.4.1.6296.101.23.24.5.3.1
		sleGponCfmTestControlRequest OBJECT-TYPE
			SYNTAX INTEGER
				{
				setLoopback(1),
				setTraceRoute(2)
				}
			MAX-ACCESS read-write
			STATUS current
			DESCRIPTION
				"The request of a user command"
			::= { sleGponCfmTestControl 1 }


--  1.3.6.1.4.1.6296.101.23.24.5.3.2
		sleGponCfmTestControlStatus OBJECT-TYPE
			SYNTAX SleControlStatusType
			MAX-ACCESS read-only
			STATUS current
			DESCRIPTION
				"The status of user command"
			::= { sleGponCfmTestControl 2 }


--  1.3.6.1.4.1.6296.101.23.24.5.3.3
		sleGponCfmTestControlTimer OBJECT-TYPE
			SYNTAX Gauge32
			MAX-ACCESS read-write
			STATUS current
			DESCRIPTION
				"The maximum time for the manager for a long running user command"
			::= { sleGponCfmTestControl 3 }


--  1.3.6.1.4.1.6296.101.23.24.5.3.4
		sleGponCfmTestControlTimeStamp OBJECT-TYPE
			SYNTAX TimeTicks
			MAX-ACCESS read-only
			STATUS current
			DESCRIPTION
				"The time stamp of the last command(end of command)"
			::= { sleGponCfmTestControl 4 }


--  1.3.6.1.4.1.6296.101.23.24.5.3.5
		sleGponCfmTestControlReqResult OBJECT-TYPE
			SYNTAX SleControlRequestResultType
			MAX-ACCESS read-only
			STATUS current
			DESCRIPTION
				"The result of the last user command"
			::= { sleGponCfmTestControl 5 }


		sleGponCfmTestControlOltId OBJECT-TYPE
			SYNTAX Integer32 (1..2147483647)
			MAX-ACCESS read-write
			STATUS current
			DESCRIPTION
				"Gpon Olt Index"
			::= { sleGponCfmTestControl 6 }


--  1.3.6.1.4.1.6296.101.23.24.5.3.7
		sleGponCfmTestControlOnuId OBJECT-TYPE
			SYNTAX Integer32
			MAX-ACCESS read-write
			STATUS current
			DESCRIPTION
				"Gpon Onu Index"
			::= { sleGponCfmTestControl 7 }


--  1.3.6.1.4.1.6296.101.23.24.5.3.8
		sleGponCfmTestControlSlotType OBJECT-TYPE
			SYNTAX INTEGER
				{
				ethernet(1),
				iphost(2),
				ces(3),
				virtualEthernet(4),
				mapper(5),
				gem(6),
				bridgeAni(7)
				}
			MAX-ACCESS read-write
			STATUS current
			DESCRIPTION
				"The slot Type"
			::= { sleGponCfmTestControl 8 }


--  1.3.6.1.4.1.6296.101.23.24.5.3.9
		sleGponCfmTestControlPortindex OBJECT-TYPE
			SYNTAX Integer32
			MAX-ACCESS read-write
			STATUS current
			DESCRIPTION
				"The port index."
			::= { sleGponCfmTestControl 9 }


--  1.3.6.1.4.1.6296.101.23.24.5.3.10
		sleGponCfmTestControlMepid OBJECT-TYPE
			SYNTAX INTEGER (1..8196)
			MAX-ACCESS read-write
			STATUS current
			DESCRIPTION
				"This attribute specifies the MEP's own identity in the MA. For a given MA,
				the MEP ID must be unique throughout the network defined by the MD. The
				MEP ID is defined in the range 1..8191."
			::= { sleGponCfmTestControl 10 }


--  1.3.6.1.4.1.6296.101.23.24.5.3.11
		sleGponCfmTestControlRmepid OBJECT-TYPE
			SYNTAX INTEGER (1..8196)
			MAX-ACCESS read-write
			STATUS current
			DESCRIPTION
				"Remote MepId"
			::= { sleGponCfmTestControl 11 }


--  1.3.6.1.4.1.6296.101.23.24.5.3.12
		sleGponCfmTestControlRmac OBJECT-TYPE
			SYNTAX OCTET STRING
			MAX-ACCESS read-write
			STATUS current
			DESCRIPTION
				"Target Mac address"
			::= { sleGponCfmTestControl 12 }


--  1.3.6.1.4.1.6296.101.23.24.5.3.13
		sleGponCfmTestControlCount OBJECT-TYPE
			SYNTAX Integer32
			MAX-ACCESS read-write
			STATUS current
			DESCRIPTION
				"The number of Loopback messages to be transmitted"
			::= { sleGponCfmTestControl 13 }


--  1.3.6.1.4.1.6296.101.23.24.5.3.14
		sleGponCfmTestControlPriority OBJECT-TYPE
			SYNTAX INTEGER (0..7)
			MAX-ACCESS read-write
			STATUS current
			DESCRIPTION
				"Priority. 3 bit value to be used in the VLAN tag"
			::= { sleGponCfmTestControl 14 }


--  1.3.6.1.4.1.6296.101.23.24.5.3.15
		sleGponCfmTestControlLength OBJECT-TYPE
			SYNTAX INTEGER (5..1480)
			MAX-ACCESS read-write
			STATUS current
			DESCRIPTION
				"Indicates the length of Data TLV"
			::= { sleGponCfmTestControl 15 }


--  1.3.6.1.4.1.6296.101.23.24.5.3.16
		sleGponCfmTestControlTtl OBJECT-TYPE
			SYNTAX INTEGER (1..64)
			MAX-ACCESS read-write
			STATUS current
			DESCRIPTION
				"Indicates the length of Data TLV"
			::= { sleGponCfmTestControl 16 }


--  1.3.6.1.4.1.6296.101.23.24.5.4
		sleGponCfmTestNotification OBJECT IDENTIFIER ::= { sleGponCfmTest 4 }


--  1.3.6.1.4.1.6296.101.23.24.5.4.1
		sleGponCfmTestLbChanged NOTIFICATION-TYPE
			OBJECTS { sleGponCfmTestControlRequest, sleGponCfmTestControlTimeStamp, sleGponCfmTestControlReqResult, sleGponCfmTestControlOltId, sleGponCfmTestControlOnuId,
				sleGponCfmTestControlSlotType, sleGponCfmTestControlPortindex, sleGponCfmTestControlMepid, sleGponCfmTestControlCount, sleGponCfmTestControlPriority,
				sleGponCfmTestControlLength, sleGponCfmTestControlRmepid, sleGponCfmTestControlRmac }
			STATUS current
			DESCRIPTION
				" "
			::= { sleGponCfmTestNotification 1 }


--  1.3.6.1.4.1.6296.101.23.24.5.4.2
		sleGponCfmTestTrChanged NOTIFICATION-TYPE
			OBJECTS { sleGponCfmTestControlRequest, sleGponCfmTestControlTimeStamp, sleGponCfmTestControlReqResult, sleGponCfmTestControlOltId, sleGponCfmTestControlOnuId,
				sleGponCfmTestControlSlotType, sleGponCfmTestControlPortindex, sleGponCfmTestControlMepid, sleGponCfmTestControlCount, sleGponCfmTestControlPriority,
				sleGponCfmTestControlLength, sleGponCfmTestControlTtl, sleGponCfmTestControlRmepid, sleGponCfmTestControlRmac }
			STATUS current
			DESCRIPTION
				" "
			::= { sleGponCfmTestNotification 2 }


--  1.3.6.1.4.1.6296.101.23.24.6
		sleGponCfmRmep OBJECT IDENTIFIER ::= { sleGponCfm 6 }


--  1.3.6.1.4.1.6296.101.23.24.6.1
		sleGponCfmRmepTable OBJECT-TYPE
			SYNTAX SEQUENCE OF SleGponCfmRmepEntry
			MAX-ACCESS not-accessible
			STATUS current
			DESCRIPTION
				"Description."
			::= { sleGponCfmRmep 1 }


--  1.3.6.1.4.1.6296.101.23.24.6.1.1
		sleGponCfmRmepEntry OBJECT-TYPE
			SYNTAX SleGponCfmRmepEntry
			MAX-ACCESS not-accessible
			STATUS current
			DESCRIPTION
				"Description."
			INDEX { sleGponOltId, sleGponOnuId, sleGponCfmMepSlotType, sleGponCfmMepPortIndex, sleGponCfmMepMepid,
				sleGponCfmRmepIndex }
			::= { sleGponCfmRmepTable 1 }


		SleGponCfmRmepEntry ::=
			SEQUENCE {
				sleGponCfmRmepSlotType
					INTEGER,
				sleGponCfmRmepPortIndex
					Integer32,
				sleGponCfmRmepMepId
					INTEGER,
				sleGponCfmRmepIndex
					INTEGER,
				sleGponCfmRmepRmepId
					INTEGER,
				sleGponCfmRmepRmac
					OCTET STRING,
				sleGponCfmRmepState
					INTEGER
			 }

--  1.3.6.1.4.1.6296.101.23.24.6.1.1.1
		sleGponCfmRmepSlotType OBJECT-TYPE
			SYNTAX INTEGER
				{
				ethernet(1),
				iphost(2),
				ces(3),
				virtualEthernet(4),
				mapper(5),
				gem(6),
				bridgeAni(7)
				}
			MAX-ACCESS read-only
			STATUS current
			DESCRIPTION
				"The slot Type"
			::= { sleGponCfmRmepEntry 1 }


--  1.3.6.1.4.1.6296.101.23.24.6.1.1.2
		sleGponCfmRmepPortIndex OBJECT-TYPE
			SYNTAX Integer32
			MAX-ACCESS read-only
			STATUS current
			DESCRIPTION
				"The port index."
			::= { sleGponCfmRmepEntry 2 }


--  1.3.6.1.4.1.6296.101.23.24.6.1.1.3
		sleGponCfmRmepMepId OBJECT-TYPE
			SYNTAX INTEGER (1..8196)
			MAX-ACCESS read-only
			STATUS current
			DESCRIPTION
				"This attribute specifies the MEP's own identity in the MA. For a given MA,
				the MEP ID must be unique throughout the network defined by the MD. The
				MEP ID is defined in the range 1..8191."
			::= { sleGponCfmRmepEntry 3 }


--  1.3.6.1.4.1.6296.101.23.24.6.1.1.4
		sleGponCfmRmepIndex OBJECT-TYPE
			SYNTAX INTEGER (1..8191)
			MAX-ACCESS read-only
			STATUS current
			DESCRIPTION
				"The Remote mep index"
			::= { sleGponCfmRmepEntry 4 }


--  1.3.6.1.4.1.6296.101.23.24.6.1.1.5
		sleGponCfmRmepRmepId OBJECT-TYPE
			SYNTAX INTEGER (1..8196)
			MAX-ACCESS read-only
			STATUS current
			DESCRIPTION
				"Remote Mepid"
			::= { sleGponCfmRmepEntry 5 }


--  1.3.6.1.4.1.6296.101.23.24.6.1.1.6
		sleGponCfmRmepRmac OBJECT-TYPE
			SYNTAX OCTET STRING
			MAX-ACCESS read-only
			STATUS current
			DESCRIPTION
				"Mac address."
			::= { sleGponCfmRmepEntry 6 }


--  1.3.6.1.4.1.6296.101.23.24.6.1.1.7
		sleGponCfmRmepState OBJECT-TYPE
			SYNTAX INTEGER
				{
				idle(1),
				start(2),
				failed(3),
				ok(4)
				}
			MAX-ACCESS read-only
			STATUS current
			DESCRIPTION
				"Indicates the operational state of the remote MEP State machines"
			::= { sleGponCfmRmepEntry 7 }


--  1.3.6.1.4.1.6296.101.23.24.6.2
		sleGponCfmRmepControl OBJECT IDENTIFIER ::= { sleGponCfmRmep 2 }


--  1.3.6.1.4.1.6296.101.23.24.6.2.1
		sleGponCfmRmepControlRequest OBJECT-TYPE
			SYNTAX INTEGER { updateRmepInfo(1) }
			MAX-ACCESS read-write
			STATUS current
			DESCRIPTION
				"The request of a user command"
			::= { sleGponCfmRmepControl 1 }


--  1.3.6.1.4.1.6296.101.23.24.6.2.2
		sleGponCfmRmepControlStatus OBJECT-TYPE
			SYNTAX SleControlStatusType
			MAX-ACCESS read-only
			STATUS current
			DESCRIPTION
				"The status of user command"
			::= { sleGponCfmRmepControl 2 }


--  1.3.6.1.4.1.6296.101.23.24.6.2.3
		sleGponCfmRmepControlTimer OBJECT-TYPE
			SYNTAX Gauge32
			MAX-ACCESS read-write
			STATUS current
			DESCRIPTION
				"The maximum time for the manager for a long running user command"
			::= { sleGponCfmRmepControl 3 }


--  1.3.6.1.4.1.6296.101.23.24.6.2.4
		sleGponCfmRmepControlTimeStamp OBJECT-TYPE
			SYNTAX TimeTicks
			MAX-ACCESS read-only
			STATUS current
			DESCRIPTION
				"The time stamp of the last command(end of command)"
			::= { sleGponCfmRmepControl 4 }


--  1.3.6.1.4.1.6296.101.23.24.6.2.5
		sleGponCfmRmepControlReqResult OBJECT-TYPE
			SYNTAX SleControlRequestResultType
			MAX-ACCESS read-only
			STATUS current
			DESCRIPTION
				"The result of the last user command"
			::= { sleGponCfmRmepControl 5 }


		sleGponCfmRmepControlOltId OBJECT-TYPE
			SYNTAX Integer32 (1..2147483647)
			MAX-ACCESS read-write
			STATUS current
			DESCRIPTION
				"Gpon Olt Index"
			::= { sleGponCfmRmepControl 6 }


--  1.3.6.1.4.1.6296.101.23.24.6.2.7
		sleGponCfmRmepControlOnuId OBJECT-TYPE
			SYNTAX Integer32
			MAX-ACCESS read-write
			STATUS current
			DESCRIPTION
				"Gpon Onu Index"
			::= { sleGponCfmRmepControl 7 }


--  1.3.6.1.4.1.6296.101.23.24.6.2.8
		sleGponCfmRmepControlSlotType OBJECT-TYPE
			SYNTAX INTEGER
				{
				ethernet(1),
				iphost(2),
				ces(3),
				virtualEthernet(4),
				mapper(5),
				gem(6),
				bridgeAni(7)
				}
			MAX-ACCESS read-write
			STATUS current
			DESCRIPTION
				"The slot Type"
			::= { sleGponCfmRmepControl 8 }


--  1.3.6.1.4.1.6296.101.23.24.6.2.9
		sleGponCfmRmepControlPortindex OBJECT-TYPE
			SYNTAX Integer32
			MAX-ACCESS read-write
			STATUS current
			DESCRIPTION
				"The port index."
			::= { sleGponCfmRmepControl 9 }


--  1.3.6.1.4.1.6296.101.23.24.6.2.10
		sleGponCfmRmepControlMepid OBJECT-TYPE
			SYNTAX INTEGER (1..8196)
			MAX-ACCESS read-write
			STATUS current
			DESCRIPTION
				"This attribute specifies the MEP's own identity in the MA. For a given MA,
				the MEP ID must be unique throughout the network defined by the MD. The
				MEP ID is defined in the range 1..8191."
			::= { sleGponCfmRmepControl 10 }


--  1.3.6.1.4.1.6296.101.23.24.6.3
		copyOfsleGponCfmMepNotification OBJECT IDENTIFIER ::= { sleGponCfmRmep 3 }


--  1.3.6.1.4.1.6296.101.23.24.6.3.1
		sleGponCfmRmepUpdated NOTIFICATION-TYPE
			OBJECTS { sleGponCfmRmepControlRequest, sleGponCfmRmepControlTimeStamp, sleGponCfmRmepControlReqResult, sleGponCfmRmepControlOltId, sleGponCfmRmepControlOnuId,
				sleGponCfmRmepControlSlotType, sleGponCfmRmepControlPortindex, sleGponCfmRmepControlMepid }
			STATUS current
			DESCRIPTION
				" "
			::= { copyOfsleGponCfmMepNotification 1 }


		sleGponOnuGsp OBJECT IDENTIFIER ::= { sleGpon 25 }


		sleGponOnuGspTable OBJECT-TYPE
			SYNTAX SEQUENCE OF SleGponOnuGspEntry
			MAX-ACCESS not-accessible
			STATUS current
			DESCRIPTION
				"Description."
			::= { sleGponOnuGsp 1 }


		sleGponOnuGspEntry OBJECT-TYPE
			SYNTAX SleGponOnuGspEntry
			MAX-ACCESS not-accessible
			STATUS current
			DESCRIPTION
				"Description."
			INDEX { sleGponOltId, sleGponOnuId, sleGponOnuGspType, sleGponOnuGspIndex }
			::= { sleGponOnuGspTable 1 }


		SleGponOnuGspEntry ::=
			SEQUENCE {
				sleGponOnuGspType
					INTEGER,
				sleGponOnuGspIndex
					Integer32,
				sleGponOnuGspData
					OCTET STRING
			 }

		sleGponOnuGspType OBJECT-TYPE
			SYNTAX INTEGER
				{
				gspStatusDocTable(1),
				gspConfDocTable(2)
				}
			MAX-ACCESS read-only
			STATUS current
			DESCRIPTION
				"SP(Generic status portal) Table Type
				1: GSP(Generic status portal) Status document table
				2: GSP(Generic status portal) Configuration document table"
			::= { sleGponOnuGspEntry 1 }


		sleGponOnuGspIndex OBJECT-TYPE
			SYNTAX Integer32 (1..65535)
			MAX-ACCESS read-only
			STATUS current
			DESCRIPTION
				"GSP(Generic status portal) document table Index
				Each Index means 1KB data."
			::= { sleGponOnuGspEntry 2 }


		sleGponOnuGspData OBJECT-TYPE
			SYNTAX OCTET STRING
			MAX-ACCESS read-only
			STATUS current
			DESCRIPTION
				"GSP(Generic status portal) document table"
			::= { sleGponOnuGspEntry 3 }


--  1.3.6.1.4.1.6296.101.23.24.1.2
		sleGponOnuGspControl OBJECT IDENTIFIER ::= { sleGponOnuGsp 2 }


--  1.3.6.1.4.1.6296.101.23.24.1.2.1
		sleGponOnuGspControlRequest OBJECT-TYPE
			SYNTAX INTEGER { updateOnuGspInfo(1) }
			MAX-ACCESS read-write
			STATUS current
			DESCRIPTION
				"The request of a user command"
			::= { sleGponOnuGspControl 1 }


--  1.3.6.1.4.1.6296.101.23.24.1.2.2
		sleGponOnuGspControlStatus OBJECT-TYPE
			SYNTAX SleControlStatusType
			MAX-ACCESS read-only
			STATUS current
			DESCRIPTION
				"The status of user command"
			::= { sleGponOnuGspControl 2 }


--  1.3.6.1.4.1.6296.101.23.24.1.2.3
		sleGponOnuGspControlTimer OBJECT-TYPE
			SYNTAX Gauge32
			MAX-ACCESS read-write
			STATUS current
			DESCRIPTION
				"The maximum time for the manager for a long running user command"
			::= { sleGponOnuGspControl 3 }


--  1.3.6.1.4.1.6296.101.23.24.1.2.4
		sleGponOnuGspControlTimeStamp OBJECT-TYPE
			SYNTAX TimeTicks
			MAX-ACCESS read-only
			STATUS current
			DESCRIPTION
				"The time stamp of the last command(end of command)"
			::= { sleGponOnuGspControl 4 }


--  1.3.6.1.4.1.6296.101.23.24.1.2.5
		sleGponOnuGspControlReqResult OBJECT-TYPE
			SYNTAX SleControlRequestResultType
			MAX-ACCESS read-only
			STATUS current
			DESCRIPTION
				"The result of the last user command"
			::= { sleGponOnuGspControl 5 }


		sleGponOnuGspControlOltId OBJECT-TYPE
			SYNTAX Integer32 (1..2147483647)
			MAX-ACCESS read-write
			STATUS current
			DESCRIPTION
				"Gpon Olt Index"
			::= { sleGponOnuGspControl 6 }


--  1.3.6.1.4.1.6296.101.23.24.1.2.6
		sleGponOnuGspControlOnuId OBJECT-TYPE
			SYNTAX Integer32
			MAX-ACCESS read-write
			STATUS current
			DESCRIPTION
				"Gpon Onu Index (OxFF is all onu)"
			::= { sleGponOnuGspControl 7 }


--  1.3.6.1.4.1.6296.101.23.24.1.2.6
		sleGponOnuGspControlType OBJECT-TYPE
			SYNTAX INTEGER
				{
				gspStatusDocTable(1),
				gspConfDocTable(2)
				}
			MAX-ACCESS read-write
			STATUS current
			DESCRIPTION
				"GSP(Generic status portal) Table Type"
			::= { sleGponOnuGspControl 8 }


		sleGponOnuGspNotification OBJECT IDENTIFIER ::= { sleGponOnuGsp 3 }


		sleGponOnuGspInfoUpdated NOTIFICATION-TYPE
			OBJECTS { sleGponOnuGspControlRequest, sleGponOnuGspControlTimeStamp, sleGponOnuGspControlReqResult, sleGponOnuGspControlOltId, sleGponOnuGspControlOnuId,
				sleGponOnuGspControlType }
			STATUS current
			DESCRIPTION
				"updateOnuGspInfo"
			::= { sleGponOnuGspNotification 1 }


--  1.3.6.1.4.1.6296.101.23.51
		sleGponProfile2 OBJECT IDENTIFIER ::= { sleGpon 51 }


--   1.3.6.1.4.1.6296.101.23.51.1
-- 1.3.6.1.4.1.6296.101.23.51.1
		sleGponProfile2Dba OBJECT IDENTIFIER ::= { sleGponProfile2 1 }


--   1.3.6.1.4.1.6296.101.23.51.1.1
-- 1.3.6.1.4.1.6296.101.23.51.1.1
		sleGponProfile2DbaTable OBJECT-TYPE
			SYNTAX SEQUENCE OF SleGponProfile2DbaEntry
			MAX-ACCESS not-accessible
			STATUS current
			DESCRIPTION
				"sleGponProfile2DbaTable"
			::= { sleGponProfile2Dba 1 }


--   1.3.6.1.4.1.6296.101.23.51.1.1.1
-- 1.3.6.1.4.1.6296.101.23.51.1.1.1
		sleGponProfile2DbaEntry OBJECT-TYPE
			SYNTAX SleGponProfile2DbaEntry
			MAX-ACCESS not-accessible
			STATUS current
			DESCRIPTION
				"key: sleGponProfile2DbaIndex"
			INDEX { sleGponProfile2DbaIndex }
			::= { sleGponProfile2DbaTable 1 }


		SleGponProfile2DbaEntry ::=
			SEQUENCE {
				sleGponProfile2DbaIndex
					Integer32,
				sleGponProfile2DbaName
					OCTET STRING,
				sleGponProfile2DbaMode
					INTEGER,
				sleGponProfile2DbaSlaAssured
					Integer32,
				sleGponProfile2DbaSlaFixed
					Integer32,
				sleGponProfile2DbaSlaMax
					Integer32,
				sleGponProfile2DbaSlaMaxFlags
					INTEGER
			 }

--   1.3.6.1.4.1.6296.101.23.51.1.1.1.1
-- 1.3.6.1.4.1.6296.101.23.51.1.1.1.1
		sleGponProfile2DbaIndex OBJECT-TYPE
			SYNTAX Integer32 (1..65535)
			MAX-ACCESS read-only
			STATUS current
			DESCRIPTION
				"The DBA profile index."
			::= { sleGponProfile2DbaEntry 1 }


--   1.3.6.1.4.1.6296.101.23.51.1.1.1.2
-- 1.3.6.1.4.1.6296.101.23.51.1.1.1.2
		sleGponProfile2DbaName OBJECT-TYPE
			SYNTAX OCTET STRING
			MAX-ACCESS read-only
			STATUS current
			DESCRIPTION
				"The DBA profile name."
			::= { sleGponProfile2DbaEntry 2 }


--   1.3.6.1.4.1.6296.101.23.51.1.1.1.3
-- 1.3.6.1.4.1.6296.101.23.51.1.1.1.3
		sleGponProfile2DbaMode OBJECT-TYPE
			SYNTAX INTEGER
				{
				sr(1),
				nsr(2),
				fixedUbr(3),
				fixedCbr(4)
				}
			MAX-ACCESS read-only
			STATUS current
			DESCRIPTION
				"The SLA mode."
			::= { sleGponProfile2DbaEntry 3 }


--   1.3.6.1.4.1.6296.101.23.51.1.1.1.4
-- 1.3.6.1.4.1.6296.101.23.51.1.1.1.4
		sleGponProfile2DbaSlaAssured OBJECT-TYPE
			SYNTAX Integer32
			MAX-ACCESS read-only
			STATUS current
			DESCRIPTION
				"The SLA Assured bandwidth"
			::= { sleGponProfile2DbaEntry 4 }


--   1.3.6.1.4.1.6296.101.23.51.1.1.1.5
-- 1.3.6.1.4.1.6296.101.23.51.1.1.1.5
		sleGponProfile2DbaSlaFixed OBJECT-TYPE
			SYNTAX Integer32
			MAX-ACCESS read-only
			STATUS current
			DESCRIPTION
				"The SLA fixed bandwidth"
			::= { sleGponProfile2DbaEntry 5 }


--   1.3.6.1.4.1.6296.101.23.51.1.1.1.6
-- 1.3.6.1.4.1.6296.101.23.51.1.1.1.6
		sleGponProfile2DbaSlaMax OBJECT-TYPE
			SYNTAX Integer32
			MAX-ACCESS read-only
			STATUS current
			DESCRIPTION
				"The SLA maximum bandwidth"
			::= { sleGponProfile2DbaEntry 6 }


--   1.3.6.1.4.1.6296.101.23.51.1.1.1.7
-- 1.3.6.1.4.1.6296.101.23.51.1.1.1.7
		sleGponProfile2DbaSlaMaxFlags OBJECT-TYPE
			SYNTAX INTEGER
				{
				nonAssured(1),
				bestEffort(2),
				unknown(255)
				}
			MAX-ACCESS read-write
			STATUS current
			DESCRIPTION
				"The SLA maximum Flags"
			::= { sleGponProfile2DbaEntry 7 }


--   1.3.6.1.4.1.6296.101.23.51.1.2
-- 1.3.6.1.4.1.6296.101.23.51.1.2
		sleGponProfile2DbaControl OBJECT IDENTIFIER ::= { sleGponProfile2Dba 2 }


--   1.3.6.1.4.1.6296.101.23.51.1.2.1
-- 1.3.6.1.4.1.6296.101.23.51.1.2.1
		sleGponProfile2DbaControlRequest OBJECT-TYPE
			SYNTAX INTEGER
				{
				addDbaProfile(1),
				delDbaProfile(2),
				setDbaSla(3)
				}
			MAX-ACCESS read-write
			STATUS current
			DESCRIPTION
				"The request of a user command"
			::= { sleGponProfile2DbaControl 1 }


--   1.3.6.1.4.1.6296.101.23.51.1.2.2
-- 1.3.6.1.4.1.6296.101.23.51.1.2.2
		sleGponProfile2DbaControlStatus OBJECT-TYPE
			SYNTAX SleControlStatusType
			MAX-ACCESS read-write
			STATUS current
			DESCRIPTION
				"The status of user command"
			::= { sleGponProfile2DbaControl 2 }


--   1.3.6.1.4.1.6296.101.23.51.1.2.3
-- 1.3.6.1.4.1.6296.101.23.51.1.2.3
		sleGponProfile2DbaControlTimer OBJECT-TYPE
			SYNTAX Gauge32
			MAX-ACCESS read-write
			STATUS current
			DESCRIPTION
				"The maximum time for the manager for a long running user command"
			::= { sleGponProfile2DbaControl 3 }


--   1.3.6.1.4.1.6296.101.23.51.1.2.4
-- 1.3.6.1.4.1.6296.101.23.51.1.2.4
		sleGponProfile2DbaControlTimeStamp OBJECT-TYPE
			SYNTAX TimeTicks
			MAX-ACCESS read-write
			STATUS current
			DESCRIPTION
				"The time stamp of the last command(end of command)"
			::= { sleGponProfile2DbaControl 4 }


--   1.3.6.1.4.1.6296.101.23.51.1.2.5
-- 1.3.6.1.4.1.6296.101.23.51.1.2.5
		sleGponProfile2DbaControlReqResult OBJECT-TYPE
			SYNTAX SleControlRequestResultType
			MAX-ACCESS read-write
			STATUS current
			DESCRIPTION
				"The result of the last user command
				"
			::= { sleGponProfile2DbaControl 5 }


--   1.3.6.1.4.1.6296.101.23.51.1.2.6
-- 1.3.6.1.4.1.6296.101.23.51.1.2.6
		sleGponProfile2DbaControlName OBJECT-TYPE
			SYNTAX OCTET STRING
			MAX-ACCESS read-write
			STATUS current
			DESCRIPTION
				"The DBA profile name."
			::= { sleGponProfile2DbaControl 6 }


--   1.3.6.1.4.1.6296.101.23.51.1.2.7
-- 1.3.6.1.4.1.6296.101.23.51.1.2.7
		sleGponProfile2DbaControlMode OBJECT-TYPE
			SYNTAX INTEGER
				{
				sr(1),
				nsr(2),
				fixedUbr(3),
				fixedCbr(4)
				}
			MAX-ACCESS read-write
			STATUS current
			DESCRIPTION
				"The SLA mode."
			::= { sleGponProfile2DbaControl 7 }


--   1.3.6.1.4.1.6296.101.23.51.1.2.8
-- 1.3.6.1.4.1.6296.101.23.51.1.2.8
		sleGponProfile2DbaControlSlaAssured OBJECT-TYPE
			SYNTAX Integer32
			MAX-ACCESS read-write
			STATUS current
			DESCRIPTION
				"The SLA Assured bandwidth"
			::= { sleGponProfile2DbaControl 8 }


--   1.3.6.1.4.1.6296.101.23.51.1.2.9
-- 1.3.6.1.4.1.6296.101.23.51.1.2.9
		sleGponProfile2DbaControlSlaFixed OBJECT-TYPE
			SYNTAX Integer32
			MAX-ACCESS read-write
			STATUS current
			DESCRIPTION
				"The SLA fixed bandwidth"
			::= { sleGponProfile2DbaControl 9 }


--   1.3.6.1.4.1.6296.101.23.51.1.2.10
-- 1.3.6.1.4.1.6296.101.23.51.1.2.10
		sleGponProfile2DbaControlSlaMax OBJECT-TYPE
			SYNTAX Integer32
			MAX-ACCESS read-write
			STATUS current
			DESCRIPTION
				"The SLA maximum bandwidth"
			::= { sleGponProfile2DbaControl 10 }


--   1.3.6.1.4.1.6296.101.23.51.1.2.11
-- 1.3.6.1.4.1.6296.101.23.51.1.2.11
		sleGponProfile2DbaControlSlaMaxFlags OBJECT-TYPE
			SYNTAX INTEGER
				{
				nonAssured(1),
				bestEffort(2),
				unknown(255)
				}
			MAX-ACCESS read-write
			STATUS current
			DESCRIPTION
				"The SLA maximum Flags"
			::= { sleGponProfile2DbaControl 11 }


--   1.3.6.1.4.1.6296.101.23.51.1.3
-- 1.3.6.1.4.1.6296.101.23.51.1.3
		sleGponProfile2DbaNotification OBJECT IDENTIFIER ::= { sleGponProfile2Dba 3 }


--   1.3.6.1.4.1.6296.101.23.51.1.3.1
-- 1.3.6.1.4.1.6296.101.23.51.1.3.1
		sleGponProfile2DbaAdded NOTIFICATION-TYPE
			OBJECTS { sleGponProfile2DbaControlRequest, sleGponProfile2DbaControlTimeStamp, sleGponProfile2DbaControlReqResult, sleGponProfile2DbaControlName, sleGponProfile2DbaControlMode,
				sleGponProfile2DbaControlSlaAssured, sleGponProfile2DbaControlSlaFixed, sleGponProfile2DbaControlSlaMax, sleGponProfile2DbaControlSlaMaxFlags }
			STATUS current
			DESCRIPTION
				"Description."
			::= { sleGponProfile2DbaNotification 1 }


--   1.3.6.1.4.1.6296.101.23.51.1.3.2
-- 1.3.6.1.4.1.6296.101.23.51.1.3.2
		sleGponProfile2DbaDeleted NOTIFICATION-TYPE
			OBJECTS { sleGponProfile2DbaControlRequest, sleGponProfile2DbaControlTimeStamp, sleGponProfile2DbaControlReqResult, sleGponProfile2DbaControlName }
			STATUS current
			DESCRIPTION
				"Description."
			::= { sleGponProfile2DbaNotification 2 }


--   1.3.6.1.4.1.6296.101.23.51.1.3.3
-- 1.3.6.1.4.1.6296.101.23.51.1.3.3
		sleGponProfile2DbaSlaChanged NOTIFICATION-TYPE
			OBJECTS { sleGponProfile2DbaControlRequest, sleGponProfile2DbaControlTimeStamp, sleGponProfile2DbaControlReqResult, sleGponProfile2DbaControlName, sleGponProfile2DbaControlMode,
				sleGponProfile2DbaControlSlaAssured, sleGponProfile2DbaControlSlaFixed, sleGponProfile2DbaControlSlaMax, sleGponProfile2DbaControlSlaMaxFlags }
			STATUS current
			DESCRIPTION
				"Description."
			::= { sleGponProfile2DbaNotification 3 }


--   1.3.6.1.4.1.6296.101.23.51.2
-- 1.3.6.1.4.1.6296.101.23.51.2
		sleGponProfile2Traffic OBJECT IDENTIFIER ::= { sleGponProfile2 2 }


--   1.3.6.1.4.1.6296.101.23.51.2.1
-- 1.3.6.1.4.1.6296.101.23.51.2.1
		sleGponProfile2TrafficTable OBJECT-TYPE
			SYNTAX SEQUENCE OF SleGponProfile2TrafficEntry
			MAX-ACCESS not-accessible
			STATUS current
			DESCRIPTION
				"sleGponProfile2TrafficTable"
			::= { sleGponProfile2Traffic 1 }


--  sleGponProfile2TrafficTable
-- 1.3.6.1.4.1.6296.101.23.51.2.1.1
-- 1.3.6.1.4.1.6296.101.23.51.2.1.1
		sleGponProfile2TrafficEntry OBJECT-TYPE
			SYNTAX SleGponProfile2TrafficEntry
			MAX-ACCESS not-accessible
			STATUS current
			DESCRIPTION
				"key: sleGponProfile2TrafficIndex"
			INDEX { sleGponProfile2TrafficIndex }
			::= { sleGponProfile2TrafficTable 1 }


		SleGponProfile2TrafficEntry ::=
			SEQUENCE {
				sleGponProfile2TrafficIndex
					Integer32,
				sleGponProfile2TrafficName
					OCTET STRING
			 }

--  key: sleGponProfile2TrafficIndex
-- 1.3.6.1.4.1.6296.101.23.51.2.1.1.1
-- 1.3.6.1.4.1.6296.101.23.51.2.1.1.1
		sleGponProfile2TrafficIndex OBJECT-TYPE
			SYNTAX Integer32 (1..65535)
			MAX-ACCESS read-only
			STATUS current
			DESCRIPTION
				"The traffic profile index"
			::= { sleGponProfile2TrafficEntry 1 }


--   1.3.6.1.4.1.6296.101.23.51.2.1.1.2
-- 1.3.6.1.4.1.6296.101.23.51.2.1.1.2
		sleGponProfile2TrafficName OBJECT-TYPE
			SYNTAX OCTET STRING
			MAX-ACCESS read-only
			STATUS current
			DESCRIPTION
				"The traffic profile name."
			::= { sleGponProfile2TrafficEntry 2 }


--   1.3.6.1.4.1.6296.101.23.51.2.2
-- 1.3.6.1.4.1.6296.101.23.51.2.2
		sleGponProfile2TrafficControl OBJECT IDENTIFIER ::= { sleGponProfile2Traffic 2 }


--   1.3.6.1.4.1.6296.101.23.51.2.2.1
-- 1.3.6.1.4.1.6296.101.23.51.2.2.1
		sleGponProfile2TrafficControlRequest OBJECT-TYPE
			SYNTAX INTEGER
				{
				addTrafficProfile(1),
				delTrafficProfile(2)
				}
			MAX-ACCESS read-write
			STATUS current
			DESCRIPTION
				"The request of a user command"
			::= { sleGponProfile2TrafficControl 1 }


--   1.3.6.1.4.1.6296.101.23.51.2.2.2
-- 1.3.6.1.4.1.6296.101.23.51.2.2.2
		sleGponProfile2TrafficControlStatus OBJECT-TYPE
			SYNTAX SleControlStatusType
			MAX-ACCESS read-write
			STATUS current
			DESCRIPTION
				"The status of user command"
			::= { sleGponProfile2TrafficControl 2 }


--   1.3.6.1.4.1.6296.101.23.51.2.2.3
-- 1.3.6.1.4.1.6296.101.23.51.2.2.3
		sleGponProfile2TrafficControlTimer OBJECT-TYPE
			SYNTAX Gauge32
			MAX-ACCESS read-write
			STATUS current
			DESCRIPTION
				"The maximum time for the manager for a long running user command"
			::= { sleGponProfile2TrafficControl 3 }


--   1.3.6.1.4.1.6296.101.23.51.2.2.4
-- 1.3.6.1.4.1.6296.101.23.51.2.2.4
		sleGponProfile2TrafficControlTimeStamp OBJECT-TYPE
			SYNTAX TimeTicks
			MAX-ACCESS read-write
			STATUS current
			DESCRIPTION
				"The time stamp of the last command(end of command)"
			::= { sleGponProfile2TrafficControl 4 }


--   1.3.6.1.4.1.6296.101.23.51.2.2.5
-- 1.3.6.1.4.1.6296.101.23.51.2.2.5
		sleGponProfile2TrafficControlReqResult OBJECT-TYPE
			SYNTAX SleControlRequestResultType
			MAX-ACCESS read-write
			STATUS current
			DESCRIPTION
				"The result of the last user command"
			::= { sleGponProfile2TrafficControl 5 }


--   1.3.6.1.4.1.6296.101.23.51.2.2.6
-- 1.3.6.1.4.1.6296.101.23.51.2.2.6
		sleGponProfile2TrafficControlName OBJECT-TYPE
			SYNTAX OCTET STRING
			MAX-ACCESS read-write
			STATUS current
			DESCRIPTION
				"The Traffic profile name."
			::= { sleGponProfile2TrafficControl 6 }


--   1.3.6.1.4.1.6296.101.23.51.2.3
-- 1.3.6.1.4.1.6296.101.23.51.2.3
		sleGponProfile2TrafficNotification OBJECT IDENTIFIER ::= { sleGponProfile2Traffic 3 }


--   1.3.6.1.4.1.6296.101.23.51.2.3.1
-- 1.3.6.1.4.1.6296.101.23.51.2.3.1
		sleGponProfile2TrafficAdded NOTIFICATION-TYPE
			OBJECTS { sleGponProfile2TrafficControlRequest, sleGponProfile2TrafficControlStatus, sleGponProfile2TrafficControlTimer, sleGponProfile2TrafficControlTimeStamp, sleGponProfile2TrafficControlReqResult,
				sleGponProfile2TrafficControlName }
			STATUS current
			DESCRIPTION
				"Description."
			::= { sleGponProfile2TrafficNotification 1 }


--   1.3.6.1.4.1.6296.101.23.51.2.3.2
-- 1.3.6.1.4.1.6296.101.23.51.2.3.2
		sleGponProfile2TrafficDeleted NOTIFICATION-TYPE
			OBJECTS { sleGponProfile2TrafficControlRequest, sleGponProfile2TrafficControlStatus, sleGponProfile2TrafficControlTimer, sleGponProfile2TrafficControlTimeStamp, sleGponProfile2TrafficControlReqResult,
				sleGponProfile2TrafficControlName }
			STATUS current
			DESCRIPTION
				"Description."
			::= { sleGponProfile2TrafficNotification 2 }


--   1.3.6.1.4.1.6296.101.23.51.3
-- 1.3.6.1.4.1.6296.101.23.51.3
		sleGponProfile2Mapper OBJECT IDENTIFIER ::= { sleGponProfile2 3 }


--   1.3.6.1.4.1.6296.101.23.51.3.1
-- 1.3.6.1.4.1.6296.101.23.51.3.1
		sleGponProfile2MapperTable OBJECT-TYPE
			SYNTAX SEQUENCE OF SleGponProfile2MapperEntry
			MAX-ACCESS not-accessible
			STATUS current
			DESCRIPTION
				"sleGponProfile2MapperTable"
			::= { sleGponProfile2Mapper 1 }


--   1.3.6.1.4.1.6296.101.23.51.3.1.1
-- 1.3.6.1.4.1.6296.101.23.51.3.1.1
		sleGponProfile2MapperEntry OBJECT-TYPE
			SYNTAX SleGponProfile2MapperEntry
			MAX-ACCESS not-accessible
			STATUS current
			DESCRIPTION
				"key: sleGponProfile2TrafficIndex, sleGponProfile2MapperId"
			INDEX { sleGponProfile2TrafficIndex, sleGponProfile2MapperId }
			::= { sleGponProfile2MapperTable 1 }


		SleGponProfile2MapperEntry ::=
			SEQUENCE {
				sleGponProfile2MapperId
					Integer32,
				sleGponProfile2MapperGemportCount
					Integer32,
				sleGponProfile2MapperDefaultCoS
					Integer32,
				sleGponProfile2MapperDscp2Pbit
					EnableFlag,
				sleGponProfile2MapperCos0
					Integer32,
				sleGponProfile2MapperCos1
					Integer32,
				sleGponProfile2MapperCos2
					Integer32,
				sleGponProfile2MapperCos3
					Integer32,
				sleGponProfile2MapperCos4
					Integer32,
				sleGponProfile2MapperCos5
					Integer32,
				sleGponProfile2MapperCos6
					Integer32,
				sleGponProfile2MapperCos7
					Integer32,
				sleGponProfile2MapperActiveEth
					INTEGER
			 }

--   1.3.6.1.4.1.6296.101.23.51.3.1.1.1
-- 1.3.6.1.4.1.6296.101.23.51.3.1.1.1
		sleGponProfile2MapperId OBJECT-TYPE
			SYNTAX Integer32 (1..65535)
			MAX-ACCESS read-only
			STATUS current
			DESCRIPTION
				"The mapper ID."
			::= { sleGponProfile2MapperEntry 1 }


--   1.3.6.1.4.1.6296.101.23.51.3.1.1.2
-- 1.3.6.1.4.1.6296.101.23.51.3.1.1.2
		sleGponProfile2MapperGemportCount OBJECT-TYPE
			SYNTAX Integer32
			MAX-ACCESS read-only
			STATUS current
			DESCRIPTION
				"The mapper gemport count (1|2|4|8)"
			::= { sleGponProfile2MapperEntry 2 }


--   1.3.6.1.4.1.6296.101.23.51.3.1.1.3
-- 1.3.6.1.4.1.6296.101.23.51.3.1.1.3
		sleGponProfile2MapperDefaultCoS OBJECT-TYPE
			SYNTAX Integer32
			MAX-ACCESS read-only
			STATUS current
			DESCRIPTION
				"The mapper default CoS."
			::= { sleGponProfile2MapperEntry 3 }


--   1.3.6.1.4.1.6296.101.23.51.3.1.1.4
-- 1.3.6.1.4.1.6296.101.23.51.3.1.1.4
		sleGponProfile2MapperDscp2Pbit OBJECT-TYPE
			SYNTAX EnableFlag
			MAX-ACCESS read-only
			STATUS current
			DESCRIPTION
				"The DSCP to P bit marking"
			::= { sleGponProfile2MapperEntry 4 }


--   1.3.6.1.4.1.6296.101.23.51.3.1.1.5
-- 1.3.6.1.4.1.6296.101.23.51.3.1.1.5
		sleGponProfile2MapperCos0 OBJECT-TYPE
			SYNTAX Integer32
			MAX-ACCESS read-only
			STATUS current
			DESCRIPTION
				"COS to GEM port mapping configuration (Cos0)"
			::= { sleGponProfile2MapperEntry 5 }


--   1.3.6.1.4.1.6296.101.23.51.3.1.1.6
-- 1.3.6.1.4.1.6296.101.23.51.3.1.1.6
		sleGponProfile2MapperCos1 OBJECT-TYPE
			SYNTAX Integer32
			MAX-ACCESS read-only
			STATUS current
			DESCRIPTION
				"COS to GEM port mapping configuration (Cos1)"
			::= { sleGponProfile2MapperEntry 6 }


--   1.3.6.1.4.1.6296.101.23.51.3.1.1.7
-- 1.3.6.1.4.1.6296.101.23.51.3.1.1.7
		sleGponProfile2MapperCos2 OBJECT-TYPE
			SYNTAX Integer32
			MAX-ACCESS read-only
			STATUS current
			DESCRIPTION
				"COS to GEM port mapping configuration (Cos2)"
			::= { sleGponProfile2MapperEntry 7 }


--   1.3.6.1.4.1.6296.101.23.51.3.1.1.8
-- 1.3.6.1.4.1.6296.101.23.51.3.1.1.8
		sleGponProfile2MapperCos3 OBJECT-TYPE
			SYNTAX Integer32
			MAX-ACCESS read-only
			STATUS current
			DESCRIPTION
				"COS to GEM port mapping configuration (Cos3)"
			::= { sleGponProfile2MapperEntry 8 }


--   1.3.6.1.4.1.6296.101.23.51.3.1.1.9
-- 1.3.6.1.4.1.6296.101.23.51.3.1.1.9
		sleGponProfile2MapperCos4 OBJECT-TYPE
			SYNTAX Integer32
			MAX-ACCESS read-only
			STATUS current
			DESCRIPTION
				"COS to GEM port mapping configuration (Cos4)"
			::= { sleGponProfile2MapperEntry 9 }


--   1.3.6.1.4.1.6296.101.23.51.3.1.1.10
-- 1.3.6.1.4.1.6296.101.23.51.3.1.1.10
		sleGponProfile2MapperCos5 OBJECT-TYPE
			SYNTAX Integer32
			MAX-ACCESS read-only
			STATUS current
			DESCRIPTION
				"COS to GEM port mapping configuration (Cos5)"
			::= { sleGponProfile2MapperEntry 10 }


--   1.3.6.1.4.1.6296.101.23.51.3.1.1.11
-- 1.3.6.1.4.1.6296.101.23.51.3.1.1.11
		sleGponProfile2MapperCos6 OBJECT-TYPE
			SYNTAX Integer32
			MAX-ACCESS read-only
			STATUS current
			DESCRIPTION
				"COS to GEM port mapping configuration (Cos6)"
			::= { sleGponProfile2MapperEntry 11 }


--   1.3.6.1.4.1.6296.101.23.51.3.1.1.12
-- 1.3.6.1.4.1.6296.101.23.51.3.1.1.12
		sleGponProfile2MapperCos7 OBJECT-TYPE
			SYNTAX Integer32
			MAX-ACCESS read-only
			STATUS current
			DESCRIPTION
				"COS to GEM port mapping configuration (Cos7)"
			::= { sleGponProfile2MapperEntry 12 }


--  1.3.6.1.4.1.6296.101.23.51.3.1.1.13
		sleGponProfile2MapperActiveEth OBJECT-TYPE
			SYNTAX INTEGER
				{
				normalMapper(0),
				activeEthMapper(1)
				}
			MAX-ACCESS read-only
			STATUS current
			DESCRIPTION
				"The Active Ethernet type."
			::= { sleGponProfile2MapperEntry 13 }


--   1.3.6.1.4.1.6296.101.23.51.3.2
-- 1.3.6.1.4.1.6296.101.23.51.3.2
		sleGponProfile2MapperControl OBJECT IDENTIFIER ::= { sleGponProfile2Mapper 2 }


--   1.3.6.1.4.1.6296.101.23.51.3.2.1
-- 1.3.6.1.4.1.6296.101.23.51.3.2.1
		sleGponProfile2MapperControlRequest OBJECT-TYPE
			SYNTAX INTEGER
				{
				addMapper(1),
				delMapper(2),
				setGemportCount(3),
				setDefaultCos(4),
				setDscp2Bit(5),
				setCosGemport(6),
				addActiveEthMapper(7),
				delActiveEthMapper(8)
				}
			MAX-ACCESS read-write
			STATUS current
			DESCRIPTION
				"The request of a user command"
			::= { sleGponProfile2MapperControl 1 }


--   1.3.6.1.4.1.6296.101.23.51.3.2.2
-- 1.3.6.1.4.1.6296.101.23.51.3.2.2
		sleGponProfile2MapperControlStatus OBJECT-TYPE
			SYNTAX SleControlStatusType
			MAX-ACCESS read-write
			STATUS current
			DESCRIPTION
				"The status of user command"
			::= { sleGponProfile2MapperControl 2 }


--   1.3.6.1.4.1.6296.101.23.51.3.2.3
-- 1.3.6.1.4.1.6296.101.23.51.3.2.3
		sleGponProfile2MapperControlTimer OBJECT-TYPE
			SYNTAX Gauge32
			MAX-ACCESS read-write
			STATUS current
			DESCRIPTION
				"The maximum time for the manager for a long running user command"
			::= { sleGponProfile2MapperControl 3 }


--   1.3.6.1.4.1.6296.101.23.51.3.2.4
-- 1.3.6.1.4.1.6296.101.23.51.3.2.4
		sleGponProfile2MapperControlTimeStamp OBJECT-TYPE
			SYNTAX TimeTicks
			MAX-ACCESS read-write
			STATUS current
			DESCRIPTION
				"The time stamp of the last command(end of command)"
			::= { sleGponProfile2MapperControl 4 }


--   1.3.6.1.4.1.6296.101.23.51.3.2.5
-- 1.3.6.1.4.1.6296.101.23.51.3.2.5
		sleGponProfile2MapperControlReqResult OBJECT-TYPE
			SYNTAX SleControlRequestResultType
			MAX-ACCESS read-write
			STATUS current
			DESCRIPTION
				"The result of the last user command
				"
			::= { sleGponProfile2MapperControl 5 }


--   1.3.6.1.4.1.6296.101.23.51.3.2.6
-- 1.3.6.1.4.1.6296.101.23.51.3.2.6
		sleGponProfile2MapperControlTName OBJECT-TYPE
			SYNTAX OCTET STRING
			MAX-ACCESS read-write
			STATUS current
			DESCRIPTION
				"The Traffic profile name."
			::= { sleGponProfile2MapperControl 6 }


--   1.3.6.1.4.1.6296.101.23.51.3.2.7
-- 1.3.6.1.4.1.6296.101.23.51.3.2.7
		sleGponProfile2MapperControlId OBJECT-TYPE
			SYNTAX Integer32
			MAX-ACCESS read-write
			STATUS current
			DESCRIPTION
				"The mapper ID."
			::= { sleGponProfile2MapperControl 7 }


--   1.3.6.1.4.1.6296.101.23.51.3.2.8
-- 1.3.6.1.4.1.6296.101.23.51.3.2.8
		sleGponProfile2MapperControlGemportCount OBJECT-TYPE
			SYNTAX Integer32
			MAX-ACCESS read-write
			STATUS current
			DESCRIPTION
				"The mapper gemport count (1|2|4|8)"
			::= { sleGponProfile2MapperControl 8 }


--   1.3.6.1.4.1.6296.101.23.51.3.2.9
-- 1.3.6.1.4.1.6296.101.23.51.3.2.9
		sleGponProfile2MapperControlDefaultCoS OBJECT-TYPE
			SYNTAX Integer32
			MAX-ACCESS read-write
			STATUS current
			DESCRIPTION
				"The mapper default CoS."
			::= { sleGponProfile2MapperControl 9 }


--   1.3.6.1.4.1.6296.101.23.51.3.2.10
-- 1.3.6.1.4.1.6296.101.23.51.3.2.10
		sleGponProfile2MapperControlDscp2Pbit OBJECT-TYPE
			SYNTAX EnableFlag
			MAX-ACCESS read-write
			STATUS current
			DESCRIPTION
				"The DSCP to P bit marking"
			::= { sleGponProfile2MapperControl 10 }


--   1.3.6.1.4.1.6296.101.23.51.3.2.11
-- 1.3.6.1.4.1.6296.101.23.51.3.2.11
		sleGponProfile2MapperControlCosIndex OBJECT-TYPE
			SYNTAX INTEGER
				{
				cos0(1),
				cos1(2),
				cos2(3),
				cos3(4),
				cos4(5),
				cos5(6),
				cos6(7),
				cos7(8)
				}
			MAX-ACCESS read-write
			STATUS current
			DESCRIPTION
				"The CoS Index."
			::= { sleGponProfile2MapperControl 11 }


--   1.3.6.1.4.1.6296.101.23.51.3.2.12
-- 1.3.6.1.4.1.6296.101.23.51.3.2.12
		sleGponProfile2MapperControlCosGemport OBJECT-TYPE
			SYNTAX Integer32
			MAX-ACCESS read-write
			STATUS current
			DESCRIPTION
				"The gemport number."
			::= { sleGponProfile2MapperControl 12 }


--   1.3.6.1.4.1.6296.101.23.51.3.3
-- 1.3.6.1.4.1.6296.101.23.51.3.3
		sleGponProfile2MapperNotification OBJECT IDENTIFIER ::= { sleGponProfile2Mapper 3 }


--   1.3.6.1.4.1.6296.101.23.51.3.3.1
-- 1.3.6.1.4.1.6296.101.23.51.3.3.1
		sleGponProfile2MapperAdded NOTIFICATION-TYPE
			OBJECTS { sleGponProfile2MapperControlRequest, sleGponProfile2MapperControlStatus, sleGponProfile2MapperControlTimer, sleGponProfile2MapperControlTimeStamp, sleGponProfile2MapperControlReqResult,
				sleGponProfile2MapperControlTName, sleGponProfile2MapperControlId, sleGponProfile2MapperControlGemportCount, sleGponProfile2MapperControlDefaultCoS, sleGponProfile2MapperControlDscp2Pbit
				 }
			STATUS current
			DESCRIPTION
				"addMapper"
			::= { sleGponProfile2MapperNotification 1 }


--   1.3.6.1.4.1.6296.101.23.51.3.3.2
-- 1.3.6.1.4.1.6296.101.23.51.3.3.2
		sleGponProfile2MapperDeleted NOTIFICATION-TYPE
			OBJECTS { sleGponProfile2MapperControlRequest, sleGponProfile2MapperControlStatus, sleGponProfile2MapperControlTimer, sleGponProfile2MapperControlTimeStamp, sleGponProfile2MapperControlReqResult,
				sleGponProfile2MapperControlTName, sleGponProfile2MapperControlId }
			STATUS current
			DESCRIPTION
				"Description."
			::= { sleGponProfile2MapperNotification 2 }


--   1.3.6.1.4.1.6296.101.23.51.3.3.3
-- 1.3.6.1.4.1.6296.101.23.51.3.3.3
		sleGponProfile2MapperGemportCountChanged NOTIFICATION-TYPE
			OBJECTS { sleGponProfile2MapperControlRequest, sleGponProfile2MapperControlStatus, sleGponProfile2MapperControlTimer, sleGponProfile2MapperControlTimeStamp, sleGponProfile2MapperControlReqResult,
				sleGponProfile2MapperControlTName, sleGponProfile2MapperControlId, sleGponProfile2MapperControlGemportCount }
			STATUS current
			DESCRIPTION
				"Description."
			::= { sleGponProfile2MapperNotification 3 }


--   1.3.6.1.4.1.6296.101.23.51.3.3.4
-- 1.3.6.1.4.1.6296.101.23.51.3.3.4
		sleGponProfile2MapperDefaultCoSChanged NOTIFICATION-TYPE
			OBJECTS { sleGponProfile2MapperControlRequest, sleGponProfile2MapperControlStatus, sleGponProfile2MapperControlTimer, sleGponProfile2MapperControlTimeStamp, sleGponProfile2MapperControlReqResult,
				sleGponProfile2MapperControlTName, sleGponProfile2MapperControlId, sleGponProfile2MapperControlDefaultCoS }
			STATUS current
			DESCRIPTION
				"Description."
			::= { sleGponProfile2MapperNotification 4 }


--   1.3.6.1.4.1.6296.101.23.51.3.3.5
-- 1.3.6.1.4.1.6296.101.23.51.3.3.5
		sleGponProfile2MapperDscp2BitChanged NOTIFICATION-TYPE
			OBJECTS { sleGponProfile2MapperControlRequest, sleGponProfile2MapperControlStatus, sleGponProfile2MapperControlTimer, sleGponProfile2MapperControlTimeStamp, sleGponProfile2MapperControlReqResult,
				sleGponProfile2MapperControlTName, sleGponProfile2MapperControlId, sleGponProfile2MapperControlDefaultCoS }
			STATUS current
			DESCRIPTION
				"Description."
			::= { sleGponProfile2MapperNotification 5 }


--   1.3.6.1.4.1.6296.101.23.51.3.3.6
-- 1.3.6.1.4.1.6296.101.23.51.3.3.6
		sleGponProfile2MapperCosGemportChanged NOTIFICATION-TYPE
			OBJECTS { sleGponProfile2MapperControlRequest, sleGponProfile2MapperControlStatus, sleGponProfile2MapperControlTimer, sleGponProfile2MapperControlTimeStamp, sleGponProfile2MapperControlReqResult,
				sleGponProfile2MapperControlTName, sleGponProfile2MapperControlId, sleGponProfile2MapperControlCosIndex, sleGponProfile2MapperControlCosGemport }
			STATUS current
			DESCRIPTION
				"Description."
			::= { sleGponProfile2MapperNotification 6 }


--   1.3.6.1.4.1.6296.101.23.51.3.3.1
-- 1.3.6.1.4.1.6296.101.23.51.3.3.7
		sleGponProfile2MapperActiveEthCreated NOTIFICATION-TYPE
			OBJECTS { sleGponProfile2MapperControlRequest, sleGponProfile2MapperControlTimeStamp, sleGponProfile2MapperControlReqResult, sleGponProfile2MapperControlTName, sleGponProfile2MapperControlId,
				sleGponProfile2MapperControlGemportCount, sleGponProfile2MapperControlDefaultCoS, sleGponProfile2MapperControlDscp2Pbit }
			STATUS current
			DESCRIPTION
				"addActiveEthMapper"
			::= { sleGponProfile2MapperNotification 7 }


--   1.3.6.1.4.1.6296.101.23.51.3.3.2
-- 1.3.6.1.4.1.6296.101.23.51.3.3.8
		sleGponProfile2MapperActiveEthDeleted NOTIFICATION-TYPE
			OBJECTS { sleGponProfile2MapperControlRequest, sleGponProfile2MapperControlTimeStamp, sleGponProfile2MapperControlReqResult, sleGponProfile2MapperControlTName, sleGponProfile2MapperControlId
				 }
			STATUS current
			DESCRIPTION
				"delActiveEthMapper"
			::= { sleGponProfile2MapperNotification 8 }


--   1.3.6.1.4.1.6296.101.23.51.4
-- 1.3.6.1.4.1.6296.101.23.51.4
		sleGponProfile2Bridge OBJECT IDENTIFIER ::= { sleGponProfile2 4 }


--   1.3.6.1.4.1.6296.101.23.51.4.1
-- 1.3.6.1.4.1.6296.101.23.51.4.1
		sleGponProfile2BridgeTable OBJECT-TYPE
			SYNTAX SEQUENCE OF SleGponProfile2BridgeEntry
			MAX-ACCESS not-accessible
			STATUS current
			DESCRIPTION
				"sleGponProfile2BridgeTable"
			::= { sleGponProfile2Bridge 1 }


--   1.3.6.1.4.1.6296.101.23.51.4.1.1
-- 1.3.6.1.4.1.6296.101.23.51.4.1.1
		sleGponProfile2BridgeEntry OBJECT-TYPE
			SYNTAX SleGponProfile2BridgeEntry
			MAX-ACCESS not-accessible
			STATUS current
			DESCRIPTION
				"key: sleGponProfile2TrafficIndex, sleGponProfile2BridgeId"
			INDEX { sleGponProfile2TrafficIndex, sleGponProfile2BridgeId }
			::= { sleGponProfile2BridgeTable 1 }


		SleGponProfile2BridgeEntry ::=
			SEQUENCE {
				sleGponProfile2BridgeId
					Integer32,
				sleGponProfile2BridgeMacLearning
					EnableFlag,
				sleGponProfile2BridgeMaxHost
					Integer32,
				sleGponProfile2BridgeMcastFlag
					EnableFlag,
				sleGponProfile2BridgePortBridge
					EnableFlag
			 }

--   1.3.6.1.4.1.6296.101.23.51.4.1.1.1
-- 1.3.6.1.4.1.6296.101.23.51.4.1.1.1
		sleGponProfile2BridgeId OBJECT-TYPE
			SYNTAX Integer32 (1..4094)
			MAX-ACCESS read-only
			STATUS current
			DESCRIPTION
				"The Bridge ID."
			::= { sleGponProfile2BridgeEntry 1 }


--   1.3.6.1.4.1.6296.101.23.51.4.1.1.2
-- 1.3.6.1.4.1.6296.101.23.51.4.1.1.2
		sleGponProfile2BridgeMacLearning OBJECT-TYPE
			SYNTAX EnableFlag
			MAX-ACCESS read-only
			STATUS current
			DESCRIPTION
				"The Bridge mac learning."
			::= { sleGponProfile2BridgeEntry 2 }


--   1.3.6.1.4.1.6296.101.23.51.4.1.1.3
-- 1.3.6.1.4.1.6296.101.23.51.4.1.1.3
		sleGponProfile2BridgeMaxHost OBJECT-TYPE
			SYNTAX Integer32 (0..255)
			MAX-ACCESS read-only
			STATUS current
			DESCRIPTION
				"The Bridge max host."
			::= { sleGponProfile2BridgeEntry 3 }


--   1.3.6.1.4.1.6296.101.23.51.4.1.1.4
-- 1.3.6.1.4.1.6296.101.23.51.4.1.1.4
		sleGponProfile2BridgeMcastFlag OBJECT-TYPE
			SYNTAX EnableFlag
			MAX-ACCESS read-only
			STATUS current
			DESCRIPTION
				"The Mcast supporting."
			::= { sleGponProfile2BridgeEntry 4 }


--  1.3.6.1.4.1.6296.101.23.51.4.1.1.5
		sleGponProfile2BridgePortBridge OBJECT-TYPE
			SYNTAX EnableFlag
			MAX-ACCESS read-only
			STATUS current
			DESCRIPTION
				"The Port bridge."
			::= { sleGponProfile2BridgeEntry 5 }


--   1.3.6.1.4.1.6296.101.23.51.4.2
-- 1.3.6.1.4.1.6296.101.23.51.4.2
		sleGponProfile2BridgeControl OBJECT IDENTIFIER ::= { sleGponProfile2Bridge 2 }


--   1.3.6.1.4.1.6296.101.23.51.4.2.1
-- 1.3.6.1.4.1.6296.101.23.51.4.2.1
		sleGponProfile2BridgeControlRequest OBJECT-TYPE
			SYNTAX INTEGER
				{
				addBridge(1),
				delBridge(2),
				setMacLearning(3),
				setMaxHost(4),
				setMcast(5),
				setPortBridge(6)
				}
			MAX-ACCESS read-write
			STATUS current
			DESCRIPTION
				"The request of a user command"
			::= { sleGponProfile2BridgeControl 1 }


--   1.3.6.1.4.1.6296.101.23.51.4.2.2
-- 1.3.6.1.4.1.6296.101.23.51.4.2.2
		sleGponProfile2BridgeControlStatus OBJECT-TYPE
			SYNTAX SleControlStatusType
			MAX-ACCESS read-write
			STATUS current
			DESCRIPTION
				"The status of user command"
			::= { sleGponProfile2BridgeControl 2 }


--   1.3.6.1.4.1.6296.101.23.51.4.2.3
-- 1.3.6.1.4.1.6296.101.23.51.4.2.3
		sleGponProfile2BridgeControlTimer OBJECT-TYPE
			SYNTAX Gauge32
			MAX-ACCESS read-write
			STATUS current
			DESCRIPTION
				"The maximum time for the manager for a long running user command"
			::= { sleGponProfile2BridgeControl 3 }


--   1.3.6.1.4.1.6296.101.23.51.4.2.4
-- 1.3.6.1.4.1.6296.101.23.51.4.2.4
		sleGponProfile2BridgeControlTimeStamp OBJECT-TYPE
			SYNTAX TimeTicks
			MAX-ACCESS read-write
			STATUS current
			DESCRIPTION
				"The time stamp of the last command(end of command)"
			::= { sleGponProfile2BridgeControl 4 }


--   1.3.6.1.4.1.6296.101.23.51.4.2.5
-- 1.3.6.1.4.1.6296.101.23.51.4.2.5
		sleGponProfile2BridgeControlReqResult OBJECT-TYPE
			SYNTAX SleControlRequestResultType
			MAX-ACCESS read-write
			STATUS current
			DESCRIPTION
				"The result of the last user command"
			::= { sleGponProfile2BridgeControl 5 }


--   1.3.6.1.4.1.6296.101.23.51.4.2.6
-- 1.3.6.1.4.1.6296.101.23.51.4.2.6
		sleGponProfile2BridgeControlTName OBJECT-TYPE
			SYNTAX OCTET STRING
			MAX-ACCESS read-write
			STATUS current
			DESCRIPTION
				"The Traffic profile name."
			::= { sleGponProfile2BridgeControl 6 }


--   1.3.6.1.4.1.6296.101.23.51.4.2.7
-- 1.3.6.1.4.1.6296.101.23.51.4.2.7
		sleGponProfile2BridgeControlId OBJECT-TYPE
			SYNTAX Integer32
			MAX-ACCESS read-write
			STATUS current
			DESCRIPTION
				"The bridge ID."
			::= { sleGponProfile2BridgeControl 7 }


--   1.3.6.1.4.1.6296.101.23.51.4.2.8
-- 1.3.6.1.4.1.6296.101.23.51.4.2.8
		sleGponProfile2BridgeControlMacLearning OBJECT-TYPE
			SYNTAX EnableFlag
			MAX-ACCESS read-write
			STATUS current
			DESCRIPTION
				"The Bridge mac learning."
			::= { sleGponProfile2BridgeControl 8 }


--   1.3.6.1.4.1.6296.101.23.51.4.2.9
-- 1.3.6.1.4.1.6296.101.23.51.4.2.9
		sleGponProfile2BridgeControlMaxHost OBJECT-TYPE
			SYNTAX Integer32
			MAX-ACCESS read-write
			STATUS current
			DESCRIPTION
				"The Bridge max host."
			::= { sleGponProfile2BridgeControl 9 }


--   1.3.6.1.4.1.6296.101.23.51.4.2.10
-- 1.3.6.1.4.1.6296.101.23.51.4.2.10
		sleGponProfile2BridgeControlMcastFlag OBJECT-TYPE
			SYNTAX EnableFlag
			MAX-ACCESS read-write
			STATUS current
			DESCRIPTION
				"The Mcast supporting."
			::= { sleGponProfile2BridgeControl 10 }


--  1.3.6.1.4.1.6296.101.23.51.4.2.11
		sleGponProfile2BridgeControlPortBridge OBJECT-TYPE
			SYNTAX EnableFlag
			MAX-ACCESS read-write
			STATUS current
			DESCRIPTION
				"The Mcast supporting."
			::= { sleGponProfile2BridgeControl 11 }


--   1.3.6.1.4.1.6296.101.23.51.4.3
-- 1.3.6.1.4.1.6296.101.23.51.4.3
		sleGponProfile2BridgeNotification OBJECT IDENTIFIER ::= { sleGponProfile2Bridge 3 }


--   1.3.6.1.4.1.6296.101.23.51.4.3.1
-- 1.3.6.1.4.1.6296.101.23.51.4.3.1
		sleGponProfile2BridgeAdded NOTIFICATION-TYPE
			OBJECTS { sleGponProfile2BridgeControlRequest, sleGponProfile2BridgeControlTimeStamp, sleGponProfile2BridgeControlReqResult, sleGponProfile2BridgeControlTName, sleGponProfile2BridgeControlId,
				sleGponProfile2BridgeControlMacLearning }
			STATUS current
			DESCRIPTION
				"Description."
			::= { sleGponProfile2BridgeNotification 1 }


--   1.3.6.1.4.1.6296.101.23.51.4.3.2
-- 1.3.6.1.4.1.6296.101.23.51.4.3.2
		sleGponProfile2BridgeDeleted NOTIFICATION-TYPE
			OBJECTS { sleGponProfile2BridgeControlRequest, sleGponProfile2BridgeControlStatus, sleGponProfile2BridgeControlTimer, sleGponProfile2BridgeControlTimeStamp, sleGponProfile2BridgeControlReqResult,
				sleGponProfile2BridgeControlTName, sleGponProfile2BridgeControlId }
			STATUS current
			DESCRIPTION
				"Description."
			::= { sleGponProfile2BridgeNotification 2 }


--   1.3.6.1.4.1.6296.101.23.51.4.3.3
-- 1.3.6.1.4.1.6296.101.23.51.4.3.3
		sleGponProfile2BridgeMacLearningChanged NOTIFICATION-TYPE
			OBJECTS { sleGponProfile2BridgeControlRequest, sleGponProfile2BridgeControlTimeStamp, sleGponProfile2BridgeControlReqResult, sleGponProfile2BridgeControlTName, sleGponProfile2BridgeControlId,
				sleGponProfile2BridgeControlMacLearning }
			STATUS current
			DESCRIPTION
				"Description."
			::= { sleGponProfile2BridgeNotification 3 }


--   1.3.6.1.4.1.6296.101.23.51.4.3.4
-- 1.3.6.1.4.1.6296.101.23.51.4.3.4
		sleGponProfile2BridgeMaxHostChanged NOTIFICATION-TYPE
			OBJECTS { sleGponProfile2BridgeControlRequest, sleGponProfile2BridgeControlTimeStamp, sleGponProfile2BridgeControlReqResult, sleGponProfile2BridgeControlTName, sleGponProfile2BridgeControlId,
				sleGponProfile2BridgeControlMaxHost }
			STATUS current
			DESCRIPTION
				"Description."
			::= { sleGponProfile2BridgeNotification 4 }


--   1.3.6.1.4.1.6296.101.23.51.4.3.5
-- 1.3.6.1.4.1.6296.101.23.51.4.3.5
		sleGponProfile2BridgeMcastChanged NOTIFICATION-TYPE
			OBJECTS { sleGponProfile2BridgeControlRequest, sleGponProfile2BridgeControlStatus, sleGponProfile2BridgeControlTimer, sleGponProfile2BridgeControlTimeStamp, sleGponProfile2BridgeControlReqResult,
				sleGponProfile2BridgeControlTName, sleGponProfile2BridgeControlId, sleGponProfile2BridgeControlMcastFlag }
			STATUS current
			DESCRIPTION
				"Description."
			::= { sleGponProfile2BridgeNotification 5 }


--  1.3.6.1.4.1.6296.101.23.51.4.3.6
		sleGponProfile2BridgePortBridgeChanged NOTIFICATION-TYPE
			OBJECTS { sleGponProfile2BridgeControlRequest, sleGponProfile2BridgeControlStatus, sleGponProfile2BridgeControlTimer, sleGponProfile2BridgeControlTimeStamp, sleGponProfile2BridgeControlReqResult,
				sleGponProfile2BridgeControlTName, sleGponProfile2BridgeControlId }
			STATUS current
			DESCRIPTION
				"setPortBridge"
			::= { sleGponProfile2BridgeNotification 6 }


--   1.3.6.1.4.1.6296.101.23.51.5
-- 1.3.6.1.4.1.6296.101.23.51.5
		sleGponProfile2BridgeAni OBJECT IDENTIFIER ::= { sleGponProfile2 5 }


--   1.3.6.1.4.1.6296.101.23.51.5.1
-- 1.3.6.1.4.1.6296.101.23.51.5.1
		sleGponProfile2BridgeAniTable OBJECT-TYPE
			SYNTAX SEQUENCE OF SleGponProfile2BridgeAniEntry
			MAX-ACCESS not-accessible
			STATUS current
			DESCRIPTION
				"sleGponProfile2BridgeAniTable"
			::= { sleGponProfile2BridgeAni 1 }


--   1.3.6.1.4.1.6296.101.23.51.5.1.1
-- 1.3.6.1.4.1.6296.101.23.51.5.1.1
		sleGponProfile2BridgeAniEntry OBJECT-TYPE
			SYNTAX SleGponProfile2BridgeAniEntry
			MAX-ACCESS not-accessible
			STATUS current
			DESCRIPTION
				"key: sleGponProfile2TrafficIndex, sleGponProfile2BridgeId, sleGponProfile2BridgeAniId"
			INDEX { sleGponProfile2TrafficIndex, sleGponProfile2BridgeId, sleGponProfile2BridgeAniId }
			::= { sleGponProfile2BridgeAniTable 1 }


		SleGponProfile2BridgeAniEntry ::=
			SEQUENCE {
				sleGponProfile2BridgeAniId
					Integer32,
				sleGponProfile2BridgeAniVlanFilterMode
					INTEGER,
				sleGponProfile2BridgeAniVlanFilter
					OCTET STRING,
				sleGponProfile2BridgeAniMacFilterPreassign
					BITS
			 }

--   1.3.6.1.4.1.6296.101.23.51.5.1.1.1
-- 1.3.6.1.4.1.6296.101.23.51.5.1.1.1
		sleGponProfile2BridgeAniId OBJECT-TYPE
			SYNTAX Integer32 (1..65535)
			MAX-ACCESS read-only
			STATUS current
			DESCRIPTION
				"The Bridge ani mapper-ID."
			::= { sleGponProfile2BridgeAniEntry 1 }


--   1.3.6.1.4.1.6296.101.23.51.5.1.1.2
-- 1.3.6.1.4.1.6296.101.23.51.5.1.1.2
		sleGponProfile2BridgeAniVlanFilterMode OBJECT-TYPE
			SYNTAX INTEGER
				{
				allow(1),
				deny(2)
				}
			MAX-ACCESS read-only
			STATUS current
			DESCRIPTION
				"Allow or deny that untagged fowarding operation "
			::= { sleGponProfile2BridgeAniEntry 2 }


--   1.3.6.1.4.1.6296.101.23.51.5.1.1.3
-- 1.3.6.1.4.1.6296.101.23.51.5.1.1.3
		sleGponProfile2BridgeAniVlanFilter OBJECT-TYPE
			SYNTAX OCTET STRING
			MAX-ACCESS read-only
			STATUS current
			DESCRIPTION
				"The vlan-filter VID list."
			::= { sleGponProfile2BridgeAniEntry 3 }


--  1.3.6.1.4.1.6296.101.23.51.5.1.1.4
		sleGponProfile2BridgeAniMacFilterPreassign OBJECT-TYPE
			SYNTAX BITS
				{
				ipv4Multicast(0),
				ipv6Multicast(1),
				ipv4Broadcast(2),
				rarp(3),
				ipx(4),
				netBEUI(5),
				appleTalk(6),
				bridgeManagementInformation(7),
				arp(8),
				pppoeBroadcast(9)
				}
			MAX-ACCESS read-only
			STATUS current
			DESCRIPTION
				"MAC Filter Preassign Table
				0 -> forward
				1 -> filter"
			::= { sleGponProfile2BridgeAniEntry 4 }


--   1.3.6.1.4.1.6296.101.23.51.5.2
-- 1.3.6.1.4.1.6296.101.23.51.5.2
		sleGponProfile2BridgeAniControl OBJECT IDENTIFIER ::= { sleGponProfile2BridgeAni 2 }


--   1.3.6.1.4.1.6296.101.23.51.5.2.1
-- 1.3.6.1.4.1.6296.101.23.51.5.2.1
		sleGponProfile2BridgeAniControlRequest OBJECT-TYPE
			SYNTAX INTEGER
				{
				addBridgeAni(1),
				delBridgeAni(2),
				setVlanFilter(3),
				setAniMacFilterPreassign(4)
				}
			MAX-ACCESS read-write
			STATUS current
			DESCRIPTION
				"The request of a user command"
			::= { sleGponProfile2BridgeAniControl 1 }


--   1.3.6.1.4.1.6296.101.23.51.5.2.2
-- 1.3.6.1.4.1.6296.101.23.51.5.2.2
		sleGponProfile2BridgeAniControlStatus OBJECT-TYPE
			SYNTAX SleControlStatusType
			MAX-ACCESS read-write
			STATUS current
			DESCRIPTION
				"The status of user command"
			::= { sleGponProfile2BridgeAniControl 2 }


--   1.3.6.1.4.1.6296.101.23.51.5.2.3
-- 1.3.6.1.4.1.6296.101.23.51.5.2.3
		sleGponProfile2BridgeAniControlTimer OBJECT-TYPE
			SYNTAX Gauge32
			MAX-ACCESS read-write
			STATUS current
			DESCRIPTION
				"The maximum time for the manager for a long running user command"
			::= { sleGponProfile2BridgeAniControl 3 }


--   1.3.6.1.4.1.6296.101.23.51.5.2.4
-- 1.3.6.1.4.1.6296.101.23.51.5.2.4
		sleGponProfile2BridgeAniControlTimeStamp OBJECT-TYPE
			SYNTAX TimeTicks
			MAX-ACCESS read-write
			STATUS current
			DESCRIPTION
				"The time stamp of the last command(end of command)"
			::= { sleGponProfile2BridgeAniControl 4 }


--   1.3.6.1.4.1.6296.101.23.51.5.2.5
-- 1.3.6.1.4.1.6296.101.23.51.5.2.5
		sleGponProfile2BridgeAniControlReqResult OBJECT-TYPE
			SYNTAX SleControlRequestResultType
			MAX-ACCESS read-write
			STATUS current
			DESCRIPTION
				"The result of the last user command"
			::= { sleGponProfile2BridgeAniControl 5 }


--   1.3.6.1.4.1.6296.101.23.51.5.2.6
-- 1.3.6.1.4.1.6296.101.23.51.5.2.6
		sleGponProfile2BridgeAniControlTName OBJECT-TYPE
			SYNTAX OCTET STRING
			MAX-ACCESS read-write
			STATUS current
			DESCRIPTION
				"The Traffic profile name."
			::= { sleGponProfile2BridgeAniControl 6 }


--   1.3.6.1.4.1.6296.101.23.51.5.2.7
-- 1.3.6.1.4.1.6296.101.23.51.5.2.7
		sleGponProfile2BridgeAniControlBridgeId OBJECT-TYPE
			SYNTAX Integer32
			MAX-ACCESS read-write
			STATUS current
			DESCRIPTION
				"The bridge ID."
			::= { sleGponProfile2BridgeAniControl 7 }


--   1.3.6.1.4.1.6296.101.23.51.5.2.8
-- 1.3.6.1.4.1.6296.101.23.51.5.2.8
		sleGponProfile2BridgeAniControlId OBJECT-TYPE
			SYNTAX Integer32
			MAX-ACCESS read-write
			STATUS current
			DESCRIPTION
				"The bridge Ani ID."
			::= { sleGponProfile2BridgeAniControl 8 }


--   1.3.6.1.4.1.6296.101.23.51.5.2.9
-- 1.3.6.1.4.1.6296.101.23.51.5.2.9
		sleGponProfile2BridgeAniControlVlanFilterMode OBJECT-TYPE
			SYNTAX INTEGER
				{
				allow(1),
				deny(2)
				}
			MAX-ACCESS read-write
			STATUS current
			DESCRIPTION
				"Allow or deny that untagged fowarding operation "
			::= { sleGponProfile2BridgeAniControl 9 }


--   1.3.6.1.4.1.6296.101.23.51.5.2.10
-- 1.3.6.1.4.1.6296.101.23.51.5.2.10
		sleGponProfile2BridgeAniControlVlanFilter OBJECT-TYPE
			SYNTAX OCTET STRING
			MAX-ACCESS read-write
			STATUS current
			DESCRIPTION
				"The vlan-filter VID list."
			::= { sleGponProfile2BridgeAniControl 10 }


--  1.3.6.1.4.1.6296.101.23.51.5.2.11
		sleGponProfile2BridgeAniControlMacFilterPreassign OBJECT-TYPE
			SYNTAX BITS
				{
				ipv4Multicast(0),
				ipv6Multicast(1),
				ipv4Broadcast(2),
				rarp(3),
				ipx(4),
				netBEUI(5),
				appleTalk(6),
				bridgeManagementInformation(7),
				arp(8),
				pppoeBroadcast(9)
				}
			MAX-ACCESS read-write
			STATUS current
			DESCRIPTION
				"MAC Filter Preassign Table
				0 -> forward
				1 -> filter"
			::= { sleGponProfile2BridgeAniControl 11 }


--   1.3.6.1.4.1.6296.101.23.51.5.3
-- 1.3.6.1.4.1.6296.101.23.51.5.3
		sleGponProfile2BridgeAniNotification OBJECT IDENTIFIER ::= { sleGponProfile2BridgeAni 3 }


--   1.3.6.1.4.1.6296.101.23.51.5.3.1
-- 1.3.6.1.4.1.6296.101.23.51.5.3.1
		sleGponProfile2BridgeAniAdded NOTIFICATION-TYPE
			OBJECTS { sleGponProfile2BridgeAniControlRequest, sleGponProfile2BridgeAniControlStatus, sleGponProfile2BridgeAniControlTimer, sleGponProfile2BridgeAniControlTimeStamp, sleGponProfile2BridgeAniControlReqResult,
				sleGponProfile2BridgeAniControlTName, sleGponProfile2BridgeAniControlBridgeId, sleGponProfile2BridgeAniControlId }
			STATUS current
			DESCRIPTION
				"Description."
			::= { sleGponProfile2BridgeAniNotification 1 }


--   1.3.6.1.4.1.6296.101.23.51.5.3.2
-- 1.3.6.1.4.1.6296.101.23.51.5.3.2
		sleGponProfile2BridgeAniDeleted NOTIFICATION-TYPE
			OBJECTS { sleGponProfile2BridgeAniControlRequest, sleGponProfile2BridgeAniControlStatus, sleGponProfile2BridgeAniControlTimer, sleGponProfile2BridgeAniControlTimeStamp, sleGponProfile2BridgeAniControlReqResult,
				sleGponProfile2BridgeAniControlTName, sleGponProfile2BridgeAniControlBridgeId, sleGponProfile2BridgeAniControlId }
			STATUS current
			DESCRIPTION
				"Description."
			::= { sleGponProfile2BridgeAniNotification 2 }


--   1.3.6.1.4.1.6296.101.23.51.5.3.3
-- 1.3.6.1.4.1.6296.101.23.51.5.3.3
		sleGponProfile2BridgeAniVlanFilterChanged NOTIFICATION-TYPE
			OBJECTS { sleGponProfile2BridgeAniControlRequest, sleGponProfile2BridgeAniControlStatus, sleGponProfile2BridgeAniControlTimer, sleGponProfile2BridgeAniControlTimeStamp, sleGponProfile2BridgeAniControlReqResult,
				sleGponProfile2BridgeAniControlTName, sleGponProfile2BridgeAniControlBridgeId, sleGponProfile2BridgeAniControlId, sleGponProfile2BridgeAniControlVlanFilterMode, sleGponProfile2BridgeAniControlVlanFilter
				 }
			STATUS current
			DESCRIPTION
				"Description."
			::= { sleGponProfile2BridgeAniNotification 3 }


--  1.3.6.1.4.1.6296.101.23.51.5.3.4
		sleGponProfile2BridgeAniMacFilterPreassignChanged NOTIFICATION-TYPE
			OBJECTS { sleGponProfile2BridgeAniControlRequest, sleGponProfile2BridgeAniControlTimeStamp, sleGponProfile2BridgeAniControlReqResult, sleGponProfile2BridgeAniControlTName, sleGponProfile2BridgeAniControlBridgeId,
				sleGponProfile2BridgeAniControlId, sleGponProfile2BridgeAniControlMacFilterPreassign }
			STATUS current
			DESCRIPTION
				"setAniMacFilterPreassign"
			::= { sleGponProfile2BridgeAniNotification 4 }


--   1.3.6.1.4.1.6296.101.23.51.6
-- 1.3.6.1.4.1.6296.101.23.51.6
		sleGponProfile2BridgeUni OBJECT IDENTIFIER ::= { sleGponProfile2 6 }


--   1.3.6.1.4.1.6296.101.23.51.6.1
-- 1.3.6.1.4.1.6296.101.23.51.6.1
		sleGponProfile2BridgeUniTable OBJECT-TYPE
			SYNTAX SEQUENCE OF SleGponProfile2BridgeUniEntry
			MAX-ACCESS not-accessible
			STATUS current
			DESCRIPTION
				"sleGponProfile2BridgeUniTable"
			::= { sleGponProfile2BridgeUni 1 }


--   1.3.6.1.4.1.6296.101.23.51.6.1.1
-- 1.3.6.1.4.1.6296.101.23.51.6.1.1
		sleGponProfile2BridgeUniEntry OBJECT-TYPE
			SYNTAX SleGponProfile2BridgeUniEntry
			MAX-ACCESS not-accessible
			STATUS current
			DESCRIPTION
				"key: sleGponProfile2TrafficIndex, sleGponProfile2BridgeId, sleGponProfile2BridgeUniType, sleGponProfile2BridgeUniId"
			INDEX { sleGponProfile2TrafficIndex, sleGponProfile2BridgeId, sleGponProfile2BridgeUniType, sleGponProfile2BridgeUniId }
			::= { sleGponProfile2BridgeUniTable 1 }


		SleGponProfile2BridgeUniEntry ::=
			SEQUENCE {
				sleGponProfile2BridgeUniType
					INTEGER,
				sleGponProfile2BridgeUniId
					Integer32,
				sleGponProfile2BridgeUniVlanOpDsOperFlag
					INTEGER,
				sleGponProfile2BridgeUniVlanOpUsOperFlag
					INTEGER,
				sleGponProfile2BridgeUniVlanOpUsOperVid
					Integer32,
				sleGponProfile2BridgeUniVlanOpUsOperCos
					Integer32,
				sleGponProfile2BridgeUniPortAdmin
					EnableFlag,
				sleGponProfile2BridgeUniRateLimitDownSir
					Integer32,
				sleGponProfile2BridgeUniRateLimitDownPir
					Integer32,
				sleGponProfile2BridgeUniRateLimitUpSir
					Integer32,
				sleGponProfile2BridgeUniRateLimitUpPir
					Integer32,
				sleGponProfile2BridgeUniIgmpMaxGroup
					Integer32,
				sleGponProfile2BridgeUniMaxFrame
					Integer32,
				sleGponProfile2BridgeUniMcastProfile
					OCTET STRING,
				sleGponProfile2BridgeUniVlanFilterMode
					INTEGER,
				sleGponProfile2BridgeUniVlanFilter
					OCTET STRING,
				sleGponProfile2BridgeUniIpMode
					INTEGER,
				sleGponProfile2BridgeUniDns1
					IpAddress,
				sleGponProfile2BridgeUniDns2
					IpAddress,
				sleGponProfile2BridgeUniVoIPProfile
					OCTET STRING,
				sleGponProfile2BridgeUniMaxHost
					INTEGER,
				sleGponProfile2BridgeUniExtVlanName
					OCTET STRING,
				sleGponProfile2BridgeUniMcastRateLimit
					Integer32,
				sleGponProfile2BridgeUniMacFilterPreassign
					BITS,
				sleGponProfile2BridgeUniRateLimitProfile
					OCTET STRING,
				sleGponProfile2BridgeUniIneterDomainName
					OCTET STRING
			 }

--   1.3.6.1.4.1.6296.101.23.51.6.1.1.1
-- 1.3.6.1.4.1.6296.101.23.51.6.1.1.1
		sleGponProfile2BridgeUniType OBJECT-TYPE
			SYNTAX INTEGER
				{
				eth(1),
				voip(2),
				virtualEth(3)
				}
			MAX-ACCESS read-only
			STATUS current
			DESCRIPTION
				"The Bridge Uni Type."
			::= { sleGponProfile2BridgeUniEntry 1 }


--   1.3.6.1.4.1.6296.101.23.51.6.1.1.2
-- 1.3.6.1.4.1.6296.101.23.51.6.1.1.2
		sleGponProfile2BridgeUniId OBJECT-TYPE
			SYNTAX Integer32 (1..65535)
			MAX-ACCESS read-only
			STATUS current
			DESCRIPTION
				"The Bridge Uni mapper-ID."
			::= { sleGponProfile2BridgeUniEntry 2 }


--   1.3.6.1.4.1.6296.101.23.51.6.1.1.3
-- 1.3.6.1.4.1.6296.101.23.51.6.1.1.3
		sleGponProfile2BridgeUniVlanOpDsOperFlag OBJECT-TYPE
			SYNTAX INTEGER
				{
				unused(0),
				keep(1),
				remove(2)
				}
			MAX-ACCESS read-only
			STATUS current
			DESCRIPTION
				"The VLAN Tagging Operation Data & DS VLAN Tagging Operation mode"
			::= { sleGponProfile2BridgeUniEntry 3 }


--   1.3.6.1.4.1.6296.101.23.51.6.1.1.4
-- 1.3.6.1.4.1.6296.101.23.51.6.1.1.4
		sleGponProfile2BridgeUniVlanOpUsOperFlag OBJECT-TYPE
			SYNTAX INTEGER
				{
				unused(0),
				keep(1),
				overwrite(2),
				add(3)
				}
			MAX-ACCESS read-only
			STATUS current
			DESCRIPTION
				"The VLAN Tagging Operation Data & US VLAN Tagging Operation mode"
			::= { sleGponProfile2BridgeUniEntry 4 }


--   1.3.6.1.4.1.6296.101.23.51.6.1.1.5
-- 1.3.6.1.4.1.6296.101.23.51.6.1.1.5
		sleGponProfile2BridgeUniVlanOpUsOperVid OBJECT-TYPE
			SYNTAX Integer32
			MAX-ACCESS read-only
			STATUS current
			DESCRIPTION
				"The US Oper Vid."
			::= { sleGponProfile2BridgeUniEntry 5 }


--   1.3.6.1.4.1.6296.101.23.51.6.1.1.6
-- 1.3.6.1.4.1.6296.101.23.51.6.1.1.6
		sleGponProfile2BridgeUniVlanOpUsOperCos OBJECT-TYPE
			SYNTAX Integer32
			MAX-ACCESS read-only
			STATUS current
			DESCRIPTION
				"The US Oper tag CoS value"
			::= { sleGponProfile2BridgeUniEntry 6 }


--   1.3.6.1.4.1.6296.101.23.51.6.1.1.7
-- 1.3.6.1.4.1.6296.101.23.51.6.1.1.7
		sleGponProfile2BridgeUniPortAdmin OBJECT-TYPE
			SYNTAX EnableFlag
			MAX-ACCESS read-only
			STATUS current
			DESCRIPTION
				"The port admin status"
			::= { sleGponProfile2BridgeUniEntry 7 }


--   1.3.6.1.4.1.6296.101.23.51.6.1.1.8
-- 1.3.6.1.4.1.6296.101.23.51.6.1.1.8
		sleGponProfile2BridgeUniRateLimitDownSir OBJECT-TYPE
			SYNTAX Integer32
			MAX-ACCESS read-only
			STATUS current
			DESCRIPTION
				"The download rate-limit control : SIR (Bandwidth in steps of 64Kbps)"
			::= { sleGponProfile2BridgeUniEntry 8 }


--   1.3.6.1.4.1.6296.101.23.51.6.1.1.9
-- 1.3.6.1.4.1.6296.101.23.51.6.1.1.9
		sleGponProfile2BridgeUniRateLimitDownPir OBJECT-TYPE
			SYNTAX Integer32
			MAX-ACCESS read-only
			STATUS current
			DESCRIPTION
				"The download rate-limit control : PIR (Bandwidth in steps of 64Kbps)"
			::= { sleGponProfile2BridgeUniEntry 9 }


--   1.3.6.1.4.1.6296.101.23.51.6.1.1.10
-- 1.3.6.1.4.1.6296.101.23.51.6.1.1.10
		sleGponProfile2BridgeUniRateLimitUpSir OBJECT-TYPE
			SYNTAX Integer32
			MAX-ACCESS read-only
			STATUS current
			DESCRIPTION
				"The upload rate-limit control : SIR (Bandwidth in steps of 64Kbps)"
			::= { sleGponProfile2BridgeUniEntry 10 }


--   1.3.6.1.4.1.6296.101.23.51.6.1.1.11
-- 1.3.6.1.4.1.6296.101.23.51.6.1.1.11
		sleGponProfile2BridgeUniRateLimitUpPir OBJECT-TYPE
			SYNTAX Integer32
			MAX-ACCESS read-only
			STATUS current
			DESCRIPTION
				"The upload rate-limit control : SIR (Bandwidth in steps of 64Kbps)"
			::= { sleGponProfile2BridgeUniEntry 11 }


--   1.3.6.1.4.1.6296.101.23.51.6.1.1.12
-- 1.3.6.1.4.1.6296.101.23.51.6.1.1.12
		sleGponProfile2BridgeUniIgmpMaxGroup OBJECT-TYPE
			SYNTAX Integer32
			MAX-ACCESS read-only
			STATUS current
			DESCRIPTION
				"The IGMP max group"
			::= { sleGponProfile2BridgeUniEntry 12 }


--   1.3.6.1.4.1.6296.101.23.51.6.1.1.13
-- 1.3.6.1.4.1.6296.101.23.51.6.1.1.13
		sleGponProfile2BridgeUniMaxFrame OBJECT-TYPE
			SYNTAX Integer32
			MAX-ACCESS read-only
			STATUS current
			DESCRIPTION
				"The max-frame"
			::= { sleGponProfile2BridgeUniEntry 13 }


--   1.3.6.1.4.1.6296.101.23.51.6.1.1.14
-- 1.3.6.1.4.1.6296.101.23.51.6.1.1.14
		sleGponProfile2BridgeUniMcastProfile OBJECT-TYPE
			SYNTAX OCTET STRING
			MAX-ACCESS read-only
			STATUS current
			DESCRIPTION
				"The multicast profile name"
			::= { sleGponProfile2BridgeUniEntry 14 }


--   1.3.6.1.4.1.6296.101.23.51.6.1.1.15
-- 1.3.6.1.4.1.6296.101.23.51.6.1.1.15
		sleGponProfile2BridgeUniVlanFilterMode OBJECT-TYPE
			SYNTAX INTEGER
				{
				allow(1),
				deny(2)
				}
			MAX-ACCESS read-only
			STATUS current
			DESCRIPTION
				"Allow or deny that untagged fowarding operation "
			::= { sleGponProfile2BridgeUniEntry 15 }


--   1.3.6.1.4.1.6296.101.23.51.6.1.1.16
-- 1.3.6.1.4.1.6296.101.23.51.6.1.1.16
		sleGponProfile2BridgeUniVlanFilter OBJECT-TYPE
			SYNTAX OCTET STRING
			MAX-ACCESS read-only
			STATUS current
			DESCRIPTION
				"The vlan-filter VID list."
			::= { sleGponProfile2BridgeUniEntry 16 }


--   1.3.6.1.4.1.6296.101.23.51.6.1.1.17
-- 1.3.6.1.4.1.6296.101.23.51.6.1.1.17
		sleGponProfile2BridgeUniIpMode OBJECT-TYPE
			SYNTAX INTEGER
				{
				static(1),
				dhcp(2),
				none(3)
				}
			MAX-ACCESS read-only
			STATUS current
			DESCRIPTION
				"The UNI IP mode."
			::= { sleGponProfile2BridgeUniEntry 17 }


--   1.3.6.1.4.1.6296.101.23.51.6.1.1.18
-- 1.3.6.1.4.1.6296.101.23.51.6.1.1.18
		sleGponProfile2BridgeUniDns1 OBJECT-TYPE
			SYNTAX IpAddress
			MAX-ACCESS read-only
			STATUS current
			DESCRIPTION
				"The DNS address 1."
			::= { sleGponProfile2BridgeUniEntry 18 }


--   1.3.6.1.4.1.6296.101.23.51.6.1.1.19
-- 1.3.6.1.4.1.6296.101.23.51.6.1.1.19
		sleGponProfile2BridgeUniDns2 OBJECT-TYPE
			SYNTAX IpAddress
			MAX-ACCESS read-only
			STATUS current
			DESCRIPTION
				"The DNS address 2."
			::= { sleGponProfile2BridgeUniEntry 19 }


--   1.3.6.1.4.1.6296.101.23.51.6.1.1.20
-- 1.3.6.1.4.1.6296.101.23.51.6.1.1.20
		sleGponProfile2BridgeUniVoIPProfile OBJECT-TYPE
			SYNTAX OCTET STRING
			MAX-ACCESS read-only
			STATUS current
			DESCRIPTION
				"The VoIP profile name."
			::= { sleGponProfile2BridgeUniEntry 20 }


--  1.3.6.1.4.1.6296.101.23.51.6.1.1.21
		sleGponProfile2BridgeUniMaxHost OBJECT-TYPE
			SYNTAX INTEGER (1..65535)
			MAX-ACCESS read-only
			STATUS current
			DESCRIPTION
				"The UNI max host."
			::= { sleGponProfile2BridgeUniEntry 21 }


--  1.3.6.1.4.1.6296.101.23.51.6.1.1.22
		sleGponProfile2BridgeUniExtVlanName OBJECT-TYPE
			SYNTAX OCTET STRING
			MAX-ACCESS read-only
			STATUS current
			DESCRIPTION
				"The Extended vlan name."
			::= { sleGponProfile2BridgeUniEntry 22 }


--  1.3.6.1.4.1.6296.101.23.51.6.1.1.23
		sleGponProfile2BridgeUniMcastRateLimit OBJECT-TYPE
			SYNTAX Integer32 (0..1031616)
			MAX-ACCESS read-only
			STATUS current
			DESCRIPTION
				"The multicast rate-limit bandwidth (Bandwidth in steps of 8Kbps), 0 is disable"
			::= { sleGponProfile2BridgeUniEntry 23 }


--  1.3.6.1.4.1.6296.101.23.51.6.1.1.24
		sleGponProfile2BridgeUniMacFilterPreassign OBJECT-TYPE
			SYNTAX BITS
				{
				ipv4Multicast(0),
				ipv6Multicast(1),
				ipv4Broadcast(2),
				rarp(3),
				ipx(4),
				netBEUI(5),
				appleTalk(6),
				bridgeManagementInformation(7),
				arp(8),
				pppoeBroadcast(9)
				}
			MAX-ACCESS read-only
			STATUS current
			DESCRIPTION
				"MAC Filter Preassign Table
				0 -> forward
				1 -> filter"
			::= { sleGponProfile2BridgeUniEntry 24 }


--  1.3.6.1.4.1.6296.101.23.51.6.1.1.25
		sleGponProfile2BridgeUniRateLimitProfile OBJECT-TYPE
			SYNTAX OCTET STRING
			MAX-ACCESS read-only
			STATUS current
			DESCRIPTION
				"The rate-limit profile name."
			::= { sleGponProfile2BridgeUniEntry 25 }


		sleGponProfile2BridgeUniIneterDomainName OBJECT-TYPE
			SYNTAX OCTET STRING
			MAX-ACCESS read-only
			STATUS current
			DESCRIPTION
				"The virtual ethernet interface domain name"
			::= { sleGponProfile2BridgeUniEntry 26 }


--   1.3.6.1.4.1.6296.101.23.51.6.2
-- 1.3.6.1.4.1.6296.101.23.51.6.2
		sleGponProfile2BridgeUniControl OBJECT IDENTIFIER ::= { sleGponProfile2BridgeUni 2 }


--   1.3.6.1.4.1.6296.101.23.51.6.2.1
-- 1.3.6.1.4.1.6296.101.23.51.6.2.1
		sleGponProfile2BridgeUniControlRequest OBJECT-TYPE
			SYNTAX INTEGER
				{
				addBridgeUni(1),
				delBridgeUni(2),
				setVlanUsOper(3),
				setVlanDsOper(4),
				setPortAdmin(5),
				setRateLimit(6),
				setIgmpMaxGroup(7),
				setMaxFrame(8),
				setMcastProfile(9),
				setVlanFilter(10),
				setIpInfo(11),
				setVoipProfile(12),
				setMaxHost(13),
				setExtendedVlan(14),
				setMcastRateLimit(15),
				setUniMacFilterPreassign(16),
				setUniRateLimitProfile(17),
				setUniInterDomainName(18)
				}
			MAX-ACCESS read-write
			STATUS current
			DESCRIPTION
				"The request of a user command"
			::= { sleGponProfile2BridgeUniControl 1 }


--   1.3.6.1.4.1.6296.101.23.51.6.2.2
-- 1.3.6.1.4.1.6296.101.23.51.6.2.2
		sleGponProfile2BridgeUniControlStatus OBJECT-TYPE
			SYNTAX SleControlStatusType
			MAX-ACCESS read-write
			STATUS current
			DESCRIPTION
				"The status of user command"
			::= { sleGponProfile2BridgeUniControl 2 }


--   1.3.6.1.4.1.6296.101.23.51.6.2.3
-- 1.3.6.1.4.1.6296.101.23.51.6.2.3
		sleGponProfile2BridgeUniControlTimer OBJECT-TYPE
			SYNTAX Gauge32
			MAX-ACCESS read-write
			STATUS current
			DESCRIPTION
				"The maximum time for the manager for a long running user command"
			::= { sleGponProfile2BridgeUniControl 3 }


--   1.3.6.1.4.1.6296.101.23.51.6.2.4
-- 1.3.6.1.4.1.6296.101.23.51.6.2.4
		sleGponProfile2BridgeUniControlTimeStamp OBJECT-TYPE
			SYNTAX TimeTicks
			MAX-ACCESS read-write
			STATUS current
			DESCRIPTION
				"The time stamp of the last command(end of command)"
			::= { sleGponProfile2BridgeUniControl 4 }


--   1.3.6.1.4.1.6296.101.23.51.6.2.5
-- 1.3.6.1.4.1.6296.101.23.51.6.2.5
		sleGponProfile2BridgeUniControlReqResult OBJECT-TYPE
			SYNTAX SleControlRequestResultType
			MAX-ACCESS read-write
			STATUS current
			DESCRIPTION
				"The result of the last user command"
			::= { sleGponProfile2BridgeUniControl 5 }


--   1.3.6.1.4.1.6296.101.23.51.6.2.6
-- 1.3.6.1.4.1.6296.101.23.51.6.2.6
		sleGponProfile2BridgeUniControlTName OBJECT-TYPE
			SYNTAX OCTET STRING
			MAX-ACCESS read-write
			STATUS current
			DESCRIPTION
				"The Traffic profile name."
			::= { sleGponProfile2BridgeUniControl 6 }


--   1.3.6.1.4.1.6296.101.23.51.6.2.7
-- 1.3.6.1.4.1.6296.101.23.51.6.2.7
		sleGponProfile2BridgeUniControlBridgeId OBJECT-TYPE
			SYNTAX Integer32
			MAX-ACCESS read-write
			STATUS current
			DESCRIPTION
				"The bridge ID."
			::= { sleGponProfile2BridgeUniControl 7 }


--   1.3.6.1.4.1.6296.101.23.51.6.2.8
-- 1.3.6.1.4.1.6296.101.23.51.6.2.8
		sleGponProfile2BridgeUniControlType OBJECT-TYPE
			SYNTAX INTEGER
				{
				eth(1),
				voip(2),
				virtualEth(3)
				}
			MAX-ACCESS read-write
			STATUS current
			DESCRIPTION
				"The Bridge Uni Type."
			::= { sleGponProfile2BridgeUniControl 8 }


--   1.3.6.1.4.1.6296.101.23.51.6.2.9
-- 1.3.6.1.4.1.6296.101.23.51.6.2.9
		sleGponProfile2BridgeUniControlId OBJECT-TYPE
			SYNTAX Integer32
			MAX-ACCESS read-write
			STATUS current
			DESCRIPTION
				"The bridge Uni ID."
			::= { sleGponProfile2BridgeUniControl 9 }


--   1.3.6.1.4.1.6296.101.23.51.6.2.10
-- 1.3.6.1.4.1.6296.101.23.51.6.2.10
		sleGponProfile2BridgeUniControlVlanOpDsOperFlag OBJECT-TYPE
			SYNTAX INTEGER
				{
				unused(0),
				keep(1),
				remove(2)
				}
			MAX-ACCESS read-write
			STATUS current
			DESCRIPTION
				"The VLAN Tagging Operation Data & DS VLAN Tagging Operation mode"
			::= { sleGponProfile2BridgeUniControl 10 }


--   1.3.6.1.4.1.6296.101.23.51.6.2.11
-- 1.3.6.1.4.1.6296.101.23.51.6.2.11
		sleGponProfile2BridgeUniControlVlanOpUsOperFlag OBJECT-TYPE
			SYNTAX INTEGER
				{
				unused(0),
				keep(1),
				overwrite(2),
				add(3)
				}
			MAX-ACCESS read-write
			STATUS current
			DESCRIPTION
				"The VLAN Tagging Operation Data & US VLAN Tagging Operation mode"
			::= { sleGponProfile2BridgeUniControl 11 }


--   1.3.6.1.4.1.6296.101.23.51.6.2.12
-- 1.3.6.1.4.1.6296.101.23.51.6.2.12
		sleGponProfile2BridgeUniControlVlanOpUsOperVid OBJECT-TYPE
			SYNTAX Integer32
			MAX-ACCESS read-write
			STATUS current
			DESCRIPTION
				"The US Oper Vid."
			::= { sleGponProfile2BridgeUniControl 12 }


--   1.3.6.1.4.1.6296.101.23.51.6.2.13
-- 1.3.6.1.4.1.6296.101.23.51.6.2.13
		sleGponProfile2BridgeUniControlVlanOpUsOperCos OBJECT-TYPE
			SYNTAX Integer32
			MAX-ACCESS read-write
			STATUS current
			DESCRIPTION
				"The US Oper tag CoS value"
			::= { sleGponProfile2BridgeUniControl 13 }


--   1.3.6.1.4.1.6296.101.23.51.6.2.14
-- 1.3.6.1.4.1.6296.101.23.51.6.2.14
		sleGponProfile2BridgeUniControlPortAdmin OBJECT-TYPE
			SYNTAX EnableFlag
			MAX-ACCESS read-write
			STATUS current
			DESCRIPTION
				"The port admin status"
			::= { sleGponProfile2BridgeUniControl 14 }


--   1.3.6.1.4.1.6296.101.23.51.6.2.15
-- 1.3.6.1.4.1.6296.101.23.51.6.2.15
		sleGponProfile2BridgeUniControlRateLimitDownSir OBJECT-TYPE
			SYNTAX Integer32
			MAX-ACCESS read-write
			STATUS current
			DESCRIPTION
				"The download rate-limit control : SIR (Bandwidth in steps of 64Kbps)"
			::= { sleGponProfile2BridgeUniControl 15 }


--   1.3.6.1.4.1.6296.101.23.51.6.2.16
-- 1.3.6.1.4.1.6296.101.23.51.6.2.16
		sleGponProfile2BridgeUniControlRateLimitDownPir OBJECT-TYPE
			SYNTAX Integer32
			MAX-ACCESS read-write
			STATUS current
			DESCRIPTION
				"The download rate-limit control : PIR (Bandwidth in steps of 64Kbps)"
			::= { sleGponProfile2BridgeUniControl 16 }


--   1.3.6.1.4.1.6296.101.23.51.6.2.17
-- 1.3.6.1.4.1.6296.101.23.51.6.2.17
		sleGponProfile2BridgeUniControlRateLimitUpSir OBJECT-TYPE
			SYNTAX Integer32
			MAX-ACCESS read-write
			STATUS current
			DESCRIPTION
				"The upload rate-limit control : SIR (Bandwidth in steps of 64Kbps)"
			::= { sleGponProfile2BridgeUniControl 17 }


--   1.3.6.1.4.1.6296.101.23.51.6.2.18
-- 1.3.6.1.4.1.6296.101.23.51.6.2.18
		sleGponProfile2BridgeUniControlRateLimitUpPir OBJECT-TYPE
			SYNTAX Integer32
			MAX-ACCESS read-write
			STATUS current
			DESCRIPTION
				"The upload rate-limit control : SIR (Bandwidth in steps of 64Kbps)"
			::= { sleGponProfile2BridgeUniControl 18 }


--   1.3.6.1.4.1.6296.101.23.51.6.2.19
-- 1.3.6.1.4.1.6296.101.23.51.6.2.19
		sleGponProfile2BridgeUniControlIgmpMaxGroup OBJECT-TYPE
			SYNTAX Integer32
			MAX-ACCESS read-write
			STATUS current
			DESCRIPTION
				"The IGMP max group"
			::= { sleGponProfile2BridgeUniControl 19 }


--   1.3.6.1.4.1.6296.101.23.51.6.2.20
-- 1.3.6.1.4.1.6296.101.23.51.6.2.20
		sleGponProfile2BridgeUniControlMaxFrame OBJECT-TYPE
			SYNTAX Integer32
			MAX-ACCESS read-write
			STATUS current
			DESCRIPTION
				"The max-frame"
			::= { sleGponProfile2BridgeUniControl 20 }


--   1.3.6.1.4.1.6296.101.23.51.6.2.21
-- 1.3.6.1.4.1.6296.101.23.51.6.2.21
		sleGponProfile2BridgeUniControlMcastProfile OBJECT-TYPE
			SYNTAX OCTET STRING
			MAX-ACCESS read-write
			STATUS current
			DESCRIPTION
				"The multicast profile name"
			::= { sleGponProfile2BridgeUniControl 21 }


--   1.3.6.1.4.1.6296.101.23.51.6.2.22
-- 1.3.6.1.4.1.6296.101.23.51.6.2.22
		sleGponProfile2BridgeUniControlVlanFilterMode OBJECT-TYPE
			SYNTAX INTEGER
				{
				allow(1),
				deny(2)
				}
			MAX-ACCESS read-write
			STATUS current
			DESCRIPTION
				"Allow or deny that untagged fowarding operation "
			::= { sleGponProfile2BridgeUniControl 22 }


--   1.3.6.1.4.1.6296.101.23.51.6.2.23
-- 1.3.6.1.4.1.6296.101.23.51.6.2.23
		sleGponProfile2BridgeUniControlVlanFilter OBJECT-TYPE
			SYNTAX OCTET STRING
			MAX-ACCESS read-write
			STATUS current
			DESCRIPTION
				"The vlan-filter VID list."
			::= { sleGponProfile2BridgeUniControl 23 }


--   1.3.6.1.4.1.6296.101.23.51.6.2.24
-- 1.3.6.1.4.1.6296.101.23.51.6.2.24
		sleGponProfile2BridgeUniControlIpMode OBJECT-TYPE
			SYNTAX INTEGER
				{
				static(1),
				dhcp(2),
				none(3)
				}
			MAX-ACCESS read-write
			STATUS current
			DESCRIPTION
				"The IP mode."
			::= { sleGponProfile2BridgeUniControl 24 }


--   1.3.6.1.4.1.6296.101.23.51.6.2.25
-- 1.3.6.1.4.1.6296.101.23.51.6.2.25
		sleGponProfile2BridgeUniControlDns1 OBJECT-TYPE
			SYNTAX IpAddress
			MAX-ACCESS read-write
			STATUS current
			DESCRIPTION
				"The DNS address 1."
			::= { sleGponProfile2BridgeUniControl 25 }


--   1.3.6.1.4.1.6296.101.23.51.6.2.26
-- 1.3.6.1.4.1.6296.101.23.51.6.2.26
		sleGponProfile2BridgeUniControlDns2 OBJECT-TYPE
			SYNTAX IpAddress
			MAX-ACCESS read-write
			STATUS current
			DESCRIPTION
				"The DNS address 2."
			::= { sleGponProfile2BridgeUniControl 26 }


--   1.3.6.1.4.1.6296.101.23.51.6.2.27
-- 1.3.6.1.4.1.6296.101.23.51.6.2.27
		sleGponProfile2BridgeUniControlVoIPProfile OBJECT-TYPE
			SYNTAX OCTET STRING
			MAX-ACCESS read-write
			STATUS current
			DESCRIPTION
				"The VoIP profile name."
			::= { sleGponProfile2BridgeUniControl 27 }


--  1.3.6.1.4.1.6296.101.23.51.6.2.28
		sleGponProfile2BridgeUniControlMaxHost OBJECT-TYPE
			SYNTAX INTEGER (1..65535)
			MAX-ACCESS read-write
			STATUS current
			DESCRIPTION
				"The UNI max host."
			::= { sleGponProfile2BridgeUniControl 28 }


--  1.3.6.1.4.1.6296.101.23.51.6.2.29
		sleGponProfile2BridgeUniControlExtVlanName OBJECT-TYPE
			SYNTAX OCTET STRING
			MAX-ACCESS read-write
			STATUS current
			DESCRIPTION
				"The Extended vlan name."
			::= { sleGponProfile2BridgeUniControl 29 }


--  1.3.6.1.4.1.6296.101.23.51.6.2.30
		sleGponProfile2BridgeUniControlMcastRateLimit OBJECT-TYPE
			SYNTAX Integer32 (0..1031616)
			MAX-ACCESS read-write
			STATUS current
			DESCRIPTION
				"The multicast rate-limit bandwidth (Bandwidth in steps of 8Kbps), 0 is disable"
			::= { sleGponProfile2BridgeUniControl 30 }


--  1.3.6.1.4.1.6296.101.23.51.6.2.31
		sleGponProfile2BridgeUniControlMacFilterPreassign OBJECT-TYPE
			SYNTAX BITS
				{
				ipv4Multicast(0),
				ipv6Multicast(1),
				ipv4Broadcast(2),
				rarp(3),
				ipx(4),
				netBEUI(5),
				appleTalk(6),
				bridgeManagementInformation(7),
				arp(8),
				pppoeBroadcast(9)
				}
			MAX-ACCESS read-write
			STATUS current
			DESCRIPTION
				"MAC Filter Preassign Table
				0 -> forward
				1 -> filter"
			::= { sleGponProfile2BridgeUniControl 31 }


--  1.3.6.1.4.1.6296.101.23.51.6.2.32
		sleGponProfile2BridgeUniControlRateLimitProfile OBJECT-TYPE
			SYNTAX OCTET STRING
			MAX-ACCESS read-write
			STATUS current
			DESCRIPTION
				"The rate-limit profile name."
			::= { sleGponProfile2BridgeUniControl 32 }


		sleGponProfile2BridgeUniControlInterDomainName OBJECT-TYPE
			SYNTAX OCTET STRING
			MAX-ACCESS read-write
			STATUS current
			DESCRIPTION
				"The virtual ethernet interface domain name"
			::= { sleGponProfile2BridgeUniControl 33 }


--   1.3.6.1.4.1.6296.101.23.51.6.3
-- 1.3.6.1.4.1.6296.101.23.51.6.3
		sleGponProfile2BridgeUniNotification OBJECT IDENTIFIER ::= { sleGponProfile2BridgeUni 3 }


--   1.3.6.1.4.1.6296.101.23.51.6.3.1
-- 1.3.6.1.4.1.6296.101.23.51.6.3.1
		sleGponProfile2BridgeUniAdded NOTIFICATION-TYPE
			OBJECTS { sleGponProfile2BridgeUniControlRequest, sleGponProfile2BridgeUniControlStatus, sleGponProfile2BridgeUniControlTimer, sleGponProfile2BridgeUniControlTimeStamp, sleGponProfile2BridgeUniControlReqResult,
				sleGponProfile2BridgeUniControlTName, sleGponProfile2BridgeUniControlBridgeId, sleGponProfile2BridgeUniControlType, sleGponProfile2BridgeUniControlId }
			STATUS current
			DESCRIPTION
				"Description."
			::= { sleGponProfile2BridgeUniNotification 1 }


--   1.3.6.1.4.1.6296.101.23.51.6.3.2
-- 1.3.6.1.4.1.6296.101.23.51.6.3.2
		sleGponProfile2BridgeUniDeleted NOTIFICATION-TYPE
			OBJECTS { sleGponProfile2BridgeUniControlRequest, sleGponProfile2BridgeUniControlStatus, sleGponProfile2BridgeUniControlTimer, sleGponProfile2BridgeUniControlTimeStamp, sleGponProfile2BridgeUniControlReqResult,
				sleGponProfile2BridgeUniControlTName, sleGponProfile2BridgeUniControlBridgeId, sleGponProfile2BridgeUniControlType, sleGponProfile2BridgeUniControlId }
			STATUS current
			DESCRIPTION
				"Description."
			::= { sleGponProfile2BridgeUniNotification 2 }


--   1.3.6.1.4.1.6296.101.23.51.6.3.3
-- 1.3.6.1.4.1.6296.101.23.51.6.3.3
		sleGponProfile2BridgeUniVlanDsOpChanged NOTIFICATION-TYPE
			OBJECTS { sleGponProfile2BridgeUniControlRequest, sleGponProfile2BridgeUniControlStatus, sleGponProfile2BridgeUniControlTimer, sleGponProfile2BridgeUniControlTimeStamp, sleGponProfile2BridgeUniControlReqResult,
				sleGponProfile2BridgeUniControlTName, sleGponProfile2BridgeUniControlBridgeId, sleGponProfile2BridgeUniControlType, sleGponProfile2BridgeUniControlId, sleGponProfile2BridgeUniControlVlanOpDsOperFlag
				 }
			STATUS current
			DESCRIPTION
				"Description."
			::= { sleGponProfile2BridgeUniNotification 3 }


--   1.3.6.1.4.1.6296.101.23.51.6.3.4
-- 1.3.6.1.4.1.6296.101.23.51.6.3.4
		sleGponProfile2BridgeUniVlanUsOpChanged NOTIFICATION-TYPE
			OBJECTS { sleGponProfile2BridgeUniControlRequest, sleGponProfile2BridgeUniControlStatus, sleGponProfile2BridgeUniControlTimer, sleGponProfile2BridgeUniControlTimeStamp, sleGponProfile2BridgeUniControlReqResult,
				sleGponProfile2BridgeUniControlTName, sleGponProfile2BridgeUniControlBridgeId, sleGponProfile2BridgeUniControlType, sleGponProfile2BridgeUniControlId, sleGponProfile2BridgeUniControlVlanOpUsOperFlag,
				sleGponProfile2BridgeUniControlVlanOpUsOperVid, sleGponProfile2BridgeUniControlVlanOpUsOperCos }
			STATUS current
			DESCRIPTION
				"Description."
			::= { sleGponProfile2BridgeUniNotification 4 }


--   1.3.6.1.4.1.6296.101.23.51.6.3.5
-- 1.3.6.1.4.1.6296.101.23.51.6.3.5
		sleGponProfile2BridgeUniPortAdminChanged NOTIFICATION-TYPE
			OBJECTS { sleGponProfile2BridgeUniControlRequest, sleGponProfile2BridgeUniControlStatus, sleGponProfile2BridgeUniControlTimer, sleGponProfile2BridgeUniControlTimeStamp, sleGponProfile2BridgeUniControlReqResult,
				sleGponProfile2BridgeUniControlTName, sleGponProfile2BridgeUniControlBridgeId, sleGponProfile2BridgeUniControlType, sleGponProfile2BridgeUniControlId, sleGponProfile2BridgeUniControlPortAdmin
				 }
			STATUS current
			DESCRIPTION
				"Description."
			::= { sleGponProfile2BridgeUniNotification 5 }


--   1.3.6.1.4.1.6296.101.23.51.6.3.6
-- 1.3.6.1.4.1.6296.101.23.51.6.3.6
		sleGponProfile2BridgeUniRateLimitChanged NOTIFICATION-TYPE
			OBJECTS { sleGponProfile2BridgeUniControlRequest, sleGponProfile2BridgeUniControlStatus, sleGponProfile2BridgeUniControlTimer, sleGponProfile2BridgeUniControlTimeStamp, sleGponProfile2BridgeUniControlReqResult,
				sleGponProfile2BridgeUniControlTName, sleGponProfile2BridgeUniControlBridgeId, sleGponProfile2BridgeUniControlType, sleGponProfile2BridgeUniControlId, sleGponProfile2BridgeUniControlRateLimitDownSir,
				sleGponProfile2BridgeUniControlRateLimitDownPir, sleGponProfile2BridgeUniControlRateLimitUpSir, sleGponProfile2BridgeUniControlRateLimitUpPir }
			STATUS current
			DESCRIPTION
				"Description."
			::= { sleGponProfile2BridgeUniNotification 6 }


--   1.3.6.1.4.1.6296.101.23.51.6.3.7
-- 1.3.6.1.4.1.6296.101.23.51.6.3.7
		sleGponProfile2BridgeUniIgmpMaxGroupChanged NOTIFICATION-TYPE
			OBJECTS { sleGponProfile2BridgeUniControlRequest, sleGponProfile2BridgeUniControlStatus, sleGponProfile2BridgeUniControlTimer, sleGponProfile2BridgeUniControlTimeStamp, sleGponProfile2BridgeUniControlReqResult,
				sleGponProfile2BridgeUniControlTName, sleGponProfile2BridgeUniControlBridgeId, sleGponProfile2BridgeUniControlType, sleGponProfile2BridgeUniControlId, sleGponProfile2BridgeUniControlIgmpMaxGroup
				 }
			STATUS current
			DESCRIPTION
				"Description."
			::= { sleGponProfile2BridgeUniNotification 7 }


--   1.3.6.1.4.1.6296.101.23.51.6.3.8
-- 1.3.6.1.4.1.6296.101.23.51.6.3.8
		sleGponProfile2BridgeUniMaxFrameChanged NOTIFICATION-TYPE
			OBJECTS { sleGponProfile2BridgeUniControlRequest, sleGponProfile2BridgeUniControlStatus, sleGponProfile2BridgeUniControlTimer, sleGponProfile2BridgeUniControlTimeStamp, sleGponProfile2BridgeUniControlReqResult,
				sleGponProfile2BridgeUniControlTName, sleGponProfile2BridgeUniControlBridgeId, sleGponProfile2BridgeUniControlType, sleGponProfile2BridgeUniControlId, sleGponProfile2BridgeUniControlMaxFrame
				 }
			STATUS current
			DESCRIPTION
				"Description."
			::= { sleGponProfile2BridgeUniNotification 8 }


--   1.3.6.1.4.1.6296.101.23.51.6.3.9
-- 1.3.6.1.4.1.6296.101.23.51.6.3.9
		sleGponProfile2BridgeUniMcastProfileChanged NOTIFICATION-TYPE
			OBJECTS { sleGponProfile2BridgeUniControlRequest, sleGponProfile2BridgeUniControlStatus, sleGponProfile2BridgeUniControlTimer, sleGponProfile2BridgeUniControlTimeStamp, sleGponProfile2BridgeUniControlReqResult,
				sleGponProfile2BridgeUniControlTName, sleGponProfile2BridgeUniControlBridgeId, sleGponProfile2BridgeUniControlType, sleGponProfile2BridgeUniControlId, sleGponProfile2BridgeUniControlMcastProfile
				 }
			STATUS current
			DESCRIPTION
				"Description."
			::= { sleGponProfile2BridgeUniNotification 9 }


--   1.3.6.1.4.1.6296.101.23.51.6.3.10
-- 1.3.6.1.4.1.6296.101.23.51.6.3.10
		sleGponProfile2BridgeUniVlanFilterChanged NOTIFICATION-TYPE
			OBJECTS { sleGponProfile2BridgeUniControlRequest, sleGponProfile2BridgeUniControlStatus, sleGponProfile2BridgeUniControlTimer, sleGponProfile2BridgeUniControlTimeStamp, sleGponProfile2BridgeUniControlReqResult,
				sleGponProfile2BridgeUniControlTName, sleGponProfile2BridgeUniControlBridgeId, sleGponProfile2BridgeUniControlType, sleGponProfile2BridgeUniControlId, sleGponProfile2BridgeUniControlVlanFilterMode,
				sleGponProfile2BridgeUniControlVlanFilter }
			STATUS current
			DESCRIPTION
				"Description."
			::= { sleGponProfile2BridgeUniNotification 10 }


--   1.3.6.1.4.1.6296.101.23.51.6.3.11
-- 1.3.6.1.4.1.6296.101.23.51.6.3.11
		sleGponProfile2BridgeUniIpInfoChanged NOTIFICATION-TYPE
			OBJECTS { sleGponProfile2BridgeUniControlRequest, sleGponProfile2BridgeUniControlTimeStamp, sleGponProfile2BridgeUniControlReqResult, sleGponProfile2BridgeUniControlTName, sleGponProfile2BridgeUniControlBridgeId,
				sleGponProfile2BridgeUniControlType, sleGponProfile2BridgeUniControlId, sleGponProfile2BridgeUniControlIpMode, sleGponProfile2BridgeUniControlDns1, sleGponProfile2BridgeUniControlDns2
				 }
			STATUS current
			DESCRIPTION
				"Description."
			::= { sleGponProfile2BridgeUniNotification 11 }


--   1.3.6.1.4.1.6296.101.23.51.6.3.12
-- 1.3.6.1.4.1.6296.101.23.51.6.3.12
		sleGponProfile2BridgeUniVoipProfileChanged NOTIFICATION-TYPE
			OBJECTS { sleGponProfile2BridgeAniControlRequest, sleGponProfile2BridgeAniControlTimeStamp, sleGponProfile2BridgeAniControlReqResult, sleGponProfile2BridgeAniControlTName, sleGponProfile2BridgeAniControlBridgeId,
				sleGponProfile2BridgeAniControlId, sleGponProfile2BridgeUniControlVoIPProfile }
			STATUS current
			DESCRIPTION
				"Description."
			::= { sleGponProfile2BridgeUniNotification 12 }


--   1.3.6.1.4.1.6296.101.23.51.6.3.12
-- 1.3.6.1.4.1.6296.101.23.51.6.3.13
		sleGponProfile2BridgeUniMaxHostChanged NOTIFICATION-TYPE
			OBJECTS { sleGponProfile2BridgeAniControlRequest, sleGponProfile2BridgeAniControlTimeStamp, sleGponProfile2BridgeAniControlReqResult, sleGponProfile2BridgeAniControlTName, sleGponProfile2BridgeAniControlBridgeId,
				sleGponProfile2BridgeAniControlId, sleGponProfile2BridgeUniControlMaxHost }
			STATUS current
			DESCRIPTION
				"Description."
			::= { sleGponProfile2BridgeUniNotification 13 }


--  1.3.6.1.4.1.6296.101.23.51.6.3.14
		sleGponProfile2BridgeUniExtendedVlanChanged NOTIFICATION-TYPE
			OBJECTS { sleGponProfile2BridgeUniControlRequest, sleGponProfile2BridgeUniControlTimeStamp, sleGponProfile2BridgeUniControlReqResult, sleGponProfile2BridgeUniControlBridgeId, sleGponProfile2BridgeUniControlType,
				sleGponProfile2BridgeUniControlId, sleGponProfile2BridgeUniControlExtVlanName }
			STATUS current
			DESCRIPTION
				"setExtendedVlan"
			::= { sleGponProfile2BridgeUniNotification 14 }


--  1.3.6.1.4.1.6296.101.23.51.6.3.15
		sleGponProfile2BridgeUniMcastRateLimitChanged NOTIFICATION-TYPE
			OBJECTS { sleGponProfile2BridgeUniControlRequest, sleGponProfile2BridgeUniControlTimeStamp, sleGponProfile2BridgeUniControlReqResult, sleGponProfile2BridgeUniControlBridgeId, sleGponProfile2BridgeUniControlType,
				sleGponProfile2BridgeUniControlId, sleGponProfile2BridgeUniControlMcastRateLimit }
			STATUS current
			DESCRIPTION
				"setExtendedVlan"
			::= { sleGponProfile2BridgeUniNotification 15 }


--   1.3.6.1.4.1.6296.101.23.51.6.3.5
-- 1.3.6.1.4.1.6296.101.23.51.6.3.16
		sleGponProfile2BridgeUniMacFilterPreassignChanged NOTIFICATION-TYPE
			OBJECTS { sleGponProfile2BridgeUniControlRequest, sleGponProfile2BridgeUniControlTimeStamp, sleGponProfile2BridgeUniControlReqResult, sleGponProfile2BridgeUniControlTName, sleGponProfile2BridgeUniControlBridgeId,
				sleGponProfile2BridgeUniControlType, sleGponProfile2BridgeUniControlId, sleGponProfile2BridgeUniControlMacFilterPreassign }
			STATUS current
			DESCRIPTION
				"setUniMacFilterPreassign"
			::= { sleGponProfile2BridgeUniNotification 16 }


--   1.3.6.1.4.1.6296.101.23.51.6.3.5
-- 1.3.6.1.4.1.6296.101.23.51.6.3.17
		sleGponProfile2BridgeUniRateLimitProfileChanged NOTIFICATION-TYPE
			OBJECTS { sleGponProfile2BridgeUniControlRequest, sleGponProfile2BridgeUniControlTimeStamp, sleGponProfile2BridgeUniControlReqResult, sleGponProfile2BridgeUniControlTName, sleGponProfile2BridgeUniControlBridgeId,
				sleGponProfile2BridgeUniControlType, sleGponProfile2BridgeUniControlId, sleGponProfile2BridgeUniControlRateLimitProfile }
			STATUS current
			DESCRIPTION
				"setUniRateLimitProfile"
			::= { sleGponProfile2BridgeUniNotification 17 }


		sleGponProfile2BridgeUniInterDomainNameChanged NOTIFICATION-TYPE
			OBJECTS { sleGponProfile2BridgeUniControlRequest, sleGponProfile2BridgeUniControlTimeStamp, sleGponProfile2BridgeUniControlReqResult, sleGponProfile2BridgeUniControlTName, sleGponProfile2BridgeUniControlBridgeId,
				sleGponProfile2BridgeUniControlType, sleGponProfile2BridgeUniControlId, sleGponProfile2BridgeUniControlInterDomainName }
			STATUS current
			DESCRIPTION
				"setUniInterDomainName"
			::= { sleGponProfile2BridgeUniNotification 18 }


--   1.3.6.1.4.1.6296.101.23.51.7
-- 1.3.6.1.4.1.6296.101.23.51.7
		sleGponProfile2Tcont OBJECT IDENTIFIER ::= { sleGponProfile2 7 }


--   1.3.6.1.4.1.6296.101.23.51.7.1
-- 1.3.6.1.4.1.6296.101.23.51.7.1
		sleGponProfile2TcontTable OBJECT-TYPE
			SYNTAX SEQUENCE OF SleGponProfile2TcontEntry
			MAX-ACCESS not-accessible
			STATUS current
			DESCRIPTION
				"sleGponProfile2TcontTable"
			::= { sleGponProfile2Tcont 1 }


--   1.3.6.1.4.1.6296.101.23.51.7.1.1
-- 1.3.6.1.4.1.6296.101.23.51.7.1.1
		sleGponProfile2TcontEntry OBJECT-TYPE
			SYNTAX SleGponProfile2TcontEntry
			MAX-ACCESS not-accessible
			STATUS current
			DESCRIPTION
				"key: sleGponProfile2TrafficIndex, sleGponProfile2TcontId"
			INDEX { sleGponProfile2TrafficIndex, sleGponProfile2TcontId }
			::= { sleGponProfile2TcontTable 1 }


		SleGponProfile2TcontEntry ::=
			SEQUENCE {
				sleGponProfile2TcontId
					Integer32,
				sleGponProfile2TcontDbaProfile
					OCTET STRING,
				sleGponProfile2TcontQueue1Weight
					Integer32,
				sleGponProfile2TcontQueue2Weight
					Integer32,
				sleGponProfile2TcontQueue3Weight
					Integer32,
				sleGponProfile2TcontQueue4Weight
					Integer32,
				sleGponProfile2TcontQueue5Weight
					Integer32,
				sleGponProfile2TcontQueue6Weight
					Integer32,
				sleGponProfile2TcontQueue7Weight
					Integer32,
				sleGponProfile2TcontQueue8Weight
					Integer32
			 }

--   1.3.6.1.4.1.6296.101.23.51.7.1.1.1
-- 1.3.6.1.4.1.6296.101.23.51.7.1.1.1
		sleGponProfile2TcontId OBJECT-TYPE
			SYNTAX Integer32 (1..65535)
			MAX-ACCESS read-only
			STATUS current
			DESCRIPTION
				"The Tcont ID"
			::= { sleGponProfile2TcontEntry 1 }


--   1.3.6.1.4.1.6296.101.23.51.7.1.1.2
-- 1.3.6.1.4.1.6296.101.23.51.7.1.1.2
		sleGponProfile2TcontDbaProfile OBJECT-TYPE
			SYNTAX OCTET STRING
			MAX-ACCESS read-only
			STATUS current
			DESCRIPTION
				"The DBA profile"
			::= { sleGponProfile2TcontEntry 2 }


--  1.3.6.1.4.1.6296.101.23.51.7.1.1.3
		sleGponProfile2TcontQueue1Weight OBJECT-TYPE
			SYNTAX Integer32 (1..255)
			MAX-ACCESS read-only
			STATUS current
			DESCRIPTION
				"The queue weight"
			::= { sleGponProfile2TcontEntry 3 }


--  1.3.6.1.4.1.6296.101.23.51.7.1.1.4
		sleGponProfile2TcontQueue2Weight OBJECT-TYPE
			SYNTAX Integer32 (1..255)
			MAX-ACCESS read-only
			STATUS current
			DESCRIPTION
				"The queue weight"
			::= { sleGponProfile2TcontEntry 4 }


--  1.3.6.1.4.1.6296.101.23.51.7.1.1.5
		sleGponProfile2TcontQueue3Weight OBJECT-TYPE
			SYNTAX Integer32 (1..255)
			MAX-ACCESS read-only
			STATUS current
			DESCRIPTION
				"The queue weight"
			::= { sleGponProfile2TcontEntry 5 }


--  1.3.6.1.4.1.6296.101.23.51.7.1.1.6
		sleGponProfile2TcontQueue4Weight OBJECT-TYPE
			SYNTAX Integer32 (1..255)
			MAX-ACCESS read-only
			STATUS current
			DESCRIPTION
				"The queue weight"
			::= { sleGponProfile2TcontEntry 6 }


--  1.3.6.1.4.1.6296.101.23.51.7.1.1.7
		sleGponProfile2TcontQueue5Weight OBJECT-TYPE
			SYNTAX Integer32 (1..255)
			MAX-ACCESS read-only
			STATUS current
			DESCRIPTION
				"The queue weight"
			::= { sleGponProfile2TcontEntry 7 }


--  1.3.6.1.4.1.6296.101.23.51.7.1.1.8
		sleGponProfile2TcontQueue6Weight OBJECT-TYPE
			SYNTAX Integer32 (1..255)
			MAX-ACCESS read-only
			STATUS current
			DESCRIPTION
				"The queue weight"
			::= { sleGponProfile2TcontEntry 8 }


--  1.3.6.1.4.1.6296.101.23.51.7.1.1.9
		sleGponProfile2TcontQueue7Weight OBJECT-TYPE
			SYNTAX Integer32 (1..255)
			MAX-ACCESS read-only
			STATUS current
			DESCRIPTION
				"The queue weight"
			::= { sleGponProfile2TcontEntry 9 }


--  1.3.6.1.4.1.6296.101.23.51.7.1.1.10
		sleGponProfile2TcontQueue8Weight OBJECT-TYPE
			SYNTAX Integer32 (1..255)
			MAX-ACCESS read-only
			STATUS current
			DESCRIPTION
				"The queue weight"
			::= { sleGponProfile2TcontEntry 10 }


--   1.3.6.1.4.1.6296.101.23.51.7.2
-- 1.3.6.1.4.1.6296.101.23.51.7.2
		sleGponProfile2TcontControl OBJECT IDENTIFIER ::= { sleGponProfile2Tcont 2 }


--   1.3.6.1.4.1.6296.101.23.51.7.2.1
-- 1.3.6.1.4.1.6296.101.23.51.7.2.1
		sleGponProfile2TcontControlRequest OBJECT-TYPE
			SYNTAX INTEGER
				{
				addTcont(1),
				delTacont(2),
				setDbaProfile(3),
				setQueueWeight(4)
				}
			MAX-ACCESS read-write
			STATUS current
			DESCRIPTION
				"The request of a user command"
			::= { sleGponProfile2TcontControl 1 }


--   1.3.6.1.4.1.6296.101.23.51.7.2.2
-- 1.3.6.1.4.1.6296.101.23.51.7.2.2
		sleGponProfile2TcontControlStatus OBJECT-TYPE
			SYNTAX SleControlStatusType
			MAX-ACCESS read-write
			STATUS current
			DESCRIPTION
				"The status of user command"
			::= { sleGponProfile2TcontControl 2 }


--   1.3.6.1.4.1.6296.101.23.51.7.2.3
-- 1.3.6.1.4.1.6296.101.23.51.7.2.3
		sleGponProfile2TcontControlTimer OBJECT-TYPE
			SYNTAX Gauge32
			MAX-ACCESS read-write
			STATUS current
			DESCRIPTION
				"The maximum time for the manager for a long running user command"
			::= { sleGponProfile2TcontControl 3 }


--   1.3.6.1.4.1.6296.101.23.51.7.2.4
-- 1.3.6.1.4.1.6296.101.23.51.7.2.4
		sleGponProfile2TcontControlTimeStamp OBJECT-TYPE
			SYNTAX TimeTicks
			MAX-ACCESS read-write
			STATUS current
			DESCRIPTION
				"The time stamp of the last command(end of command)"
			::= { sleGponProfile2TcontControl 4 }


--   1.3.6.1.4.1.6296.101.23.51.7.2.5
-- 1.3.6.1.4.1.6296.101.23.51.7.2.5
		sleGponProfile2TcontControlReqResult OBJECT-TYPE
			SYNTAX SleControlRequestResultType
			MAX-ACCESS read-write
			STATUS current
			DESCRIPTION
				"The result of the last user command"
			::= { sleGponProfile2TcontControl 5 }


--   1.3.6.1.4.1.6296.101.23.51.7.2.6
-- 1.3.6.1.4.1.6296.101.23.51.7.2.6
		sleGponProfile2TcontControlTName OBJECT-TYPE
			SYNTAX OCTET STRING
			MAX-ACCESS read-write
			STATUS current
			DESCRIPTION
				"The Traffic profile name."
			::= { sleGponProfile2TcontControl 6 }


--   1.3.6.1.4.1.6296.101.23.51.7.2.7
-- 1.3.6.1.4.1.6296.101.23.51.7.2.7
		sleGponProfile2TcontControlID OBJECT-TYPE
			SYNTAX Integer32
			MAX-ACCESS read-write
			STATUS current
			DESCRIPTION
				"The tcont ID"
			::= { sleGponProfile2TcontControl 7 }


--   1.3.6.1.4.1.6296.101.23.51.7.2.8
-- 1.3.6.1.4.1.6296.101.23.51.7.2.8
		sleGponProfile2TcontControlDbaProfile OBJECT-TYPE
			SYNTAX OCTET STRING
			MAX-ACCESS read-write
			STATUS current
			DESCRIPTION
				"The DBA profile"
			::= { sleGponProfile2TcontControl 8 }


--  1.3.6.1.4.1.6296.101.23.51.7.2.9
		sleGponProfile2TcontControlQueue1Weight OBJECT-TYPE
			SYNTAX Integer32 (1..255)
			MAX-ACCESS read-write
			STATUS current
			DESCRIPTION
				"The queue weight"
			::= { sleGponProfile2TcontControl 9 }


--  1.3.6.1.4.1.6296.101.23.51.7.2.10
		sleGponProfile2TcontControlQueue2Weight OBJECT-TYPE
			SYNTAX Integer32 (1..255)
			MAX-ACCESS read-write
			STATUS current
			DESCRIPTION
				"The queue weight"
			::= { sleGponProfile2TcontControl 10 }


--  1.3.6.1.4.1.6296.101.23.51.7.2.11
		sleGponProfile2TcontControlQueue3Weight OBJECT-TYPE
			SYNTAX Integer32 (1..255)
			MAX-ACCESS read-write
			STATUS current
			DESCRIPTION
				"The queue weight"
			::= { sleGponProfile2TcontControl 11 }


--  1.3.6.1.4.1.6296.101.23.51.7.2.12
		sleGponProfile2TcontControlQueue4Weight OBJECT-TYPE
			SYNTAX Integer32 (1..255)
			MAX-ACCESS read-write
			STATUS current
			DESCRIPTION
				"The queue weight"
			::= { sleGponProfile2TcontControl 12 }


--  1.3.6.1.4.1.6296.101.23.51.7.2.13
		sleGponProfile2TcontControlQueue5Weight OBJECT-TYPE
			SYNTAX Integer32 (1..255)
			MAX-ACCESS read-write
			STATUS current
			DESCRIPTION
				"The queue weight"
			::= { sleGponProfile2TcontControl 13 }


--  1.3.6.1.4.1.6296.101.23.51.7.2.14
		sleGponProfile2TcontControlQueue6Weight OBJECT-TYPE
			SYNTAX Integer32 (1..255)
			MAX-ACCESS read-write
			STATUS current
			DESCRIPTION
				"The queue weight"
			::= { sleGponProfile2TcontControl 14 }


--  1.3.6.1.4.1.6296.101.23.51.7.2.15
		sleGponProfile2TcontControlQueue7Weight OBJECT-TYPE
			SYNTAX Integer32 (1..255)
			MAX-ACCESS read-write
			STATUS current
			DESCRIPTION
				"The queue weight"
			::= { sleGponProfile2TcontControl 15 }


--  1.3.6.1.4.1.6296.101.23.51.7.2.16
		sleGponProfile2TcontControlQueue8Weight OBJECT-TYPE
			SYNTAX Integer32 (1..255)
			MAX-ACCESS read-write
			STATUS current
			DESCRIPTION
				"The queue weight"
			::= { sleGponProfile2TcontControl 16 }


--   1.3.6.1.4.1.6296.101.23.51.7.3
-- 1.3.6.1.4.1.6296.101.23.51.7.3
		sleGponProfile2TcontNotification OBJECT IDENTIFIER ::= { sleGponProfile2Tcont 3 }


--   1.3.6.1.4.1.6296.101.23.51.7.3.1
-- 1.3.6.1.4.1.6296.101.23.51.7.3.1
		sleGponProfile2TcontAdded NOTIFICATION-TYPE
			OBJECTS { sleGponProfile2TcontControlRequest, sleGponProfile2TcontControlTimeStamp, sleGponProfile2TcontControlReqResult, sleGponProfile2TcontControlTName, sleGponProfile2TcontControlID,
				sleGponProfile2TcontControlDbaProfile }
			STATUS current
			DESCRIPTION
				"addTcont"
			::= { sleGponProfile2TcontNotification 1 }


--   1.3.6.1.4.1.6296.101.23.51.7.3.1
-- 1.3.6.1.4.1.6296.101.23.51.7.3.2
		sleGponProfile2TcontDeleted NOTIFICATION-TYPE
			OBJECTS { sleGponProfile2TcontControlRequest, sleGponProfile2TcontControlTimeStamp, sleGponProfile2TcontControlReqResult, sleGponProfile2TcontControlTName, sleGponProfile2TcontControlID
				 }
			STATUS current
			DESCRIPTION
				"delTacont"
			::= { sleGponProfile2TcontNotification 2 }


--   1.3.6.1.4.1.6296.101.23.51.7.3.1
-- 1.3.6.1.4.1.6296.101.23.51.7.3.3
		sleGponProfile2TcontDbaChanged NOTIFICATION-TYPE
			OBJECTS { sleGponProfile2TcontControlRequest, sleGponProfile2TcontControlTimeStamp, sleGponProfile2TcontControlReqResult, sleGponProfile2TcontControlTName, sleGponProfile2TcontControlID,
				sleGponProfile2TcontControlDbaProfile }
			STATUS current
			DESCRIPTION
				"setDbaProfile"
			::= { sleGponProfile2TcontNotification 3 }


--  1.3.6.1.4.1.6296.101.23.51.7.3.4
		sleGponProfile2TcontQueueWeight NOTIFICATION-TYPE
			OBJECTS { sleGponProfile2TcontControlRequest, sleGponProfile2TcontControlTimeStamp, sleGponProfile2TcontControlReqResult, sleGponProfile2TcontControlTName, sleGponProfile2TcontControlID,
				sleGponProfile2TcontControlDbaProfile, sleGponProfile2TcontControlQueue1Weight, sleGponProfile2TcontControlQueue2Weight, sleGponProfile2TcontControlQueue3Weight, sleGponProfile2TcontControlQueue4Weight,
				sleGponProfile2TcontControlQueue5Weight, sleGponProfile2TcontControlQueue6Weight, sleGponProfile2TcontControlQueue7Weight, sleGponProfile2TcontControlQueue8Weight }
			STATUS current
			DESCRIPTION
				"setQueueWeight"
			::= { sleGponProfile2TcontNotification 4 }


--   1.3.6.1.4.1.6296.101.23.51.8
-- 1.3.6.1.4.1.6296.101.23.51.8
		sleGponProfile2TcontGemport OBJECT IDENTIFIER ::= { sleGponProfile2 8 }


--   1.3.6.1.4.1.6296.101.23.51.8.1
-- 1.3.6.1.4.1.6296.101.23.51.8.1
		sleGponProfile2TcontGemportTable OBJECT-TYPE
			SYNTAX SEQUENCE OF SleGponProfile2TcontGemportEntry
			MAX-ACCESS not-accessible
			STATUS current
			DESCRIPTION
				"sleGponProfile2TcontGemportTable"
			::= { sleGponProfile2TcontGemport 1 }


--   1.3.6.1.4.1.6296.101.23.51.8.1.1
-- 1.3.6.1.4.1.6296.101.23.51.8.1.1
		sleGponProfile2TcontGemportEntry OBJECT-TYPE
			SYNTAX SleGponProfile2TcontGemportEntry
			MAX-ACCESS not-accessible
			STATUS current
			DESCRIPTION
				"key: sleGponProfile2TrafficIndex, sleGponProfile2TcontId, sleGponProfile2TcontGemportMapperId, sleGponProfile2TcontGemportId"
			INDEX { sleGponProfile2TrafficIndex, sleGponProfile2TcontId, sleGponProfile2TcontGemportMapperId, sleGponProfile2TcontGemportId }
			::= { sleGponProfile2TcontGemportTable 1 }


		SleGponProfile2TcontGemportEntry ::=
			SEQUENCE {
				sleGponProfile2TcontGemportMapperId
					Integer32,
				sleGponProfile2TcontGemportId
					Integer32,
				sleGponProfile2TcontGemportQueue
					Integer32
			 }

--   1.3.6.1.4.1.6296.101.23.51.8.1.1.1
-- 1.3.6.1.4.1.6296.101.23.51.8.1.1.1
		sleGponProfile2TcontGemportMapperId OBJECT-TYPE
			SYNTAX Integer32 (1..65535)
			MAX-ACCESS read-only
			STATUS current
			DESCRIPTION
				"The tcont mapper ID."
			::= { sleGponProfile2TcontGemportEntry 1 }


--   1.3.6.1.4.1.6296.101.23.51.8.1.1.2
-- 1.3.6.1.4.1.6296.101.23.51.8.1.1.2
		sleGponProfile2TcontGemportId OBJECT-TYPE
			SYNTAX Integer32 (1..65535)
			MAX-ACCESS read-only
			STATUS current
			DESCRIPTION
				"The Tcont gemport Id"
			::= { sleGponProfile2TcontGemportEntry 2 }


--   1.3.6.1.4.1.6296.101.23.51.8.1.1.3
-- 1.3.6.1.4.1.6296.101.23.51.8.1.1.3
		sleGponProfile2TcontGemportQueue OBJECT-TYPE
			SYNTAX Integer32 (0 | 1..8)
			MAX-ACCESS read-only
			STATUS current
			DESCRIPTION
				"The Tcont gemport Queue"
			::= { sleGponProfile2TcontGemportEntry 3 }


--   1.3.6.1.4.1.6296.101.23.51.8.2
-- 1.3.6.1.4.1.6296.101.23.51.8.2
		sleGponProfile2TcontGemportControl OBJECT IDENTIFIER ::= { sleGponProfile2TcontGemport 2 }


--   1.3.6.1.4.1.6296.101.23.51.8.2.1
-- 1.3.6.1.4.1.6296.101.23.51.8.2.1
		sleGponProfile2TcontGemportControlRequest OBJECT-TYPE
			SYNTAX INTEGER
				{
				addTcontGemport(1),
				delTcontGemport(2)
				}
			MAX-ACCESS read-write
			STATUS current
			DESCRIPTION
				"The request of a user command"
			::= { sleGponProfile2TcontGemportControl 1 }


--   1.3.6.1.4.1.6296.101.23.51.8.2.2
-- 1.3.6.1.4.1.6296.101.23.51.8.2.2
		sleGponProfile2TcontGemportControlStatus OBJECT-TYPE
			SYNTAX SleControlStatusType
			MAX-ACCESS read-write
			STATUS current
			DESCRIPTION
				"The status of user command"
			::= { sleGponProfile2TcontGemportControl 2 }


--   1.3.6.1.4.1.6296.101.23.51.8.2.3
-- 1.3.6.1.4.1.6296.101.23.51.8.2.3
		sleGponProfile2TcontGemportControlTimer OBJECT-TYPE
			SYNTAX Gauge32
			MAX-ACCESS read-write
			STATUS current
			DESCRIPTION
				"The maximum time for the manager for a long running user command"
			::= { sleGponProfile2TcontGemportControl 3 }


--   1.3.6.1.4.1.6296.101.23.51.8.2.4
-- 1.3.6.1.4.1.6296.101.23.51.8.2.4
		sleGponProfile2TcontGemportControlTimeStamp OBJECT-TYPE
			SYNTAX TimeTicks
			MAX-ACCESS read-write
			STATUS current
			DESCRIPTION
				"The time stamp of the last command(end of command)"
			::= { sleGponProfile2TcontGemportControl 4 }


--   1.3.6.1.4.1.6296.101.23.51.8.2.5
-- 1.3.6.1.4.1.6296.101.23.51.8.2.5
		sleGponProfile2TcontGemportControlReqResult OBJECT-TYPE
			SYNTAX SleControlRequestResultType
			MAX-ACCESS read-write
			STATUS current
			DESCRIPTION
				"The result of the last user command"
			::= { sleGponProfile2TcontGemportControl 5 }


--   1.3.6.1.4.1.6296.101.23.51.8.2.6
-- 1.3.6.1.4.1.6296.101.23.51.8.2.6
		sleGponProfile2TcontGemportControlTName OBJECT-TYPE
			SYNTAX OCTET STRING
			MAX-ACCESS read-write
			STATUS current
			DESCRIPTION
				"The Traffic profile name."
			::= { sleGponProfile2TcontGemportControl 6 }


--   1.3.6.1.4.1.6296.101.23.51.8.2.7
-- 1.3.6.1.4.1.6296.101.23.51.8.2.7
		sleGponProfile2TcontGemportControlTcontId OBJECT-TYPE
			SYNTAX Integer32
			MAX-ACCESS read-write
			STATUS current
			DESCRIPTION
				"The tcont ID"
			::= { sleGponProfile2TcontGemportControl 7 }


--   1.3.6.1.4.1.6296.101.23.51.8.2.8
-- 1.3.6.1.4.1.6296.101.23.51.8.2.8
		sleGponProfile2TcontGemportControlMapperId OBJECT-TYPE
			SYNTAX Integer32
			MAX-ACCESS read-write
			STATUS current
			DESCRIPTION
				"The tcont mapper ID."
			::= { sleGponProfile2TcontGemportControl 8 }


--   1.3.6.1.4.1.6296.101.23.51.8.2.9
-- 1.3.6.1.4.1.6296.101.23.51.8.2.9
		sleGponProfile2TcontGemportControlId OBJECT-TYPE
			SYNTAX Integer32
			MAX-ACCESS read-write
			STATUS current
			DESCRIPTION
				"The gemport ID"
			::= { sleGponProfile2TcontGemportControl 9 }


--   1.3.6.1.4.1.6296.101.23.51.8.2.10
-- 1.3.6.1.4.1.6296.101.23.51.8.2.10
		sleGponProfile2TcontGemportControlQueue OBJECT-TYPE
			SYNTAX Integer32 (0 | 1..8)
			MAX-ACCESS read-write
			STATUS current
			DESCRIPTION
				"The gemport queue"
			::= { sleGponProfile2TcontGemportControl 10 }


--   1.3.6.1.4.1.6296.101.23.51.8.3
-- 1.3.6.1.4.1.6296.101.23.51.8.3
		sleGponProfile2TcontGemportNotification OBJECT IDENTIFIER ::= { sleGponProfile2TcontGemport 3 }


--   1.3.6.1.4.1.6296.101.23.51.8.3.1
-- 1.3.6.1.4.1.6296.101.23.51.8.3.1
		sleGponProfile2TcontGemportAdded NOTIFICATION-TYPE
			OBJECTS { sleGponProfile2TcontGemportControlRequest, sleGponProfile2TcontGemportControlStatus, sleGponProfile2TcontGemportControlTimer, sleGponProfile2TcontGemportControlTimeStamp, sleGponProfile2TcontGemportControlReqResult,
				sleGponProfile2TcontGemportControlTName, sleGponProfile2TcontGemportControlTcontId, sleGponProfile2TcontGemportControlMapperId, sleGponProfile2TcontGemportControlId, sleGponProfile2TcontGemportControlQueue
				 }
			STATUS current
			DESCRIPTION
				"Description."
			::= { sleGponProfile2TcontGemportNotification 1 }


--   1.3.6.1.4.1.6296.101.23.51.8.3.2
-- 1.3.6.1.4.1.6296.101.23.51.8.3.2
		sleGponProfile2TcontGemportDeleted NOTIFICATION-TYPE
			OBJECTS { sleGponProfile2TcontGemportControlRequest, sleGponProfile2TcontGemportControlTimeStamp, sleGponProfile2TcontGemportControlReqResult, sleGponProfile2TcontGemportControlTName, sleGponProfile2TcontGemportControlTcontId,
				sleGponProfile2TcontGemportControlMapperId, sleGponProfile2TcontGemportControlId }
			STATUS current
			DESCRIPTION
				"Description."
			::= { sleGponProfile2TcontGemportNotification 2 }


--   1.3.6.1.4.1.6296.101.23.51.9
-- 1.3.6.1.4.1.6296.101.23.51.9
		sleGponProfile2Mcast OBJECT IDENTIFIER ::= { sleGponProfile2 9 }


--   1.3.6.1.4.1.6296.101.23.51.9.1
-- 1.3.6.1.4.1.6296.101.23.51.9.1
		sleGponProfile2McastTable OBJECT-TYPE
			SYNTAX SEQUENCE OF SleGponProfile2McastEntry
			MAX-ACCESS not-accessible
			STATUS current
			DESCRIPTION
				"sleGponProfile2McastTable"
			::= { sleGponProfile2Mcast 1 }


--   1.3.6.1.4.1.6296.101.23.51.9.1.1
-- 1.3.6.1.4.1.6296.101.23.51.9.1.1
		sleGponProfile2McastEntry OBJECT-TYPE
			SYNTAX SleGponProfile2McastEntry
			MAX-ACCESS not-accessible
			STATUS current
			DESCRIPTION
				"key: sleGponProfile2McastIndex"
			INDEX { sleGponProfile2McastIndex }
			::= { sleGponProfile2McastTable 1 }


		SleGponProfile2McastEntry ::=
			SEQUENCE {
				sleGponProfile2McastIndex
					Integer32,
				sleGponProfile2McastName
					OCTET STRING,
				sleGponProfile2McastIgmpFunc
					INTEGER,
				sleGponProfile2McastIgmpImmLeave
					EnableFlag,
				sleGponProfile2McastIgmpRobust
					Integer32,
				sleGponProfile2McastIgmpQuerierAddress
					IpAddress,
				sleGponProfile2McastIgmpQuerierMaxRespTime
					Integer32,
				sleGponProfile2McastIgmpQuerierInterval
					Integer32,
				sleGponProfile2McastIgmpVersion
					INTEGER,
				sleGponProfile2McastIgmpUpRateLimit
					Integer32,
				sleGponProfile2McastIgmpTagCtrl
					INTEGER,
				sleGponProfile2McastIgmpTagCtrlVid
					Integer32,
				sleGponProfile2McastIgmpTagCtrlCos
					Integer32,
				sleGponProfile2McastIgmpDsTagCtrl
					INTEGER,
				sleGponProfile2McastIgmpDsTagCtrlVid
					Integer32,
				sleGponProfile2McastIgmpDsTagCtrlCos
					Integer32
			 }

--   1.3.6.1.4.1.6296.101.23.51.9.1.1.1
-- 1.3.6.1.4.1.6296.101.23.51.9.1.1.1
		sleGponProfile2McastIndex OBJECT-TYPE
			SYNTAX Integer32 (1..65535)
			MAX-ACCESS read-only
			STATUS current
			DESCRIPTION
				"The Mcast profile index."
			::= { sleGponProfile2McastEntry 1 }


--   1.3.6.1.4.1.6296.101.23.51.9.1.1.2
-- 1.3.6.1.4.1.6296.101.23.51.9.1.1.2
		sleGponProfile2McastName OBJECT-TYPE
			SYNTAX OCTET STRING
			MAX-ACCESS read-only
			STATUS current
			DESCRIPTION
				"The Mcast profile name."
			::= { sleGponProfile2McastEntry 2 }


--   1.3.6.1.4.1.6296.101.23.51.9.1.1.3
-- 1.3.6.1.4.1.6296.101.23.51.9.1.1.3
		sleGponProfile2McastIgmpFunc OBJECT-TYPE
			SYNTAX INTEGER
				{
				snooping(1),
				proxy(2),
				spr(3)
				}
			MAX-ACCESS read-only
			STATUS current
			DESCRIPTION
				"The Igmp function
				snooping :  Igmp snooping (default)
				proxy : Igmp proxy
				spr : Igmp snooping with proxy"
			::= { sleGponProfile2McastEntry 3 }


--   1.3.6.1.4.1.6296.101.23.51.9.1.1.4
-- 1.3.6.1.4.1.6296.101.23.51.9.1.1.4
		sleGponProfile2McastIgmpImmLeave OBJECT-TYPE
			SYNTAX EnableFlag
			MAX-ACCESS read-only
			STATUS current
			DESCRIPTION
				"The immediate leave processing"
			::= { sleGponProfile2McastEntry 4 }


--   1.3.6.1.4.1.6296.101.23.51.9.1.1.5
-- 1.3.6.1.4.1.6296.101.23.51.9.1.1.5
		sleGponProfile2McastIgmpRobust OBJECT-TYPE
			SYNTAX Integer32 (0 | 1..7)
			MAX-ACCESS read-only
			STATUS current
			DESCRIPTION
				"IGMP Snooping robustness variable"
			::= { sleGponProfile2McastEntry 5 }


--   1.3.6.1.4.1.6296.101.23.51.9.1.1.6
-- 1.3.6.1.4.1.6296.101.23.51.9.1.1.6
		sleGponProfile2McastIgmpQuerierAddress OBJECT-TYPE
			SYNTAX IpAddress
			MAX-ACCESS read-only
			STATUS current
			DESCRIPTION
				"The IGMP querier address."
			::= { sleGponProfile2McastEntry 6 }


--   1.3.6.1.4.1.6296.101.23.51.9.1.1.7
-- 1.3.6.1.4.1.6296.101.23.51.9.1.1.7
		sleGponProfile2McastIgmpQuerierMaxRespTime OBJECT-TYPE
			SYNTAX Integer32 (1..25)
			MAX-ACCESS read-only
			STATUS current
			DESCRIPTION
				"The IGMP querier max-response time"
			::= { sleGponProfile2McastEntry 7 }


--   1.3.6.1.4.1.6296.101.23.51.9.1.1.8
-- 1.3.6.1.4.1.6296.101.23.51.9.1.1.8
		sleGponProfile2McastIgmpQuerierInterval OBJECT-TYPE
			SYNTAX Integer32 (1..3600)
			MAX-ACCESS read-only
			STATUS current
			DESCRIPTION
				"The IGMP querier query-interval."
			::= { sleGponProfile2McastEntry 8 }


--   1.3.6.1.4.1.6296.101.23.51.9.1.1.9
-- 1.3.6.1.4.1.6296.101.23.51.9.1.1.9
		sleGponProfile2McastIgmpVersion OBJECT-TYPE
			SYNTAX INTEGER
				{
				version1(1),
				version2(2),
				version3(3)
				}
			MAX-ACCESS read-only
			STATUS current
			DESCRIPTION
				"The IGMP version."
			::= { sleGponProfile2McastEntry 9 }


--   1.3.6.1.4.1.6296.101.23.51.9.1.1.10
-- 1.3.6.1.4.1.6296.101.23.51.9.1.1.10
		sleGponProfile2McastIgmpUpRateLimit OBJECT-TYPE
			SYNTAX Integer32
			MAX-ACCESS read-only
			STATUS current
			DESCRIPTION
				"The IGMP upstream rate-limit"
			::= { sleGponProfile2McastEntry 10 }


--   1.3.6.1.4.1.6296.101.23.51.9.1.1.11
-- 1.3.6.1.4.1.6296.101.23.51.9.1.1.11
		sleGponProfile2McastIgmpTagCtrl OBJECT-TYPE
			SYNTAX INTEGER
				{
				bypass(1),
				add(2),
				replaceWithPbit(3),
				replace(4),
				unknown(255)
				}
			MAX-ACCESS read-only
			STATUS current
			DESCRIPTION
				"The Igmp upstream tag control action. (TCI)"
			::= { sleGponProfile2McastEntry 11 }


--   1.3.6.1.4.1.6296.101.23.51.9.1.1.12
-- 1.3.6.1.4.1.6296.101.23.51.9.1.1.12
		sleGponProfile2McastIgmpTagCtrlVid OBJECT-TYPE
			SYNTAX Integer32 (0 | 1..4095)
			MAX-ACCESS read-only
			STATUS current
			DESCRIPTION
				"The vid of TCI
				1~4095 are vailable.
				0 is None"
			::= { sleGponProfile2McastEntry 12 }


--   1.3.6.1.4.1.6296.101.23.51.9.1.1.13
-- 1.3.6.1.4.1.6296.101.23.51.9.1.1.13
		sleGponProfile2McastIgmpTagCtrlCos OBJECT-TYPE
			SYNTAX Integer32 (0..7 | 255)
			MAX-ACCESS read-only
			STATUS current
			DESCRIPTION
				"The Cos of TCI
				0~7 are available.
				255 is None."
			::= { sleGponProfile2McastEntry 13 }


		sleGponProfile2McastIgmpDsTagCtrl OBJECT-TYPE
			SYNTAX INTEGER
				{
				bypass(1),
				remove(2),
				add(3),
				replaceWithPbit(4),
				replace(5),
				unknown(255)
				}
			MAX-ACCESS read-only
			STATUS current
			DESCRIPTION
				"The Igmp downstream tag control action. (TCI)"
			::= { sleGponProfile2McastEntry 14 }


		sleGponProfile2McastIgmpDsTagCtrlVid OBJECT-TYPE
			SYNTAX Integer32 (0 | 1..4095)
			MAX-ACCESS read-only
			STATUS current
			DESCRIPTION
				"The vid of TCI
				1~4095 are vailable.
				0 is None"
			::= { sleGponProfile2McastEntry 15 }


		sleGponProfile2McastIgmpDsTagCtrlCos OBJECT-TYPE
			SYNTAX Integer32 (0..7 | 255)
			MAX-ACCESS read-only
			STATUS current
			DESCRIPTION
				"The Cos of TCI
				0~7 are available.
				255 is None."
			::= { sleGponProfile2McastEntry 16 }


--   1.3.6.1.4.1.6296.101.23.51.9.2
-- 1.3.6.1.4.1.6296.101.23.51.9.2
		sleGponProfile2McastControl OBJECT IDENTIFIER ::= { sleGponProfile2Mcast 2 }


--   1.3.6.1.4.1.6296.101.23.51.9.2.1
-- 1.3.6.1.4.1.6296.101.23.51.9.2.1
		sleGponProfile2McastControlRequest OBJECT-TYPE
			SYNTAX INTEGER
				{
				addMcastProfile(1),
				delMcastProfile(2),
				setIgmpFunction(3),
				setIgmpImmLeave(4),
				setIgmpRobuts(5),
				setIgmpQueirierInfo(6),
				setIgmpVersion(7),
				setIgmpUpRateLimit(8),
				setIgmpTagCtrl(9),
				setIgmpDsTagCtrl(10)
				}
			MAX-ACCESS read-write
			STATUS current
			DESCRIPTION
				"The request of a user command"
			::= { sleGponProfile2McastControl 1 }


--   1.3.6.1.4.1.6296.101.23.51.9.2.2
-- 1.3.6.1.4.1.6296.101.23.51.9.2.2
		sleGponProfile2McastControlStatus OBJECT-TYPE
			SYNTAX SleControlStatusType
			MAX-ACCESS read-write
			STATUS current
			DESCRIPTION
				"The status of user command"
			::= { sleGponProfile2McastControl 2 }


--   1.3.6.1.4.1.6296.101.23.51.9.2.3
-- 1.3.6.1.4.1.6296.101.23.51.9.2.3
		sleGponProfile2McastControlTimer OBJECT-TYPE
			SYNTAX Gauge32
			MAX-ACCESS read-write
			STATUS current
			DESCRIPTION
				"The maximum time for the manager for a long running user command"
			::= { sleGponProfile2McastControl 3 }


--   1.3.6.1.4.1.6296.101.23.51.9.2.4
-- 1.3.6.1.4.1.6296.101.23.51.9.2.4
		sleGponProfile2McastControlTimeStamp OBJECT-TYPE
			SYNTAX TimeTicks
			MAX-ACCESS read-write
			STATUS current
			DESCRIPTION
				"The time stamp of the last command(end of command)"
			::= { sleGponProfile2McastControl 4 }


--   1.3.6.1.4.1.6296.101.23.51.9.2.5
-- 1.3.6.1.4.1.6296.101.23.51.9.2.5
		sleGponProfile2McastControlReqResult OBJECT-TYPE
			SYNTAX SleControlRequestResultType
			MAX-ACCESS read-write
			STATUS current
			DESCRIPTION
				"The result of the last user command"
			::= { sleGponProfile2McastControl 5 }


--   1.3.6.1.4.1.6296.101.23.51.9.2.6
-- 1.3.6.1.4.1.6296.101.23.51.9.2.6
		sleGponProfile2McastControlName OBJECT-TYPE
			SYNTAX OCTET STRING
			MAX-ACCESS read-write
			STATUS current
			DESCRIPTION
				"The Multicast profile name."
			::= { sleGponProfile2McastControl 6 }


--   1.3.6.1.4.1.6296.101.23.51.9.2.7
-- 1.3.6.1.4.1.6296.101.23.51.9.2.7
		sleGponProfile2McastControlIgmpFunc OBJECT-TYPE
			SYNTAX INTEGER
				{
				snooping(1),
				proxy(2),
				spr(3)
				}
			MAX-ACCESS read-write
			STATUS current
			DESCRIPTION
				"The Igmp function
				snooping :  Igmp snooping (default)
				proxy : Igmp proxy
				spr : Igmp snooping with proxy"
			::= { sleGponProfile2McastControl 7 }


--   1.3.6.1.4.1.6296.101.23.51.9.2.8
-- 1.3.6.1.4.1.6296.101.23.51.9.2.8
		sleGponProfile2McastControlIgmpImmLeave OBJECT-TYPE
			SYNTAX EnableFlag
			MAX-ACCESS read-write
			STATUS current
			DESCRIPTION
				"The immediate leave processing"
			::= { sleGponProfile2McastControl 8 }


--   1.3.6.1.4.1.6296.101.23.51.9.2.9
-- 1.3.6.1.4.1.6296.101.23.51.9.2.9
		sleGponProfile2McastControlIgmpRobust OBJECT-TYPE
			SYNTAX Integer32 (0 | 1..7)
			MAX-ACCESS read-write
			STATUS current
			DESCRIPTION
				"IGMP Snooping robustness variable
				"
			::= { sleGponProfile2McastControl 9 }


--   1.3.6.1.4.1.6296.101.23.51.9.2.10
-- 1.3.6.1.4.1.6296.101.23.51.9.2.10
		sleGponProfile2McastControlIgmpQuerierAddress OBJECT-TYPE
			SYNTAX IpAddress
			MAX-ACCESS read-write
			STATUS current
			DESCRIPTION
				"The IGMP querier address."
			::= { sleGponProfile2McastControl 10 }


--   1.3.6.1.4.1.6296.101.23.51.9.2.11
-- 1.3.6.1.4.1.6296.101.23.51.9.2.11
		sleGponProfile2McastControlIgmpQuerierMaxRespTime OBJECT-TYPE
			SYNTAX Integer32 (1..25)
			MAX-ACCESS read-write
			STATUS current
			DESCRIPTION
				"The IGMP querier max-response time"
			::= { sleGponProfile2McastControl 11 }


--   1.3.6.1.4.1.6296.101.23.51.9.2.12
-- 1.3.6.1.4.1.6296.101.23.51.9.2.12
		sleGponProfile2McastControlIgmpQuerierInterval OBJECT-TYPE
			SYNTAX Integer32 (1..3600)
			MAX-ACCESS read-write
			STATUS current
			DESCRIPTION
				"The IGMP querier query-interval."
			::= { sleGponProfile2McastControl 12 }


--   1.3.6.1.4.1.6296.101.23.51.9.2.13
-- 1.3.6.1.4.1.6296.101.23.51.9.2.13
		sleGponProfile2McastControlIgmpVersion OBJECT-TYPE
			SYNTAX INTEGER
				{
				version1(1),
				version2(2),
				version3(3)
				}
			MAX-ACCESS read-write
			STATUS current
			DESCRIPTION
				"The IGMP version."
			::= { sleGponProfile2McastControl 13 }


--   1.3.6.1.4.1.6296.101.23.51.9.2.14
-- 1.3.6.1.4.1.6296.101.23.51.9.2.14
		sleGponProfile2McastControlIgmpUpRateLimit OBJECT-TYPE
			SYNTAX Integer32
			MAX-ACCESS read-write
			STATUS current
			DESCRIPTION
				"The IGMP upstream rate-limit"
			::= { sleGponProfile2McastControl 14 }


--   1.3.6.1.4.1.6296.101.23.51.9.2.15
-- 1.3.6.1.4.1.6296.101.23.51.9.2.15
		sleGponProfile2McastControlIgmpTagCtrl OBJECT-TYPE
			SYNTAX INTEGER
				{
				bypass(1),
				add(2),
				replaceWithPbit(3),
				replace(4),
				unknown(255)
				}
			MAX-ACCESS read-write
			STATUS current
			DESCRIPTION
				"The Igmp upstream tag control action. (TCI)"
			::= { sleGponProfile2McastControl 15 }


--   1.3.6.1.4.1.6296.101.23.51.9.2.16
-- 1.3.6.1.4.1.6296.101.23.51.9.2.16
		sleGponProfile2McastControlIgmpTagCtrlVid OBJECT-TYPE
			SYNTAX Integer32 (1..4095)
			MAX-ACCESS read-write
			STATUS current
			DESCRIPTION
				"The vid of TCI
				1~4095 are vailable.
				"
			::= { sleGponProfile2McastControl 16 }


--   1.3.6.1.4.1.6296.101.23.51.9.2.17
-- 1.3.6.1.4.1.6296.101.23.51.9.2.17
		sleGponProfile2McastControlIgmpTagCtrlCos OBJECT-TYPE
			SYNTAX Integer32 (0..7)
			MAX-ACCESS read-write
			STATUS current
			DESCRIPTION
				"The Cos of TCI
				0~7 are available.
				"
			::= { sleGponProfile2McastControl 17 }


		sleGponProfile2McastControlIgmpDsTagCtrl OBJECT-TYPE
			SYNTAX INTEGER
				{
				bypass(1),
				remove(2),
				add(3),
				replaceWithPbit(4),
				replace(5),
				unknown(255)
				}
			MAX-ACCESS read-write
			STATUS current
			DESCRIPTION
				"The Igmp downstream tag control action. (TCI)"
			::= { sleGponProfile2McastControl 18 }


		sleGponProfile2McastControlIgmpDsTagCtrlVid OBJECT-TYPE
			SYNTAX Integer32 (1..4095)
			MAX-ACCESS read-write
			STATUS current
			DESCRIPTION
				"The vid of TCI
				1~4095 are vailable."
			::= { sleGponProfile2McastControl 19 }


		sleGponProfile2McastControlIgmpDsTagCtrlCos OBJECT-TYPE
			SYNTAX Integer32 (0..7)
			MAX-ACCESS read-write
			STATUS current
			DESCRIPTION
				"The Cos of TCI
				0~7 are available."
			::= { sleGponProfile2McastControl 20 }


--   1.3.6.1.4.1.6296.101.23.51.9.3
-- 1.3.6.1.4.1.6296.101.23.51.9.3
		sleGponProfile2McastNotification OBJECT IDENTIFIER ::= { sleGponProfile2Mcast 3 }


--   1.3.6.1.4.1.6296.101.23.51.9.3.1
-- 1.3.6.1.4.1.6296.101.23.51.9.3.1
		sleGponProfile2McastProfileAdded NOTIFICATION-TYPE
			OBJECTS { sleGponProfile2McastControlRequest, sleGponProfile2McastControlStatus, sleGponProfile2McastControlTimer, sleGponProfile2McastControlTimeStamp, sleGponProfile2McastControlReqResult,
				sleGponProfile2McastControlName }
			STATUS current
			DESCRIPTION
				"Description."
			::= { sleGponProfile2McastNotification 1 }


--   1.3.6.1.4.1.6296.101.23.51.9.3.2
-- 1.3.6.1.4.1.6296.101.23.51.9.3.2
		sleGponProfile2McastProfileDeleted NOTIFICATION-TYPE
			OBJECTS { sleGponProfile2McastControlRequest, sleGponProfile2McastControlStatus, sleGponProfile2McastControlTimer, sleGponProfile2McastControlTimeStamp, sleGponProfile2McastControlReqResult,
				sleGponProfile2McastControlName }
			STATUS current
			DESCRIPTION
				"Description."
			::= { sleGponProfile2McastNotification 2 }


--   1.3.6.1.4.1.6296.101.23.51.9.3.3
-- 1.3.6.1.4.1.6296.101.23.51.9.3.3
		sleGponProfile2McastIgmpFuncChanged NOTIFICATION-TYPE
			OBJECTS { sleGponProfile2McastControlRequest, sleGponProfile2McastControlStatus, sleGponProfile2McastControlTimer, sleGponProfile2McastControlTimeStamp, sleGponProfile2McastControlReqResult,
				sleGponProfile2McastControlName, sleGponProfile2McastControlIgmpFunc }
			STATUS current
			DESCRIPTION
				"Description."
			::= { sleGponProfile2McastNotification 3 }


--   1.3.6.1.4.1.6296.101.23.51.9.3.4
-- 1.3.6.1.4.1.6296.101.23.51.9.3.4
		sleGponProfile2McastIgmpImmLeaveChanged NOTIFICATION-TYPE
			OBJECTS { sleGponProfile2McastControlRequest, sleGponProfile2McastControlStatus, sleGponProfile2McastControlTimer, sleGponProfile2McastControlTimeStamp, sleGponProfile2McastControlReqResult,
				sleGponProfile2McastControlName, sleGponProfile2McastControlIgmpImmLeave }
			STATUS current
			DESCRIPTION
				"Description."
			::= { sleGponProfile2McastNotification 4 }


--   1.3.6.1.4.1.6296.101.23.51.9.3.5
-- 1.3.6.1.4.1.6296.101.23.51.9.3.5
		sleGponProfile2McastIgmpRobustChanged NOTIFICATION-TYPE
			OBJECTS { sleGponProfile2McastControlRequest, sleGponProfile2McastControlStatus, sleGponProfile2McastControlTimer, sleGponProfile2McastControlTimeStamp, sleGponProfile2McastControlReqResult,
				sleGponProfile2McastControlName, sleGponProfile2McastControlIgmpRobust }
			STATUS current
			DESCRIPTION
				"Description."
			::= { sleGponProfile2McastNotification 5 }


--   1.3.6.1.4.1.6296.101.23.51.9.3.6
-- 1.3.6.1.4.1.6296.101.23.51.9.3.6
		sleGponProfile2McastIgmpQuerierInfoChanged NOTIFICATION-TYPE
			OBJECTS { sleGponProfile2McastControlRequest, sleGponProfile2McastControlStatus, sleGponProfile2McastControlTimer, sleGponProfile2McastControlTimeStamp, sleGponProfile2McastControlReqResult,
				sleGponProfile2McastControlName, sleGponProfile2McastControlIgmpQuerierAddress, sleGponProfile2McastControlIgmpQuerierMaxRespTime, sleGponProfile2McastControlIgmpQuerierInterval }
			STATUS current
			DESCRIPTION
				"Description."
			::= { sleGponProfile2McastNotification 6 }


--   1.3.6.1.4.1.6296.101.23.51.9.3.7
-- 1.3.6.1.4.1.6296.101.23.51.9.3.7
		sleGponProfile2McastIgmpVersionChanged NOTIFICATION-TYPE
			OBJECTS { sleGponProfile2McastControlRequest, sleGponProfile2McastControlStatus, sleGponProfile2McastControlTimer, sleGponProfile2McastControlTimeStamp, sleGponProfile2McastControlReqResult,
				sleGponProfile2McastControlName, sleGponProfile2McastControlIgmpVersion }
			STATUS current
			DESCRIPTION
				"Description."
			::= { sleGponProfile2McastNotification 7 }


--   1.3.6.1.4.1.6296.101.23.51.9.3.8
-- 1.3.6.1.4.1.6296.101.23.51.9.3.8
		sleGponProfile2McastIgmpUpRateLimitChanged NOTIFICATION-TYPE
			OBJECTS { sleGponProfile2McastControlRequest, sleGponProfile2McastControlStatus, sleGponProfile2McastControlTimer, sleGponProfile2McastControlTimeStamp, sleGponProfile2McastControlReqResult,
				sleGponProfile2McastControlName, sleGponProfile2McastControlIgmpUpRateLimit }
			STATUS current
			DESCRIPTION
				"Description."
			::= { sleGponProfile2McastNotification 8 }


--   1.3.6.1.4.1.6296.101.23.51.9.3.9
-- 1.3.6.1.4.1.6296.101.23.51.9.3.9
		sleGponProfile2McastIgmpTagCtrlChanged NOTIFICATION-TYPE
			OBJECTS { sleGponProfile2McastControlRequest, sleGponProfile2McastControlStatus, sleGponProfile2McastControlTimer, sleGponProfile2McastControlTimeStamp, sleGponProfile2McastControlReqResult,
				sleGponProfile2McastControlName, sleGponProfile2McastControlIgmpTagCtrl, sleGponProfile2McastControlIgmpTagCtrlVid, sleGponProfile2McastControlIgmpTagCtrlCos }
			STATUS current
			DESCRIPTION
				"Description."
			::= { sleGponProfile2McastNotification 9 }


		sleGponProfile2McastIgmpDsTagCtrlChanged NOTIFICATION-TYPE
			OBJECTS { sleGponProfile2McastControlRequest, sleGponProfile2McastControlTimeStamp, sleGponProfile2McastControlReqResult, sleGponProfile2McastControlName, sleGponProfile2McastControlIgmpDsTagCtrl,
				sleGponProfile2McastControlIgmpDsTagCtrlVid, sleGponProfile2McastControlIgmpDsTagCtrlCos }
			STATUS current
			DESCRIPTION
				"setIgmpDsTagCtrl"
			::= { sleGponProfile2McastNotification 10 }


--   1.3.6.1.4.1.6296.101.23.51.10
-- 1.3.6.1.4.1.6296.101.23.51.10
		sleGponProfile2McastACL OBJECT IDENTIFIER ::= { sleGponProfile2 10 }


--   1.3.6.1.4.1.6296.101.23.51.10.1
-- 1.3.6.1.4.1.6296.101.23.51.10.1
		sleGponProfile2McastAclTable OBJECT-TYPE
			SYNTAX SEQUENCE OF SleGponProfile2McastAclEntry
			MAX-ACCESS not-accessible
			STATUS current
			DESCRIPTION
				"sleGponProfile2McastAclTable"
			::= { sleGponProfile2McastACL 1 }


--   1.3.6.1.4.1.6296.101.23.51.10.1.1
-- 1.3.6.1.4.1.6296.101.23.51.10.1.1
		sleGponProfile2McastAclEntry OBJECT-TYPE
			SYNTAX SleGponProfile2McastAclEntry
			MAX-ACCESS not-accessible
			STATUS current
			DESCRIPTION
				"key: sleGponProfile2McastIndex, sleGponProfile2McastAclIndex"
			INDEX { sleGponProfile2McastIndex, sleGponProfile2McastAclIndex }
			::= { sleGponProfile2McastAclTable 1 }


		SleGponProfile2McastAclEntry ::=
			SEQUENCE {
				sleGponProfile2McastAclIndex
					Integer32,
				sleGponProfile2McastAclVid
					Integer32,
				sleGponProfile2McastAclDstIpStart
					IpAddress,
				sleGponProfile2McastAclDstIpEnd
					IpAddress,
				sleGponProfile2McastAclSrcIp
					IpAddress,
				sleGponProfile2McastAclBandwidth
					Integer32,
				sleGponProfile2McastAclGem
					Integer32,
				sleGponProfile2McastAclCos
					Integer32
			 }

--   1.3.6.1.4.1.6296.101.23.51.10.1.1.1
-- 1.3.6.1.4.1.6296.101.23.51.10.1.1.1
		sleGponProfile2McastAclIndex OBJECT-TYPE
			SYNTAX Integer32 (1..65535)
			MAX-ACCESS read-only
			STATUS current
			DESCRIPTION
				"The Mcast access-list index."
			::= { sleGponProfile2McastAclEntry 1 }


--   1.3.6.1.4.1.6296.101.23.51.10.1.1.2
-- 1.3.6.1.4.1.6296.101.23.51.10.1.1.2
		sleGponProfile2McastAclVid OBJECT-TYPE
			SYNTAX Integer32 (0 | 1..4094)
			MAX-ACCESS read-write
			STATUS current
			DESCRIPTION
				"This specific the VLAN carrying the multicast group DS"
			::= { sleGponProfile2McastAclEntry 2 }


--   1.3.6.1.4.1.6296.101.23.51.10.1.1.3
-- 1.3.6.1.4.1.6296.101.23.51.10.1.1.3
		sleGponProfile2McastAclDstIpStart OBJECT-TYPE
			SYNTAX IpAddress
			MAX-ACCESS read-only
			STATUS current
			DESCRIPTION
				"The destination IP range-start."
			::= { sleGponProfile2McastAclEntry 3 }


--   1.3.6.1.4.1.6296.101.23.51.10.1.1.4
-- 1.3.6.1.4.1.6296.101.23.51.10.1.1.4
		sleGponProfile2McastAclDstIpEnd OBJECT-TYPE
			SYNTAX IpAddress
			MAX-ACCESS read-only
			STATUS current
			DESCRIPTION
				"The destination IP range-end"
			::= { sleGponProfile2McastAclEntry 4 }


--   1.3.6.1.4.1.6296.101.23.51.10.1.1.5
-- 1.3.6.1.4.1.6296.101.23.51.10.1.1.5
		sleGponProfile2McastAclSrcIp OBJECT-TYPE
			SYNTAX IpAddress
			MAX-ACCESS read-only
			STATUS current
			DESCRIPTION
				"The source IP."
			::= { sleGponProfile2McastAclEntry 5 }


--   1.3.6.1.4.1.6296.101.23.51.10.1.1.6
-- 1.3.6.1.4.1.6296.101.23.51.10.1.1.6
		sleGponProfile2McastAclBandwidth OBJECT-TYPE
			SYNTAX Integer32
			MAX-ACCESS read-only
			STATUS current
			DESCRIPTION
				"The Imputed group bandwidth"
			::= { sleGponProfile2McastAclEntry 6 }


--   1.3.6.1.4.1.6296.101.23.51.10.1.1.7
-- 1.3.6.1.4.1.6296.101.23.51.10.1.1.7
		sleGponProfile2McastAclGem OBJECT-TYPE
			SYNTAX Integer32 (1..25)
			MAX-ACCESS read-only
			STATUS current
			DESCRIPTION
				"Th GEM port ID"
			::= { sleGponProfile2McastAclEntry 7 }


--  1.3.6.1.4.1.6296.101.23.51.10.1.1.8
		sleGponProfile2McastAclCos OBJECT-TYPE
			SYNTAX Integer32 (0..7)
			MAX-ACCESS read-only
			STATUS current
			DESCRIPTION
				"The IGMP access-list CoS"
			::= { sleGponProfile2McastAclEntry 8 }


--   1.3.6.1.4.1.6296.101.23.51.10.2
-- 1.3.6.1.4.1.6296.101.23.51.10.2
		sleGponProfile2McastAclControl OBJECT IDENTIFIER ::= { sleGponProfile2McastACL 2 }


--   1.3.6.1.4.1.6296.101.23.51.10.2.1
-- 1.3.6.1.4.1.6296.101.23.51.10.2.1
		sleGponProfile2McastAclControlRequest OBJECT-TYPE
			SYNTAX INTEGER
				{
				addMcastAcl(1),
				delMcastAcl(2)
				}
			MAX-ACCESS read-write
			STATUS current
			DESCRIPTION
				"The request of a user command"
			::= { sleGponProfile2McastAclControl 1 }


--   1.3.6.1.4.1.6296.101.23.51.10.2.2
-- 1.3.6.1.4.1.6296.101.23.51.10.2.2
		sleGponProfile2McastAclControlStatus OBJECT-TYPE
			SYNTAX SleControlStatusType
			MAX-ACCESS read-write
			STATUS current
			DESCRIPTION
				"The status of user command"
			::= { sleGponProfile2McastAclControl 2 }


--   1.3.6.1.4.1.6296.101.23.51.10.2.3
-- 1.3.6.1.4.1.6296.101.23.51.10.2.3
		sleGponProfile2McastAclControlTimer OBJECT-TYPE
			SYNTAX Gauge32
			MAX-ACCESS read-write
			STATUS current
			DESCRIPTION
				"The maximum time for the manager for a long running user command"
			::= { sleGponProfile2McastAclControl 3 }


--   1.3.6.1.4.1.6296.101.23.51.10.2.4
-- 1.3.6.1.4.1.6296.101.23.51.10.2.4
		sleGponProfile2McastAclControlTimeStamp OBJECT-TYPE
			SYNTAX TimeTicks
			MAX-ACCESS read-write
			STATUS current
			DESCRIPTION
				"The time stamp of the last command(end of command)"
			::= { sleGponProfile2McastAclControl 4 }


--   1.3.6.1.4.1.6296.101.23.51.10.2.5
-- 1.3.6.1.4.1.6296.101.23.51.10.2.5
		sleGponProfile2McastAclControlReqResult OBJECT-TYPE
			SYNTAX SleControlRequestResultType
			MAX-ACCESS read-write
			STATUS current
			DESCRIPTION
				"The result of the last user command
				"
			::= { sleGponProfile2McastAclControl 5 }


--   1.3.6.1.4.1.6296.101.23.51.10.2.6
-- 1.3.6.1.4.1.6296.101.23.51.10.2.6
		sleGponProfile2McastAclControlIndex OBJECT-TYPE
			SYNTAX Integer32
			MAX-ACCESS read-write
			STATUS current
			DESCRIPTION
				"The Mcast access-list index."
			::= { sleGponProfile2McastAclControl 6 }


--   1.3.6.1.4.1.6296.101.23.51.10.2.7
-- 1.3.6.1.4.1.6296.101.23.51.10.2.7
		sleGponProfile2McastAclControlVid OBJECT-TYPE
			SYNTAX Integer32 (0 | 1..4094)
			MAX-ACCESS read-write
			STATUS current
			DESCRIPTION
				"This specific the VLAN carrying the multicast group DS"
			::= { sleGponProfile2McastAclControl 7 }


--   1.3.6.1.4.1.6296.101.23.51.10.2.8
-- 1.3.6.1.4.1.6296.101.23.51.10.2.8
		sleGponProfile2McastAclControlName OBJECT-TYPE
			SYNTAX OCTET STRING
			MAX-ACCESS read-write
			STATUS current
			DESCRIPTION
				"The Mcast profile name."
			::= { sleGponProfile2McastAclControl 8 }


--   1.3.6.1.4.1.6296.101.23.51.10.2.9
-- 1.3.6.1.4.1.6296.101.23.51.10.2.9
		sleGponProfile2McastAclControlDstIpStart OBJECT-TYPE
			SYNTAX IpAddress
			MAX-ACCESS read-write
			STATUS current
			DESCRIPTION
				"The destination IP range-start."
			::= { sleGponProfile2McastAclControl 9 }


--   1.3.6.1.4.1.6296.101.23.51.10.2.10
-- 1.3.6.1.4.1.6296.101.23.51.10.2.10
		sleGponProfile2McastAclControlDstIpEnd OBJECT-TYPE
			SYNTAX IpAddress
			MAX-ACCESS read-write
			STATUS current
			DESCRIPTION
				"The destination IP range-end"
			::= { sleGponProfile2McastAclControl 10 }


--   1.3.6.1.4.1.6296.101.23.51.10.2.11
-- 1.3.6.1.4.1.6296.101.23.51.10.2.11
		sleGponProfile2McastAclControlSrcIp OBJECT-TYPE
			SYNTAX IpAddress
			MAX-ACCESS read-write
			STATUS current
			DESCRIPTION
				"The source IP."
			::= { sleGponProfile2McastAclControl 11 }


--   1.3.6.1.4.1.6296.101.23.51.10.2.12
-- 1.3.6.1.4.1.6296.101.23.51.10.2.12
		sleGponProfile2McastAclControlBandwidth OBJECT-TYPE
			SYNTAX Integer32
			MAX-ACCESS read-write
			STATUS current
			DESCRIPTION
				"The Imputed group bandwidth"
			::= { sleGponProfile2McastAclControl 12 }


--   1.3.6.1.4.1.6296.101.23.51.10.2.13
-- 1.3.6.1.4.1.6296.101.23.51.10.2.13
		sleGponProfile2McastAclControlGem OBJECT-TYPE
			SYNTAX Integer32 (1..25)
			MAX-ACCESS read-write
			STATUS current
			DESCRIPTION
				"The GEM port ID"
			::= { sleGponProfile2McastAclControl 13 }


--  1.3.6.1.4.1.6296.101.23.51.10.2.14
		sleGponProfile2McastAclControlCos OBJECT-TYPE
			SYNTAX Integer32 (0..7)
			MAX-ACCESS read-write
			STATUS current
			DESCRIPTION
				"The IGMP access-list CoS"
			::= { sleGponProfile2McastAclControl 14 }


--   1.3.6.1.4.1.6296.101.23.51.10.3
-- 1.3.6.1.4.1.6296.101.23.51.10.3
		sleGponProfile2McastAclNotification OBJECT IDENTIFIER ::= { sleGponProfile2McastACL 3 }


--   1.3.6.1.4.1.6296.101.23.51.10.3.1
-- 1.3.6.1.4.1.6296.101.23.51.10.3.1
		sleGponProfile2McastAclAdded NOTIFICATION-TYPE
			OBJECTS { sleGponProfile2McastAclControlRequest, sleGponProfile2McastAclControlStatus, sleGponProfile2McastAclControlTimer, sleGponProfile2McastAclControlTimeStamp, sleGponProfile2McastAclControlReqResult,
				sleGponProfile2McastAclControlVid, sleGponProfile2McastAclControlDstIpStart, sleGponProfile2McastAclControlDstIpEnd, sleGponProfile2McastAclControlSrcIp, sleGponProfile2McastAclControlBandwidth,
				sleGponProfile2McastAclControlCos, sleGponProfile2McastAclControlGem, sleGponProfile2McastAclControlName }
			STATUS current
			DESCRIPTION
				"addMcastAcl"
			::= { sleGponProfile2McastAclNotification 1 }


--   1.3.6.1.4.1.6296.101.23.51.10.3.2
-- 1.3.6.1.4.1.6296.101.23.51.10.3.2
		sleGponProfile2McastAclDeleted NOTIFICATION-TYPE
			OBJECTS { sleGponProfile2McastAclControlRequest, sleGponProfile2McastAclControlStatus, sleGponProfile2McastAclControlTimer, sleGponProfile2McastAclControlTimeStamp, sleGponProfile2McastAclControlReqResult,
				sleGponProfile2McastAclControlVid, sleGponProfile2McastAclControlName }
			STATUS current
			DESCRIPTION
				"delMcastAcl"
			::= { sleGponProfile2McastAclNotification 2 }


--   1.3.6.1.4.1.6296.101.23.51.11
-- 1.3.6.1.4.1.6296.101.23.51.11
		sleGponProfile2McastSACL OBJECT IDENTIFIER ::= { sleGponProfile2 11 }


--   1.3.6.1.4.1.6296.101.23.51.11.1
-- 1.3.6.1.4.1.6296.101.23.51.11.1
		sleGponProfile2McastSAclTable OBJECT-TYPE
			SYNTAX SEQUENCE OF SleGponProfile2McastSAclEntry
			MAX-ACCESS not-accessible
			STATUS current
			DESCRIPTION
				"sleGponProfile2McastSAclTable"
			::= { sleGponProfile2McastSACL 1 }


--   1.3.6.1.4.1.6296.101.23.51.11.1.1
-- 1.3.6.1.4.1.6296.101.23.51.11.1.1
		sleGponProfile2McastSAclEntry OBJECT-TYPE
			SYNTAX SleGponProfile2McastSAclEntry
			MAX-ACCESS not-accessible
			STATUS current
			DESCRIPTION
				"key: sleGponProfile2McastIndex, sleGponProfile2McastSAclIndex"
			INDEX { sleGponProfile2McastIndex, sleGponProfile2McastSAclIndex }
			::= { sleGponProfile2McastSAclTable 1 }


		SleGponProfile2McastSAclEntry ::=
			SEQUENCE {
				sleGponProfile2McastSAclIndex
					Integer32,
				sleGponProfile2McastSAclVid
					Integer32,
				sleGponProfile2McastSAclDstIpStart
					IpAddress,
				sleGponProfile2McastSAclDstIpEnd
					IpAddress,
				sleGponProfile2McastSAclSrcIp
					IpAddress,
				sleGponProfile2McastSAclBandwidth
					Integer32,
				sleGponProfile2McastSAclGem
					Integer32,
				sleGponProfile2McastSAclCos
					Integer32
			 }

--   1.3.6.1.4.1.6296.101.23.51.11.1.1.1
-- 1.3.6.1.4.1.6296.101.23.51.11.1.1.1
		sleGponProfile2McastSAclIndex OBJECT-TYPE
			SYNTAX Integer32 (1..65535)
			MAX-ACCESS read-only
			STATUS current
			DESCRIPTION
				"The Mcast statis access-list index."
			::= { sleGponProfile2McastSAclEntry 1 }


--   1.3.6.1.4.1.6296.101.23.51.11.1.1.2
-- 1.3.6.1.4.1.6296.101.23.51.11.1.1.2
		sleGponProfile2McastSAclVid OBJECT-TYPE
			SYNTAX Integer32 (0 | 1..4094)
			MAX-ACCESS read-only
			STATUS current
			DESCRIPTION
				"This specific the VLAN carrying the multicast group DS"
			::= { sleGponProfile2McastSAclEntry 2 }


--   1.3.6.1.4.1.6296.101.23.51.11.1.1.3
-- 1.3.6.1.4.1.6296.101.23.51.11.1.1.3
		sleGponProfile2McastSAclDstIpStart OBJECT-TYPE
			SYNTAX IpAddress
			MAX-ACCESS read-only
			STATUS current
			DESCRIPTION
				"The destination IP range-start."
			::= { sleGponProfile2McastSAclEntry 3 }


--   1.3.6.1.4.1.6296.101.23.51.11.1.1.4
-- 1.3.6.1.4.1.6296.101.23.51.11.1.1.4
		sleGponProfile2McastSAclDstIpEnd OBJECT-TYPE
			SYNTAX IpAddress
			MAX-ACCESS read-only
			STATUS current
			DESCRIPTION
				"The destination IP range-end"
			::= { sleGponProfile2McastSAclEntry 4 }


--   1.3.6.1.4.1.6296.101.23.51.11.1.1.5
-- 1.3.6.1.4.1.6296.101.23.51.11.1.1.5
		sleGponProfile2McastSAclSrcIp OBJECT-TYPE
			SYNTAX IpAddress
			MAX-ACCESS read-only
			STATUS current
			DESCRIPTION
				"The source IP."
			::= { sleGponProfile2McastSAclEntry 5 }


--   1.3.6.1.4.1.6296.101.23.51.11.1.1.6
-- 1.3.6.1.4.1.6296.101.23.51.11.1.1.6
		sleGponProfile2McastSAclBandwidth OBJECT-TYPE
			SYNTAX Integer32
			MAX-ACCESS read-only
			STATUS current
			DESCRIPTION
				"The Imputed group bandwidth"
			::= { sleGponProfile2McastSAclEntry 6 }


--   1.3.6.1.4.1.6296.101.23.51.11.1.1.7
-- 1.3.6.1.4.1.6296.101.23.51.11.1.1.7
		sleGponProfile2McastSAclGem OBJECT-TYPE
			SYNTAX Integer32 (1..25)
			MAX-ACCESS read-only
			STATUS current
			DESCRIPTION
				"EM port ID"
			::= { sleGponProfile2McastSAclEntry 7 }


--  1.3.6.1.4.1.6296.101.23.51.11.1.1.8
		sleGponProfile2McastSAclCos OBJECT-TYPE
			SYNTAX Integer32 (0..7)
			MAX-ACCESS read-only
			STATUS current
			DESCRIPTION
				"The Multicast access-list CoS"
			::= { sleGponProfile2McastSAclEntry 8 }


--   1.3.6.1.4.1.6296.101.23.51.11.2
-- 1.3.6.1.4.1.6296.101.23.51.11.2
		sleGponProfile2McastSAclControl OBJECT IDENTIFIER ::= { sleGponProfile2McastSACL 2 }


--   1.3.6.1.4.1.6296.101.23.51.11.2.1
-- 1.3.6.1.4.1.6296.101.23.51.11.2.1
		sleGponProfile2McastSAclControlRequest OBJECT-TYPE
			SYNTAX INTEGER
				{
				addMcastSACL(1),
				delMcastSACL(2)
				}
			MAX-ACCESS read-write
			STATUS current
			DESCRIPTION
				"The request of a user command"
			::= { sleGponProfile2McastSAclControl 1 }


--   1.3.6.1.4.1.6296.101.23.51.11.2.2
-- 1.3.6.1.4.1.6296.101.23.51.11.2.2
		sleGponProfile2McastSAclControlStatus OBJECT-TYPE
			SYNTAX SleControlStatusType
			MAX-ACCESS read-write
			STATUS current
			DESCRIPTION
				"The status of user command"
			::= { sleGponProfile2McastSAclControl 2 }


--   1.3.6.1.4.1.6296.101.23.51.11.2.3
-- 1.3.6.1.4.1.6296.101.23.51.11.2.3
		sleGponProfile2McastSAclControlTimer OBJECT-TYPE
			SYNTAX Gauge32
			MAX-ACCESS read-write
			STATUS current
			DESCRIPTION
				"The maximum time for the manager for a long running user command"
			::= { sleGponProfile2McastSAclControl 3 }


--   1.3.6.1.4.1.6296.101.23.51.11.2.4
-- 1.3.6.1.4.1.6296.101.23.51.11.2.4
		sleGponProfile2McastSAclControlTimeStamp OBJECT-TYPE
			SYNTAX TimeTicks
			MAX-ACCESS read-write
			STATUS current
			DESCRIPTION
				"The time stamp of the last command(end of command)"
			::= { sleGponProfile2McastSAclControl 4 }


--   1.3.6.1.4.1.6296.101.23.51.11.2.5
-- 1.3.6.1.4.1.6296.101.23.51.11.2.5
		sleGponProfile2McastSAclControlReqResult OBJECT-TYPE
			SYNTAX SleControlRequestResultType
			MAX-ACCESS read-write
			STATUS current
			DESCRIPTION
				"The result of the last user command"
			::= { sleGponProfile2McastSAclControl 5 }


--   1.3.6.1.4.1.6296.101.23.51.11.2.6
-- 1.3.6.1.4.1.6296.101.23.51.11.2.6
		sleGponProfile2McastSAclControlIndex OBJECT-TYPE
			SYNTAX Integer32
			MAX-ACCESS read-write
			STATUS current
			DESCRIPTION
				"The Mcast statis access-list index."
			::= { sleGponProfile2McastSAclControl 6 }


--   1.3.6.1.4.1.6296.101.23.51.11.2.7
-- 1.3.6.1.4.1.6296.101.23.51.11.2.7
		sleGponProfile2McastSAclControlVid OBJECT-TYPE
			SYNTAX Integer32 (0 | 1..4094)
			MAX-ACCESS read-write
			STATUS current
			DESCRIPTION
				"This specific the VLAN carrying the multicast group DS"
			::= { sleGponProfile2McastSAclControl 7 }


--   1.3.6.1.4.1.6296.101.23.51.11.2.8
-- 1.3.6.1.4.1.6296.101.23.51.11.2.8
		sleGponProfile2McastSAclControlName OBJECT-TYPE
			SYNTAX OCTET STRING
			MAX-ACCESS read-write
			STATUS current
			DESCRIPTION
				"The Mcast statis access-list name."
			::= { sleGponProfile2McastSAclControl 8 }


--   1.3.6.1.4.1.6296.101.23.51.11.2.9
-- 1.3.6.1.4.1.6296.101.23.51.11.2.9
		sleGponProfile2McastSAclControlDstIpStart OBJECT-TYPE
			SYNTAX IpAddress
			MAX-ACCESS read-write
			STATUS current
			DESCRIPTION
				"The destination IP range-start."
			::= { sleGponProfile2McastSAclControl 9 }


--   1.3.6.1.4.1.6296.101.23.51.11.2.10
-- 1.3.6.1.4.1.6296.101.23.51.11.2.10
		sleGponProfile2McastSAclControlDstIpEnd OBJECT-TYPE
			SYNTAX IpAddress
			MAX-ACCESS read-write
			STATUS current
			DESCRIPTION
				"The destination IP range-end"
			::= { sleGponProfile2McastSAclControl 10 }


--   1.3.6.1.4.1.6296.101.23.51.11.2.11
-- 1.3.6.1.4.1.6296.101.23.51.11.2.11
		sleGponProfile2McastSAclControlSrcIp OBJECT-TYPE
			SYNTAX IpAddress
			MAX-ACCESS read-write
			STATUS current
			DESCRIPTION
				"The source IP."
			::= { sleGponProfile2McastSAclControl 11 }


--   1.3.6.1.4.1.6296.101.23.51.11.2.12
-- 1.3.6.1.4.1.6296.101.23.51.11.2.12
		sleGponProfile2McastSAclControlBandwidth OBJECT-TYPE
			SYNTAX Integer32
			MAX-ACCESS read-write
			STATUS current
			DESCRIPTION
				"The Imputed group bandwidth"
			::= { sleGponProfile2McastSAclControl 12 }


--   1.3.6.1.4.1.6296.101.23.51.11.2.13
-- 1.3.6.1.4.1.6296.101.23.51.11.2.13
		sleGponProfile2McastSAclControlGem OBJECT-TYPE
			SYNTAX Integer32 (1..25)
			MAX-ACCESS read-write
			STATUS current
			DESCRIPTION
				"The GEM port ID"
			::= { sleGponProfile2McastSAclControl 13 }


--  1.3.6.1.4.1.6296.101.23.51.11.2.14
		sleGponProfile2McastSAclControlCos OBJECT-TYPE
			SYNTAX Integer32 (0..7)
			MAX-ACCESS read-write
			STATUS current
			DESCRIPTION
				"The Multicast access-list CoS"
			::= { sleGponProfile2McastSAclControl 14 }


--   1.3.6.1.4.1.6296.101.23.51.11.3
-- 1.3.6.1.4.1.6296.101.23.51.11.3
		sleGponProfile2McastSAclNotification OBJECT IDENTIFIER ::= { sleGponProfile2McastSACL 3 }


--   1.3.6.1.4.1.6296.101.23.51.11.3.1
-- 1.3.6.1.4.1.6296.101.23.51.11.3.1
		sleGponProfile2McastSAclAdded NOTIFICATION-TYPE
			OBJECTS { sleGponProfile2McastSAclControlRequest, sleGponProfile2McastSAclControlTimeStamp, sleGponProfile2McastSAclControlReqResult, sleGponProfile2McastSAclControlVid, sleGponProfile2McastSAclControlName,
				sleGponProfile2McastSAclControlDstIpStart, sleGponProfile2McastSAclControlDstIpEnd, sleGponProfile2McastSAclControlSrcIp, sleGponProfile2McastSAclControlBandwidth, sleGponProfile2McastSAclControlGem,
				sleGponProfile2McastSAclControlCos }
			STATUS current
			DESCRIPTION
				"Description."
			::= { sleGponProfile2McastSAclNotification 1 }


--   1.3.6.1.4.1.6296.101.23.51.11.3.2
-- 1.3.6.1.4.1.6296.101.23.51.11.3.2
		sleGponProfile2McastSAclDeleted NOTIFICATION-TYPE
			OBJECTS { sleGponProfile2McastSAclControlRequest, sleGponProfile2McastSAclControlTimeStamp, sleGponProfile2McastSAclControlReqResult, sleGponProfile2McastSAclControlName, sleGponProfile2McastSAclControlIndex
				 }
			STATUS current
			DESCRIPTION
				"Description."
			::= { sleGponProfile2McastSAclNotification 2 }


--   1.3.6.1.4.1.6296.101.23.51.12
-- 1.3.6.1.4.1.6296.101.23.51.12
		sleGponProfile2Onu OBJECT IDENTIFIER ::= { sleGponProfile2 12 }


--   1.3.6.1.4.1.6296.101.23.51.12.1
-- 1.3.6.1.4.1.6296.101.23.51.12.1
		sleGponProfile2OnuTable OBJECT-TYPE
			SYNTAX SEQUENCE OF SleGponProfile2OnuEntry
			MAX-ACCESS not-accessible
			STATUS current
			DESCRIPTION
				"sleGponProfile2OnuTable"
			::= { sleGponProfile2Onu 1 }


--   1.3.6.1.4.1.6296.101.23.51.12.1.1
-- 1.3.6.1.4.1.6296.101.23.51.12.1.1
		sleGponProfile2OnuEntry OBJECT-TYPE
			SYNTAX SleGponProfile2OnuEntry
			MAX-ACCESS not-accessible
			STATUS current
			DESCRIPTION
				"key: sleGponProfile2OnuIndex"
			INDEX { sleGponProfile2OnuIndex }
			::= { sleGponProfile2OnuTable 1 }


		SleGponProfile2OnuEntry ::=
			SEQUENCE {
				sleGponProfile2OnuIndex
					Integer32,
				sleGponProfile2OnuName
					OCTET STRING,
				sleGponProfile2OnuRxPowerHighThresh
					Integer32,
				sleGponProfile2OnuRxPowerLowThresh
					Integer32,
				sleGponProfile2OnuRogueAlarmCount
					Integer32,
				sleGponProfile2OnuRoguePollingInterval
					Integer32,
				sleGponProfile2OnuRoguePollingCount
					Integer32,
				sleGponProfile2OnuRogueWaitingTime
					Integer32,
				sleGponProfile2OnuTrafficProfile
					OCTET STRING,
				sleGponProfile2OnuPmProfile
					OCTET STRING,
				sleGponProfile2OnuCircuitPackCardConfigCDs1E1
					INTEGER,
				sleGponProfile2OnuCircuitPackCardConfigCDs1E1J1
					INTEGER,
				sleGponProfile2OnuSWWatchdog
					INTEGER,
				sleGponProfile2OnuLinkPassThrough
					INTEGER,
				sleGponProfile2OnuCpuLoadThr
					INTEGER,
				sleGponProfile2OnuMemoryUsageThr
					INTEGER,
				sleGponProfile2OnuTemperatureHighThr
					INTEGER,
				sleGponProfile2OnuTemperatureLowThr
					INTEGER,
				sleGponProfile2OnuLoopDetectStatus
					INTEGER,
				sleGponProfile2OnuLoopDetectSendPeriod
					Integer32,
				sleGponProfile2OnuLoopDetectDetectedAction
					INTEGER,
				sleGponProfile2OnuLoopDetectBlcokTimer
					Integer32,
				sleGponProfile2OnuTr069Url
					OCTET STRING,
				sleGponProfile2OnuTr069AccessId
					OCTET STRING,
				sleGponProfile2OnuTr069AccessPassword
					OCTET STRING,
				sleGponProfile2OnuTr069Status
					INTEGER,
				sleGponProfile2OnuTr069Tag
					Integer32,
				sleGponProfile2OnuSwitchControlUplinkMacLearning
					INTEGER,
				sleGponPorifle2OnuAniVoltageHighThr
					Integer32,
				sleGponPorifle2OnuAniVoltageLowThr
					Integer32,
				sleGponPorifle2OnuAniTemperatureHighThr
					Integer32,
				sleGponPorifle2OnuAniTemperatureLowThr
					Integer32,
				sleGponPorifle2OnuAniTxBiasHighThr
					Integer32,
				sleGponPorifle2OnuAniTxBiasLowThr
					Integer32,
				sleGponPorifle2OnuAniTxpowerHighThr
					Integer32,
				sleGponPorifle2OnuAniTxpowerLowThr
					Integer32,
				sleGponProfile2OnuIgmpMaxGroups
					Integer32,
				sleGponProfile2OnuIgmpUpRateLimit
					Integer32,
				sleGponProfile2OnuIgmpHostTracking
					INTEGER,
				sleGponProfile2OnuMacFullPolicy
					INTEGER,
				sleGponProfile2OnuCpuPacketLimitBroadcast
					Integer32,
				sleGponProfile2OnuCpuPacketLimitMulticast
					Integer32,
				sleGponProfile2OnuCpuPacketLimitDlf
					Integer32,
				sleGponProfile2OnuRateLimitDownstream
					Integer32,
				sleGponProfile2OnuTrapToCpuDlf
					INTEGER,
				sleGponProfile2OnuMgmtIpPathStatus
					INTEGER,
				sleGponProfile2OnuMgmtIpPathProtocol
					INTEGER,
				sleGponProfile2OnuMgmtIpPathId
					OCTET STRING,
				sleGponProfile2OnuMgmtIpPathPassword
					OCTET STRING,
				sleGponProfile2OnuMgmtIpPathUrl
					OCTET STRING,
				sleGponProfile2OnuMgmtIpPathFilename
					OCTET STRING,
				sleGponProfile2OnuGsp
					INTEGER,
				sleGponProfile2OnuGspAvcReportRate
					INTEGER,
				sleGponProfile2OnuSnmpROCommunity
					OCTET STRING,
				sleGponProfile2OnuSnmpRWCommunity
					OCTET STRING,
				sleGponProfile2OnuSnmpSecurityName
					OCTET STRING,
				sleGponProfile2OnuSnmpAgentAddresHost
					Integer32,
				sleGponProfile2OnuSnmpTrapHostAddress
					IpAddress,
				sleGponProfile2OnuSnmpTrapHostPort
					Integer32,
				sleGponProfile2OnuSnmpSysName
					OCTET STRING
			 }

--   1.3.6.1.4.1.6296.101.23.51.12.1.1.1
-- 1.3.6.1.4.1.6296.101.23.51.12.1.1.1
		sleGponProfile2OnuIndex OBJECT-TYPE
			SYNTAX Integer32 (1..65535)
			MAX-ACCESS read-only
			STATUS current
			DESCRIPTION
				"The ONU profile index."
			::= { sleGponProfile2OnuEntry 1 }


--   1.3.6.1.4.1.6296.101.23.51.12.1.1.2
-- 1.3.6.1.4.1.6296.101.23.51.12.1.1.2
		sleGponProfile2OnuName OBJECT-TYPE
			SYNTAX OCTET STRING
			MAX-ACCESS read-only
			STATUS current
			DESCRIPTION
				"The Onu profile name."
			::= { sleGponProfile2OnuEntry 2 }


--   1.3.6.1.4.1.6296.101.23.51.12.1.1.3
-- 1.3.6.1.4.1.6296.101.23.51.12.1.1.3
		sleGponProfile2OnuRxPowerHighThresh OBJECT-TYPE
			SYNTAX Integer32 (-127..0 | 255)
			UNITS "dBm"
			MAX-ACCESS read-only
			STATUS current
			DESCRIPTION
				"ONU Receive power configuration : high threshold
				"
			::= { sleGponProfile2OnuEntry 3 }


--   1.3.6.1.4.1.6296.101.23.51.12.1.1.4
-- 1.3.6.1.4.1.6296.101.23.51.12.1.1.4
		sleGponProfile2OnuRxPowerLowThresh OBJECT-TYPE
			SYNTAX Integer32 (-127..0 | 255)
			UNITS "dBm"
			MAX-ACCESS read-write
			STATUS current
			DESCRIPTION
				"ONU Receive power configuration : low threshold
				"
			::= { sleGponProfile2OnuEntry 4 }


--   1.3.6.1.4.1.6296.101.23.51.12.1.1.5
-- 1.3.6.1.4.1.6296.101.23.51.12.1.1.5
		sleGponProfile2OnuRogueAlarmCount OBJECT-TYPE
			SYNTAX Integer32 (-1 | 1..5)
			MAX-ACCESS read-only
			STATUS current
			DESCRIPTION
				"The count of rogue onu alarm.
				"
			::= { sleGponProfile2OnuEntry 5 }


--   1.3.6.1.4.1.6296.101.23.51.12.1.1.6
-- 1.3.6.1.4.1.6296.101.23.51.12.1.1.6
		sleGponProfile2OnuRoguePollingInterval OBJECT-TYPE
			SYNTAX Integer32 (-1 | 10..60000)
			MAX-ACCESS read-only
			STATUS current
			DESCRIPTION
				"The polling interval of rogue alarm.
				"
			::= { sleGponProfile2OnuEntry 6 }


--   1.3.6.1.4.1.6296.101.23.51.12.1.1.7
-- 1.3.6.1.4.1.6296.101.23.51.12.1.1.7
		sleGponProfile2OnuRoguePollingCount OBJECT-TYPE
			SYNTAX Integer32 (1..250)
			MAX-ACCESS read-only
			STATUS current
			DESCRIPTION
				"The polling count of rogue ONU."
			::= { sleGponProfile2OnuEntry 7 }


--   1.3.6.1.4.1.6296.101.23.51.12.1.1.8
-- 1.3.6.1.4.1.6296.101.23.51.12.1.1.8
		sleGponProfile2OnuRogueWaitingTime OBJECT-TYPE
			SYNTAX Integer32 (-1 | 100..50000)
			UNITS "msec"
			MAX-ACCESS read-only
			STATUS current
			DESCRIPTION
				"The waiting time of rogue onu alarm
				"
			::= { sleGponProfile2OnuEntry 8 }


--   1.3.6.1.4.1.6296.101.23.51.12.1.1.9
-- 1.3.6.1.4.1.6296.101.23.51.12.1.1.9
		sleGponProfile2OnuTrafficProfile OBJECT-TYPE
			SYNTAX OCTET STRING
			MAX-ACCESS read-only
			STATUS current
			DESCRIPTION
				"The traffic profile name.
				"
			::= { sleGponProfile2OnuEntry 9 }


--   1.3.6.1.4.1.6296.101.23.51.12.1.1.10
-- 1.3.6.1.4.1.6296.101.23.51.12.1.1.10
		sleGponProfile2OnuPmProfile OBJECT-TYPE
			SYNTAX OCTET STRING
			MAX-ACCESS read-only
			STATUS current
			DESCRIPTION
				"The PM profile assigned to ONU profile."
			::= { sleGponProfile2OnuEntry 10 }


--  1.3.6.1.4.1.6296.101.23.51.12.1.1.11
		sleGponProfile2OnuCircuitPackCardConfigCDs1E1 OBJECT-TYPE
			SYNTAX INTEGER
				{
				ds1(0),
				e1(1),
				unUsed(255)
				}
			MAX-ACCESS read-only
			STATUS current
			DESCRIPTION
				"Card Configuration value in Circuit Pack ME.
				CDs1E1 -> Configurable DS1/E1
				CDs1E1J1 -> Configurable DS1/E1/J1
				"
			::= { sleGponProfile2OnuEntry 11 }


--  1.3.6.1.4.1.6296.101.23.51.12.1.1.12
		sleGponProfile2OnuCircuitPackCardConfigCDs1E1J1 OBJECT-TYPE
			SYNTAX INTEGER
				{
				ds1(0),
				e1(1),
				j1(2),
				unUsed(255)
				}
			MAX-ACCESS read-only
			STATUS current
			DESCRIPTION
				"Card Configuration value in Circuit Pack ME.
				CDs1E1 -> Configurable DS1/E1
				CDs1E1J1 -> Configurable DS1/E1/J1
				"
			::= { sleGponProfile2OnuEntry 12 }


--  1.3.6.1.4.1.6296.101.23.51.12.1.1.13
		sleGponProfile2OnuSWWatchdog OBJECT-TYPE
			SYNTAX INTEGER
				{
				disable(0),
				enable(1)
				}
			MAX-ACCESS read-only
			STATUS current
			DESCRIPTION
				"gpon-sw-watchdog (enable|disable)"
			::= { sleGponProfile2OnuEntry 13 }


--  1.3.6.1.4.1.6296.101.23.51.12.1.1.14
		sleGponProfile2OnuLinkPassThrough OBJECT-TYPE
			SYNTAX INTEGER
				{
				disable(0),
				enable(1)
				}
			MAX-ACCESS read-only
			STATUS current
			DESCRIPTION
				"link-pass-through (enable|disable)"
			::= { sleGponProfile2OnuEntry 14 }


--  1.3.6.1.4.1.6296.101.23.51.12.1.1.15
		sleGponProfile2OnuCpuLoadThr OBJECT-TYPE
			SYNTAX INTEGER (0..100)
			MAX-ACCESS read-only
			STATUS current
			DESCRIPTION
				"The cpu load threshold "
			::= { sleGponProfile2OnuEntry 15 }


--  1.3.6.1.4.1.6296.101.23.51.12.1.1.16
		sleGponProfile2OnuMemoryUsageThr OBJECT-TYPE
			SYNTAX INTEGER (0..100)
			MAX-ACCESS read-only
			STATUS current
			DESCRIPTION
				"The memory usage threshold."
			::= { sleGponProfile2OnuEntry 16 }


--  1.3.6.1.4.1.6296.101.23.51.12.1.1.17
		sleGponProfile2OnuTemperatureHighThr OBJECT-TYPE
			SYNTAX INTEGER (-40..0 | 1..100)
			MAX-ACCESS read-only
			STATUS current
			DESCRIPTION
				"The temperature high threshold"
			::= { sleGponProfile2OnuEntry 17 }


--  1.3.6.1.4.1.6296.101.23.51.12.1.1.18
		sleGponProfile2OnuTemperatureLowThr OBJECT-TYPE
			SYNTAX INTEGER (-40..0 | 1..100)
			MAX-ACCESS read-only
			STATUS current
			DESCRIPTION
				"The temperature low threshold"
			::= { sleGponProfile2OnuEntry 18 }


--  1.3.6.1.4.1.6296.101.23.51.12.1.1.19
		sleGponProfile2OnuLoopDetectStatus OBJECT-TYPE
			SYNTAX INTEGER
				{
				disable(0),
				enable(1)
				}
			MAX-ACCESS read-only
			STATUS current
			DESCRIPTION
				"The loop detect status."
			::= { sleGponProfile2OnuEntry 19 }


--  1.3.6.1.4.1.6296.101.23.51.12.1.1.20
		sleGponProfile2OnuLoopDetectSendPeriod OBJECT-TYPE
			SYNTAX Integer32 (0..65535)
			MAX-ACCESS read-only
			STATUS current
			DESCRIPTION
				"The sending period configuration for loop dectect. (default:10 sec)
				0: disable"
			::= { sleGponProfile2OnuEntry 20 }


--  1.3.6.1.4.1.6296.101.23.51.12.1.1.21
		sleGponProfile2OnuLoopDetectDetectedAction OBJECT-TYPE
			SYNTAX INTEGER
				{
				check(0),
				block(1)
				}
			MAX-ACCESS read-only
			STATUS current
			DESCRIPTION
				"The detected action."
			::= { sleGponProfile2OnuEntry 21 }


--  1.3.6.1.4.1.6296.101.23.51.12.1.1.22
		sleGponProfile2OnuLoopDetectBlcokTimer OBJECT-TYPE
			SYNTAX Integer32 (0..65535)
			MAX-ACCESS read-only
			STATUS current
			DESCRIPTION
				"the block timer. (default:600 sec)
				0: unlimited."
			::= { sleGponProfile2OnuEntry 22 }


--  1.3.6.1.4.1.6296.101.23.51.12.1.1.23
		sleGponProfile2OnuTr069Url OBJECT-TYPE
			SYNTAX OCTET STRING
			MAX-ACCESS read-only
			STATUS current
			DESCRIPTION
				"The tr-069 management URL"
			::= { sleGponProfile2OnuEntry 23 }


--  1.3.6.1.4.1.6296.101.23.51.12.1.1.24
		sleGponProfile2OnuTr069AccessId OBJECT-TYPE
			SYNTAX OCTET STRING
			MAX-ACCESS read-only
			STATUS current
			DESCRIPTION
				"The tr-069 management Access ID"
			::= { sleGponProfile2OnuEntry 24 }


--  1.3.6.1.4.1.6296.101.23.51.12.1.1.25
		sleGponProfile2OnuTr069AccessPassword OBJECT-TYPE
			SYNTAX OCTET STRING
			MAX-ACCESS read-only
			STATUS current
			DESCRIPTION
				"The tr-069 management Access password"
			::= { sleGponProfile2OnuEntry 25 }


--  1.3.6.1.4.1.6296.101.23.51.12.1.1.26
		sleGponProfile2OnuTr069Status OBJECT-TYPE
			SYNTAX INTEGER
				{
				disable(0),
				enable(1)
				}
			MAX-ACCESS read-only
			STATUS current
			DESCRIPTION
				"The tr-069 management status"
			::= { sleGponProfile2OnuEntry 26 }


--  1.3.6.1.4.1.6296.101.23.51.12.1.1.27
		sleGponProfile2OnuTr069Tag OBJECT-TYPE
			SYNTAX Integer32 (1..4094)
			MAX-ACCESS read-only
			STATUS current
			DESCRIPTION
				"The Tr069 Vlan tag."
			::= { sleGponProfile2OnuEntry 27 }


--  1.3.6.1.4.1.6296.101.23.51.12.1.1.28
		sleGponProfile2OnuSwitchControlUplinkMacLearning OBJECT-TYPE
			SYNTAX INTEGER
				{
				disable(0),
				enable(1)
				}
			MAX-ACCESS read-only
			STATUS current
			DESCRIPTION
				"The ONT switch uplink MAC learning"
			::= { sleGponProfile2OnuEntry 28 }


--  1.3.6.1.4.1.6296.101.23.51.12.1.1.29
		sleGponPorifle2OnuAniVoltageHighThr OBJECT-TYPE
			SYNTAX Integer32
			MAX-ACCESS read-only
			STATUS current
			DESCRIPTION
				"The voltage high threshold. (0.1 V)"
			::= { sleGponProfile2OnuEntry 29 }


--  1.3.6.1.4.1.6296.101.23.51.12.1.1.30
		sleGponPorifle2OnuAniVoltageLowThr OBJECT-TYPE
			SYNTAX Integer32
			MAX-ACCESS read-only
			STATUS current
			DESCRIPTION
				"The voltage low threshold. (0.1 V)"
			::= { sleGponProfile2OnuEntry 30 }


--  1.3.6.1.4.1.6296.101.23.51.12.1.1.31
		sleGponPorifle2OnuAniTemperatureHighThr OBJECT-TYPE
			SYNTAX Integer32
			MAX-ACCESS read-only
			STATUS current
			DESCRIPTION
				"The temperature high threshold."
			::= { sleGponProfile2OnuEntry 31 }


--  1.3.6.1.4.1.6296.101.23.51.12.1.1.32
		sleGponPorifle2OnuAniTemperatureLowThr OBJECT-TYPE
			SYNTAX Integer32
			MAX-ACCESS read-only
			STATUS current
			DESCRIPTION
				"The temperature low threshold."
			::= { sleGponProfile2OnuEntry 32 }


--  1.3.6.1.4.1.6296.101.23.51.12.1.1.33
		sleGponPorifle2OnuAniTxBiasHighThr OBJECT-TYPE
			SYNTAX Integer32
			MAX-ACCESS read-only
			STATUS current
			DESCRIPTION
				"The TX-bias high threshold."
			::= { sleGponProfile2OnuEntry 33 }


--  1.3.6.1.4.1.6296.101.23.51.12.1.1.34
		sleGponPorifle2OnuAniTxBiasLowThr OBJECT-TYPE
			SYNTAX Integer32
			MAX-ACCESS read-only
			STATUS current
			DESCRIPTION
				"The TX-bias low threshold."
			::= { sleGponProfile2OnuEntry 34 }


--  1.3.6.1.4.1.6296.101.23.51.12.1.1.35
		sleGponPorifle2OnuAniTxpowerHighThr OBJECT-TYPE
			SYNTAX Integer32
			MAX-ACCESS read-only
			STATUS current
			DESCRIPTION
				"The TX power high threshold. (0.1 dBm)"
			::= { sleGponProfile2OnuEntry 35 }


--  1.3.6.1.4.1.6296.101.23.51.12.1.1.36
		sleGponPorifle2OnuAniTxpowerLowThr OBJECT-TYPE
			SYNTAX Integer32
			MAX-ACCESS read-only
			STATUS current
			DESCRIPTION
				"The TX power low threshold. (0.1 dBm)"
			::= { sleGponProfile2OnuEntry 36 }


--  1.3.6.1.4.1.6296.101.23.51.12.1.1.37
		sleGponProfile2OnuIgmpMaxGroups OBJECT-TYPE
			SYNTAX Integer32 (0..255)
			MAX-ACCESS read-only
			STATUS current
			DESCRIPTION
				"The max count of IGMP group. (0:unlimited)"
			::= { sleGponProfile2OnuEntry 37 }


--  1.3.6.1.4.1.6296.101.23.51.12.1.1.38
		sleGponProfile2OnuIgmpUpRateLimit OBJECT-TYPE
			SYNTAX Integer32 (0..65535)
			MAX-ACCESS read-only
			STATUS current
			DESCRIPTION
				"The IGMP upstream rate limit.(0:unlimited)"
			::= { sleGponProfile2OnuEntry 38 }


--  1.3.6.1.4.1.6296.101.23.51.12.1.1.39
		sleGponProfile2OnuIgmpHostTracking OBJECT-TYPE
			SYNTAX INTEGER
				{
				disable(0),
				enable(1)
				}
			MAX-ACCESS read-only
			STATUS current
			DESCRIPTION
				"Igmp Host Tracking (enable|disable)"
			::= { sleGponProfile2OnuEntry 39 }


--  1.3.6.1.4.1.6296.101.23.51.12.1.1.40
		sleGponProfile2OnuMacFullPolicy OBJECT-TYPE
			SYNTAX INTEGER
				{
				drop(0),
				forward(1)
				}
			MAX-ACCESS read-only
			STATUS current
			DESCRIPTION
				"Mac Full Policy (drop|forward)"
			::= { sleGponProfile2OnuEntry 40 }


--  1.3.6.1.4.1.6296.101.23.51.12.1.1.41
		sleGponProfile2OnuCpuPacketLimitBroadcast OBJECT-TYPE
			SYNTAX Integer32 (0 | 100..40000)
			MAX-ACCESS read-only
			STATUS current
			DESCRIPTION
				"CPU Packet Limit Broadcast(Packet limit in steps of 100)"
			::= { sleGponProfile2OnuEntry 41 }


--  1.3.6.1.4.1.6296.101.23.51.12.1.1.42
		sleGponProfile2OnuCpuPacketLimitMulticast OBJECT-TYPE
			SYNTAX Integer32 (0 | 100..40000)
			MAX-ACCESS read-only
			STATUS current
			DESCRIPTION
				"CPU Packet Limit Multicast(Packet limit in steps of 100)"
			::= { sleGponProfile2OnuEntry 42 }


--  1.3.6.1.4.1.6296.101.23.51.12.1.1.43
		sleGponProfile2OnuCpuPacketLimitDlf OBJECT-TYPE
			SYNTAX Integer32 (0 | 100..40000)
			MAX-ACCESS read-only
			STATUS current
			DESCRIPTION
				"CPU Packet Limit L2 DLF(Packet limit in steps of 100)"
			::= { sleGponProfile2OnuEntry 43 }


--  1.3.6.1.4.1.6296.101.23.51.12.1.1.44
		sleGponProfile2OnuRateLimitDownstream OBJECT-TYPE
			SYNTAX Integer32
			MAX-ACCESS read-only
			STATUS current
			DESCRIPTION
				"The rate limit for downstream (Bandwidth in steps of 64Kbps)"
			::= { sleGponProfile2OnuEntry 44 }


--  1.3.6.1.4.1.6296.101.23.51.12.1.1.45
		sleGponProfile2OnuTrapToCpuDlf OBJECT-TYPE
			SYNTAX INTEGER
				{
				disable(0),
				enable(1)
				}
			MAX-ACCESS read-only
			STATUS current
			DESCRIPTION
				"The DLF is traped to CPU"
			::= { sleGponProfile2OnuEntry 45 }


--  1.3.6.1.4.1.6296.101.23.51.12.1.1.46
		sleGponProfile2OnuMgmtIpPathStatus OBJECT-TYPE
			SYNTAX INTEGER
				{
				disable(0),
				enable(1)
				}
			MAX-ACCESS read-only
			STATUS current
			DESCRIPTION
				"The Ip-path management status"
			::= { sleGponProfile2OnuEntry 46 }


--  1.3.6.1.4.1.6296.101.23.51.12.1.1.47
		sleGponProfile2OnuMgmtIpPathProtocol OBJECT-TYPE
			SYNTAX INTEGER
				{
				ftp(1),
				tftp(2)
				}
			MAX-ACCESS read-only
			STATUS current
			DESCRIPTION
				"The Ip-path management protocol"
			::= { sleGponProfile2OnuEntry 47 }


--  1.3.6.1.4.1.6296.101.23.51.12.1.1.48
		sleGponProfile2OnuMgmtIpPathId OBJECT-TYPE
			SYNTAX OCTET STRING
			MAX-ACCESS read-only
			STATUS current
			DESCRIPTION
				"The Ip-path management access ID"
			::= { sleGponProfile2OnuEntry 48 }


--  1.3.6.1.4.1.6296.101.23.51.12.1.1.49
		sleGponProfile2OnuMgmtIpPathPassword OBJECT-TYPE
			SYNTAX OCTET STRING
			MAX-ACCESS read-only
			STATUS current
			DESCRIPTION
				"The Ip-path management access password"
			::= { sleGponProfile2OnuEntry 49 }


--  1.3.6.1.4.1.6296.101.23.51.12.1.1.50
		sleGponProfile2OnuMgmtIpPathUrl OBJECT-TYPE
			SYNTAX OCTET STRING
			MAX-ACCESS read-only
			STATUS current
			DESCRIPTION
				"The Ip-path management URL"
			::= { sleGponProfile2OnuEntry 50 }


--  1.3.6.1.4.1.6296.101.23.51.12.1.1.51
		sleGponProfile2OnuMgmtIpPathFilename OBJECT-TYPE
			SYNTAX OCTET STRING
			MAX-ACCESS read-only
			STATUS current
			DESCRIPTION
				"The Ip-path management File name"
			::= { sleGponProfile2OnuEntry 51 }


--  1.3.6.1.4.1.6296.101.23.51.12.1.1.51
		sleGponProfile2OnuGsp OBJECT-TYPE
			SYNTAX INTEGER
				{
				disable(0),
				enable(1)
				}
			MAX-ACCESS read-only
			STATUS current
			DESCRIPTION
				"The generic status portal managed entity provides a way for the OLT to discover the status and configuration information of a non-OMCI management domain within an ONU"
			::= { sleGponProfile2OnuEntry 52 }


--  1.3.6.1.4.1.6296.101.23.51.12.1.1.51
		sleGponProfile2OnuGspAvcReportRate OBJECT-TYPE
			SYNTAX INTEGER
				{
				disable(0),
				min10(1),
				sec1(2),
				everyChange(3)
				}
			MAX-ACCESS read-only
			STATUS current
			DESCRIPTION
				"This attribute governs the rate at which the generic status portal generates attribute value change notifications."
			::= { sleGponProfile2OnuEntry 53 }


		sleGponProfile2OnuSnmpROCommunity OBJECT-TYPE
			SYNTAX OCTET STRING
			MAX-ACCESS read-only
			STATUS current
			DESCRIPTION
				"ead Only community key"
			::= { sleGponProfile2OnuEntry 54 }


		sleGponProfile2OnuSnmpRWCommunity OBJECT-TYPE
			SYNTAX OCTET STRING
			MAX-ACCESS read-only
			STATUS current
			DESCRIPTION
				"Read Write community key"
			::= { sleGponProfile2OnuEntry 55 }


		sleGponProfile2OnuSnmpSecurityName OBJECT-TYPE
			SYNTAX OCTET STRING
			MAX-ACCESS read-only
			STATUS current
			DESCRIPTION
				"Security Name"
			::= { sleGponProfile2OnuEntry 56 }


		sleGponProfile2OnuSnmpAgentAddresHost OBJECT-TYPE
			SYNTAX Integer32
			MAX-ACCESS read-only
			STATUS current
			DESCRIPTION
				"ONU Ip-host config data index"
			::= { sleGponProfile2OnuEntry 57 }


		sleGponProfile2OnuSnmpTrapHostAddress OBJECT-TYPE
			SYNTAX IpAddress
			MAX-ACCESS read-only
			STATUS current
			DESCRIPTION
				"Host address for received traps"
			::= { sleGponProfile2OnuEntry 58 }


		sleGponProfile2OnuSnmpTrapHostPort OBJECT-TYPE
			SYNTAX Integer32 (0 | 1..65535)
			MAX-ACCESS read-only
			STATUS current
			DESCRIPTION
				"Trap communication port"
			::= { sleGponProfile2OnuEntry 59 }


		sleGponProfile2OnuSnmpSysName OBJECT-TYPE
			SYNTAX OCTET STRING
			MAX-ACCESS read-only
			STATUS current
			DESCRIPTION
				"An administratively-assigned name for this managed node.
				By convention, this is the node's fully-qualified domain name.
				"
			::= { sleGponProfile2OnuEntry 60 }


--   1.3.6.1.4.1.6296.101.23.51.12.2
-- 1.3.6.1.4.1.6296.101.23.51.12.2
		sleGponProfile2OnuControl OBJECT IDENTIFIER ::= { sleGponProfile2Onu 2 }


--   1.3.6.1.4.1.6296.101.23.51.12.2.1
-- 1.3.6.1.4.1.6296.101.23.51.12.2.1
		sleGponProfile2OnuControlRequest OBJECT-TYPE
			SYNTAX INTEGER
				{
				addOnuProfile(1),
				delOnuProfile(2),
				setRogueOnuInfo(3),
				setRxPower(4),
				setTrafficProfile(5),
				setPmProfile(6),
				setCircuitPack(7),
				setSWWatchdog(8),
				setLinkPassThrough(9),
				setCpuLoadThr(10),
				setMemoryUsageThr(11),
				setTemperatureHighThr(12),
				setTemperatureLowThr(13),
				setLoopDetect(14),
				setTr069Url(15),
				clearTr069Url(16),
				setTr069Status(17),
				setTr069Access(18),
				clearTr069Access(19),
				setTr069Tag(20),
				clearTr069Tag(21),
				setSwitchControl(22),
				setAniVoltageHighThr(23),
				setAniVoltageLowThr(24),
				setAniTemperatureHighThr(25),
				setAniTemperatureLowThr(26),
				setAniTxBiasHighThr(27),
				setAniTxBiasLowThr(28),
				setAniTxpowerHighThr(29),
				setAniTxpowerLowThr(30),
				setIgmpMaxGroups(31),
				setIgmpUpRateLimit(32),
				setIgmpHostTracking(33),
				setMacFullPolicy(34),
				setCpuPacketLimitBroadcast(35),
				setCpuPacketLimitMulticast(36),
				setCpuPacketLimitDlf(37),
				setRateLimitDownstream(38),
				setTrapToCpuDlf(39),
				setMgmtIpPathStatus(40),
				setMgmtIpPathProtocol(41),
				setMgmtIpPathInfo(42),
				clearMgmtIpPath(43),
				setGsp(44),
				setSnmpRoCommunity(45),
				setSnmpRwCommunity(46),
				setSnmpSecurityName(47),
				setSnmpAgentAddress(48),
				setSnmpTrapHost(49),
				setSnmpSysName(50)
				}
			MAX-ACCESS read-write
			STATUS current
			DESCRIPTION
				"The request of a user command"
			::= { sleGponProfile2OnuControl 1 }


--   1.3.6.1.4.1.6296.101.23.51.12.2.2
-- 1.3.6.1.4.1.6296.101.23.51.12.2.2
		sleGponProfile2OnuControlStatus OBJECT-TYPE
			SYNTAX SleControlStatusType
			MAX-ACCESS read-only
			STATUS current
			DESCRIPTION
				"The status of user command"
			::= { sleGponProfile2OnuControl 2 }


--   1.3.6.1.4.1.6296.101.23.51.12.2.3
-- 1.3.6.1.4.1.6296.101.23.51.12.2.3
		sleGponProfile2OnuControlTimer OBJECT-TYPE
			SYNTAX Gauge32
			MAX-ACCESS read-write
			STATUS current
			DESCRIPTION
				"The maximum time for the manager for a long running user command"
			::= { sleGponProfile2OnuControl 3 }


--   1.3.6.1.4.1.6296.101.23.51.12.2.4
-- 1.3.6.1.4.1.6296.101.23.51.12.2.4
		sleGponProfile2OnuControlTimeStamp OBJECT-TYPE
			SYNTAX TimeTicks
			MAX-ACCESS read-only
			STATUS current
			DESCRIPTION
				"The time stamp of the last command(end of command)"
			::= { sleGponProfile2OnuControl 4 }


--   1.3.6.1.4.1.6296.101.23.51.12.2.5
-- 1.3.6.1.4.1.6296.101.23.51.12.2.5
		sleGponProfile2OnuControlReqResult OBJECT-TYPE
			SYNTAX SleControlRequestResultType
			MAX-ACCESS read-write
			STATUS current
			DESCRIPTION
				"The result of the last user command
				"
			::= { sleGponProfile2OnuControl 5 }


--   1.3.6.1.4.1.6296.101.23.51.12.2.6
-- 1.3.6.1.4.1.6296.101.23.51.12.2.6
		sleGponProfile2OnuControlName OBJECT-TYPE
			SYNTAX OCTET STRING
			MAX-ACCESS read-write
			STATUS current
			DESCRIPTION
				"The Onu profile name."
			::= { sleGponProfile2OnuControl 6 }


--   1.3.6.1.4.1.6296.101.23.51.12.2.7
-- 1.3.6.1.4.1.6296.101.23.51.12.2.7
		sleGponProfile2OnuControlRxPowerHighThresh OBJECT-TYPE
			SYNTAX Integer32 (-127..0 | 255)
			MAX-ACCESS read-write
			STATUS current
			DESCRIPTION
				"ONU Receive power configuration : high threshold"
			::= { sleGponProfile2OnuControl 7 }


--   1.3.6.1.4.1.6296.101.23.51.12.2.8
-- 1.3.6.1.4.1.6296.101.23.51.12.2.8
		sleGponProfile2OnuControlRxPowerLowThresh OBJECT-TYPE
			SYNTAX Integer32 (-127..0 | 255)
			MAX-ACCESS read-write
			STATUS current
			DESCRIPTION
				"ONU Receive power configuration : low threshold"
			::= { sleGponProfile2OnuControl 8 }


--   1.3.6.1.4.1.6296.101.23.51.12.2.9
-- 1.3.6.1.4.1.6296.101.23.51.12.2.9
		sleGponProfile2OnuControlRogueAlarmCount OBJECT-TYPE
			SYNTAX Integer32 (-1 | 1..5)
			MAX-ACCESS read-write
			STATUS current
			DESCRIPTION
				"The count of rogue onu alarm."
			::= { sleGponProfile2OnuControl 9 }


--   1.3.6.1.4.1.6296.101.23.51.12.2.10
-- 1.3.6.1.4.1.6296.101.23.51.12.2.10
		sleGponProfile2OnuControlRoguePollingInterval OBJECT-TYPE
			SYNTAX Integer32 (-1 | 10..60000)
			MAX-ACCESS read-write
			STATUS current
			DESCRIPTION
				"The polling interval of rogue alarm.
				"
			::= { sleGponProfile2OnuControl 10 }


--   1.3.6.1.4.1.6296.101.23.51.12.2.11
-- 1.3.6.1.4.1.6296.101.23.51.12.2.11
		sleGponProfile2OnuControlRoguePollingCount OBJECT-TYPE
			SYNTAX Integer32 (1..250)
			MAX-ACCESS read-write
			STATUS current
			DESCRIPTION
				"The polling count of rogue alarm."
			::= { sleGponProfile2OnuControl 11 }


--   1.3.6.1.4.1.6296.101.23.51.12.2.12
-- 1.3.6.1.4.1.6296.101.23.51.12.2.12
		sleGponProfile2OnuControlRogueWaitingTime OBJECT-TYPE
			SYNTAX Integer32 (-1 | 100..50000)
			MAX-ACCESS read-write
			STATUS current
			DESCRIPTION
				"The waiting time of rogue onu alarm"
			::= { sleGponProfile2OnuControl 12 }


--   1.3.6.1.4.1.6296.101.23.51.12.2.13
-- 1.3.6.1.4.1.6296.101.23.51.12.2.13
		sleGponProfile2OnuControlTrafficProfile OBJECT-TYPE
			SYNTAX OCTET STRING
			MAX-ACCESS read-write
			STATUS current
			DESCRIPTION
				"The traffic profile name."
			::= { sleGponProfile2OnuControl 13 }


--   1.3.6.1.4.1.6296.101.23.51.12.2.14
-- 1.3.6.1.4.1.6296.101.23.51.12.2.14
		sleGponProfile2OnuControlPmProfile OBJECT-TYPE
			SYNTAX OCTET STRING
			MAX-ACCESS read-write
			STATUS current
			DESCRIPTION
				"The PM profile assigned to ONU profile."
			::= { sleGponProfile2OnuControl 14 }


--  1.3.6.1.4.1.6296.101.23.51.12.2.15
		sleGponProfile2OnuControlCircuitPackCardConfigCDs1E1 OBJECT-TYPE
			SYNTAX INTEGER
				{
				ds1(0),
				e1(1),
				unUsed(255)
				}
			MAX-ACCESS read-write
			STATUS current
			DESCRIPTION
				"Card Configuration value in Circuit Pack ME.
				CDs1E1 -> Configurable DS1/E1
				CDs1E1J1 -> Configurable DS1/E1/J1
				"
			::= { sleGponProfile2OnuControl 15 }


--  1.3.6.1.4.1.6296.101.23.51.12.2.16
		sleGponProfile2OnuControlCircuitPackCardConfigCDs1E1J1 OBJECT-TYPE
			SYNTAX INTEGER
				{
				ds1(0),
				e1(1),
				j1(2),
				unUsed(255)
				}
			MAX-ACCESS read-write
			STATUS current
			DESCRIPTION
				"Card Configuration value in Circuit Pack ME.
				CDs1E1 -> Configurable DS1/E1
				CDs1E1J1 -> Configurable DS1/E1/J1
				"
			::= { sleGponProfile2OnuControl 16 }


--  1.3.6.1.4.1.6296.101.23.51.12.2.17
		sleGponProfile2OnuControlSWWatchdog OBJECT-TYPE
			SYNTAX INTEGER
				{
				disable(0),
				enable(1)
				}
			MAX-ACCESS read-write
			STATUS current
			DESCRIPTION
				"gpon-sw-watchdog (enable|disable)"
			::= { sleGponProfile2OnuControl 17 }


--  1.3.6.1.4.1.6296.101.23.51.12.2.18
		sleGponProfile2OnuControlLinkPassThrough OBJECT-TYPE
			SYNTAX INTEGER
				{
				disable(0),
				enable(1)
				}
			MAX-ACCESS read-write
			STATUS current
			DESCRIPTION
				"link-pass-through (enable|disable)"
			::= { sleGponProfile2OnuControl 18 }


--  1.3.6.1.4.1.6296.101.23.51.12.2.19
		sleGponProfile2OnuControlCpuLoadThr OBJECT-TYPE
			SYNTAX INTEGER (0..100)
			MAX-ACCESS read-write
			STATUS current
			DESCRIPTION
				"The cpu load threshold "
			::= { sleGponProfile2OnuControl 19 }


--  1.3.6.1.4.1.6296.101.23.51.12.2.20
		sleGponProfile2OnuControlMemoryUsageThr OBJECT-TYPE
			SYNTAX INTEGER (0..100)
			MAX-ACCESS read-write
			STATUS current
			DESCRIPTION
				"The memory usage threshold."
			::= { sleGponProfile2OnuControl 20 }


--  1.3.6.1.4.1.6296.101.23.51.12.2.21
		sleGponProfile2OnuControlTemperatureHighThr OBJECT-TYPE
			SYNTAX INTEGER (-40..0 | 1..100)
			MAX-ACCESS read-write
			STATUS current
			DESCRIPTION
				"The temperature high threshold"
			::= { sleGponProfile2OnuControl 21 }


--  1.3.6.1.4.1.6296.101.23.51.12.2.22
		sleGponProfile2OnuControlTemperatureLowThr OBJECT-TYPE
			SYNTAX INTEGER (-40..0 | 1..100)
			MAX-ACCESS read-write
			STATUS current
			DESCRIPTION
				"The temperature low threshold"
			::= { sleGponProfile2OnuControl 22 }


--  1.3.6.1.4.1.6296.101.23.51.12.2.23
		sleGponProfile2OnuControlLoopDetectStatus OBJECT-TYPE
			SYNTAX INTEGER
				{
				disable(0),
				enable(1)
				}
			MAX-ACCESS read-write
			STATUS current
			DESCRIPTION
				"The loop detect status."
			::= { sleGponProfile2OnuControl 23 }


--  1.3.6.1.4.1.6296.101.23.51.12.2.24
		sleGponProfile2OnuControlLoopDetectSendPeriod OBJECT-TYPE
			SYNTAX Integer32 (0..65535)
			MAX-ACCESS read-write
			STATUS current
			DESCRIPTION
				"The sending period configuration for loop dectect. (default:10 sec)
				0: disable

				"
			::= { sleGponProfile2OnuControl 24 }


--  1.3.6.1.4.1.6296.101.23.51.12.2.25
		sleGponProfile2OnuControlLoopDetectDetectedAction OBJECT-TYPE
			SYNTAX INTEGER
				{
				check(0),
				block(1)
				}
			MAX-ACCESS read-write
			STATUS current
			DESCRIPTION
				"The detected action."
			::= { sleGponProfile2OnuControl 25 }


--  1.3.6.1.4.1.6296.101.23.51.12.2.26
		sleGponProfile2OnuControlLoopDetectBlcokTimer OBJECT-TYPE
			SYNTAX Integer32 (0..65535)
			MAX-ACCESS read-write
			STATUS current
			DESCRIPTION
				"the block timer. (default:600 sec)
				0: unlimited."
			::= { sleGponProfile2OnuControl 26 }


--  1.3.6.1.4.1.6296.101.23.51.12.2.27
		sleGponProfile2OnuControlTr069Url OBJECT-TYPE
			SYNTAX OCTET STRING
			MAX-ACCESS read-write
			STATUS current
			DESCRIPTION
				"The tr-069 management URL"
			::= { sleGponProfile2OnuControl 27 }


--  1.3.6.1.4.1.6296.101.23.51.12.2.28
		sleGponProfile2OnuControlTr069AccessId OBJECT-TYPE
			SYNTAX OCTET STRING
			MAX-ACCESS read-write
			STATUS current
			DESCRIPTION
				"The tr-069 management Access ID"
			::= { sleGponProfile2OnuControl 28 }


--  1.3.6.1.4.1.6296.101.23.51.12.2.29
		sleGponProfile2OnuControlTr069AccessPassword OBJECT-TYPE
			SYNTAX OCTET STRING
			MAX-ACCESS read-write
			STATUS current
			DESCRIPTION
				"The tr-069 management Access password"
			::= { sleGponProfile2OnuControl 29 }


--  1.3.6.1.4.1.6296.101.23.51.12.2.30
		sleGponProfile2OnuControlTr069Status OBJECT-TYPE
			SYNTAX INTEGER
				{
				disable(0),
				enable(1)
				}
			MAX-ACCESS read-write
			STATUS current
			DESCRIPTION
				"The tr-069 management status"
			::= { sleGponProfile2OnuControl 30 }


--  1.3.6.1.4.1.6296.101.23.51.12.2.31
		sleGponProfile2OnuControlTr069Tag OBJECT-TYPE
			SYNTAX Integer32 (1..4094)
			MAX-ACCESS read-write
			STATUS current
			DESCRIPTION
				"Description."
			::= { sleGponProfile2OnuControl 31 }


--  1.3.6.1.4.1.6296.101.23.51.12.2.32
		sleGponProfile2OnuControlSwitchControlUplinkMacLearning OBJECT-TYPE
			SYNTAX INTEGER
				{
				disable(0),
				enable(1)
				}
			MAX-ACCESS read-write
			STATUS current
			DESCRIPTION
				"The ONT switch uplink MAC learning"
			::= { sleGponProfile2OnuControl 32 }


--  1.3.6.1.4.1.6296.101.23.51.12.2.33
		sleGponPorifle2OnuControlAniVoltageHighThr OBJECT-TYPE
			SYNTAX Integer32
			MAX-ACCESS read-write
			STATUS current
			DESCRIPTION
				"The voltage high threshold (0.1 V)"
			::= { sleGponProfile2OnuControl 33 }


--  1.3.6.1.4.1.6296.101.23.51.12.2.34
		sleGponPorifle2OnuControlAniVoltageLowThr OBJECT-TYPE
			SYNTAX Integer32
			MAX-ACCESS read-write
			STATUS current
			DESCRIPTION
				"The voltage low threshold (0.1 V)"
			::= { sleGponProfile2OnuControl 34 }


--  1.3.6.1.4.1.6296.101.23.51.12.2.35
		sleGponPorifle2OnuControlAniTemperatureHighThr OBJECT-TYPE
			SYNTAX Integer32
			MAX-ACCESS read-write
			STATUS current
			DESCRIPTION
				"The temperature high threshold"
			::= { sleGponProfile2OnuControl 35 }


--  1.3.6.1.4.1.6296.101.23.51.12.2.36
		sleGponPorifle2OnuControlAniTemperatureLowThr OBJECT-TYPE
			SYNTAX Integer32
			MAX-ACCESS read-write
			STATUS current
			DESCRIPTION
				"The temperature low threshold"
			::= { sleGponProfile2OnuControl 36 }


--  1.3.6.1.4.1.6296.101.23.51.12.2.37
		sleGponPorifle2OnuControlAniTxBiasHighThr OBJECT-TYPE
			SYNTAX Integer32
			MAX-ACCESS read-write
			STATUS current
			DESCRIPTION
				"The tx-bias high threshold"
			::= { sleGponProfile2OnuControl 37 }


--  1.3.6.1.4.1.6296.101.23.51.12.2.38
		sleGponPorifle2OnuControlAniTxBiasLowThr OBJECT-TYPE
			SYNTAX Integer32
			MAX-ACCESS read-write
			STATUS current
			DESCRIPTION
				"The tx-bias low threshold"
			::= { sleGponProfile2OnuControl 38 }


--  1.3.6.1.4.1.6296.101.23.51.12.2.39
		sleGponPorifle2OnuControlAniTxpowerHighThr OBJECT-TYPE
			SYNTAX Integer32
			MAX-ACCESS read-write
			STATUS current
			DESCRIPTION
				"The TX power high threshold (0.1 dBm)"
			::= { sleGponProfile2OnuControl 39 }


--  1.3.6.1.4.1.6296.101.23.51.12.2.40
		sleGponPorifle2OnuControlAniTxpowerLowThr OBJECT-TYPE
			SYNTAX Integer32
			MAX-ACCESS read-write
			STATUS current
			DESCRIPTION
				"The TX power low threshold (0.1 dBm)"
			::= { sleGponProfile2OnuControl 40 }


--  1.3.6.1.4.1.6296.101.23.51.12.2.41
		sleGponProfile2OnuControlIgmpMaxGroups OBJECT-TYPE
			SYNTAX Integer32 (0..255)
			MAX-ACCESS read-write
			STATUS current
			DESCRIPTION
				"The max count of IGMP group. (0:unlimited)"
			::= { sleGponProfile2OnuControl 41 }


--  1.3.6.1.4.1.6296.101.23.51.12.2.42
		sleGponProfile2OnuControlIgmpUpRateLimit OBJECT-TYPE
			SYNTAX Integer32 (0..65535)
			MAX-ACCESS read-write
			STATUS current
			DESCRIPTION
				"The IGMP upstream rate limit.(0:unlimited)"
			::= { sleGponProfile2OnuControl 42 }


--  1.3.6.1.4.1.6296.101.23.51.12.2.43
		sleGponProfile2OnuControlIgmpHostTracking OBJECT-TYPE
			SYNTAX INTEGER
				{
				disable(0),
				enable(1)
				}
			MAX-ACCESS read-write
			STATUS current
			DESCRIPTION
				"Igmp Host Tracking (enable|disable)"
			::= { sleGponProfile2OnuControl 43 }


--  1.3.6.1.4.1.6296.101.23.51.12.2.44
		sleGponProfile2OnuControlMacFullPolicy OBJECT-TYPE
			SYNTAX INTEGER
				{
				drop(0),
				forward(1)
				}
			MAX-ACCESS read-write
			STATUS current
			DESCRIPTION
				"The mac table full policy (drop|forward)"
			::= { sleGponProfile2OnuControl 44 }


--  1.3.6.1.4.1.6296.101.23.51.12.2.45
		sleGponProfile2OnuControlCpuPacketLimitBroadcast OBJECT-TYPE
			SYNTAX Integer32 (0 | 100..40000)
			MAX-ACCESS read-write
			STATUS current
			DESCRIPTION
				"The cpu packet rate broadcast limit.(Packet limit in steps of 100)(0: unlimited)"
			::= { sleGponProfile2OnuControl 45 }


--  1.3.6.1.4.1.6296.101.23.51.12.2.46
		sleGponProfile2OnuControlCpuPacketLimitMulticast OBJECT-TYPE
			SYNTAX Integer32 (0 | 100..40000)
			MAX-ACCESS read-write
			STATUS current
			DESCRIPTION
				"The cpu packet rate multicast limit.(Packet limit in steps of 100)(0: unlimited)"
			::= { sleGponProfile2OnuControl 46 }


--  1.3.6.1.4.1.6296.101.23.51.12.2.47
		sleGponProfile2OnuControlCpuPacketLimitDlf OBJECT-TYPE
			SYNTAX Integer32 (0 | 100..40000)
			MAX-ACCESS read-write
			STATUS current
			DESCRIPTION
				"The cpu packet rate L2 dlf limit.(Packet limit in steps of 100)(0: unlimited)"
			::= { sleGponProfile2OnuControl 47 }


--  1.3.6.1.4.1.6296.101.23.51.12.2.48
		sleGponProfile2OnuControlRateLimitDownstream OBJECT-TYPE
			SYNTAX Integer32
			MAX-ACCESS read-write
			STATUS current
			DESCRIPTION
				"The overall rate limit for downstream (Bandwidth in steps of 64Kbps)"
			::= { sleGponProfile2OnuControl 48 }


--  1.3.6.1.4.1.6296.101.23.51.12.2.49
		sleGponProfile2OnuControlTrapToCpuDlf OBJECT-TYPE
			SYNTAX INTEGER
				{
				disable(0),
				enable(1)
				}
			MAX-ACCESS read-write
			STATUS current
			DESCRIPTION
				"The DLF is traped to CPU"
			::= { sleGponProfile2OnuControl 49 }


--  1.3.6.1.4.1.6296.101.23.51.12.2.50
		sleGponProfile2OnuControlMgmtIpPathStatus OBJECT-TYPE
			SYNTAX INTEGER
				{
				disable(0),
				enable(1)
				}
			MAX-ACCESS read-write
			STATUS current
			DESCRIPTION
				"The Ip-path management status"
			::= { sleGponProfile2OnuControl 50 }


--  1.3.6.1.4.1.6296.101.23.51.12.2.51
		sleGponProfile2OnuControlMgmtIpPathProtocol OBJECT-TYPE
			SYNTAX INTEGER
				{
				ftp(1),
				tftp(2)
				}
			MAX-ACCESS read-write
			STATUS current
			DESCRIPTION
				"The Ip-path management protocol"
			::= { sleGponProfile2OnuControl 51 }


--  1.3.6.1.4.1.6296.101.23.51.12.2.52
		sleGponProfile2OnuControlMgmtIpPathId OBJECT-TYPE
			SYNTAX OCTET STRING
			MAX-ACCESS read-write
			STATUS current
			DESCRIPTION
				"The Ip-path management access ID"
			::= { sleGponProfile2OnuControl 52 }


--  1.3.6.1.4.1.6296.101.23.51.12.2.53
		sleGponProfile2OnuControlMgmtIpPathPassword OBJECT-TYPE
			SYNTAX OCTET STRING
			MAX-ACCESS read-write
			STATUS current
			DESCRIPTION
				"The Ip-path management access password"
			::= { sleGponProfile2OnuControl 53 }


--  1.3.6.1.4.1.6296.101.23.51.12.2.54
		sleGponProfile2OnuControlMgmtIpPathUrl OBJECT-TYPE
			SYNTAX OCTET STRING
			MAX-ACCESS read-write
			STATUS current
			DESCRIPTION
				"The Ip-path management URL"
			::= { sleGponProfile2OnuControl 54 }


--  1.3.6.1.4.1.6296.101.23.51.12.2.55
		sleGponProfile2OnuControlMgmtIpPathFilename OBJECT-TYPE
			SYNTAX OCTET STRING
			MAX-ACCESS read-write
			STATUS current
			DESCRIPTION
				"The Ip-path management File name"
			::= { sleGponProfile2OnuControl 55 }


--  1.3.6.1.4.1.6296.101.23.51.12.2.55
		sleGponProfile2OnuControlGsp OBJECT-TYPE
			SYNTAX INTEGER
				{
				disable(0),
				enable(1)
				}
			MAX-ACCESS read-write
			STATUS current
			DESCRIPTION
				"The generic status portal managed entity provides a way for the OLT to discover the status and configuration information of a non-OMCI management domain within an ONU"
			::= { sleGponProfile2OnuControl 56 }


--  1.3.6.1.4.1.6296.101.23.51.12.2.55
		sleGponProfile2OnuControlGspAvcReportRate OBJECT-TYPE
			SYNTAX INTEGER
				{
				disable(0),
				min10(1),
				sec1(2),
				everyChange(3)
				}
			MAX-ACCESS read-write
			STATUS current
			DESCRIPTION
				"This attribute governs the rate at which the generic status portal generates attribute value change notifications."
			::= { sleGponProfile2OnuControl 57 }


		sleGponProfile2OnuControlSnmpROCommunity OBJECT-TYPE
			SYNTAX OCTET STRING
			MAX-ACCESS read-write
			STATUS current
			DESCRIPTION
				"Read Only community key"
			::= { sleGponProfile2OnuControl 58 }


		sleGponProfile2OnuControlSnmpRWCommunity OBJECT-TYPE
			SYNTAX OCTET STRING
			MAX-ACCESS read-write
			STATUS current
			DESCRIPTION
				"Read Write community key"
			::= { sleGponProfile2OnuControl 59 }


		sleGponProfile2OnuControlSnmpSecurityName OBJECT-TYPE
			SYNTAX OCTET STRING
			MAX-ACCESS read-write
			STATUS current
			DESCRIPTION
				"Security Name"
			::= { sleGponProfile2OnuControl 60 }


		sleGponProfile2OnuControlSnmpAgentAddresHost OBJECT-TYPE
			SYNTAX Integer32
			MAX-ACCESS read-write
			STATUS current
			DESCRIPTION
				"ONU Ip-host config data index"
			::= { sleGponProfile2OnuControl 61 }


		sleGponProfile2OnuControlSnmpTrapHostAddress OBJECT-TYPE
			SYNTAX IpAddress
			MAX-ACCESS read-write
			STATUS current
			DESCRIPTION
				"Host address for received traps"
			::= { sleGponProfile2OnuControl 62 }


		sleGponProfile2OnuControlSnmpTrapHostPort OBJECT-TYPE
			SYNTAX Integer32 (0 | 1..65535)
			MAX-ACCESS read-write
			STATUS current
			DESCRIPTION
				"Host address for received traps"
			::= { sleGponProfile2OnuControl 63 }


		sleGponProfile2OnuControlSnmpSysName OBJECT-TYPE
			SYNTAX OCTET STRING
			MAX-ACCESS read-write
			STATUS current
			DESCRIPTION
				"An administratively-assigned name for this managed node.
				By convention, this is the node's fully-qualified domain name.
				"
			::= { sleGponProfile2OnuControl 64 }


--   1.3.6.1.4.1.6296.101.23.51.12.3
-- 1.3.6.1.4.1.6296.101.23.51.12.3
		sleGponProfile2OnuNotification OBJECT IDENTIFIER ::= { sleGponProfile2Onu 3 }


--   1.3.6.1.4.1.6296.101.23.51.12.3.1
-- 1.3.6.1.4.1.6296.101.23.51.12.3.1
		sleGponProfile2OnuAdded NOTIFICATION-TYPE
			OBJECTS { sleGponProfile2OnuControlRequest, sleGponProfile2OnuControlTimeStamp, sleGponProfile2OnuControlReqResult, sleGponProfile2OnuControlName }
			STATUS current
			DESCRIPTION
				"Description."
			::= { sleGponProfile2OnuNotification 1 }


--   1.3.6.1.4.1.6296.101.23.51.12.3.2
-- 1.3.6.1.4.1.6296.101.23.51.12.3.2
		sleGponProfile2OnuDeleted NOTIFICATION-TYPE
			OBJECTS { sleGponProfile2OnuControlRequest, sleGponProfile2OnuControlTimeStamp, sleGponProfile2OnuControlReqResult, sleGponProfile2OnuControlName }
			STATUS current
			DESCRIPTION
				"Description."
			::= { sleGponProfile2OnuNotification 2 }


--   1.3.6.1.4.1.6296.101.23.51.12.3.3
-- 1.3.6.1.4.1.6296.101.23.51.12.3.3
		sleGponProfile2OnuRogueInfoChanged NOTIFICATION-TYPE
			OBJECTS { sleGponProfile2OnuControlRequest, sleGponProfile2OnuControlTimeStamp, sleGponProfile2OnuControlReqResult, sleGponProfile2OnuControlName, sleGponProfile2OnuControlRogueAlarmCount,
				sleGponProfile2OnuControlRoguePollingInterval, sleGponProfile2OnuControlRogueWaitingTime, sleGponProfile2OnuControlRoguePollingCount }
			STATUS current
			DESCRIPTION
				"Description."
			::= { sleGponProfile2OnuNotification 3 }


--   1.3.6.1.4.1.6296.101.23.51.12.3.4
-- 1.3.6.1.4.1.6296.101.23.51.12.3.4
		sleGponProfile2OnuRxPowerChanged NOTIFICATION-TYPE
			OBJECTS { sleGponProfile2OnuControlRequest, sleGponProfile2OnuControlTimeStamp, sleGponProfile2OnuControlReqResult, sleGponProfile2OnuControlName, sleGponProfile2OnuControlRxPowerHighThresh,
				sleGponProfile2OnuControlRxPowerLowThresh }
			STATUS current
			DESCRIPTION
				"Description."
			::= { sleGponProfile2OnuNotification 4 }


--   1.3.6.1.4.1.6296.101.23.51.12.3.5
-- 1.3.6.1.4.1.6296.101.23.51.12.3.5
		sleGponProfile2OnuTrafficProfileChanged NOTIFICATION-TYPE
			OBJECTS { sleGponProfile2OnuControlRequest, sleGponProfile2OnuControlTimeStamp, sleGponProfile2OnuControlReqResult, sleGponProfile2OnuControlName, sleGponProfile2OnuControlTrafficProfile
				 }
			STATUS current
			DESCRIPTION
				"Description."
			::= { sleGponProfile2OnuNotification 5 }


--   1.3.6.1.4.1.6296.101.23.51.12.3.6
-- 1.3.6.1.4.1.6296.101.23.51.12.3.6
		sleGponProfile2OnuPmProfileChanged NOTIFICATION-TYPE
			OBJECTS { sleGponProfile2OnuControlRequest, sleGponProfile2OnuControlTimeStamp, sleGponProfile2OnuControlReqResult, sleGponProfile2OnuControlName, sleGponProfile2OnuControlPmProfile
				 }
			STATUS current
			DESCRIPTION
				"Description."
			::= { sleGponProfile2OnuNotification 6 }


--   1.3.6.1.4.1.6296.101.23.51.12.3.6
-- 1.3.6.1.4.1.6296.101.23.51.12.3.7
		sleGponProfile2OnuCircuitPackChanged NOTIFICATION-TYPE
			OBJECTS { sleGponProfile2OnuControlRequest, sleGponProfile2OnuControlTimeStamp, sleGponProfile2OnuControlReqResult, sleGponProfile2OnuControlName, sleGponProfile2OnuControlCircuitPackCardConfigCDs1E1,
				sleGponProfile2OnuControlCircuitPackCardConfigCDs1E1J1 }
			STATUS current
			DESCRIPTION
				"Card Configuration value in Circuit Pack ME.
				CDs1E1 -> Configurable DS1/E1
				CDs1E1J1 -> Configurable DS1/E1/J1
				"
			::= { sleGponProfile2OnuNotification 7 }


--  1.3.6.1.4.1.6296.101.23.51.12.3.8
		sleGponProfile2OnuSWWatchdogChanged NOTIFICATION-TYPE
			OBJECTS { sleGponProfile2OnuControlRequest, sleGponProfile2OnuControlTimeStamp, sleGponProfile2OnuControlReqResult, sleGponProfile2OnuControlSWWatchdog }
			STATUS current
			DESCRIPTION
				"setSWWatchdog"
			::= { sleGponProfile2OnuNotification 8 }


--  1.3.6.1.4.1.6296.101.23.51.12.3.9
		sleGponProfile2OnuLinkPassThroughChanged NOTIFICATION-TYPE
			OBJECTS { sleGponProfile2OnuControlRequest, sleGponProfile2OnuControlTimeStamp, sleGponProfile2OnuControlReqResult, sleGponProfile2OnuControlLinkPassThrough }
			STATUS current
			DESCRIPTION
				"setLinkPassThrough "
			::= { sleGponProfile2OnuNotification 9 }


--  1.3.6.1.4.1.6296.101.23.51.12.3.10
		sleGponProfile2OnuCpuLoadThrChanged NOTIFICATION-TYPE
			OBJECTS { sleGponProfile2OnuControlRequest, sleGponProfile2OnuControlTimeStamp, sleGponProfile2OnuControlReqResult, sleGponProfile2OnuControlCpuLoadThr }
			STATUS current
			DESCRIPTION
				"setCpuLoadThr"
			::= { sleGponProfile2OnuNotification 10 }


--  1.3.6.1.4.1.6296.101.23.51.12.3.11
		sleGponProfile2OnuMemoryUsageThrChanged NOTIFICATION-TYPE
			OBJECTS { sleGponProfile2OnuControlRequest, sleGponProfile2OnuControlTimeStamp, sleGponProfile2OnuControlReqResult, sleGponProfile2OnuControlMemoryUsageThr }
			STATUS current
			DESCRIPTION
				"setMemoryUsageThr"
			::= { sleGponProfile2OnuNotification 11 }


--  1.3.6.1.4.1.6296.101.23.51.12.3.12
		sleGponProfile2OnuTemperatureHighThrChanged NOTIFICATION-TYPE
			OBJECTS { sleGponProfile2OnuControlRequest, sleGponProfile2OnuControlTimeStamp, sleGponProfile2OnuControlReqResult, sleGponProfile2OnuControlTemperatureHighThr }
			STATUS current
			DESCRIPTION
				"setTemperatureHighThr"
			::= { sleGponProfile2OnuNotification 12 }


--  1.3.6.1.4.1.6296.101.23.51.12.3.13
		sleGponProfile2OnuTemperatureThrChanged NOTIFICATION-TYPE
			OBJECTS { sleGponProfile2OnuControlRequest, sleGponProfile2OnuControlTimeStamp, sleGponProfile2OnuControlReqResult, sleGponProfile2OnuControlTemperatureLowThr }
			STATUS current
			DESCRIPTION
				"setTemperatureLowThr"
			::= { sleGponProfile2OnuNotification 13 }


--  1.3.6.1.4.1.6296.101.23.51.12.3.14
		sleGponProfile2OnuLoopDetectChanged NOTIFICATION-TYPE
			OBJECTS { sleGponProfile2OnuControlRequest, sleGponProfile2OnuControlTimeStamp, sleGponProfile2OnuControlReqResult, sleGponProfile2OnuIndex, sleGponProfile2OnuControlName,
				sleGponProfile2OnuControlLoopDetectStatus, sleGponProfile2OnuControlLoopDetectSendPeriod, sleGponProfile2OnuControlLoopDetectDetectedAction, sleGponProfile2OnuControlLoopDetectBlcokTimer }
			STATUS current
			DESCRIPTION
				"setLoopDetect"
			::= { sleGponProfile2OnuNotification 14 }


--  1.3.6.1.4.1.6296.101.23.51.12.3.15
		sleGponProfile2OnuTr069UrlChanged NOTIFICATION-TYPE
			OBJECTS { sleGponProfile2OnuControlRequest, sleGponProfile2OnuControlTimeStamp, sleGponProfile2OnuControlReqResult, sleGponProfile2OnuControlTr069Url }
			STATUS current
			DESCRIPTION
				"setTr069Url "
			::= { sleGponProfile2OnuNotification 15 }


--  1.3.6.1.4.1.6296.101.23.51.12.3.16
		sleGponProfile2OnuTr069UrlCleared NOTIFICATION-TYPE
			OBJECTS { sleGponProfile2OnuControlRequest, sleGponProfile2OnuControlTimeStamp, sleGponProfile2OnuControlReqResult, sleGponProfile2OnuControlTr069Url }
			STATUS current
			DESCRIPTION
				"clearTr069Url "
			::= { sleGponProfile2OnuNotification 16 }


--  1.3.6.1.4.1.6296.101.23.51.12.3.17
		sleGponProfile2OnuTr069StatusChanged NOTIFICATION-TYPE
			OBJECTS { sleGponProfile2OnuControlRequest, sleGponProfile2OnuControlTimeStamp, sleGponProfile2OnuControlReqResult, sleGponProfile2OnuControlTr069Status }
			STATUS current
			DESCRIPTION
				"setTr069Status "
			::= { sleGponProfile2OnuNotification 17 }


--  1.3.6.1.4.1.6296.101.23.51.12.3.18
		sleGponProfile2OnuTr069AccessChanged NOTIFICATION-TYPE
			OBJECTS { sleGponProfile2OnuControlRequest, sleGponProfile2OnuControlTimeStamp, sleGponProfile2OnuControlReqResult, sleGponProfile2OnuControlTr069AccessId, sleGponProfile2OnuControlTr069AccessPassword
				 }
			STATUS current
			DESCRIPTION
				"setTr069Access"
			::= { sleGponProfile2OnuNotification 18 }


--  1.3.6.1.4.1.6296.101.23.51.12.3.19
		sleGponProfile2OnuTr069AccessCleared NOTIFICATION-TYPE
			OBJECTS { sleGponProfile2OnuControlRequest, sleGponProfile2OnuControlTimeStamp, sleGponProfile2OnuControlReqResult, sleGponProfile2OnuControlTr069AccessId, sleGponProfile2OnuControlTr069AccessPassword
				 }
			STATUS current
			DESCRIPTION
				"clearTr069Access"
			::= { sleGponProfile2OnuNotification 19 }


--  1.3.6.1.4.1.6296.101.23.51.12.3.20
		sleGponProfile2OnuTr069TagChanged NOTIFICATION-TYPE
			OBJECTS { sleGponProfile2OnuControlRequest, sleGponProfile2OnuControlTimeStamp, sleGponProfile2OnuControlReqResult, sleGponProfile2OnuControlTr069Tag }
			STATUS current
			DESCRIPTION
				"setTr069Tag"
			::= { sleGponProfile2OnuNotification 20 }


--  1.3.6.1.4.1.6296.101.23.51.12.3.21
		sleGponProfile2OnuTr069TagCleared NOTIFICATION-TYPE
			OBJECTS { sleGponProfile2OnuControlRequest, sleGponProfile2OnuControlTimeStamp, sleGponProfile2OnuControlReqResult, sleGponProfile2OnuControlTr069Tag }
			STATUS current
			DESCRIPTION
				"clearTr069Tag"
			::= { sleGponProfile2OnuNotification 21 }


--  1.3.6.1.4.1.6296.101.23.51.12.3.22
		sleGponProfile2OnuSwitchControlChanged NOTIFICATION-TYPE
			OBJECTS { sleGponProfile2OnuControlRequest, sleGponProfile2OnuControlTimeStamp, sleGponProfile2OnuControlReqResult, sleGponProfile2OnuIndex, sleGponProfile2OnuControlName,
				sleGponProfile2OnuControlSwitchControlUplinkMacLearning }
			STATUS current
			DESCRIPTION
				"setSwitchControl"
			::= { sleGponProfile2OnuNotification 22 }


--  1.3.6.1.4.1.6296.101.23.51.12.3.23
		sleGponProfile2OnuAniVoltageHighThrChanged NOTIFICATION-TYPE
			OBJECTS { sleGponProfile2OnuControlRequest, sleGponProfile2OnuControlTimeStamp, sleGponProfile2OnuControlReqResult, sleGponProfile2OnuIndex, sleGponProfile2OnuControlName,
				sleGponPorifle2OnuControlAniVoltageHighThr }
			STATUS current
			DESCRIPTION
				"setAniVoltageHighThr"
			::= { sleGponProfile2OnuNotification 23 }


--  1.3.6.1.4.1.6296.101.23.51.12.3.24
		sleGponProfile2OnuAniVoltageLowThrChanged NOTIFICATION-TYPE
			OBJECTS { sleGponProfile2OnuControlRequest, sleGponProfile2OnuControlTimeStamp, sleGponProfile2OnuControlReqResult, sleGponProfile2OnuIndex, sleGponProfile2OnuControlName,
				sleGponPorifle2OnuControlAniVoltageLowThr }
			STATUS current
			DESCRIPTION
				"setAniVoltageLowThr"
			::= { sleGponProfile2OnuNotification 24 }


--  1.3.6.1.4.1.6296.101.23.51.12.3.25
		sleGponProfile2OnuAniTemperatureHighThrChanged NOTIFICATION-TYPE
			OBJECTS { sleGponProfile2OnuControlRequest, sleGponProfile2OnuControlTimeStamp, sleGponProfile2OnuControlReqResult, sleGponProfile2OnuIndex, sleGponProfile2OnuControlName,
				sleGponPorifle2OnuControlAniTemperatureHighThr }
			STATUS current
			DESCRIPTION
				"setAniTemperatureHighThr"
			::= { sleGponProfile2OnuNotification 25 }


--  1.3.6.1.4.1.6296.101.23.51.12.3.26
		sleGponProfile2OnuAniTemperatureLowThrChanged NOTIFICATION-TYPE
			OBJECTS { sleGponProfile2OnuControlRequest, sleGponProfile2OnuControlTimeStamp, sleGponProfile2OnuControlReqResult, sleGponProfile2OnuIndex, sleGponProfile2OnuControlName,
				sleGponPorifle2OnuControlAniTemperatureLowThr }
			STATUS current
			DESCRIPTION
				"setAniTemperatureLowThr"
			::= { sleGponProfile2OnuNotification 26 }


--  1.3.6.1.4.1.6296.101.23.51.12.3.27
		sleGponProfile2OnuAniTxBiasHighThrChanged NOTIFICATION-TYPE
			OBJECTS { sleGponProfile2OnuControlRequest, sleGponProfile2OnuControlTimeStamp, sleGponProfile2OnuControlReqResult, sleGponProfile2OnuIndex, sleGponProfile2OnuControlName,
				sleGponPorifle2OnuControlAniTxBiasHighThr }
			STATUS current
			DESCRIPTION
				"setAniTxBiasHighThr"
			::= { sleGponProfile2OnuNotification 27 }


--  1.3.6.1.4.1.6296.101.23.51.12.3.28
		sleGponProfile2OnuAniTxBiasLowThrChanged NOTIFICATION-TYPE
			OBJECTS { sleGponProfile2OnuControlRequest, sleGponProfile2OnuControlTimeStamp, sleGponProfile2OnuControlReqResult, sleGponProfile2OnuIndex, sleGponProfile2OnuControlName,
				sleGponPorifle2OnuControlAniTxBiasLowThr }
			STATUS current
			DESCRIPTION
				"setAniTxBiasLowThr"
			::= { sleGponProfile2OnuNotification 28 }


--  1.3.6.1.4.1.6296.101.23.51.12.3.29
		sleGponProfile2OnuAniTxpowerHighThrChanged NOTIFICATION-TYPE
			OBJECTS { sleGponProfile2OnuControlRequest, sleGponProfile2OnuControlTimeStamp, sleGponProfile2OnuControlReqResult, sleGponProfile2OnuIndex, sleGponProfile2OnuControlName,
				sleGponPorifle2OnuControlAniTxpowerHighThr }
			STATUS current
			DESCRIPTION
				"setAniTxpowerHighThr"
			::= { sleGponProfile2OnuNotification 29 }


--  1.3.6.1.4.1.6296.101.23.51.12.3.30
		sleGponProfile2OnuAniTxpowerLowThrChanged NOTIFICATION-TYPE
			OBJECTS { sleGponProfile2OnuControlRequest, sleGponProfile2OnuControlTimeStamp, sleGponProfile2OnuControlReqResult, sleGponProfile2OnuIndex, sleGponProfile2OnuControlName,
				sleGponPorifle2OnuControlAniTxpowerLowThr }
			STATUS current
			DESCRIPTION
				"setAniTxpowerLowThr"
			::= { sleGponProfile2OnuNotification 30 }


--  1.3.6.1.4.1.6296.101.23.51.12.3.31
		sleGponProfile2OnuIgmpMaxGroupsChanged NOTIFICATION-TYPE
			OBJECTS { sleGponProfile2OnuControlRequest, sleGponProfile2OnuControlTimeStamp, sleGponProfile2OnuControlReqResult, sleGponProfile2OnuControlName, sleGponProfile2OnuControlIgmpMaxGroups
				 }
			STATUS current
			DESCRIPTION
				"setIgmpMaxGroups"
			::= { sleGponProfile2OnuNotification 31 }


--  1.3.6.1.4.1.6296.101.23.51.12.3.32
		sleGponProfile2OnuIgmpUpRateLimitChanged NOTIFICATION-TYPE
			OBJECTS { sleGponProfile2OnuControlRequest, sleGponProfile2OnuControlTimeStamp, sleGponProfile2OnuControlReqResult, sleGponProfile2OnuControlName, sleGponProfile2OnuControlIgmpUpRateLimit
				 }
			STATUS current
			DESCRIPTION
				"setIgmpUpRateLimit"
			::= { sleGponProfile2OnuNotification 32 }


--  1.3.6.1.4.1.6296.101.23.51.12.3.33
		sleGponProfile2OnuIgmpHostTrackingChanged NOTIFICATION-TYPE
			OBJECTS { sleGponProfile2OnuControlRequest, sleGponProfile2OnuControlTimeStamp, sleGponProfile2OnuControlReqResult, sleGponProfile2OnuControlName, sleGponProfile2OnuControlIgmpHostTracking
				 }
			STATUS current
			DESCRIPTION
				"setIgmpHostTracking"
			::= { sleGponProfile2OnuNotification 33 }


--  1.3.6.1.4.1.6296.101.23.51.12.3.34
		sleGponProfile2OnuMacFullPolicyChanged NOTIFICATION-TYPE
			OBJECTS { sleGponProfile2OnuControlRequest, sleGponProfile2OnuControlTimeStamp, sleGponProfile2OnuControlReqResult, sleGponProfile2OnuControlName, sleGponProfile2OnuControlMacFullPolicy
				 }
			STATUS current
			DESCRIPTION
				"setMacFullPolicy"
			::= { sleGponProfile2OnuNotification 34 }


--  1.3.6.1.4.1.6296.101.23.51.12.3.35
		sleGponProfile2OnuCpuPacketLimitBroadcastChanged NOTIFICATION-TYPE
			OBJECTS { sleGponProfile2OnuControlRequest, sleGponProfile2OnuControlTimeStamp, sleGponProfile2OnuControlReqResult, sleGponProfile2OnuControlName, sleGponProfile2OnuControlCpuPacketLimitBroadcast
				 }
			STATUS current
			DESCRIPTION
				"setCpuPacketLimitBroadcast"
			::= { sleGponProfile2OnuNotification 35 }


--  1.3.6.1.4.1.6296.101.23.51.12.3.36
		sleGponProfile2OnuCpuPacketLimitMulticastChanged NOTIFICATION-TYPE
			OBJECTS { sleGponProfile2OnuControlRequest, sleGponProfile2OnuControlTimeStamp, sleGponProfile2OnuControlReqResult, sleGponProfile2OnuControlName, sleGponProfile2OnuControlCpuPacketLimitMulticast
				 }
			STATUS current
			DESCRIPTION
				"setOnuCpuPacketLimitMulticast"
			::= { sleGponProfile2OnuNotification 36 }


--  1.3.6.1.4.1.6296.101.23.51.12.3.37
		sleGponProfile2OnuCpuPacketLimitDlfChanged NOTIFICATION-TYPE
			OBJECTS { sleGponProfile2OnuControlRequest, sleGponProfile2OnuControlTimeStamp, sleGponProfile2OnuControlReqResult, sleGponProfile2OnuControlName, sleGponProfile2OnuControlCpuPacketLimitDlf
				 }
			STATUS current
			DESCRIPTION
				"setOnuCpuPacketLimitDlf"
			::= { sleGponProfile2OnuNotification 37 }


--  1.3.6.1.4.1.6296.101.23.51.12.3.38
		sleGponProfile2OnuRateLimitDownstreamChanged NOTIFICATION-TYPE
			OBJECTS { sleGponProfile2OnuControlRequest, sleGponProfile2OnuControlTimeStamp, sleGponProfile2OnuControlReqResult, sleGponProfile2OnuControlName, sleGponProfile2OnuControlRateLimitDownstream
				 }
			STATUS current
			DESCRIPTION
				"setRateLimitDownstream "
			::= { sleGponProfile2OnuNotification 38 }


--  1.3.6.1.4.1.6296.101.23.51.12.3.39
		sleGponProfile2OnuTrapToCpuDlfChanged NOTIFICATION-TYPE
			OBJECTS { sleGponProfile2OnuControlRequest, sleGponProfile2OnuControlTimeStamp, sleGponProfile2OnuControlReqResult, sleGponProfile2OnuControlName, sleGponProfile2OnuControlTrapToCpuDlf
				 }
			STATUS current
			DESCRIPTION
				"setTrapToCpuDlf"
			::= { sleGponProfile2OnuNotification 39 }


--  1.3.6.1.4.1.6296.101.23.51.12.3.40
		sleGponProfile2OnuIpPathStatusChanged NOTIFICATION-TYPE
			OBJECTS { sleGponProfile2OnuControlRequest, sleGponProfile2OnuControlTimeStamp, sleGponProfile2OnuControlReqResult, sleGponProfile2OnuControlMgmtIpPathStatus }
			STATUS current
			DESCRIPTION
				" "
			::= { sleGponProfile2OnuNotification 40 }


--  1.3.6.1.4.1.6296.101.23.51.12.3.41
		sleGponProfile2OnuIpPathProtocolChanged NOTIFICATION-TYPE
			OBJECTS { sleGponProfile2OnuControlRequest, sleGponProfile2OnuControlTimeStamp, sleGponProfile2OnuControlReqResult, sleGponProfile2OnuControlMgmtIpPathProtocol, sleGponProfile2OnuControlMgmtIpPathId,
				sleGponProfile2OnuControlMgmtIpPathPassword }
			STATUS current
			DESCRIPTION
				" "
			::= { sleGponProfile2OnuNotification 41 }


--  1.3.6.1.4.1.6296.101.23.51.12.3.42
		sleGponProfile2OnuIpPathInfoChanged NOTIFICATION-TYPE
			OBJECTS { sleGponProfile2OnuControlRequest, sleGponProfile2OnuControlTimeStamp, sleGponProfile2OnuControlReqResult, sleGponProfile2OnuControlMgmtIpPathUrl, sleGponProfile2OnuControlMgmtIpPathFilename
				 }
			STATUS current
			DESCRIPTION
				" "
			::= { sleGponProfile2OnuNotification 42 }


--  1.3.6.1.4.1.6296.101.23.51.12.3.43
		sleGponProfile2OnuIpPathCleared NOTIFICATION-TYPE
			OBJECTS { sleGponProfile2OnuControlRequest, sleGponProfile2OnuControlTimeStamp, sleGponProfile2OnuControlReqResult }
			STATUS current
			DESCRIPTION
				" "
			::= { sleGponProfile2OnuNotification 43 }


--  1.3.6.1.4.1.6296.101.23.51.12.3.43
		sleGponProfile2OnuGspChanged NOTIFICATION-TYPE
			OBJECTS { sleGponProfile2OnuControlRequest, sleGponProfile2OnuControlTimeStamp, sleGponProfile2OnuControlReqResult, sleGponProfile2DbaControlRequest, sleGponProfile2OnuControlName,
				sleGponProfile2OnuControlGsp, sleGponProfile2OnuControlGspAvcReportRate }
			STATUS current
			DESCRIPTION
				"setGsp"
			::= { sleGponProfile2OnuNotification 44 }


		sleGponProfile2OnuSnmpRoCommunityChanged NOTIFICATION-TYPE
			OBJECTS { sleGponProfile2OnuControlRequest, sleGponProfile2OnuControlTimeStamp, sleGponProfile2OnuControlReqResult, sleGponProfile2OnuControlName, sleGponProfile2OnuControlSnmpROCommunity
				 }
			STATUS current
			DESCRIPTION
				"setSnmpRoCommunity"
			::= { sleGponProfile2OnuNotification 45 }


		sleGponProfile2OnuSnmpRwCommunityChanged NOTIFICATION-TYPE
			OBJECTS { sleGponProfile2OnuControlRequest, sleGponProfile2OnuControlTimeStamp, sleGponProfile2OnuControlReqResult, sleGponProfile2OnuControlName, sleGponProfile2OnuControlSnmpRWCommunity
				 }
			STATUS current
			DESCRIPTION
				"setSnmpRwCommunity"
			::= { sleGponProfile2OnuNotification 46 }


		sleGponProfile2OnuSnmpSecurityNameChanged NOTIFICATION-TYPE
			OBJECTS { sleGponProfile2OnuControlRequest, sleGponProfile2OnuControlTimeStamp, sleGponProfile2OnuControlReqResult, sleGponProfile2OnuControlName, sleGponProfile2OnuControlSnmpSecurityName
				 }
			STATUS current
			DESCRIPTION
				"setSnmpSecurityName "
			::= { sleGponProfile2OnuNotification 47 }


		sleGponProfile2OnuSnmpAgentAddressChanged NOTIFICATION-TYPE
			OBJECTS { sleGponProfile2OnuControlRequest, sleGponProfile2OnuControlTimeStamp, sleGponProfile2OnuControlReqResult, sleGponProfile2OnuControlName, sleGponProfile2OnuControlSnmpAgentAddresHost
				 }
			STATUS current
			DESCRIPTION
				"setSnmpAgentAddress"
			::= { sleGponProfile2OnuNotification 48 }


		sleGponProfile2OnuSnmpTrapHostChanged NOTIFICATION-TYPE
			OBJECTS { sleGponProfile2OnuControlRequest, sleGponProfile2OnuControlTimeStamp, sleGponProfile2OnuControlReqResult, sleGponProfile2OnuControlName, sleGponProfile2OnuControlSnmpTrapHostAddress,
				sleGponProfile2OnuControlSnmpTrapHostPort }
			STATUS current
			DESCRIPTION
				"setSnmpTrapHost"
			::= { sleGponProfile2OnuNotification 49 }


		sleGponProfile2OnuSnmpSysNameChanged NOTIFICATION-TYPE
			OBJECTS { sleGponProfile2OnuControlRequest, sleGponProfile2OnuControlTimeStamp, sleGponProfile2OnuControlReqResult, sleGponProfile2OnuControlName, sleGponProfile2OnuControlSnmpSysName
				 }
			STATUS current
			DESCRIPTION
				"setSnmpSysName"
			::= { sleGponProfile2OnuNotification 50 }


--   1.3.6.1.4.1.6296.101.23.51.13
-- 1.3.6.1.4.1.6296.101.23.51.13
		sleGponProfile2OnuUni OBJECT IDENTIFIER ::= { sleGponProfile2 13 }


--   1.3.6.1.4.1.6296.101.23.51.13.1
-- 1.3.6.1.4.1.6296.101.23.51.13.1
		sleGponProfile2OnuUniTable OBJECT-TYPE
			SYNTAX SEQUENCE OF SleGponProfile2OnuUniEntry
			MAX-ACCESS not-accessible
			STATUS current
			DESCRIPTION
				"sleGponProfile2OnuUniTable"
			::= { sleGponProfile2OnuUni 1 }


--   1.3.6.1.4.1.6296.101.23.51.13.1.1
-- 1.3.6.1.4.1.6296.101.23.51.13.1.1
		sleGponProfile2OnuUniEntry OBJECT-TYPE
			SYNTAX SleGponProfile2OnuUniEntry
			MAX-ACCESS not-accessible
			STATUS current
			DESCRIPTION
				"key: sleGponProfile2OnuIndex, sleGponProfile2OnuUniId, sleGponProfile2OnuUniType"
			INDEX { sleGponProfile2OnuIndex, sleGponProfile2OnuUniId, sleGponProfile2OnuUniType }
			::= { sleGponProfile2OnuUniTable 1 }


		SleGponProfile2OnuUniEntry ::=
			SEQUENCE {
				sleGponProfile2OnuUniId
					Integer32,
				sleGponProfile2OnuUniType
					INTEGER,
				sleGponProfile2OnuUniDownSir
					Integer32,
				sleGponProfile2OnuUniDownPir
					Integer32,
				sleGponProfile2OnuUniVlanDsOper
					INTEGER,
				sleGponProfile2OnuUniVlanUSOper
					INTEGER,
				sleGponProfile2OnuUniVlanUsOperVID
					Integer32,
				sleGponProfile2OnuUniVlanUsOperCoS
					Integer32,
				sleGponProfile2OnuUniIgmpMaxGroup
					Integer32,
				sleGponProfile2OnuUniPortAdmin
					INTEGER
			 }

--   1.3.6.1.4.1.6296.101.23.51.13.1.1.1
-- 1.3.6.1.4.1.6296.101.23.51.13.1.1.1
		sleGponProfile2OnuUniId OBJECT-TYPE
			SYNTAX Integer32 (1..65535)
			MAX-ACCESS read-only
			STATUS current
			DESCRIPTION
				"The UNI configuration : UNI Id
				"
			::= { sleGponProfile2OnuUniEntry 1 }


--   1.3.6.1.4.1.6296.101.23.51.13.1.1.2
-- 1.3.6.1.4.1.6296.101.23.51.13.1.1.2
		sleGponProfile2OnuUniType OBJECT-TYPE
			SYNTAX INTEGER { eth(1) }
			MAX-ACCESS read-only
			STATUS current
			DESCRIPTION
				"The UNI configuration : UNI type
				"
			::= { sleGponProfile2OnuUniEntry 2 }


--   1.3.6.1.4.1.6296.101.23.51.13.1.1.3
-- 1.3.6.1.4.1.6296.101.23.51.13.1.1.3
		sleGponProfile2OnuUniDownSir OBJECT-TYPE
			SYNTAX Integer32
			MAX-ACCESS read-only
			STATUS current
			DESCRIPTION
				"The UNI configuration : rate-limit downstream SIR
				"
			::= { sleGponProfile2OnuUniEntry 3 }


--   1.3.6.1.4.1.6296.101.23.51.13.1.1.4
-- 1.3.6.1.4.1.6296.101.23.51.13.1.1.4
		sleGponProfile2OnuUniDownPir OBJECT-TYPE
			SYNTAX Integer32
			MAX-ACCESS read-only
			STATUS current
			DESCRIPTION
				"The UNI configuration : rate-limit downstream PIR
				"
			::= { sleGponProfile2OnuUniEntry 4 }


--   1.3.6.1.4.1.6296.101.23.51.13.1.1.5
-- 1.3.6.1.4.1.6296.101.23.51.13.1.1.5
		sleGponProfile2OnuUniVlanDsOper OBJECT-TYPE
			SYNTAX INTEGER
				{
				keep(1),
				overwrite(2),
				add(3),
				remove(4),
				unused(255)
				}
			MAX-ACCESS read-only
			STATUS current
			DESCRIPTION
				" VLAN Tagging Operation Data : DS VLAN Tagging Operation mode"
			::= { sleGponProfile2OnuUniEntry 5 }


--   1.3.6.1.4.1.6296.101.23.51.13.1.1.6
-- 1.3.6.1.4.1.6296.101.23.51.13.1.1.6
		sleGponProfile2OnuUniVlanUSOper OBJECT-TYPE
			SYNTAX INTEGER
				{
				keep(1),
				overwrite(2),
				add(3),
				unused(255)
				}
			MAX-ACCESS read-only
			STATUS current
			DESCRIPTION
				" VLAN Tagging Operation Data : US VLAN Tagging Operation mode"
			::= { sleGponProfile2OnuUniEntry 6 }


--   1.3.6.1.4.1.6296.101.23.51.13.1.1.7
-- 1.3.6.1.4.1.6296.101.23.51.13.1.1.7
		sleGponProfile2OnuUniVlanUsOperVID OBJECT-TYPE
			SYNTAX Integer32 (0 | 1..4096)
			MAX-ACCESS read-only
			STATUS current
			DESCRIPTION
				"US VLAN tag VID value"
			::= { sleGponProfile2OnuUniEntry 7 }


--   1.3.6.1.4.1.6296.101.23.51.13.1.1.8
-- 1.3.6.1.4.1.6296.101.23.51.13.1.1.8
		sleGponProfile2OnuUniVlanUsOperCoS OBJECT-TYPE
			SYNTAX Integer32 (-1 | 0..7)
			MAX-ACCESS read-only
			STATUS current
			DESCRIPTION
				" US VLAN tag COS value"
			::= { sleGponProfile2OnuUniEntry 8 }


--   1.3.6.1.4.1.6296.101.23.51.13.1.1.9
-- 1.3.6.1.4.1.6296.101.23.51.13.1.1.9
		sleGponProfile2OnuUniIgmpMaxGroup OBJECT-TYPE
			SYNTAX Integer32 (-1 | 0..255)
			MAX-ACCESS read-only
			STATUS current
			DESCRIPTION
				"The maximum number of IGMP groups"
			::= { sleGponProfile2OnuUniEntry 9 }


--   1.3.6.1.4.1.6296.101.23.51.13.1.1.10
-- 1.3.6.1.4.1.6296.101.23.51.13.1.1.10
		sleGponProfile2OnuUniPortAdmin OBJECT-TYPE
			SYNTAX INTEGER
				{
				enable(1),
				disable(2),
				unknown(255)
				}
			MAX-ACCESS read-only
			STATUS current
			DESCRIPTION
				"The port's admin-status."
			::= { sleGponProfile2OnuUniEntry 10 }


--   1.3.6.1.4.1.6296.101.23.51.13.2
-- 1.3.6.1.4.1.6296.101.23.51.13.2
		sleGponProfile2OnuUniControl OBJECT IDENTIFIER ::= { sleGponProfile2OnuUni 2 }


--   1.3.6.1.4.1.6296.101.23.51.13.2.1
-- 1.3.6.1.4.1.6296.101.23.51.13.2.1
		sleGponProfile2OnuUniControlRequest OBJECT-TYPE
			SYNTAX INTEGER
				{
				setUniRateLimit(1),
				setUniVlanDsOper(2),
				setUniVlanUsOper(3),
				setUniIgmpMaxGroup(4),
				setUniPortAdmin(5)
				}
			MAX-ACCESS read-write
			STATUS current
			DESCRIPTION
				"The request of a user command"
			::= { sleGponProfile2OnuUniControl 1 }


--   1.3.6.1.4.1.6296.101.23.51.13.2.2
-- 1.3.6.1.4.1.6296.101.23.51.13.2.2
		sleGponProfile2OnuUniControlStatus OBJECT-TYPE
			SYNTAX SleControlStatusType
			MAX-ACCESS read-only
			STATUS current
			DESCRIPTION
				"The status of user command"
			::= { sleGponProfile2OnuUniControl 2 }


--   1.3.6.1.4.1.6296.101.23.51.13.2.3
-- 1.3.6.1.4.1.6296.101.23.51.13.2.3
		sleGponProfile2OnuUniControlTimer OBJECT-TYPE
			SYNTAX Gauge32
			MAX-ACCESS read-write
			STATUS current
			DESCRIPTION
				"The maximum time for the manager for a long running user command"
			::= { sleGponProfile2OnuUniControl 3 }


--   1.3.6.1.4.1.6296.101.23.51.13.2.4
-- 1.3.6.1.4.1.6296.101.23.51.13.2.4
		sleGponProfile2OnuUniControlTimeStamp OBJECT-TYPE
			SYNTAX TimeTicks
			MAX-ACCESS read-only
			STATUS current
			DESCRIPTION
				"The time stamp of the last command(end of command)"
			::= { sleGponProfile2OnuUniControl 4 }


--   1.3.6.1.4.1.6296.101.23.51.13.2.5
-- 1.3.6.1.4.1.6296.101.23.51.13.2.5
		sleGponProfile2OnuUniControlReqResult OBJECT-TYPE
			SYNTAX SleControlRequestResultType
			MAX-ACCESS read-only
			STATUS current
			DESCRIPTION
				"The result of the last user command"
			::= { sleGponProfile2OnuUniControl 5 }


--   1.3.6.1.4.1.6296.101.23.51.13.2.6
-- 1.3.6.1.4.1.6296.101.23.51.13.2.6
		sleGponProfile2OnuUniControlOnuProfile OBJECT-TYPE
			SYNTAX OCTET STRING
			MAX-ACCESS read-write
			STATUS current
			DESCRIPTION
				"The ONU profile name"
			::= { sleGponProfile2OnuUniControl 6 }


--   1.3.6.1.4.1.6296.101.23.51.13.2.7
-- 1.3.6.1.4.1.6296.101.23.51.13.2.7
		sleGponProfile2OnuUniControlId OBJECT-TYPE
			SYNTAX Integer32
			MAX-ACCESS read-write
			STATUS current
			DESCRIPTION
				"The UNI configuration : UNI Id"
			::= { sleGponProfile2OnuUniControl 7 }


--   1.3.6.1.4.1.6296.101.23.51.13.2.8
-- 1.3.6.1.4.1.6296.101.23.51.13.2.8
		sleGponProfile2OnuUniControlType OBJECT-TYPE
			SYNTAX INTEGER { eth(1) }
			MAX-ACCESS read-write
			STATUS current
			DESCRIPTION
				"The UNI configuration : UNI type"
			::= { sleGponProfile2OnuUniControl 8 }


--   1.3.6.1.4.1.6296.101.23.51.13.2.9
-- 1.3.6.1.4.1.6296.101.23.51.13.2.9
		sleGponProfile2OnuUniControlDownSir OBJECT-TYPE
			SYNTAX Integer32
			MAX-ACCESS read-write
			STATUS current
			DESCRIPTION
				"The UNI configuration : rate-limit downstream SIR
				"
			::= { sleGponProfile2OnuUniControl 9 }


--   1.3.6.1.4.1.6296.101.23.51.13.2.10
-- 1.3.6.1.4.1.6296.101.23.51.13.2.10
		sleGponProfile2OnuUniControlDownPir OBJECT-TYPE
			SYNTAX Integer32
			MAX-ACCESS read-write
			STATUS current
			DESCRIPTION
				"The UNI configuration : rate-limit downstream PIR"
			::= { sleGponProfile2OnuUniControl 10 }


--   1.3.6.1.4.1.6296.101.23.51.13.2.11
-- 1.3.6.1.4.1.6296.101.23.51.13.2.11
		sleGponProfile2OnuUniControlVlanDsOper OBJECT-TYPE
			SYNTAX INTEGER
				{
				keep(1),
				overwrite(2),
				add(3),
				remove(4),
				unused(255)
				}
			MAX-ACCESS read-write
			STATUS current
			DESCRIPTION
				" VLAN Tagging Operation Data : DS VLAN Tagging Operation mode"
			::= { sleGponProfile2OnuUniControl 11 }


--   1.3.6.1.4.1.6296.101.23.51.13.2.12
-- 1.3.6.1.4.1.6296.101.23.51.13.2.12
		sleGponProfile2OnuUniControlVlanUsOper OBJECT-TYPE
			SYNTAX INTEGER
				{
				keep(1),
				overwrite(2),
				add(3),
				unused(255)
				}
			MAX-ACCESS read-write
			STATUS current
			DESCRIPTION
				" VLAN Tagging Operation Data : US VLAN Tagging Operation mode"
			::= { sleGponProfile2OnuUniControl 12 }


--   1.3.6.1.4.1.6296.101.23.51.13.2.13
-- 1.3.6.1.4.1.6296.101.23.51.13.2.13
		sleGponProfile2OnuUniControlVlanUsOperVID OBJECT-TYPE
			SYNTAX Integer32 (0 | 1..4096)
			MAX-ACCESS read-write
			STATUS current
			DESCRIPTION
				"US VLAN tag VID value"
			::= { sleGponProfile2OnuUniControl 13 }


--   1.3.6.1.4.1.6296.101.23.51.13.2.14
-- 1.3.6.1.4.1.6296.101.23.51.13.2.14
		sleGponProfile2OnuUniControlVlanUsOperCoS OBJECT-TYPE
			SYNTAX Integer32 (-1 | 0..7)
			MAX-ACCESS read-write
			STATUS current
			DESCRIPTION
				" US VLAN tag COS value"
			::= { sleGponProfile2OnuUniControl 14 }


--   1.3.6.1.4.1.6296.101.23.51.13.2.15
-- 1.3.6.1.4.1.6296.101.23.51.13.2.15
		sleGponProfile2OnuUniControlIgmpMaxGroup OBJECT-TYPE
			SYNTAX Integer32 (-1 | 0..255)
			MAX-ACCESS read-write
			STATUS current
			DESCRIPTION
				"The maximum number of IGMP groups"
			::= { sleGponProfile2OnuUniControl 15 }


--   1.3.6.1.4.1.6296.101.23.51.13.2.16
-- 1.3.6.1.4.1.6296.101.23.51.13.2.16
		sleGponProfile2OnuUniControlPortAdmin OBJECT-TYPE
			SYNTAX INTEGER
				{
				enable(1),
				disable(2),
				unknown(3)
				}
			MAX-ACCESS read-write
			STATUS current
			DESCRIPTION
				"The port's admin-status."
			::= { sleGponProfile2OnuUniControl 16 }


--   1.3.6.1.4.1.6296.101.23.51.13.3
-- 1.3.6.1.4.1.6296.101.23.51.13.3
		sleGponProfile2OnuUniNotification OBJECT IDENTIFIER ::= { sleGponProfile2OnuUni 3 }


--   1.3.6.1.4.1.6296.101.23.51.13.3.1
-- 1.3.6.1.4.1.6296.101.23.51.13.3.1
		sleGponProfile2OnuUniRateLimitChanged NOTIFICATION-TYPE
			OBJECTS { sleGponProfile2OnuUniControlRequest, sleGponProfile2OnuUniControlTimeStamp, sleGponProfile2OnuUniControlReqResult, sleGponProfile2OnuUniControlOnuProfile, sleGponProfile2OnuUniControlId,
				sleGponProfile2OnuUniControlType, sleGponProfile2OnuUniControlDownSir, sleGponProfile2OnuUniControlDownPir }
			STATUS current
			DESCRIPTION
				"Description."
			::= { sleGponProfile2OnuUniNotification 1 }


--   1.3.6.1.4.1.6296.101.23.51.13.3.2
-- 1.3.6.1.4.1.6296.101.23.51.13.3.2
		sleGponProfile2OnuUniVlanDsOperChanged NOTIFICATION-TYPE
			OBJECTS { sleGponProfile2OnuUniControlRequest, sleGponProfile2OnuUniControlTimeStamp, sleGponProfile2OnuUniControlReqResult, sleGponProfile2OnuUniControlOnuProfile, sleGponProfile2OnuUniControlId,
				sleGponProfile2OnuUniControlType, sleGponProfile2OnuUniControlVlanDsOper }
			STATUS current
			DESCRIPTION
				"Description."
			::= { sleGponProfile2OnuUniNotification 2 }


--   1.3.6.1.4.1.6296.101.23.51.13.3.3
-- 1.3.6.1.4.1.6296.101.23.51.13.3.3
		sleGponProfile2OnuUniVlanUsOperChanged NOTIFICATION-TYPE
			OBJECTS { sleGponProfile2OnuUniControlRequest, sleGponProfile2OnuUniControlTimeStamp, sleGponProfile2OnuUniControlReqResult, sleGponProfile2OnuUniControlOnuProfile, sleGponProfile2OnuUniControlId,
				sleGponProfile2OnuUniControlType, sleGponProfile2OnuUniControlVlanUsOper, sleGponProfile2OnuUniControlVlanUsOperVID, sleGponProfile2OnuUniControlVlanUsOperCoS }
			STATUS current
			DESCRIPTION
				"Description."
			::= { sleGponProfile2OnuUniNotification 3 }


--   1.3.6.1.4.1.6296.101.23.51.13.3.4
-- 1.3.6.1.4.1.6296.101.23.51.13.3.4
		sleGponProfile2OnuUniIgmpMaxGroupChanged NOTIFICATION-TYPE
			OBJECTS { sleGponProfile2OnuUniControlRequest, sleGponProfile2OnuUniControlTimeStamp, sleGponProfile2OnuUniControlReqResult, sleGponProfile2OnuUniControlOnuProfile, sleGponProfile2OnuUniControlId,
				sleGponProfile2OnuUniControlType, sleGponProfile2OnuUniControlIgmpMaxGroup }
			STATUS current
			DESCRIPTION
				"Description."
			::= { sleGponProfile2OnuUniNotification 4 }


--   1.3.6.1.4.1.6296.101.23.51.13.3.5
-- 1.3.6.1.4.1.6296.101.23.51.13.3.5
		sleGponProfile2OnuUniPortAdminChanged NOTIFICATION-TYPE
			OBJECTS { sleGponProfile2OnuUniControlStatus, sleGponProfile2OnuUniControlTimeStamp, sleGponProfile2OnuUniControlReqResult, sleGponProfile2OnuUniControlOnuProfile, sleGponProfile2OnuUniControlId,
				sleGponProfile2OnuUniControlType, sleGponProfile2OnuUniControlPortAdmin }
			STATUS current
			DESCRIPTION
				"Description."
			::= { sleGponProfile2OnuUniNotification 5 }


--   1.3.6.1.4.1.6296.101.23.51.14
-- 1.3.6.1.4.1.6296.101.23.51.14
		sleGponProfile2PM OBJECT IDENTIFIER ::= { sleGponProfile2 14 }


--   1.3.6.1.4.1.6296.101.23.51.14.1
-- 1.3.6.1.4.1.6296.101.23.51.14.1
		sleGponProfile2PMProfileTable OBJECT-TYPE
			SYNTAX SEQUENCE OF SleGponProfile2PMProfileEntry
			MAX-ACCESS not-accessible
			STATUS current
			DESCRIPTION
				"sleGponProfile2PMProfileTable"
			::= { sleGponProfile2PM 1 }


--   1.3.6.1.4.1.6296.101.23.51.14.1.1
-- 1.3.6.1.4.1.6296.101.23.51.14.1.1
		sleGponProfile2PMProfileEntry OBJECT-TYPE
			SYNTAX SleGponProfile2PMProfileEntry
			MAX-ACCESS not-accessible
			STATUS current
			DESCRIPTION
				"key: sleGponProfile2PMProfileIndex"
			INDEX { sleGponProfile2PMProfileIndex }
			::= { sleGponProfile2PMProfileTable 1 }


		SleGponProfile2PMProfileEntry ::=
			SEQUENCE {
				sleGponProfile2PMProfileIndex
					Integer32,
				sleGponProfile2PMProfileName
					OCTET STRING,
				sleGponProfile2PMProfilePMGemPort
					EnableFlag,
				sleGponProfile2PMProfilePMAniPort
					EnableFlag,
				sleGponProfile2PMProfilePMUniEthFrameUp
					EnableFlag,
				sleGponProfile2PMProfilePMUniEthFrameDown
					EnableFlag,
				sleGponProfile2PMProfilePMUniEth3
					EnableFlag,
				sleGponProfile2PMProfilePMPseduowire
					EnableFlag,
				sleGponProfile2PMProfilePMUniCes
					EnableFlag,
				sleGponProfile2PMProfilePMGemNCTP
					EnableFlag
			 }

--   1.3.6.1.4.1.6296.101.23.51.14.1.1.1
-- 1.3.6.1.4.1.6296.101.23.51.14.1.1.1
		sleGponProfile2PMProfileIndex OBJECT-TYPE
			SYNTAX Integer32 (1..65535)
			MAX-ACCESS read-only
			STATUS current
			DESCRIPTION
				"The PM profile Index"
			::= { sleGponProfile2PMProfileEntry 1 }


--   1.3.6.1.4.1.6296.101.23.51.14.1.1.2
-- 1.3.6.1.4.1.6296.101.23.51.14.1.1.2
		sleGponProfile2PMProfileName OBJECT-TYPE
			SYNTAX OCTET STRING
			MAX-ACCESS read-only
			STATUS current
			DESCRIPTION
				"The Performace Monitoring profile name.
				"
			::= { sleGponProfile2PMProfileEntry 2 }


--   1.3.6.1.4.1.6296.101.23.51.14.1.1.3
-- 1.3.6.1.4.1.6296.101.23.51.14.1.1.3
		sleGponProfile2PMProfilePMGemPort OBJECT-TYPE
			SYNTAX EnableFlag
			MAX-ACCESS read-only
			STATUS current
			DESCRIPTION
				"The Gemport block counter : enable|disable
				"
			::= { sleGponProfile2PMProfileEntry 3 }


--   1.3.6.1.4.1.6296.101.23.51.14.1.1.4
-- 1.3.6.1.4.1.6296.101.23.51.14.1.1.4
		sleGponProfile2PMProfilePMAniPort OBJECT-TYPE
			SYNTAX EnableFlag
			MAX-ACCESS read-only
			STATUS current
			DESCRIPTION
				"The ANI port counter : enable|disable
				"
			::= { sleGponProfile2PMProfileEntry 4 }


--   1.3.6.1.4.1.6296.101.23.51.14.1.1.5
-- 1.3.6.1.4.1.6296.101.23.51.14.1.1.5
		sleGponProfile2PMProfilePMUniEthFrameUp OBJECT-TYPE
			SYNTAX EnableFlag
			MAX-ACCESS read-only
			STATUS current
			DESCRIPTION
				"The Performace Monitoring: UNI Ethernet frame up"
			::= { sleGponProfile2PMProfileEntry 5 }


--   1.3.6.1.4.1.6296.101.23.51.14.1.1.6
-- 1.3.6.1.4.1.6296.101.23.51.14.1.1.6
		sleGponProfile2PMProfilePMUniEthFrameDown OBJECT-TYPE
			SYNTAX EnableFlag
			MAX-ACCESS read-only
			STATUS current
			DESCRIPTION
				"The Performace Monitoring: UNI Ethernet frame down"
			::= { sleGponProfile2PMProfileEntry 6 }


--   1.3.6.1.4.1.6296.101.23.51.14.1.1.7
-- 1.3.6.1.4.1.6296.101.23.51.14.1.1.7
		sleGponProfile2PMProfilePMUniEth3 OBJECT-TYPE
			SYNTAX EnableFlag
			MAX-ACCESS read-only
			STATUS current
			DESCRIPTION
				"The Performace Monitoring: UNI Ethernet 3 flag"
			::= { sleGponProfile2PMProfileEntry 7 }


--  1.3.6.1.4.1.6296.101.23.51.14.1.1.8
		sleGponProfile2PMProfilePMPseduowire OBJECT-TYPE
			SYNTAX EnableFlag
			MAX-ACCESS read-only
			STATUS current
			DESCRIPTION
				"The Pseudowire PM history data counter"
			::= { sleGponProfile2PMProfileEntry 8 }


--  1.3.6.1.4.1.6296.101.23.51.14.1.1.9
		sleGponProfile2PMProfilePMUniCes OBJECT-TYPE
			SYNTAX EnableFlag
			MAX-ACCESS read-only
			STATUS current
			DESCRIPTION
				"Thr UNI CES PM history data counter"
			::= { sleGponProfile2PMProfileEntry 9 }


--  1.3.6.1.4.1.6296.101.23.51.14.1.1.10
		sleGponProfile2PMProfilePMGemNCTP OBJECT-TYPE
			SYNTAX EnableFlag
			MAX-ACCESS read-only
			STATUS current
			DESCRIPTION
				"Thr UNI CES PM history data counter"
			::= { sleGponProfile2PMProfileEntry 10 }


--   1.3.6.1.4.1.6296.101.23.51.14.2
-- 1.3.6.1.4.1.6296.101.23.51.14.2
		sleGponProfile2PMProfileControl OBJECT IDENTIFIER ::= { sleGponProfile2PM 2 }


--   1.3.6.1.4.1.6296.101.23.51.14.2.1
-- 1.3.6.1.4.1.6296.101.23.51.14.2.1
		sleGponProfile2PMProfileControlRequest OBJECT-TYPE
			SYNTAX INTEGER
				{
				addPmProfile(1),
				delPmProfile(2),
				updatePmProfile(3)
				}
			MAX-ACCESS read-write
			STATUS current
			DESCRIPTION
				"The request of a user command"
			::= { sleGponProfile2PMProfileControl 1 }


--   1.3.6.1.4.1.6296.101.23.51.14.2.2
-- 1.3.6.1.4.1.6296.101.23.51.14.2.2
		sleGponProfile2PMProfileControlStatus OBJECT-TYPE
			SYNTAX SleControlStatusType
			MAX-ACCESS read-only
			STATUS current
			DESCRIPTION
				"The status of user command"
			::= { sleGponProfile2PMProfileControl 2 }


--   1.3.6.1.4.1.6296.101.23.51.14.2.3
-- 1.3.6.1.4.1.6296.101.23.51.14.2.3
		sleGponProfile2PMProfileControlTimer OBJECT-TYPE
			SYNTAX Gauge32
			MAX-ACCESS read-write
			STATUS current
			DESCRIPTION
				"The maximum time for the manager for a long running user command"
			::= { sleGponProfile2PMProfileControl 3 }


--   1.3.6.1.4.1.6296.101.23.51.14.2.4
-- 1.3.6.1.4.1.6296.101.23.51.14.2.4
		sleGponProfile2PMProfileControlTimeStamp OBJECT-TYPE
			SYNTAX TimeTicks
			MAX-ACCESS read-only
			STATUS current
			DESCRIPTION
				"The time stamp of the last command(end of command)"
			::= { sleGponProfile2PMProfileControl 4 }


--   1.3.6.1.4.1.6296.101.23.51.14.2.5
-- 1.3.6.1.4.1.6296.101.23.51.14.2.5
		sleGponProfile2PMProfileControlReqResult OBJECT-TYPE
			SYNTAX SleControlRequestResultType
			MAX-ACCESS read-only
			STATUS current
			DESCRIPTION
				"The result of the last user command
				"
			::= { sleGponProfile2PMProfileControl 5 }


--   1.3.6.1.4.1.6296.101.23.51.14.2.6
-- 1.3.6.1.4.1.6296.101.23.51.14.2.6
		sleGponProfile2PMProfileControlName OBJECT-TYPE
			SYNTAX OCTET STRING
			MAX-ACCESS read-write
			STATUS current
			DESCRIPTION
				"The Performace Monitoring profile name.
				"
			::= { sleGponProfile2PMProfileControl 6 }


--   1.3.6.1.4.1.6296.101.23.51.14.2.7
-- 1.3.6.1.4.1.6296.101.23.51.14.2.7
		sleGponProfile2PMProfileControlPMGemPort OBJECT-TYPE
			SYNTAX EnableFlag
			MAX-ACCESS read-write
			STATUS current
			DESCRIPTION
				"The Gemport block counter : enable|disable"
			::= { sleGponProfile2PMProfileControl 7 }


--   1.3.6.1.4.1.6296.101.23.51.14.2.8
-- 1.3.6.1.4.1.6296.101.23.51.14.2.8
		sleGponProfile2PMProfileControlPMAniPort OBJECT-TYPE
			SYNTAX EnableFlag
			MAX-ACCESS read-write
			STATUS current
			DESCRIPTION
				"The ANI port counter : enable|disable
				"
			::= { sleGponProfile2PMProfileControl 8 }


--   1.3.6.1.4.1.6296.101.23.51.14.2.9
-- 1.3.6.1.4.1.6296.101.23.51.14.2.9
		sleGponProfile2PMProfileControlPMUniEthFrameUp OBJECT-TYPE
			SYNTAX EnableFlag
			MAX-ACCESS read-write
			STATUS current
			DESCRIPTION
				"The Performace Monitoring: UNI Ethernet frame up"
			::= { sleGponProfile2PMProfileControl 9 }


--   1.3.6.1.4.1.6296.101.23.51.14.2.10
-- 1.3.6.1.4.1.6296.101.23.51.14.2.10
		sleGponProfile2PMProfileControlPMUniEthFrameDown OBJECT-TYPE
			SYNTAX EnableFlag
			MAX-ACCESS read-write
			STATUS current
			DESCRIPTION
				"The Performace Monitoring: UNI Ethernet frame down"
			::= { sleGponProfile2PMProfileControl 10 }


--   1.3.6.1.4.1.6296.101.23.51.14.2.11
-- 1.3.6.1.4.1.6296.101.23.51.14.2.11
		sleGponProfile2PMProfileControlPMUniEth3 OBJECT-TYPE
			SYNTAX EnableFlag
			MAX-ACCESS read-write
			STATUS current
			DESCRIPTION
				"The Performace Monitoring: UNI Ethernet 3 flag"
			::= { sleGponProfile2PMProfileControl 11 }


--  1.3.6.1.4.1.6296.101.23.51.14.2.12
		sleGponProfile2PMProfileControlPMPseduowire OBJECT-TYPE
			SYNTAX EnableFlag
			MAX-ACCESS read-write
			STATUS current
			DESCRIPTION
				"The Pseudowire PM history data counter"
			::= { sleGponProfile2PMProfileControl 12 }


--  1.3.6.1.4.1.6296.101.23.51.14.2.13
		sleGponProfile2PMProfileControlPMUniCes OBJECT-TYPE
			SYNTAX EnableFlag
			MAX-ACCESS read-write
			STATUS current
			DESCRIPTION
				"Thr UNI CES PM history data counter"
			::= { sleGponProfile2PMProfileControl 13 }


--  1.3.6.1.4.1.6296.101.23.51.14.2.14
		sleGponProfile2PMProfileControlPMGemNCTP OBJECT-TYPE
			SYNTAX EnableFlag
			MAX-ACCESS read-write
			STATUS current
			DESCRIPTION
				"Thr UNI CES PM history data counter"
			::= { sleGponProfile2PMProfileControl 14 }


--   1.3.6.1.4.1.6296.101.23.51.14.3
-- 1.3.6.1.4.1.6296.101.23.51.14.3
		sleGponProfile2PMProfileNotification OBJECT IDENTIFIER ::= { sleGponProfile2PM 3 }


--   1.3.6.1.4.1.6296.101.23.51.14.3.1
-- 1.3.6.1.4.1.6296.101.23.51.14.3.1
		sleGponProfile2PMProfileAdded NOTIFICATION-TYPE
			OBJECTS { sleGponProfile2PMProfileControlRequest, sleGponProfile2PMProfileControlTimeStamp, sleGponProfile2PMProfileControlReqResult, sleGponProfile2PMProfileControlName, sleGponProfile2PMProfileControlPMGemPort,
				sleGponProfile2PMProfileControlPMAniPort, sleGponProfile2PMProfileControlPMPseduowire, sleGponProfile2PMProfileControlPMUniCes, sleGponProfile2PMProfileControlPMUniEth3, sleGponProfile2PMProfileControlPMUniEthFrameUp,
				sleGponProfile2PMProfileControlPMUniEthFrameDown }
			STATUS current
			DESCRIPTION
				"Description."
			::= { sleGponProfile2PMProfileNotification 1 }


--   1.3.6.1.4.1.6296.101.23.51.14.3.2
-- 1.3.6.1.4.1.6296.101.23.51.14.3.2
		sleGponProfile2PMProfileDeleted NOTIFICATION-TYPE
			OBJECTS { sleGponProfile2PMProfileControlRequest, sleGponProfile2PMProfileControlTimeStamp, sleGponProfile2PMProfileControlReqResult, sleGponProfile2PMProfileControlName }
			STATUS current
			DESCRIPTION
				"Description."
			::= { sleGponProfile2PMProfileNotification 2 }


--  1.3.6.1.4.1.6296.101.23.51.14.3.3
		sleGponProfile2PMProfileChanged NOTIFICATION-TYPE
			OBJECTS { sleGponProfile2PMProfileControlRequest, sleGponProfile2PMProfileControlTimeStamp, sleGponProfile2PMProfileControlReqResult, sleGponProfile2PMProfileControlName, sleGponProfile2PMProfileControlPMGemPort,
				sleGponProfile2PMProfileControlPMAniPort, sleGponProfile2PMProfileControlPMUniEthFrameUp, sleGponProfile2PMProfileControlPMUniEthFrameDown, sleGponProfile2PMProfileControlPMUniEth3, sleGponProfile2PMProfileControlPMPseduowire,
				sleGponProfile2PMProfileControlPMUniCes, sleGponProfile2PMProfileControlPMGemNCTP }
			STATUS current
			DESCRIPTION
				"Description."
			::= { sleGponProfile2PMProfileNotification 3 }


--   1.3.6.1.4.1.6296.101.23.51.15
-- 1.3.6.1.4.1.6296.101.23.51.15
		sleGponProfile2OnuBridge OBJECT IDENTIFIER ::= { sleGponProfile2 15 }


--   1.3.6.1.4.1.6296.101.23.51.15.1
-- 1.3.6.1.4.1.6296.101.23.51.15.1
		sleGponProfile2OnuBridgeTable OBJECT-TYPE
			SYNTAX SEQUENCE OF SleGponProfile2OnuBridgeEntry
			MAX-ACCESS not-accessible
			STATUS current
			DESCRIPTION
				"sleGponProfile2OnuBridgeTable"
			::= { sleGponProfile2OnuBridge 1 }


--   1.3.6.1.4.1.6296.101.23.51.15.1.1
-- 1.3.6.1.4.1.6296.101.23.51.15.1.1
		sleGponProfile2OnuBridgeEntry OBJECT-TYPE
			SYNTAX SleGponProfile2OnuBridgeEntry
			MAX-ACCESS not-accessible
			STATUS current
			DESCRIPTION
				"key: sleGponProfile2OnuIndex, sleGponProfile2OnuBridgeId"
			INDEX { sleGponProfile2OnuIndex, sleGponProfile2OnuBridgeId }
			::= { sleGponProfile2OnuBridgeTable 1 }


		SleGponProfile2OnuBridgeEntry ::=
			SEQUENCE {
				sleGponProfile2OnuBridgeId
					Integer32,
				sleGponProfile2OnuBridgeMaxHost
					Integer32
			 }

--   1.3.6.1.4.1.6296.101.23.51.15.1.1.1
-- 1.3.6.1.4.1.6296.101.23.51.15.1.1.1
		sleGponProfile2OnuBridgeId OBJECT-TYPE
			SYNTAX Integer32 (1..65535)
			MAX-ACCESS read-only
			STATUS current
			DESCRIPTION
				"The MAC bridge id of Onu profile."
			::= { sleGponProfile2OnuBridgeEntry 1 }


--   1.3.6.1.4.1.6296.101.23.51.15.1.1.2
-- 1.3.6.1.4.1.6296.101.23.51.15.1.1.2
		sleGponProfile2OnuBridgeMaxHost OBJECT-TYPE
			SYNTAX Integer32 (-1 | 0..255)
			MAX-ACCESS read-only
			STATUS current
			DESCRIPTION
				"The max-host of MAC bridge."
			::= { sleGponProfile2OnuBridgeEntry 2 }


--   1.3.6.1.4.1.6296.101.23.51.15.2
-- 1.3.6.1.4.1.6296.101.23.51.15.2
		sleGponProfile2OnuBridgeControl OBJECT IDENTIFIER ::= { sleGponProfile2OnuBridge 2 }


--   1.3.6.1.4.1.6296.101.23.51.15.2.1
-- 1.3.6.1.4.1.6296.101.23.51.15.2.1
		sleGponProfile2OnuBridgeControlRequest OBJECT-TYPE
			SYNTAX INTEGER { setMaxHost(1) }
			MAX-ACCESS read-write
			STATUS current
			DESCRIPTION
				"The request of a user command"
			::= { sleGponProfile2OnuBridgeControl 1 }


--   1.3.6.1.4.1.6296.101.23.51.15.2.2
-- 1.3.6.1.4.1.6296.101.23.51.15.2.2
		sleGponProfile2OnuBridgeControlStatus OBJECT-TYPE
			SYNTAX SleControlStatusType
			MAX-ACCESS read-only
			STATUS current
			DESCRIPTION
				"The status of user command"
			::= { sleGponProfile2OnuBridgeControl 2 }


--   1.3.6.1.4.1.6296.101.23.51.15.2.3
-- 1.3.6.1.4.1.6296.101.23.51.15.2.3
		sleGponProfile2OnuBridgeControlTimer OBJECT-TYPE
			SYNTAX Gauge32
			MAX-ACCESS read-write
			STATUS current
			DESCRIPTION
				"The maximum time for the manager for a long running user command"
			::= { sleGponProfile2OnuBridgeControl 3 }


--   1.3.6.1.4.1.6296.101.23.51.15.2.4
-- 1.3.6.1.4.1.6296.101.23.51.15.2.4
		sleGponProfile2OnuBridgeControlTimeStamp OBJECT-TYPE
			SYNTAX TimeTicks
			MAX-ACCESS read-only
			STATUS current
			DESCRIPTION
				"The time stamp of the last command(end of command)"
			::= { sleGponProfile2OnuBridgeControl 4 }


--   1.3.6.1.4.1.6296.101.23.51.15.2.5
-- 1.3.6.1.4.1.6296.101.23.51.15.2.5
		sleGponProfile2OnuBridgeControlReqResult OBJECT-TYPE
			SYNTAX SleControlRequestResultType
			MAX-ACCESS read-only
			STATUS current
			DESCRIPTION
				"The result of the last user command
				"
			::= { sleGponProfile2OnuBridgeControl 5 }


--   1.3.6.1.4.1.6296.101.23.51.15.2.6
-- 1.3.6.1.4.1.6296.101.23.51.15.2.6
		sleGponProfile2OnuBridgeControlOnuProfile OBJECT-TYPE
			SYNTAX OCTET STRING
			MAX-ACCESS read-write
			STATUS current
			DESCRIPTION
				"The ONU profile name."
			::= { sleGponProfile2OnuBridgeControl 6 }


--   The ONU profile name.
-- 1.3.6.1.4.1.6296.101.23.51.15.2.7
-- 1.3.6.1.4.1.6296.101.23.51.15.2.7
		sleGponProfile2OnuBridgeControlId OBJECT-TYPE
			SYNTAX Integer32
			MAX-ACCESS read-write
			STATUS current
			DESCRIPTION
				"The MAC bridge id of Onu profile."
			::= { sleGponProfile2OnuBridgeControl 7 }


--   1.3.6.1.4.1.6296.101.23.51.15.2.8
-- 1.3.6.1.4.1.6296.101.23.51.15.2.8
		sleGponProfile2OnuBridgeControlMaxHost OBJECT-TYPE
			SYNTAX Integer32 (-1 | 0..255)
			MAX-ACCESS read-write
			STATUS current
			DESCRIPTION
				"The max-host of MAC bridge."
			::= { sleGponProfile2OnuBridgeControl 8 }


--   1.3.6.1.4.1.6296.101.23.51.15.3
-- 1.3.6.1.4.1.6296.101.23.51.15.3
		sleGponProfile2OnuBridgeNotification OBJECT IDENTIFIER ::= { sleGponProfile2OnuBridge 3 }


--   1.3.6.1.4.1.6296.101.23.51.15.3.1
-- 1.3.6.1.4.1.6296.101.23.51.15.3.1
		sleGponProfile2OnuBridgeMaxHostChanged NOTIFICATION-TYPE
			OBJECTS { sleGponProfile2OnuBridgeControlRequest, sleGponProfile2OnuBridgeControlTimeStamp, sleGponProfile2OnuBridgeControlReqResult, sleGponProfile2OnuBridgeControlOnuProfile, sleGponProfile2OnuBridgeControlId,
				sleGponProfile2OnuBridgeControlMaxHost }
			STATUS current
			DESCRIPTION
				"Description."
			::= { sleGponProfile2OnuBridgeNotification 1 }


--   1.3.6.1.4.1.6296.101.23.51.16
-- 1.3.6.1.4.1.6296.101.23.51.16
		sleGponProfile2OnuTcont OBJECT IDENTIFIER ::= { sleGponProfile2 16 }


--   1.3.6.1.4.1.6296.101.23.51.16.1
-- 1.3.6.1.4.1.6296.101.23.51.16.1
		sleGponProfile2OnuTcontTable OBJECT-TYPE
			SYNTAX SEQUENCE OF SleGponProfile2OnuTcontEntry
			MAX-ACCESS not-accessible
			STATUS current
			DESCRIPTION
				"sleGponProfile2OnuTcontTable"
			::= { sleGponProfile2OnuTcont 1 }


--   1.3.6.1.4.1.6296.101.23.51.16.1.1
-- 1.3.6.1.4.1.6296.101.23.51.16.1.1
		sleGponProfile2OnuTcontEntry OBJECT-TYPE
			SYNTAX SleGponProfile2OnuTcontEntry
			MAX-ACCESS not-accessible
			STATUS current
			DESCRIPTION
				"key: sleGponProfile2OnuIndex, sleGponProfile2OnuTcontId"
			INDEX { sleGponProfile2OnuIndex, sleGponProfile2OnuTcontId }
			::= { sleGponProfile2OnuTcontTable 1 }


		SleGponProfile2OnuTcontEntry ::=
			SEQUENCE {
				sleGponProfile2OnuTcontId
					Integer32,
				sleGponProfile2OnuTcontDbaProfile
					OCTET STRING
			 }

--   1.3.6.1.4.1.6296.101.23.51.16.1.1.1
-- 1.3.6.1.4.1.6296.101.23.51.16.1.1.1
		sleGponProfile2OnuTcontId OBJECT-TYPE
			SYNTAX Integer32 (1..65535)
			MAX-ACCESS read-only
			STATUS current
			DESCRIPTION
				"The Tcont id of Onu profile."
			::= { sleGponProfile2OnuTcontEntry 1 }


--   1.3.6.1.4.1.6296.101.23.51.16.1.1.2
-- 1.3.6.1.4.1.6296.101.23.51.16.1.1.2
		sleGponProfile2OnuTcontDbaProfile OBJECT-TYPE
			SYNTAX OCTET STRING
			MAX-ACCESS read-only
			STATUS current
			DESCRIPTION
				"The DBA profile name."
			::= { sleGponProfile2OnuTcontEntry 2 }


--   1.3.6.1.4.1.6296.101.23.51.16.2
-- 1.3.6.1.4.1.6296.101.23.51.16.2
		sleGponProfile2OnuTcontControl OBJECT IDENTIFIER ::= { sleGponProfile2OnuTcont 2 }


--   1.3.6.1.4.1.6296.101.23.51.16.2.1
-- 1.3.6.1.4.1.6296.101.23.51.16.2.1
		sleGponProfile2OnuTcontControlRequest OBJECT-TYPE
			SYNTAX INTEGER { setDbaProfile(1) }
			MAX-ACCESS read-write
			STATUS current
			DESCRIPTION
				"The request of a user command"
			::= { sleGponProfile2OnuTcontControl 1 }


--   1.3.6.1.4.1.6296.101.23.51.16.2.2
-- 1.3.6.1.4.1.6296.101.23.51.16.2.2
		sleGponProfile2OnuTcontControlStatus OBJECT-TYPE
			SYNTAX SleControlStatusType
			MAX-ACCESS read-only
			STATUS current
			DESCRIPTION
				"The status of user command"
			::= { sleGponProfile2OnuTcontControl 2 }


--   1.3.6.1.4.1.6296.101.23.51.16.2.3
-- 1.3.6.1.4.1.6296.101.23.51.16.2.3
		sleGponProfile2OnuTcontControlTimer OBJECT-TYPE
			SYNTAX Gauge32
			MAX-ACCESS read-write
			STATUS current
			DESCRIPTION
				"The maximum time for the manager for a long running user command"
			::= { sleGponProfile2OnuTcontControl 3 }


--   1.3.6.1.4.1.6296.101.23.51.16.2.4
-- 1.3.6.1.4.1.6296.101.23.51.16.2.4
		sleGponProfile2OnuTcontControlTimeStamp OBJECT-TYPE
			SYNTAX TimeTicks
			MAX-ACCESS read-only
			STATUS current
			DESCRIPTION
				"The time stamp of the last command(end of command)"
			::= { sleGponProfile2OnuTcontControl 4 }


--   1.3.6.1.4.1.6296.101.23.51.16.2.5
-- 1.3.6.1.4.1.6296.101.23.51.16.2.5
		sleGponProfile2OnuTcontControlReqResult OBJECT-TYPE
			SYNTAX SleControlRequestResultType
			MAX-ACCESS read-only
			STATUS current
			DESCRIPTION
				"The result of the last user command"
			::= { sleGponProfile2OnuTcontControl 5 }


--   1.3.6.1.4.1.6296.101.23.51.16.2.6
-- 1.3.6.1.4.1.6296.101.23.51.16.2.6
		sleGponProfile2OnuTcontControlOnuProfile OBJECT-TYPE
			SYNTAX OCTET STRING
			MAX-ACCESS read-write
			STATUS current
			DESCRIPTION
				"The ONU profile name."
			::= { sleGponProfile2OnuTcontControl 6 }


--   The ONU profile name.
-- 1.3.6.1.4.1.6296.101.23.51.16.2.7
-- 1.3.6.1.4.1.6296.101.23.51.16.2.7
		sleGponProfile2OnuTcontControlId OBJECT-TYPE
			SYNTAX Integer32
			MAX-ACCESS read-write
			STATUS current
			DESCRIPTION
				"The Tcont id of Onu profile."
			::= { sleGponProfile2OnuTcontControl 7 }


--   1.3.6.1.4.1.6296.101.23.51.16.2.8
-- 1.3.6.1.4.1.6296.101.23.51.16.2.8
		sleGponProfile2OnuTcontControlDbaProfile OBJECT-TYPE
			SYNTAX OCTET STRING
			MAX-ACCESS read-write
			STATUS current
			DESCRIPTION
				"The DBA profile name."
			::= { sleGponProfile2OnuTcontControl 8 }


--   1.3.6.1.4.1.6296.101.23.51.16.3
-- 1.3.6.1.4.1.6296.101.23.51.16.3
		sleGponProfile2OnuTcontNotification OBJECT IDENTIFIER ::= { sleGponProfile2OnuTcont 3 }


--   1.3.6.1.4.1.6296.101.23.51.16.3.1
-- 1.3.6.1.4.1.6296.101.23.51.16.3.1
		sleGponProfile2OnuTcontDbaProfileChanged NOTIFICATION-TYPE
			OBJECTS { sleGponProfile2OnuTcontControlRequest, sleGponProfile2OnuTcontControlTimeStamp, sleGponProfile2OnuTcontControlReqResult, sleGponProfile2OnuTcontControlOnuProfile, sleGponProfile2OnuTcontControlId,
				sleGponProfile2OnuTcontControlDbaProfile }
			STATUS current
			DESCRIPTION
				"Description."
			::= { sleGponProfile2OnuTcontNotification 1 }


--  1.3.6.1.4.1.6296.101.23.51.17
		sleGponProfile2IpHost OBJECT IDENTIFIER ::= { sleGponProfile2 17 }


--  1.3.6.1.4.1.6296.101.23.51.17.1
		sleGponProfile2IpHostSvc OBJECT IDENTIFIER ::= { sleGponProfile2IpHost 1 }


--  1.3.6.1.4.1.6296.101.23.51.17.1.1
		sleGponProfile2IpHostSvcTable OBJECT-TYPE
			SYNTAX SEQUENCE OF SleGponProfile2IpHostSvcEntry
			MAX-ACCESS not-accessible
			STATUS current
			DESCRIPTION
				"sleGponProfile2IpHostSvcTable"
			::= { sleGponProfile2IpHostSvc 1 }


--  1.3.6.1.4.1.6296.101.23.51.17.1.1.1
		sleGponProfile2IpHostSvcEntry OBJECT-TYPE
			SYNTAX SleGponProfile2IpHostSvcEntry
			MAX-ACCESS not-accessible
			STATUS current
			DESCRIPTION
				"key: sleGponProfile2TrafficIndex, sleGponProfile2IpHostSvcId"
			INDEX { sleGponProfile2TrafficIndex, sleGponProfile2IpHostSvcId }
			::= { sleGponProfile2IpHostSvcTable 1 }


		SleGponProfile2IpHostSvcEntry ::=
			SEQUENCE {
				sleGponProfile2IpHostSvcId
					INTEGER,
				sleGponProfile2IpHostSvcAddressType
					INTEGER,
				sleGponProfile2IpHostSvcPriDns
					IpAddress,
				sleGponProfile2IpHostSvcSecDns
					IpAddress,
				sleGponProfile2IpHostSvcVlanFilterMode
					INTEGER,
				sleGponProfile2IpHostSvcVlanFilter
					OCTET STRING,
				sleGponProfile2IpHostSvcVlanOpDsOperFlag
					INTEGER,
				sleGponProfile2IpHostSvcVlanOpUsOperFlag
					INTEGER,
				sleGponProfile2IpHostSvcVlanOpUsOperVid
					INTEGER,
				sleGponProfile2IpHostSvcVlanOpUsOperCos
					INTEGER,
				sleGponProfile2IpHostSvcExtVlanName
					OCTET STRING,
				sleGponProfile2Ipv6HostSvcSuppressRs
					INTEGER,
				sleGponProfile2Ipv6HostSvcDhcpClient
					INTEGER,
				sleGponProfile2Ipv6HostSvcPriDns
					InetAddress,
				sleGponProfile2Ipv6HostSvcSecDns
					InetAddress
			 }

--  1.3.6.1.4.1.6296.101.23.51.17.1.1.1.1
		sleGponProfile2IpHostSvcId OBJECT-TYPE
			SYNTAX INTEGER (1..65535)
			MAX-ACCESS read-only
			STATUS current
			DESCRIPTION
				"The IP host service id of GPON profile."
			::= { sleGponProfile2IpHostSvcEntry 1 }


--  1.3.6.1.4.1.6296.101.23.51.17.1.1.1.2
		sleGponProfile2IpHostSvcAddressType OBJECT-TYPE
			SYNTAX INTEGER
				{
				unUsed(0),
				static(1),
				dhcp(2)
				}
			MAX-ACCESS read-only
			STATUS current
			DESCRIPTION
				"The address type.
				0: unused
				1: static
				2: DHCP"
			::= { sleGponProfile2IpHostSvcEntry 2 }


--  1.3.6.1.4.1.6296.101.23.51.17.1.1.1.3
		sleGponProfile2IpHostSvcPriDns OBJECT-TYPE
			SYNTAX IpAddress
			MAX-ACCESS read-only
			STATUS current
			DESCRIPTION
				"The primary DNS address."
			::= { sleGponProfile2IpHostSvcEntry 3 }


--  1.3.6.1.4.1.6296.101.23.51.17.1.1.1.4
		sleGponProfile2IpHostSvcSecDns OBJECT-TYPE
			SYNTAX IpAddress
			MAX-ACCESS read-only
			STATUS current
			DESCRIPTION
				"The second DNS address."
			::= { sleGponProfile2IpHostSvcEntry 4 }


--  1.3.6.1.4.1.6296.101.23.51.17.1.1.1.5
		sleGponProfile2IpHostSvcVlanFilterMode OBJECT-TYPE
			SYNTAX INTEGER
				{
				unUsed(0),
				allow(1),
				deny(2)
				}
			MAX-ACCESS read-only
			STATUS current
			DESCRIPTION
				"The VLAN filter mode
				0: unused
				1: allow
				2: deny"
			::= { sleGponProfile2IpHostSvcEntry 5 }


--  1.3.6.1.4.1.6296.101.23.51.17.1.1.1.6
		sleGponProfile2IpHostSvcVlanFilter OBJECT-TYPE
			SYNTAX OCTET STRING
			MAX-ACCESS read-only
			STATUS current
			DESCRIPTION
				"The VLAN filter name."
			::= { sleGponProfile2IpHostSvcEntry 6 }


--  1.3.6.1.4.1.6296.101.23.51.17.1.1.1.7
		sleGponProfile2IpHostSvcVlanOpDsOperFlag OBJECT-TYPE
			SYNTAX INTEGER
				{
				unUsed(0),
				keep(1),
				overwrite(2),
				add(3),
				remove(4)
				}
			MAX-ACCESS read-only
			STATUS current
			DESCRIPTION
				"The VLAN down stream operation flag
				"
			::= { sleGponProfile2IpHostSvcEntry 7 }


--  1.3.6.1.4.1.6296.101.23.51.17.1.1.1.8
		sleGponProfile2IpHostSvcVlanOpUsOperFlag OBJECT-TYPE
			SYNTAX INTEGER
				{
				unUsed(0),
				keep(1),
				overwrite(2),
				add(3),
				remove(4)
				}
			MAX-ACCESS read-only
			STATUS current
			DESCRIPTION
				"The VLAN up stream operation flag"
			::= { sleGponProfile2IpHostSvcEntry 8 }


--  1.3.6.1.4.1.6296.101.23.51.17.1.1.1.9
		sleGponProfile2IpHostSvcVlanOpUsOperVid OBJECT-TYPE
			SYNTAX INTEGER (1..65535)
			MAX-ACCESS read-only
			STATUS current
			DESCRIPTION
				"The VLAN Up stream operation VID."
			::= { sleGponProfile2IpHostSvcEntry 9 }


--  1.3.6.1.4.1.6296.101.23.51.17.1.1.1.10
		sleGponProfile2IpHostSvcVlanOpUsOperCos OBJECT-TYPE
			SYNTAX INTEGER (1..65535)
			MAX-ACCESS read-only
			STATUS current
			DESCRIPTION
				"The VLAN Up stream operation COS."
			::= { sleGponProfile2IpHostSvcEntry 10 }


--  1.3.6.1.4.1.6296.101.23.51.17.1.1.1.11
		sleGponProfile2IpHostSvcExtVlanName OBJECT-TYPE
			SYNTAX OCTET STRING
			MAX-ACCESS read-only
			STATUS current
			DESCRIPTION
				"The Extended vlan name."
			::= { sleGponProfile2IpHostSvcEntry 11 }


		sleGponProfile2Ipv6HostSvcSuppressRs OBJECT-TYPE
			SYNTAX INTEGER
				{
				disable(0),
				enable(1)
				}
			MAX-ACCESS read-only
			STATUS current
			DESCRIPTION
				"enable to generates router solicitation (RS)"
			::= { sleGponProfile2IpHostSvcEntry 12 }


		sleGponProfile2Ipv6HostSvcDhcpClient OBJECT-TYPE
			SYNTAX INTEGER
				{
				stateless(0),
				na(1)
				}
			MAX-ACCESS read-only
			STATUS current
			DESCRIPTION
				"DHCP operation IPv6 Address"
			::= { sleGponProfile2IpHostSvcEntry 13 }


		sleGponProfile2Ipv6HostSvcPriDns OBJECT-TYPE
			SYNTAX InetAddress
			MAX-ACCESS read-only
			STATUS current
			DESCRIPTION
				"DHCP operation IPv6 Address"
			::= { sleGponProfile2IpHostSvcEntry 14 }


		sleGponProfile2Ipv6HostSvcSecDns OBJECT-TYPE
			SYNTAX InetAddress
			MAX-ACCESS read-only
			STATUS current
			DESCRIPTION
				"Secondary DNS Server IPv6 Address"
			::= { sleGponProfile2IpHostSvcEntry 15 }


--  1.3.6.1.4.1.6296.101.23.51.17.1.2
		sleGponProfile2IpHostSvcControl OBJECT IDENTIFIER ::= { sleGponProfile2IpHostSvc 2 }


--  1.3.6.1.4.1.6296.101.23.51.17.1.2.1
		sleGponProfile2IpHostSvcControlRequest OBJECT-TYPE
			SYNTAX INTEGER
				{
				addIpHostSvc(1),
				delIpHostSvc(2),
				setAddressType(3),
				setDns(4),
				setVlanFilter(5),
				setVlanDsOper(6),
				setVlanUsOper(7),
				setExtendedVlan(8),
				setIpv6SuppressRs(9),
				setIpv6DhcpClient(10),
				setIpv6Dns(11)
				}
			MAX-ACCESS read-write
			STATUS current
			DESCRIPTION
				"The request of a user command"
			::= { sleGponProfile2IpHostSvcControl 1 }


--  1.3.6.1.4.1.6296.101.23.51.17.1.2.2
		sleGponProfile2IpHostSvcControlStatus OBJECT-TYPE
			SYNTAX SleControlStatusType
			MAX-ACCESS read-only
			STATUS current
			DESCRIPTION
				"The status of user command"
			::= { sleGponProfile2IpHostSvcControl 2 }


--  1.3.6.1.4.1.6296.101.23.51.17.1.2.3
		sleGponProfile2IpHostSvcControlTimer OBJECT-TYPE
			SYNTAX Gauge32
			MAX-ACCESS read-write
			STATUS current
			DESCRIPTION
				"The maximum time for the manager for a long running user command"
			::= { sleGponProfile2IpHostSvcControl 3 }


--  1.3.6.1.4.1.6296.101.23.51.17.1.2.4
		sleGponProfile2IpHostSvcControlTimeStamp OBJECT-TYPE
			SYNTAX TimeTicks
			MAX-ACCESS read-only
			STATUS current
			DESCRIPTION
				"The time stamp of the last command(end of command)"
			::= { sleGponProfile2IpHostSvcControl 4 }


--  1.3.6.1.4.1.6296.101.23.51.17.1.2.5
		sleGponProfile2IpHostSvcControlReqResult OBJECT-TYPE
			SYNTAX SleControlRequestResultType
			MAX-ACCESS read-only
			STATUS current
			DESCRIPTION
				"The result of the last user command"
			::= { sleGponProfile2IpHostSvcControl 5 }


--  1.3.6.1.4.1.6296.101.23.51.17.1.2.6
		sleGponProfile2IpHostSvcControlTName OBJECT-TYPE
			SYNTAX OCTET STRING
			MAX-ACCESS read-write
			STATUS current
			DESCRIPTION
				"The Traffic profile name."
			::= { sleGponProfile2IpHostSvcControl 6 }


--  The ONU profile name.
-- 1.3.6.1.4.1.6296.101.23.51.17.1.2.7
		sleGponProfile2IpHostSvcControlId OBJECT-TYPE
			SYNTAX INTEGER (1..65535)
			MAX-ACCESS read-write
			STATUS current
			DESCRIPTION
				"The IP host service id of GPON profile."
			::= { sleGponProfile2IpHostSvcControl 7 }


--  1.3.6.1.4.1.6296.101.23.51.17.1.2.8
		sleGponProfile2IpHostSvcControlAddressType OBJECT-TYPE
			SYNTAX INTEGER
				{
				unUsed(0),
				static(1),
				dhcp(2)
				}
			MAX-ACCESS read-write
			STATUS current
			DESCRIPTION
				"The address type.
				0: unused
				1: static
				2: DHCP"
			::= { sleGponProfile2IpHostSvcControl 8 }


--  1.3.6.1.4.1.6296.101.23.51.17.1.2.9
		sleGponProfile2IpHostSvcControlPriDns OBJECT-TYPE
			SYNTAX IpAddress
			MAX-ACCESS read-write
			STATUS current
			DESCRIPTION
				"The primary DNS address."
			::= { sleGponProfile2IpHostSvcControl 9 }


--  1.3.6.1.4.1.6296.101.23.51.17.1.2.10
		sleGponProfile2IpHostSvcControlSecDns OBJECT-TYPE
			SYNTAX IpAddress
			MAX-ACCESS read-write
			STATUS current
			DESCRIPTION
				"The second DNS address."
			::= { sleGponProfile2IpHostSvcControl 10 }


--  1.3.6.1.4.1.6296.101.23.51.17.1.2.11
		sleGponProfile2IpHostSvcControlVlanFilterMode OBJECT-TYPE
			SYNTAX INTEGER
				{
				unUsed(0),
				allow(1),
				deny(2)
				}
			MAX-ACCESS read-write
			STATUS current
			DESCRIPTION
				"The VLAN filter mode
				0: unused
				1: allow
				2: deny"
			::= { sleGponProfile2IpHostSvcControl 11 }


--  1.3.6.1.4.1.6296.101.23.51.17.1.2.12
		sleGponProfile2IpHostSvcControlVlanFilter OBJECT-TYPE
			SYNTAX OCTET STRING
			MAX-ACCESS read-write
			STATUS current
			DESCRIPTION
				"The VLAN filter name."
			::= { sleGponProfile2IpHostSvcControl 12 }


--  1.3.6.1.4.1.6296.101.23.51.17.1.2.13
		sleGponProfile2IpHostSvcControlVlanOpDsOperFlag OBJECT-TYPE
			SYNTAX INTEGER
				{
				unUsed(0),
				keep(1),
				overwrite(2),
				add(3),
				remove(4)
				}
			MAX-ACCESS read-write
			STATUS current
			DESCRIPTION
				"The VLAN down stream operation flag
				"
			::= { sleGponProfile2IpHostSvcControl 13 }


--  1.3.6.1.4.1.6296.101.23.51.17.1.2.14
		sleGponProfile2IpHostSvcControlVlanOpUsOperFlag OBJECT-TYPE
			SYNTAX INTEGER
				{
				unUsed(0),
				keep(1),
				overwrite(2),
				add(3),
				remove(4)
				}
			MAX-ACCESS read-write
			STATUS current
			DESCRIPTION
				"The VLAN up stream operation flag"
			::= { sleGponProfile2IpHostSvcControl 14 }


--  1.3.6.1.4.1.6296.101.23.51.17.1.2.15
		sleGponProfile2IpHostSvcControlVlanOpUsOperVid OBJECT-TYPE
			SYNTAX INTEGER (1..65535)
			MAX-ACCESS read-write
			STATUS current
			DESCRIPTION
				"The VLAN Up stream operation VID."
			::= { sleGponProfile2IpHostSvcControl 15 }


--  1.3.6.1.4.1.6296.101.23.51.17.1.2.16
		sleGponProfile2IpHostSvcControlVlanOpUsOperCos OBJECT-TYPE
			SYNTAX INTEGER (1..65535)
			MAX-ACCESS read-write
			STATUS current
			DESCRIPTION
				"The VLAN Up stream operation COS."
			::= { sleGponProfile2IpHostSvcControl 16 }


--  1.3.6.1.4.1.6296.101.23.51.17.1.2.17
		sleGponProfile2IpHostSvcControlExtVlanName OBJECT-TYPE
			SYNTAX OCTET STRING
			MAX-ACCESS read-write
			STATUS current
			DESCRIPTION
				"The Extended vlan name."
			::= { sleGponProfile2IpHostSvcControl 17 }


		sleGponProfile2Ipv6HostSvcControlSuppressRs OBJECT-TYPE
			SYNTAX INTEGER
				{
				disable(0),
				enable(1)
				}
			MAX-ACCESS read-write
			STATUS current
			DESCRIPTION
				"enable to generates router solicitation (RS)"
			::= { sleGponProfile2IpHostSvcControl 18 }


		sleGponProfile2Ipv6HostSvcControlDhcpClient OBJECT-TYPE
			SYNTAX INTEGER
				{
				stateless(0),
				na(1)
				}
			MAX-ACCESS read-write
			STATUS current
			DESCRIPTION
				"DHCP operation IPv6 Address"
			::= { sleGponProfile2IpHostSvcControl 19 }


		sleGponProfile2Ipv6HostSvcControlPriDns OBJECT-TYPE
			SYNTAX InetAddress
			MAX-ACCESS read-write
			STATUS current
			DESCRIPTION
				"Primary DNS Server IPv6 Address"
			::= { sleGponProfile2IpHostSvcControl 20 }


		sleGponProfile2Ipv6HostSvcControlSecDns OBJECT-TYPE
			SYNTAX InetAddress
			MAX-ACCESS read-write
			STATUS current
			DESCRIPTION
				"Secondary DNS Server IPv6 Address"
			::= { sleGponProfile2IpHostSvcControl 21 }


--  1.3.6.1.4.1.6296.101.23.51.17.1.3
		sleGponProfile2IpHostSvcNotification OBJECT IDENTIFIER ::= { sleGponProfile2IpHostSvc 3 }


--  1.3.6.1.4.1.6296.101.23.51.17.1.3.1
		sleGponProfile2IpHostSvcIpHostSvcCreated NOTIFICATION-TYPE
			OBJECTS { sleGponProfile2IpHostSvcControlRequest, sleGponProfile2IpHostSvcControlTimeStamp, sleGponProfile2IpHostSvcControlReqResult, sleGponProfile2IpHostSvcControlTName, sleGponProfile2IpHostSvcControlId
				 }
			STATUS current
			DESCRIPTION
				"Description."
			::= { sleGponProfile2IpHostSvcNotification 1 }


--  1.3.6.1.4.1.6296.101.23.51.17.1.3.2
		sleGponProfile2IpHostSvcIpHostSvcDeleted NOTIFICATION-TYPE
			OBJECTS { sleGponProfile2IpHostSvcControlRequest, sleGponProfile2IpHostSvcControlTimeStamp, sleGponProfile2IpHostSvcControlReqResult, sleGponProfile2IpHostSvcControlTName, sleGponProfile2IpHostSvcControlId
				 }
			STATUS current
			DESCRIPTION
				"Description."
			::= { sleGponProfile2IpHostSvcNotification 2 }


--  1.3.6.1.4.1.6296.101.23.51.17.1.3.3
		sleGponProfile2IpHostSvcAddressTypeChanged NOTIFICATION-TYPE
			OBJECTS { sleGponProfile2IpHostSvcControlRequest, sleGponProfile2IpHostSvcControlTimeStamp, sleGponProfile2IpHostSvcControlReqResult, sleGponProfile2IpHostSvcControlId, sleGponProfile2IpHostSvcControlAddressType
				 }
			STATUS current
			DESCRIPTION
				"Description."
			::= { sleGponProfile2IpHostSvcNotification 3 }


--  1.3.6.1.4.1.6296.101.23.51.17.1.3.4
		sleGponProfile2IpHostSvcDnsChanged NOTIFICATION-TYPE
			OBJECTS { sleGponProfile2IpHostSvcControlRequest, sleGponProfile2IpHostSvcControlTimeStamp, sleGponProfile2IpHostSvcControlReqResult, sleGponProfile2IpHostSvcControlId, sleGponProfile2IpHostSvcControlPriDns,
				sleGponProfile2IpHostSvcControlSecDns }
			STATUS current
			DESCRIPTION
				"Description."
			::= { sleGponProfile2IpHostSvcNotification 4 }


--  1.3.6.1.4.1.6296.101.23.51.17.1.3.5
		sleGponProfile2IpHostSvcVlanFilterChanged NOTIFICATION-TYPE
			OBJECTS { sleGponProfile2IpHostSvcControlRequest, sleGponProfile2IpHostSvcControlTimeStamp, sleGponProfile2IpHostSvcControlReqResult, sleGponProfile2IpHostSvcControlId, sleGponProfile2IpHostSvcControlVlanFilterMode,
				sleGponProfile2IpHostSvcControlVlanFilter }
			STATUS current
			DESCRIPTION
				"Description."
			::= { sleGponProfile2IpHostSvcNotification 5 }


--  1.3.6.1.4.1.6296.101.23.51.17.1.3.6
		sleGponProfile2IpHostSvcVlanDsOperChanged NOTIFICATION-TYPE
			OBJECTS { sleGponProfile2IpHostSvcControlRequest, sleGponProfile2IpHostSvcControlTimeStamp, sleGponProfile2IpHostSvcControlReqResult, sleGponProfile2IpHostSvcControlId, sleGponProfile2IpHostSvcControlVlanOpDsOperFlag
				 }
			STATUS current
			DESCRIPTION
				"Description."
			::= { sleGponProfile2IpHostSvcNotification 6 }


--  1.3.6.1.4.1.6296.101.23.51.17.1.3.7
		sleGponProfile2IpHostSvcVlanUsOperChanged NOTIFICATION-TYPE
			OBJECTS { sleGponProfile2IpHostSvcControlRequest, sleGponProfile2IpHostSvcControlTimeStamp, sleGponProfile2IpHostSvcControlReqResult, sleGponProfile2IpHostSvcControlId, sleGponProfile2IpHostSvcControlVlanOpUsOperFlag,
				sleGponProfile2IpHostSvcControlVlanOpUsOperVid, sleGponProfile2IpHostSvcControlVlanOpUsOperCos }
			STATUS current
			DESCRIPTION
				"Description."
			::= { sleGponProfile2IpHostSvcNotification 7 }


--  1.3.6.1.4.1.6296.101.23.51.17.1.3.8
		sleGponProfile2IpHostSvcExtendedVlanChanged NOTIFICATION-TYPE
			OBJECTS { sleGponProfile2IpHostSvcControlRequest, sleGponProfile2IpHostSvcControlTimeStamp, sleGponProfile2IpHostSvcControlReqResult, sleGponProfile2IpHostSvcControlId, sleGponProfile2IpHostSvcControlExtVlanName
				 }
			STATUS current
			DESCRIPTION
				"setExtendedVlan"
			::= { sleGponProfile2IpHostSvcNotification 8 }


		sleGponProfile2Ipv6HostSvcSuppressRsChanged NOTIFICATION-TYPE
			OBJECTS { sleGponProfile2IpHostSvcControlRequest, sleGponProfile2IpHostSvcControlTimeStamp, sleGponProfile2IpHostSvcControlReqResult, sleGponProfile2IpHostSvcControlId, sleGponProfile2Ipv6HostSvcControlDhcpClient
				 }
			STATUS current
			DESCRIPTION
				"setIpv6SuppressRs"
			::= { sleGponProfile2IpHostSvcNotification 9 }


		sleGponProfile2Ipv6HostSvcDhcpClientChanged NOTIFICATION-TYPE
			OBJECTS { sleGponProfile2IpHostSvcControlRequest, sleGponProfile2IpHostSvcControlTimeStamp, sleGponProfile2IpHostSvcControlReqResult, sleGponProfile2IpHostSvcControlId, sleGponProfile2Ipv6HostSvcControlDhcpClient
				 }
			STATUS current
			DESCRIPTION
				"setIpv6DhcpClient"
			::= { sleGponProfile2IpHostSvcNotification 10 }


		sleGponProfile2Ipv6HostSvcDnsChanged NOTIFICATION-TYPE
			OBJECTS { sleGponProfile2IpHostSvcControlRequest, sleGponProfile2IpHostSvcControlTimeStamp, sleGponProfile2IpHostSvcControlReqResult, sleGponProfile2IpHostSvcControlId, sleGponProfile2Ipv6HostSvcControlPriDns,
				sleGponProfile2Ipv6HostSvcControlSecDns }
			STATUS current
			DESCRIPTION
				"setIpv6Dns"
			::= { sleGponProfile2IpHostSvcNotification 11 }


--  1.3.6.1.4.1.6296.101.23.51.17.2
		sleGponProfile2IpHostVoip OBJECT IDENTIFIER ::= { sleGponProfile2IpHost 2 }


--  1.3.6.1.4.1.6296.101.23.51.17.2.1
		sleGponProfile2IpHostVoipTable OBJECT-TYPE
			SYNTAX SEQUENCE OF SleGponProfile2IpHostVoipEntry
			MAX-ACCESS not-accessible
			STATUS current
			DESCRIPTION
				"sleGponProfile2IpHostVoipTable"
			::= { sleGponProfile2IpHostVoip 1 }


--  1.3.6.1.4.1.6296.101.23.51.17.2.1.1
		sleGponProfile2IpHostVoipEntry OBJECT-TYPE
			SYNTAX SleGponProfile2IpHostVoipEntry
			MAX-ACCESS not-accessible
			STATUS current
			DESCRIPTION
				"sleGponProfile2TrafficIndex, sleGponProfile2IpHostSvcId, sleGponProfile2IpHostVoipId"
			INDEX { sleGponProfile2TrafficIndex, sleGponProfile2IpHostSvcId, sleGponProfile2IpHostVoipId }
			::= { sleGponProfile2IpHostVoipTable 1 }


		SleGponProfile2IpHostVoipEntry ::=
			SEQUENCE {
				sleGponProfile2IpHostVoipId
					INTEGER
			 }

--  1.3.6.1.4.1.6296.101.23.51.17.2.1.1.1
		sleGponProfile2IpHostVoipId OBJECT-TYPE
			SYNTAX INTEGER (1..65535)
			MAX-ACCESS read-only
			STATUS current
			DESCRIPTION
				"The VoIP id of GPON profile."
			::= { sleGponProfile2IpHostVoipEntry 1 }


--  1.3.6.1.4.1.6296.101.23.51.17.2.2
		sleGponProfile2IpHostVoipControl OBJECT IDENTIFIER ::= { sleGponProfile2IpHostVoip 2 }


--  1.3.6.1.4.1.6296.101.23.51.17.2.2.1
		sleGponProfile2IpHostVoipControlRequest OBJECT-TYPE
			SYNTAX INTEGER
				{
				addVoipSvc(1),
				delVoipSvc(2)
				}
			MAX-ACCESS read-write
			STATUS current
			DESCRIPTION
				"The request of a user command"
			::= { sleGponProfile2IpHostVoipControl 1 }


--  1.3.6.1.4.1.6296.101.23.51.17.2.2.2
		sleGponProfile2IpHostVoipControlStatus OBJECT-TYPE
			SYNTAX SleControlStatusType
			MAX-ACCESS read-only
			STATUS current
			DESCRIPTION
				"The status of user command"
			::= { sleGponProfile2IpHostVoipControl 2 }


--  1.3.6.1.4.1.6296.101.23.51.17.2.2.3
		sleGponProfile2IpHostVoipControlTimer OBJECT-TYPE
			SYNTAX Gauge32
			MAX-ACCESS read-write
			STATUS current
			DESCRIPTION
				"The maximum time for the manager for a long running user command"
			::= { sleGponProfile2IpHostVoipControl 3 }


--  1.3.6.1.4.1.6296.101.23.51.17.2.2.4
		sleGponProfile2IpHostVoipControlTimeStamp OBJECT-TYPE
			SYNTAX TimeTicks
			MAX-ACCESS read-only
			STATUS current
			DESCRIPTION
				"The time stamp of the last command(end of command)"
			::= { sleGponProfile2IpHostVoipControl 4 }


--  1.3.6.1.4.1.6296.101.23.51.17.2.2.5
		sleGponProfile2IpHostVoipControlReqResult OBJECT-TYPE
			SYNTAX SleControlRequestResultType
			MAX-ACCESS read-only
			STATUS current
			DESCRIPTION
				"The result of the last user command"
			::= { sleGponProfile2IpHostVoipControl 5 }


--  1.3.6.1.4.1.6296.101.23.51.17.2.2.6
		sleGponProfile2IpHostVoipControlTName OBJECT-TYPE
			SYNTAX OCTET STRING
			MAX-ACCESS read-write
			STATUS current
			DESCRIPTION
				"The Traffic profile name."
			::= { sleGponProfile2IpHostVoipControl 6 }


--  The ONU profile name.
-- 1.3.6.1.4.1.6296.101.23.51.17.2.2.7
		sleGponProfile2IpHostVoipControlIpHostSvcId OBJECT-TYPE
			SYNTAX INTEGER (1..65535)
			MAX-ACCESS read-write
			STATUS current
			DESCRIPTION
				"The IP host service id of GPON profile."
			::= { sleGponProfile2IpHostVoipControl 7 }


--  1.3.6.1.4.1.6296.101.23.51.17.2.2.8
		sleGponProfile2IpHostVoipControlId OBJECT-TYPE
			SYNTAX INTEGER (1..65535)
			MAX-ACCESS read-write
			STATUS current
			DESCRIPTION
				"The VoIP id of GPON profile."
			::= { sleGponProfile2IpHostVoipControl 8 }


--  1.3.6.1.4.1.6296.101.23.51.17.2.3
		sleGponProfile2IpHostVoipNotification OBJECT IDENTIFIER ::= { sleGponProfile2IpHostVoip 3 }


--  1.3.6.1.4.1.6296.101.23.51.17.2.3.1
		sleGponProfile2IpHostVoipVoipSvcCreated NOTIFICATION-TYPE
			OBJECTS { sleGponProfile2IpHostVoipControlRequest, sleGponProfile2IpHostVoipControlTimeStamp, sleGponProfile2IpHostVoipControlReqResult, sleGponProfile2IpHostVoipControlTName, sleGponProfile2IpHostVoipControlIpHostSvcId,
				sleGponProfile2IpHostVoipControlId }
			STATUS current
			DESCRIPTION
				"Description."
			::= { sleGponProfile2IpHostVoipNotification 1 }


--  1.3.6.1.4.1.6296.101.23.51.17.2.3.2
		sleGponProfile2IpHostVoipVoipSvcDeleted NOTIFICATION-TYPE
			OBJECTS { sleGponProfile2IpHostVoipControlRequest, sleGponProfile2IpHostVoipControlTimeStamp, sleGponProfile2IpHostVoipControlReqResult, sleGponProfile2IpHostVoipControlTName, sleGponProfile2IpHostVoipControlIpHostSvcId,
				sleGponProfile2IpHostVoipControlId }
			STATUS current
			DESCRIPTION
				"Description."
			::= { sleGponProfile2IpHostVoipNotification 2 }


--  1.3.6.1.4.1.6296.101.23.51.17.3
		sleGponProfile2IpHostTdm OBJECT IDENTIFIER ::= { sleGponProfile2IpHost 3 }


--  1.3.6.1.4.1.6296.101.23.51.17.3.1
		sleGponProfile2IpHostTdmTable OBJECT-TYPE
			SYNTAX SEQUENCE OF SleGponProfile2IpHostTdmEntry
			MAX-ACCESS not-accessible
			STATUS current
			DESCRIPTION
				"sleGponProfile2IpHostTdmTable"
			::= { sleGponProfile2IpHostTdm 1 }


--  1.3.6.1.4.1.6296.101.23.51.17.3.1.1
		sleGponProfile2IpHostTdmEntry OBJECT-TYPE
			SYNTAX SleGponProfile2IpHostTdmEntry
			MAX-ACCESS not-accessible
			STATUS current
			DESCRIPTION
				"key: sleGponProfile2TrafficIndex, sleGponProfile2IpHostSvcId, sleGponProfile2IpHostTdmId"
			INDEX { sleGponProfile2TrafficIndex, sleGponProfile2IpHostSvcId, sleGponProfile2IpHostTdmId }
			::= { sleGponProfile2IpHostTdmTable 1 }


		SleGponProfile2IpHostTdmEntry ::=
			SEQUENCE {
				sleGponProfile2IpHostTdmId
					INTEGER
			 }

--  1.3.6.1.4.1.6296.101.23.51.17.3.1.1.1
		sleGponProfile2IpHostTdmId OBJECT-TYPE
			SYNTAX INTEGER (1..65535)
			MAX-ACCESS read-only
			STATUS current
			DESCRIPTION
				"The TDM id of GPON profile."
			::= { sleGponProfile2IpHostTdmEntry 1 }


--  1.3.6.1.4.1.6296.101.23.51.17.3.2
		sleGponProfile2IpHostTdmControl OBJECT IDENTIFIER ::= { sleGponProfile2IpHostTdm 2 }


--  1.3.6.1.4.1.6296.101.23.51.17.3.2.1
		sleGponProfile2IpHostTdmControlRequest OBJECT-TYPE
			SYNTAX INTEGER
				{
				addVoipSvc(1),
				delVoipSvc(2)
				}
			MAX-ACCESS read-write
			STATUS current
			DESCRIPTION
				"The request of a user command"
			::= { sleGponProfile2IpHostTdmControl 1 }


--  1.3.6.1.4.1.6296.101.23.51.17.3.2.2
		sleGponProfile2IpHostTdmControlStatus OBJECT-TYPE
			SYNTAX SleControlStatusType
			MAX-ACCESS read-only
			STATUS current
			DESCRIPTION
				"The status of user command"
			::= { sleGponProfile2IpHostTdmControl 2 }


--  1.3.6.1.4.1.6296.101.23.51.17.3.2.3
		sleGponProfile2IpHostTdmControlTimer OBJECT-TYPE
			SYNTAX Gauge32
			MAX-ACCESS read-write
			STATUS current
			DESCRIPTION
				"The maximum time for the manager for a long running user command"
			::= { sleGponProfile2IpHostTdmControl 3 }


--  1.3.6.1.4.1.6296.101.23.51.17.3.2.4
		sleGponProfile2IpHostTdmControlTimeStamp OBJECT-TYPE
			SYNTAX TimeTicks
			MAX-ACCESS read-only
			STATUS current
			DESCRIPTION
				"The time stamp of the last command(end of command)"
			::= { sleGponProfile2IpHostTdmControl 4 }


--  1.3.6.1.4.1.6296.101.23.51.17.3.2.5
		sleGponProfile2IpHostTdmControlReqResult OBJECT-TYPE
			SYNTAX SleControlRequestResultType
			MAX-ACCESS read-only
			STATUS current
			DESCRIPTION
				"The result of the last user command"
			::= { sleGponProfile2IpHostTdmControl 5 }


--  1.3.6.1.4.1.6296.101.23.51.17.3.2.6
		sleGponProfile2IpHostTdmControlTName OBJECT-TYPE
			SYNTAX OCTET STRING
			MAX-ACCESS read-write
			STATUS current
			DESCRIPTION
				"The Traffic profile name."
			::= { sleGponProfile2IpHostTdmControl 6 }


--  The ONU profile name.
-- 1.3.6.1.4.1.6296.101.23.51.17.3.2.7
		sleGponProfile2IpHostTdmControlIpHostSvcId OBJECT-TYPE
			SYNTAX INTEGER (1..65535)
			MAX-ACCESS read-write
			STATUS current
			DESCRIPTION
				"The IP host service id of GPON profile."
			::= { sleGponProfile2IpHostTdmControl 7 }


--  1.3.6.1.4.1.6296.101.23.51.17.3.2.8
		sleGponProfile2IpHostTdmControlId OBJECT-TYPE
			SYNTAX INTEGER (1..65535)
			MAX-ACCESS read-write
			STATUS current
			DESCRIPTION
				"The TDM id of GPON profile."
			::= { sleGponProfile2IpHostTdmControl 8 }


--  1.3.6.1.4.1.6296.101.23.51.17.3.3
		sleGponProfile2IpHostTdmNotification OBJECT IDENTIFIER ::= { sleGponProfile2IpHostTdm 3 }


--  1.3.6.1.4.1.6296.101.23.51.17.3.3.1
		sleGponProfile2IpHostTdmSvcCreated NOTIFICATION-TYPE
			OBJECTS { sleGponProfile2IpHostTdmControlRequest, sleGponProfile2IpHostTdmControlTimeStamp, sleGponProfile2IpHostTdmControlReqResult, sleGponProfile2IpHostTdmControlTName, sleGponProfile2IpHostTdmControlIpHostSvcId,
				sleGponProfile2IpHostTdmControlId }
			STATUS current
			DESCRIPTION
				"Description."
			::= { sleGponProfile2IpHostTdmNotification 1 }


--  1.3.6.1.4.1.6296.101.23.51.17.3.3.2
		sleGponProfile2IpHostTdmSvcDeleted NOTIFICATION-TYPE
			OBJECTS { sleGponProfile2IpHostTdmControlRequest, sleGponProfile2IpHostTdmControlTimeStamp, sleGponProfile2IpHostTdmControlReqResult, sleGponProfile2IpHostTdmControlTName, sleGponProfile2IpHostTdmControlIpHostSvcId,
				sleGponProfile2IpHostTdmControlId }
			STATUS current
			DESCRIPTION
				"Description."
			::= { sleGponProfile2IpHostTdmNotification 2 }


--  1.3.6.1.4.1.6296.101.23.51.18
		sleGponProfile2Voip OBJECT IDENTIFIER ::= { sleGponProfile2 18 }


--  1.3.6.1.4.1.6296.101.23.51.18.1
		sleGponProfile2VoipSvc OBJECT IDENTIFIER ::= { sleGponProfile2Voip 1 }


--  1.3.6.1.4.1.6296.101.23.51.18.1.1
		sleGponProfile2VoipSvcTable OBJECT-TYPE
			SYNTAX SEQUENCE OF SleGponProfile2VoipSvcEntry
			MAX-ACCESS not-accessible
			STATUS current
			DESCRIPTION
				"sleGponProfile2VoipSvcTable"
			::= { sleGponProfile2VoipSvc 1 }


--  1.3.6.1.4.1.6296.101.23.51.18.1.1.1
		sleGponProfile2VoipSvcEntry OBJECT-TYPE
			SYNTAX SleGponProfile2VoipSvcEntry
			MAX-ACCESS not-accessible
			STATUS current
			DESCRIPTION
				"key: sleGponProfile2TrafficIndex, sleGponProfile2VoipSvcId"
			INDEX { sleGponProfile2TrafficIndex, sleGponProfile2VoipSvcId }
			::= { sleGponProfile2VoipSvcTable 1 }


		SleGponProfile2VoipSvcEntry ::=
			SEQUENCE {
				sleGponProfile2VoipSvcId
					INTEGER,
				sleGponProfile2VoipSvcProtocolPort
					INTEGER,
				sleGponProfile2VoipSvcProtocolTos
					INTEGER,
				sleGponProfile2VoipSvcManageMethod
					INTEGER,
				sleGponProfile2VoipSvcProtocol
					INTEGER,
				sleGponProfile2VoipSvcIppathUrl
					OCTET STRING,
				sleGponProfile2VoipSvcIppathUser
					OCTET STRING,
				sleGponProfile2VoipSvcIppathPasswd
					OCTET STRING,
				sleGponProfile2VoipSvcVoipProfile
					OCTET STRING,
				sleGponProfile2VoipSvcProtocolType
					INTEGER
			 }

--  1.3.6.1.4.1.6296.101.23.51.18.1.1.1.1
		sleGponProfile2VoipSvcId OBJECT-TYPE
			SYNTAX INTEGER (1..65535)
			MAX-ACCESS read-only
			STATUS current
			DESCRIPTION
				"The VoIP service id."
			::= { sleGponProfile2VoipSvcEntry 1 }


--  1.3.6.1.4.1.6296.101.23.51.18.1.1.1.2
		sleGponProfile2VoipSvcProtocolPort OBJECT-TYPE
			SYNTAX INTEGER (1..65535)
			MAX-ACCESS read-only
			STATUS current
			DESCRIPTION
				"UDP port in port"
			::= { sleGponProfile2VoipSvcEntry 2 }


--  1.3.6.1.4.1.6296.101.23.51.18.1.1.1.3
		sleGponProfile2VoipSvcProtocolTos OBJECT-TYPE
			SYNTAX INTEGER (1..65535)
			MAX-ACCESS read-only
			STATUS current
			DESCRIPTION
				"The UDP port TOS."
			::= { sleGponProfile2VoipSvcEntry 3 }


--  1.3.6.1.4.1.6296.101.23.51.18.1.1.1.4
		sleGponProfile2VoipSvcManageMethod OBJECT-TYPE
			SYNTAX INTEGER
				{
				unUsed(0),
				omci(1),
				ipPath(2)
				}
			MAX-ACCESS read-only
			STATUS current
			DESCRIPTION
				"The management method
				0: unused
				1: omci
				2: ippath"
			::= { sleGponProfile2VoipSvcEntry 4 }


--  1.3.6.1.4.1.6296.101.23.51.18.1.1.1.5
		sleGponProfile2VoipSvcProtocol OBJECT-TYPE
			SYNTAX INTEGER
				{
				sip(1),
				h248(2),
				mgcp(3),
				unUsed(255)
				}
			MAX-ACCESS read-only
			STATUS current
			DESCRIPTION
				"The VoIP service protocol
				1: sip
				2: h248
				3: mgcp
				255: unused"
			::= { sleGponProfile2VoipSvcEntry 5 }


--  1.3.6.1.4.1.6296.101.23.51.18.1.1.1.6
		sleGponProfile2VoipSvcIppathUrl OBJECT-TYPE
			SYNTAX OCTET STRING
			MAX-ACCESS read-only
			STATUS current
			DESCRIPTION
				"The IP path URL."
			::= { sleGponProfile2VoipSvcEntry 6 }


--  1.3.6.1.4.1.6296.101.23.51.18.1.1.1.7
		sleGponProfile2VoipSvcIppathUser OBJECT-TYPE
			SYNTAX OCTET STRING
			MAX-ACCESS read-only
			STATUS current
			DESCRIPTION
				"The IP path user name."
			::= { sleGponProfile2VoipSvcEntry 7 }


--  1.3.6.1.4.1.6296.101.23.51.18.1.1.1.8
		sleGponProfile2VoipSvcIppathPasswd OBJECT-TYPE
			SYNTAX OCTET STRING
			MAX-ACCESS read-only
			STATUS current
			DESCRIPTION
				"The IP path password."
			::= { sleGponProfile2VoipSvcEntry 8 }


--  1.3.6.1.4.1.6296.101.23.51.18.1.1.1.9
		sleGponProfile2VoipSvcVoipProfile OBJECT-TYPE
			SYNTAX OCTET STRING
			MAX-ACCESS read-only
			STATUS current
			DESCRIPTION
				"The VoIP profile name."
			::= { sleGponProfile2VoipSvcEntry 9 }


--  1.3.6.1.4.1.6296.101.23.51.18.1.1.1.10
		sleGponProfile2VoipSvcProtocolType OBJECT-TYPE
			SYNTAX INTEGER
				{
				tcp(6),
				udp(17),
				tlsp(56)
				}
			MAX-ACCESS read-only
			STATUS current
			DESCRIPTION
				"The IP protocol type."
			::= { sleGponProfile2VoipSvcEntry 10 }


--  1.3.6.1.4.1.6296.101.23.51.18.1.2
		sleGponProfile2VoipSvcControl OBJECT IDENTIFIER ::= { sleGponProfile2VoipSvc 2 }


--  1.3.6.1.4.1.6296.101.23.51.18.1.2.1
		sleGponProfile2VoipSvcControlRequest OBJECT-TYPE
			SYNTAX INTEGER
				{
				addVoipSvc(1),
				delVoipSvc(2),
				setUdpPort(3),
				setManageMethod(4),
				setProtocol(5),
				setIppathUrl(6),
				setIppathAuth(7),
				setVoipProfile(8)
				}
			MAX-ACCESS read-write
			STATUS current
			DESCRIPTION
				"The request of a user command"
			::= { sleGponProfile2VoipSvcControl 1 }


--  1.3.6.1.4.1.6296.101.23.51.18.1.2.2
		sleGponProfile2VoipSvcControlStatus OBJECT-TYPE
			SYNTAX SleControlStatusType
			MAX-ACCESS read-only
			STATUS current
			DESCRIPTION
				"The status of user command"
			::= { sleGponProfile2VoipSvcControl 2 }


--  1.3.6.1.4.1.6296.101.23.51.18.1.2.3
		sleGponProfile2VoipSvcControlTimer OBJECT-TYPE
			SYNTAX Gauge32
			MAX-ACCESS read-write
			STATUS current
			DESCRIPTION
				"The maximum time for the manager for a long running user command"
			::= { sleGponProfile2VoipSvcControl 3 }


--  1.3.6.1.4.1.6296.101.23.51.18.1.2.4
		sleGponProfile2VoipSvcControlTimeStamp OBJECT-TYPE
			SYNTAX TimeTicks
			MAX-ACCESS read-only
			STATUS current
			DESCRIPTION
				"The time stamp of the last command(end of command)"
			::= { sleGponProfile2VoipSvcControl 4 }


--  1.3.6.1.4.1.6296.101.23.51.18.1.2.5
		sleGponProfile2VoipSvcControlReqResult OBJECT-TYPE
			SYNTAX SleControlRequestResultType
			MAX-ACCESS read-only
			STATUS current
			DESCRIPTION
				"The result of the last user command"
			::= { sleGponProfile2VoipSvcControl 5 }


--  1.3.6.1.4.1.6296.101.23.51.18.1.2.6
		sleGponProfile2VoipSvcControlTName OBJECT-TYPE
			SYNTAX OCTET STRING
			MAX-ACCESS read-write
			STATUS current
			DESCRIPTION
				"The Traffic profile name."
			::= { sleGponProfile2VoipSvcControl 6 }


--  The ONU profile name.
-- 1.3.6.1.4.1.6296.101.23.51.18.1.2.7
		sleGponProfile2VoipSvcControlId OBJECT-TYPE
			SYNTAX INTEGER (1..65535)
			MAX-ACCESS read-write
			STATUS current
			DESCRIPTION
				"The VoIP service id."
			::= { sleGponProfile2VoipSvcControl 7 }


--  1.3.6.1.4.1.6296.101.23.51.18.1.2.8
		sleGponProfile2VoipSvcControlProtocolPort OBJECT-TYPE
			SYNTAX INTEGER (1..65535)
			MAX-ACCESS read-write
			STATUS current
			DESCRIPTION
				"UDP port in port"
			::= { sleGponProfile2VoipSvcControl 8 }


--  1.3.6.1.4.1.6296.101.23.51.18.1.2.9
		sleGponProfile2VoipSvcControlProtocolTos OBJECT-TYPE
			SYNTAX INTEGER (1..65535)
			MAX-ACCESS read-write
			STATUS current
			DESCRIPTION
				"The UDP port TOS."
			::= { sleGponProfile2VoipSvcControl 9 }


--  1.3.6.1.4.1.6296.101.23.51.18.1.2.10
		sleGponProfile2VoipSvcControlManageMethod OBJECT-TYPE
			SYNTAX INTEGER
				{
				unUsed(0),
				omci(1),
				ipPath(2)
				}
			MAX-ACCESS read-write
			STATUS current
			DESCRIPTION
				"The management method
				0: unused
				1: omci
				2: ippath"
			::= { sleGponProfile2VoipSvcControl 10 }


--  1.3.6.1.4.1.6296.101.23.51.18.1.2.11
		sleGponProfile2VoipSvcControlProtocol OBJECT-TYPE
			SYNTAX INTEGER
				{
				sip(1),
				h248(2),
				mgcp(3),
				unUsed(255)
				}
			MAX-ACCESS read-write
			STATUS current
			DESCRIPTION
				"The VoIP service protocol
				1: sip
				2: h248
				3: mgcp
				255: unused"
			::= { sleGponProfile2VoipSvcControl 11 }


--  1.3.6.1.4.1.6296.101.23.51.18.1.2.12
		sleGponProfile2VoipSvcControlIppathUrl OBJECT-TYPE
			SYNTAX OCTET STRING
			MAX-ACCESS read-write
			STATUS current
			DESCRIPTION
				"The IP path URL."
			::= { sleGponProfile2VoipSvcControl 12 }


--  1.3.6.1.4.1.6296.101.23.51.18.1.2.13
		sleGponProfile2VoipSvcControlIppathUser OBJECT-TYPE
			SYNTAX OCTET STRING
			MAX-ACCESS read-write
			STATUS current
			DESCRIPTION
				"The IP path user name."
			::= { sleGponProfile2VoipSvcControl 13 }


--  1.3.6.1.4.1.6296.101.23.51.18.1.2.14
		sleGponProfile2VoipSvcControlIppathPasswd OBJECT-TYPE
			SYNTAX OCTET STRING
			MAX-ACCESS read-write
			STATUS current
			DESCRIPTION
				"The IP path password."
			::= { sleGponProfile2VoipSvcControl 14 }


--  1.3.6.1.4.1.6296.101.23.51.18.1.2.15
		sleGponProfile2VoipSvcControlVoipProfile OBJECT-TYPE
			SYNTAX OCTET STRING
			MAX-ACCESS read-write
			STATUS current
			DESCRIPTION
				"The VoIP profile name."
			::= { sleGponProfile2VoipSvcControl 15 }


--  1.3.6.1.4.1.6296.101.23.51.18.1.2.16
		sleGponProfile2VoipSvcControlProtocolType OBJECT-TYPE
			SYNTAX INTEGER
				{
				tcp(6),
				udp(17),
				tlsp(56)
				}
			MAX-ACCESS read-write
			STATUS current
			DESCRIPTION
				"The IP protocol type."
			::= { sleGponProfile2VoipSvcControl 16 }


--  1.3.6.1.4.1.6296.101.23.51.18.1.3
		sleGponProfile2VoipSvcNotification OBJECT IDENTIFIER ::= { sleGponProfile2VoipSvc 3 }


--  1.3.6.1.4.1.6296.101.23.51.18.1.3.1
		sleGponProfile2VoipSvcVoipSvcCreated NOTIFICATION-TYPE
			OBJECTS { sleGponProfile2VoipSvcControlRequest, sleGponProfile2VoipSvcControlTimeStamp, sleGponProfile2VoipSvcControlReqResult, sleGponProfile2VoipSvcControlTName, sleGponProfile2VoipSvcControlId
				 }
			STATUS current
			DESCRIPTION
				"Description."
			::= { sleGponProfile2VoipSvcNotification 1 }


--  1.3.6.1.4.1.6296.101.23.51.18.1.3.2
		sleGponProfile2VoipSvcVoipSvcDeleted NOTIFICATION-TYPE
			OBJECTS { sleGponProfile2TdmSvcControlRequest, sleGponProfile2TdmSvcControlTimeStamp, sleGponProfile2TdmSvcControlReqResult, sleGponProfile2TdmSvcControlTName, sleGponProfile2TdmSvcControlId
				 }
			STATUS current
			DESCRIPTION
				"Description."
			::= { sleGponProfile2VoipSvcNotification 2 }


--  1.3.6.1.4.1.6296.101.23.51.18.1.3.3
		sleGponProfile2VoipSvcUdpPortChanged NOTIFICATION-TYPE
			OBJECTS { sleGponProfile2VoipSvcControlRequest, sleGponProfile2VoipSvcControlTimeStamp, sleGponProfile2VoipSvcControlReqResult, sleGponProfile2VoipSvcControlId, sleGponProfile2VoipSvcControlTName,
				sleGponProfile2VoipSvcControlProtocolPort, sleGponProfile2VoipSvcControlProtocolTos, sleGponProfile2VoipSvcControlProtocolType }
			STATUS current
			DESCRIPTION
				"Description."
			::= { sleGponProfile2VoipSvcNotification 3 }


--  1.3.6.1.4.1.6296.101.23.51.18.1.3.4
		sleGponProfile2VoipSvcManageMethodChanged NOTIFICATION-TYPE
			OBJECTS { sleGponProfile2VoipSvcControlRequest, sleGponProfile2VoipSvcControlTimeStamp, sleGponProfile2VoipSvcControlReqResult, sleGponProfile2VoipSvcControlId, sleGponProfile2VoipSvcControlManageMethod,
				sleGponProfile2VoipSvcControlTName }
			STATUS current
			DESCRIPTION
				"Description."
			::= { sleGponProfile2VoipSvcNotification 4 }


--  1.3.6.1.4.1.6296.101.23.51.18.1.3.5
		sleGponProfile2VoipSvcProtocolChanged NOTIFICATION-TYPE
			OBJECTS { sleGponProfile2VoipSvcControlRequest, sleGponProfile2VoipSvcControlTimeStamp, sleGponProfile2VoipSvcControlReqResult, sleGponProfile2VoipSvcControlId, sleGponProfile2VoipSvcControlProtocol,
				sleGponProfile2VoipSvcControlTName }
			STATUS current
			DESCRIPTION
				"Description."
			::= { sleGponProfile2VoipSvcNotification 5 }


--  1.3.6.1.4.1.6296.101.23.51.18.1.3.6
		sleGponProfile2VoipSvcIppathUrlChanged NOTIFICATION-TYPE
			OBJECTS { sleGponProfile2VoipSvcControlRequest, sleGponProfile2VoipSvcControlTimeStamp, sleGponProfile2VoipSvcControlReqResult, sleGponProfile2VoipSvcControlId, sleGponProfile2VoipSvcControlIppathUrl,
				sleGponProfile2VoipSvcControlTName }
			STATUS current
			DESCRIPTION
				"Description."
			::= { sleGponProfile2VoipSvcNotification 6 }


--  1.3.6.1.4.1.6296.101.23.51.18.1.3.7
		sleGponProfile2VoipSvcIppathAuthChanged NOTIFICATION-TYPE
			OBJECTS { sleGponProfile2VoipSvcControlRequest, sleGponProfile2VoipSvcControlTimeStamp, sleGponProfile2VoipSvcControlReqResult, sleGponProfile2VoipSvcControlId, sleGponProfile2VoipSvcControlIppathUser,
				sleGponProfile2VoipSvcControlIppathPasswd, sleGponProfile2VoipSvcControlTName }
			STATUS current
			DESCRIPTION
				"Description."
			::= { sleGponProfile2VoipSvcNotification 7 }


--  1.3.6.1.4.1.6296.101.23.51.18.1.3.8
		sleGponProfile2VoipSvcVoipProfileChanged NOTIFICATION-TYPE
			OBJECTS { sleGponProfile2VoipSvcControlRequest, sleGponProfile2VoipSvcControlTimeStamp, sleGponProfile2VoipSvcControlReqResult, sleGponProfile2VoipSvcControlId, sleGponProfile2VoipSvcControlVoipProfile,
				sleGponProfile2VoipSvcControlTName }
			STATUS current
			DESCRIPTION
				"Description."
			::= { sleGponProfile2VoipSvcNotification 8 }


--  1.3.6.1.4.1.6296.101.23.51.18.2
		sleGponProfile2VoipSvcUni OBJECT IDENTIFIER ::= { sleGponProfile2Voip 2 }


--  1.3.6.1.4.1.6296.101.23.51.18.2.1
		sleGponProfile2VoipSvcUniTable OBJECT-TYPE
			SYNTAX SEQUENCE OF SleGponProfile2VoipSvcUniEntry
			MAX-ACCESS not-accessible
			STATUS current
			DESCRIPTION
				"sleGponProfile2VoipSvcUniTable"
			::= { sleGponProfile2VoipSvcUni 1 }


--  1.3.6.1.4.1.6296.101.23.51.18.2.1.1
		sleGponProfile2VoipSvcUniEntry OBJECT-TYPE
			SYNTAX SleGponProfile2VoipSvcUniEntry
			MAX-ACCESS not-accessible
			STATUS current
			DESCRIPTION
				"key: sleGponProfile2TrafficIndex, sleGponProfile2VoipSvcId, sleGponProfile2VoipSvcUniType, sleGponProfile2VoipSvcUniId"
			INDEX { sleGponProfile2TrafficIndex, sleGponProfile2VoipSvcId, sleGponProfile2VoipSvcUniType, sleGponProfile2VoipSvcUniId }
			::= { sleGponProfile2VoipSvcUniTable 1 }


		SleGponProfile2VoipSvcUniEntry ::=
			SEQUENCE {
				sleGponProfile2VoipSvcUniType
					INTEGER,
				sleGponProfile2VoipSvcUniId
					INTEGER,
				sleGponProfile2VoipSvcUniImpedance
					INTEGER,
				sleGponProfile2VoipSvcUniTransmissionPath
					INTEGER,
				sleGponProfile2VoipSvcUniGainRx
					INTEGER,
				sleGponProfile2VoipSvcUniGainTx
					INTEGER,
				sleGponProfile2VoipSvcUniHoldOverTime
					INTEGER
			 }

--  1.3.6.1.4.1.6296.101.23.51.18.2.1.1.1
		sleGponProfile2VoipSvcUniType OBJECT-TYPE
			SYNTAX INTEGER
				{
				pots(1),
				isdn(2)
				}
			MAX-ACCESS read-only
			STATUS current
			DESCRIPTION
				"The UNI type."
			::= { sleGponProfile2VoipSvcUniEntry 1 }


--  1.3.6.1.4.1.6296.101.23.51.18.2.1.1.2
		sleGponProfile2VoipSvcUniId OBJECT-TYPE
			SYNTAX INTEGER (1..65535)
			MAX-ACCESS read-only
			STATUS current
			DESCRIPTION
				"The UNI id."
			::= { sleGponProfile2VoipSvcUniEntry 2 }


--  1.3.6.1.4.1.6296.101.23.51.18.2.1.1.3
		sleGponProfile2VoipSvcUniImpedance OBJECT-TYPE
			SYNTAX INTEGER
				{
				impedance600(0),
				impedance900(1),
				impedance750(2),
				impedance820(3),
				impedance1050(4)
				}
			MAX-ACCESS read-only
			STATUS current
			DESCRIPTION
				"The UNI impedance."
			::= { sleGponProfile2VoipSvcUniEntry 3 }


--  1.3.6.1.4.1.6296.101.23.51.18.2.1.1.4
		sleGponProfile2VoipSvcUniTransmissionPath OBJECT-TYPE
			SYNTAX INTEGER
				{
				fullTime(0),
				partTime(1)
				}
			MAX-ACCESS read-only
			STATUS current
			DESCRIPTION
				"The transmission path."
			::= { sleGponProfile2VoipSvcUniEntry 4 }


--  1.3.6.1.4.1.6296.101.23.51.18.2.1.1.5
		sleGponProfile2VoipSvcUniGainRx OBJECT-TYPE
			SYNTAX INTEGER (1..65535)
			MAX-ACCESS read-only
			STATUS current
			DESCRIPTION
				"The UNI gain RX."
			::= { sleGponProfile2VoipSvcUniEntry 5 }


--  1.3.6.1.4.1.6296.101.23.51.18.2.1.1.6
		sleGponProfile2VoipSvcUniGainTx OBJECT-TYPE
			SYNTAX INTEGER (1..65535)
			MAX-ACCESS read-only
			STATUS current
			DESCRIPTION
				"The UNI gain TX."
			::= { sleGponProfile2VoipSvcUniEntry 6 }


--  1.3.6.1.4.1.6296.101.23.51.18.2.1.1.7
		sleGponProfile2VoipSvcUniHoldOverTime OBJECT-TYPE
			SYNTAX INTEGER (1..65535)
			MAX-ACCESS read-only
			STATUS current
			DESCRIPTION
				"The hold over time."
			::= { sleGponProfile2VoipSvcUniEntry 7 }


--  1.3.6.1.4.1.6296.101.23.51.18.2.2
		sleGponProfile2VoipSvcUniControl OBJECT IDENTIFIER ::= { sleGponProfile2VoipSvcUni 2 }


--  1.3.6.1.4.1.6296.101.23.51.18.2.2.1
		sleGponProfile2VoipSvcUniControlRequest OBJECT-TYPE
			SYNTAX INTEGER
				{
				addVoipSvcUni(1),
				delVoipSvcUni(2),
				setImpedance(3),
				setTransmissionPath(4),
				setGain(5),
				setHoldOverTime(6)
				}
			MAX-ACCESS read-write
			STATUS current
			DESCRIPTION
				"The request of a user command"
			::= { sleGponProfile2VoipSvcUniControl 1 }


--  1.3.6.1.4.1.6296.101.23.51.18.2.2.2
		sleGponProfile2VoipSvcUniControlStatus OBJECT-TYPE
			SYNTAX SleControlStatusType
			MAX-ACCESS read-only
			STATUS current
			DESCRIPTION
				"The status of user command"
			::= { sleGponProfile2VoipSvcUniControl 2 }


--  1.3.6.1.4.1.6296.101.23.51.18.2.2.3
		sleGponProfile2VoipSvcUniControlTimer OBJECT-TYPE
			SYNTAX Gauge32
			MAX-ACCESS read-write
			STATUS current
			DESCRIPTION
				"The maximum time for the manager for a long running user command"
			::= { sleGponProfile2VoipSvcUniControl 3 }


--  1.3.6.1.4.1.6296.101.23.51.18.2.2.4
		sleGponProfile2VoipSvcUniControlTimeStamp OBJECT-TYPE
			SYNTAX TimeTicks
			MAX-ACCESS read-only
			STATUS current
			DESCRIPTION
				"The time stamp of the last command(end of command)"
			::= { sleGponProfile2VoipSvcUniControl 4 }


--  1.3.6.1.4.1.6296.101.23.51.18.2.2.5
		sleGponProfile2VoipSvcUniControlReqResult OBJECT-TYPE
			SYNTAX SleControlRequestResultType
			MAX-ACCESS read-only
			STATUS current
			DESCRIPTION
				"The result of the last user command"
			::= { sleGponProfile2VoipSvcUniControl 5 }


--  1.3.6.1.4.1.6296.101.23.51.18.2.2.6
		sleGponProfile2VoipSvcUniControlTName OBJECT-TYPE
			SYNTAX OCTET STRING
			MAX-ACCESS read-write
			STATUS current
			DESCRIPTION
				"The Traffic profile name."
			::= { sleGponProfile2VoipSvcUniControl 6 }


--  The ONU profile name.
-- 1.3.6.1.4.1.6296.101.23.51.18.2.2.7
		sleGponProfile2VoipSvcUniControlVoipSvcId OBJECT-TYPE
			SYNTAX INTEGER (1..65535)
			MAX-ACCESS read-write
			STATUS current
			DESCRIPTION
				"The VoIP service id."
			::= { sleGponProfile2VoipSvcUniControl 7 }


--  1.3.6.1.4.1.6296.101.23.51.18.2.2.8
		sleGponProfile2VoipSvcUniControlType OBJECT-TYPE
			SYNTAX INTEGER
				{
				pots(1),
				isdn(2)
				}
			MAX-ACCESS read-write
			STATUS current
			DESCRIPTION
				"The UNI type."
			::= { sleGponProfile2VoipSvcUniControl 8 }


--  1.3.6.1.4.1.6296.101.23.51.18.2.2.9
		sleGponProfile2VoipSvcUniControlId OBJECT-TYPE
			SYNTAX INTEGER (1..65535)
			MAX-ACCESS read-write
			STATUS current
			DESCRIPTION
				"The UNI id."
			::= { sleGponProfile2VoipSvcUniControl 9 }


--  1.3.6.1.4.1.6296.101.23.51.18.2.2.10
		sleGponProfile2VoipSvcUniControlImpedance OBJECT-TYPE
			SYNTAX INTEGER
				{
				impedance600(0),
				impedance900(1),
				impedance750(2),
				impedance820(3),
				impedance1050(4)
				}
			MAX-ACCESS read-write
			STATUS current
			DESCRIPTION
				"The UNI impedance."
			::= { sleGponProfile2VoipSvcUniControl 10 }


--  1.3.6.1.4.1.6296.101.23.51.18.2.2.11
		sleGponProfile2VoipSvcUniControlTransmissionPath OBJECT-TYPE
			SYNTAX INTEGER
				{
				fullTime(0),
				partTime(1)
				}
			MAX-ACCESS read-write
			STATUS current
			DESCRIPTION
				"The transmission path."
			::= { sleGponProfile2VoipSvcUniControl 11 }


--  1.3.6.1.4.1.6296.101.23.51.18.2.2.12
		sleGponProfile2VoipSvcUniControlGainRx OBJECT-TYPE
			SYNTAX INTEGER (1..65535)
			MAX-ACCESS read-write
			STATUS current
			DESCRIPTION
				"The UNI gain RX."
			::= { sleGponProfile2VoipSvcUniControl 12 }


--  1.3.6.1.4.1.6296.101.23.51.18.2.2.13
		sleGponProfile2VoipSvcUniControlGainTx OBJECT-TYPE
			SYNTAX INTEGER (1..65535)
			MAX-ACCESS read-write
			STATUS current
			DESCRIPTION
				"The UNI gain TX."
			::= { sleGponProfile2VoipSvcUniControl 13 }


--  1.3.6.1.4.1.6296.101.23.51.18.2.2.14
		sleGponProfile2VoipSvcUniControlHoldOverTime OBJECT-TYPE
			SYNTAX INTEGER (1..65535)
			MAX-ACCESS read-write
			STATUS current
			DESCRIPTION
				"The hold over time."
			::= { sleGponProfile2VoipSvcUniControl 14 }


--  1.3.6.1.4.1.6296.101.23.51.18.2.3
		sleGponProfile2VoipSvcUniNotification OBJECT IDENTIFIER ::= { sleGponProfile2VoipSvcUni 3 }


--  1.3.6.1.4.1.6296.101.23.51.18.2.3.1
		sleGponProfile2VoipSvcUniVoipSvcUniCreated NOTIFICATION-TYPE
			OBJECTS { sleGponProfile2VoipSvcUniControlRequest, sleGponProfile2VoipSvcUniControlTimeStamp, sleGponProfile2VoipSvcUniControlReqResult, sleGponProfile2VoipSvcUniControlTName, sleGponProfile2VoipSvcUniControlVoipSvcId,
				sleGponProfile2VoipSvcUniControlType, sleGponProfile2VoipSvcUniControlId }
			STATUS current
			DESCRIPTION
				"Description."
			::= { sleGponProfile2VoipSvcUniNotification 1 }


--  1.3.6.1.4.1.6296.101.23.51.18.2.3.2
		sleGponProfile2VoipSvcUniVoipSvcUniDeleted NOTIFICATION-TYPE
			OBJECTS { sleGponProfile2VoipSvcUniControlRequest, sleGponProfile2VoipSvcUniControlTimeStamp, sleGponProfile2VoipSvcUniControlReqResult, sleGponProfile2VoipSvcUniControlTName, sleGponProfile2VoipSvcUniControlVoipSvcId,
				sleGponProfile2VoipSvcUniControlType, sleGponProfile2VoipSvcUniControlId }
			STATUS current
			DESCRIPTION
				"Description."
			::= { sleGponProfile2VoipSvcUniNotification 2 }


--  1.3.6.1.4.1.6296.101.23.51.18.2.3.3
		sleGponProfile2VoipSvcUniImpedanceChanged NOTIFICATION-TYPE
			OBJECTS { sleGponProfile2VoipSvcUniControlRequest, sleGponProfile2VoipSvcUniControlTimeStamp, sleGponProfile2VoipSvcUniControlReqResult, sleGponProfile2VoipSvcUniControlVoipSvcId, sleGponProfile2VoipSvcUniControlId,
				sleGponProfile2VoipSvcUniControlImpedance, sleGponProfile2VoipSvcUniControlTName, sleGponProfile2VoipSvcUniControlType }
			STATUS current
			DESCRIPTION
				"Description."
			::= { sleGponProfile2VoipSvcUniNotification 3 }


--  1.3.6.1.4.1.6296.101.23.51.18.2.3.4
		sleGponProfile2VoipSvcUniTransmissionPathChanged NOTIFICATION-TYPE
			OBJECTS { sleGponProfile2VoipSvcUniControlRequest, sleGponProfile2VoipSvcUniControlTimeStamp, sleGponProfile2VoipSvcUniControlReqResult, sleGponProfile2VoipSvcUniControlVoipSvcId, sleGponProfile2VoipSvcUniControlId,
				sleGponProfile2VoipSvcUniControlTransmissionPath, sleGponProfile2VoipSvcUniControlTName, sleGponProfile2VoipSvcUniControlType }
			STATUS current
			DESCRIPTION
				"Description."
			::= { sleGponProfile2VoipSvcUniNotification 4 }


--  1.3.6.1.4.1.6296.101.23.51.18.2.3.5
		sleGponProfile2VoipSvcUniGainChanged NOTIFICATION-TYPE
			OBJECTS { sleGponProfile2VoipSvcUniControlRequest, sleGponProfile2VoipSvcUniControlTimeStamp, sleGponProfile2VoipSvcUniControlReqResult, sleGponProfile2VoipSvcUniControlVoipSvcId, sleGponProfile2VoipSvcUniControlId,
				sleGponProfile2VoipSvcUniControlGainRx, sleGponProfile2VoipSvcUniControlGainTx, sleGponProfile2VoipSvcUniControlTName, sleGponProfile2VoipSvcUniControlType }
			STATUS current
			DESCRIPTION
				"Description."
			::= { sleGponProfile2VoipSvcUniNotification 5 }


--  1.3.6.1.4.1.6296.101.23.51.18.2.3.6
		sleGponProfile2VoipSvcUniHoldOverTimeChanged NOTIFICATION-TYPE
			OBJECTS { sleGponProfile2VoipSvcUniControlRequest, sleGponProfile2VoipSvcUniControlTimeStamp, sleGponProfile2VoipSvcUniControlReqResult, sleGponProfile2VoipSvcUniControlVoipSvcId, sleGponProfile2VoipSvcUniControlId,
				sleGponProfile2VoipSvcUniControlHoldOverTime, sleGponProfile2VoipSvcUniControlTName, sleGponProfile2VoipSvcUniControlType }
			STATUS current
			DESCRIPTION
				"Description."
			::= { sleGponProfile2VoipSvcUniNotification 6 }


--  1.3.6.1.4.1.6296.101.23.51.19
		sleGponProfile2Tdm OBJECT IDENTIFIER ::= { sleGponProfile2 19 }


--  1.3.6.1.4.1.6296.101.23.51.19.1
		sleGponProfile2TdmTable OBJECT-TYPE
			SYNTAX SEQUENCE OF SleGponProfile2TdmEntry
			MAX-ACCESS not-accessible
			STATUS current
			DESCRIPTION
				"sleGponProfile2TdmTable"
			::= { sleGponProfile2Tdm 1 }


--  1.3.6.1.4.1.6296.101.23.51.19.1.1
		sleGponProfile2TdmEntry OBJECT-TYPE
			SYNTAX SleGponProfile2TdmEntry
			MAX-ACCESS not-accessible
			STATUS current
			DESCRIPTION
				"key: sleGponProfile2TrafficIndex, sleGponProfile2TdmId"
			INDEX { sleGponProfile2TrafficIndex, sleGponProfile2TdmId }
			::= { sleGponProfile2TdmTable 1 }


		SleGponProfile2TdmEntry ::=
			SEQUENCE {
				sleGponProfile2TdmId
					INTEGER,
				sleGponProfile2TdmExpectedType
					INTEGER,
				sleGponProfile2TdmFraming
					INTEGER,
				sleGponProfile2TdmEncoding
					INTEGER,
				sleGponProfile2TdmLineLengthPowerFeed
					INTEGER,
				sleGponProfile2TdmDs1Mode
					INTEGER,
				sleGponProfile2TdmLineType
					INTEGER
			 }

--  1.3.6.1.4.1.6296.101.23.51.19.1.1.1
		sleGponProfile2TdmId OBJECT-TYPE
			SYNTAX INTEGER (1..65535)
			MAX-ACCESS read-only
			STATUS current
			DESCRIPTION
				"The TDM index."
			::= { sleGponProfile2TdmEntry 1 }


--  1.3.6.1.4.1.6296.101.23.51.19.1.1.2
		sleGponProfile2TdmExpectedType OBJECT-TYPE
			SYNTAX INTEGER
				{
				auto(0),
				ds1(13),
				e1(14),
				cDs1E1(16)
				}
			MAX-ACCESS read-only
			STATUS current
			DESCRIPTION
				"The expected type.
				0: auto
				13: ds1
				14: e1
				16: cDs1E1 "
			::= { sleGponProfile2TdmEntry 2 }


--  1.3.6.1.4.1.6296.101.23.51.19.1.1.3
		sleGponProfile2TdmFraming OBJECT-TYPE
			SYNTAX INTEGER
				{
				extendSuperframe(0),
				superframe(1),
				unframed(2),
				g704(3),
				jtG7604(4),
				basigG704(5),
				basigCrc(6),
				basicTs16(7),
				basigCrcTs16(8)
				}
			MAX-ACCESS read-only
			STATUS current
			DESCRIPTION
				"The TDM framing.
				1: extendSuperframe(0)
				2: superframe(1)
				3: unframed(2)
				4: g704(3)
				5: jtG7604(4)
				6: basigG704(5)
				7: basigCrc(6)
				8: basicTs16(7)
				9: basigCrcTs16(8)"
			::= { sleGponProfile2TdmEntry 3 }


--  1.3.6.1.4.1.6296.101.23.51.19.1.1.4
		sleGponProfile2TdmEncoding OBJECT-TYPE
			SYNTAX INTEGER
				{
				b8zs(0),
				ami(1),
				hdb3(2),
				b3zs(3)
				}
			MAX-ACCESS read-only
			STATUS current
			DESCRIPTION
				"The TDM encoding.
				1: b8zs(0)
				2: ami(1)
				3: hdb3(2)
				4: b3zs(3)
				"
			::= { sleGponProfile2TdmEntry 4 }


--  1.3.6.1.4.1.6296.101.23.51.19.1.1.5
		sleGponProfile2TdmLineLengthPowerFeed OBJECT-TYPE
			SYNTAX INTEGER
				{
				ds1Nonpower110(0),
				ds1Nonpower220(1),
				ds1Nonpower330(2),
				ds1Nonpower440(3),
				ds1Nonpower550(4),
				ds1Nonpower660(5),
				ds1Shortpower133(6),
				ds1Shortpowert266(7),
				ds1Shortpower399(8),
				ds1Shortpowert533(9),
				ds1Shortpowert655(10),
				ds1Longpowert0(11),
				ds1Longpowert7dot5(12),
				ds1Longpowert15(13),
				ds1Longpowert22dot5(14),
				ds3powert225(15),
				ds3powert450(16),
				lengthMax(17),
				unUsed(255)
				}
			MAX-ACCESS read-only
			STATUS current
			DESCRIPTION
				"The line length power feedback."
			::= { sleGponProfile2TdmEntry 5 }


--  1.3.6.1.4.1.6296.101.23.51.19.1.1.6
		sleGponProfile2TdmDs1Mode OBJECT-TYPE
			SYNTAX INTEGER
				{
				ds1CpeShort(0),
				ds1CpeLong(1),
				ds1NiuCpeNoPower(2),
				ds1NiuCpewithPower(3),
				unUsed(255)
				}
			MAX-ACCESS read-only
			STATUS current
			DESCRIPTION
				"The TDM down stream 1 mode.
				1: ds1CpeShort(0)
				2: ds1CpeLong(1)
				3: ds1NiuCpeNoPower(2)
				4: ds1NiuCpewithPower(3)
				5: unUsed(255)
				"
			::= { sleGponProfile2TdmEntry 6 }


--  1.3.6.1.4.1.6296.101.23.51.19.1.1.7
		sleGponProfile2TdmLineType OBJECT-TYPE
			SYNTAX INTEGER
				{
				other(0),
				ds3M23(1),
				ds3Syntran(2),
				ds3CbitPartity(3),
				ds3ClearChannel(4),
				e3Framed(5),
				e3Plcp(6)
				}
			MAX-ACCESS read-only
			STATUS current
			DESCRIPTION
				"The TDM line type.
				1: other(0)
				2: ds3M23(1)
				3: ds3Syntran(2)
				4: ds3CbitPartity(3)
				5: ds3ClearChannel(4)
				6: e3Framed(5)
				7: e3Plcp(6)"
			::= { sleGponProfile2TdmEntry 7 }


--  1.3.6.1.4.1.6296.101.23.51.19.2
		sleGponProfile2TdmControl OBJECT IDENTIFIER ::= { sleGponProfile2Tdm 2 }


--  1.3.6.1.4.1.6296.101.23.51.19.2.1
		sleGponProfile2TdmControlRequest OBJECT-TYPE
			SYNTAX INTEGER
				{
				addtdmPort(1),
				delTdmPort(2),
				setExpectedType(3),
				setFraming(4),
				setEncoding(5),
				setLineLengthPowerFeed(6),
				setDs1Mode(7),
				setLineType(8)
				}
			MAX-ACCESS read-write
			STATUS current
			DESCRIPTION
				"The request of a user command"
			::= { sleGponProfile2TdmControl 1 }


--  1.3.6.1.4.1.6296.101.23.51.19.2.2
		sleGponProfile2TdmControlStatus OBJECT-TYPE
			SYNTAX SleControlStatusType
			MAX-ACCESS read-only
			STATUS current
			DESCRIPTION
				"The status of user command"
			::= { sleGponProfile2TdmControl 2 }


--  1.3.6.1.4.1.6296.101.23.51.19.2.3
		sleGponProfile2TdmControlTimer OBJECT-TYPE
			SYNTAX Gauge32
			MAX-ACCESS read-write
			STATUS current
			DESCRIPTION
				"The maximum time for the manager for a long running user command"
			::= { sleGponProfile2TdmControl 3 }


--  1.3.6.1.4.1.6296.101.23.51.19.2.4
		sleGponProfile2TdmControlTimeStamp OBJECT-TYPE
			SYNTAX TimeTicks
			MAX-ACCESS read-only
			STATUS current
			DESCRIPTION
				"The time stamp of the last command(end of command)"
			::= { sleGponProfile2TdmControl 4 }


--  1.3.6.1.4.1.6296.101.23.51.19.2.5
		sleGponProfile2TdmControlReqResult OBJECT-TYPE
			SYNTAX SleControlRequestResultType
			MAX-ACCESS read-only
			STATUS current
			DESCRIPTION
				"The result of the last user command
				"
			::= { sleGponProfile2TdmControl 5 }


--  1.3.6.1.4.1.6296.101.23.51.19.2.6
		sleGponProfile2TdmControlTName OBJECT-TYPE
			SYNTAX OCTET STRING
			MAX-ACCESS read-write
			STATUS current
			DESCRIPTION
				"CES Name"
			::= { sleGponProfile2TdmControl 6 }


--  The ONU profile name.
-- 1.3.6.1.4.1.6296.101.23.51.19.2.7
		sleGponProfile2TdmControlId OBJECT-TYPE
			SYNTAX Integer32
			MAX-ACCESS read-write
			STATUS current
			DESCRIPTION
				"TDM (CES) Port Number"
			::= { sleGponProfile2TdmControl 7 }


--  1.3.6.1.4.1.6296.101.23.51.19.2.8
		sleGponProfile2TdmControlExpectedType OBJECT-TYPE
			SYNTAX INTEGER
				{
				auto(0),
				ds1(1),
				e1(2),
				cDs1E1(3)
				}
			MAX-ACCESS read-write
			STATUS current
			DESCRIPTION
				"CES Port Expected Type
				Autosense (Default value)
				DS1 (value 13 : 1.544 Mbit/s local (T-interface) module))
				E1 (value 14 : 2.048 Mbit/s local (T-interface) module))
				C-DS1/E1 (value 16 : Configurable DS1/E1)"
			::= { sleGponProfile2TdmControl 8 }


--  1.3.6.1.4.1.6296.101.23.51.19.2.9
		sleGponProfile2TdmControlFramig OBJECT-TYPE
			SYNTAX INTEGER
				{
				extendSuperframe(0),
				superframe(1),
				unframed(2),
				g704(3),
				jtG7604(4),
				basigG704(5),
				basigCrc(6),
				basicTs16(7),
				basigCrcTs16(8)
				}
			MAX-ACCESS read-write
			STATUS current
			DESCRIPTION
				"CES Port DS1 Framing"
			::= { sleGponProfile2TdmControl 9 }


--  1.3.6.1.4.1.6296.101.23.51.19.2.10
		sleGponProfile2TdmControlEncoding OBJECT-TYPE
			SYNTAX INTEGER
				{
				b8zs(0),
				ami(1),
				hdb3(2),
				b3zs(3)
				}
			MAX-ACCESS read-write
			STATUS current
			DESCRIPTION
				"CES Port Encoding for DS1 and DS3 interface"
			::= { sleGponProfile2TdmControl 10 }


--  1.3.6.1.4.1.6296.101.23.51.19.2.11
		sleGponProfile2TdmControlLineLengthPowerFeed OBJECT-TYPE
			SYNTAX INTEGER
				{
				ds1Nonpower110(0),
				ds1Nonpower220(1),
				ds1Nonpower330(2),
				ds1Nonpower440(3),
				ds1Nonpower550(4),
				ds1Nonpower660(5),
				ds1Nonpower133(6),
				ds1Nonpower266(7),
				ds1Nonpower399(8),
				ds1Nonpower533(9),
				ds1Nonpower655(10),
				ds1Longpowert0(11),
				ds1Longpowert7dot5(12),
				ds1Longpowert15(13),
				ds1Longpowert22dot5(14),
				ds1Longpowert225(15),
				ds1Longpowert450(16),
				lengthMax(17),
				unUsed(255)
				}
			MAX-ACCESS read-write
			STATUS current
			DESCRIPTION
				"CES Port line length of the twisted pair cable Power Feed Option (db)"
			::= { sleGponProfile2TdmControl 11 }


--  1.3.6.1.4.1.6296.101.23.51.19.2.12
		sleGponProfile2TdmControlDs1Mode OBJECT-TYPE
			SYNTAX INTEGER
				{
				ds1CpeShort(0),
				ds1CpeLong(1),
				ds1NiuCpeNoPower(2),
				ds1NiuCpewithPower(3),
				unUsed(255)
				}
			MAX-ACCESS read-write
			STATUS current
			DESCRIPTION
				"Select connect CES Port DS1 mode"
			::= { sleGponProfile2TdmControl 12 }


--  1.3.6.1.4.1.6296.101.23.51.19.2.13
		sleGponProfile2TdmControlLineType OBJECT-TYPE
			SYNTAX INTEGER
				{
				other(0),
				ds3M23(1),
				ds3Syntran(2),
				ds3CbitPartity(3),
				ds3ClearChannel(4),
				e3Framed(5),
				e3Plcp(6)
				}
			MAX-ACCESS read-write
			STATUS current
			DESCRIPTION
				"CES Port line type for DS3 for E3 interface"
			::= { sleGponProfile2TdmControl 13 }


--  1.3.6.1.4.1.6296.101.23.51.19.3
		sleGponProfile2TdmNotification OBJECT IDENTIFIER ::= { sleGponProfile2Tdm 3 }


--  1.3.6.1.4.1.6296.101.23.51.19.3.1
		sleGponProfile2TdmPortCreated NOTIFICATION-TYPE
			OBJECTS { sleGponProfile2TdmControlRequest, sleGponProfile2TdmControlTimeStamp, sleGponProfile2TdmControlReqResult, sleGponProfile2TdmControlId, sleGponProfile2TdmControlTName
				 }
			STATUS current
			DESCRIPTION
				"Description."
			::= { sleGponProfile2TdmNotification 1 }


--  1.3.6.1.4.1.6296.101.23.51.19.3.2
		sleGponProfile2TdmPortDeleted NOTIFICATION-TYPE
			OBJECTS { sleGponProfile2TdmControlRequest, sleGponProfile2TdmControlTimeStamp, sleGponProfile2TdmControlReqResult, sleGponProfile2TdmControlId, sleGponProfile2TdmControlTName
				 }
			STATUS current
			DESCRIPTION
				"Description."
			::= { sleGponProfile2TdmNotification 2 }


--  1.3.6.1.4.1.6296.101.23.51.19.3.3
		sleGponProfile2TdmExpectedTypeChanged NOTIFICATION-TYPE
			OBJECTS { sleGponProfile2TdmControlRequest, sleGponProfile2TdmControlTimeStamp, sleGponProfile2TdmControlReqResult, sleGponProfile2TdmControlId, sleGponProfile2TdmControlExpectedType
				 }
			STATUS current
			DESCRIPTION
				"Description."
			::= { sleGponProfile2TdmNotification 3 }


--  1.3.6.1.4.1.6296.101.23.51.19.3.4
		sleGponProfile2TdmFramingChanged NOTIFICATION-TYPE
			OBJECTS { sleGponProfile2TdmControlRequest, sleGponProfile2TdmControlTimeStamp, sleGponProfile2TdmControlReqResult, sleGponProfile2TdmControlId, sleGponProfile2TdmControlFramig
				 }
			STATUS current
			DESCRIPTION
				"Description."
			::= { sleGponProfile2TdmNotification 4 }


--  1.3.6.1.4.1.6296.101.23.51.19.3.5
		sleGponProfile2TdmEncodingChanged NOTIFICATION-TYPE
			OBJECTS { sleGponProfile2TdmControlRequest, sleGponProfile2TdmControlTimeStamp, sleGponProfile2TdmControlReqResult, sleGponProfile2TdmControlId, sleGponProfile2TdmControlEncoding
				 }
			STATUS current
			DESCRIPTION
				"Description."
			::= { sleGponProfile2TdmNotification 5 }


--  1.3.6.1.4.1.6296.101.23.51.19.3.6
		sleGponProfile2TdmLineLengthPowerFeedChanged NOTIFICATION-TYPE
			OBJECTS { sleGponProfile2TdmControlRequest, sleGponProfile2TdmControlTimeStamp, sleGponProfile2TdmControlReqResult, sleGponProfile2TdmControlId, sleGponProfile2TdmControlLineLengthPowerFeed
				 }
			STATUS current
			DESCRIPTION
				"Description."
			::= { sleGponProfile2TdmNotification 6 }


--  1.3.6.1.4.1.6296.101.23.51.19.3.7
		sleGponProfile2TdmDs1ModeChanged NOTIFICATION-TYPE
			OBJECTS { sleGponProfile2TdmControlRequest, sleGponProfile2TdmControlTimeStamp, sleGponProfile2TdmControlReqResult, sleGponProfile2TdmControlId, sleGponProfile2TdmControlDs1Mode
				 }
			STATUS current
			DESCRIPTION
				"Description."
			::= { sleGponProfile2TdmNotification 7 }


--  1.3.6.1.4.1.6296.101.23.51.19.3.8
		sleGponProfile2TdmLineTypeChanged NOTIFICATION-TYPE
			OBJECTS { sleGponProfile2TdmControlRequest, sleGponProfile2TdmControlTimeStamp, sleGponProfile2TdmControlReqResult, sleGponProfile2TdmControlId, sleGponProfile2TdmControlLineType
				 }
			STATUS current
			DESCRIPTION
				"Description."
			::= { sleGponProfile2TdmNotification 8 }


--  1.3.6.1.4.1.6296.101.23.51.20
		sleGponProfile2TdmSvc OBJECT IDENTIFIER ::= { sleGponProfile2 20 }


--  1.3.6.1.4.1.6296.101.23.51.20.1
		sleGponProfile2TdmSvcTable OBJECT-TYPE
			SYNTAX SEQUENCE OF SleGponProfile2TdmSvcEntry
			MAX-ACCESS not-accessible
			STATUS current
			DESCRIPTION
				"sleGponProfile2TdmSvcTable"
			::= { sleGponProfile2TdmSvc 1 }


--  1.3.6.1.4.1.6296.101.23.51.20.1.1
		sleGponProfile2TdmSvcEntry OBJECT-TYPE
			SYNTAX SleGponProfile2TdmSvcEntry
			MAX-ACCESS not-accessible
			STATUS current
			DESCRIPTION
				"key: sleGponProfile2TrafficIndex, sleGponProfile2TdmSvcId, sleGponProfile2IpHostTdmId"
			INDEX { sleGponProfile2TrafficIndex, sleGponProfile2TdmSvcId, sleGponProfile2IpHostTdmId }
			::= { sleGponProfile2TdmSvcTable 1 }


		SleGponProfile2TdmSvcEntry ::=
			SEQUENCE {
				sleGponProfile2TdmSvcId
					INTEGER,
				sleGponProfile2TdmSvcMode
					INTEGER,
				sleGponProfile2TdmSvcTdmPwProfileName
					OCTET STRING,
				sleGponProfile2TdmSvcTimeSlot
					OCTET STRING,
				sleGponProfile2TdmSvcFilterMode
					INTEGER,
				sleGponProfile2TdmSvcFilter
					OCTET STRING,
				sleGponProfile2TdmSvcEthDestMac
					OCTET STRING,
				sleGponProfile2TdmSvcEthVid
					INTEGER,
				sleGponProfile2TdmSvcEthCoS
					INTEGER,
				sleGponProfile2TdmSvcTranPayloadEcid
					INTEGER,
				sleGponProfile2TdmSvcTranSignallingEcid
					INTEGER,
				sleGponProfile2TdmSvcRecvPayloadEcid
					INTEGER,
				sleGponProfile2TdmSvcRecvSignallingEcid
					INTEGER,
				sleGponProfile2TdmSvcExpectPayloadEcid
					INTEGER,
				sleGponProfile2TdmSvcExpectSignallingEcid
					INTEGER,
				sleGponProfile2TdmSvcProtocolPort
					INTEGER,
				sleGponProfile2TdmSvcProtocolTos
					INTEGER,
				sleGponProfile2TdmSvcFarEndIpURL
					OCTET STRING,
				sleGponProfile2TdmSvcMplsLabelIndicator
					INTEGER,
				sleGponProfile2TdmSvcMplsPwDirection
					INTEGER,
				sleGponProfile2TdmSvcMplsPwLabelUp
					INTEGER,
				sleGponProfile2TdmSvcMplsPwLabelDown
					INTEGER,
				sleGponProfile2TdmSvcMplsPwLabelExp
					INTEGER,
				sleGponProfile2TdmSvcMplsPwTunnelDirection
					INTEGER,
				sleGponProfile2TdmSvcMplsPwTunnelLabelUp
					INTEGER,
				sleGponProfile2TdmSvcMplsPwTunnelLabelDown
					INTEGER,
				sleGponProfile2TdmSvcMplsPwTunnelLabelExp
					INTEGER,
				sleGponProfile2TdmSvcCesBuffCdvTolerance
					INTEGER,
				sleGponProfile2TdmSvcCesChannelAssociateSignal
					INTEGER,
				sleGponProfile2TdmSvcProtocolType
					INTEGER
			 }

--  1.3.6.1.4.1.6296.101.23.51.20.1.1.1
		sleGponProfile2TdmSvcId OBJECT-TYPE
			SYNTAX INTEGER (1..65535)
			MAX-ACCESS read-only
			STATUS current
			DESCRIPTION
				"Select TDM mode"
			::= { sleGponProfile2TdmSvcEntry 1 }


--  1.3.6.1.4.1.6296.101.23.51.20.1.1.2
		sleGponProfile2TdmSvcMode OBJECT-TYPE
			SYNTAX INTEGER
				{
				pwMef8(1),
				pwIp(2),
				pwMpls(3),
				pwMplsGem(4),
				sdh(5)
				}
			MAX-ACCESS read-only
			STATUS current
			DESCRIPTION
				"The TDM service mode.
				1: pwMef8(1)
				2: pwIp(2)
				3: pwMpls(3)
				4: pwMplsGem(4)
				5: sdh(5)"
			::= { sleGponProfile2TdmSvcEntry 2 }


--  1.3.6.1.4.1.6296.101.23.51.20.1.1.3
		sleGponProfile2TdmSvcTdmPwProfileName OBJECT-TYPE
			SYNTAX OCTET STRING
			MAX-ACCESS read-only
			STATUS current
			DESCRIPTION
				"TDM Pseudowire Profile Name"
			::= { sleGponProfile2TdmSvcEntry 3 }


--  1.3.6.1.4.1.6296.101.23.51.20.1.1.4
		sleGponProfile2TdmSvcTimeSlot OBJECT-TYPE
			SYNTAX OCTET STRING
			MAX-ACCESS read-only
			STATUS current
			DESCRIPTION
				"The time slot."
			::= { sleGponProfile2TdmSvcEntry 4 }


--  1.3.6.1.4.1.6296.101.23.51.20.1.1.5
		sleGponProfile2TdmSvcFilterMode OBJECT-TYPE
			SYNTAX INTEGER
				{
				unUsed(0),
				allow(1),
				deny(2)
				}
			MAX-ACCESS read-only
			STATUS current
			DESCRIPTION
				"Allow or deny that untagged fowarding operation"
			::= { sleGponProfile2TdmSvcEntry 5 }


--  1.3.6.1.4.1.6296.101.23.51.20.1.1.6
		sleGponProfile2TdmSvcFilter OBJECT-TYPE
			SYNTAX OCTET STRING
			MAX-ACCESS read-only
			STATUS current
			DESCRIPTION
				"VLAN Tagging Filter Data"
			::= { sleGponProfile2TdmSvcEntry 6 }


--  1.3.6.1.4.1.6296.101.23.51.20.1.1.7
		sleGponProfile2TdmSvcEthDestMac OBJECT-TYPE
			SYNTAX OCTET STRING
			MAX-ACCESS read-only
			STATUS current
			DESCRIPTION
				"The Destination MAC address"
			::= { sleGponProfile2TdmSvcEntry 7 }


--  1.3.6.1.4.1.6296.101.23.51.20.1.1.8
		sleGponProfile2TdmSvcEthVid OBJECT-TYPE
			SYNTAX INTEGER (1..65535)
			MAX-ACCESS read-only
			STATUS current
			DESCRIPTION
				"The Ethernet Flow Tag Policy VID Value"
			::= { sleGponProfile2TdmSvcEntry 8 }


--  1.3.6.1.4.1.6296.101.23.51.20.1.1.9
		sleGponProfile2TdmSvcEthCoS OBJECT-TYPE
			SYNTAX INTEGER (1..65535)
			MAX-ACCESS read-only
			STATUS current
			DESCRIPTION
				"The Ethernet Flow Tag Policy COS Value"
			::= { sleGponProfile2TdmSvcEntry 9 }


--  1.3.6.1.4.1.6296.101.23.51.20.1.1.10
		sleGponProfile2TdmSvcTranPayloadEcid OBJECT-TYPE
			SYNTAX INTEGER (1..65535)
			MAX-ACCESS read-only
			STATUS current
			DESCRIPTION
				"The Trasmit Payload ECID"
			::= { sleGponProfile2TdmSvcEntry 10 }


--  1.3.6.1.4.1.6296.101.23.51.20.1.1.11
		sleGponProfile2TdmSvcTranSignallingEcid OBJECT-TYPE
			SYNTAX INTEGER (1..65535)
			MAX-ACCESS read-only
			STATUS current
			DESCRIPTION
				"The Trasmit Signalling ECID"
			::= { sleGponProfile2TdmSvcEntry 11 }


--  1.3.6.1.4.1.6296.101.23.51.20.1.1.12
		sleGponProfile2TdmSvcRecvPayloadEcid OBJECT-TYPE
			SYNTAX INTEGER (1..65535)
			MAX-ACCESS read-only
			STATUS current
			DESCRIPTION
				"The Recive Payload ECID"
			::= { sleGponProfile2TdmSvcEntry 12 }


--  1.3.6.1.4.1.6296.101.23.51.20.1.1.13
		sleGponProfile2TdmSvcRecvSignallingEcid OBJECT-TYPE
			SYNTAX INTEGER (1..65535)
			MAX-ACCESS read-only
			STATUS current
			DESCRIPTION
				"The Recive Signalling ECID"
			::= { sleGponProfile2TdmSvcEntry 13 }


--  1.3.6.1.4.1.6296.101.23.51.20.1.1.14
		sleGponProfile2TdmSvcExpectPayloadEcid OBJECT-TYPE
			SYNTAX INTEGER (1..65535)
			MAX-ACCESS read-only
			STATUS current
			DESCRIPTION
				"The Expected Payload ECID"
			::= { sleGponProfile2TdmSvcEntry 14 }


--  1.3.6.1.4.1.6296.101.23.51.20.1.1.15
		sleGponProfile2TdmSvcExpectSignallingEcid OBJECT-TYPE
			SYNTAX INTEGER (1..65535)
			MAX-ACCESS read-only
			STATUS current
			DESCRIPTION
				"The Expected Signalling ECID"
			::= { sleGponProfile2TdmSvcEntry 15 }


--  1.3.6.1.4.1.6296.101.23.51.20.1.1.16
		sleGponProfile2TdmSvcProtocolPort OBJECT-TYPE
			SYNTAX INTEGER (1..65535)
			MAX-ACCESS read-only
			STATUS current
			DESCRIPTION
				"The UDP port number"
			::= { sleGponProfile2TdmSvcEntry 16 }


--  1.3.6.1.4.1.6296.101.23.51.20.1.1.17
		sleGponProfile2TdmSvcProtocolTos OBJECT-TYPE
			SYNTAX INTEGER (1..65535)
			MAX-ACCESS read-only
			STATUS current
			DESCRIPTION
				"The UDP TOS value"
			::= { sleGponProfile2TdmSvcEntry 17 }


--  1.3.6.1.4.1.6296.101.23.51.20.1.1.18
		sleGponProfile2TdmSvcFarEndIpURL OBJECT-TYPE
			SYNTAX OCTET STRING
			MAX-ACCESS read-only
			STATUS current
			DESCRIPTION
				"The PW IP mode far end termination IP URL"
			::= { sleGponProfile2TdmSvcEntry 18 }


--  1.3.6.1.4.1.6296.101.23.51.20.1.1.19
		sleGponProfile2TdmSvcMplsLabelIndicator OBJECT-TYPE
			SYNTAX INTEGER
				{
				single(0),
				double(1),
				unUsed(255)
				}
			MAX-ACCESS read-only
			STATUS current
			DESCRIPTION
				"The MPLS Label stacking situation"
			::= { sleGponProfile2TdmSvcEntry 19 }


--  1.3.6.1.4.1.6296.101.23.51.20.1.1.20
		sleGponProfile2TdmSvcMplsPwDirection OBJECT-TYPE
			SYNTAX INTEGER
				{
				usOnly(0),
				dsOnly(1),
				bidirectional(2),
				unUsed(255)
				}
			MAX-ACCESS read-only
			STATUS current
			DESCRIPTION
				"The Inner MPLS direction"
			::= { sleGponProfile2TdmSvcEntry 20 }


--  1.3.6.1.4.1.6296.101.23.51.20.1.1.21
		sleGponProfile2TdmSvcMplsPwLabelUp OBJECT-TYPE
			SYNTAX INTEGER (1..65535)
			MAX-ACCESS read-only
			STATUS current
			DESCRIPTION
				"The Label of the Inner MPLS pseudowire (Uplink)"
			::= { sleGponProfile2TdmSvcEntry 21 }


--  1.3.6.1.4.1.6296.101.23.51.20.1.1.22
		sleGponProfile2TdmSvcMplsPwLabelDown OBJECT-TYPE
			SYNTAX INTEGER (1..65535)
			MAX-ACCESS read-only
			STATUS current
			DESCRIPTION
				"The Label of the Inner MPLS pseudowire (Downlink)"
			::= { sleGponProfile2TdmSvcEntry 22 }


--  1.3.6.1.4.1.6296.101.23.51.20.1.1.23
		sleGponProfile2TdmSvcMplsPwLabelExp OBJECT-TYPE
			SYNTAX INTEGER (1..65535)
			MAX-ACCESS read-only
			STATUS current
			DESCRIPTION
				"The Label of the Inner MPLS pseudowire (Expert)"
			::= { sleGponProfile2TdmSvcEntry 23 }


--  1.3.6.1.4.1.6296.101.23.51.20.1.1.24
		sleGponProfile2TdmSvcMplsPwTunnelDirection OBJECT-TYPE
			SYNTAX INTEGER
				{
				usOnly(0),
				dsOnly(1),
				bidirectional(2)
				}
			MAX-ACCESS read-only
			STATUS current
			DESCRIPTION
				"The Outer MPLS direction"
			::= { sleGponProfile2TdmSvcEntry 24 }


--  1.3.6.1.4.1.6296.101.23.51.20.1.1.25
		sleGponProfile2TdmSvcMplsPwTunnelLabelUp OBJECT-TYPE
			SYNTAX INTEGER (1..65535)
			MAX-ACCESS read-only
			STATUS current
			DESCRIPTION
				"The Label of the Outer label for MPLS tunnel (Uplink)"
			::= { sleGponProfile2TdmSvcEntry 25 }


--  1.3.6.1.4.1.6296.101.23.51.20.1.1.26
		sleGponProfile2TdmSvcMplsPwTunnelLabelDown OBJECT-TYPE
			SYNTAX INTEGER (1..65535)
			MAX-ACCESS read-only
			STATUS current
			DESCRIPTION
				"The Label of the Outer label for MPLS tunnel (Downlink)"
			::= { sleGponProfile2TdmSvcEntry 26 }


--  1.3.6.1.4.1.6296.101.23.51.20.1.1.27
		sleGponProfile2TdmSvcMplsPwTunnelLabelExp OBJECT-TYPE
			SYNTAX INTEGER (1..65535)
			MAX-ACCESS read-only
			STATUS current
			DESCRIPTION
				"The Label of the Outer label for MPLS tunnel (Expert)"
			::= { sleGponProfile2TdmSvcEntry 27 }


--  1.3.6.1.4.1.6296.101.23.51.20.1.1.28
		sleGponProfile2TdmSvcCesBuffCdvTolerance OBJECT-TYPE
			SYNTAX INTEGER (1..65535)
			MAX-ACCESS read-only
			STATUS current
			DESCRIPTION
				"sleGponProfile2TdmSvcCesBuffCdvTolerance"
			::= { sleGponProfile2TdmSvcEntry 28 }


--  1.3.6.1.4.1.6296.101.23.51.20.1.1.29
		sleGponProfile2TdmSvcCesChannelAssociateSignal OBJECT-TYPE
			SYNTAX INTEGER
				{
				basic(0),
				e1Cas(1),
				sfCas(2),
				ds1EsfCas(3),
				j2Cas(4),
				unUsed(255)
				}
			MAX-ACCESS read-only
			STATUS current
			DESCRIPTION
				"sleGponProfile2TdmSvcCesChannelAssociateSignal"
			::= { sleGponProfile2TdmSvcEntry 29 }


--  1.3.6.1.4.1.6296.101.23.51.20.1.1.30
		sleGponProfile2TdmSvcProtocolType OBJECT-TYPE
			SYNTAX INTEGER
				{
				tcp(6),
				udp(17),
				tlsp(56)
				}
			MAX-ACCESS read-write
			STATUS current
			DESCRIPTION
				"The IP protocol type."
			::= { sleGponProfile2TdmSvcEntry 30 }


--  1.3.6.1.4.1.6296.101.23.51.20.2
		sleGponProfile2TdmSvcControl OBJECT IDENTIFIER ::= { sleGponProfile2TdmSvc 2 }


--  1.3.6.1.4.1.6296.101.23.51.20.2.1
		sleGponProfile2TdmSvcControlRequest OBJECT-TYPE
			SYNTAX INTEGER
				{
				addTdmService(1),
				delTemService(2),
				setTdmPwProfile(3),
				setVlanFilter(4),
				setEthDestMac(5),
				setEthTagPolicy(6),
				setTranEcid(7),
				setRecvEcid(8),
				setExpectEcid(9),
				setUdpPort(10),
				setFarEndIp(11),
				setMplsLabelIndicator(12),
				setMplsPwDirection(13),
				setMplsPwLabel(14),
				setMplsPwTunnelDirection(15),
				setMplsPwTunnelLabel(16),
				setCesBuffCdvTolerance(17),
				setCesChannelAssociateSignal(18)
				}
			MAX-ACCESS read-write
			STATUS current
			DESCRIPTION
				"The request of a user command"
			::= { sleGponProfile2TdmSvcControl 1 }


--  1.3.6.1.4.1.6296.101.23.51.20.2.2
		sleGponProfile2TdmSvcControlStatus OBJECT-TYPE
			SYNTAX SleControlStatusType
			MAX-ACCESS read-only
			STATUS current
			DESCRIPTION
				"The status of user command"
			::= { sleGponProfile2TdmSvcControl 2 }


--  1.3.6.1.4.1.6296.101.23.51.20.2.3
		sleGponProfile2TdmSvcControlTimer OBJECT-TYPE
			SYNTAX Gauge32
			MAX-ACCESS read-write
			STATUS current
			DESCRIPTION
				"The maximum time for the manager for a long running user command"
			::= { sleGponProfile2TdmSvcControl 3 }


--  1.3.6.1.4.1.6296.101.23.51.20.2.4
		sleGponProfile2TdmSvcControlTimeStamp OBJECT-TYPE
			SYNTAX TimeTicks
			MAX-ACCESS read-only
			STATUS current
			DESCRIPTION
				"The time stamp of the last command(end of command)"
			::= { sleGponProfile2TdmSvcControl 4 }


--  1.3.6.1.4.1.6296.101.23.51.20.2.5
		sleGponProfile2TdmSvcControlReqResult OBJECT-TYPE
			SYNTAX SleControlRequestResultType
			MAX-ACCESS read-only
			STATUS current
			DESCRIPTION
				"The result of the last user command"
			::= { sleGponProfile2TdmSvcControl 5 }


--  1.3.6.1.4.1.6296.101.23.51.20.2.6
		sleGponProfile2TdmSvcControlTName OBJECT-TYPE
			SYNTAX OCTET STRING
			MAX-ACCESS read-write
			STATUS current
			DESCRIPTION
				"TDM Service Name"
			::= { sleGponProfile2TdmSvcControl 6 }


--  The ONU profile name.
-- 1.3.6.1.4.1.6296.101.23.51.20.2.7
		sleGponProfile2TdmSvcControlTdmId OBJECT-TYPE
			SYNTAX Integer32
			MAX-ACCESS read-write
			STATUS current
			DESCRIPTION
				"TDM (CES) Port Number"
			::= { sleGponProfile2TdmSvcControl 7 }


--  1.3.6.1.4.1.6296.101.23.51.20.2.8
		sleGponProfile2TdmSvcControlId OBJECT-TYPE
			SYNTAX INTEGER (1..65535)
			MAX-ACCESS read-write
			STATUS current
			DESCRIPTION
				"TDM Service ID"
			::= { sleGponProfile2TdmSvcControl 8 }


--  1.3.6.1.4.1.6296.101.23.51.20.2.9
		sleGponProfile2TdmSvcControlMode OBJECT-TYPE
			SYNTAX INTEGER
				{
				pwMef8(1),
				pwIp(2),
				pwMpls(3),
				pwMplsGem(4),
				sdh(5)
				}
			MAX-ACCESS read-write
			STATUS current
			DESCRIPTION
				"Select TDM mode"
			::= { sleGponProfile2TdmSvcControl 9 }


--  1.3.6.1.4.1.6296.101.23.51.20.2.10
		sleGponProfile2TdmSvcControlTdmPwProfileName OBJECT-TYPE
			SYNTAX OCTET STRING
			MAX-ACCESS read-write
			STATUS current
			DESCRIPTION
				"TDM Pseudowire Profile Name"
			::= { sleGponProfile2TdmSvcControl 10 }


--  1.3.6.1.4.1.6296.101.23.51.20.2.11
		sleGponProfile2TdmSvcControlTimeSlot OBJECT-TYPE
			SYNTAX OCTET STRING
			MAX-ACCESS read-write
			STATUS current
			DESCRIPTION
				"Time slot"
			::= { sleGponProfile2TdmSvcControl 11 }


--  1.3.6.1.4.1.6296.101.23.51.20.2.12
		sleGponProfile2TdmSvcControlFilterMode OBJECT-TYPE
			SYNTAX INTEGER
				{
				unUsed(0),
				allow(1),
				deny(2)
				}
			MAX-ACCESS read-write
			STATUS current
			DESCRIPTION
				"Allow or deny that untagged fowarding operation"
			::= { sleGponProfile2TdmSvcControl 12 }


--  1.3.6.1.4.1.6296.101.23.51.20.2.13
		sleGponProfile2TdmSvcControlFilter OBJECT-TYPE
			SYNTAX OCTET STRING
			MAX-ACCESS read-write
			STATUS current
			DESCRIPTION
				"VLAN Tagging Filter Data"
			::= { sleGponProfile2TdmSvcControl 13 }


--  1.3.6.1.4.1.6296.101.23.51.20.2.14
		sleGponProfile2TdmSvcControlEthDestMac OBJECT-TYPE
			SYNTAX OCTET STRING
			MAX-ACCESS read-write
			STATUS current
			DESCRIPTION
				"Destination MAC address"
			::= { sleGponProfile2TdmSvcControl 14 }


--  1.3.6.1.4.1.6296.101.23.51.20.2.15
		sleGponProfile2TdmSvcControlEthVid OBJECT-TYPE
			SYNTAX INTEGER (1..65535)
			MAX-ACCESS read-write
			STATUS current
			DESCRIPTION
				"Ethernet Flow Tag Policy VID Value"
			::= { sleGponProfile2TdmSvcControl 15 }


--  1.3.6.1.4.1.6296.101.23.51.20.2.16
		sleGponProfile2TdmSvcControlEthCoS OBJECT-TYPE
			SYNTAX INTEGER (1..65535)
			MAX-ACCESS read-write
			STATUS current
			DESCRIPTION
				"Ethernet Flow Tag Policy COS Value"
			::= { sleGponProfile2TdmSvcControl 16 }


--  1.3.6.1.4.1.6296.101.23.51.20.2.17
		sleGponProfile2TdmSvcControlTranPayloadEcid OBJECT-TYPE
			SYNTAX INTEGER (1..65535)
			MAX-ACCESS read-write
			STATUS current
			DESCRIPTION
				"Trasmit Payload ECID"
			::= { sleGponProfile2TdmSvcControl 17 }


--  1.3.6.1.4.1.6296.101.23.51.20.2.18
		sleGponProfile2TdmSvcControlTranSignallingEcid OBJECT-TYPE
			SYNTAX INTEGER (1..65535)
			MAX-ACCESS read-write
			STATUS current
			DESCRIPTION
				"Trasmit Signalling ECID"
			::= { sleGponProfile2TdmSvcControl 18 }


--  1.3.6.1.4.1.6296.101.23.51.20.2.19
		sleGponProfile2TdmSvcControlRecvPayloadEcid OBJECT-TYPE
			SYNTAX INTEGER (1..65535)
			MAX-ACCESS read-write
			STATUS current
			DESCRIPTION
				"Recive Payload ECID"
			::= { sleGponProfile2TdmSvcControl 19 }


--  1.3.6.1.4.1.6296.101.23.51.20.2.20
		sleGponProfile2TdmSvcControlRecvSignallingEcid OBJECT-TYPE
			SYNTAX INTEGER (1..65535)
			MAX-ACCESS read-write
			STATUS current
			DESCRIPTION
				"Recive Signalling ECID"
			::= { sleGponProfile2TdmSvcControl 20 }


--  1.3.6.1.4.1.6296.101.23.51.20.2.21
		sleGponProfile2TdmSvcControlExpectPayloadEcid OBJECT-TYPE
			SYNTAX INTEGER (1..65535)
			MAX-ACCESS read-write
			STATUS current
			DESCRIPTION
				"Expected Payload ECID"
			::= { sleGponProfile2TdmSvcControl 21 }


--  1.3.6.1.4.1.6296.101.23.51.20.2.22
		sleGponProfile2TdmSvcControlExpectSignallingEcid OBJECT-TYPE
			SYNTAX INTEGER (1..65535)
			MAX-ACCESS read-write
			STATUS current
			DESCRIPTION
				"Expected Signalling ECID"
			::= { sleGponProfile2TdmSvcControl 22 }


--  1.3.6.1.4.1.6296.101.23.51.20.2.23
		sleGponProfile2TdmSvcControlProtocolPort OBJECT-TYPE
			SYNTAX INTEGER (1..65535)
			MAX-ACCESS read-write
			STATUS current
			DESCRIPTION
				"UDP port number"
			::= { sleGponProfile2TdmSvcControl 23 }


--  1.3.6.1.4.1.6296.101.23.51.20.2.24
		sleGponProfile2TdmSvcControlProtocolTos OBJECT-TYPE
			SYNTAX INTEGER (1..65535)
			MAX-ACCESS read-write
			STATUS current
			DESCRIPTION
				"UDP TOS value"
			::= { sleGponProfile2TdmSvcControl 24 }


--  1.3.6.1.4.1.6296.101.23.51.20.2.25
		sleGponProfile2TdmSvcControlFarEndIpURL OBJECT-TYPE
			SYNTAX OCTET STRING
			MAX-ACCESS read-write
			STATUS current
			DESCRIPTION
				"PW IP mode far end termination IP URL"
			::= { sleGponProfile2TdmSvcControl 25 }


--  1.3.6.1.4.1.6296.101.23.51.20.2.26
		sleGponProfile2TdmSvcControlMplsLabelIndicator OBJECT-TYPE
			SYNTAX INTEGER
				{
				single(0),
				double(1),
				unUsed(255)
				}
			MAX-ACCESS read-write
			STATUS current
			DESCRIPTION
				"MPLS Label stacking situation"
			::= { sleGponProfile2TdmSvcControl 26 }


--  1.3.6.1.4.1.6296.101.23.51.20.2.27
		sleGponProfile2TdmSvcControlMplsPwDirection OBJECT-TYPE
			SYNTAX INTEGER
				{
				usOnly(0),
				dsOnly(1),
				bidirectional(2),
				unUsed(255)
				}
			MAX-ACCESS read-write
			STATUS current
			DESCRIPTION
				"Inner MPLS direction"
			::= { sleGponProfile2TdmSvcControl 27 }


--  1.3.6.1.4.1.6296.101.23.51.20.2.28
		sleGponProfile2TdmSvcControlMplsPwLabelUp OBJECT-TYPE
			SYNTAX INTEGER (1..65535)
			MAX-ACCESS read-write
			STATUS current
			DESCRIPTION
				"Label of the Inner MPLS pseudowire (Uplink)"
			::= { sleGponProfile2TdmSvcControl 28 }


--  1.3.6.1.4.1.6296.101.23.51.20.2.29
		sleGponProfile2TdmSvcControlMplsPwLabelDown OBJECT-TYPE
			SYNTAX INTEGER (1..65535)
			MAX-ACCESS read-write
			STATUS current
			DESCRIPTION
				"Label of the Inner MPLS pseudowire (Downlink)"
			::= { sleGponProfile2TdmSvcControl 29 }


--  1.3.6.1.4.1.6296.101.23.51.20.2.30
		sleGponProfile2TdmSvcControlMplsPwLabelExp OBJECT-TYPE
			SYNTAX INTEGER (1..65535)
			MAX-ACCESS read-write
			STATUS current
			DESCRIPTION
				"Label of the Inner MPLS pseudowire (Expert)"
			::= { sleGponProfile2TdmSvcControl 30 }


--  1.3.6.1.4.1.6296.101.23.51.20.2.31
		sleGponProfile2TdmSvcControlMplsPwTunnelDirection OBJECT-TYPE
			SYNTAX INTEGER
				{
				usOnly(0),
				dsOnly(1),
				bidirectional(2)
				}
			MAX-ACCESS read-write
			STATUS current
			DESCRIPTION
				"Outer MPLS direction"
			::= { sleGponProfile2TdmSvcControl 31 }


--  1.3.6.1.4.1.6296.101.23.51.20.2.32
		sleGponProfile2TdmSvcControlMplsPwTunnelLabelUp OBJECT-TYPE
			SYNTAX INTEGER (1..65535)
			MAX-ACCESS read-write
			STATUS current
			DESCRIPTION
				"Label of the Outer label for MPLS tunnel (Uplink)"
			::= { sleGponProfile2TdmSvcControl 32 }


--  1.3.6.1.4.1.6296.101.23.51.20.2.33
		sleGponProfile2TdmSvcControlMplsPwTunnelLabelDown OBJECT-TYPE
			SYNTAX INTEGER (1..65535)
			MAX-ACCESS read-write
			STATUS current
			DESCRIPTION
				"Label of the Outer label for MPLS tunnel (Downlink)"
			::= { sleGponProfile2TdmSvcControl 33 }


--  1.3.6.1.4.1.6296.101.23.51.20.2.34
		sleGponProfile2TdmSvcControlMplsPwTunnelLabelExp OBJECT-TYPE
			SYNTAX INTEGER (1..65535)
			MAX-ACCESS read-write
			STATUS current
			DESCRIPTION
				"Label of the Outer label for MPLS tunnel (Expert)"
			::= { sleGponProfile2TdmSvcControl 34 }


--  1.3.6.1.4.1.6296.101.23.51.20.2.35
		sleGponProfile2TdmSvcControlCesBuffCdvTolerance OBJECT-TYPE
			SYNTAX INTEGER (1..65535)
			MAX-ACCESS read-write
			STATUS current
			DESCRIPTION
				"sleGponProfile2TdmSvcControlCesBuffCdvTolerance (unused)"
			::= { sleGponProfile2TdmSvcControl 35 }


--  1.3.6.1.4.1.6296.101.23.51.20.2.36
		sleGponProfile2TdmSvcControlCesChannelAssociateSignal OBJECT-TYPE
			SYNTAX INTEGER
				{
				basic(0),
				e1Cas(1),
				sfCas(2),
				ds1EsfCas(3),
				j2Cas(4),
				unUsed(255)
				}
			MAX-ACCESS read-write
			STATUS current
			DESCRIPTION
				"sleGponProfile2TdmSvcControlCesChannelAssociateSignal (unused)"
			::= { sleGponProfile2TdmSvcControl 36 }


--  1.3.6.1.4.1.6296.101.23.51.20.2.37
		sleGponProfile2TdmSvcControlProtocolType OBJECT-TYPE
			SYNTAX INTEGER
				{
				tcp(6),
				udp(17),
				tlsp(56)
				}
			MAX-ACCESS read-write
			STATUS current
			DESCRIPTION
				"The IP protocol type."
			::= { sleGponProfile2TdmSvcControl 37 }


--  1.3.6.1.4.1.6296.101.23.51.20.3
		sleGponProfile2TdmSvcNotification OBJECT IDENTIFIER ::= { sleGponProfile2TdmSvc 3 }


--  1.3.6.1.4.1.6296.101.23.51.20.3.1
		sleGponProfile2TdmSvcTdmServiceCreated NOTIFICATION-TYPE
			OBJECTS { sleGponProfile2TdmSvcControlRequest, sleGponProfile2TdmSvcControlTimeStamp, sleGponProfile2TdmSvcControlReqResult, sleGponProfile2TdmSvcControlId, sleGponProfile2TdmSvcControlTdmId,
				sleGponProfile2TdmSvcControlMode }
			STATUS current
			DESCRIPTION
				"Description."
			::= { sleGponProfile2TdmSvcNotification 1 }


--  1.3.6.1.4.1.6296.101.23.51.20.3.2
		sleGponProfile2TdmSvcTdmServiceDeleted NOTIFICATION-TYPE
			OBJECTS { sleGponProfile2TdmSvcControlId, sleGponProfile2TdmSvcControlTName, sleGponProfile2TdmSvcControlTdmId, sleGponProfile2TdmSvcControlMode, sleGponProfile2TdmSvcControlRequest,
				sleGponProfile2TdmSvcControlTimeStamp, sleGponProfile2TdmSvcControlReqResult }
			STATUS current
			DESCRIPTION
				"Description."
			::= { sleGponProfile2TdmSvcNotification 2 }


--  1.3.6.1.4.1.6296.101.23.51.20.3.3
		sleGponProfile2TdmSvcTdmPwProfileChanged NOTIFICATION-TYPE
			OBJECTS { sleGponProfile2TdmSvcControlTdmId, sleGponProfile2TdmSvcControlId, sleGponProfile2TdmSvcControlTdmPwProfileName, sleGponProfile2TdmSvcControlTimeSlot, sleGponProfile2TdmSvcControlRequest,
				sleGponProfile2TdmSvcControlTimeStamp, sleGponProfile2TdmSvcControlReqResult }
			STATUS current
			DESCRIPTION
				"Description."
			::= { sleGponProfile2TdmSvcNotification 3 }


--  1.3.6.1.4.1.6296.101.23.51.20.3.4
		sleGponProfile2TdmSvcTdmVlanFilterChanged NOTIFICATION-TYPE
			OBJECTS { sleGponProfile2TdmSvcControlId, sleGponProfile2TdmSvcControlRequest, sleGponProfile2TdmSvcControlTimeStamp, sleGponProfile2TdmSvcControlReqResult, sleGponProfile2TdmSvcControlFilterMode,
				sleGponProfile2TdmSvcControlFilter }
			STATUS current
			DESCRIPTION
				"Description."
			::= { sleGponProfile2TdmSvcNotification 4 }


--  1.3.6.1.4.1.6296.101.23.51.20.3.5
		sleGponProfile2TdmSvcTdmEthDestMacChanged NOTIFICATION-TYPE
			OBJECTS { sleGponProfile2TdmSvcControlTdmId, sleGponProfile2TdmSvcControlId, sleGponProfile2TdmSvcControlEthDestMac, sleGponProfile2TdmSvcControlRequest, sleGponProfile2TdmSvcControlTimeStamp,
				sleGponProfile2TdmSvcControlReqResult }
			STATUS current
			DESCRIPTION
				"Description."
			::= { sleGponProfile2TdmSvcNotification 5 }


--  1.3.6.1.4.1.6296.101.23.51.20.3.6
		sleGponProfile2TdmSvcTdmEthTagPolicyChanged NOTIFICATION-TYPE
			OBJECTS { sleGponProfile2TdmSvcControlTdmId, sleGponProfile2TdmSvcControlId, sleGponProfile2TdmSvcControlEthVid, sleGponProfile2TdmSvcControlEthCoS, sleGponProfile2TdmSvcControlRequest,
				sleGponProfile2TdmSvcControlTimeStamp, sleGponProfile2TdmSvcControlReqResult }
			STATUS current
			DESCRIPTION
				"Description."
			::= { sleGponProfile2TdmSvcNotification 6 }


--  1.3.6.1.4.1.6296.101.23.51.20.3.7
		sleGponProfile2TdmSvcTdmTranEcidChanged NOTIFICATION-TYPE
			OBJECTS { sleGponProfile2TdmSvcControlTranPayloadEcid, sleGponProfile2TdmSvcControlTranSignallingEcid, sleGponProfile2TdmSvcControlTdmId, sleGponProfile2TdmSvcControlId, sleGponProfile2TdmSvcControlRequest,
				sleGponProfile2TdmSvcControlTimeStamp, sleGponProfile2TdmSvcControlReqResult }
			STATUS current
			DESCRIPTION
				"Description."
			::= { sleGponProfile2TdmSvcNotification 7 }


--  1.3.6.1.4.1.6296.101.23.51.20.3.8
		sleGponProfile2TdmSvcTdmRecvEcidChanged NOTIFICATION-TYPE
			OBJECTS { sleGponProfile2TdmSvcControlTdmId, sleGponProfile2TdmSvcControlId, sleGponProfile2TdmSvcControlRecvPayloadEcid, sleGponProfile2TdmSvcControlRecvSignallingEcid, sleGponProfile2TdmSvcControlRequest,
				sleGponProfile2TdmSvcControlTimeStamp, sleGponProfile2TdmSvcControlReqResult }
			STATUS current
			DESCRIPTION
				"Description."
			::= { sleGponProfile2TdmSvcNotification 8 }


--  1.3.6.1.4.1.6296.101.23.51.20.3.9
		sleGponProfile2TdmSvcTdmExpectEcidChanged NOTIFICATION-TYPE
			OBJECTS { sleGponProfile2TdmSvcControlTdmId, sleGponProfile2TdmSvcControlId, sleGponProfile2TdmSvcControlExpectPayloadEcid, sleGponProfile2TdmSvcControlExpectSignallingEcid, sleGponProfile2TdmSvcControlRequest,
				sleGponProfile2TdmSvcControlTimeStamp, sleGponProfile2TdmSvcControlReqResult }
			STATUS current
			DESCRIPTION
				"Description."
			::= { sleGponProfile2TdmSvcNotification 9 }


--  1.3.6.1.4.1.6296.101.23.51.20.3.10
		sleGponProfile2TdmSvcTdmUdpPortChanged NOTIFICATION-TYPE
			OBJECTS { sleGponProfile2TdmSvcControlTdmId, sleGponProfile2TdmSvcControlId, sleGponProfile2TdmSvcControlRequest, sleGponProfile2TdmSvcControlTimeStamp, sleGponProfile2TdmSvcControlReqResult,
				sleGponProfile2TdmSvcControlProtocolPort, sleGponProfile2TdmSvcControlProtocolTos, sleGponProfile2TdmSvcControlProtocolType }
			STATUS current
			DESCRIPTION
				"Description."
			::= { sleGponProfile2TdmSvcNotification 10 }


--  1.3.6.1.4.1.6296.101.23.51.20.3.11
		sleGponProfile2TdmSvcTdmFarEndIpChanged NOTIFICATION-TYPE
			OBJECTS { sleGponProfile2TdmSvcControlTdmId, sleGponProfile2TdmSvcControlId, sleGponProfile2TdmSvcControlFarEndIpURL, sleGponProfile2TdmSvcControlRequest, sleGponProfile2TdmSvcControlTimeStamp,
				sleGponProfile2TdmSvcControlReqResult }
			STATUS current
			DESCRIPTION
				"Description."
			::= { sleGponProfile2TdmSvcNotification 11 }


--  1.3.6.1.4.1.6296.101.23.51.20.3.12
		sleGponProfile2TdmSvcMplsLabelIndicatorChanged NOTIFICATION-TYPE
			OBJECTS { sleGponProfile2TdmSvcControlTdmId, sleGponProfile2TdmSvcControlId, sleGponProfile2TdmSvcControlMplsLabelIndicator, sleGponProfile2TdmSvcControlRequest, sleGponProfile2TdmSvcControlTimeStamp,
				sleGponProfile2TdmSvcControlReqResult }
			STATUS current
			DESCRIPTION
				"Description."
			::= { sleGponProfile2TdmSvcNotification 12 }


--  1.3.6.1.4.1.6296.101.23.51.20.3.13
		sleGponProfile2TdmSvcMplsPwDirectionChanged NOTIFICATION-TYPE
			OBJECTS { sleGponProfile2TdmSvcControlTdmId, sleGponProfile2TdmSvcControlId, sleGponProfile2TdmSvcControlMplsPwDirection, sleGponProfile2TdmSvcControlRequest, sleGponProfile2TdmSvcControlTimeStamp,
				sleGponProfile2TdmSvcControlReqResult }
			STATUS current
			DESCRIPTION
				"Description."
			::= { sleGponProfile2TdmSvcNotification 13 }


--  1.3.6.1.4.1.6296.101.23.51.20.3.14
		sleGponProfile2TdmSvcMplsPwLabelChanged NOTIFICATION-TYPE
			OBJECTS { sleGponProfile2TdmSvcControlTdmId, sleGponProfile2TdmSvcControlId, sleGponProfile2TdmSvcControlMplsPwLabelUp, sleGponProfile2TdmSvcControlMplsPwLabelDown, sleGponProfile2TdmSvcControlMplsPwLabelExp,
				sleGponProfile2TdmSvcControlRequest, sleGponProfile2TdmSvcControlTimeStamp, sleGponProfile2TdmSvcControlReqResult }
			STATUS current
			DESCRIPTION
				"Description."
			::= { sleGponProfile2TdmSvcNotification 14 }


--  1.3.6.1.4.1.6296.101.23.51.20.3.15
		sleGponProfile2TdmSvcMplsPwTunnelDirectionChanged NOTIFICATION-TYPE
			OBJECTS { sleGponProfile2TdmSvcControlTdmId, sleGponProfile2TdmSvcControlId, sleGponProfile2TdmSvcControlMplsPwTunnelDirection, sleGponProfile2TdmSvcControlRequest, sleGponProfile2TdmSvcControlTimeStamp,
				sleGponProfile2TdmSvcControlReqResult }
			STATUS current
			DESCRIPTION
				"Description."
			::= { sleGponProfile2TdmSvcNotification 15 }


--  1.3.6.1.4.1.6296.101.23.51.20.3.16
		sleGponProfile2TdmSvcMplsPwTunnelLabelChanged NOTIFICATION-TYPE
			OBJECTS { sleGponProfile2TdmSvcControlTdmId, sleGponProfile2TdmSvcControlId, sleGponProfile2TdmSvcControlMplsPwTunnelLabelUp, sleGponProfile2TdmSvcControlMplsPwTunnelLabelDown, sleGponProfile2TdmSvcControlMplsPwTunnelLabelExp,
				sleGponProfile2TdmSvcControlRequest, sleGponProfile2TdmSvcControlTimeStamp, sleGponProfile2TdmSvcControlReqResult }
			STATUS current
			DESCRIPTION
				"Description."
			::= { sleGponProfile2TdmSvcNotification 16 }


--  1.3.6.1.4.1.6296.101.23.51.20.3.17
		sleGponProfile2TdmSvcCesBuffCdvToleranceChanged NOTIFICATION-TYPE
			OBJECTS { sleGponProfile2TdmSvcControlTdmId, sleGponProfile2TdmSvcControlId, sleGponProfile2TdmSvcControlCesBuffCdvTolerance, sleGponProfile2TdmSvcControlRequest, sleGponProfile2TdmSvcControlTimeStamp,
				sleGponProfile2TdmSvcControlReqResult }
			STATUS current
			DESCRIPTION
				"Description."
			::= { sleGponProfile2TdmSvcNotification 17 }


--  1.3.6.1.4.1.6296.101.23.51.20.3.18
		sleGponProfile2TdmSvcCesChannelAssociateSignalChanged NOTIFICATION-TYPE
			OBJECTS { sleGponProfile2TdmSvcControlTdmId, sleGponProfile2TdmSvcControlId, sleGponProfile2TdmSvcControlCesChannelAssociateSignal, sleGponProfile2TdmSvcControlRequest, sleGponProfile2TdmSvcControlTimeStamp,
				sleGponProfile2TdmSvcControlReqResult }
			STATUS current
			DESCRIPTION
				"Description."
			::= { sleGponProfile2TdmSvcNotification 18 }


--  1.3.6.1.4.1.6296.101.23.51.21
		sleGponProfile2BridgeGem OBJECT IDENTIFIER ::= { sleGponProfile2 21 }


--  1.3.6.1.4.1.6296.101.23.51.21.1
		sleGponProfile2BridgeGemTable OBJECT-TYPE
			SYNTAX SEQUENCE OF SleGponProfile2BridgeGemEntry
			MAX-ACCESS not-accessible
			STATUS current
			DESCRIPTION
				"sleGponProfile2BridgeGemTable"
			::= { sleGponProfile2BridgeGem 1 }


--  1.3.6.1.4.1.6296.101.23.51.21.1.1
		sleGponProfile2BridgeGemEntry OBJECT-TYPE
			SYNTAX SleGponProfile2BridgeGemEntry
			MAX-ACCESS not-accessible
			STATUS current
			DESCRIPTION
				"key: sleGponProfile2TrafficIndex, sleGponProfile2BridgeId, sleGponProfile2BridgeGemId"
			INDEX { sleGponProfile2TrafficIndex, sleGponProfile2BridgeId, sleGponProfile2BridgeGemId }
			::= { sleGponProfile2BridgeGemTable 1 }


		SleGponProfile2BridgeGemEntry ::=
			SEQUENCE {
				sleGponProfile2BridgeGemId
					INTEGER,
				sleGponProfile2BridgeGemVlanFilterMode
					INTEGER,
				sleGponProfile2BridgeGemVlanFilter
					INTEGER
			 }

--  1.3.6.1.4.1.6296.101.23.51.21.1.1.1
		sleGponProfile2BridgeGemId OBJECT-TYPE
			SYNTAX INTEGER (1..65535)
			MAX-ACCESS read-only
			STATUS current
			DESCRIPTION
				"The Gem ID"
			::= { sleGponProfile2BridgeGemEntry 1 }


--  1.3.6.1.4.1.6296.101.23.51.21.1.1.2
		sleGponProfile2BridgeGemVlanFilterMode OBJECT-TYPE
			SYNTAX INTEGER
				{
				unUsed(0),
				allow(1),
				derny(2)
				}
			MAX-ACCESS read-only
			STATUS current
			DESCRIPTION
				"Allow or deny that untagged fowarding operation"
			::= { sleGponProfile2BridgeGemEntry 2 }


--  1.3.6.1.4.1.6296.101.23.51.21.1.1.3
		sleGponProfile2BridgeGemVlanFilter OBJECT-TYPE
			SYNTAX INTEGER (1..65535)
			MAX-ACCESS read-only
			STATUS current
			DESCRIPTION
				"The Vlan filter."
			::= { sleGponProfile2BridgeGemEntry 3 }


--  1.3.6.1.4.1.6296.101.23.51.21.2
		sleGponProfile2BridgeGemControl OBJECT IDENTIFIER ::= { sleGponProfile2BridgeGem 2 }


--  1.3.6.1.4.1.6296.101.23.51.21.2.1
		sleGponProfile2BridgeGemControlRequest OBJECT-TYPE
			SYNTAX INTEGER
				{
				addBridgeGem(1),
				delBridgeGem(2),
				setVlanFilter(3)
				}
			MAX-ACCESS read-write
			STATUS current
			DESCRIPTION
				"The request of a user command"
			::= { sleGponProfile2BridgeGemControl 1 }


--  1.3.6.1.4.1.6296.101.23.51.21.2.2
		sleGponProfile2BridgeGemControlStatus OBJECT-TYPE
			SYNTAX SleControlStatusType
			MAX-ACCESS read-only
			STATUS current
			DESCRIPTION
				"The status of user command"
			::= { sleGponProfile2BridgeGemControl 2 }


--  1.3.6.1.4.1.6296.101.23.51.21.2.3
		sleGponProfile2BridgeGemControlTimer OBJECT-TYPE
			SYNTAX Gauge32
			MAX-ACCESS read-write
			STATUS current
			DESCRIPTION
				"The maximum time for the manager for a long running user command"
			::= { sleGponProfile2BridgeGemControl 3 }


--  1.3.6.1.4.1.6296.101.23.51.21.2.4
		sleGponProfile2BridgeGemControlTimeStamp OBJECT-TYPE
			SYNTAX TimeTicks
			MAX-ACCESS read-only
			STATUS current
			DESCRIPTION
				"The time stamp of the last command(end of command)"
			::= { sleGponProfile2BridgeGemControl 4 }


--  1.3.6.1.4.1.6296.101.23.51.21.2.5
		sleGponProfile2BridgeGemControlReqResult OBJECT-TYPE
			SYNTAX SleControlRequestResultType
			MAX-ACCESS read-only
			STATUS current
			DESCRIPTION
				"The result of the last user command"
			::= { sleGponProfile2BridgeGemControl 5 }


--  1.3.6.1.4.1.6296.101.23.51.21.2.6
		sleGponProfile2BridgeGemControlTName OBJECT-TYPE
			SYNTAX OCTET STRING
			MAX-ACCESS read-write
			STATUS current
			DESCRIPTION
				"The Traffic profile name."
			::= { sleGponProfile2BridgeGemControl 6 }


--  The ONU profile name.
-- 1.3.6.1.4.1.6296.101.23.51.21.2.7
		sleGponProfile2BridgeGemControlBridgeId OBJECT-TYPE
			SYNTAX INTEGER (1..65535)
			MAX-ACCESS read-write
			STATUS current
			DESCRIPTION
				"The Bridge ID."
			::= { sleGponProfile2BridgeGemControl 7 }


--  1.3.6.1.4.1.6296.101.23.51.21.2.8
		sleGponProfile2BridgeGemControlId OBJECT-TYPE
			SYNTAX INTEGER (1..65535)
			MAX-ACCESS read-write
			STATUS current
			DESCRIPTION
				"The Gem ID"
			::= { sleGponProfile2BridgeGemControl 8 }


--  1.3.6.1.4.1.6296.101.23.51.21.2.9
		sleGponProfile2BridgeGemControlVlanFilterMode OBJECT-TYPE
			SYNTAX INTEGER
				{
				unUsed(0),
				allow(1),
				derny(2)
				}
			MAX-ACCESS read-write
			STATUS current
			DESCRIPTION
				"Allow or deny that untagged fowarding operation"
			::= { sleGponProfile2BridgeGemControl 9 }


--  1.3.6.1.4.1.6296.101.23.51.21.2.10
		sleGponProfile2BridgeGemControlVlanFilter OBJECT-TYPE
			SYNTAX INTEGER (1..65535)
			MAX-ACCESS read-write
			STATUS current
			DESCRIPTION
				"The VLAN Tagging Filter Data"
			::= { sleGponProfile2BridgeGemControl 10 }


--  1.3.6.1.4.1.6296.101.23.51.21.3
		sleGponProfile2BridgeGemNotification OBJECT IDENTIFIER ::= { sleGponProfile2BridgeGem 3 }


--  1.3.6.1.4.1.6296.101.23.51.21.3.1
		sleGponProfile2BridgeGemBridgeGemCreated NOTIFICATION-TYPE
			OBJECTS { sleGponProfile2BridgeGemControlRequest, sleGponProfile2BridgeGemControlTimeStamp, sleGponProfile2BridgeGemControlReqResult, sleGponProfile2BridgeGemControlTName, sleGponProfile2BridgeGemControlBridgeId,
				sleGponProfile2BridgeGemControlId }
			STATUS current
			DESCRIPTION
				"Description."
			::= { sleGponProfile2BridgeGemNotification 1 }


--  1.3.6.1.4.1.6296.101.23.51.21.3.2
		sleGponProfile2BridgeGemBridgeGemDeleted NOTIFICATION-TYPE
			OBJECTS { sleGponProfile2BridgeGemControlRequest, sleGponProfile2BridgeGemControlTimeStamp, sleGponProfile2BridgeGemControlReqResult, sleGponProfile2BridgeGemControlTName, sleGponProfile2BridgeGemControlBridgeId,
				sleGponProfile2BridgeGemControlId }
			STATUS current
			DESCRIPTION
				"Description."
			::= { sleGponProfile2BridgeGemNotification 2 }


--  1.3.6.1.4.1.6296.101.23.51.21.3.3
		sleGponProfile2BridgeGemVlanFilterChanged NOTIFICATION-TYPE
			OBJECTS { sleGponProfile2BridgeGemControlRequest, sleGponProfile2BridgeGemControlTimeStamp, sleGponProfile2BridgeGemControlReqResult, sleGponProfile2BridgeGemControlBridgeId, sleGponProfile2BridgeGemControlId,
				sleGponProfile2BridgeGemControlVlanFilterMode, sleGponProfile2BridgeGemControlVlanFilter }
			STATUS current
			DESCRIPTION
				"Description."
			::= { sleGponProfile2BridgeGemNotification 3 }


--  1.3.6.1.4.1.6296.101.23.51.22
		sleGponProfile2BridgeTdm OBJECT IDENTIFIER ::= { sleGponProfile2 22 }


--  1.3.6.1.4.1.6296.101.23.51.22.1
		sleGponProfile2BridgeTdmTable OBJECT-TYPE
			SYNTAX SEQUENCE OF SleGponProfile2BridgeTdmEntry
			MAX-ACCESS not-accessible
			STATUS current
			DESCRIPTION
				"sleGponProfile2BridgeTdmTable"
			::= { sleGponProfile2BridgeTdm 1 }


--  1.3.6.1.4.1.6296.101.23.51.22.1.1
		sleGponProfile2BridgeTdmEntry OBJECT-TYPE
			SYNTAX SleGponProfile2BridgeTdmEntry
			MAX-ACCESS not-accessible
			STATUS current
			DESCRIPTION
				"key: sleGponProfile2TrafficIndex, sleGponProfile2BridgeId, sleGponProfile2BridgeTdmId"
			INDEX { sleGponProfile2TrafficIndex, sleGponProfile2BridgeId, sleGponProfile2BridgeTdmId }
			::= { sleGponProfile2BridgeTdmTable 1 }


		SleGponProfile2BridgeTdmEntry ::=
			SEQUENCE {
				sleGponProfile2BridgeTdmId
					INTEGER
			 }

--  1.3.6.1.4.1.6296.101.23.51.22.1.1.1
		sleGponProfile2BridgeTdmId OBJECT-TYPE
			SYNTAX INTEGER (1..65535)
			MAX-ACCESS read-only
			STATUS current
			DESCRIPTION
				"The TDM Service link."
			::= { sleGponProfile2BridgeTdmEntry 1 }


--  1.3.6.1.4.1.6296.101.23.51.22.2
		sleGponProfile2BridgeTdmControl OBJECT IDENTIFIER ::= { sleGponProfile2BridgeTdm 2 }


--  1.3.6.1.4.1.6296.101.23.51.22.2.1
		sleGponProfile2BridgeTdmControlRequest OBJECT-TYPE
			SYNTAX INTEGER
				{
				addBridgeTdm(1),
				delBridgeTdm(2)
				}
			MAX-ACCESS read-write
			STATUS current
			DESCRIPTION
				"The request of a user command"
			::= { sleGponProfile2BridgeTdmControl 1 }


--  1.3.6.1.4.1.6296.101.23.51.22.2.2
		sleGponProfile2BridgeTdmControlStatus OBJECT-TYPE
			SYNTAX SleControlStatusType
			MAX-ACCESS read-only
			STATUS current
			DESCRIPTION
				"The status of user command"
			::= { sleGponProfile2BridgeTdmControl 2 }


--  1.3.6.1.4.1.6296.101.23.51.22.2.3
		sleGponProfile2BridgeTdmControlTimer OBJECT-TYPE
			SYNTAX Gauge32
			MAX-ACCESS read-write
			STATUS current
			DESCRIPTION
				"The maximum time for the manager for a long running user command"
			::= { sleGponProfile2BridgeTdmControl 3 }


--  1.3.6.1.4.1.6296.101.23.51.22.2.4
		sleGponProfile2BridgeTdmControlTimeStamp OBJECT-TYPE
			SYNTAX TimeTicks
			MAX-ACCESS read-only
			STATUS current
			DESCRIPTION
				"The time stamp of the last command(end of command)"
			::= { sleGponProfile2BridgeTdmControl 4 }


--  1.3.6.1.4.1.6296.101.23.51.22.2.5
		sleGponProfile2BridgeTdmControlReqResult OBJECT-TYPE
			SYNTAX SleControlRequestResultType
			MAX-ACCESS read-only
			STATUS current
			DESCRIPTION
				"The result of the last user command"
			::= { sleGponProfile2BridgeTdmControl 5 }


--  1.3.6.1.4.1.6296.101.23.51.22.2.6
		sleGponProfile2BridgeTdmControlTName OBJECT-TYPE
			SYNTAX OCTET STRING
			MAX-ACCESS read-write
			STATUS current
			DESCRIPTION
				"The Traffic profile name."
			::= { sleGponProfile2BridgeTdmControl 6 }


--  The ONU profile name.
-- 1.3.6.1.4.1.6296.101.23.51.22.2.7
		sleGponProfile2BridgeTdmControlBridgeId OBJECT-TYPE
			SYNTAX INTEGER (1..65535)
			MAX-ACCESS read-write
			STATUS current
			DESCRIPTION
				"The Bridge ID."
			::= { sleGponProfile2BridgeTdmControl 7 }


--  1.3.6.1.4.1.6296.101.23.51.22.2.8
		sleGponProfile2BridgeTdmControlId OBJECT-TYPE
			SYNTAX INTEGER (1..65535)
			MAX-ACCESS read-write
			STATUS current
			DESCRIPTION
				"The TDM Service link."
			::= { sleGponProfile2BridgeTdmControl 8 }


--  1.3.6.1.4.1.6296.101.23.51.22.3
		sleGponProfile2BridgeTdmNotification OBJECT IDENTIFIER ::= { sleGponProfile2BridgeTdm 3 }


--  1.3.6.1.4.1.6296.101.23.51.22.3.1
		sleGponProfile2BridgeTdmBridgeTdmCreated NOTIFICATION-TYPE
			OBJECTS { sleGponProfile2BridgeTdmControlTName, sleGponProfile2BridgeTdmControlBridgeId, sleGponProfile2BridgeTdmControlId, sleGponProfile2BridgeTdmControlRequest, sleGponProfile2BridgeTdmControlTimeStamp,
				sleGponProfile2BridgeTdmControlReqResult }
			STATUS current
			DESCRIPTION
				"Description."
			::= { sleGponProfile2BridgeTdmNotification 1 }


--  1.3.6.1.4.1.6296.101.23.51.22.3.2
		sleGponProfile2BridgeTdmBridgeTdmDeleted NOTIFICATION-TYPE
			OBJECTS { sleGponProfile2BridgeTdmControlTName, sleGponProfile2BridgeTdmControlBridgeId, sleGponProfile2BridgeTdmControlId, sleGponProfile2BridgeTdmControlRequest, sleGponProfile2BridgeTdmControlTimeStamp,
				sleGponProfile2BridgeTdmControlReqResult }
			STATUS current
			DESCRIPTION
				"Description."
			::= { sleGponProfile2BridgeTdmNotification 2 }


--  1.3.6.1.4.1.6296.101.23.51.23
		sleGponProfile2BridgeIpHost OBJECT IDENTIFIER ::= { sleGponProfile2 23 }


--  1.3.6.1.4.1.6296.101.23.51.23.1
		sleGponProfile2BridgeIpHostTable OBJECT-TYPE
			SYNTAX SEQUENCE OF SleGponProfile2BridgeIpHostEntry
			MAX-ACCESS not-accessible
			STATUS current
			DESCRIPTION
				"sleGponProfile2BridgeIpHostTable"
			::= { sleGponProfile2BridgeIpHost 1 }


--  1.3.6.1.4.1.6296.101.23.51.23.1.1
		sleGponProfile2BridgeIpHostEntry OBJECT-TYPE
			SYNTAX SleGponProfile2BridgeIpHostEntry
			MAX-ACCESS not-accessible
			STATUS current
			DESCRIPTION
				"key: sleGponProfile2TrafficIndex, sleGponProfile2BridgeId, sleGponProfile2BridgeIpHostId"
			INDEX { sleGponProfile2TrafficIndex, sleGponProfile2BridgeId, sleGponProfile2BridgeIpHostId }
			::= { sleGponProfile2BridgeIpHostTable 1 }


		SleGponProfile2BridgeIpHostEntry ::=
			SEQUENCE {
				sleGponProfile2BridgeIpHostId
					INTEGER
			 }

--  1.3.6.1.4.1.6296.101.23.51.23.1.1.1
		sleGponProfile2BridgeIpHostId OBJECT-TYPE
			SYNTAX INTEGER (1..65535)
			MAX-ACCESS read-only
			STATUS current
			DESCRIPTION
				"The Host ID"
			::= { sleGponProfile2BridgeIpHostEntry 1 }


--  1.3.6.1.4.1.6296.101.23.51.23.2
		sleGponProfile2BridgeIpHostControl OBJECT IDENTIFIER ::= { sleGponProfile2BridgeIpHost 2 }


--  1.3.6.1.4.1.6296.101.23.51.23.2.1
		sleGponProfile2BridgeIpHostControlRequest OBJECT-TYPE
			SYNTAX INTEGER
				{
				addBridgeIpHost(1),
				delBridgeIpHost(2)
				}
			MAX-ACCESS read-write
			STATUS current
			DESCRIPTION
				"The request of a user command"
			::= { sleGponProfile2BridgeIpHostControl 1 }


--  1.3.6.1.4.1.6296.101.23.51.23.2.2
		sleGponProfile2BridgeIpHostControlStatus OBJECT-TYPE
			SYNTAX SleControlStatusType
			MAX-ACCESS read-only
			STATUS current
			DESCRIPTION
				"The status of user command"
			::= { sleGponProfile2BridgeIpHostControl 2 }


--  1.3.6.1.4.1.6296.101.23.51.23.2.3
		sleGponProfile2BridgeIpHostControlTimer OBJECT-TYPE
			SYNTAX Gauge32
			MAX-ACCESS read-write
			STATUS current
			DESCRIPTION
				"The maximum time for the manager for a long running user command"
			::= { sleGponProfile2BridgeIpHostControl 3 }


--  1.3.6.1.4.1.6296.101.23.51.23.2.4
		sleGponProfile2BridgeIpHostControlTimeStamp OBJECT-TYPE
			SYNTAX TimeTicks
			MAX-ACCESS read-only
			STATUS current
			DESCRIPTION
				"The time stamp of the last command(end of command)"
			::= { sleGponProfile2BridgeIpHostControl 4 }


--  1.3.6.1.4.1.6296.101.23.51.23.2.5
		sleGponProfile2BridgeIpHostControlReqResult OBJECT-TYPE
			SYNTAX SleControlRequestResultType
			MAX-ACCESS read-only
			STATUS current
			DESCRIPTION
				"The result of the last user command"
			::= { sleGponProfile2BridgeIpHostControl 5 }


--  1.3.6.1.4.1.6296.101.23.51.23.2.6
		sleGponProfile2BridgeIpHostControlTName OBJECT-TYPE
			SYNTAX OCTET STRING
			MAX-ACCESS read-write
			STATUS current
			DESCRIPTION
				"The Traffic profile name."
			::= { sleGponProfile2BridgeIpHostControl 6 }


--  The ONU profile name.
-- 1.3.6.1.4.1.6296.101.23.51.23.2.7
		sleGponProfile2BridgeIpHostControlBridgeId OBJECT-TYPE
			SYNTAX INTEGER (1..65535)
			MAX-ACCESS read-write
			STATUS current
			DESCRIPTION
				"The Bridge ID."
			::= { sleGponProfile2BridgeIpHostControl 7 }


--  1.3.6.1.4.1.6296.101.23.51.23.2.8
		sleGponProfile2BridgeIpHostControlId OBJECT-TYPE
			SYNTAX INTEGER (1..65535)
			MAX-ACCESS read-write
			STATUS current
			DESCRIPTION
				"The Host ID"
			::= { sleGponProfile2BridgeIpHostControl 8 }


--  1.3.6.1.4.1.6296.101.23.51.23.3
		sleGponProfile2BridgeIpHostNotification OBJECT IDENTIFIER ::= { sleGponProfile2BridgeIpHost 3 }


--  1.3.6.1.4.1.6296.101.23.51.23.3.1
		sleGponProfile2BridgeIpHostBridgeIpHostCreated NOTIFICATION-TYPE
			OBJECTS { sleGponProfile2BridgeIpHostControlRequest, sleGponProfile2BridgeIpHostControlTimeStamp, sleGponProfile2BridgeIpHostControlReqResult, sleGponProfile2BridgeIpHostControlTName, sleGponProfile2BridgeIpHostControlBridgeId,
				sleGponProfile2BridgeIpHostControlId }
			STATUS current
			DESCRIPTION
				"Description."
			::= { sleGponProfile2BridgeIpHostNotification 1 }


--  1.3.6.1.4.1.6296.101.23.51.23.3.2
		sleGponProfile2BridgeIpHostBridgeIpHostDeleted NOTIFICATION-TYPE
			OBJECTS { sleGponProfile2BridgeIpHostControlRequest, sleGponProfile2BridgeIpHostControlTimeStamp, sleGponProfile2BridgeIpHostControlReqResult, sleGponProfile2BridgeIpHostControlTName, sleGponProfile2BridgeIpHostControlBridgeId,
				sleGponProfile2BridgeIpHostControlId }
			STATUS current
			DESCRIPTION
				"Description."
			::= { sleGponProfile2BridgeIpHostNotification 2 }


--  1.3.6.1.4.1.6296.101.23.51.24
		sleGponProfile2ExtVlan OBJECT IDENTIFIER ::= { sleGponProfile2 24 }


--  1.3.6.1.4.1.6296.101.23.51.24.1
		sleGponProfile2ExtVlanBasic OBJECT IDENTIFIER ::= { sleGponProfile2ExtVlan 1 }


--  1.3.6.1.4.1.6296.101.23.51.24.1.1
		sleGponProfile2ExtVlanTable OBJECT-TYPE
			SYNTAX SEQUENCE OF SleGponProfile2ExtVlanEntry
			MAX-ACCESS not-accessible
			STATUS current
			DESCRIPTION
				"Description."
			::= { sleGponProfile2ExtVlanBasic 1 }


--  1.3.6.1.4.1.6296.101.23.51.24.1.1.1
		sleGponProfile2ExtVlanEntry OBJECT-TYPE
			SYNTAX SleGponProfile2ExtVlanEntry
			MAX-ACCESS not-accessible
			STATUS current
			DESCRIPTION
				"Description."
			INDEX { sleGponProfile2ExtVlanIndex }
			::= { sleGponProfile2ExtVlanTable 1 }


		SleGponProfile2ExtVlanEntry ::=
			SEQUENCE {
				sleGponProfile2ExtVlanIndex
					INTEGER,
				sleGponProfile2ExtVlanName
					OCTET STRING,
				sleGponProfile2ExtVlanDownStreamMode
					INTEGER,
				sleGponProfile2ExtVlanDscpToCosMapTable
					OCTET STRING,
				sleGponProfile2ExtVlanTpidInput
					INTEGER,
				sleGponProfile2ExtVlanTpidOutput
					INTEGER
			 }

--  1.3.6.1.4.1.6296.101.23.51.24.1.1.1.1
		sleGponProfile2ExtVlanIndex OBJECT-TYPE
			SYNTAX INTEGER (1..65535)
			MAX-ACCESS read-only
			STATUS current
			DESCRIPTION
				"Description."
			::= { sleGponProfile2ExtVlanEntry 1 }


--  1.3.6.1.4.1.6296.101.23.51.24.1.1.1.2
		sleGponProfile2ExtVlanName OBJECT-TYPE
			SYNTAX OCTET STRING
			MAX-ACCESS read-only
			STATUS current
			DESCRIPTION
				"Description."
			::= { sleGponProfile2ExtVlanEntry 2 }


--  1.3.6.1.4.1.6296.101.23.51.24.1.1.1.3
		sleGponProfile2ExtVlanDownStreamMode OBJECT-TYPE
			SYNTAX INTEGER
				{
				enable(0),
				disable(1)
				}
			MAX-ACCESS read-write
			STATUS current
			DESCRIPTION
				"Description."
			::= { sleGponProfile2ExtVlanEntry 3 }


--  1.3.6.1.4.1.6296.101.23.51.24.1.1.1.4
		sleGponProfile2ExtVlanDscpToCosMapTable OBJECT-TYPE
			SYNTAX OCTET STRING
			MAX-ACCESS read-only
			STATUS current
			DESCRIPTION
				"Description."
			::= { sleGponProfile2ExtVlanEntry 4 }


--  1.3.6.1.4.1.6296.101.23.51.24.1.1.1.5
		sleGponProfile2ExtVlanTpidInput OBJECT-TYPE
			SYNTAX INTEGER (1..65535)
			MAX-ACCESS read-only
			STATUS current
			DESCRIPTION
				"Description."
			::= { sleGponProfile2ExtVlanEntry 5 }


--  1.3.6.1.4.1.6296.101.23.51.24.1.1.1.6
		sleGponProfile2ExtVlanTpidOutput OBJECT-TYPE
			SYNTAX INTEGER (1..65535)
			MAX-ACCESS read-only
			STATUS current
			DESCRIPTION
				"Description."
			::= { sleGponProfile2ExtVlanEntry 6 }


--  1.3.6.1.4.1.6296.101.23.51.24.1.2
		sleGponProfile2ExtVlanControl OBJECT IDENTIFIER ::= { sleGponProfile2ExtVlanBasic 2 }


--  1.3.6.1.4.1.6296.101.23.51.24.1.2.1
		sleGponProfile2ExtVlanControlRequest OBJECT-TYPE
			SYNTAX INTEGER
				{
				addExtendedVlanProfile(1),
				delExtendedVlanProfile(2),
				setDownstreamMode(3),
				setDscpToCosMapTable(4),
				setTpid(5)
				}
			MAX-ACCESS read-write
			STATUS current
			DESCRIPTION
				"The request of a user command"
			::= { sleGponProfile2ExtVlanControl 1 }


--  1.3.6.1.4.1.6296.101.23.51.24.1.2.2
		sleGponProfile2ExtVlanControlStatus OBJECT-TYPE
			SYNTAX SleControlStatusType
			MAX-ACCESS read-only
			STATUS current
			DESCRIPTION
				"The status of user command"
			::= { sleGponProfile2ExtVlanControl 2 }


--  1.3.6.1.4.1.6296.101.23.51.24.1.2.3
		sleGponProfile2ExtVlanControlTimer OBJECT-TYPE
			SYNTAX Gauge32
			MAX-ACCESS read-write
			STATUS current
			DESCRIPTION
				"The maximum time for the manager for a long running user command"
			::= { sleGponProfile2ExtVlanControl 3 }


--  1.3.6.1.4.1.6296.101.23.51.24.1.2.4
		sleGponProfile2ExtVlanControlTimeStamp OBJECT-TYPE
			SYNTAX TimeTicks
			MAX-ACCESS read-only
			STATUS current
			DESCRIPTION
				"The time stamp of the last command(end of command)"
			::= { sleGponProfile2ExtVlanControl 4 }


--  1.3.6.1.4.1.6296.101.23.51.24.1.2.5
		sleGponProfile2ExtVlanControlReqResult OBJECT-TYPE
			SYNTAX SleControlRequestResultType
			MAX-ACCESS read-only
			STATUS current
			DESCRIPTION
				"The result of the last user command"
			::= { sleGponProfile2ExtVlanControl 5 }


--  1.3.6.1.4.1.6296.101.23.51.24.1.2.6
		sleGponProfile2ExtVlanControlName OBJECT-TYPE
			SYNTAX OCTET STRING
			MAX-ACCESS read-write
			STATUS current
			DESCRIPTION
				"Description."
			::= { sleGponProfile2ExtVlanControl 6 }


--  1.3.6.1.4.1.6296.101.23.51.24.1.2.7
		sleGponProfile2ExtVlanControlDownStreamMode OBJECT-TYPE
			SYNTAX INTEGER
				{
				enable(0),
				disable(1)
				}
			MAX-ACCESS read-write
			STATUS current
			DESCRIPTION
				"Description."
			::= { sleGponProfile2ExtVlanControl 7 }


--  1.3.6.1.4.1.6296.101.23.51.24.1.2.8
		sleGponProfile2ExtVlanControlDscpToCosMapTable OBJECT-TYPE
			SYNTAX OCTET STRING
			MAX-ACCESS read-write
			STATUS current
			DESCRIPTION
				"Description."
			::= { sleGponProfile2ExtVlanControl 8 }


--  1.3.6.1.4.1.6296.101.23.51.24.1.2.9
		sleGponProfile2ExtVlanControlTpidInput OBJECT-TYPE
			SYNTAX INTEGER (1..65535)
			MAX-ACCESS read-write
			STATUS current
			DESCRIPTION
				"Description."
			::= { sleGponProfile2ExtVlanControl 9 }


--  1.3.6.1.4.1.6296.101.23.51.24.1.2.10
		sleGponProfile2ExtVlanControlTpidOutput OBJECT-TYPE
			SYNTAX INTEGER (1..65535)
			MAX-ACCESS read-write
			STATUS current
			DESCRIPTION
				"Description."
			::= { sleGponProfile2ExtVlanControl 10 }


--  1.3.6.1.4.1.6296.101.23.51.24.1.3
		sleGponProfile2ExtVlanNotification OBJECT IDENTIFIER ::= { sleGponProfile2ExtVlanBasic 3 }


--  1.3.6.1.4.1.6296.101.23.51.24.1.3.1
		sleGponProfile2ExtVlanProfileAdded NOTIFICATION-TYPE
			OBJECTS { sleGponProfile2ExtVlanControlRequest, sleGponProfile2ExtVlanControlTimeStamp, sleGponProfile2ExtVlanControlReqResult, sleGponProfile2ExtVlanControlName }
			STATUS current
			DESCRIPTION
				"Description."
			::= { sleGponProfile2ExtVlanNotification 1 }


--  1.3.6.1.4.1.6296.101.23.51.24.1.3.2
		sleGponProfile2ExtVlanProfileDeleted NOTIFICATION-TYPE
			OBJECTS { sleGponProfile2ExtVlanControlRequest, sleGponProfile2ExtVlanControlTimeStamp, sleGponProfile2ExtVlanControlReqResult, sleGponProfile2ExtVlanControlName }
			STATUS current
			DESCRIPTION
				"Description."
			::= { sleGponProfile2ExtVlanNotification 2 }


--  1.3.6.1.4.1.6296.101.23.51.24.1.3.3
		sleGponProfile2ExtVlanDownStreamModeChanged NOTIFICATION-TYPE
			OBJECTS { sleGponProfile2ExtVlanControlRequest, sleGponProfile2ExtVlanControlTimeStamp, sleGponProfile2ExtVlanControlReqResult, sleGponProfile2ExtVlanControlName, sleGponProfile2ExtVlanControlDownStreamMode
				 }
			STATUS current
			DESCRIPTION
				"Description."
			::= { sleGponProfile2ExtVlanNotification 3 }


--  1.3.6.1.4.1.6296.101.23.51.24.1.3.4
		sleGponProfile2ExtVlanDscpToCosMapTableChanged NOTIFICATION-TYPE
			OBJECTS { sleGponProfile2ExtVlanControlRequest, sleGponProfile2ExtVlanControlTimeStamp, sleGponProfile2ExtVlanControlReqResult, sleGponProfile2ExtVlanControlName, sleGponProfile2ExtVlanControlDscpToCosMapTable
				 }
			STATUS current
			DESCRIPTION
				"Description."
			::= { sleGponProfile2ExtVlanNotification 4 }


--  1.3.6.1.4.1.6296.101.23.51.24.1.3.5
		sleGponProfile2ExtVlanTpidChanged NOTIFICATION-TYPE
			OBJECTS { sleGponProfile2ExtVlanControlRequest, sleGponProfile2ExtVlanControlTimeStamp, sleGponProfile2ExtVlanControlReqResult, sleGponProfile2ExtVlanControlName, sleGponProfile2ExtVlanControlTpidInput,
				sleGponProfile2ExtVlanControlTpidOutput }
			STATUS current
			DESCRIPTION
				"Description."
			::= { sleGponProfile2ExtVlanNotification 5 }


--  1.3.6.1.4.1.6296.101.23.51.24.2
		sleGponProfile2ExtVlanTag OBJECT IDENTIFIER ::= { sleGponProfile2ExtVlan 2 }


--  1.3.6.1.4.1.6296.101.23.51.24.2.1
		sleGponProfile2ExtVlanTagTable OBJECT-TYPE
			SYNTAX SEQUENCE OF SleGponProfile2ExtVlanTagEntry
			MAX-ACCESS not-accessible
			STATUS current
			DESCRIPTION
				"Description."
			::= { sleGponProfile2ExtVlanTag 1 }


--  1.3.6.1.4.1.6296.101.23.51.24.2.1.1
		sleGponProfile2ExtVlanTagEntry OBJECT-TYPE
			SYNTAX SleGponProfile2ExtVlanTagEntry
			MAX-ACCESS not-accessible
			STATUS current
			DESCRIPTION
				"Description."
			INDEX { sleGponProfile2ExtVlanIndex, sleGponProfile2ExtVlanTagType, sleGponProfile2ExtVlanTagIndex }
			::= { sleGponProfile2ExtVlanTagTable 1 }


		SleGponProfile2ExtVlanTagEntry ::=
			SEQUENCE {
				sleGponProfile2ExtVlanTagType
					INTEGER,
				sleGponProfile2ExtVlanTagIndex
					INTEGER,
				sleGponProfile2ExtVlanTagTreatTag
					INTEGER,
				sleGponProfile2ExtVlanTagTreatInnerCopyVid
					INTEGER,
				sleGponProfile2ExtVlanTagTreatInnerCopyCos
					INTEGER,
				sleGponProfile2ExtVlanTagTreatInnerTpidDei
					INTEGER,
				sleGponProfile2ExtVlanTagTreatOuterCopyVid
					INTEGER,
				sleGponProfile2ExtVlanTagTreatOuterCopyCos
					INTEGER,
				sleGponProfile2ExtVlanTagTreatOuterTpidDei
					INTEGER,
				sleGponProfile2ExtVlanTagFilterEtherType
					INTEGER,
				sleGponProfile2ExtVlanTagFilterInnerVid
					INTEGER,
				sleGponProfile2ExtVlanTagFilterInnerCos
					INTEGER,
				sleGponProfile2ExtVlanTagFilterInnerTpidDei
					INTEGER,
				sleGponProfile2ExtVlanTagFilterOuterVid
					INTEGER,
				sleGponProfile2ExtVlanTagFilterOuterCos
					INTEGER,
				sleGponProfile2ExtVlanTagFilterOuterTpidDei
					INTEGER
			 }

--  1.3.6.1.4.1.6296.101.23.51.24.2.1.1.1
		sleGponProfile2ExtVlanTagType OBJECT-TYPE
			SYNTAX INTEGER
				{
				unTaggedFrame(1),
				singleTaggedFrame(2),
				doubleTaggedFrame(3)
				}
			MAX-ACCESS read-only
			STATUS current
			DESCRIPTION
				"Description."
			::= { sleGponProfile2ExtVlanTagEntry 1 }


--  1.3.6.1.4.1.6296.101.23.51.24.2.1.1.2
		sleGponProfile2ExtVlanTagIndex OBJECT-TYPE
			SYNTAX INTEGER (1..65535)
			MAX-ACCESS read-only
			STATUS current
			DESCRIPTION
				"Description."
			::= { sleGponProfile2ExtVlanTagEntry 2 }


--  1.3.6.1.4.1.6296.101.23.51.24.2.1.1.3
		sleGponProfile2ExtVlanTagTreatTag OBJECT-TYPE
			SYNTAX INTEGER
				{
				notRemove(0),
				remove(1),
				both(2),
				notMatchDiscardInDs(3)
				}
			MAX-ACCESS read-only
			STATUS current
			DESCRIPTION
				"Description."
			::= { sleGponProfile2ExtVlanTagEntry 3 }


--  1.3.6.1.4.1.6296.101.23.51.24.2.1.1.4
		sleGponProfile2ExtVlanTagTreatInnerCopyVid OBJECT-TYPE
			SYNTAX INTEGER (0..4094 | 4096 | 4097)
			MAX-ACCESS read-only
			STATUS current
			DESCRIPTION
				"Description."
			::= { sleGponProfile2ExtVlanTagEntry 4 }


--  1.3.6.1.4.1.6296.101.23.51.24.2.1.1.5
		sleGponProfile2ExtVlanTagTreatInnerCopyCos OBJECT-TYPE
			SYNTAX INTEGER (0..7 | 8 | 9 | 10 | 15)
			MAX-ACCESS read-only
			STATUS current
			DESCRIPTION
				"Description."
			::= { sleGponProfile2ExtVlanTagEntry 5 }


--  1.3.6.1.4.1.6296.101.23.51.24.2.1.1.6
		sleGponProfile2ExtVlanTagTreatInnerTpidDei OBJECT-TYPE
			SYNTAX INTEGER
				{
				tpidCopyInner(0),
				tpidCopyOuter(1),
				tpidOutputDeiCopyInner(2),
				tpidOutputDeiOuter(3),
				tpid0x8100(4),
				tpidReserved(5),
				tpidOutputDei0(6),
				tpidOutputDei1(7)
				}
			MAX-ACCESS read-only
			STATUS current
			DESCRIPTION
				"Description."
			::= { sleGponProfile2ExtVlanTagEntry 6 }


--  1.3.6.1.4.1.6296.101.23.51.24.2.1.1.7
		sleGponProfile2ExtVlanTagTreatOuterCopyVid OBJECT-TYPE
			SYNTAX INTEGER (0..4094 | 4096 | 4097)
			MAX-ACCESS read-only
			STATUS current
			DESCRIPTION
				"Description."
			::= { sleGponProfile2ExtVlanTagEntry 7 }


--  1.3.6.1.4.1.6296.101.23.51.24.2.1.1.8
		sleGponProfile2ExtVlanTagTreatOuterCopyCos OBJECT-TYPE
			SYNTAX INTEGER (0..7 | 8 | 9 | 10 | 15)
			MAX-ACCESS read-only
			STATUS current
			DESCRIPTION
				"Description."
			::= { sleGponProfile2ExtVlanTagEntry 8 }


--  1.3.6.1.4.1.6296.101.23.51.24.2.1.1.9
		sleGponProfile2ExtVlanTagTreatOuterTpidDei OBJECT-TYPE
			SYNTAX INTEGER
				{
				tpidCopyInner(0),
				tpidCopyOuter(1),
				tpidOutputDeiCopyInner(2),
				tpidOutputDeiOuter(3),
				tpid0x8100(4),
				tpidReserved(5),
				tpidOutputDei0(6),
				tpidOutputDei1(7)
				}
			MAX-ACCESS read-only
			STATUS current
			DESCRIPTION
				"Description."
			::= { sleGponProfile2ExtVlanTagEntry 9 }


--  1.3.6.1.4.1.6296.101.23.51.24.2.1.1.10
		sleGponProfile2ExtVlanTagFilterEtherType OBJECT-TYPE
			SYNTAX INTEGER
				{
				unused(0),
				ipoe(1),
				pppoe(2),
				arp(3),
				ipv6Ipoe(4)
				}
			MAX-ACCESS read-only
			STATUS current
			DESCRIPTION
				"Description."
			::= { sleGponProfile2ExtVlanTagEntry 10 }


--  1.3.6.1.4.1.6296.101.23.51.24.2.1.1.11
		sleGponProfile2ExtVlanTagFilterInnerVid OBJECT-TYPE
			SYNTAX INTEGER (0..4094 | 4096)
			MAX-ACCESS read-only
			STATUS current
			DESCRIPTION
				"Description."
			::= { sleGponProfile2ExtVlanTagEntry 11 }


--  1.3.6.1.4.1.6296.101.23.51.24.2.1.1.12
		sleGponProfile2ExtVlanTagFilterInnerCos OBJECT-TYPE
			SYNTAX INTEGER (0..7 | 8)
			MAX-ACCESS read-only
			STATUS current
			DESCRIPTION
				"Description."
			::= { sleGponProfile2ExtVlanTagEntry 12 }


--  1.3.6.1.4.1.6296.101.23.51.24.2.1.1.13
		sleGponProfile2ExtVlanTagFilterInnerTpidDei OBJECT-TYPE
			SYNTAX INTEGER
				{
				tpidany(0),
				tpid0x8100(4),
				tpidInput(5),
				tpidInputDei0(6),
				tpidInputDei1(7)
				}
			MAX-ACCESS read-only
			STATUS current
			DESCRIPTION
				"Description."
			::= { sleGponProfile2ExtVlanTagEntry 13 }


--  1.3.6.1.4.1.6296.101.23.51.24.2.1.1.14
		sleGponProfile2ExtVlanTagFilterOuterVid OBJECT-TYPE
			SYNTAX INTEGER (0..4094 | 4096)
			MAX-ACCESS read-only
			STATUS current
			DESCRIPTION
				"Description."
			::= { sleGponProfile2ExtVlanTagEntry 14 }


--  1.3.6.1.4.1.6296.101.23.51.24.2.1.1.15
		sleGponProfile2ExtVlanTagFilterOuterCos OBJECT-TYPE
			SYNTAX INTEGER (0..7 | 8)
			MAX-ACCESS read-only
			STATUS current
			DESCRIPTION
				"Description."
			::= { sleGponProfile2ExtVlanTagEntry 15 }


--  1.3.6.1.4.1.6296.101.23.51.24.2.1.1.16
		sleGponProfile2ExtVlanTagFilterOuterTpidDei OBJECT-TYPE
			SYNTAX INTEGER
				{
				tpidany(0),
				tpid0x8100(4),
				tpidInput(5),
				tpidInputDei0(6),
				tpidInputDei1(7)
				}
			MAX-ACCESS read-only
			STATUS current
			DESCRIPTION
				"Description."
			::= { sleGponProfile2ExtVlanTagEntry 16 }


--  1.3.6.1.4.1.6296.101.23.51.24.2.2
		sleGponProfile2ExtVlanTagControl OBJECT IDENTIFIER ::= { sleGponProfile2ExtVlanTag 2 }


--  1.3.6.1.4.1.6296.101.23.51.24.2.2.1
		sleGponProfile2ExtVlanTagControlRequest OBJECT-TYPE
			SYNTAX INTEGER
				{
				addExtendedVlanTag(1),
				delExtendedVlanTag(2),
				setTreatmentTag(3),
				setTreatmentInner(4),
				setTreatmentOuter(5),
				setFilterEtherType(6),
				setFilterInner(7),
				setFilterOuter(8)
				}
			MAX-ACCESS read-write
			STATUS current
			DESCRIPTION
				"The request of a user command"
			::= { sleGponProfile2ExtVlanTagControl 1 }


--  1.3.6.1.4.1.6296.101.23.51.24.2.2.2
		sleGponProfile2ExtVlanTagControlStatus OBJECT-TYPE
			SYNTAX SleControlStatusType
			MAX-ACCESS read-only
			STATUS current
			DESCRIPTION
				"The status of user command"
			::= { sleGponProfile2ExtVlanTagControl 2 }


--  1.3.6.1.4.1.6296.101.23.51.24.2.2.3
		sleGponProfile2ExtVlanTagControlTimer OBJECT-TYPE
			SYNTAX Gauge32
			MAX-ACCESS read-write
			STATUS current
			DESCRIPTION
				"The maximum time for the manager for a long running user command"
			::= { sleGponProfile2ExtVlanTagControl 3 }


--  1.3.6.1.4.1.6296.101.23.51.24.2.2.4
		sleGponProfile2ExtVlanTagControlTimeStamp OBJECT-TYPE
			SYNTAX TimeTicks
			MAX-ACCESS read-only
			STATUS current
			DESCRIPTION
				"The time stamp of the last command(end of command)"
			::= { sleGponProfile2ExtVlanTagControl 4 }


--  1.3.6.1.4.1.6296.101.23.51.24.2.2.5
		sleGponProfile2ExtVlanTagControlReqResult OBJECT-TYPE
			SYNTAX SleControlRequestResultType
			MAX-ACCESS read-only
			STATUS current
			DESCRIPTION
				"The result of the last user command"
			::= { sleGponProfile2ExtVlanTagControl 5 }


--  1.3.6.1.4.1.6296.101.23.51.24.2.2.6
		sleGponProfile2ExtVlanTagControlName OBJECT-TYPE
			SYNTAX OCTET STRING
			MAX-ACCESS read-write
			STATUS current
			DESCRIPTION
				"Description."
			::= { sleGponProfile2ExtVlanTagControl 6 }


--  1.3.6.1.4.1.6296.101.23.51.24.2.2.7
		sleGponProfile2ExtVlanTagControlType OBJECT-TYPE
			SYNTAX INTEGER
				{
				unTaggedFrame(1),
				singleTaggedFrame(2),
				doubleTaggedFrame(3)
				}
			MAX-ACCESS read-write
			STATUS current
			DESCRIPTION
				"Description."
			::= { sleGponProfile2ExtVlanTagControl 7 }


--  1.3.6.1.4.1.6296.101.23.51.24.2.2.8
		sleGponProfile2ExtVlanTagControlIndex OBJECT-TYPE
			SYNTAX INTEGER (1..65535)
			MAX-ACCESS read-write
			STATUS current
			DESCRIPTION
				"Description."
			::= { sleGponProfile2ExtVlanTagControl 8 }


--  1.3.6.1.4.1.6296.101.23.51.24.2.2.9
		sleGponProfile2ExtVlanTagControlTreatTag OBJECT-TYPE
			SYNTAX INTEGER
				{
				notRemove(0),
				remove(1),
				both(2),
				notMatchDiscardInDs(3)
				}
			MAX-ACCESS read-write
			STATUS current
			DESCRIPTION
				"Description."
			::= { sleGponProfile2ExtVlanTagControl 9 }


--  1.3.6.1.4.1.6296.101.23.51.24.2.2.10
		sleGponProfile2ExtVlanTagControlTreatInnerCopyVid OBJECT-TYPE
			SYNTAX INTEGER (0..4094 | 4096 | 4097)
			MAX-ACCESS read-write
			STATUS current
			DESCRIPTION
				"(0-4094) | 4096(copy_inner) | 4097(copy_outer)"
			::= { sleGponProfile2ExtVlanTagControl 10 }


--  1.3.6.1.4.1.6296.101.23.51.24.2.2.11
		sleGponProfile2ExtVlanTagControlTreatInnerCopyCos OBJECT-TYPE
			SYNTAX INTEGER (0..7 | 8 | 9 | 10 | 15)
			MAX-ACCESS read-write
			STATUS current
			DESCRIPTION
				"(0-7) | 8(copy_inner) | 9(copy_outer)|10(dscpToPbit)15(unused) "
			::= { sleGponProfile2ExtVlanTagControl 11 }


--  1.3.6.1.4.1.6296.101.23.51.24.2.2.12
		sleGponProfile2ExtVlanTagControlTreatInnerTpidDei OBJECT-TYPE
			SYNTAX INTEGER
				{
				tpidCopyInner(0),
				tpidCopyOuter(1),
				tpidOutputDeiCopyInner(2),
				tpidOutputDeiOuter(3),
				tpid0x8100(4),
				tpidReserved(5),
				tpidOutputDei0(6),
				tpidOutputDei1(7)
				}
			MAX-ACCESS read-write
			STATUS current
			DESCRIPTION
				"Description."
			::= { sleGponProfile2ExtVlanTagControl 12 }


--  1.3.6.1.4.1.6296.101.23.51.24.2.2.13
		sleGponProfile2ExtVlanTagControlTreatOuterCopyVid OBJECT-TYPE
			SYNTAX INTEGER (0..4094 | 4096 | 4097)
			MAX-ACCESS read-write
			STATUS current
			DESCRIPTION
				"(0-4094) | 4096(copy_inner) | 4097(copy_outer)"
			::= { sleGponProfile2ExtVlanTagControl 13 }


--  1.3.6.1.4.1.6296.101.23.51.24.2.2.14
		sleGponProfile2ExtVlanTagControlTreatOuterCopyCos OBJECT-TYPE
			SYNTAX INTEGER (0..7 | 8 | 9 | 10 | 15)
			MAX-ACCESS read-write
			STATUS current
			DESCRIPTION
				"(0-7) | 8(copy_inner) | 9(copy_outer)|10(dscpToPbit)15(unused) "
			::= { sleGponProfile2ExtVlanTagControl 14 }


--  1.3.6.1.4.1.6296.101.23.51.24.2.2.15
		sleGponProfile2ExtVlanTagControlTreatOuterTpidDei OBJECT-TYPE
			SYNTAX INTEGER
				{
				tpidCopyInner(0),
				tpidCopyOuter(1),
				tpidOutputDeiCopyInner(2),
				tpidOutputDeiOuter(3),
				tpid0x8100(4),
				tpidReserved(5),
				tpidOutputDei0(6),
				tpidOutputDei1(7)
				}
			MAX-ACCESS read-write
			STATUS current
			DESCRIPTION
				"Description."
			::= { sleGponProfile2ExtVlanTagControl 15 }


--  1.3.6.1.4.1.6296.101.23.51.24.2.2.16
		sleGponProfile2ExtVlanTagControlFilterEtherType OBJECT-TYPE
			SYNTAX INTEGER
				{
				unused(0),
				ipoe(1),
				pppoe(2),
				arp(3),
				ipv6Ipoe(4)
				}
			MAX-ACCESS read-write
			STATUS current
			DESCRIPTION
				"Description."
			::= { sleGponProfile2ExtVlanTagControl 16 }


--  1.3.6.1.4.1.6296.101.23.51.24.2.2.17
		sleGponProfile2ExtVlanTagControlFilterInnerVid OBJECT-TYPE
			SYNTAX INTEGER (0..4094 | 4096)
			MAX-ACCESS read-write
			STATUS current
			DESCRIPTION
				"(0-4094) | any(4096"
			::= { sleGponProfile2ExtVlanTagControl 17 }


--  1.3.6.1.4.1.6296.101.23.51.24.2.2.18
		sleGponProfile2ExtVlanTagControlFilterInnerCos OBJECT-TYPE
			SYNTAX INTEGER (0..7 | 8)
			MAX-ACCESS read-write
			STATUS current
			DESCRIPTION
				"(0-7) | 8(any)"
			::= { sleGponProfile2ExtVlanTagControl 18 }


--  1.3.6.1.4.1.6296.101.23.51.24.2.2.19
		sleGponProfile2ExtVlanTagControlFilterInnerTpidDei OBJECT-TYPE
			SYNTAX INTEGER
				{
				tpidany(0),
				tpid0x8100(4),
				tpidInput(5),
				tpidInputDei0(6),
				tpidInputDei1(7)
				}
			MAX-ACCESS read-write
			STATUS current
			DESCRIPTION
				"0(Tpidany) |  4(TpidDefault) 5(TpidInput), 6(TpidInputDei0), 7 (TpidInputDei1)"
			::= { sleGponProfile2ExtVlanTagControl 19 }


--  1.3.6.1.4.1.6296.101.23.51.24.2.2.20
		sleGponProfile2ExtVlanTagControlFilterOuterVid OBJECT-TYPE
			SYNTAX INTEGER (0..4094 | 4096)
			MAX-ACCESS read-write
			STATUS current
			DESCRIPTION
				"(0-4094) | any(4096"
			::= { sleGponProfile2ExtVlanTagControl 20 }


--  1.3.6.1.4.1.6296.101.23.51.24.2.2.21
		sleGponProfile2ExtVlanTagControlFilterOuterCos OBJECT-TYPE
			SYNTAX INTEGER (0..7 | 8)
			MAX-ACCESS read-write
			STATUS current
			DESCRIPTION
				"(0-7) | 8(any)"
			::= { sleGponProfile2ExtVlanTagControl 21 }


--  1.3.6.1.4.1.6296.101.23.51.24.2.2.22
		sleGponProfile2ExtVlanTagControlFilterOuterTpidDei OBJECT-TYPE
			SYNTAX INTEGER
				{
				tpidany(0),
				tpid0x8100(4),
				tpidInput(5),
				tpidInputDei0(6),
				tpidInputDei1(7)
				}
			MAX-ACCESS read-write
			STATUS current
			DESCRIPTION
				"0(Tpidany) |  4(TpidDefault) 5(TpidInput), 6(TpidInputDei0), 7 (TpidInputDei1)"
			::= { sleGponProfile2ExtVlanTagControl 22 }


--  1.3.6.1.4.1.6296.101.23.51.24.2.3
		sleGponProfile2ExtVlanTagNotification OBJECT IDENTIFIER ::= { sleGponProfile2ExtVlanTag 3 }


--  1.3.6.1.4.1.6296.101.23.51.24.2.3.1
		sleGponProfile2ExtVlanTagAdded NOTIFICATION-TYPE
			OBJECTS { sleGponProfile2ExtVlanTagControlRequest, sleGponProfile2ExtVlanTagControlTimeStamp, sleGponProfile2ExtVlanTagControlReqResult, sleGponProfile2ExtVlanTagControlName, sleGponProfile2ExtVlanTagControlType,
				sleGponProfile2ExtVlanTagControlIndex }
			STATUS current
			DESCRIPTION
				"Description."
			::= { sleGponProfile2ExtVlanTagNotification 1 }


--  1.3.6.1.4.1.6296.101.23.51.24.2.3.2
		sleGponProfile2ExtVlanTagDeleted NOTIFICATION-TYPE
			OBJECTS { sleGponProfile2ExtVlanTagControlRequest, sleGponProfile2ExtVlanTagControlTimeStamp, sleGponProfile2ExtVlanTagControlReqResult, sleGponProfile2ExtVlanTagControlName, sleGponProfile2ExtVlanTagControlType,
				sleGponProfile2ExtVlanTagControlIndex }
			STATUS current
			DESCRIPTION
				"Description."
			::= { sleGponProfile2ExtVlanTagNotification 2 }


--  1.3.6.1.4.1.6296.101.23.51.24.2.3.3
		sleGponProfile2ExtVlanTagTreatmentTag NOTIFICATION-TYPE
			OBJECTS { sleGponProfile2ExtVlanTagControlRequest, sleGponProfile2ExtVlanTagControlTimeStamp, sleGponProfile2ExtVlanTagControlReqResult, sleGponProfile2ExtVlanTagControlName, sleGponProfile2ExtVlanTagControlType,
				sleGponProfile2ExtVlanTagControlIndex, sleGponProfile2ExtVlanTagControlTreatTag }
			STATUS current
			DESCRIPTION
				"Description."
			::= { sleGponProfile2ExtVlanTagNotification 3 }


--  1.3.6.1.4.1.6296.101.23.51.24.2.3.4
		sleGponProfile2ExtVlanTagTreatmentInnerChanged NOTIFICATION-TYPE
			OBJECTS { sleGponProfile2ExtVlanTagControlRequest, sleGponProfile2ExtVlanTagControlTimeStamp, sleGponProfile2ExtVlanTagControlReqResult, sleGponProfile2ExtVlanTagControlName, sleGponProfile2ExtVlanTagControlType,
				sleGponProfile2ExtVlanTagControlIndex, sleGponProfile2ExtVlanTagControlTreatInnerCopyVid, sleGponProfile2ExtVlanTagControlTreatInnerCopyCos, sleGponProfile2ExtVlanTagControlTreatInnerTpidDei }
			STATUS current
			DESCRIPTION
				"Description."
			::= { sleGponProfile2ExtVlanTagNotification 4 }


--  1.3.6.1.4.1.6296.101.23.51.24.2.3.5
		sleGponProfile2ExtVlanTagTreatmentOuterChanged NOTIFICATION-TYPE
			OBJECTS { sleGponProfile2ExtVlanTagControlRequest, sleGponProfile2ExtVlanTagControlTimeStamp, sleGponProfile2ExtVlanTagControlReqResult, sleGponProfile2ExtVlanTagControlName, sleGponProfile2ExtVlanTagControlType,
				sleGponProfile2ExtVlanTagControlIndex, sleGponProfile2ExtVlanTagControlTreatOuterCopyVid, sleGponProfile2ExtVlanTagControlTreatOuterCopyCos, sleGponProfile2ExtVlanTagControlTreatOuterTpidDei }
			STATUS current
			DESCRIPTION
				"Description."
			::= { sleGponProfile2ExtVlanTagNotification 5 }


--  1.3.6.1.4.1.6296.101.23.51.24.2.3.6
		sleGponProfile2ExtVlanTagFilterEtherTypeChanged NOTIFICATION-TYPE
			OBJECTS { sleGponProfile2ExtVlanTagControlRequest, sleGponProfile2ExtVlanTagControlTimeStamp, sleGponProfile2ExtVlanTagControlReqResult, sleGponProfile2ExtVlanTagControlName, sleGponProfile2ExtVlanTagControlType,
				sleGponProfile2ExtVlanTagControlIndex, sleGponProfile2ExtVlanTagControlFilterEtherType }
			STATUS current
			DESCRIPTION
				"Description."
			::= { sleGponProfile2ExtVlanTagNotification 6 }


--  1.3.6.1.4.1.6296.101.23.51.24.2.3.7
		sleGponProfile2ExtVlanTagFilterInnerChanged NOTIFICATION-TYPE
			OBJECTS { sleGponProfile2ExtVlanTagControlRequest, sleGponProfile2ExtVlanTagControlTimeStamp, sleGponProfile2ExtVlanTagControlReqResult, sleGponProfile2ExtVlanTagControlName, sleGponProfile2ExtVlanTagControlType,
				sleGponProfile2ExtVlanTagControlIndex, sleGponProfile2ExtVlanTagControlFilterInnerVid, sleGponProfile2ExtVlanTagControlFilterInnerCos, sleGponProfile2ExtVlanTagControlFilterInnerTpidDei }
			STATUS current
			DESCRIPTION
				"Description."
			::= { sleGponProfile2ExtVlanTagNotification 7 }


--  1.3.6.1.4.1.6296.101.23.51.24.2.3.8
		sleGponProfile2ExtVlanTagFilterOuterChanged NOTIFICATION-TYPE
			OBJECTS { sleGponProfile2ExtVlanTagControlRequest, sleGponProfile2ExtVlanTagControlTimeStamp, sleGponProfile2ExtVlanTagControlReqResult, sleGponProfile2ExtVlanTagControlName, sleGponProfile2ExtVlanTagControlType,
				sleGponProfile2ExtVlanTagControlIndex, sleGponProfile2ExtVlanTagControlFilterOuterVid, sleGponProfile2ExtVlanTagControlFilterOuterCos, sleGponProfile2ExtVlanTagControlFilterOuterTpidDei }
			STATUS current
			DESCRIPTION
				"Description."
			::= { sleGponProfile2ExtVlanTagNotification 8 }


--  1.3.6.1.4.1.6296.101.23.51.25
		sleGponProfile2MapperGem OBJECT IDENTIFIER ::= { sleGponProfile2 25 }


--  1.3.6.1.4.1.6296.101.23.51.25.1
		sleGponProfile2MapperGemTable OBJECT-TYPE
			SYNTAX SEQUENCE OF SleGponProfile2MapperGemEntry
			MAX-ACCESS not-accessible
			STATUS current
			DESCRIPTION
				"Description."
			::= { sleGponProfile2MapperGem 1 }


--  1.3.6.1.4.1.6296.101.23.51.25.1.1
		sleGponProfile2MapperGemEntry OBJECT-TYPE
			SYNTAX SleGponProfile2MapperGemEntry
			MAX-ACCESS not-accessible
			STATUS current
			DESCRIPTION
				"Description."
			INDEX { sleGponProfile2TrafficIndex, sleGponProfile2MapperIndex, sleGponProfile2MapperGemId }
			::= { sleGponProfile2MapperGemTable 1 }


		SleGponProfile2MapperGemEntry ::=
			SEQUENCE {
				sleGponProfile2MapperIndex
					Integer32,
				sleGponProfile2MapperGemId
					Integer32,
				sleGponProfile2MapperGemRateLimitDownSir
					Integer32,
				sleGponProfile2MapperGemRateLimitDownPir
					Integer32,
				sleGponProfile2MapperGemRateLimitUpSir
					Integer32,
				sleGponProfile2MapperGemRateLimitUpPir
					Integer32,
				sleGponProfile2MapperGemRateLimitProfile
					OCTET STRING
			 }

--  1.3.6.1.4.1.6296.101.23.51.25.1.1.1
		sleGponProfile2MapperIndex OBJECT-TYPE
			SYNTAX Integer32 (1..65535)
			MAX-ACCESS read-only
			STATUS current
			DESCRIPTION
				"The mapper index."
			::= { sleGponProfile2MapperGemEntry 1 }


--  1.3.6.1.4.1.6296.101.23.51.25.1.1.2
		sleGponProfile2MapperGemId OBJECT-TYPE
			SYNTAX Integer32 (1..65535)
			MAX-ACCESS read-only
			STATUS current
			DESCRIPTION
				"The GEM index."
			::= { sleGponProfile2MapperGemEntry 2 }


--  1.3.6.1.4.1.6296.101.23.51.25.1.1.3
		sleGponProfile2MapperGemRateLimitDownSir OBJECT-TYPE
			SYNTAX Integer32
			MAX-ACCESS read-only
			STATUS current
			DESCRIPTION
				"The downstream rate-limit control : SIR (Bandwidth in steps of 64Kbps)"
			::= { sleGponProfile2MapperGemEntry 3 }


--  1.3.6.1.4.1.6296.101.23.51.25.1.1.4
		sleGponProfile2MapperGemRateLimitDownPir OBJECT-TYPE
			SYNTAX Integer32
			MAX-ACCESS read-only
			STATUS current
			DESCRIPTION
				"The downstream rate-limit control : PIR (Bandwidth in steps of 64Kbps)"
			::= { sleGponProfile2MapperGemEntry 4 }


--  1.3.6.1.4.1.6296.101.23.51.25.1.1.5
		sleGponProfile2MapperGemRateLimitUpSir OBJECT-TYPE
			SYNTAX Integer32
			MAX-ACCESS read-only
			STATUS current
			DESCRIPTION
				"The upstream rate-limit control : SIR (Bandwidth in steps of 64Kbps)"
			::= { sleGponProfile2MapperGemEntry 5 }


--  1.3.6.1.4.1.6296.101.23.51.25.1.1.6
		sleGponProfile2MapperGemRateLimitUpPir OBJECT-TYPE
			SYNTAX Integer32
			MAX-ACCESS read-only
			STATUS current
			DESCRIPTION
				"The upstream rate-limit control : PIR (Bandwidth in steps of 64Kbps)"
			::= { sleGponProfile2MapperGemEntry 6 }


--  1.3.6.1.4.1.6296.101.23.51.25.1.1.7
		sleGponProfile2MapperGemRateLimitProfile OBJECT-TYPE
			SYNTAX OCTET STRING
			MAX-ACCESS read-only
			STATUS current
			DESCRIPTION
				"The rate-limit profile name."
			::= { sleGponProfile2MapperGemEntry 7 }


--  1.3.6.1.4.1.6296.101.23.51.25.2
		sleGponProfile2MapperGemControl OBJECT IDENTIFIER ::= { sleGponProfile2MapperGem 2 }


--  1.3.6.1.4.1.6296.101.23.51.25.2.1
		sleGponProfile2MapperGemControlRequest OBJECT-TYPE
			SYNTAX INTEGER
				{
				setGemRateLimit(1),
				delGemRateLimit(2),
				setGemRatelimitProfile(3)
				}
			MAX-ACCESS read-write
			STATUS current
			DESCRIPTION
				"The request of a user command"
			::= { sleGponProfile2MapperGemControl 1 }


--  1.3.6.1.4.1.6296.101.23.51.25.2.2
		sleGponProfile2MapperGemControlStatus OBJECT-TYPE
			SYNTAX SleControlStatusType
			MAX-ACCESS read-only
			STATUS current
			DESCRIPTION
				"The status of user command"
			::= { sleGponProfile2MapperGemControl 2 }


--  1.3.6.1.4.1.6296.101.23.51.25.2.3
		sleGponProfile2MapperGemControlTimer OBJECT-TYPE
			SYNTAX Gauge32
			MAX-ACCESS read-write
			STATUS current
			DESCRIPTION
				"The maximum time for the manager for a long running user command"
			::= { sleGponProfile2MapperGemControl 3 }


--  1.3.6.1.4.1.6296.101.23.51.25.2.4
		sleGponProfile2MapperGemControlTimeStamp OBJECT-TYPE
			SYNTAX TimeTicks
			MAX-ACCESS read-only
			STATUS current
			DESCRIPTION
				"The time stamp of the last command(end of command)"
			::= { sleGponProfile2MapperGemControl 4 }


--  1.3.6.1.4.1.6296.101.23.51.25.2.5
		sleGponProfile2MapperGemControlReqResult OBJECT-TYPE
			SYNTAX SleControlRequestResultType
			MAX-ACCESS read-only
			STATUS current
			DESCRIPTION
				"The result of the last user command"
			::= { sleGponProfile2MapperGemControl 5 }


--  1.3.6.1.4.1.6296.101.23.51.25.2.6
		sleGponProfile2MapperGemControlTrafficName OBJECT-TYPE
			SYNTAX OCTET STRING
			MAX-ACCESS read-write
			STATUS current
			DESCRIPTION
				"The Traffic profile name."
			::= { sleGponProfile2MapperGemControl 6 }


--  1.3.6.1.4.1.6296.101.23.51.25.2.7
		sleGponProfile2MapperGemControlIndex OBJECT-TYPE
			SYNTAX Integer32
			MAX-ACCESS read-write
			STATUS current
			DESCRIPTION
				"The mapper index."
			::= { sleGponProfile2MapperGemControl 7 }


--  1.3.6.1.4.1.6296.101.23.51.25.2.8
		sleGponProfile2MapperGemControlGemIndex OBJECT-TYPE
			SYNTAX Integer32
			MAX-ACCESS read-write
			STATUS current
			DESCRIPTION
				"The GEM index."
			::= { sleGponProfile2MapperGemControl 8 }


--  1.3.6.1.4.1.6296.101.23.51.25.2.9
		sleGponProfile2MapperGemControlRateLimitDownSir OBJECT-TYPE
			SYNTAX Integer32
			MAX-ACCESS read-write
			STATUS current
			DESCRIPTION
				"The downstream rate-limit control : SIR (Bandwidth in steps of 64Kbps)"
			::= { sleGponProfile2MapperGemControl 9 }


--  1.3.6.1.4.1.6296.101.23.51.25.2.10
		sleGponProfile2MapperGemControlRateLimitDownPir OBJECT-TYPE
			SYNTAX Integer32
			MAX-ACCESS read-write
			STATUS current
			DESCRIPTION
				"The downstream rate-limit control : PIR (Bandwidth in steps of 64Kbps)"
			::= { sleGponProfile2MapperGemControl 10 }


--  1.3.6.1.4.1.6296.101.23.51.25.2.11
		sleGponProfile2MapperGemControlRateLimitUpSir OBJECT-TYPE
			SYNTAX Integer32
			MAX-ACCESS read-write
			STATUS current
			DESCRIPTION
				"The upstream rate-limit control : SIR (Bandwidth in steps of 64Kbps)"
			::= { sleGponProfile2MapperGemControl 11 }


--  1.3.6.1.4.1.6296.101.23.51.25.2.12
		sleGponProfile2MapperGemControlRateLimitUpPir OBJECT-TYPE
			SYNTAX Integer32
			MAX-ACCESS read-write
			STATUS current
			DESCRIPTION
				"The upstream rate-limit control : PIR (Bandwidth in steps of 64Kbps)"
			::= { sleGponProfile2MapperGemControl 12 }


--  1.3.6.1.4.1.6296.101.23.51.25.2.13
		sleGponProfile2MapperGemControlRateLimitProfile OBJECT-TYPE
			SYNTAX OCTET STRING
			MAX-ACCESS read-write
			STATUS current
			DESCRIPTION
				"The rate-limit profile name."
			::= { sleGponProfile2MapperGemControl 13 }


--  1.3.6.1.4.1.6296.101.23.51.25.3
		sleGponProfile2MapperGemNotification OBJECT IDENTIFIER ::= { sleGponProfile2MapperGem 3 }


--  1.3.6.1.4.1.6296.101.23.51.25.3.1
		sleGponProfile2MapperGemRateLimitChanged NOTIFICATION-TYPE
			OBJECTS { sleGponProfile2MapperGemControlRequest, sleGponProfile2MapperGemControlTimeStamp, sleGponProfile2MapperGemControlReqResult, sleGponProfile2MapperGemControlTrafficName, sleGponProfile2MapperGemControlIndex,
				sleGponProfile2MapperGemControlGemIndex, sleGponProfile2MapperGemControlRateLimitDownSir, sleGponProfile2MapperGemControlRateLimitDownPir, sleGponProfile2MapperGemControlRateLimitUpSir, sleGponProfile2MapperGemControlRateLimitUpPir
				 }
			STATUS current
			DESCRIPTION
				"setGemRateLimit"
			::= { sleGponProfile2MapperGemNotification 1 }


--  1.3.6.1.4.1.6296.101.23.51.25.3.2
		sleGponProfile2MapperGemRateLimitDeleted NOTIFICATION-TYPE
			OBJECTS { sleGponProfile2MapperGemControlRequest, sleGponProfile2MapperGemControlTimeStamp, sleGponProfile2MapperGemControlReqResult, sleGponProfile2MapperGemControlTrafficName, sleGponProfile2MapperGemControlIndex,
				sleGponProfile2MapperGemControlGemIndex }
			STATUS current
			DESCRIPTION
				"delGemRateLimit"
			::= { sleGponProfile2MapperGemNotification 2 }


--  1.3.6.1.4.1.6296.101.23.51.25.3.3
		sleGponProfile2MapperGemRateLimitProfileChanged NOTIFICATION-TYPE
			OBJECTS { sleGponProfile2MapperGemControlRequest, sleGponProfile2MapperGemControlTimeStamp, sleGponProfile2MapperGemControlReqResult, sleGponProfile2MapperGemControlTrafficName, sleGponProfile2MapperGemControlIndex,
				sleGponProfile2MapperGemControlGemIndex, sleGponProfile2MapperGemControlRateLimitProfile }
			STATUS current
			DESCRIPTION
				"setGemRatelimitProfile"
			::= { sleGponProfile2MapperGemNotification 3 }


--  1.3.6.1.4.1.6296.101.23.51.26
		sleGponProfile2GemNctp OBJECT IDENTIFIER ::= { sleGponProfile2 26 }


--  1.3.6.1.4.1.6296.101.23.51.26.1
		sleGponProfile2GemNctpTable OBJECT-TYPE
			SYNTAX SEQUENCE OF SleGponProfile2GemNctpEntry
			MAX-ACCESS not-accessible
			STATUS current
			DESCRIPTION
				"Description."
			::= { sleGponProfile2GemNctp 1 }


--  1.3.6.1.4.1.6296.101.23.51.26.1.1
		sleGponProfile2GemNctpEntry OBJECT-TYPE
			SYNTAX SleGponProfile2GemNctpEntry
			MAX-ACCESS not-accessible
			STATUS current
			DESCRIPTION
				"Description."
			INDEX { sleGponProfile2TrafficIndex, sleGponProfile2GemNctpIndex }
			::= { sleGponProfile2GemNctpTable 1 }


		SleGponProfile2GemNctpEntry ::=
			SEQUENCE {
				sleGponProfile2GemNctpIndex
					Integer32,
				sleGponProfile2GemNctpServiceId
					Integer32,
				sleGponProfile2GemNctpServiceType
					INTEGER
			 }

--  1.3.6.1.4.1.6296.101.23.51.26.1.1.1
		sleGponProfile2GemNctpIndex OBJECT-TYPE
			SYNTAX Integer32 (1..65535)
			MAX-ACCESS read-only
			STATUS current
			DESCRIPTION
				"The NCTP index."
			::= { sleGponProfile2GemNctpEntry 1 }


--  1.3.6.1.4.1.6296.101.23.51.26.1.1.2
		sleGponProfile2GemNctpServiceId OBJECT-TYPE
			SYNTAX Integer32
			MAX-ACCESS read-only
			STATUS current
			DESCRIPTION
				"The NCTP service index."
			::= { sleGponProfile2GemNctpEntry 2 }


--  1.3.6.1.4.1.6296.101.23.51.26.1.1.3
		sleGponProfile2GemNctpServiceType OBJECT-TYPE
			SYNTAX INTEGER
				{
				svcTypeBridge(1),
				svcTypeIphost(2),
				svcTypeVRP(3)
				}
			MAX-ACCESS read-write
			STATUS current
			DESCRIPTION
				"The NCTP service type"
			::= { sleGponProfile2GemNctpEntry 3 }


--  1.3.6.1.4.1.6296.101.23.51.26.2
		sleGponProfile2GemNctpControl OBJECT IDENTIFIER ::= { sleGponProfile2GemNctp 2 }


--  1.3.6.1.4.1.6296.101.23.51.26.2.1
		sleGponProfile2GemNctpControlRequest OBJECT-TYPE
			SYNTAX INTEGER
				{
				addNCTPService(1),
				delNCTPService(2),
				setNCTPService(3)
				}
			MAX-ACCESS read-write
			STATUS current
			DESCRIPTION
				"The request of a user command"
			::= { sleGponProfile2GemNctpControl 1 }


--  1.3.6.1.4.1.6296.101.23.51.26.2.2
		sleGponProfile2GemNctpControlStatus OBJECT-TYPE
			SYNTAX SleControlStatusType
			MAX-ACCESS read-only
			STATUS current
			DESCRIPTION
				"The status of user command"
			::= { sleGponProfile2GemNctpControl 2 }


--  1.3.6.1.4.1.6296.101.23.51.26.2.3
		sleGponProfile2GemNctpControlTimer OBJECT-TYPE
			SYNTAX Gauge32
			MAX-ACCESS read-write
			STATUS current
			DESCRIPTION
				"The maximum time for the manager for a long running user command"
			::= { sleGponProfile2GemNctpControl 3 }


--  1.3.6.1.4.1.6296.101.23.51.26.2.4
		sleGponProfile2GemNctpControlTimeStamp OBJECT-TYPE
			SYNTAX TimeTicks
			MAX-ACCESS read-only
			STATUS current
			DESCRIPTION
				"The time stamp of the last command(end of command)"
			::= { sleGponProfile2GemNctpControl 4 }


--  1.3.6.1.4.1.6296.101.23.51.26.2.5
		sleGponProfile2GemNctpControlReqResult OBJECT-TYPE
			SYNTAX SleControlRequestResultType
			MAX-ACCESS read-only
			STATUS current
			DESCRIPTION
				"The result of the last user command"
			::= { sleGponProfile2GemNctpControl 5 }


--  1.3.6.1.4.1.6296.101.23.51.26.2.6
		sleGponProfile2GemNctpControlTname OBJECT-TYPE
			SYNTAX OCTET STRING
			MAX-ACCESS read-write
			STATUS current
			DESCRIPTION
				"The Traffic profile name."
			::= { sleGponProfile2GemNctpControl 6 }


--  1.3.6.1.4.1.6296.101.23.51.26.2.7
		sleGponProfile2GemNctpControlIndex OBJECT-TYPE
			SYNTAX Integer32
			MAX-ACCESS read-write
			STATUS current
			DESCRIPTION
				"The NCTP index."
			::= { sleGponProfile2GemNctpControl 7 }


--  1.3.6.1.4.1.6296.101.23.51.26.2.8
		sleGponProfile2GemNctpControlServiceId OBJECT-TYPE
			SYNTAX Integer32
			MAX-ACCESS read-write
			STATUS current
			DESCRIPTION
				"The NCTP service index."
			::= { sleGponProfile2GemNctpControl 8 }


--  1.3.6.1.4.1.6296.101.23.51.26.2.9
		sleGponProfile2GemNctpControlServiceType OBJECT-TYPE
			SYNTAX INTEGER
				{
				svcTypeBridge(1),
				svcTypeIphost(2),
				svcTypeVRP(3)
				}
			MAX-ACCESS read-write
			STATUS current
			DESCRIPTION
				"The NCTP service type"
			::= { sleGponProfile2GemNctpControl 9 }


--  1.3.6.1.4.1.6296.101.23.51.26.3
		sleGponProfile2GemNctpNotification OBJECT IDENTIFIER ::= { sleGponProfile2GemNctp 3 }


--  1.3.6.1.4.1.6296.101.23.51.26.3.1
		sleGponProfile2GemNctpServiceAdded NOTIFICATION-TYPE
			OBJECTS { sleGponProfile2GemNctpControlRequest, sleGponProfile2GemNctpControlTimeStamp, sleGponProfile2GemNctpControlReqResult, sleGponProfile2GemNctpControlTname, sleGponProfile2GemNctpControlIndex,
				sleGponProfile2GemNctpControlServiceId, sleGponProfile2GemNctpControlServiceType }
			STATUS current
			DESCRIPTION
				"addNCTPService"
			::= { sleGponProfile2GemNctpNotification 1 }


--  1.3.6.1.4.1.6296.101.23.51.26.3.2
		sleGponProfile2GemNctpServiceDeleted NOTIFICATION-TYPE
			OBJECTS { sleGponProfile2GemNctpControlRequest, sleGponProfile2GemNctpControlTimeStamp, sleGponProfile2GemNctpControlReqResult, sleGponProfile2GemNctpControlTname, sleGponProfile2GemNctpControlIndex
				 }
			STATUS current
			DESCRIPTION
				"delNCTPService"
			::= { sleGponProfile2GemNctpNotification 2 }


--  1.3.6.1.4.1.6296.101.23.51.26.3.3
		sleGponProfile2GemNctpServiceChanged NOTIFICATION-TYPE
			OBJECTS { sleGponProfile2GemNctpControlRequest, sleGponProfile2GemNctpControlTimeStamp, sleGponProfile2GemNctpControlReqResult, sleGponProfile2GemNctpControlTname, sleGponProfile2GemNctpControlIndex,
				sleGponProfile2GemNctpControlServiceId, sleGponProfile2GemNctpControlServiceType }
			STATUS current
			DESCRIPTION
				"setNCTPService"
			::= { sleGponProfile2GemNctpNotification 3 }


--  1.3.6.1.4.1.6296.101.23.51.27
		sleGponProfile2VideoReturnPathSvc OBJECT IDENTIFIER ::= { sleGponProfile2 27 }


--  1.3.6.1.4.1.6296.101.23.51.27.1
		sleGponProfile2VideoReturnPathSvcTable OBJECT-TYPE
			SYNTAX SEQUENCE OF SleGponProfile2VideoReturnPathSvcEntry
			MAX-ACCESS not-accessible
			STATUS current
			DESCRIPTION
				"Description."
			::= { sleGponProfile2VideoReturnPathSvc 1 }


--  1.3.6.1.4.1.6296.101.23.51.27.1.1
		sleGponProfile2VideoReturnPathSvcEntry OBJECT-TYPE
			SYNTAX SleGponProfile2VideoReturnPathSvcEntry
			MAX-ACCESS not-accessible
			STATUS current
			DESCRIPTION
				"Description."
			INDEX { sleGponProfile2TrafficIndex, sleGponProfile2VideoReturnPathSvcIndex }
			::= { sleGponProfile2VideoReturnPathSvcTable 1 }


		SleGponProfile2VideoReturnPathSvcEntry ::=
			SEQUENCE {
				sleGponProfile2VideoReturnPathSvcIndex
					Integer32,
				sleGponProfile2VideoReturnPathSvcMode
					INTEGER,
				sleGponProfile2VideoReturnPathSvcFrequency
					Integer32,
				sleGponProfile2VideoReturnPathSvcPhysical
					BITS
			 }

--  1.3.6.1.4.1.6296.101.23.51.27.1.1.1
		sleGponProfile2VideoReturnPathSvcIndex OBJECT-TYPE
			SYNTAX Integer32 (1..65535)
			MAX-ACCESS read-only
			STATUS current
			DESCRIPTION
				"The SVC index."
			::= { sleGponProfile2VideoReturnPathSvcEntry 1 }


--  1.3.6.1.4.1.6296.101.23.51.27.1.1.2
		sleGponProfile2VideoReturnPathSvcMode OBJECT-TYPE
			SYNTAX INTEGER
				{
				mode1VRP256k(0),
				mode2VRP256k(1),
				mode2VRP1M(2),
				mode2VRP3M(3)
				}
			MAX-ACCESS read-only
			STATUS current
			DESCRIPTION
				"The SVC mode."
			::= { sleGponProfile2VideoReturnPathSvcEntry 2 }


--  1.3.6.1.4.1.6296.101.23.51.27.1.1.3
		sleGponProfile2VideoReturnPathSvcFrequency OBJECT-TYPE
			SYNTAX Integer32
			MAX-ACCESS read-only
			STATUS current
			DESCRIPTION
				"The SVC frequency"
			::= { sleGponProfile2VideoReturnPathSvcEntry 3 }


--  1.3.6.1.4.1.6296.101.23.51.27.1.1.4
		sleGponProfile2VideoReturnPathSvcPhysical OBJECT-TYPE
			SYNTAX BITS
				{
				vrpStage13(0),
				vrpStage12(1),
				vrpStage11(2),
				vrpStage10(3),
				vrpStage9(4),
				vrpStage8(5),
				vrpStage7(6),
				vrpStage6(7),
				vrpDQPSKmode(8)
				}
			MAX-ACCESS read-write
			STATUS current
			DESCRIPTION
				"The SVC physical."
			::= { sleGponProfile2VideoReturnPathSvcEntry 4 }


--  1.3.6.1.4.1.6296.101.23.51.27.2
		sleGponProfile2VideoReturnPathSvcControl OBJECT IDENTIFIER ::= { sleGponProfile2VideoReturnPathSvc 2 }


--  1.3.6.1.4.1.6296.101.23.51.27.2.1
		sleGponProfile2VideoReturnPathSvcControlRequest OBJECT-TYPE
			SYNTAX INTEGER
				{
				addVrp(1),
				delVrp(2),
				setVrpMode(3),
				setVrpFrequency(4),
				setVrpPhysical(5)
				}
			MAX-ACCESS read-write
			STATUS current
			DESCRIPTION
				"The request of a user command"
			::= { sleGponProfile2VideoReturnPathSvcControl 1 }


--  1.3.6.1.4.1.6296.101.23.51.27.2.2
		sleGponProfile2VideoReturnPathSvcControlStatus OBJECT-TYPE
			SYNTAX SleControlStatusType
			MAX-ACCESS read-only
			STATUS current
			DESCRIPTION
				"The status of user command"
			::= { sleGponProfile2VideoReturnPathSvcControl 2 }


--  1.3.6.1.4.1.6296.101.23.51.27.2.3
		sleGponProfile2VideoReturnPathSvcControlTimer OBJECT-TYPE
			SYNTAX Gauge32
			MAX-ACCESS read-write
			STATUS current
			DESCRIPTION
				"The maximum time for the manager for a long running user command"
			::= { sleGponProfile2VideoReturnPathSvcControl 3 }


--  1.3.6.1.4.1.6296.101.23.51.27.2.4
		sleGponProfile2VideoReturnPathSvcControlTimeStamp OBJECT-TYPE
			SYNTAX TimeTicks
			MAX-ACCESS read-only
			STATUS current
			DESCRIPTION
				"The time stamp of the last command(end of command)"
			::= { sleGponProfile2VideoReturnPathSvcControl 4 }


--  1.3.6.1.4.1.6296.101.23.51.27.2.5
		sleGponProfile2VideoReturnPathSvcControlReqResult OBJECT-TYPE
			SYNTAX SleControlRequestResultType
			MAX-ACCESS read-only
			STATUS current
			DESCRIPTION
				"The result of the last user command"
			::= { sleGponProfile2VideoReturnPathSvcControl 5 }


--  1.3.6.1.4.1.6296.101.23.51.27.2.6
		sleGponProfile2VideoReturnPathSvcControlTname OBJECT-TYPE
			SYNTAX OCTET STRING
			MAX-ACCESS read-write
			STATUS current
			DESCRIPTION
				"The Traffic profile name."
			::= { sleGponProfile2VideoReturnPathSvcControl 6 }


--  1.3.6.1.4.1.6296.101.23.51.27.2.7
		sleGponProfile2VideoReturnPathSvcControlIndex OBJECT-TYPE
			SYNTAX Integer32
			MAX-ACCESS read-write
			STATUS current
			DESCRIPTION
				"The SVC index."
			::= { sleGponProfile2VideoReturnPathSvcControl 7 }


--  1.3.6.1.4.1.6296.101.23.51.27.2.8
		sleGponProfile2VideoReturnPathSvcControlMode OBJECT-TYPE
			SYNTAX INTEGER
				{
				mode1VRP256k(0),
				mode2VRP256k(1),
				mode2VRP1M(2),
				mode2VRP3M(3)
				}
			MAX-ACCESS read-write
			STATUS current
			DESCRIPTION
				"The SVC mode."
			::= { sleGponProfile2VideoReturnPathSvcControl 8 }


--  1.3.6.1.4.1.6296.101.23.51.27.2.9
		sleGponProfile2VideoReturnPathSvcControlFrequency OBJECT-TYPE
			SYNTAX Integer32
			MAX-ACCESS read-write
			STATUS current
			DESCRIPTION
				"The SVC frequency"
			::= { sleGponProfile2VideoReturnPathSvcControl 9 }


--  1.3.6.1.4.1.6296.101.23.51.27.2.10
		sleGponProfile2VideoReturnPathSvcControlPhysical OBJECT-TYPE
			SYNTAX BITS
				{
				vrpStage13(0),
				vrpStage12(1),
				vrpStage11(2),
				vrpStage10(3),
				vrpStage9(4),
				vrpStage8(5),
				vrpStage7(6),
				vrpStage6(7),
				vrpDQPSKmode(8)
				}
			MAX-ACCESS read-write
			STATUS current
			DESCRIPTION
				"The SVC physical."
			::= { sleGponProfile2VideoReturnPathSvcControl 10 }


--  1.3.6.1.4.1.6296.101.23.51.27.3
		sleGponProfile2VideoReturnPathSvcNotification OBJECT IDENTIFIER ::= { sleGponProfile2VideoReturnPathSvc 3 }


--  1.3.6.1.4.1.6296.101.23.51.27.3.1
		sleGponProfile2VideoReturnPathSvcAdded NOTIFICATION-TYPE
			OBJECTS { sleGponProfile2VideoReturnPathSvcControlRequest, sleGponProfile2VideoReturnPathSvcControlTimeStamp, sleGponProfile2VideoReturnPathSvcControlReqResult, sleGponProfile2VideoReturnPathSvcControlTname, sleGponProfile2VideoReturnPathSvcControlIndex,
				sleGponProfile2VideoReturnPathSvcControlMode, sleGponProfile2VideoReturnPathSvcControlFrequency, sleGponProfile2VideoReturnPathSvcControlPhysical }
			STATUS current
			DESCRIPTION
				"addVrp "
			::= { sleGponProfile2VideoReturnPathSvcNotification 1 }


--  1.3.6.1.4.1.6296.101.23.51.27.3.2
		sleGponProfile2VideoReturnPathSvcDeleted NOTIFICATION-TYPE
			OBJECTS { sleGponProfile2VideoReturnPathSvcControlRequest, sleGponProfile2VideoReturnPathSvcControlTimeStamp, sleGponProfile2VideoReturnPathSvcControlReqResult, sleGponProfile2VideoReturnPathSvcControlTname, sleGponProfile2VideoReturnPathSvcControlIndex
				 }
			STATUS current
			DESCRIPTION
				"delVrp "
			::= { sleGponProfile2VideoReturnPathSvcNotification 2 }


--  1.3.6.1.4.1.6296.101.23.51.27.3.3
		sleGponProfile2VideoReturnPathSvcModeChanged NOTIFICATION-TYPE
			OBJECTS { sleGponProfile2VideoReturnPathSvcControlRequest, sleGponProfile2VideoReturnPathSvcControlTimeStamp, sleGponProfile2VideoReturnPathSvcControlReqResult, sleGponProfile2VideoReturnPathSvcControlTname, sleGponProfile2VideoReturnPathSvcControlIndex,
				sleGponProfile2VideoReturnPathSvcControlMode }
			STATUS current
			DESCRIPTION
				"setVrpMode"
			::= { sleGponProfile2VideoReturnPathSvcNotification 3 }


--  1.3.6.1.4.1.6296.101.23.51.27.3.4
		sleGponProfile2VideoReturnPathSvcFrequencyChanged NOTIFICATION-TYPE
			OBJECTS { sleGponProfile2VideoReturnPathSvcControlRequest, sleGponProfile2VideoReturnPathSvcControlTimeStamp, sleGponProfile2VideoReturnPathSvcControlReqResult, sleGponProfile2VideoReturnPathSvcControlTname, sleGponProfile2VideoReturnPathSvcControlIndex,
				sleGponProfile2VideoReturnPathSvcControlFrequency }
			STATUS current
			DESCRIPTION
				"setVrpFrequency"
			::= { sleGponProfile2VideoReturnPathSvcNotification 4 }


--  1.3.6.1.4.1.6296.101.23.51.27.3.5
		sleGponProfile2VideoReturnPathSvcPhysicalChanged NOTIFICATION-TYPE
			OBJECTS { sleGponProfile2VideoReturnPathSvcControlRequest, sleGponProfile2VideoReturnPathSvcControlTimeStamp, sleGponProfile2VideoReturnPathSvcControlReqResult, sleGponProfile2VideoReturnPathSvcControlTname, sleGponProfile2VideoReturnPathSvcControlIndex,
				sleGponProfile2VideoReturnPathSvcControlPhysical }
			STATUS current
			DESCRIPTION
				"setVrpPhysical"
			::= { sleGponProfile2VideoReturnPathSvcNotification 5 }


--  1.3.6.1.4.1.6296.101.23.51.28
		sleGponProfile2PortMgmt OBJECT IDENTIFIER ::= { sleGponProfile2 28 }


--  1.3.6.1.4.1.6296.101.23.51.28.1
		sleGponProfile2PortMgmtTable OBJECT-TYPE
			SYNTAX SEQUENCE OF SleGponProfile2PortMgmtEntry
			MAX-ACCESS not-accessible
			STATUS current
			DESCRIPTION
				"Description."
			::= { sleGponProfile2PortMgmt 1 }


--  1.3.6.1.4.1.6296.101.23.51.28.1.1
		sleGponProfile2PortMgmtEntry OBJECT-TYPE
			SYNTAX SleGponProfile2PortMgmtEntry
			MAX-ACCESS not-accessible
			STATUS current
			DESCRIPTION
				"Description."
			INDEX { sleGponProfile2TrafficIndex, sleGponProfile2PortMgmtSlotId, sleGponProfile2PortMgmtPortId }
			::= { sleGponProfile2PortMgmtTable 1 }


		SleGponProfile2PortMgmtEntry ::=
			SEQUENCE {
				sleGponProfile2PortMgmtSlotId
					INTEGER,
				sleGponProfile2PortMgmtPortId
					Integer32,
				sleGponProfile2PortMgmtMode
					INTEGER,
				sleGponProfile2PotMgmtVirtualEthNum
					Integer32
			 }

--  1.3.6.1.4.1.6296.101.23.51.28.1.1.1
		sleGponProfile2PortMgmtSlotId OBJECT-TYPE
			SYNTAX INTEGER
				{
				ethernet(1),
				pots(2),
				ces(3),
				video(4)
				}
			MAX-ACCESS read-only
			STATUS current
			DESCRIPTION
				"The Slot ID"
			::= { sleGponProfile2PortMgmtEntry 1 }


--  1.3.6.1.4.1.6296.101.23.51.28.1.1.2
		sleGponProfile2PortMgmtPortId OBJECT-TYPE
			SYNTAX Integer32 (1..32)
			MAX-ACCESS read-only
			STATUS current
			DESCRIPTION
				"The Port ID"
			::= { sleGponProfile2PortMgmtEntry 2 }


--  1.3.6.1.4.1.6296.101.23.51.28.1.1.3
		sleGponProfile2PortMgmtMode OBJECT-TYPE
			SYNTAX INTEGER
				{
				modeOMCI(0),
				modeNonOMCI(1)
				}
			MAX-ACCESS read-only
			STATUS current
			DESCRIPTION
				"The Mgmt mode.
				0 : OMCI mode
				1 : Non-OMCI mode
				"
			::= { sleGponProfile2PortMgmtEntry 3 }


--  1.3.6.1.4.1.6296.101.23.51.28.1.1.4
		sleGponProfile2PotMgmtVirtualEthNum OBJECT-TYPE
			SYNTAX Integer32 (1..32)
			MAX-ACCESS read-only
			STATUS current
			DESCRIPTION
				"Virtual Eth Number"
			::= { sleGponProfile2PortMgmtEntry 4 }


--  1.3.6.1.4.1.6296.101.23.51.28.2
		sleGponProfile2PortMgmtControl OBJECT IDENTIFIER ::= { sleGponProfile2PortMgmt 2 }


--  1.3.6.1.4.1.6296.101.23.51.28.2.1
		sleGponProfile2PortMgmtControlRequest OBJECT-TYPE
			SYNTAX INTEGER
				{
				setPortMgmtMode(1),
				unsetPortMgmtMode(2)
				}
			MAX-ACCESS read-write
			STATUS current
			DESCRIPTION
				"The request of a user command"
			::= { sleGponProfile2PortMgmtControl 1 }


--  1.3.6.1.4.1.6296.101.23.51.28.2.2
		sleGponProfile2PortMgmtControlStatus OBJECT-TYPE
			SYNTAX SleControlStatusType
			MAX-ACCESS read-only
			STATUS current
			DESCRIPTION
				"The status of user command"
			::= { sleGponProfile2PortMgmtControl 2 }


--  1.3.6.1.4.1.6296.101.23.51.28.2.3
		sleGponProfile2PortMgmtControlTimer OBJECT-TYPE
			SYNTAX Gauge32
			MAX-ACCESS read-write
			STATUS current
			DESCRIPTION
				"The maximum time for the manager for a long running user command"
			::= { sleGponProfile2PortMgmtControl 3 }


--  1.3.6.1.4.1.6296.101.23.51.28.2.4
		sleGponProfile2PortMgmtControlTimeStamp OBJECT-TYPE
			SYNTAX TimeTicks
			MAX-ACCESS read-only
			STATUS current
			DESCRIPTION
				"The time stamp of the last command(end of command)"
			::= { sleGponProfile2PortMgmtControl 4 }


--  1.3.6.1.4.1.6296.101.23.51.28.2.5
		sleGponProfile2PortMgmtControlReqResult OBJECT-TYPE
			SYNTAX SleControlRequestResultType
			MAX-ACCESS read-only
			STATUS current
			DESCRIPTION
				"The result of the last user command"
			::= { sleGponProfile2PortMgmtControl 5 }


--  1.3.6.1.4.1.6296.101.23.51.28.2.6
		sleGponProfile2PortMgmtControlTName OBJECT-TYPE
			SYNTAX OCTET STRING
			MAX-ACCESS read-write
			STATUS current
			DESCRIPTION
				"The Traffic profile name."
			::= { sleGponProfile2PortMgmtControl 6 }


--  1.3.6.1.4.1.6296.101.23.51.28.2.7
		sleGponProfile2PortMgmtControlSlotId OBJECT-TYPE
			SYNTAX INTEGER
				{
				ethernet(1),
				pots(2),
				ces(3),
				video(4)
				}
			MAX-ACCESS read-write
			STATUS current
			DESCRIPTION
				"The Slot ID"
			::= { sleGponProfile2PortMgmtControl 7 }


--  1.3.6.1.4.1.6296.101.23.51.28.2.8
		sleGponProfile2PortMgmtControlPortId OBJECT-TYPE
			SYNTAX Integer32 (1..32)
			MAX-ACCESS read-write
			STATUS current
			DESCRIPTION
				"The Port ID"
			::= { sleGponProfile2PortMgmtControl 8 }


--  1.3.6.1.4.1.6296.101.23.51.28.2.9
		sleGponProfile2PortMgmtControlMode OBJECT-TYPE
			SYNTAX INTEGER
				{
				modeOMCI(0),
				modeNonOMCI(1)
				}
			MAX-ACCESS read-write
			STATUS current
			DESCRIPTION
				"The Mgmt mode.
				0 : OMCI mode
				1 : Non-OMCI mode"
			::= { sleGponProfile2PortMgmtControl 9 }


--  1.3.6.1.4.1.6296.101.23.51.28.2.10
		sleGponProfile2PortMgmtControlVirtualEthNum OBJECT-TYPE
			SYNTAX Integer32 (1..32)
			MAX-ACCESS read-write
			STATUS current
			DESCRIPTION
				"Virtual Eth Number"
			::= { sleGponProfile2PortMgmtControl 10 }


--  1.3.6.1.4.1.6296.101.23.51.28.3
		sleGponProfile2PortMgmtNotification OBJECT IDENTIFIER ::= { sleGponProfile2PortMgmt 3 }


--  1.3.6.1.4.1.6296.101.23.51.28.3.1
		sleGponProfile2PortMgmtSetted NOTIFICATION-TYPE
			OBJECTS { sleGponProfile2PortMgmtControlRequest, sleGponProfile2PortMgmtControlTimeStamp, sleGponProfile2PortMgmtControlReqResult, sleGponProfile2PortMgmtControlTName, sleGponProfile2PortMgmtControlSlotId,
				sleGponProfile2PortMgmtControlPortId, sleGponProfile2PortMgmtControlMode, sleGponProfile2PortMgmtControlVirtualEthNum }
			STATUS current
			DESCRIPTION
				"setPortMgmtMode"
			::= { sleGponProfile2PortMgmtNotification 1 }


--  1.3.6.1.4.1.6296.101.23.51.28.3.2
		sleGponProfile2PortMgmtUnsetted NOTIFICATION-TYPE
			OBJECTS { sleGponProfile2PortMgmtControlRequest, sleGponProfile2PortMgmtControlTimeStamp, sleGponProfile2PortMgmtControlReqResult, sleGponProfile2PortMgmtControlTName, sleGponProfile2PortMgmtControlSlotId,
				sleGponProfile2PortMgmtControlPortId }
			STATUS current
			DESCRIPTION
				"unsetPortMgmtMode"
			::= { sleGponProfile2PortMgmtNotification 2 }


--   1.3.6.1.4.1.6296.101.23.51.9
-- 1.3.6.1.4.1.6296.101.23.51.29
		sleGponProfile2McastAccessList OBJECT IDENTIFIER ::= { sleGponProfile2 29 }


--   1.3.6.1.4.1.6296.101.23.51.9.1
-- 1.3.6.1.4.1.6296.101.23.51.29.1
		sleGponProfile2McastAccessListTable OBJECT-TYPE
			SYNTAX SEQUENCE OF SleGponProfile2McastAccessListEntry
			MAX-ACCESS not-accessible
			STATUS current
			DESCRIPTION
				"sleGponProfile2McastTable"
			::= { sleGponProfile2McastAccessList 1 }


--   1.3.6.1.4.1.6296.101.23.51.9.1.1
-- 1.3.6.1.4.1.6296.101.23.51.29.1.1
		sleGponProfile2McastAccessListEntry OBJECT-TYPE
			SYNTAX SleGponProfile2McastAccessListEntry
			MAX-ACCESS not-accessible
			STATUS current
			DESCRIPTION
				"key: sleGponProfile2McastIndex"
			INDEX { sleGponProfile2McastAccessListIndex }
			::= { sleGponProfile2McastAccessListTable 1 }


		SleGponProfile2McastAccessListEntry ::=
			SEQUENCE {
				sleGponProfile2McastAccessListIndex
					Integer32,
				sleGponProfile2McastAccessListName
					OCTET STRING
			 }

--   1.3.6.1.4.1.6296.101.23.51.9.1.1.1
-- 1.3.6.1.4.1.6296.101.23.51.29.1.1.1
		sleGponProfile2McastAccessListIndex OBJECT-TYPE
			SYNTAX Integer32 (1..65535)
			MAX-ACCESS read-only
			STATUS current
			DESCRIPTION
				"The Mcast access-list profile index."
			::= { sleGponProfile2McastAccessListEntry 1 }


--   1.3.6.1.4.1.6296.101.23.51.9.1.1.2
-- 1.3.6.1.4.1.6296.101.23.51.29.1.1.2
		sleGponProfile2McastAccessListName OBJECT-TYPE
			SYNTAX OCTET STRING
			MAX-ACCESS read-only
			STATUS current
			DESCRIPTION
				"The Mcast access-list profile name."
			::= { sleGponProfile2McastAccessListEntry 2 }


--   1.3.6.1.4.1.6296.101.23.51.9.2
-- 1.3.6.1.4.1.6296.101.23.51.29.2
		sleGponProfile2McastAccessListControl OBJECT IDENTIFIER ::= { sleGponProfile2McastAccessList 2 }


--   1.3.6.1.4.1.6296.101.23.51.9.2.1
-- 1.3.6.1.4.1.6296.101.23.51.29.2.1
		sleGponProfile2McastAccessListControlRequest OBJECT-TYPE
			SYNTAX INTEGER
				{
				addMcastACL(1),
				delMcastACL(2)
				}
			MAX-ACCESS read-write
			STATUS current
			DESCRIPTION
				"The request of a user command"
			::= { sleGponProfile2McastAccessListControl 1 }


--   1.3.6.1.4.1.6296.101.23.51.9.2.2
-- 1.3.6.1.4.1.6296.101.23.51.29.2.2
		sleGponProfile2McastAccessListControlStatus OBJECT-TYPE
			SYNTAX SleControlStatusType
			MAX-ACCESS read-write
			STATUS current
			DESCRIPTION
				"The status of user command"
			::= { sleGponProfile2McastAccessListControl 2 }


--   1.3.6.1.4.1.6296.101.23.51.9.2.3
-- 1.3.6.1.4.1.6296.101.23.51.29.2.3
		sleGponProfile2McastAccessListControlTimer OBJECT-TYPE
			SYNTAX Gauge32
			MAX-ACCESS read-write
			STATUS current
			DESCRIPTION
				"The maximum time for the manager for a long running user command"
			::= { sleGponProfile2McastAccessListControl 3 }


--   1.3.6.1.4.1.6296.101.23.51.9.2.4
-- 1.3.6.1.4.1.6296.101.23.51.29.2.4
		sleGponProfile2McastAccessListControlTimeStamp OBJECT-TYPE
			SYNTAX TimeTicks
			MAX-ACCESS read-write
			STATUS current
			DESCRIPTION
				"The time stamp of the last command(end of command)"
			::= { sleGponProfile2McastAccessListControl 4 }


--   1.3.6.1.4.1.6296.101.23.51.9.2.5
-- 1.3.6.1.4.1.6296.101.23.51.29.2.5
		sleGponProfile2McastAccessListControlReqResult OBJECT-TYPE
			SYNTAX SleControlRequestResultType
			MAX-ACCESS read-write
			STATUS current
			DESCRIPTION
				"The result of the last user command"
			::= { sleGponProfile2McastAccessListControl 5 }


--   1.3.6.1.4.1.6296.101.23.51.9.2.6
-- 1.3.6.1.4.1.6296.101.23.51.29.2.6
		sleGponProfile2McastAccessListControlName OBJECT-TYPE
			SYNTAX OCTET STRING
			MAX-ACCESS read-write
			STATUS current
			DESCRIPTION
				"The Mcast access-list profile name."
			::= { sleGponProfile2McastAccessListControl 6 }


--   1.3.6.1.4.1.6296.101.23.51.9.3
-- 1.3.6.1.4.1.6296.101.23.51.29.3
		sleGponProfile2McastAccessListNotification OBJECT IDENTIFIER ::= { sleGponProfile2McastAccessList 3 }


--   1.3.6.1.4.1.6296.101.23.51.9.3.1
-- 1.3.6.1.4.1.6296.101.23.51.29.3.1
		sleGponProfile2McastAccessListAdded NOTIFICATION-TYPE
			OBJECTS { sleGponProfile2McastControlRequest, sleGponProfile2McastControlTimeStamp, sleGponProfile2McastControlReqResult, sleGponProfile2McastControlName }
			STATUS current
			DESCRIPTION
				"addMcastACL"
			::= { sleGponProfile2McastAccessListNotification 1 }


--   1.3.6.1.4.1.6296.101.23.51.9.3.1
-- 1.3.6.1.4.1.6296.101.23.51.29.3.2
		sleGponProfile2McastAccessListDeleted NOTIFICATION-TYPE
			OBJECTS { sleGponProfile2McastControlRequest, sleGponProfile2McastControlTimeStamp, sleGponProfile2McastControlReqResult, sleGponProfile2McastControlName }
			STATUS current
			DESCRIPTION
				"delMcastACL"
			::= { sleGponProfile2McastAccessListNotification 2 }


--   1.3.6.1.4.1.6296.101.23.51.10
-- 1.3.6.1.4.1.6296.101.23.51.30
		sleGponProfile2McastAccessListDynamic OBJECT IDENTIFIER ::= { sleGponProfile2 30 }


--   1.3.6.1.4.1.6296.101.23.51.10.1
-- 1.3.6.1.4.1.6296.101.23.51.30.1
		sleGponProfile2McastAccessListDynamicTable OBJECT-TYPE
			SYNTAX SEQUENCE OF SleGponProfile2McastAccessListDynamicEntry
			MAX-ACCESS not-accessible
			STATUS current
			DESCRIPTION
				"sleGponProfile2McastAclTable"
			::= { sleGponProfile2McastAccessListDynamic 1 }


--   1.3.6.1.4.1.6296.101.23.51.10.1.1
-- 1.3.6.1.4.1.6296.101.23.51.30.1.1
		sleGponProfile2McastAccessListDynamicEntry OBJECT-TYPE
			SYNTAX SleGponProfile2McastAccessListDynamicEntry
			MAX-ACCESS not-accessible
			STATUS current
			DESCRIPTION
				"key: sleGponProfile2McastIndex, sleGponProfile2McastAclIndex"
			INDEX { sleGponProfile2McastAccessListIndex, sleGponProfile2McastAccessListDynamicIndex }
			::= { sleGponProfile2McastAccessListDynamicTable 1 }


		SleGponProfile2McastAccessListDynamicEntry ::=
			SEQUENCE {
				sleGponProfile2McastAccessListDynamicIndex
					Integer32,
				sleGponProfile2McastAccessListDynamicVid
					Integer32,
				sleGponProfile2McastAccessListDynamicDstIpStart
					IpAddress,
				sleGponProfile2McastAccessListDynamicDstIpEnd
					IpAddress,
				sleGponProfile2McastAccessListDynamicSrcIp
					IpAddress,
				sleGponProfile2McastAccessListDynamicBandwidth
					Integer32,
				sleGponProfile2McastAccessListDynamicGem
					Integer32,
				sleGponProfile2McastAccessListDynamicCos
					Integer32
			 }

--   1.3.6.1.4.1.6296.101.23.51.10.1.1.1
-- 1.3.6.1.4.1.6296.101.23.51.30.1.1.1
		sleGponProfile2McastAccessListDynamicIndex OBJECT-TYPE
			SYNTAX Integer32 (1..65535)
			MAX-ACCESS read-only
			STATUS current
			DESCRIPTION
				"The Mcast access-list dynamic index."
			::= { sleGponProfile2McastAccessListDynamicEntry 1 }


--   1.3.6.1.4.1.6296.101.23.51.10.1.1.2
-- 1.3.6.1.4.1.6296.101.23.51.30.1.1.2
		sleGponProfile2McastAccessListDynamicVid OBJECT-TYPE
			SYNTAX Integer32 (0 | 1..4094)
			MAX-ACCESS read-write
			STATUS current
			DESCRIPTION
				"This specific the VLAN carrying the multicast group DS"
			::= { sleGponProfile2McastAccessListDynamicEntry 2 }


--   1.3.6.1.4.1.6296.101.23.51.10.1.1.3
-- 1.3.6.1.4.1.6296.101.23.51.30.1.1.3
		sleGponProfile2McastAccessListDynamicDstIpStart OBJECT-TYPE
			SYNTAX IpAddress
			MAX-ACCESS read-only
			STATUS current
			DESCRIPTION
				"The destination IP range-start."
			::= { sleGponProfile2McastAccessListDynamicEntry 3 }


--   1.3.6.1.4.1.6296.101.23.51.10.1.1.4
-- 1.3.6.1.4.1.6296.101.23.51.30.1.1.4
		sleGponProfile2McastAccessListDynamicDstIpEnd OBJECT-TYPE
			SYNTAX IpAddress
			MAX-ACCESS read-only
			STATUS current
			DESCRIPTION
				"The destination IP range-end"
			::= { sleGponProfile2McastAccessListDynamicEntry 4 }


--   1.3.6.1.4.1.6296.101.23.51.10.1.1.5
-- 1.3.6.1.4.1.6296.101.23.51.30.1.1.5
		sleGponProfile2McastAccessListDynamicSrcIp OBJECT-TYPE
			SYNTAX IpAddress
			MAX-ACCESS read-only
			STATUS current
			DESCRIPTION
				"The source IP."
			::= { sleGponProfile2McastAccessListDynamicEntry 5 }


--   1.3.6.1.4.1.6296.101.23.51.10.1.1.6
-- 1.3.6.1.4.1.6296.101.23.51.30.1.1.6
		sleGponProfile2McastAccessListDynamicBandwidth OBJECT-TYPE
			SYNTAX Integer32
			MAX-ACCESS read-only
			STATUS current
			DESCRIPTION
				"The Imputed group bandwidth"
			::= { sleGponProfile2McastAccessListDynamicEntry 6 }


--   1.3.6.1.4.1.6296.101.23.51.10.1.1.7
-- 1.3.6.1.4.1.6296.101.23.51.30.1.1.7
		sleGponProfile2McastAccessListDynamicGem OBJECT-TYPE
			SYNTAX Integer32 (1..25)
			MAX-ACCESS read-only
			STATUS current
			DESCRIPTION
				"Th GEM port ID"
			::= { sleGponProfile2McastAccessListDynamicEntry 7 }


--  1.3.6.1.4.1.6296.101.23.51.30.1.1.8
		sleGponProfile2McastAccessListDynamicCos OBJECT-TYPE
			SYNTAX Integer32 (0..7)
			MAX-ACCESS read-only
			STATUS current
			DESCRIPTION
				"The access-list CoS"
			::= { sleGponProfile2McastAccessListDynamicEntry 8 }


--   1.3.6.1.4.1.6296.101.23.51.10.2
-- 1.3.6.1.4.1.6296.101.23.51.30.2
		sleGponProfile2McastAccessListDynamicControl OBJECT IDENTIFIER ::= { sleGponProfile2McastAccessListDynamic 2 }


--   1.3.6.1.4.1.6296.101.23.51.10.2.1
-- 1.3.6.1.4.1.6296.101.23.51.30.2.1
		sleGponProfile2McastAccessListDynamicControlRequest OBJECT-TYPE
			SYNTAX INTEGER
				{
				addMcastAclDynamic(1),
				delMcastAclDynamic(2)
				}
			MAX-ACCESS read-write
			STATUS current
			DESCRIPTION
				"The request of a user command"
			::= { sleGponProfile2McastAccessListDynamicControl 1 }


--   1.3.6.1.4.1.6296.101.23.51.10.2.2
-- 1.3.6.1.4.1.6296.101.23.51.30.2.2
		sleGponProfile2McastAccessListDynamicControlStatus OBJECT-TYPE
			SYNTAX SleControlStatusType
			MAX-ACCESS read-write
			STATUS current
			DESCRIPTION
				"The status of user command"
			::= { sleGponProfile2McastAccessListDynamicControl 2 }


--   1.3.6.1.4.1.6296.101.23.51.10.2.3
-- 1.3.6.1.4.1.6296.101.23.51.30.2.3
		sleGponProfile2McastAccessListDynamicControlTimer OBJECT-TYPE
			SYNTAX Gauge32
			MAX-ACCESS read-write
			STATUS current
			DESCRIPTION
				"The maximum time for the manager for a long running user command"
			::= { sleGponProfile2McastAccessListDynamicControl 3 }


--   1.3.6.1.4.1.6296.101.23.51.10.2.4
-- 1.3.6.1.4.1.6296.101.23.51.30.2.4
		sleGponProfile2McastAccessListDynamicControlTimeStamp OBJECT-TYPE
			SYNTAX TimeTicks
			MAX-ACCESS read-write
			STATUS current
			DESCRIPTION
				"The time stamp of the last command(end of command)"
			::= { sleGponProfile2McastAccessListDynamicControl 4 }


--   1.3.6.1.4.1.6296.101.23.51.10.2.5
-- 1.3.6.1.4.1.6296.101.23.51.30.2.5
		sleGponProfile2McastAccessListDynamicControlReqResult OBJECT-TYPE
			SYNTAX SleControlRequestResultType
			MAX-ACCESS read-write
			STATUS current
			DESCRIPTION
				"The result of the last user command
				"
			::= { sleGponProfile2McastAccessListDynamicControl 5 }


--   1.3.6.1.4.1.6296.101.23.51.10.2.6
-- 1.3.6.1.4.1.6296.101.23.51.30.2.6
		sleGponProfile2McastAccessListDynamicControlIndex OBJECT-TYPE
			SYNTAX Integer32
			MAX-ACCESS read-write
			STATUS current
			DESCRIPTION
				"The Mcast access-list  dynamic index."
			::= { sleGponProfile2McastAccessListDynamicControl 6 }


--   1.3.6.1.4.1.6296.101.23.51.10.2.7
-- 1.3.6.1.4.1.6296.101.23.51.30.2.7
		sleGponProfile2McastAccessListDynamicControlVid OBJECT-TYPE
			SYNTAX Integer32 (0 | 1..4094)
			MAX-ACCESS read-write
			STATUS current
			DESCRIPTION
				"This specific the VLAN carrying the multicast group DS"
			::= { sleGponProfile2McastAccessListDynamicControl 7 }


--   1.3.6.1.4.1.6296.101.23.51.10.2.8
-- 1.3.6.1.4.1.6296.101.23.51.30.2.8
		sleGponProfile2McastAccessListDynamicControlName OBJECT-TYPE
			SYNTAX OCTET STRING
			MAX-ACCESS read-write
			STATUS current
			DESCRIPTION
				"The Mcast profile name."
			::= { sleGponProfile2McastAccessListDynamicControl 8 }


--   1.3.6.1.4.1.6296.101.23.51.10.2.9
-- 1.3.6.1.4.1.6296.101.23.51.30.2.9
		sleGponProfile2McastAccessListDynamicControlDstIpStart OBJECT-TYPE
			SYNTAX IpAddress
			MAX-ACCESS read-write
			STATUS current
			DESCRIPTION
				"The destination IP range-start."
			::= { sleGponProfile2McastAccessListDynamicControl 9 }


--   1.3.6.1.4.1.6296.101.23.51.10.2.10
-- 1.3.6.1.4.1.6296.101.23.51.30.2.10
		sleGponProfile2McastAccessListDynamicControlDstIpEnd OBJECT-TYPE
			SYNTAX IpAddress
			MAX-ACCESS read-write
			STATUS current
			DESCRIPTION
				"The destination IP range-end"
			::= { sleGponProfile2McastAccessListDynamicControl 10 }


--   1.3.6.1.4.1.6296.101.23.51.10.2.11
-- 1.3.6.1.4.1.6296.101.23.51.30.2.11
		sleGponProfile2McastAccessListDynamicControlSrcIp OBJECT-TYPE
			SYNTAX IpAddress
			MAX-ACCESS read-write
			STATUS current
			DESCRIPTION
				"The source IP."
			::= { sleGponProfile2McastAccessListDynamicControl 11 }


--   1.3.6.1.4.1.6296.101.23.51.10.2.12
-- 1.3.6.1.4.1.6296.101.23.51.30.2.12
		sleGponProfile2McastAccessListDynamicControlBandwidth OBJECT-TYPE
			SYNTAX Integer32
			MAX-ACCESS read-write
			STATUS current
			DESCRIPTION
				"The Imputed group bandwidth"
			::= { sleGponProfile2McastAccessListDynamicControl 12 }


--   1.3.6.1.4.1.6296.101.23.51.10.2.13
-- 1.3.6.1.4.1.6296.101.23.51.30.2.13
		sleGponProfile2McastAccessListDynamicControlGem OBJECT-TYPE
			SYNTAX Integer32 (1..25)
			MAX-ACCESS read-write
			STATUS current
			DESCRIPTION
				"The GEM port ID"
			::= { sleGponProfile2McastAccessListDynamicControl 13 }


--  1.3.6.1.4.1.6296.101.23.51.30.2.14
		sleGponProfile2McastAccessListDynamicControlCos OBJECT-TYPE
			SYNTAX Integer32 (0..7)
			MAX-ACCESS read-write
			STATUS current
			DESCRIPTION
				"The access-list CoS"
			::= { sleGponProfile2McastAccessListDynamicControl 14 }


--   1.3.6.1.4.1.6296.101.23.51.10.3
-- 1.3.6.1.4.1.6296.101.23.51.30.3
		sleGponProfile2McastAccessListDynamicNotification OBJECT IDENTIFIER ::= { sleGponProfile2McastAccessListDynamic 3 }


--   1.3.6.1.4.1.6296.101.23.51.10.3.1
-- 1.3.6.1.4.1.6296.101.23.51.30.3.1
		sleGponProfile2McastAccessListDynamicAdded NOTIFICATION-TYPE
			OBJECTS { sleGponProfile2McastAccessListDynamicControlRequest, sleGponProfile2McastAccessListDynamicControlTimeStamp, sleGponProfile2McastAccessListDynamicControlReqResult, sleGponProfile2McastAccessListDynamicControlVid, sleGponProfile2McastAccessListDynamicControlName,
				sleGponProfile2McastAccessListDynamicControlDstIpStart, sleGponProfile2McastAccessListDynamicControlDstIpEnd, sleGponProfile2McastAccessListDynamicControlSrcIp, sleGponProfile2McastAccessListDynamicControlBandwidth, sleGponProfile2McastAccessListDynamicControlGem,
				sleGponProfile2McastAccessListDynamicControlCos }
			STATUS current
			DESCRIPTION
				"addMcastAclDynamic"
			::= { sleGponProfile2McastAccessListDynamicNotification 1 }


--   1.3.6.1.4.1.6296.101.23.51.10.3.1
-- 1.3.6.1.4.1.6296.101.23.51.30.3.2
		sleGponProfile2McastAccessListDynamicDeleted NOTIFICATION-TYPE
			OBJECTS { sleGponProfile2McastAccessListDynamicControlRequest, sleGponProfile2McastAccessListDynamicControlTimeStamp, sleGponProfile2McastAccessListDynamicControlReqResult, sleGponProfile2McastAccessListDynamicControlVid, sleGponProfile2McastAccessListDynamicControlName
				 }
			STATUS current
			DESCRIPTION
				"delMcastAclDynamic"
			::= { sleGponProfile2McastAccessListDynamicNotification 2 }


--   1.3.6.1.4.1.6296.101.23.51.10
-- 1.3.6.1.4.1.6296.101.23.51.31
		sleGponProfile2McastAccessListStatic OBJECT IDENTIFIER ::= { sleGponProfile2 31 }


--   1.3.6.1.4.1.6296.101.23.51.10.1
-- 1.3.6.1.4.1.6296.101.23.51.31.1
		sleGponProfile2McastAccessListStaticTable OBJECT-TYPE
			SYNTAX SEQUENCE OF SleGponProfile2McastAccessListStaticEntry
			MAX-ACCESS not-accessible
			STATUS current
			DESCRIPTION
				"sleGponProfile2McastAclTable"
			::= { sleGponProfile2McastAccessListStatic 1 }


--   1.3.6.1.4.1.6296.101.23.51.10.1.1
-- 1.3.6.1.4.1.6296.101.23.51.31.1.1
		sleGponProfile2McastAccessListStaticEntry OBJECT-TYPE
			SYNTAX SleGponProfile2McastAccessListStaticEntry
			MAX-ACCESS not-accessible
			STATUS current
			DESCRIPTION
				"key: sleGponProfile2McastIndex, sleGponProfile2McastAclIndex"
			INDEX { sleGponProfile2McastAccessListIndex, sleGponProfile2McastAccessListStaticIndex }
			::= { sleGponProfile2McastAccessListStaticTable 1 }


		SleGponProfile2McastAccessListStaticEntry ::=
			SEQUENCE {
				sleGponProfile2McastAccessListStaticIndex
					Integer32,
				sleGponProfile2McastAccessListStaticVid
					Integer32,
				sleGponProfile2McastAccessListStaticDstIpStart
					IpAddress,
				sleGponProfile2McastAccessListStaticDstIpEnd
					IpAddress,
				sleGponProfile2McastAccessListStaticSrcIp
					IpAddress,
				sleGponProfile2McastAccessListStaticBandwidth
					Integer32,
				sleGponProfile2McastAccessListStaticGem
					Integer32,
				sleGponProfile2McastAccessListStaticCos
					Integer32
			 }

--   1.3.6.1.4.1.6296.101.23.51.10.1.1.1
-- 1.3.6.1.4.1.6296.101.23.51.31.1.1.1
		sleGponProfile2McastAccessListStaticIndex OBJECT-TYPE
			SYNTAX Integer32 (1..65535)
			MAX-ACCESS read-only
			STATUS current
			DESCRIPTION
				"The Mcast access-list static index."
			::= { sleGponProfile2McastAccessListStaticEntry 1 }


--   1.3.6.1.4.1.6296.101.23.51.10.1.1.2
-- 1.3.6.1.4.1.6296.101.23.51.31.1.1.2
		sleGponProfile2McastAccessListStaticVid OBJECT-TYPE
			SYNTAX Integer32 (0 | 1..4094)
			MAX-ACCESS read-write
			STATUS current
			DESCRIPTION
				"This specific the VLAN carrying the multicast group DS"
			::= { sleGponProfile2McastAccessListStaticEntry 2 }


--   1.3.6.1.4.1.6296.101.23.51.10.1.1.3
-- 1.3.6.1.4.1.6296.101.23.51.31.1.1.3
		sleGponProfile2McastAccessListStaticDstIpStart OBJECT-TYPE
			SYNTAX IpAddress
			MAX-ACCESS read-only
			STATUS current
			DESCRIPTION
				"The destination IP range-start."
			::= { sleGponProfile2McastAccessListStaticEntry 3 }


--   1.3.6.1.4.1.6296.101.23.51.10.1.1.4
-- 1.3.6.1.4.1.6296.101.23.51.31.1.1.4
		sleGponProfile2McastAccessListStaticDstIpEnd OBJECT-TYPE
			SYNTAX IpAddress
			MAX-ACCESS read-only
			STATUS current
			DESCRIPTION
				"The destination IP range-end"
			::= { sleGponProfile2McastAccessListStaticEntry 4 }


--   1.3.6.1.4.1.6296.101.23.51.10.1.1.5
-- 1.3.6.1.4.1.6296.101.23.51.31.1.1.5
		sleGponProfile2McastAccessListStaticSrcIp OBJECT-TYPE
			SYNTAX IpAddress
			MAX-ACCESS read-only
			STATUS current
			DESCRIPTION
				"The source IP."
			::= { sleGponProfile2McastAccessListStaticEntry 5 }


--   1.3.6.1.4.1.6296.101.23.51.10.1.1.6
-- 1.3.6.1.4.1.6296.101.23.51.31.1.1.6
		sleGponProfile2McastAccessListStaticBandwidth OBJECT-TYPE
			SYNTAX Integer32
			MAX-ACCESS read-only
			STATUS current
			DESCRIPTION
				"The Imputed group bandwidth"
			::= { sleGponProfile2McastAccessListStaticEntry 6 }


--   1.3.6.1.4.1.6296.101.23.51.10.1.1.7
-- 1.3.6.1.4.1.6296.101.23.51.31.1.1.7
		sleGponProfile2McastAccessListStaticGem OBJECT-TYPE
			SYNTAX Integer32 (1..25)
			MAX-ACCESS read-only
			STATUS current
			DESCRIPTION
				"Th GEM port ID"
			::= { sleGponProfile2McastAccessListStaticEntry 7 }


--  1.3.6.1.4.1.6296.101.23.51.31.1.1.8
		sleGponProfile2McastAccessListStaticCos OBJECT-TYPE
			SYNTAX Integer32 (0..7)
			MAX-ACCESS read-only
			STATUS current
			DESCRIPTION
				"The access-list CoS"
			::= { sleGponProfile2McastAccessListStaticEntry 8 }


--   1.3.6.1.4.1.6296.101.23.51.10.2
-- 1.3.6.1.4.1.6296.101.23.51.31.2
		sleGponProfile2McastAccessListStaticControl OBJECT IDENTIFIER ::= { sleGponProfile2McastAccessListStatic 2 }


--   1.3.6.1.4.1.6296.101.23.51.10.2.1
-- 1.3.6.1.4.1.6296.101.23.51.31.2.1
		sleGponProfile2McastAccessListStaticControlRequest OBJECT-TYPE
			SYNTAX INTEGER
				{
				addMcastAclStatic(1),
				delMcastAclStatic(2)
				}
			MAX-ACCESS read-write
			STATUS current
			DESCRIPTION
				"The request of a user command"
			::= { sleGponProfile2McastAccessListStaticControl 1 }


--   1.3.6.1.4.1.6296.101.23.51.10.2.2
-- 1.3.6.1.4.1.6296.101.23.51.31.2.2
		sleGponProfile2McastAccessListStaticControlStatus OBJECT-TYPE
			SYNTAX SleControlStatusType
			MAX-ACCESS read-write
			STATUS current
			DESCRIPTION
				"The status of user command"
			::= { sleGponProfile2McastAccessListStaticControl 2 }


--   1.3.6.1.4.1.6296.101.23.51.10.2.3
-- 1.3.6.1.4.1.6296.101.23.51.31.2.3
		sleGponProfile2McastAccessListStaticControlTimer OBJECT-TYPE
			SYNTAX Gauge32
			MAX-ACCESS read-write
			STATUS current
			DESCRIPTION
				"The maximum time for the manager for a long running user command"
			::= { sleGponProfile2McastAccessListStaticControl 3 }


--   1.3.6.1.4.1.6296.101.23.51.10.2.4
-- 1.3.6.1.4.1.6296.101.23.51.31.2.4
		sleGponProfile2McastAccessListStaticControlTimeStamp OBJECT-TYPE
			SYNTAX TimeTicks
			MAX-ACCESS read-write
			STATUS current
			DESCRIPTION
				"The time stamp of the last command(end of command)"
			::= { sleGponProfile2McastAccessListStaticControl 4 }


--   1.3.6.1.4.1.6296.101.23.51.10.2.5
-- 1.3.6.1.4.1.6296.101.23.51.31.2.5
		sleGponProfile2McastAccessListStaticControlReqResult OBJECT-TYPE
			SYNTAX SleControlRequestResultType
			MAX-ACCESS read-write
			STATUS current
			DESCRIPTION
				"The result of the last user command
				"
			::= { sleGponProfile2McastAccessListStaticControl 5 }


--   1.3.6.1.4.1.6296.101.23.51.10.2.6
-- 1.3.6.1.4.1.6296.101.23.51.31.2.6
		sleGponProfile2McastAccessListStaticControlIndex OBJECT-TYPE
			SYNTAX Integer32
			MAX-ACCESS read-write
			STATUS current
			DESCRIPTION
				"The Mcast access-list  static index."
			::= { sleGponProfile2McastAccessListStaticControl 6 }


--   1.3.6.1.4.1.6296.101.23.51.10.2.7
-- 1.3.6.1.4.1.6296.101.23.51.31.2.7
		sleGponProfile2McastAccessListStaticControlVid OBJECT-TYPE
			SYNTAX Integer32 (0 | 1..4094)
			MAX-ACCESS read-write
			STATUS current
			DESCRIPTION
				"This specific the VLAN carrying the multicast group DS"
			::= { sleGponProfile2McastAccessListStaticControl 7 }


--   1.3.6.1.4.1.6296.101.23.51.10.2.8
-- 1.3.6.1.4.1.6296.101.23.51.31.2.8
		sleGponProfile2McastAccessListStaticControlName OBJECT-TYPE
			SYNTAX OCTET STRING
			MAX-ACCESS read-write
			STATUS current
			DESCRIPTION
				"The Mcast profile name."
			::= { sleGponProfile2McastAccessListStaticControl 8 }


--   1.3.6.1.4.1.6296.101.23.51.10.2.9
-- 1.3.6.1.4.1.6296.101.23.51.31.2.9
		sleGponProfile2McastAccessListStaticControlDstIpStart OBJECT-TYPE
			SYNTAX IpAddress
			MAX-ACCESS read-write
			STATUS current
			DESCRIPTION
				"The destination IP range-start."
			::= { sleGponProfile2McastAccessListStaticControl 9 }


--   1.3.6.1.4.1.6296.101.23.51.10.2.10
-- 1.3.6.1.4.1.6296.101.23.51.31.2.10
		sleGponProfile2McastAccessListStaticControlDstIpEnd OBJECT-TYPE
			SYNTAX IpAddress
			MAX-ACCESS read-write
			STATUS current
			DESCRIPTION
				"The destination IP range-end"
			::= { sleGponProfile2McastAccessListStaticControl 10 }


--   1.3.6.1.4.1.6296.101.23.51.10.2.11
-- 1.3.6.1.4.1.6296.101.23.51.31.2.11
		sleGponProfile2McastAccessListStaticControlSrcIp OBJECT-TYPE
			SYNTAX IpAddress
			MAX-ACCESS read-write
			STATUS current
			DESCRIPTION
				"The source IP."
			::= { sleGponProfile2McastAccessListStaticControl 11 }


--   1.3.6.1.4.1.6296.101.23.51.10.2.12
-- 1.3.6.1.4.1.6296.101.23.51.31.2.12
		sleGponProfile2McastAccessListStaticControlBandwidth OBJECT-TYPE
			SYNTAX Integer32
			MAX-ACCESS read-write
			STATUS current
			DESCRIPTION
				"The Imputed group bandwidth"
			::= { sleGponProfile2McastAccessListStaticControl 12 }


--   1.3.6.1.4.1.6296.101.23.51.10.2.13
-- 1.3.6.1.4.1.6296.101.23.51.31.2.13
		sleGponProfile2McastAccessListStaticControlGem OBJECT-TYPE
			SYNTAX Integer32 (1..25)
			MAX-ACCESS read-write
			STATUS current
			DESCRIPTION
				"The GEM port ID"
			::= { sleGponProfile2McastAccessListStaticControl 13 }


--  1.3.6.1.4.1.6296.101.23.51.31.2.14
		sleGponProfile2McastAccessListStaticControlCos OBJECT-TYPE
			SYNTAX Integer32 (0..7)
			MAX-ACCESS read-write
			STATUS current
			DESCRIPTION
				"The access-list CoS"
			::= { sleGponProfile2McastAccessListStaticControl 14 }


--   1.3.6.1.4.1.6296.101.23.51.10.3
-- 1.3.6.1.4.1.6296.101.23.51.31.3
		sleGponProfile2McastAccessListStaticControlNotification OBJECT IDENTIFIER ::= { sleGponProfile2McastAccessListStatic 3 }


--   1.3.6.1.4.1.6296.101.23.51.10.3.1
-- 1.3.6.1.4.1.6296.101.23.51.31.3.1
		sleGponProfile2McastAccessListStaticControlAdded NOTIFICATION-TYPE
			OBJECTS { sleGponProfile2McastAccessListStaticControlRequest, sleGponProfile2McastAccessListStaticControlTimeStamp, sleGponProfile2McastAccessListStaticControlReqResult, sleGponProfile2McastAccessListStaticControlVid, sleGponProfile2McastAccessListStaticControlName,
				sleGponProfile2McastAccessListStaticControlDstIpStart, sleGponProfile2McastAccessListStaticControlDstIpEnd, sleGponProfile2McastAccessListStaticControlSrcIp, sleGponProfile2McastAccessListStaticControlBandwidth, sleGponProfile2McastAccessListStaticControlGem,
				sleGponProfile2McastAccessListStaticControlCos }
			STATUS current
			DESCRIPTION
				"addMcastAclStatic"
			::= { sleGponProfile2McastAccessListStaticControlNotification 1 }


--   1.3.6.1.4.1.6296.101.23.51.10.3.1
-- 1.3.6.1.4.1.6296.101.23.51.31.3.2
		sleGponProfile2McastAccessListStaticControlDeleted NOTIFICATION-TYPE
			OBJECTS { sleGponProfile2McastAccessListStaticControlRequest, sleGponProfile2McastAccessListStaticControlTimeStamp, sleGponProfile2McastAccessListStaticControlReqResult, sleGponProfile2McastAccessListStaticControlVid, sleGponProfile2McastAccessListStaticControlName
				 }
			STATUS current
			DESCRIPTION
				"delMcastAclStatic"
			::= { sleGponProfile2McastAccessListStaticControlNotification 2 }


--  1.3.6.1.4.1.6296.101.23.51.32
		sleGponProfile2RateLimit OBJECT IDENTIFIER ::= { sleGponProfile2 32 }


--  1.3.6.1.4.1.6296.101.23.51.32.1
		sleGponProfile2RateLimitTable OBJECT-TYPE
			SYNTAX SEQUENCE OF SleGponProfile2RateLimitEntry
			MAX-ACCESS not-accessible
			STATUS current
			DESCRIPTION
				"Description."
			::= { sleGponProfile2RateLimit 1 }


--  1.3.6.1.4.1.6296.101.23.51.32.1.1
		sleGponProfile2RateLimitEntry OBJECT-TYPE
			SYNTAX SleGponProfile2RateLimitEntry
			MAX-ACCESS not-accessible
			STATUS current
			DESCRIPTION
				"Description."
			INDEX { sleGponProfile2RateLimitIndex }
			::= { sleGponProfile2RateLimitTable 1 }


		SleGponProfile2RateLimitEntry ::=
			SEQUENCE {
				sleGponProfile2RateLimitIndex
					Integer32,
				sleGponProfile2RateLimitName
					OCTET STRING,
				sleGponProfile2RateLimitUpPir
					Integer32,
				sleGponProfile2RateLimitUpSir
					Integer32,
				sleGponProfile2RateLimitDownPir
					Integer32,
				sleGponProfile2RateLimitDownSir
					Integer32
			 }

--  1.3.6.1.4.1.6296.101.23.51.32.1.1.1
		sleGponProfile2RateLimitIndex OBJECT-TYPE
			SYNTAX Integer32 (0..65535)
			MAX-ACCESS read-only
			STATUS current
			DESCRIPTION
				"The rate limit index."
			::= { sleGponProfile2RateLimitEntry 1 }


--  1.3.6.1.4.1.6296.101.23.51.32.1.1.2
		sleGponProfile2RateLimitName OBJECT-TYPE
			SYNTAX OCTET STRING
			MAX-ACCESS read-only
			STATUS current
			DESCRIPTION
				"The rate limit name."
			::= { sleGponProfile2RateLimitEntry 2 }


--   1.3.6.1.4.1.6296.101.23.51.6.1.1.11
-- 1.3.6.1.4.1.6296.101.23.51.32.1.1.3
		sleGponProfile2RateLimitUpPir OBJECT-TYPE
			SYNTAX Integer32
			MAX-ACCESS read-only
			STATUS current
			DESCRIPTION
				"The upload rate-limit control : SIR (Bandwidth in steps of 64Kbps)"
			::= { sleGponProfile2RateLimitEntry 3 }


--   1.3.6.1.4.1.6296.101.23.51.6.1.1.10
-- 1.3.6.1.4.1.6296.101.23.51.32.1.1.4
		sleGponProfile2RateLimitUpSir OBJECT-TYPE
			SYNTAX Integer32
			MAX-ACCESS read-only
			STATUS current
			DESCRIPTION
				"The upload rate-limit control : SIR (Bandwidth in steps of 64Kbps)"
			::= { sleGponProfile2RateLimitEntry 4 }


--   1.3.6.1.4.1.6296.101.23.51.6.1.1.9
-- 1.3.6.1.4.1.6296.101.23.51.32.1.1.5
		sleGponProfile2RateLimitDownPir OBJECT-TYPE
			SYNTAX Integer32
			MAX-ACCESS read-only
			STATUS current
			DESCRIPTION
				"The download rate-limit control : PIR (Bandwidth in steps of 64Kbps)"
			::= { sleGponProfile2RateLimitEntry 5 }


--   1.3.6.1.4.1.6296.101.23.51.6.1.1.8
-- 1.3.6.1.4.1.6296.101.23.51.32.1.1.6
		sleGponProfile2RateLimitDownSir OBJECT-TYPE
			SYNTAX Integer32
			MAX-ACCESS read-only
			STATUS current
			DESCRIPTION
				"The download rate-limit control : SIR (Bandwidth in steps of 64Kbps)"
			::= { sleGponProfile2RateLimitEntry 6 }


--   1.3.6.1.4.1.6296.101.23.51.6.2
-- 1.3.6.1.4.1.6296.101.23.51.32.2
		sleGponProfile2RateLimitControl OBJECT IDENTIFIER ::= { sleGponProfile2RateLimit 2 }


--   1.3.6.1.4.1.6296.101.23.51.6.2.1
-- 1.3.6.1.4.1.6296.101.23.51.32.2.1
		sleGponProfile2RateLimitControlRequest OBJECT-TYPE
			SYNTAX INTEGER
				{
				addRateLimitProfile(1),
				delRateLimitProfile(2),
				setRateLimitProfile(3)
				}
			MAX-ACCESS read-write
			STATUS current
			DESCRIPTION
				"The request of a user command"
			::= { sleGponProfile2RateLimitControl 1 }


--   1.3.6.1.4.1.6296.101.23.51.6.2.2
-- 1.3.6.1.4.1.6296.101.23.51.32.2.2
		sleGponProfile2RateLimitControlStatus OBJECT-TYPE
			SYNTAX SleControlStatusType
			MAX-ACCESS read-write
			STATUS current
			DESCRIPTION
				"The status of user command"
			::= { sleGponProfile2RateLimitControl 2 }


--   1.3.6.1.4.1.6296.101.23.51.6.2.3
-- 1.3.6.1.4.1.6296.101.23.51.32.2.3
		sleGponProfile2RateLimitControlTimer OBJECT-TYPE
			SYNTAX Gauge32
			MAX-ACCESS read-write
			STATUS current
			DESCRIPTION
				"The maximum time for the manager for a long running user command"
			::= { sleGponProfile2RateLimitControl 3 }


--   1.3.6.1.4.1.6296.101.23.51.6.2.4
-- 1.3.6.1.4.1.6296.101.23.51.32.2.4
		sleGponProfile2RateLimitControlTimeStamp OBJECT-TYPE
			SYNTAX TimeTicks
			MAX-ACCESS read-write
			STATUS current
			DESCRIPTION
				"The time stamp of the last command(end of command)"
			::= { sleGponProfile2RateLimitControl 4 }


--   1.3.6.1.4.1.6296.101.23.51.6.2.5
-- 1.3.6.1.4.1.6296.101.23.51.32.2.5
		sleGponProfile2RateLimitControlReqResult OBJECT-TYPE
			SYNTAX SleControlRequestResultType
			MAX-ACCESS read-write
			STATUS current
			DESCRIPTION
				"The result of the last user command"
			::= { sleGponProfile2RateLimitControl 5 }


--   1.3.6.1.4.1.6296.101.23.51.6.2.6
-- 1.3.6.1.4.1.6296.101.23.51.32.2.6
		sleGponProfile2RateLimitControlName OBJECT-TYPE
			SYNTAX OCTET STRING
			MAX-ACCESS read-write
			STATUS current
			DESCRIPTION
				"The rate limit name."
			::= { sleGponProfile2RateLimitControl 6 }


--   1.3.6.1.4.1.6296.101.23.51.6.2.18
-- 1.3.6.1.4.1.6296.101.23.51.32.2.7
		sleGponProfile2RateLimitControlUpPir OBJECT-TYPE
			SYNTAX Integer32
			MAX-ACCESS read-write
			STATUS current
			DESCRIPTION
				"The upload rate-limit control : SIR (Bandwidth in steps of 64Kbps)"
			::= { sleGponProfile2RateLimitControl 7 }


--   1.3.6.1.4.1.6296.101.23.51.6.2.17
-- 1.3.6.1.4.1.6296.101.23.51.32.2.8
		sleGponProfile2RateLimitControlUpSir OBJECT-TYPE
			SYNTAX Integer32
			MAX-ACCESS read-write
			STATUS current
			DESCRIPTION
				"The upload rate-limit control : SIR (Bandwidth in steps of 64Kbps)"
			::= { sleGponProfile2RateLimitControl 8 }


--   1.3.6.1.4.1.6296.101.23.51.6.2.16
-- 1.3.6.1.4.1.6296.101.23.51.32.2.9
		sleGponProfile2RateLimitControlDownPir OBJECT-TYPE
			SYNTAX Integer32
			MAX-ACCESS read-write
			STATUS current
			DESCRIPTION
				"The download rate-limit control : PIR (Bandwidth in steps of 64Kbps)"
			::= { sleGponProfile2RateLimitControl 9 }


--   1.3.6.1.4.1.6296.101.23.51.6.2.15
-- 1.3.6.1.4.1.6296.101.23.51.32.2.10
		sleGponProfile2RateLimitControlDownSir OBJECT-TYPE
			SYNTAX Integer32
			MAX-ACCESS read-write
			STATUS current
			DESCRIPTION
				"The download rate-limit control : SIR (Bandwidth in steps of 64Kbps)"
			::= { sleGponProfile2RateLimitControl 10 }


--  1.3.6.1.4.1.6296.101.23.51.32.3
		sleGponProfile2RateLimitNotification OBJECT IDENTIFIER ::= { sleGponProfile2RateLimit 3 }


--  1.3.6.1.4.1.6296.101.23.51.32.3.1
		sleGponProfile2RateLimitProfileCreated NOTIFICATION-TYPE
			OBJECTS { sleGponProfile2RateLimitControlRequest, sleGponProfile2RateLimitControlTimeStamp, sleGponProfile2RateLimitControlReqResult, sleGponProfile2RateLimitControlName, sleGponProfile2RateLimitControlDownSir,
				sleGponProfile2RateLimitControlDownPir, sleGponProfile2RateLimitControlUpSir, sleGponProfile2RateLimitControlUpPir }
			STATUS current
			DESCRIPTION
				"addRateLimitProfile"
			::= { sleGponProfile2RateLimitNotification 1 }


--  1.3.6.1.4.1.6296.101.23.51.32.3.2
		sleGponProfile2RateLimitProfileDeleted NOTIFICATION-TYPE
			OBJECTS { sleGponProfile2RateLimitControlRequest, sleGponProfile2RateLimitControlTimeStamp, sleGponProfile2RateLimitControlReqResult, sleGponProfile2RateLimitControlName }
			STATUS current
			DESCRIPTION
				"delRateLimitProfile"
			::= { sleGponProfile2RateLimitNotification 2 }


--  1.3.6.1.4.1.6296.101.23.51.32.3.3
		sleGponProfile2RateLimitProfileChanged NOTIFICATION-TYPE
			OBJECTS { sleGponProfile2RateLimitControlRequest, sleGponProfile2RateLimitControlTimeStamp, sleGponProfile2RateLimitControlReqResult, sleGponProfile2RateLimitControlName, sleGponProfile2RateLimitControlDownSir,
				sleGponProfile2RateLimitControlDownPir, sleGponProfile2RateLimitControlUpSir, sleGponProfile2RateLimitControlUpPir }
			STATUS current
			DESCRIPTION
				"setRateLimitProfile"
			::= { sleGponProfile2RateLimitNotification 3 }


--  1.3.6.1.4.1.6296.101.23.51.32
		sleGponProfile2BridgeUniPQ OBJECT IDENTIFIER ::= { sleGponProfile2 33 }


--  1.3.6.1.4.1.6296.101.23.51.32.1
		sleGponProfile2BridgeUniPQTable OBJECT-TYPE
			SYNTAX SEQUENCE OF SleGponProfile2BridgeUniPQEntry
			MAX-ACCESS not-accessible
			STATUS current
			DESCRIPTION
				"Description."
			::= { sleGponProfile2BridgeUniPQ 1 }


--  1.3.6.1.4.1.6296.101.23.51.32.1.1
		sleGponProfile2BridgeUniPQEntry OBJECT-TYPE
			SYNTAX SleGponProfile2BridgeUniPQEntry
			MAX-ACCESS not-accessible
			STATUS current
			DESCRIPTION
				"Description."
			INDEX { sleGponProfile2TrafficIndex, sleGponProfile2BridgeId, sleGponProfile2BridgeUniType, sleGponProfile2BridgeUniId, sleGponProfile2BridgeUniPQId
				 }
			::= { sleGponProfile2BridgeUniPQTable 1 }


		SleGponProfile2BridgeUniPQEntry ::=
			SEQUENCE {
				sleGponProfile2BridgeUniPQId
					Integer32,
				sleGponProfile2BridgeUniPQGreenMinThreshold
					Integer32,
				sleGponProfile2BridgeUniPQGreenMaxThreshold
					Integer32,
				sleGponProfile2BridgeUniPQYellowMinThreshold
					Integer32,
				sleGponProfile2BridgeUniPQYellowMaxThreshold
					Integer32,
				sleGponProfile2BridgeUniPQGreenProbability
					Integer32,
				sleGponProfile2BridgeUniPQYellowProbability
					Integer32,
				sleGponProfile2BridgeUniPQAverageCoefficient
					Integer32,
				sleGponProfile2BridgeUniPQDropPrecedence
					INTEGER
			 }

		sleGponProfile2BridgeUniPQId OBJECT-TYPE
			SYNTAX Integer32 (1..8)
			MAX-ACCESS read-only
			STATUS current
			DESCRIPTION
				"The Bridge Uni Priority Queue ID"
			::= { sleGponProfile2BridgeUniPQEntry 1 }


--  1.3.6.1.4.1.6296.101.23.51.32.1.1.1
		sleGponProfile2BridgeUniPQGreenMinThreshold OBJECT-TYPE
			SYNTAX Integer32 (0..65535)
			MAX-ACCESS read-only
			STATUS current
			DESCRIPTION
				"Green Packet Minimum Threshold
				(65535: Default Value)"
			::= { sleGponProfile2BridgeUniPQEntry 2 }


--  1.3.6.1.4.1.6296.101.23.51.32.1.1.1
		sleGponProfile2BridgeUniPQGreenMaxThreshold OBJECT-TYPE
			SYNTAX Integer32 (0..65535)
			MAX-ACCESS read-only
			STATUS current
			DESCRIPTION
				"Green Packet Maximum Threshold
				(65535: Default Value)"
			::= { sleGponProfile2BridgeUniPQEntry 3 }


--  1.3.6.1.4.1.6296.101.23.51.32.1.1.1
		sleGponProfile2BridgeUniPQYellowMinThreshold OBJECT-TYPE
			SYNTAX Integer32 (0..65535)
			MAX-ACCESS read-only
			STATUS current
			DESCRIPTION
				"Yellow Packet Minimum Threshold
				(65535: Default Value)"
			::= { sleGponProfile2BridgeUniPQEntry 4 }


--  1.3.6.1.4.1.6296.101.23.51.32.1.1.1
		sleGponProfile2BridgeUniPQYellowMaxThreshold OBJECT-TYPE
			SYNTAX Integer32 (0..65535)
			MAX-ACCESS read-only
			STATUS current
			DESCRIPTION
				"Yellow Packet Maximum Threshold
				(65535: Default Value)"
			::= { sleGponProfile2BridgeUniPQEntry 5 }


--  1.3.6.1.4.1.6296.101.23.51.32.1.1.1
		sleGponProfile2BridgeUniPQGreenProbability OBJECT-TYPE
			SYNTAX Integer32 (0..255)
			MAX-ACCESS read-only
			STATUS current
			DESCRIPTION
				"Green Packet Probability
				(255: Default Value)"
			::= { sleGponProfile2BridgeUniPQEntry 6 }


--  1.3.6.1.4.1.6296.101.23.51.32.1.1.1
		sleGponProfile2BridgeUniPQYellowProbability OBJECT-TYPE
			SYNTAX Integer32 (0..255)
			MAX-ACCESS read-only
			STATUS current
			DESCRIPTION
				"Yellow Packet Probability
				(255: Default Value)"
			::= { sleGponProfile2BridgeUniPQEntry 7 }


--  1.3.6.1.4.1.6296.101.23.51.32.1.1.1
		sleGponProfile2BridgeUniPQAverageCoefficient OBJECT-TYPE
			SYNTAX Integer32 (0..255)
			MAX-ACCESS read-only
			STATUS current
			DESCRIPTION
				"Averaging Coefficient, as described in Floyd and Jacobson
				(9: Default Value)"
			::= { sleGponProfile2BridgeUniPQEntry 8 }


--  1.3.6.1.4.1.6296.101.23.51.32.1.1.1
		sleGponProfile2BridgeUniPQDropPrecedence OBJECT-TYPE
			SYNTAX INTEGER
				{
				noMarking(0),
				internalMarking(1),
				dei(2),
				pcp8p0d(3),
				pcp7p1d(4),
				pcp6p2d(5),
				pcp5p3d(6),
				dscpAfClass(7)
				}
			MAX-ACCESS read-only
			STATUS current
			DESCRIPTION
				"Drop Precedence Colour Marking"
			::= { sleGponProfile2BridgeUniPQEntry 9 }


--   1.3.6.1.4.1.6296.101.23.51.6.2
-- 1.3.6.1.4.1.6296.101.23.51.32.2
		sleGponProfile2BridgeUniPQControl OBJECT IDENTIFIER ::= { sleGponProfile2BridgeUniPQ 2 }


--   1.3.6.1.4.1.6296.101.23.51.6.2.1
-- 1.3.6.1.4.1.6296.101.23.51.32.2.1
		sleGponProfile2BridgeUniPQControlRequest OBJECT-TYPE
			SYNTAX INTEGER
				{
				setPQThreshold(1),
				setPQProbability(2),
				setPQAverageCoefficient(3),
				setPQDropPrecedence(4)
				}
			MAX-ACCESS read-write
			STATUS current
			DESCRIPTION
				"The request of a user command"
			::= { sleGponProfile2BridgeUniPQControl 1 }


--   1.3.6.1.4.1.6296.101.23.51.6.2.2
-- 1.3.6.1.4.1.6296.101.23.51.32.2.2
		sleGponProfile2BridgeUniPQControlStatus OBJECT-TYPE
			SYNTAX SleControlStatusType
			MAX-ACCESS read-write
			STATUS current
			DESCRIPTION
				"The status of user command"
			::= { sleGponProfile2BridgeUniPQControl 2 }


--   1.3.6.1.4.1.6296.101.23.51.6.2.3
-- 1.3.6.1.4.1.6296.101.23.51.32.2.3
		sleGponProfile2BridgeUniPQControlTimer OBJECT-TYPE
			SYNTAX Gauge32
			MAX-ACCESS read-write
			STATUS current
			DESCRIPTION
				"The maximum time for the manager for a long running user command"
			::= { sleGponProfile2BridgeUniPQControl 3 }


--   1.3.6.1.4.1.6296.101.23.51.6.2.4
-- 1.3.6.1.4.1.6296.101.23.51.32.2.4
		sleGponProfile2BridgeUniPQControlTimeStamp OBJECT-TYPE
			SYNTAX TimeTicks
			MAX-ACCESS read-write
			STATUS current
			DESCRIPTION
				"The time stamp of the last command(end of command)"
			::= { sleGponProfile2BridgeUniPQControl 4 }


--   1.3.6.1.4.1.6296.101.23.51.6.2.5
-- 1.3.6.1.4.1.6296.101.23.51.32.2.5
		sleGponProfile2BridgeUniPQControlReqResult OBJECT-TYPE
			SYNTAX SleControlRequestResultType
			MAX-ACCESS read-write
			STATUS current
			DESCRIPTION
				"The result of the last user command"
			::= { sleGponProfile2BridgeUniPQControl 5 }


--   1.3.6.1.4.1.6296.101.23.51.6.2.6
-- 1.3.6.1.4.1.6296.101.23.51.32.2.6
		sleGponProfile2BridgeUniPQControlTName OBJECT-TYPE
			SYNTAX OCTET STRING
			MAX-ACCESS read-write
			STATUS current
			DESCRIPTION
				"The Traffic profile name."
			::= { sleGponProfile2BridgeUniPQControl 6 }


--   1.3.6.1.4.1.6296.101.23.51.6.2.18
-- 1.3.6.1.4.1.6296.101.23.51.32.2.7
		sleGponProfile2BridgeUniPQControlBridgeId OBJECT-TYPE
			SYNTAX Integer32 (1..65535)
			MAX-ACCESS read-write
			STATUS current
			DESCRIPTION
				"The bridge ID."
			::= { sleGponProfile2BridgeUniPQControl 7 }


--   1.3.6.1.4.1.6296.101.23.51.6.2.17
-- 1.3.6.1.4.1.6296.101.23.51.32.2.8
		sleGponProfile2BridgeUniPQControlType OBJECT-TYPE
			SYNTAX INTEGER
				{
				eth(1),
				virtualEth(2)
				}
			MAX-ACCESS read-write
			STATUS current
			DESCRIPTION
				"The Bridge Uni Type."
			::= { sleGponProfile2BridgeUniPQControl 8 }


--   1.3.6.1.4.1.6296.101.23.51.6.2.16
-- 1.3.6.1.4.1.6296.101.23.51.32.2.9
		sleGponProfile2BridgeUniPQControlUniId OBJECT-TYPE
			SYNTAX Integer32 (1..65535)
			MAX-ACCESS read-write
			STATUS current
			DESCRIPTION
				"The bridge Uni ID."
			::= { sleGponProfile2BridgeUniPQControl 9 }


--   1.3.6.1.4.1.6296.101.23.51.6.2.15
-- 1.3.6.1.4.1.6296.101.23.51.32.2.10
		sleGponProfile2BridgeUniPQControlId OBJECT-TYPE
			SYNTAX Integer32 (1..8)
			MAX-ACCESS read-write
			STATUS current
			DESCRIPTION
				"The bridge Uni Priority Queue ID."
			::= { sleGponProfile2BridgeUniPQControl 10 }


--   1.3.6.1.4.1.6296.101.23.51.6.2.15
-- 1.3.6.1.4.1.6296.101.23.51.32.2.10
		sleGponProfile2BridgeUniPQControlGreenMinThreshold OBJECT-TYPE
			SYNTAX Integer32 (0..65535)
			MAX-ACCESS read-write
			STATUS current
			DESCRIPTION
				"Green Packet Minimum Threshold
				(65535: Default Value)"
			::= { sleGponProfile2BridgeUniPQControl 11 }


--   1.3.6.1.4.1.6296.101.23.51.6.2.15
-- 1.3.6.1.4.1.6296.101.23.51.32.2.10
		sleGponProfile2BridgeUniPQControlGreenMaxThreshold OBJECT-TYPE
			SYNTAX Integer32 (0..65535)
			MAX-ACCESS read-write
			STATUS current
			DESCRIPTION
				"Green Packet Maximum Threshold
				(65535: Default Value)"
			::= { sleGponProfile2BridgeUniPQControl 12 }


--   1.3.6.1.4.1.6296.101.23.51.6.2.15
-- 1.3.6.1.4.1.6296.101.23.51.32.2.10
		sleGponProfile2BridgeUniPQControlYellowMinThreshold OBJECT-TYPE
			SYNTAX Integer32 (0..65535)
			MAX-ACCESS read-write
			STATUS current
			DESCRIPTION
				"Yellow Packet Minimum Threshold
				(65535: Default Value)"
			::= { sleGponProfile2BridgeUniPQControl 13 }


--   1.3.6.1.4.1.6296.101.23.51.6.2.15
-- 1.3.6.1.4.1.6296.101.23.51.32.2.10
		sleGponProfile2BridgeUniPQControlYellowMaxThreshold OBJECT-TYPE
			SYNTAX Integer32 (0..65535)
			MAX-ACCESS read-write
			STATUS current
			DESCRIPTION
				"Yellow Packet Maximum Threshold
				(65535: Default Value)"
			::= { sleGponProfile2BridgeUniPQControl 14 }


--   1.3.6.1.4.1.6296.101.23.51.6.2.15
-- 1.3.6.1.4.1.6296.101.23.51.32.2.10
		sleGponProfile2BridgeUniPQControlGreenProbability OBJECT-TYPE
			SYNTAX Integer32 (0..255)
			MAX-ACCESS read-write
			STATUS current
			DESCRIPTION
				"Green Packet Probability
				(255: Default Value)"
			::= { sleGponProfile2BridgeUniPQControl 15 }


--   1.3.6.1.4.1.6296.101.23.51.6.2.15
-- 1.3.6.1.4.1.6296.101.23.51.32.2.10
		sleGponProfile2BridgeUniPQControlYellowProbability OBJECT-TYPE
			SYNTAX Integer32 (0..255)
			MAX-ACCESS read-write
			STATUS current
			DESCRIPTION
				"Yellow Packet Probability
				(255: Default Value)
				"
			::= { sleGponProfile2BridgeUniPQControl 16 }


--   1.3.6.1.4.1.6296.101.23.51.6.2.15
-- 1.3.6.1.4.1.6296.101.23.51.32.2.10
		sleGponProfile2BridgeUniPQControlAverageCoefficient OBJECT-TYPE
			SYNTAX Integer32 (0..255)
			MAX-ACCESS read-write
			STATUS current
			DESCRIPTION
				"Averaging Coefficient, as described in Floyd and Jacobson
				(9: Default Value)"
			::= { sleGponProfile2BridgeUniPQControl 17 }


--   1.3.6.1.4.1.6296.101.23.51.6.2.15
-- 1.3.6.1.4.1.6296.101.23.51.32.2.10
		sleGponProfile2BridgeUniPQControlDropPrecedence OBJECT-TYPE
			SYNTAX INTEGER
				{
				noMarking(0),
				internalMarking(1),
				dei(2),
				pcp8p0d(3),
				pcp7p1d(4),
				pcp6p2d(5),
				pcp5p3d(6),
				dscpAfClass(7)
				}
			MAX-ACCESS read-write
			STATUS current
			DESCRIPTION
				"Drop Precedence Colour Marking"
			::= { sleGponProfile2BridgeUniPQControl 18 }


--  1.3.6.1.4.1.6296.101.23.51.32.3
		sleGponProfile2BridgeUniPQNotification OBJECT IDENTIFIER ::= { sleGponProfile2BridgeUniPQ 3 }


		sleGponProfile2BridgeUniPQThresholdChanged NOTIFICATION-TYPE
			OBJECTS { sleGponProfile2BridgeUniPQControlRequest, sleGponProfile2BridgeUniPQControlTimeStamp, sleGponProfile2BridgeUniPQControlReqResult, sleGponProfile2BridgeUniPQControlTName, sleGponProfile2BridgeUniPQControlBridgeId,
				sleGponProfile2BridgeUniPQControlType, sleGponProfile2BridgeUniPQControlUniId, sleGponProfile2BridgeUniPQControlId, sleGponProfile2BridgeUniPQControlGreenMinThreshold, sleGponProfile2BridgeUniPQControlGreenMaxThreshold,
				sleGponProfile2BridgeUniPQControlYellowMinThreshold, sleGponProfile2BridgeUniPQControlYellowMaxThreshold }
			STATUS current
			DESCRIPTION
				"setPQThreshold"
			::= { sleGponProfile2BridgeUniPQNotification 1 }


		sleGponProfile2BridgeUniPQProbabilityChanged NOTIFICATION-TYPE
			OBJECTS { sleGponProfile2BridgeUniPQControlRequest, sleGponProfile2BridgeUniPQControlTimeStamp, sleGponProfile2BridgeUniPQControlReqResult, sleGponProfile2BridgeUniPQControlTName, sleGponProfile2BridgeUniPQControlBridgeId,
				sleGponProfile2BridgeUniPQControlType, sleGponProfile2BridgeUniPQControlUniId, sleGponProfile2BridgeUniPQControlId, sleGponProfile2BridgeUniPQControlGreenProbability, sleGponProfile2BridgeUniPQControlYellowProbability
				 }
			STATUS current
			DESCRIPTION
				"setPQProbability"
			::= { sleGponProfile2BridgeUniPQNotification 2 }


		sleGponProfile2BridgeUniPQAverageCoefficientChanged NOTIFICATION-TYPE
			OBJECTS { sleGponProfile2BridgeUniPQControlRequest, sleGponProfile2BridgeUniPQControlTimeStamp, sleGponProfile2BridgeUniPQControlReqResult, sleGponProfile2BridgeUniPQControlTName, sleGponProfile2BridgeUniPQControlBridgeId,
				sleGponProfile2BridgeUniPQControlType, sleGponProfile2BridgeUniPQControlUniId, sleGponProfile2BridgeUniPQControlId, sleGponProfile2BridgeUniPQControlAverageCoefficient }
			STATUS current
			DESCRIPTION
				"setPQAverageCoefficient"
			::= { sleGponProfile2BridgeUniPQNotification 3 }


		sleGponProfile2BridgeUniPQDropPrecedenceChanged NOTIFICATION-TYPE
			OBJECTS { sleGponProfile2BridgeUniPQControlRequest, sleGponProfile2BridgeUniPQControlTimeStamp, sleGponProfile2BridgeUniPQControlReqResult, sleGponProfile2BridgeUniPQControlTName, sleGponProfile2BridgeUniPQControlBridgeId,
				sleGponProfile2BridgeUniPQControlType, sleGponProfile2BridgeUniPQControlUniId, sleGponProfile2BridgeUniPQControlId, sleGponProfile2BridgeUniPQControlDropPrecedence }
			STATUS current
			DESCRIPTION
				"setPQDropPrecedence"
			::= { sleGponProfile2BridgeUniPQNotification 4 }


--  1.3.6.1.4.1.6296.101.23.51.32
		sleGponProfile2TcontPQ OBJECT IDENTIFIER ::= { sleGponProfile2 34 }


--  1.3.6.1.4.1.6296.101.23.51.32.1
		sleGponProfile2TcontPQTable OBJECT-TYPE
			SYNTAX SEQUENCE OF SleGponProfile2TcontPQEntry
			MAX-ACCESS not-accessible
			STATUS current
			DESCRIPTION
				"Description."
			::= { sleGponProfile2TcontPQ 1 }


--  1.3.6.1.4.1.6296.101.23.51.32.1.1
		sleGponProfile2TcontPQEntry OBJECT-TYPE
			SYNTAX SleGponProfile2TcontPQEntry
			MAX-ACCESS not-accessible
			STATUS current
			DESCRIPTION
				"Description."
			INDEX { sleGponProfile2TrafficIndex, sleGponProfile2TcontId, sleGponProfile2TcontPQId }
			::= { sleGponProfile2TcontPQTable 1 }


		SleGponProfile2TcontPQEntry ::=
			SEQUENCE {
				sleGponProfile2TcontPQId
					Integer32,
				sleGponProfile2TcontPQGreenMinThreshold
					Integer32,
				sleGponProfile2TcontPQGreenMaxThreshold
					Integer32,
				sleGponProfile2TcontPQYellowMinThreshold
					Integer32,
				sleGponProfile2TcontPQYellowMaxThreshold
					Integer32,
				sleGponProfile2TcontPQGreenProbability
					Integer32,
				sleGponProfile2TcontPQYellowProbability
					Integer32,
				sleGponProfile2TcontPQAverageCoefficient
					Integer32,
				sleGponProfile2TcontPQDropPrecedence
					INTEGER
			 }

		sleGponProfile2TcontPQId OBJECT-TYPE
			SYNTAX Integer32 (1..8)
			MAX-ACCESS read-only
			STATUS current
			DESCRIPTION
				"The Tcont Priority Queue ID"
			::= { sleGponProfile2TcontPQEntry 1 }


--  1.3.6.1.4.1.6296.101.23.51.32.1.1.1
		sleGponProfile2TcontPQGreenMinThreshold OBJECT-TYPE
			SYNTAX Integer32 (0..65535)
			MAX-ACCESS read-only
			STATUS current
			DESCRIPTION
				"Green Packet Minimum Threshold
				(65535: Default Value)
				"
			::= { sleGponProfile2TcontPQEntry 2 }


--  1.3.6.1.4.1.6296.101.23.51.32.1.1.1
		sleGponProfile2TcontPQGreenMaxThreshold OBJECT-TYPE
			SYNTAX Integer32 (0..65535)
			MAX-ACCESS read-only
			STATUS current
			DESCRIPTION
				"Green Packet Maximum Threshold
				(65535: Default Value)"
			::= { sleGponProfile2TcontPQEntry 3 }


--  1.3.6.1.4.1.6296.101.23.51.32.1.1.1
		sleGponProfile2TcontPQYellowMinThreshold OBJECT-TYPE
			SYNTAX Integer32 (0..65535)
			MAX-ACCESS read-only
			STATUS current
			DESCRIPTION
				"Yellow Packet Minimum Threshold
				(65535: Default Value)"
			::= { sleGponProfile2TcontPQEntry 4 }


--  1.3.6.1.4.1.6296.101.23.51.32.1.1.1
		sleGponProfile2TcontPQYellowMaxThreshold OBJECT-TYPE
			SYNTAX Integer32 (0..65535)
			MAX-ACCESS read-only
			STATUS current
			DESCRIPTION
				"Yellow Packet Maximum Threshold
				(65535: Default Value)"
			::= { sleGponProfile2TcontPQEntry 5 }


--  1.3.6.1.4.1.6296.101.23.51.32.1.1.1
		sleGponProfile2TcontPQGreenProbability OBJECT-TYPE
			SYNTAX Integer32 (0..255)
			MAX-ACCESS read-only
			STATUS current
			DESCRIPTION
				"Green Packet Probability
				(255: Default Value)"
			::= { sleGponProfile2TcontPQEntry 6 }


--  1.3.6.1.4.1.6296.101.23.51.32.1.1.1
		sleGponProfile2TcontPQYellowProbability OBJECT-TYPE
			SYNTAX Integer32 (0..255)
			MAX-ACCESS read-only
			STATUS current
			DESCRIPTION
				"Yellow Packet Probability
				(255: Default Value)"
			::= { sleGponProfile2TcontPQEntry 7 }


--  1.3.6.1.4.1.6296.101.23.51.32.1.1.1
		sleGponProfile2TcontPQAverageCoefficient OBJECT-TYPE
			SYNTAX Integer32 (0..255)
			MAX-ACCESS read-only
			STATUS current
			DESCRIPTION
				"Averaging Coefficient, as described in Floyd and Jacobson
				(9: Default Value)
				"
			::= { sleGponProfile2TcontPQEntry 8 }


--  1.3.6.1.4.1.6296.101.23.51.32.1.1.1
		sleGponProfile2TcontPQDropPrecedence OBJECT-TYPE
			SYNTAX INTEGER
				{
				noMarking(0),
				internalMarking(1),
				dei(2),
				pcp8p0d(3),
				pcp7p1d(4),
				pcp6p2d(5),
				pcp5p3d(6),
				dscpAfClass(7)
				}
			MAX-ACCESS read-only
			STATUS current
			DESCRIPTION
				"Drop Precedence Colour Marking"
			::= { sleGponProfile2TcontPQEntry 9 }


--   1.3.6.1.4.1.6296.101.23.51.6.2
-- 1.3.6.1.4.1.6296.101.23.51.32.2
		sleGponProfile2TcontPQControl OBJECT IDENTIFIER ::= { sleGponProfile2TcontPQ 2 }


--   1.3.6.1.4.1.6296.101.23.51.6.2.1
-- 1.3.6.1.4.1.6296.101.23.51.32.2.1
		sleGponProfile2TcontPQControlRequest OBJECT-TYPE
			SYNTAX INTEGER
				{
				setPQThreshold(1),
				setPQProbability(2),
				setPQAverageCoefficient(3),
				setPQDropPrecedence(4)
				}
			MAX-ACCESS read-write
			STATUS current
			DESCRIPTION
				"The request of a user command"
			::= { sleGponProfile2TcontPQControl 1 }


--   1.3.6.1.4.1.6296.101.23.51.6.2.2
-- 1.3.6.1.4.1.6296.101.23.51.32.2.2
		sleGponProfile2TcontPQControlStatus OBJECT-TYPE
			SYNTAX SleControlStatusType
			MAX-ACCESS read-write
			STATUS current
			DESCRIPTION
				"The status of user command"
			::= { sleGponProfile2TcontPQControl 2 }


--   1.3.6.1.4.1.6296.101.23.51.6.2.3
-- 1.3.6.1.4.1.6296.101.23.51.32.2.3
		sleGponProfile2TcontPQControlTimer OBJECT-TYPE
			SYNTAX Gauge32
			MAX-ACCESS read-write
			STATUS current
			DESCRIPTION
				"The maximum time for the manager for a long running user command"
			::= { sleGponProfile2TcontPQControl 3 }


--   1.3.6.1.4.1.6296.101.23.51.6.2.4
-- 1.3.6.1.4.1.6296.101.23.51.32.2.4
		sleGponProfile2TcontPQControlTimeStamp OBJECT-TYPE
			SYNTAX TimeTicks
			MAX-ACCESS read-write
			STATUS current
			DESCRIPTION
				"The time stamp of the last command(end of command)"
			::= { sleGponProfile2TcontPQControl 4 }


--   1.3.6.1.4.1.6296.101.23.51.6.2.5
-- 1.3.6.1.4.1.6296.101.23.51.32.2.5
		sleGponProfile2TcontPQControlReqResult OBJECT-TYPE
			SYNTAX SleControlRequestResultType
			MAX-ACCESS read-write
			STATUS current
			DESCRIPTION
				"The result of the last user command"
			::= { sleGponProfile2TcontPQControl 5 }


--   1.3.6.1.4.1.6296.101.23.51.6.2.6
-- 1.3.6.1.4.1.6296.101.23.51.32.2.6
		sleGponProfile2TcontPQControlTName OBJECT-TYPE
			SYNTAX OCTET STRING
			MAX-ACCESS read-write
			STATUS current
			DESCRIPTION
				"The Traffic profile name."
			::= { sleGponProfile2TcontPQControl 6 }


--   1.3.6.1.4.1.6296.101.23.51.6.2.18
-- 1.3.6.1.4.1.6296.101.23.51.32.2.7
		sleGponProfile2TcontPQTcontId OBJECT-TYPE
			SYNTAX Integer32 (1..65535)
			MAX-ACCESS read-write
			STATUS current
			DESCRIPTION
				"The T-cont ID"
			::= { sleGponProfile2TcontPQControl 7 }


--   1.3.6.1.4.1.6296.101.23.51.6.2.15
-- 1.3.6.1.4.1.6296.101.23.51.32.2.10
		sleGponProfile2TcontPQControlId OBJECT-TYPE
			SYNTAX Integer32 (1..8)
			MAX-ACCESS read-write
			STATUS current
			DESCRIPTION
				"The bridge Uni Priority Queue ID."
			::= { sleGponProfile2TcontPQControl 8 }


--   1.3.6.1.4.1.6296.101.23.51.6.2.15
-- 1.3.6.1.4.1.6296.101.23.51.32.2.10
		sleGponProfile2TcontPQControlGreenMinThreshold OBJECT-TYPE
			SYNTAX Integer32 (0..65535)
			MAX-ACCESS read-write
			STATUS current
			DESCRIPTION
				"Green Packet Minimum Threshold
				(65535: Default Value)"
			::= { sleGponProfile2TcontPQControl 9 }


--   1.3.6.1.4.1.6296.101.23.51.6.2.15
-- 1.3.6.1.4.1.6296.101.23.51.32.2.10
		sleGponProfile2TcontPQControlGreenMaxThreshold OBJECT-TYPE
			SYNTAX Integer32 (0..65535)
			MAX-ACCESS read-write
			STATUS current
			DESCRIPTION
				"Green Packet Maximum Threshold
				(65535: Default Value)"
			::= { sleGponProfile2TcontPQControl 10 }


--   1.3.6.1.4.1.6296.101.23.51.6.2.15
-- 1.3.6.1.4.1.6296.101.23.51.32.2.10
		sleGponProfile2TcontPQControlYellowMinThreshold OBJECT-TYPE
			SYNTAX Integer32 (0..65535)
			MAX-ACCESS read-write
			STATUS current
			DESCRIPTION
				"Yellow Packet Minimum Threshold
				(65535: Default Value)"
			::= { sleGponProfile2TcontPQControl 11 }


--   1.3.6.1.4.1.6296.101.23.51.6.2.15
-- 1.3.6.1.4.1.6296.101.23.51.32.2.10
		sleGponProfile2TcontPQControlYellowMaxThreshold OBJECT-TYPE
			SYNTAX Integer32 (0..65535)
			MAX-ACCESS read-write
			STATUS current
			DESCRIPTION
				"Yellow Packet Maximum Threshold
				(65535: Default Value)"
			::= { sleGponProfile2TcontPQControl 12 }


--   1.3.6.1.4.1.6296.101.23.51.6.2.15
-- 1.3.6.1.4.1.6296.101.23.51.32.2.10
		sleGponProfile2TcontPQControlGreenProbability OBJECT-TYPE
			SYNTAX Integer32 (0..255)
			MAX-ACCESS read-write
			STATUS current
			DESCRIPTION
				"Green Packet Probability
				(255: Default Value)
				"
			::= { sleGponProfile2TcontPQControl 13 }


--   1.3.6.1.4.1.6296.101.23.51.6.2.15
-- 1.3.6.1.4.1.6296.101.23.51.32.2.10
		sleGponProfile2TcontPQControlYellowProbability OBJECT-TYPE
			SYNTAX Integer32 (0..255)
			MAX-ACCESS read-write
			STATUS current
			DESCRIPTION
				"Yellow Packet Probability
				(255: Default Value)"
			::= { sleGponProfile2TcontPQControl 14 }


--   1.3.6.1.4.1.6296.101.23.51.6.2.15
-- 1.3.6.1.4.1.6296.101.23.51.32.2.10
		sleGponProfile2TcontPQControlAverageCoefficient OBJECT-TYPE
			SYNTAX Integer32 (0..255)
			MAX-ACCESS read-write
			STATUS current
			DESCRIPTION
				"Averaging Coefficient, as described in Floyd and Jacobson
				(9: Default Value)
				"
			::= { sleGponProfile2TcontPQControl 15 }


--   1.3.6.1.4.1.6296.101.23.51.6.2.15
-- 1.3.6.1.4.1.6296.101.23.51.32.2.10
		sleGponProfile2TcontPQControlDropPrecedence OBJECT-TYPE
			SYNTAX INTEGER
				{
				noMarking(0),
				internalMarking(1),
				dei(2),
				pcp8p0d(3),
				pcp7p1d(4),
				pcp6p2d(5),
				pcp5p3d(6),
				dscpAfClass(7)
				}
			MAX-ACCESS read-write
			STATUS current
			DESCRIPTION
				"Drop Precedence Colour Marking"
			::= { sleGponProfile2TcontPQControl 16 }


--  1.3.6.1.4.1.6296.101.23.51.32.3
		copyOfsleGponProfile2BridgeUniPQNotification OBJECT IDENTIFIER ::= { sleGponProfile2TcontPQ 3 }


		sleGponProfile2TcontPQThresholdChanged NOTIFICATION-TYPE
			OBJECTS { sleGponProfile2TcontPQControlRequest, sleGponProfile2TcontPQControlTimeStamp, sleGponProfile2TcontPQControlReqResult, sleGponProfile2TcontPQControlTName, sleGponProfile2TcontPQTcontId,
				sleGponProfile2TcontPQControlId, sleGponProfile2TcontPQControlGreenMinThreshold, sleGponProfile2TcontPQControlGreenMaxThreshold, sleGponProfile2TcontPQControlYellowMinThreshold, sleGponProfile2TcontPQControlYellowMaxThreshold
				 }
			STATUS current
			DESCRIPTION
				"setPQThreshold"
			::= { copyOfsleGponProfile2BridgeUniPQNotification 1 }


		sleGponProfile2TcontPQProbabilityChanged NOTIFICATION-TYPE
			OBJECTS { sleGponProfile2TcontPQControlRequest, sleGponProfile2TcontPQControlTimeStamp, sleGponProfile2TcontPQControlReqResult, sleGponProfile2TcontPQControlTName, sleGponProfile2TcontPQTcontId,
				sleGponProfile2TcontPQControlId, sleGponProfile2TcontPQControlGreenProbability, sleGponProfile2TcontPQControlYellowProbability }
			STATUS current
			DESCRIPTION
				"setPQProbability"
			::= { copyOfsleGponProfile2BridgeUniPQNotification 2 }


		sleGponProfile2TcontPQAverageCoefficientChanged NOTIFICATION-TYPE
			OBJECTS { sleGponProfile2TcontPQControlRequest, sleGponProfile2TcontPQControlTimeStamp, sleGponProfile2TcontPQControlReqResult, sleGponProfile2TcontPQControlTName, sleGponProfile2TcontPQTcontId,
				sleGponProfile2TcontPQControlId, sleGponProfile2TcontPQControlAverageCoefficient }
			STATUS current
			DESCRIPTION
				"setPQAverageCoefficient"
			::= { copyOfsleGponProfile2BridgeUniPQNotification 3 }


		sleGponProfile2TcontPQDropPrecedenceChanged NOTIFICATION-TYPE
			OBJECTS { sleGponProfile2TcontPQControlRequest, sleGponProfile2TcontPQControlTimeStamp, sleGponProfile2TcontPQControlReqResult, sleGponProfile2TcontPQControlTName, sleGponProfile2TcontPQTcontId,
				sleGponProfile2TcontPQControlId, sleGponProfile2TcontPQControlDropPrecedence }
			STATUS current
			DESCRIPTION
				"setPQDropPrecedence"
			::= { copyOfsleGponProfile2BridgeUniPQNotification 4 }


--  1.3.6.1.4.1.6296.101.23.51.100
		sleGponProfile2Base OBJECT IDENTIFIER ::= { sleGponProfile2 100 }


--  1.3.6.1.4.1.6296.101.23.51.100.1
		sleGponProfile2BaseInfo OBJECT IDENTIFIER ::= { sleGponProfile2Base 1 }


--  1.3.6.1.4.1.6296.101.23.51.100.1.1
		sleGponProfile2BaseOnuProfileCount OBJECT-TYPE
			SYNTAX Integer32
			MAX-ACCESS read-only
			STATUS current
			DESCRIPTION
				"The GPON profile count"
			::= { sleGponProfile2BaseInfo 1 }


--  1.3.6.1.4.1.6296.101.23.51.100.1.2
		sleGponProfile2BaseDbaProfileCount OBJECT-TYPE
			SYNTAX Integer32
			MAX-ACCESS read-only
			STATUS current
			DESCRIPTION
				"The DBA profile count"
			::= { sleGponProfile2BaseInfo 2 }


--  1.3.6.1.4.1.6296.101.23.51.100.1.3
		sleGponProfile2BaseMcastProfileCount OBJECT-TYPE
			SYNTAX Integer32
			MAX-ACCESS read-only
			STATUS current
			DESCRIPTION
				"The Multicast operation profile count"
			::= { sleGponProfile2BaseInfo 3 }


--  1.3.6.1.4.1.6296.101.23.51.100.1.4
		sleGponProfile2BaseMcastAclProfileCount OBJECT-TYPE
			SYNTAX Integer32
			MAX-ACCESS read-only
			STATUS current
			DESCRIPTION
				"The multicast access list profile count"
			::= { sleGponProfile2BaseInfo 4 }


--  1.3.6.1.4.1.6296.101.23.51.100.1.5
		sleGponProfile2BaseExtVlanProfileCount OBJECT-TYPE
			SYNTAX Integer32
			MAX-ACCESS read-only
			STATUS current
			DESCRIPTION
				"The extended vlan tagging operation profile count"
			::= { sleGponProfile2BaseInfo 5 }


--  1.3.6.1.4.1.6296.101.23.51.100.1.6
		sleGponProfile2BaseVoipProfileCount OBJECT-TYPE
			SYNTAX Integer32
			MAX-ACCESS read-only
			STATUS current
			DESCRIPTION
				"The voip profile count"
			::= { sleGponProfile2BaseInfo 6 }


--  1.3.6.1.4.1.6296.101.23.51.100.1.7
		sleGponProfile2BasePmProfileCount OBJECT-TYPE
			SYNTAX Integer32
			MAX-ACCESS read-only
			STATUS current
			DESCRIPTION
				"The Performance Monitoring profile count"
			::= { sleGponProfile2BaseInfo 7 }


--  1.3.6.1.4.1.6296.101.23.51.100.1.8
		sleGponProfile2BaseTrafficProfileCount OBJECT-TYPE
			SYNTAX Integer32
			MAX-ACCESS read-only
			STATUS current
			DESCRIPTION
				"The traffic profile count"
			::= { sleGponProfile2BaseInfo 8 }


--  1.3.6.1.4.1.6296.101.23.51.100.1.9
		sleGponProfile2BaseTdmPwProfileCount OBJECT-TYPE
			SYNTAX Integer32
			MAX-ACCESS read-only
			STATUS current
			DESCRIPTION
				"The TDM PW profile count"
			::= { sleGponProfile2BaseInfo 9 }


--  1.3.6.1.4.1.6296.101.23.51.100.1.10
		sleGponProfile2BasePwMetrmsProfileCount OBJECT-TYPE
			SYNTAX Integer32
			MAX-ACCESS read-only
			STATUS current
			DESCRIPTION
				"The PW maintenance profile count"
			::= { sleGponProfile2BaseInfo 10 }


--  1.3.6.1.4.1.6296.101.23.51.100.1.11
		sleGponProfile2BaseRateLimitProfileCount OBJECT-TYPE
			SYNTAX Integer32
			MAX-ACCESS read-only
			STATUS current
			DESCRIPTION
				"The rate limit profile count"
			::= { sleGponProfile2BaseInfo 11 }


--  1.3.6.1.4.1.6296.101.23.51.100.2
		sleGponProfile2BaseControl OBJECT IDENTIFIER ::= { sleGponProfile2Base 2 }


--  1.3.6.1.4.1.6296.101.23.51.100.3
		sleGponProfile2BaseNotification OBJECT IDENTIFIER ::= { sleGponProfile2Base 3 }


--  1.3.6.1.4.1.6296.101.23.53
		sleGponGroup OBJECT-GROUP
			OBJECTS { sleGponProfile2DbaName, sleGponProfile2DbaMode, sleGponProfile2DbaSlaAssured, sleGponProfile2DbaSlaFixed, sleGponProfile2DbaSlaMax,
				sleGponProfile2DbaSlaMaxFlags, sleGponProfile2DbaControlRequest, sleGponProfile2DbaControlStatus, sleGponProfile2DbaControlTimer, sleGponProfile2DbaControlTimeStamp,
				sleGponProfile2DbaControlReqResult, sleGponProfile2DbaControlName, sleGponProfile2DbaControlMode, sleGponProfile2DbaControlSlaAssured, sleGponProfile2DbaControlSlaFixed,
				sleGponProfile2DbaControlSlaMax, sleGponProfile2DbaControlSlaMaxFlags, sleGponProfile2TrafficName, sleGponProfile2TrafficControlRequest, sleGponProfile2TrafficControlStatus,
				sleGponProfile2TrafficControlTimer, sleGponProfile2TrafficControlTimeStamp, sleGponProfile2TrafficControlReqResult, sleGponProfile2TrafficControlName, sleGponProfile2MapperId,
				sleGponProfile2MapperGemportCount, sleGponProfile2MapperDefaultCoS, sleGponProfile2MapperDscp2Pbit, sleGponProfile2MapperCos0, sleGponProfile2MapperCos1,
				sleGponProfile2MapperCos2, sleGponProfile2MapperCos3, sleGponProfile2MapperCos4, sleGponProfile2MapperCos5, sleGponProfile2MapperCos6,
				sleGponProfile2MapperCos7, sleGponProfile2MapperControlRequest, sleGponProfile2MapperControlStatus, sleGponProfile2MapperControlTimer, sleGponProfile2MapperControlTimeStamp,
				sleGponProfile2MapperControlReqResult, sleGponProfile2MapperControlTName, sleGponProfile2MapperControlId, sleGponProfile2MapperControlGemportCount, sleGponProfile2MapperControlDefaultCoS,
				sleGponProfile2MapperControlDscp2Pbit, sleGponProfile2MapperControlCosIndex, sleGponProfile2MapperControlCosGemport, sleGponProfile2BridgeId, sleGponProfile2BridgeMacLearning,
				sleGponProfile2BridgeMaxHost, sleGponProfile2BridgeMcastFlag, sleGponProfile2BridgeControlRequest, sleGponProfile2BridgeControlStatus, sleGponProfile2BridgeControlTimer,
				sleGponProfile2BridgeControlTimeStamp, sleGponProfile2BridgeControlReqResult, sleGponProfile2BridgeControlTName, sleGponProfile2BridgeControlId, sleGponProfile2BridgeControlMacLearning,
				sleGponProfile2BridgeAniId, sleGponProfile2BridgeAniVlanFilterMode, sleGponProfile2BridgeAniVlanFilter, sleGponProfile2BridgeAniControlRequest, sleGponProfile2BridgeAniControlStatus,
				sleGponProfile2BridgeAniControlTimer, sleGponProfile2BridgeAniControlTimeStamp, sleGponProfile2BridgeAniControlReqResult, sleGponProfile2BridgeAniControlTName, sleGponProfile2BridgeAniControlBridgeId,
				sleGponProfile2BridgeAniControlId, sleGponProfile2BridgeAniControlVlanFilterMode, sleGponProfile2BridgeAniControlVlanFilter, sleGponProfile2BridgeUniType, sleGponProfile2BridgeUniId,
				sleGponProfile2BridgeUniVlanOpDsOperFlag, sleGponProfile2BridgeUniVlanOpUsOperFlag, sleGponProfile2BridgeUniVlanOpUsOperVid, sleGponProfile2BridgeUniVlanOpUsOperCos, sleGponProfile2BridgeUniPortAdmin,
				sleGponProfile2BridgeUniRateLimitDownSir, sleGponProfile2BridgeUniRateLimitDownPir, sleGponProfile2BridgeUniRateLimitUpSir, sleGponProfile2BridgeUniRateLimitUpPir, sleGponProfile2BridgeUniIgmpMaxGroup,
				sleGponProfile2BridgeUniMaxFrame, sleGponProfile2BridgeUniMcastProfile, sleGponProfile2BridgeUniVlanFilterMode, sleGponProfile2BridgeUniVlanFilter, sleGponProfile2BridgeUniControlRequest,
				sleGponProfile2BridgeUniControlStatus, sleGponProfile2BridgeUniControlTimer, sleGponProfile2BridgeUniControlTimeStamp, sleGponProfile2BridgeUniControlReqResult, sleGponProfile2BridgeUniControlTName,
				sleGponProfile2BridgeUniControlBridgeId, sleGponProfile2BridgeUniControlType, sleGponProfile2BridgeUniControlId, sleGponProfile2BridgeUniControlVlanOpDsOperFlag, sleGponProfile2BridgeUniControlVlanOpUsOperFlag,
				sleGponProfile2BridgeUniControlVlanOpUsOperVid, sleGponProfile2BridgeUniControlVlanOpUsOperCos, sleGponProfile2BridgeUniControlPortAdmin, sleGponProfile2BridgeUniControlRateLimitDownSir, sleGponProfile2BridgeUniControlRateLimitDownPir,
				sleGponProfile2BridgeUniControlRateLimitUpSir, sleGponProfile2BridgeUniControlRateLimitUpPir, sleGponProfile2BridgeUniControlIgmpMaxGroup, sleGponProfile2BridgeUniControlMaxFrame, sleGponProfile2BridgeUniControlMcastProfile,
				sleGponProfile2BridgeUniControlVlanFilterMode, sleGponProfile2BridgeUniControlVlanFilter, sleGponProfile2TcontId, sleGponProfile2TcontDbaProfile, sleGponProfile2TcontGemportId,
				sleGponProfile2TcontGemportQueue, sleGponProfile2TcontGemportControlRequest, sleGponProfile2TcontGemportControlStatus, sleGponProfile2TcontGemportControlTimer, sleGponProfile2TcontGemportControlTimeStamp,
				sleGponProfile2TcontGemportControlReqResult, sleGponProfile2TcontGemportControlTName, sleGponProfile2TcontGemportControlTcontId, sleGponProfile2TcontGemportControlId, sleGponProfile2TcontGemportControlQueue,
				sleGponProfile2McastName, sleGponProfile2McastIgmpFunc, sleGponProfile2McastIgmpImmLeave, sleGponProfile2McastIgmpRobust, sleGponProfile2McastIgmpQuerierAddress,
				sleGponProfile2McastIgmpQuerierMaxRespTime, sleGponProfile2McastIgmpQuerierInterval, sleGponProfile2McastIgmpVersion, sleGponProfile2McastIgmpUpRateLimit, sleGponProfile2McastIgmpTagCtrl,
				sleGponProfile2McastIgmpTagCtrlVid, sleGponProfile2McastIgmpTagCtrlCos, sleGponProfile2McastControlRequest, sleGponProfile2McastControlStatus, sleGponProfile2McastControlTimer,
				sleGponProfile2McastControlTimeStamp, sleGponProfile2McastControlReqResult, sleGponProfile2McastControlName, sleGponProfile2McastControlIgmpFunc, sleGponProfile2McastControlIgmpImmLeave,
				sleGponProfile2McastControlIgmpRobust, sleGponProfile2McastControlIgmpQuerierAddress, sleGponProfile2McastControlIgmpQuerierMaxRespTime, sleGponProfile2McastControlIgmpQuerierInterval, sleGponProfile2McastControlIgmpVersion,
				sleGponProfile2McastControlIgmpUpRateLimit, sleGponProfile2McastControlIgmpTagCtrl, sleGponProfile2McastControlIgmpTagCtrlVid, sleGponProfile2McastControlIgmpTagCtrlCos, sleGponProfile2McastAclVid,
				sleGponProfile2McastAclDstIpStart, sleGponProfile2McastAclDstIpEnd, sleGponProfile2McastAclSrcIp, sleGponProfile2McastAclBandwidth, sleGponProfile2McastAclGem,
				sleGponProfile2McastAclControlRequest, sleGponProfile2McastAclControlStatus, sleGponProfile2McastAclControlTimer, sleGponProfile2McastAclControlTimeStamp, sleGponProfile2McastAclControlReqResult,
				sleGponProfile2McastAclControlVid, sleGponProfile2McastAclControlDstIpStart, sleGponProfile2McastAclControlDstIpEnd, sleGponProfile2McastAclControlSrcIp, sleGponProfile2McastAclControlBandwidth,
				sleGponProfile2McastAclControlGem, sleGponProfile2McastSAclVid, sleGponProfile2McastSAclDstIpStart, sleGponProfile2McastSAclDstIpEnd, sleGponProfile2McastSAclSrcIp,
				sleGponProfile2McastSAclBandwidth, sleGponProfile2McastSAclGem, sleGponProfile2McastSAclControlRequest, sleGponProfile2McastSAclControlStatus, sleGponProfile2McastSAclControlTimer,
				sleGponProfile2McastSAclControlTimeStamp, sleGponProfile2McastSAclControlReqResult, sleGponProfile2McastSAclControlVid, sleGponProfile2McastSAclControlDstIpStart, sleGponProfile2McastSAclControlDstIpEnd,
				sleGponProfile2McastSAclControlSrcIp, sleGponProfile2McastSAclControlBandwidth, sleGponProfile2McastSAclControlGem, sleGponCableDownStatus, sleGponCableDownRefCount,
				sleGponBaseControlRequest, sleGponBaseControlStatus, sleGponBaseControlTimer, sleGponBaseControlTimeStamp, sleGponBaseControlReqResult,
				sleGponBaseControlCableDownStatus, sleGponBaseControlCableDwonRefCnt, sleGponOltId, sleGponOltStatus, sleGponOltDiscoverySerialStart,
				sleGponOltLinkMaxDistance, sleGponOltKeyExchange, sleGponOltSignalCheck, sleGponOltSignalCheckAutoOnuBlock, sleGponOltDescription,
				sleGponOltAutoToManual, sleGponOltDefaultTcontDBAMode, sleGponOltDefaultTcontFixedBw, sleGponOltDefaultTcontAssuredBw, sleGponOltDefaultTcontMaxBw,
				sleGponOltDefaultProfileName, sleGponOltControlRequest, sleGponOltControlStatus, sleGponOltControlTimer, sleGponOltControlTimeStamp,
				sleGponOltControlReqResult, sleGponOltControllndex, sleGponOltControlDiscoverySerialStart, sleGponOltControlLinkMaxDistance, sleGponOltControlKeyExchange,
				sleGponOltControlSignalCheck, sleGponOltControlSignalCheckAutoOnuBlock, sleGponOltControlDescription, sleGponOltControlAutoToManual, sleGponOltControlDefaultTcontDBAMode,
				sleGponOltControlDefaultTcontFixedBw, sleGponOltControlDefaultTcontAssuredBw, sleGponOltControlDefaultTcontMaxBw, sleGponOltControlDefaultProfileName, sleGponOnuId,
				sleGponOnuStatus, sleGponOnuMode, sleGponOnuSerial, sleGponOnuPasswd, sleGponOnuPasswdMode,
				sleGponOnuEncMode, sleGponOnuProfile, sleGponOnuHostname, sleGponOnuDistance, sleGponOnuHwAddress,
				sleGponOnuNosActiveVersion, sleGponOnuNosStandbyVersion, sleGponOnuNosUpgradeStatus, sleGponOnuIsFirst, sleGponOnuRxPower,
				sleGponOnuModelName, sleGponOnuDescription, sleGponOnuNosAutoUpgradeWaitStatus, sleGponOnuNosAutoUpgradeFailCount, sleGponOnuControlRequest,
				sleGponOnuControlStatus, sleGponOnuControlTimer, sleGponOnuControlTimeStamp, sleGponOnuControlReqResult, sleGponOnuControlOltId,
				sleGponOnuControlId, sleGponOnuControlSerial, sleGponOnuControlPasswd, sleGponOnuControlPasswdMode, sleGponOnuControlEncMode,
				sleGponOnuControlProfile, sleGponOnuControlNosUpgradePath, sleGponOnuControlHwAddr, sleGponOnuControlTxOffOptic, sleGponOnuControlDescription,
				sleGponTcontId, sleGponTcontOnuId, sleGponTcontDBAMode, sleGponTcontFixedBw, sleGponTcontAssuredBw,
				sleGponTcontMaxBw, sleGponTcontControlRequest, sleGponTcontControlStatus, sleGponTcontControlTimer, sleGponTcontControlTimeStamp,
				sleGponTcontControlReqResult, sleGponTcontControlId, sleGponTcontControlOltId, sleGponTcontControlOnuId, sleGponTcontControlDBAMode,
				sleGponTcontControlFixedBw, sleGponTcontControlAssuredBw, sleGponTcontControlMaxBw, sleGponTcontControlOnuSerial, sleGponProfileId,
				sleGponProfileName, sleGponProfileDscpToPbit, sleGponProfileBaseControlRequest, sleGponProfileBaseControlStatus, sleGponProfileBaseControlTimer,
				sleGponProfileBaseControlTimeStamp, sleGponProfileBaseControlReqResult, sleGponProfileBaseControlName, sleGponProfileBaseControlDscpToPbit, sleGponProfilePortId,
				sleGponProfilePortRateLimit, sleGponProfilePortMaxHost, sleGponProfilePortVlan, sleGponProfilePortCosValue, sleGponProfilePortVlanMode,
				sleGponProfilePortVlanFilter, sleGponProfilePortControlRequest, sleGponProfilePortControlStatus, sleGponProfilePortControlTimer, sleGponProfilePortControlTimeStamp,
				sleGponProfilePortControlReqResult, sleGponProfilePortControlId, sleGponProfilePortControlPortId, sleGponProfilePortControlRateLimit, sleGponProfilePortControlMaxHost,
				sleGponProfilePortControlVlan, sleGponProfilePortControlCosValue, sleGponProfilePortControlVlanMode, sleGponProfilePortControlVlanFilter, sleGponOnuPortSlotId,
				sleGponOnuPortSlotType, sleGponOnuPortAdminStatus, sleGponOnuPortOperStatus, sleGponOnuPortControlRequest, sleGponOnuPortControlStatus,
				sleGponOnuPortControlTimer, sleGponOnuPortControlTimeStamp, sleGponOnuPortControlReqResult, sleGponOnuPortControlOltId, sleGponOnuPortControlOnuId,
				sleGponOnuPortControlSlotId, sleGponOnuPortControlPortId, sleGponOnuPortControlAdminStatus, sleGponOnuPortControlOnuSerial, sleGponOltStatsPonValidEthPacketsRx,
				sleGponOltStatsPonCpuPacketsRx, sleGponOltStatsPonPloamsRx, sleGponOltStatsPonInvalidPacketsRx, sleGponOltStatsPonValidEthPacketsTx, sleGponOltStatsPonCpuPacketsTx,
				sleGponOltStatsPonPloamsTx, sleGponOltStatsPonInvalidPacketsTx, sleGponOltStatsPerfRxValidPackets, sleGponOltStatsPerfRxErroredPackets, sleGponOltStatsPerfCRCdroppedPackets,
				sleGponOltStatsAllocId, sleGponOltStatsAllocDataRx, sleGponOltStatsOnuPonUnreceivedBursts, sleGponOltStatsOnuPonPositiveDrift, sleGponOltStatsOnuNegativeDrift,
				sleGponOltStatsOnuPonBip8Errors, sleGponOltStatsControlRequest, sleGponOltStatsControlStatus, sleGponOltStatsControlTimer, sleGponOltStatsControlTimeStamp,
				sleGponOltStatsControlReqResult, sleGponOltStatsControlOltIndex, sleGponOltStatsControlOnuIndex, sleGponFirmwareType, sleGponFirmwareName,
				sleGponFirmwareControlRequest, sleGponFirmwareControlStatus, sleGponFirmwareControlTimer, sleGponFirmwareControlTimeStamp, sleGponFirmwareControlReqResult,
				sleGponFirmwareControlName, sleGponFirmwareControlUpgradeMethod, sleGponFirmwareControlUpgradeMode, sleGponFirmwareControlServerAddress, sleGponFirmwareControlUser,
				sleGponFirmwareControlPasswd, sleGponOnuFWAutoUpgradeMode, sleGponOnuFWAutoUpgradeVersionMatch, sleGponOnuFWAutoUpgradeInvalidVersionMatch, sleGponOnuFWAutoUpgradeStatus,
				sleGponOnuFWAutoUpgradeCurrentUgradingFWName, sleGponOnuFWAutoUpgradeControlRequest, sleGponOnuFWAutoUpgradeControlStatus, sleGponOnuFWAutoUpgradeControlTimer, sleGponOnuFWAutoUpgradeControlTimeStamp,
				sleGponOnuFWAutoUpgradeControlReqResult, sleGponOnuFWAutoUpgradeControlOltId, sleGponOnuFWAutoUpgradeControlMode, sleGponOnuFWAutoUpgradeControlVersionMatch, sleGponOnuFWAutoUpgradeControlInvalidVersionMatch,
				sleGponOnuFWAutoUpgradeStartTime, sleGponOnuFWAutoUpgradeEndTime, sleGponOnuFWAutoUpgradeRebootTime, sleGponOnuFWAutoUpgradeTimeControlRequest, sleGponOnuFWAutoUpgradeTimeControlStatus,
				sleGponOnuFWAutoUpgradeTimeControlTimer, sleGponOnuFWAutoUpgradeTimeControlTimeStamp, sleGponOnuFWAutoUpgradeTimeControlReqResult, sleGponOnuFWAutoUpgradeTimeControlStartTime, sleGponOnuFWAutoUpgradeTimeControlEndTime,
				sleGponOnuFWAutoUpgradeTimeControlRebootTime, sleGponOnuFWAutoUpgradeModelId, sleGponOnuFWAutoUpgradeModelName, sleGponOnuFWAutoUpgradeModelFWName, sleGponOnuFWAutoUpgradeModelFWVersion,
				sleGponOnuFWAutoUpgradeModelStatus, sleGponOnuFWAutoUpgradeModelMethod, sleGponOnuFWAutoUpgradeModelServerAddress, sleGponOnuFWAutoUpgradeModelUser, sleGponOnuFWAutoUpgradeModelPasswd,
				sleGponOnuFWAutoUpgradeModelControlRequest, sleGponOnuFWAutoUpgradeModelControlStatus, sleGponOnuFWAutoUpgradeModelControlTimer, sleGponOnuFWAutoUpgradeModelControlTimeStamp, sleGponOnuFWAutoUpgradeModelControlReqResult,
				sleGponOnuFWAutoUpgradeModelControlName, sleGponOnuFWAutoUpgradeModelControlFWName, sleGponOnuFWAutoUpgradeModelControlMethod, sleGponOnuFWAutoUpgradeModelControlServerAddress, sleGponOnuFWAutoUpgradeModelControlUser,
				sleGponOnuFWAutoUpgradeModelControlPasswd, sleGponOnuOltRxPower, sleGponOnuLinkUpTime, sleGponOnuPortLinkUptime, sleGponOnuPortAutoNego,
				sleGponOnuPortSpeed, sleGponOnuPortControlAutoNego, sleGponOnuPortControlSpeed, sleGponOltStatsOnuPonFecCorrectedBytes, sleGponOltStatsOnuPonFecUncorrectedCodewords,
				sleGponOltStatsOnuPonFecCorrectedCodewords, sleGponOltStatsOnuPonFecReceivedCodewords, sleGponOnuAuthenticationStatus, sleGponOnuNetmask, sleGponOnuHWType,
				sleGponOnuRegistrationCnt, sleGponOnuAuthAcceptedCnt, sleGponOnuAuthRejectedCnt, sleGponOntFirmwareIndex, sleGponOntFirmwareType,
				sleGponOntFirmwareName, sleGponOntiFirmwareSize, sleGponOntFirmwareMd5, sleGponOntFirmwareOntId, sleGponOntFirmwareOntOs1Ver,
				sleGponOntFirmwareOntOs2Ver, sleGponOntFirmwareOntBLVer, sleGponOntFirmeareOntDefaultOS, sleGponOntFirmeareOntRunningOS, sleGponOntFirmwareOntGponOs1Ver,
				sleGponOntFirmwareOntGponOs2Ver, sleGponOntFirmwareOntOsStatus, sleGponOntFirmwareOntBLStatus, sleGponOntFirmwareOsUpgrdStatus, sleGponOntFirmwareOsUpgrdResult,
				sleGponOntFirmwareBLUpgrdStatus, sleGponOntFirmwareBLUpgrdResult, sleGponOntFirmwareControlReqest, sleGponOntFirmwareControlStatus, sleGponOntFirmwareControlTimer,
				sleGponOntFirmwareControlTimeStamp, sleGponOntFirmwareControlReqResult, sleGponOntFirmwareControlOltId, sleGponOntFirmwareControlOntId, sleGponOntFirmwareControlType,
				sleGponOntFirmwareControlFwName, sleGponOntFirmwareControlMethod, sleGponOntFirmwareControlServer, sleGponOntFirmwareControlUser, sleGponOntFirmwareControlPasswd,
				sleGponOnuAuthChallengedCnt, sleGponOnuVlanID, sleGponOnuRTD, sleGponOntFirmwareOltId, sleGponOltFecModeUS,
				sleGponOltFecModeDS, sleGponOltMacAgingTime, sleGponOltTransceiverPort, sleGponOltControlFecModeUS, sleGponOltControlFecModeDS,
				sleGponOltControlMacAgingTime, sleGponOltControlTransceiverPort, sleGponOnuFecModeUS, sleGponOnuIPMode, sleGponOnuIpAddress,
				sleGponOnuIPMask, sleGponOnuIPGw, sleGponOnuIPDns1, sleGponOnuIPDns2, sleGponOnuControlFecModeUS,
				sleGponOnuControlIPMode, sleGponOnuControlIPMask, sleGponOnuControlIPGw, sleGponOnuControlIPDns1, sleGponOnuControlIPDns2,
				sleGponProfileTcontProfileCnt, sleGponProfileTcontProfile, sleGponProfileVoIPProfileCnt, sleGponProfileVoIPProfile, sleGponProfileControlTcontProfileCnt,
				sleGponProfileControlTcontProfile, sleGponProfileControlVoipProfileCnt, sleGponProfileControlVoipProfile, sleGponProfileDbaId, sleGponProfileDbaName,
				sleGponProfileDbaMode, sleGponProfileDbaSlaFixedBw, sleGponProfileDbaSlaAssuredBw, sleGponProfileDbaSlaMaxBw, sleGponProfileDbaControlRequest,
				sleGponProfileDbaControlStatus, sleGponProfileDbaControlTimer, sleGponProfileDbaControlTimeStamp, sleGponProfileDbaControlReqResult, sleGponProfileDbaControlId,
				sleGponProfileDbaControlName, sleGponProfileDbaControlMode, sleGponProfileDbaControlSlaFixedBw, sleGponProfileDbaControlSlaAssuredBw, sleGponProfileDbaControlSlaMaxBw,
				sleGponProfileMultiTcontIndex, sleGponProfileMultiTcontName, sleGponProfileMultiTconTDscp2Pbit, sleGponProfileMultiTconTPriQWeightCnt, sleGponProfileMultiTconTPriQWeight,
				sleGponProfileMultiTcontGemPortType, sleGponProfileMultiTcontGemportUniPortList, sleGponProfileMultiTcontGemPortVlanCnt, sleGponProfileMultiTcontGemPortVlanList, sleGponProfileMultiTcontGemPortCount,
				sleGponProfileMultiTcontGemPortDbaProfileName1, sleGponProfileMultiTcontGemPortDbaProfileMask1, sleGponProfileMultiTcontGemPortDbaProfileName2, sleGponProfileMultiTcontGemPortDbaProfileMask2, sleGponProfileMultiTcontGemPortDbaProfileName3,
				sleGponProfileMultiTcontGemPortDbaProfileMask3, sleGponProfileMultiTcontGemPortDbaProfileName4, sleGponProfileMultiTcontGemPortDbaProfileMask4, sleGponProfileMultiTcontGemPortDbaProfileName5, sleGponProfileMultiTcontGemPortDbaProfileMask5,
				sleGponProfileMultiTcontGemPortDbaProfileName6, sleGponProfileMultiTcontGemPortDbaProfileMask6, sleGponProfileMultiTcontGemPortDbaProfileName7, sleGponProfileMultiTcontGemPortDbaProfileMask7, sleGponProfileMultiTcontGemPortDbaProfileName8,
				sleGponProfileMultiTcontGemPortDbaProfileMask8, sleGponProfileMultiTcontControllRequest, sleGponProfileMultiTcontControlStatus, sleGponProfileMultiTcontControlTimer, sleGponProfileMultiTcontControlTimeStamp,
				sleGponProfileMultiTcontControlReqResult, sleGponProfileMultiTcontControlIndex, sleGponProfileMultiTcontControlName, sleGponProfileMultiTcontControlDscp2Pbit, sleGponProfileMultiTcontControlPriQWeightCnt,
				sleGponProfileMultiTcontControlPriQWeight, sleGponProfileMultiTcontControlGemPortType, sleGponProfileMultiTcontControlGemportUniPortList, sleGponProfileMultiTcontControlGemPortVlanCnt, sleGponProfileMultiTcontControlGemPortVlanList,
				sleGponProfileMultiTcontControlGemPortCount, sleGponProfileMultiTcontControlGemPortDbaProfileName1, sleGponProfileMultiTcontControlGemPortDbaProfileMask1, sleGponProfileMultiTcontControlGemPortDbaProfileName2, sleGponProfileMultiTcontControlGemPortDbaProfileMask2,
				sleGponProfileMultiTcontControlGemPortDbaProfileName3, sleGponProfileMultiTcontControlGemPortDbaProfileMask3, sleGponProfileMultiTcontControlGemPortDbaProfileName4, sleGponProfileMultiTcontControlGemPortDbaProfileMask4, sleGponProfileMultiTcontControlGemPortDbaProfileName5,
				sleGponProfileMultiTcontControlGemPortDbaProfileMask5, sleGponProfileMultiTcontControlGemPortDbaProfileName6, sleGponProfileMultiTcontControlGemPortDbaProfileMask6, sleGponProfileMultiTcontControlGemPortDbaProfileName7, sleGponProfileMultiTcontControlGemPortDbaProfileMask7,
				sleGponProfileMultiTcontControlGemPortDbaProfileName8, sleGponProfileMultiTcontControlGemPortDbaProfileMask8, sleGponProfileVoIPIndex, sleGponProfileVoIPName, sleGponProfileVoIPServiceMode,
				sleGponProfileVoIPServiceProtocol, sleGponProfileVoIPOmciAgentURL, sleGponProfileVoIPOmciAgentProxy, sleGponProfileVoIPOmciAgentDns1, sleGponProfileVoIPOmciAgentDns2,
				sleGponProfileVoIPControlStatus, sleGponProfileVoIPControlTimer, sleGponProfileVoIPControlTimeStamp, sleGponProfileVoIPControlReqResult, sleGponProfileVoIPControlIndex,
				sleGponProfileVoIPControlName, sleGponProfileVoIPControlServiceMode, sleGponProfileVoIPControlServiceProtocol, sleGponProfileVoIPControlOmciAgentURL, sleGponProfileVoIPControlOmciAgentProxy,
				sleGponProfileVoIPControlOmciAgentDns1, sleGponProfileVoIPControlOmciAgentDns2, sleGponProfileVoIPOmciUniPortId, sleGponProfileVoIPOmciAuthName, sleGponProfileVoIPOmciAuthPasswd,
				sleGponProfileVoIPOmciPhoneNumber, sleGponProfileVoIPOmciDisplay, sleGponProfileVoIPOmciControlStatus, sleGponProfileVoIPOmciControlTimer, sleGponProfileVoIPOmciControlTimeStamp,
				sleGponProfileVoIPOmciControlReqResult, sleGponProfileVoIPOmciControlOltIndex, sleGponProfileVoIPOmciControlOnuIndex, sleGponProfileVoIPOmciControlUniId, sleGponProfileVoIPOmciControlAuthName,
				sleGponProfileVoIPOmciControlAuthPasswd, sleGponProfileVoIPOmciControlPhoneNumber, sleGponProfileVoIPOmciControlDisplay, sleGponProfileVoIPIpPathControlStatus, sleGponProfileVoIPIpPathControlTimer,
				sleGponProfileVoIPIpPathControlTimeStamp, sleGponProfileVoIPIpPathControlReqResult, sleGponProfileVoIPIpPathControlOltIndex, sleGponProfileVoIPIpPathControlOnuIndex, sleGponProfileVoIPIpPathControlAuthName,
				sleGponProfileVoIPIpPathControlAuthPasswd, sleGponOnuBatteryStatus, sleGponOnuMgmtSerialNo, sleGponProfileVoIPControlRequest, sleGponProfileVoIPOmciControlRequest,
				sleGponOnuUserMacCnt, sleGponOnuUserMacAddress, sleGponOnuUserMacVlanId, sleGponOnuUserMacPortId, sleGponProfilePortAdmin,
				sleGponProfilePortDuplex, sleGponProfilePortSpeed, sleGponProfilePortControlPortAdmin, sleGponProfilePortControlPortDuplex, sleGponProfilePortControlPortSpeed,
				sleGponOnuUserMacOltId, sleGponOnuUserMacOnuId, sleGponBridgeVoIPInfoOltId, sleGponBridgeVoIPInfoOnuId, sleGponBridgeVoIPInfoDHCP,
				sleGponBridgeVoIPInfoIpAddress, sleGponBridgeVoIPInfoMethods, sleGponBridgeVoIPInfoCurrMethods, sleGponBridgeVoIPInfoProtocols, sleGponBridgeVoIPInfoCurrProtocols,
				sleGponBridgeVoIPLineOltId, sleGponBridgeVoIPLineOnuId, sleGponBridgeVoIPLinePots, sleGponBridgeVoIPLineAdminStatus, sleGponBridgeVoIPLineOperStatus,
				sleGponBridgeVoIPLineStatus, sleGponOnuPortDuplex, sleGponOltActivateStatus, sleGponOltControlActivateStatus, sleGponOnuDeactiveReason,
				sleGponOnuFWAutoUpgradeModelControlFWTargetVersion, sleGponOnuFWAutoUpgradeModelFWTargetVersion, sleGponOnuFWAutoUpgradeMTimeControlModelName, sleGponOnuFWAutoUpgradeMTimeControlEndTime, sleGponOnuFWAutoUpgradeMTimeControlStartTime,
				sleGponOnuFWAutoUpgradeMTimeControlReqResult, sleGponOnuFWAutoUpgradeMTimeControlTimeStamp, sleGponOnuFWAutoUpgradeMTimeControlTimer, sleGponOnuFWAutoUpgradeMTimeControlStatus, sleGponOnuFWAutoUpgradeMTimeControlRequest,
				sleGponOnuFWAutoUpgradeMTimeModelName, sleGponOnuFWAutoUpgradeMTimeEndTime, sleGponOnuFWAutoUpgradeMTimeStartTime, sleGponOnuFWAutoUpgradeMTimeIndex, sleGponOnuFWAutoUpgradeSActiveVer,
				sleGponOnuFWAutoUpgradeSFailCnt, sleGponOnuFWAutoUpgradeSStatus, sleGponOnuFWAutoUpgradeSModelName, sleGponOnuFWAutoUpgradeSOnuID, sleGponOnuFWAutoUpgradeSOltID,
				sleGponOnuFWAutoUpgradeSIndex, sleGponOltProtection, sleGponOltActiveOnuCount, sleGponOltInactiveOnuCount, sleGponOltControlProtection,
				sleGponOnuControlActiveStatus, sleGponBridgeSlotIndex, sleGponBridgeSlotConnectionStatus, sleGponBridgeSlotFlags, sleGponRedGroupIndex,
				sleGponRedGroupOltAIndex, sleGponRedGroupOltAStatus, sleGponRedGroupOltBIndex, sleGponRedGroupOltBStatus, sleGponRedLastReason,
				sleGponRedGroupControlRequest, sleGponRedGroupControlStatus, sleGponRedGroupControlTimer, sleGponRedGroupControlTimeStamp, sleGponRedGroupControlReqResult,
				sleGponRedGroupControlGroupIndex, sleGponRedGroupControlOltAIndex, sleGponRedGroupControlOltBIndex, sleGponProfilePortPause, sleGponProfilePortControlPortPause,
				sleGponOnuControlPathIpAddr, sleGponOnuControlPathMacAddr, sleGponOnuControlPathStatus, sleGponOnuControlPathUptime, sleGponProfile2OnuName,
				sleGponProfile2OnuRxPowerHighThresh, sleGponProfile2OnuRxPowerLowThresh, sleGponProfile2OnuRogueAlarmCount, sleGponProfile2OnuRoguePollingInterval, sleGponProfile2OnuRogueWaitingTime,
				sleGponProfile2OnuTrafficProfile, sleGponProfile2OnuControlRequest, sleGponProfile2OnuControlStatus, sleGponProfile2OnuControlTimer, sleGponProfile2OnuControlTimeStamp,
				sleGponProfile2OnuControlReqResult, sleGponProfile2OnuControlName, sleGponProfile2OnuControlRxPowerHighThresh, sleGponProfile2OnuControlRxPowerLowThresh, sleGponProfile2OnuControlRogueAlarmCount,
				sleGponProfile2OnuControlRoguePollingInterval, sleGponProfile2OnuControlRogueWaitingTime, sleGponProfile2OnuControlTrafficProfile, sleGponProfile2OnuUniId, sleGponProfile2OnuUniType,
				sleGponProfile2OnuUniDownSir, sleGponProfile2OnuUniDownPir, sleGponProfile2OnuUniControlRequest, sleGponProfile2OnuUniControlStatus, sleGponProfile2OnuUniControlTimer,
				sleGponProfile2OnuUniControlTimeStamp, sleGponProfile2OnuUniControlReqResult, sleGponProfile2OnuUniControlId, sleGponProfile2OnuUniControlType, sleGponProfile2OnuUniControlDownSir,
				sleGponProfile2OnuUniControlDownPir, sleGponProfile2McastAclIndex, sleGponProfile2McastAclControlIndex, sleGponProfile2McastAclControlName, sleGponProfile2McastSAclIndex,
				sleGponProfile2McastSAclControlIndex, sleGponProfile2McastSAclControlName, sleGponOltLinkUpCount, sleGponOltLinkDownCount, sleGponOltAuthenCount,
				sleGponOltElapsedTimeAfterClearAuthStats, sleGponOnuPortGemblockRx, sleGponOnuPortGemblockTx, sleGponOnuPortDiscardFrames, sleGponProfileVoIPIpPathControlRequest,
				sleGponOnuIPAddr, sleGponOnuControlIPAddr, sleGponOnuPMProfile, sleGponOnuControlPMProfile, sleGponProfile2PMProfileName,
				sleGponProfile2PMProfilePMGemPort, sleGponProfile2PMProfileControlRequest, sleGponProfile2PMProfileControlStatus, sleGponProfile2PMProfileControlTimer, sleGponProfile2PMProfileControlTimeStamp,
				sleGponProfile2PMProfileControlReqResult, sleGponProfile2PMProfileControlName, sleGponProfile2TcontGemportMapperId, sleGponProfile2TcontGemportControlMapperId, sleGponProfile2OnuUniControlOnuProfile,
				sleGponProfile2PMProfileControlPMGemPort, sleGponProfile2PMProfilePMAniPort, sleGponProfile2PMProfileControlPMAniPort, sleGponOltUpElapsedTime, sleGponOltDownElapsedTime,
				sleGponOltOpticParam, sleGponOltControlOpticParam, sleGponOnuUpCount, sleGponOnuDownCount, sleGponOnuControlNosPartition,
				sleGponOnuPortElapsedTimeAfterClearStats, sleGponOnuPMStatsPrev15mLostPackets, sleGponOnuPMStatsPrev15mMisInsertedPackets, sleGponOnuPMStatsPrev15mReceivedPackets, sleGponOnuPMStatsPrev15mReceivedBlocks,
				sleGponOnuPMStatsPrev15mTransmittedBlocks, sleGponOnuPMStatsPrev15mImpairedBlocks, sleGponOnuPMStatsPrev15mDiscardedFrames, sleGponOnuPMStatsPrev30mLostPackets, sleGponOnuPMStatsPrev30mMisInsertedPackets,
				sleGponOnuPMStatsPrev30mReceivedPackets, sleGponOnuPMStatsPrev30mReceivedBlocks, sleGponOnuPMStatsPrev30mTransmittedBlocks, sleGponOnuPMStatsPrev30mImpairedBlocks, sleGponOnuPMStatsPrev30mDiscardedFrames,
				sleGponOnuPMStatsTotalLostPackets, sleGponOnuPMStatsTotalMisInsertedPackets, sleGponOnuPMStatsTotalReceivedPackets, sleGponOnuPMStatsTotalReceivedBlocks, sleGponOnuPMStatsTotalTransmittedBlocks,
				sleGponOnuPMStatsTotalImpairedBlocks, sleGponOnuPMStatsTotalDiscardedFrames, sleGponOnuPMStatsElapsedTimeAfterClear, sleGponOnuPMStatsElapsedTimeAfterUpdate, sleGponOnuPMStatsControlRequest,
				sleGponOnuPMStatsControlStatus, sleGponOnuPMStatsControlTimer, sleGponOnuPMStatsControlTimeStamp, sleGponOnuPMStatsControlReqResult, sleGponOnuPMStatsControlOltIndex,
				sleGponOnuPMStatsControlOnuIndex, sleGponProfile2DbaIndex, sleGponProfile2TrafficIndex, sleGponProfile2McastIndex, sleGponProfile2OnuIndex,
				sleGponProfile2OnuRoguePollingCount, sleGponProfile2OnuPmProfile, sleGponProfile2OnuControlRoguePollingCount, sleGponProfile2OnuControlPmProfile, sleGponProfile2OnuUniVlanDsOper,
				sleGponProfile2OnuUniVlanUSOper, sleGponProfile2OnuUniVlanUsOperVID, sleGponProfile2OnuUniVlanUsOperCoS, sleGponProfile2OnuUniIgmpMaxGroup, sleGponProfile2OnuUniPortAdmin,
				sleGponProfile2OnuUniControlVlanDsOper, sleGponProfile2OnuUniControlVlanUsOper, sleGponProfile2OnuUniControlVlanUsOperVID, sleGponProfile2OnuUniControlVlanUsOperCoS, sleGponProfile2OnuUniControlIgmpMaxGroup,
				sleGponProfile2OnuUniControlPortAdmin, sleGponProfile2PMProfileIndex, sleGponProfile2OnuBridgeId, sleGponProfile2OnuBridgeMaxHost, sleGponProfile2OnuBridgeControlRequest,
				sleGponProfile2OnuBridgeControlStatus, sleGponProfile2OnuBridgeControlTimer, sleGponProfile2OnuBridgeControlTimeStamp, sleGponProfile2OnuBridgeControlReqResult, sleGponProfile2OnuBridgeControlOnuProfile,
				sleGponProfile2OnuBridgeControlId, sleGponProfile2OnuBridgeControlMaxHost, sleGponProfile2OnuTcontId, sleGponProfile2OnuTcontDbaProfile, sleGponProfile2OnuTcontControlRequest,
				sleGponProfile2OnuTcontControlStatus, sleGponProfile2OnuTcontControlTimer, sleGponProfile2OnuTcontControlTimeStamp, sleGponProfile2OnuTcontControlReqResult, sleGponProfile2OnuTcontControlOnuProfile,
				sleGponProfile2OnuTcontControlId, sleGponProfile2OnuTcontControlDbaProfile, sleGponOnuNosDefaultPartition, sleGponOnuNosActivePartition, sleGponProfile2BridgeUniIpMode,
				sleGponProfile2BridgeUniDns1, sleGponProfile2BridgeUniDns2, sleGponProfile2BridgeUniVoIPProfile, sleGponProfile2BridgeUniControlIpMode, sleGponProfile2BridgeUniControlDns1,
				sleGponProfile2BridgeUniControlDns2, sleGponProfile2BridgeUniControlVoIPProfile, sleGponOnuHostOltId, sleGponOnuHostOnuId, sleGponOnuHostId,
				sleGponOnuHostIPAddr, sleGponOnuHostMask, sleGponOnuHostGW, sleGponOnuHostControlRequest, sleGponOnuHostControlStatus,
				sleGponOnuHostControlTimer, sleGponOnuHostControlTimeStamp, sleGponOnuHostControlReqResult, sleGponOnuHostControlOltId, sleGponOnuHostControlOnuId,
				sleGponOnuHostControlId, sleGponOnuHostControlIPAddr, sleGponOnuHostControlMask, sleGponOnuHostControlGW, sleGponBaseControlDeaultServiceProfile,
				sleGponOltSrcMacMonitorStatus, sleGponOltSrcMacMonitorAutoBlock, sleGponOltSrcMacMonitoEexpireTimeout, sleGponOltTotalUsBw, sleGponOltControlSrcMacMonitorStatus,
				sleGponOltControlSrcMacMonitorAutoBlock, sleGponOltControlSrcMacMonitoEexpireTimeout, sleGponOltControlTotalUsBw, sleGponOnuBlockStatus, sleGponOnuBlockReason,
				sleGponOnuLastActiveFailReason, sleGponOnuEqD, sleGponOnuMaxTcont, sleGponOnuMaxUsQueuePerTcont, sleGponOnuSysUpTime,
				sleGponOnuVenderProduct, sleGponOnuSlotId, sleGponOnuOperStatus, sleGponOnuMapperID, sleGponOnuControlBlock,
				sleGponServiceProfileModelName, sleGponServiceProfileProfileName, sleGponServiceProfileControlRequest, sleGponServiceProfileControlStatus, sleGponServiceProfileControlTimer,
				sleGponServiceProfileControlTimeStamp, sleGponServiceProfileControlReqResult, sleGponServiceProfileControlModelName, sleGponServiceProfileControlProfileName, sleGponOnuUserMacControlRequest,
				sleGponOnuUserMacControlStatus, sleGponOnuUserMacControlTimer, sleGponOnuUserMacControlTimeStamp, sleGponOnuUserMacControlReqResult, sleGponOnuUserMacControlOltId,
				sleGponOnuUserMacControlOnuId, sleGponOnuUserMacControlAddress, sleGponOnuUserMacControlVlanId, sleGponOntFirmwareControlOnuId, sleGponIgmpGroupOltId,
				sleGponIgmpGroupOnuId, sleGponIgmpGroupUniId, sleGponIgmpGroupUniType, sleGponIgmpGroupIndex, sleGponIgmpGroupSrcIPAddr,
				sleGponIgmpGroupDstIPAddr, sleGponIgmpGroupRptIPAddr, sleGponIgmpGroupJoinTime, sleGponProfileVoIPPotsPIndex, sleGponProfileVoIPPotsIndex,
				sleGponProfileVoIPPotsAdmin, sleGponProfileVoIPPotsControlRequest, sleGponProfileVoIPPotsControlStatus, sleGponProfileVoIPPotsControlTimer, sleGponProfileVoIPPotsControlTimeStamp,
				sleGponProfileVoIPPotsControlReqResult, sleGponProfileVoIPPotsControlProfileIndex, sleGponProfileVoIPPotsControlPotsIndex, sleGponProfileVoIPPotsControlAdmin, sleGponServiceProfileIndex,
				sleGponDefaultServiceProfile, sleGponProfileTdmPwMtIndex, sleGponProfileTdmPwMtName, sleGponProfileTdmPwMtMaxDepth, sleGponProfileTdmPwMtDesiredDepth,
				sleGponProfileTdmPwMtFillPolicy, sleGponProfileTdmPwMtMisconnectDeclarePolicy, sleGponProfileTdmPwMtMisconnectClearPolicy, sleGponProfileTdmPwMtLossDeclarePolicy, sleGponProfileTdmPwMtLossClearPolicy,
				sleGponProfileTdmPwMtBuffUnderrunDeclarePolicy, sleGponProfileTdmPwMtBuffUnderrunClearPolicy, sleGponProfileTdmPwMtMalformedDeclarePolicy, sleGponProfileTdmPwMtMalformedClearPolicy, sleGponProfileTdmPwMtRBitTransmitPolicy,
				sleGponProfileTdmPwMtRBitReceivePolicy, sleGponProfileTdmPwMtLBitReceivePolicy, sleGponProfileTdmPwMtSesThreshold, sleGponProfileTdmPwMtControlRequest, sleGponProfileTdmPwMtControlStatus,
				sleGponProfileTdmPwMtControlTimer, sleGponProfileTdmPwMtControlTimeStamp, sleGponProfileTdmPwMtControlReqResult, sleGponProfileTdmPwMtControlIndex, sleGponProfileTdmPwMtControlName,
				sleGponProfileTdmPwMtControlMaxDepth, sleGponProfileTdmPwMtControlDesiredDepth, sleGponProfileTdmPwMtControlFillPolicy, sleGponProfileTdmPwMtControlMisconnectDeclarePolicy, sleGponProfileTdmPwMtControlMisconnectClearPolicy,
				sleGponProfileTdmPwMtControlLossDeclarePolicy, sleGponProfileTdmPwMtControlLossClearPolicy, sleGponProfileTdmPwMtControlBuffUnderrunDeclarePolicy, sleGponProfileTdmPwMtControlBuffUnderrunClearPolicy, sleGponProfileTdmPwMtControlMalformedDeclarePolicy,
				sleGponProfileTdmPwMtControlMalformedClearPolicy, sleGponProfileTdmPwMtControlRBitTransmitPolicy, sleGponProfileTdmPwMtControlRBitReceivePolicy, sleGponProfileTdmPwMtControlLBitReceivePolicy, sleGponProfileTdmPwMtControlSesThreshold,
				sleGponProfileTdmPwIndex, sleGponProfileTdmPwName, sleGponProfileTdmPwServiceType, sleGponProfileTdmPwSignalling, sleGponProfileTdmPwPayloadSize,
				sleGponProfileTdmPwPayloadEncapulationDelay, sleGponProfileTdmPwTimingMode, sleGponProfileTdmPwRtpClockRefernce, sleGponProfileTdmPwRtpTimeStampMode, sleGponProfileTdmPwRtpPayloadChannel,
				sleGponProfileTdmPwRtpPayloadSignalling, sleGponProfileTdmPwRtpSyncSourceChannel, sleGponProfileTdmPwRtpSyncSourceSignalling, sleGponProfileTdmPwRtpExpectPayloadChannel, sleGponProfileTdmPwRtpExpectPaloadSignalling,
				sleGponProfileTdmPwRtpExpectSyncSourceChannel, sleGponProfileTdmPwRtpExpectSyncSourceSignalling, sleGponProfileTdmPwMtProfileName, sleGponProfileTdmPwControlRequest, sleGponProfileTdmPwControlStatus,
				sleGponProfileTdmPwControlTimer, sleGponProfileTdmPwControlTimeStamp, sleGponProfileTdmPwControlReqResult, sleGponProfileTdmPwControlIndex, sleGponProfileTdmPwControlName,
				sleGponProfileTdmPwControlServiceType, sleGponProfileTdmPwControlSignalling, sleGponProfileTdmPwControlPayloadSize, sleGponProfileTdmPwControlPayloadEncapulationDelay, sleGponProfileTdmPwControlTimingMode,
				sleGponProfileTdmPwControlRtpClockRefernce, sleGponProfileTdmPwControlRtpTimeStampMode, sleGponProfileTdmPwControlRtpPayloadChannel, sleGponProfileTdmPwControlRtpPayloadSignalling, sleGponProfileTdmPwControlRtpSyncSourceChannel,
				sleGponProfileTdmPwControlRtpSyncSourceSignalling, sleGponProfileTdmPwControlRtpExpectPayloadChannel, sleGponProfileTdmPwControlRtpExpectPaloadSignalling, sleGponProfileTdmPwControlRtpExpectSyncSourceChannel, sleGponProfileTdmPwControlRtpExpectSyncSourceSignalling,
				sleGponProfileTdmPwControlMtProfileName, sleGponProfile2TdmSvcId, sleGponProfile2TdmSvcMode, sleGponProfile2TdmSvcTdmPwProfileName, sleGponProfile2TdmSvcTimeSlot,
				sleGponProfile2TdmSvcEthDestMac, sleGponProfile2TdmSvcEthVid, sleGponProfile2TdmSvcEthCoS, sleGponProfile2TdmSvcTranPayloadEcid, sleGponProfile2TdmSvcTranSignallingEcid,
				sleGponProfile2TdmSvcRecvPayloadEcid, sleGponProfile2TdmSvcRecvSignallingEcid, sleGponProfile2TdmSvcExpectPayloadEcid, sleGponProfile2TdmSvcExpectSignallingEcid, sleGponProfile2TdmSvcFarEndIpURL,
				sleGponProfile2TdmSvcMplsLabelIndicator, sleGponProfile2TdmSvcMplsPwDirection, sleGponProfile2TdmSvcMplsPwLabelUp, sleGponProfile2TdmSvcMplsPwLabelDown, sleGponProfile2TdmSvcMplsPwLabelExp,
				sleGponProfile2TdmSvcMplsPwTunnelDirection, sleGponProfile2TdmSvcMplsPwTunnelLabelUp, sleGponProfile2TdmSvcMplsPwTunnelLabelDown, sleGponProfile2TdmSvcMplsPwTunnelLabelExp, sleGponProfile2TdmSvcCesBuffCdvTolerance,
				sleGponProfile2TdmSvcCesChannelAssociateSignal, sleGponProfile2TdmSvcControlRequest, sleGponProfile2TdmSvcControlStatus, sleGponProfile2TdmSvcControlTimer, sleGponProfile2TdmSvcControlTimeStamp,
				sleGponProfile2TdmSvcControlReqResult, sleGponProfile2TdmSvcControlTName, sleGponProfile2TdmSvcControlTdmId, sleGponProfile2TdmSvcControlId, sleGponProfile2TdmSvcControlMode,
				sleGponProfile2TdmSvcControlTdmPwProfileName, sleGponProfile2TdmSvcControlTimeSlot, sleGponProfile2TdmSvcControlEthDestMac, sleGponProfile2TdmSvcControlEthVid, sleGponProfile2TdmSvcControlEthCoS,
				sleGponProfile2TdmSvcControlTranPayloadEcid, sleGponProfile2TdmSvcControlTranSignallingEcid, sleGponProfile2TdmSvcControlRecvPayloadEcid, sleGponProfile2TdmSvcControlRecvSignallingEcid, sleGponProfile2TdmSvcControlExpectPayloadEcid,
				sleGponProfile2TdmSvcControlExpectSignallingEcid, sleGponProfile2TdmSvcControlFarEndIpURL, sleGponProfile2TdmSvcControlMplsLabelIndicator, sleGponProfile2TdmSvcControlMplsPwDirection, sleGponProfile2TdmSvcControlMplsPwLabelUp,
				sleGponProfile2TdmSvcControlMplsPwLabelDown, sleGponProfile2TdmSvcControlMplsPwLabelExp, sleGponProfile2TdmSvcControlMplsPwTunnelDirection, sleGponProfile2TdmSvcControlMplsPwTunnelLabelUp, sleGponProfile2TdmSvcControlMplsPwTunnelLabelDown,
				sleGponProfile2TdmSvcControlMplsPwTunnelLabelExp, sleGponProfile2TdmSvcControlCesBuffCdvTolerance, sleGponProfile2TdmSvcControlCesChannelAssociateSignal, sleGponProfileTdmSdhIndex, sleGponProfileTdmSdhName,
				sleGponProfileTdmSdhTuType, sleGponProfileTdmSdhGemLossIntergrationPeriod, sleGponProfileTdmSdhTransmitJ1J2, sleGponProfileTdmSdhExpectJ1J2, sleGponProfileTdmSdhReceiveJ1J2,
				sleGponProfileTdmSdhTimMonitor, sleGponProfileTdmSdhTimAis, sleGponProfileTdmSdhControlRequest, sleGponProfileTdmSdhControlStatus, sleGponProfileTdmSdhControlTimer,
				sleGponProfileTdmSdhControlTimeStamp, sleGponProfileTdmSdhControlReqResult, sleGponProfileTdmSdhControlIndex, sleGponProfileTdmSdhControlName, sleGponProfileTdmSdhControlTuType,
				sleGponProfileTdmSdhControlGemLossIntergrationPeriod, sleGponProfileTdmSdhControlTransmitJ1J2, sleGponProfileTdmSdhControlExpectJ1J2, sleGponProfileTdmSdhControlReceiveJ1J2, sleGponProfileTdmSdhControlTimMonitor,
				sleGponProfileTdmSdhControlTimAis, sleGponOnuPortId, sleGponOnuPMStatsDetailGEMPort, sleGponOnuPMStatsDetailGEMPre15mLostPackets, sleGponOnuPMStatsDetailGEMPre15mMisInsertedPackets,
				sleGponOnuPMStatsDetailGEMPre15mReceivedPackets, sleGponOnuPMStatsDetailGEMPre15mReceivedBlocks, sleGponOnuPMStatsDetailGEMPre15mTransmittedBlocks, sleGponOnuPMStatsDetailGEMPre15mImpairedBlocks, sleGponOnuPMStatsDetailGEMHourLostPackets,
				sleGponOnuPMStatsDetailGEMHourMisInsertedPackets, sleGponOnuPMStatsDetailGEMHourReceivedPackets, sleGponOnuPMStatsDetailGEMHourReceivedBlocks, sleGponOnuPMStatsDetailGEMHourTransmittedBlocks, sleGponOnuPMStatsDetailGEMHourImpairedBlocks,
				sleGponOnuPMStatsDetailGEMDayLostPackets, sleGponOnuPMStatsDetailGEMDayMisInsertedPackets, sleGponOnuPMStatsDetailGEMDayReceivedPackets, sleGponOnuPMStatsDetailGEMDayReceivedBlocks, sleGponOnuPMStatsDetailGEMDayTransmittedBlocks,
				sleGponOnuPMStatsDetailGEMDayImpairedBlocks, sleGponOnuPMStatsDetailGEMTotalLostPackets, sleGponOnuPMStatsDetailGEMTotalMisInsertedPackets, sleGponOnuPMStatsDetailGEMTotalReceivedPackets, sleGponOnuPMStatsDetailGEMTotalReceivedBlocks,
				sleGponOnuPMStatsDetailGEMTotalTransmittedBlocks, sleGponOnuPMStatsDetailGEMTotalImpairedBlocks, sleGponOnuPMStatsDetailGEMElapsedTimeAfterClear, sleGponOnuPMStatsDetailGEMElapsedTimeAfterUpdate, sleGponOnuPMStatsDetailAniPort,
				sleGponOnuPMStatsDetailAniPre15mDiscardedFrames, sleGponOnuPMStatsDetailAniHourDiscardedFrames, sleGponOnuPMStatsDetailAniDayDiscardedFrames, sleGponOnuPMStatsDetailAniTotalDiscardedFrames, sleGponOnuPMStatsDetailAniElapsedTimeAfterClear,
				sleGponOnuPMStatsDetailAniElapsedTimeAfterUpdate, sleGponOnuPMStatsDetailUniEthFrameUpUniPort, sleGponOnuPMStatsDetailUniEthFrameUpPre15mDropEvents, sleGponOnuPMStatsDetailUniEthFrameUpPre15mOctets, sleGponOnuPMStatsDetailUniEthFrameUpPre15mPackets,
				sleGponOnuPMStatsDetailUniEthFrameUpPre15mBcastPackets, sleGponOnuPMStatsDetailUniEthFrameUpPre15mMcastPackets, sleGponOnuPMStatsDetailUniEthFrameUpPre15mUcastPackets, sleGponOnuPMStatsDetailUniEthFrameUpPre15mCRCErroredPackets, sleGponOnuPMStatsDetailUniEthFrameUpPre15mUndersizePackets,
				sleGponOnuPMStatsDetailUniEthFrameUpPre15mOversizePackets, sleGponOnuPMStatsDetailUniEthFrameUpPre15mPkt64Octets, sleGponOnuPMStatsDetailUniEthFrameUpPre15mPkt65To127Octets, sleGponOnuPMStatsDetailUniEthFrameUpPre15mPkt128To255Octets, sleGponOnuPMStatsDetailUniEthFrameUpPre15mPkt256To511Octets,
				sleGponOnuPMStatsDetailUniEthFrameUpPre15mPkt512To1023Octets, sleGponOnuPMStatsDetailUniEthFrameUpPre15mPkt1024To1518Octets, sleGponOnuPMStatsDetailUniEthFrameUpHourDropEvents, sleGponOnuPMStatsDetailUniEthFrameUpHourOctets, sleGponOnuPMStatsDetailUniEthFrameUpHourPackets,
				sleGponOnuPMStatsDetailUniEthFrameUpHourBcastPackets, sleGponOnuPMStatsDetailUniEthFrameUpHourMcastPackets, sleGponOnuPMStatsDetailUniEthFrameUpHourUcastPackets, sleGponOnuPMStatsDetailUniEthFrameUpHourCRCErroredPackets, sleGponOnuPMStatsDetailUniEthFrameUpHourUndersizePackets,
				sleGponOnuPMStatsDetailUniEthFrameUpHourOversizePackets, sleGponOnuPMStatsDetailUniEthFrameUpHourPkt64Octets, sleGponOnuPMStatsDetailUniEthFrameUpHourPkt65To127Octets, sleGponOnuPMStatsDetailUniEthFrameUpHourPkt128To255Octets, sleGponOnuPMStatsDetailUniEthFrameUpHourPkt256To511Octets,
				sleGponOnuPMStatsDetailUniEthFrameUpHourPkt512To1023Octets, sleGponOnuPMStatsDetailUniEthFrameUpHourPkt1024To1518Octets, sleGponOnuPMStatsDetailUniEthFrameUpDayDropEvents, sleGponOnuPMStatsDetailUniEthFrameUpDayOctets, sleGponOnuPMStatsDetailUniEthFrameUpDayPackets,
				sleGponOnuPMStatsDetailUniEthFrameUpDayBcastPackets, sleGponOnuPMStatsDetailUniEthFrameUpDayMcastPackets, sleGponOnuPMStatsDetailUniEthFrameUpDayUcastPackets, sleGponOnuPMStatsDetailUniEthFrameUpDayCRCErroredPackets, sleGponOnuPMStatsDetailUniEthFrameUpDayUndersizePackets,
				sleGponOnuPMStatsDetailUniEthFrameUpDayOversizePackets, sleGponOnuPMStatsDetailUniEthFrameUpDayPkt64Octets, sleGponOnuPMStatsDetailUniEthFrameUpDayPkt65To127Octets, sleGponOnuPMStatsDetailUniEthFrameUpDayPkt128To255Octets, sleGponOnuPMStatsDetailUniEthFrameUpDayPkt256To511Octets,
				sleGponOnuPMStatsDetailUniEthFrameUpDayPkt512To1023Octets, sleGponOnuPMStatsDetailUniEthFrameUpDayPkt1024To1518Octets, sleGponOnuPMStatsDetailUniEthFrameUpTotalDropEvents, sleGponOnuPMStatsDetailUniEthFrameUpTotalOctets, sleGponOnuPMStatsDetailUniEthFrameUpTotalPackets,
				sleGponOnuPMStatsDetailUniEthFrameUpTotalBcastPackets, sleGponOnuPMStatsDetailUniEthFrameUpTotalMcastPackets, sleGponOnuPMStatsDetailUniEthFrameUpTotalUcastPackets, sleGponOnuPMStatsDetailUniEthFrameUpTotalCRCErroredPackets, sleGponOnuPMStatsDetailUniEthFrameUpTotalUndersizePackets,
				sleGponOnuPMStatsDetailUniEthFrameUpTotalOversizePackets, sleGponOnuPMStatsDetailUniEthFrameUpTotalPkt64Octets, sleGponOnuPMStatsDetailUniEthFrameUpTotalPkt65To127Octets, sleGponOnuPMStatsDetailUniEthFrameUpTotalPkt128To255Octets, sleGponOnuPMStatsDetailUniEthFrameUpTotalPkt256To511Octets,
				sleGponOnuPMStatsDetailUniEthFrameUpTotalPkt512To1023Octets, sleGponOnuPMStatsDetailUniEthFrameUpTotalPkt1024To1518Octets, sleGponOnuPMStatsDetailUniEthFrameUpElapsedTimeAfterClear, sleGponOnuPMStatsDetailUniEthFrameUpElapsedTimeAfterUpdate, sleGponOnuPMStatsDetailUniEthFrameDownUniPort,
				sleGponOnuPMStatsDetailUniEthFrameDownPre15mDropEvents, sleGponOnuPMStatsDetailUniEthFrameDownPre15mOctets, sleGponOnuPMStatsDetailUniEthFrameDownPre15mPackets, sleGponOnuPMStatsDetailUniEthFrameDownPre15mBcastPackets, sleGponOnuPMStatsDetailUniEthFrameDownPre15mMcastPackets,
				sleGponOnuPMStatsDetailUniEthFrameDownPre15mUcastPackets, sleGponOnuPMStatsDetailUniEthFrameDownPre15mCRCErroredPackets, sleGponOnuPMStatsDetailUniEthFrameDownPre15mUndersizePackets, sleGponOnuPMStatsDetailUniEthFrameDownPre15mOversizePackets, sleGponOnuPMStatsDetailUniEthFrameDownPre15mPkt64Octets,
				sleGponOnuPMStatsDetailUniEthFrameDownPre15mPkt65To127Octets, sleGponOnuPMStatsDetailUniEthFrameDownPre15mPkt128To255Octets, sleGponOnuPMStatsDetailUniEthFrameDownPre15mPkt256To511Octets, sleGponOnuPMStatsDetailUniEthFrameDownPre15mPkt512To1023Octets, sleGponOnuPMStatsDetailUniEthFrameDownPre15mPkt1024To1518Octets,
				sleGponOnuPMStatsDetailUniEthFrameDownHourDropEvents, sleGponOnuPMStatsDetailUniEthFrameDownHourOctets, sleGponOnuPMStatsDetailUniEthFrameDownHourPackets, sleGponOnuPMStatsDetailUniEthFrameDownHourBcastPackets, sleGponOnuPMStatsDetailUniEthFrameDownHourMcastPackets,
				sleGponOnuPMStatsDetailUniEthFrameDownHourUcastPackets, sleGponOnuPMStatsDetailUniEthFrameDownHourCRCErroredPackets, sleGponOnuPMStatsDetailUniEthFrameDownHourUndersizePackets, sleGponOnuPMStatsDetailUniEthFrameDownHourOversizePackets, sleGponOnuPMStatsDetailUniEthFrameDownHourPkt64Octets,
				sleGponOnuPMStatsDetailUniEthFrameDownHourPkt65To127Octets, sleGponOnuPMStatsDetailUniEthFrameDownHourPkt128To255Octets, sleGponOnuPMStatsDetailUniEthFrameDownHourPkt256To511Octets, sleGponOnuPMStatsDetailUniEthFrameDownHourPkt512To1023Octets, sleGponOnuPMStatsDetailUniEthFrameDownHourPkt1024To1518Octets,
				sleGponOnuPMStatsDetailUniEthFrameDownDayDropEvents, sleGponOnuPMStatsDetailUniEthFrameDownDayOctets, sleGponOnuPMStatsDetailUniEthFrameDownDayPackets, sleGponOnuPMStatsDetailUniEthFrameDownDayBcastPackets, sleGponOnuPMStatsDetailUniEthFrameDownDayMcastPackets,
				sleGponOnuPMStatsDetailUniEthFrameDownDayUcastPackets, sleGponOnuPMStatsDetailUniEthFrameDownDayCRCErroredPackets, sleGponOnuPMStatsDetailUniEthFrameDownDayUndersizePackets, sleGponOnuPMStatsDetailUniEthFrameDownDayOversizePackets, sleGponOnuPMStatsDetailUniEthFrameDownDayPkt64Octets,
				sleGponOnuPMStatsDetailUniEthFrameDownDayPkt65To127Octets, sleGponOnuPMStatsDetailUniEthFrameDownDayPkt128To255Octets, sleGponOnuPMStatsDetailUniEthFrameDownDayPkt256To511Octets, sleGponOnuPMStatsDetailUniEthFrameDownDayPkt512To1023Octets, sleGponOnuPMStatsDetailUniEthFrameDownDayPkt1024To1518Octets,
				sleGponOnuPMStatsDetailUniEthFrameDownTotalDropEvents, sleGponOnuPMStatsDetailUniEthFrameDownTotalOctets, sleGponOnuPMStatsDetailUniEthFrameDownTotalPackets, sleGponOnuPMStatsDetailUniEthFrameDownTotalBcastPackets, sleGponOnuPMStatsDetailUniEthFrameDownTotalMcastPackets,
				sleGponOnuPMStatsDetailUniEthFrameDownTotalUcastPackets, sleGponOnuPMStatsDetailUniEthFrameDownTotalCRCErroredPackets, sleGponOnuPMStatsDetailUniEthFrameDownTotalUndersizePackets, sleGponOnuPMStatsDetailUniEthFrameDownTotalOversizePackets, sleGponOnuPMStatsDetailUniEthFrameDownTotalPkt64Octets,
				sleGponOnuPMStatsDetailUniEthFrameDownTotalPkt65To127Octets, sleGponOnuPMStatsDetailUniEthFrameDownTotalPkt128To255Octets, sleGponOnuPMStatsDetailUniEthFrameDownTotalPkt256To511Octets, sleGponOnuPMStatsDetailUniEthFrameDownTotalPkt512To1023Octets, sleGponOnuPMStatsDetailUniEthFrameDownTotalPkt1024To1518Octets,
				sleGponOnuPMStatsDetailUniEthFrameDownElapsedTimeAfterClear, sleGponOnuPMStatsDetailUniEthFrameDownElapsedTimeAfterUpdate, sleGponOnuPMStatsDetailUniEth3UniPort, sleGponOnuPMStatsDetailUniEth3Pre15mDropEvents, sleGponOnuPMStatsDetailUniEth3Pre15mOctets,
				sleGponOnuPMStatsDetailUniEth3Pre15mPackets, sleGponOnuPMStatsDetailUniEth3Pre15mBcastPackets, sleGponOnuPMStatsDetailUniEth3Pre15mMcastPackets, sleGponOnuPMStatsDetailUniEth3Pre15mUcastPackets, sleGponOnuPMStatsDetailUniEth3Pre15mUndersizePackets,
				sleGponOnuPMStatsDetailUniEth3Pre15mFragments, sleGponOnuPMStatsDetailUniEth3Pre15mJabbers, sleGponOnuPMStatsDetailUniEth3Pre15mPkt64Octets, sleGponOnuPMStatsDetailUniEth3Pre15mPkt65To127Octets, sleGponOnuPMStatsDetailUniEth3Pre15mPkt128To255Octets,
				sleGponOnuPMStatsDetailUniEth3Pre15mPkt256To511Octets, sleGponOnuPMStatsDetailUniEth3Pre15mPkt512To1023Octets, sleGponOnuPMStatsDetailUniEth3Pre15mPkt1024To1518Octets, sleGponOnuPMStatsDetailUniEth3HourDropEvents, sleGponOnuPMStatsDetailUniEth3HourOctets,
				sleGponOnuPMStatsDetailUniEth3HourPackets, sleGponOnuPMStatsDetailUniEth3HourBcastPackets, sleGponOnuPMStatsDetailUniEth3HourMcastPackets, sleGponOnuPMStatsDetailUniEth3HourUcastPackets, sleGponOnuPMStatsDetailUniEth3HourUndersizePackets,
				sleGponOnuPMStatsDetailUniEth3HourFragments, sleGponOnuPMStatsDetailUniEth3HourJabbers, sleGponOnuPMStatsDetailUniEth3HourPkt64Octets, sleGponOnuPMStatsDetailUniEth3HourPkt65To127Octets, sleGponOnuPMStatsDetailUniEth3HourPkt128To255Octets,
				sleGponOnuPMStatsDetailUniEth3HourPkt256To511Octets, sleGponOnuPMStatsDetailUniEth3HourPkt512To1023Octets, sleGponOnuPMStatsDetailUniEth3HourPkt1024To1518Octets, sleGponOnuPMStatsDetailUniEth3DayDropEvents, sleGponOnuPMStatsDetailUniEth3DayOctets,
				sleGponOnuPMStatsDetailUniEth3DayPackets, sleGponOnuPMStatsDetailUniEth3DayBcastPackets, sleGponOnuPMStatsDetailUniEth3DayMcastPackets, sleGponOnuPMStatsDetailUniEth3DayUcastPackets, sleGponOnuPMStatsDetailUniEth3DayUndersizePackets,
				sleGponOnuPMStatsDetailUniEth3DayFragments, sleGponOnuPMStatsDetailUniEth3DayJabbers, sleGponOnuPMStatsDetailUniEth3DayPkt64Octets, sleGponOnuPMStatsDetailUniEth3DayPkt65To127Octets, sleGponOnuPMStatsDetailUniEth3DayPkt128To255Octets,
				sleGponOnuPMStatsDetailUniEth3DayPkt256To511Octets, sleGponOnuPMStatsDetailUniEth3DayPkt512To1023Octets, sleGponOnuPMStatsDetailUniEth3DayPkt1024To1518Octets, sleGponOnuPMStatsDetailUniEth3TotalDropEvents, sleGponOnuPMStatsDetailUniEth3TotalOctets,
				sleGponOnuPMStatsDetailUniEth3TotalPackets, sleGponOnuPMStatsDetailUniEth3TotalBcastPackets, sleGponOnuPMStatsDetailUniEth3TotalMcastPackets, sleGponOnuPMStatsDetailUniEth3TotalUcastPackets, sleGponOnuPMStatsDetailUniEth3TotalUndersizePackets,
				sleGponOnuPMStatsDetailUniEth3TotalFragments, sleGponOnuPMStatsDetailUniEth3TotalJabbers, sleGponOnuPMStatsDetailUniEth3TotalPkt64Octets, sleGponOnuPMStatsDetailUniEth3TotalPkt65To127Octets, sleGponOnuPMStatsDetailUniEth3TotalPkt128To255Octets,
				sleGponOnuPMStatsDetailUniEth3TotalPkt256To511Octets, sleGponOnuPMStatsDetailUniEth3TotalPkt512To1023Octets, sleGponOnuPMStatsDetailUniEth3TotalPkt1024To1518Octets, sleGponOnuPMStatsDetailUniEth3ElapsedTimeAfterClear, sleGponOnuPMStatsDetailUniEth3ElapsedTimeAfterUpdate,
				sleGponProfile2PMProfilePMUniEthFrameUp, sleGponProfile2PMProfilePMUniEthFrameDown, sleGponProfile2PMProfilePMUniEth3, sleGponProfile2PMProfileControlPMUniEthFrameUp, sleGponProfile2PMProfileControlPMUniEthFrameDown,
				sleGponProfile2PMProfileControlPMUniEth3, sleGponOnuPortsID, sleGponProfileVoIPIpPathAuthName, sleGponProfileVoIPIpPathAuthPasswd, sleGponProfileVoIPIpwayAuthName,
				sleGponProfileVoIPIpwayAuthPasswd, sleGponProfileVoIPIpwayURL, sleGponProfileVoIPControlIpwayAuthName, sleGponProfileVoIPControlIpwayAuthPasswd, sleGponProfileVoIPControlIpwayURL,
				sleGponProfileVoIPDetailIndex, sleGponProfileVoIPDetailName, sleGponProfileVoIPDetailFaxMode, sleGponProfileVoIPDetailCodecType1st, sleGponProfileVoIPDetailCodecPeriod1st,
				sleGponProfileVoIPDetailCodecSilenceSuppression1st, sleGponProfileVoIPDetailCodecType2nd, sleGponProfileVoIPDetailCodecPeriod2nd, sleGponProfileVoIPDetailCodecSilenceSuppression2nd, sleGponProfileVoIPDetailCodecType3rd,
				sleGponProfileVoIPDetailCodecPeriod3rd, sleGponProfileVoIPDetailCodecSilenceSuppression3rd, sleGponProfileVoIPDetailCodecType4th, sleGponProfileVoIPDetailCodecPeriod4th, sleGponProfileVoIPDetailCodecSilenceSuppression4th,
				sleGponProfileVoIPDetailOobdtmf, sleGponProfileVoIPDetailAnnouncementType, sleGponProfileVoIPDetailJitterTarget, sleGponProfileVoIPDetailJitterBuffMax, sleGponProfileVoIPDetailEchoCancel,
				sleGponProfileVoIPDetailPstnProtoVariant, sleGponProfileVoIPDetailDtmfDigitLevels, sleGponProfileVoIPDetailDtmfDigitDuration, sleGponProfileVoIPDetailHookFlashTimeMin, sleGponProfileVoIPDetailHookFlashTimeMax,
				sleGponProfileVoIPDetailSignalingCode, sleGponProfileVoIPDetailRtpLocalPortMin, sleGponProfileVoIPDetailRtpLocalPortMax, sleGponProfileVoIPDetailRtpDscpMark, sleGponProfileVoIPDetailRtpPiggybackEvent,
				sleGponProfileVoIPDetailRtpToneEvent, sleGponProfileVoIPDetailRtpDtmfEvent, sleGponProfileVoIPDetailRtpCasEvent, sleGponProfileVoIPDetailProtocol, sleGponProfileVoIPDetailMgcPriServer,
				sleGponProfileVoIPDetailMgcSecServer, sleGponProfileVoIPDetailMgcMsgVersion, sleGponProfileVoIPDetailMgcMsgFormat, sleGponProfileVoIPDetailMgcMaxRetryTime, sleGponProfileVoIPDetailMgcSvcChangeDelay,
				sleGponProfileVoIPDetailMgcTerminationId, sleGponProfileVoIPDetailMgcSoftswitch, sleGponProfileVoIPDetailVoicemailServer, sleGponProfileVoIPDetailVoicemmailExpireTime, sleGponProfileVoIPDetailReleaseTime,
				sleGponProfileVoIPDetailRohTimer, sleGponProfileVoIPDetailProxyServer, sleGponProfileVoIPDetailOutboundProxyServer, sleGponProfileVoIPDetailRegisterServer, sleGponProfileVoIPDetailHostPartServer,
				sleGponProfileVoIPDetailPriDns, sleGponProfileVoIPDetailSecDns, sleGponProfileVoIPDetailRegExpTime, sleGponProfileVoIPDetailReregHeadStartTime, sleGponProfileVoIPDetailSoftSwitchVendor,
				sleGponProfileVoIPDetailSipOptionTransmitCtl, sleGponProfileVoIPDetailSipUriFormat, sleGponProfileVoIPDetailCallerId, sleGponProfileVoIPDetailCallWaiting, sleGponProfileVoIPDetailCallProgressTransfer,
				sleGponProfileVoIPDetailCallPresent, sleGponProfileVoIPDetailDirectConnect, sleGponProfileVoIPDetailDirectConnectUri, sleGponProfileVoIPDetailBridgedLineAgentUri, sleGponProfileVoIPDetailConferenceFactoryUri,
				sleGponProfileVoIPDetailCancelCallWait, sleGponProfileVoIPDetailCallPark, sleGponProfileVoIPDetailCallerIdAct, sleGponProfileVoIPDetailCallerIdDeact, sleGponProfileVoIPDetailDoNotDisturbAct,
				sleGponProfileVoIPDetailDoNotDisturbDeact, sleGponProfileVoIPDetailDoNotDisturbPinChange, sleGponProfileVoIPDetailEmergServiceNumber, sleGponProfileVoIPDetailIntercomService, sleGponProfileVoIPDetailControlRequest,
				sleGponProfileVoIPDetailControlStatus, sleGponProfileVoIPDetailControlTimer, sleGponProfileVoIPDetailControlTimeStamp, sleGponProfileVoIPDetailControlReqResult, sleGponProfileVoIPDetailControlIndex,
				sleGponProfileVoIPDetaiControllName, sleGponProfileVoIPDetailControlFaxMode, sleGponProfileVoIPDetailControlOobdtmf, sleGponProfileVoIPDetailControlAnnouncementType, sleGponProfileVoIPDetailControlJitterTarget,
				sleGponProfileVoIPDetailControlJitterBuffMax, sleGponProfileVoIPDetailControlEchoCancel, sleGponProfileVoIPDetailControlPstnProtoVariant, sleGponProfileVoIPDetailControlDtmfDigitLevels, sleGponProfileVoIPDetailControlDtmfDigitDuration,
				sleGponProfileVoIPDetailControlHookFlashTimeMin, sleGponProfileVoIPDetailControlHookFlashTimeMax, sleGponProfileVoIPDetailControlSignalingCode, sleGponProfileVoIPDetailControlRtpLocalPortMin, sleGponProfileVoIPDetailControlRtpLocalPortMax,
				sleGponProfileVoIPDetailControlRtpDscpMark, sleGponProfileVoIPDetailControlRtpPiggybackEvent, sleGponProfileVoIPDetailControlRtpToneEvent, sleGponProfileVoIPDetailControlRtpDtmfEvent, sleGponProfileVoIPDetailControlRtpCasEvent,
				sleGponProfileVoIPDetailControlProtocol, sleGponProfileVoIPDetailControlMgcPriServer, sleGponProfileVoIPDetailControlMgcSecServer, sleGponProfileVoIPDetailControlMgcMsgVersion, sleGponProfileVoIPDetailControlMgcMsgFormat,
				sleGponProfileVoIPDetailControlMgcMaxRetryTime, sleGponProfileVoIPDetailControlMgcSvcChangeDelay, sleGponProfileVoIPDetailControlMgcTerminationId, sleGponProfileVoIPDetailControlMgcSoftswitch, sleGponProfileVoIPDetailControlVoicemailServer,
				sleGponProfileVoIPDetailControlVoicemmailExpireTime, sleGponProfileVoIPDetailControlReleaseTime, sleGponProfileVoIPDetailControlRohTimer, sleGponProfileVoIPDetailControlProxyServer, sleGponProfileVoIPDetailControlOutboundProxyServer,
				sleGponProfileVoIPDetailControlRegisterServer, sleGponProfileVoIPDetailControlHostPartServer, sleGponProfileVoIPDetailControlPriDns, sleGponProfileVoIPDetailControlSecDns, sleGponProfileVoIPDetailControlRegExpTime,
				sleGponProfileVoIPDetailControlReregHeadStartTime, sleGponProfileVoIPDetailControlSoftSwitchVendor, sleGponProfileVoIPDetailControlSipOptionTransmitCtl, sleGponProfileVoIPDetailControlSipUriFormat, sleGponProfileVoIPDetailControlCallerId,
				sleGponProfileVoIPDetailControlCallWaiting, sleGponProfileVoIPDetailControlCallProgressTransfer, sleGponProfileVoIPDetailControlCallPresent, sleGponProfileVoIPDetailControlDirectConnect, sleGponProfileVoIPDetailControlDirectConnectUri,
				sleGponProfileVoIPDetailControlBridgedLineAgentUri, sleGponProfileVoIPDetailControlConferenceFactoryUri, sleGponProfileVoIPDetailControlCancelCallWait, sleGponProfileVoIPDetailControlCallerIdAct, sleGponProfileVoIPDetailControlCallerIdDeact,
				sleGponProfileVoIPDetailControlDoNotDisturbAct, sleGponProfileVoIPDetailControlDoNotDisturbDeact, sleGponProfileVoIPDetailControlDoNotDisturbPinChange, sleGponProfileVoIPDetailControlEmergServiceNumber, sleGponProfileVoIPDetailControlIntercomService,
				sleGponProfile2BridgeUniMaxHost, sleGponProfile2BridgeUniControlMaxHost, sleGponProfile2BridgeGemId, sleGponProfile2BridgeGemVlanFilterMode, sleGponProfile2BridgeGemVlanFilter,
				sleGponProfile2BridgeGemControlRequest, sleGponProfile2BridgeGemControlStatus, sleGponProfile2BridgeGemControlTimer, sleGponProfile2BridgeGemControlTimeStamp, sleGponProfile2BridgeGemControlReqResult,
				sleGponProfile2BridgeGemControlTName, sleGponProfile2BridgeGemControlBridgeId, sleGponProfile2BridgeGemControlId, sleGponProfile2BridgeGemControlVlanFilterMode, sleGponProfile2BridgeGemControlVlanFilter,
				sleGponProfile2BridgeTdmId, sleGponProfile2BridgeTdmControlRequest, sleGponProfile2BridgeTdmControlStatus, sleGponProfile2BridgeTdmControlTimer, sleGponProfile2BridgeTdmControlTimeStamp,
				sleGponProfile2BridgeTdmControlReqResult, sleGponProfile2BridgeTdmControlTName, sleGponProfile2BridgeTdmControlBridgeId, sleGponProfile2BridgeTdmControlId, sleGponProfileVoIPIpPathURL,
				sleGponProfile2IpHostSvcId, sleGponProfile2IpHostSvcAddressType, sleGponProfile2IpHostSvcPriDns, sleGponProfile2IpHostSvcSecDns, sleGponProfile2IpHostSvcVlanFilterMode,
				sleGponProfile2IpHostSvcVlanFilter, sleGponProfile2IpHostSvcVlanOpDsOperFlag, sleGponProfile2IpHostSvcVlanOpUsOperFlag, sleGponProfile2IpHostSvcVlanOpUsOperVid, sleGponProfile2IpHostSvcVlanOpUsOperCos,
				sleGponProfile2IpHostSvcControlRequest, sleGponProfile2IpHostSvcControlStatus, sleGponProfile2IpHostSvcControlTimer, sleGponProfile2IpHostSvcControlTimeStamp, sleGponProfile2IpHostSvcControlReqResult,
				sleGponProfile2IpHostSvcControlTName, sleGponProfile2IpHostSvcControlId, sleGponProfile2IpHostSvcControlAddressType, sleGponProfile2IpHostSvcControlPriDns, sleGponProfile2IpHostSvcControlSecDns,
				sleGponProfile2IpHostSvcControlVlanFilterMode, sleGponProfile2IpHostSvcControlVlanFilter, sleGponProfile2IpHostSvcControlVlanOpDsOperFlag, sleGponProfile2IpHostSvcControlVlanOpUsOperFlag, sleGponProfile2IpHostSvcControlVlanOpUsOperVid,
				sleGponProfile2IpHostSvcControlVlanOpUsOperCos, sleGponProfile2IpHostTdmId, sleGponProfile2IpHostTdmControlRequest, sleGponProfile2IpHostTdmControlTimer, sleGponProfile2IpHostTdmControlTimeStamp,
				sleGponProfile2IpHostTdmControlReqResult, sleGponProfile2IpHostTdmControlTName, sleGponProfile2IpHostVoipControlRequest, sleGponProfile2IpHostVoipControlStatus, sleGponProfile2IpHostVoipControlTimer,
				sleGponProfile2IpHostVoipControlTimeStamp, sleGponProfile2IpHostVoipControlReqResult, sleGponProfile2IpHostVoipControlTName, sleGponProfile2IpHostVoipControlIpHostSvcId, sleGponProfile2IpHostVoipControlId,
				sleGponProfile2IpHostVoipId, sleGponProfile2IpHostTdmControlStatus, sleGponProfile2IpHostTdmControlIpHostSvcId, sleGponProfile2VoipSvcId, sleGponProfile2VoipSvcManageMethod,
				sleGponProfile2VoipSvcProtocol, sleGponProfile2VoipSvcIppathUrl, sleGponProfile2VoipSvcIppathUser, sleGponProfile2VoipSvcIppathPasswd, sleGponProfile2VoipSvcControlRequest,
				sleGponProfile2VoipSvcControlStatus, sleGponProfile2VoipSvcControlTimer, sleGponProfile2VoipSvcControlTimeStamp, sleGponProfile2VoipSvcControlReqResult, sleGponProfile2VoipSvcControlTName,
				sleGponProfile2VoipSvcControlId, sleGponProfile2VoipSvcControlManageMethod, sleGponProfile2VoipSvcControlProtocol, sleGponProfile2VoipSvcControlIppathUrl, sleGponProfile2VoipSvcControlIppathUser,
				sleGponProfile2VoipSvcControlIppathPasswd, sleGponProfile2VoipSvcUniType, sleGponProfile2VoipSvcUniId, sleGponProfile2VoipSvcUniImpedance, sleGponProfile2VoipSvcUniTransmissionPath,
				sleGponProfile2VoipSvcUniGainRx, sleGponProfile2VoipSvcUniGainTx, sleGponProfile2VoipSvcUniHoldOverTime, sleGponProfile2VoipSvcUniControlRequest, sleGponProfile2VoipSvcUniControlStatus,
				sleGponProfile2VoipSvcUniControlTimer, sleGponProfile2VoipSvcUniControlTimeStamp, sleGponProfile2VoipSvcUniControlReqResult, sleGponProfile2VoipSvcUniControlTName, sleGponProfile2VoipSvcUniControlVoipSvcId,
				sleGponProfile2VoipSvcUniControlType, sleGponProfile2VoipSvcUniControlId, sleGponProfile2VoipSvcUniControlImpedance, sleGponProfile2VoipSvcUniControlTransmissionPath, sleGponProfile2VoipSvcUniControlGainRx,
				sleGponProfile2VoipSvcUniControlGainTx, sleGponProfile2VoipSvcUniControlHoldOverTime, sleGponProfile2TdmId, sleGponProfile2TdmExpectedType, sleGponProfile2TdmEncoding,
				sleGponProfile2TdmLineLengthPowerFeed, sleGponProfile2TdmDs1Mode, sleGponProfile2TdmLineType, sleGponProfile2TdmControlRequest, sleGponProfile2TdmControlStatus,
				sleGponProfile2TdmControlTimer, sleGponProfile2TdmControlTimeStamp, sleGponProfile2TdmControlReqResult, sleGponProfile2TdmControlTName, sleGponProfile2TdmControlId,
				sleGponProfile2TdmControlExpectedType, sleGponProfile2TdmControlFramig, sleGponProfile2TdmControlEncoding, sleGponProfile2TdmControlLineLengthPowerFeed, sleGponProfile2TdmControlDs1Mode,
				sleGponProfile2TdmControlLineType, sleGponProfile2IpHostTdmControlId, sleGponProfileVoIPDetailControlCallPark, sleGponProfile2TdmSvcFilterMode, sleGponProfile2TdmSvcFilter,
				sleGponProfileVoIPDetailCallHold, sleGponProfileVoIPDetailControlCallHold, sleGponProfileVoIPDetailMgcMaxRetryAttempts, sleGponProfileVoIPDetailControlMgcMaxRetryAttempts, sleGponProfile2OnuCircuitPackCardConfigCDs1E1,
				sleGponProfile2OnuCircuitPackCardConfigCDs1E1J1, sleGponProfile2OnuControlCircuitPackCardConfigCDs1E1, sleGponProfile2BridgeIpHostId, sleGponProfile2BridgeIpHostControlRequest, sleGponProfile2BridgeIpHostControlStatus,
				sleGponProfile2BridgeIpHostControlTimer, sleGponProfile2BridgeIpHostControlTimeStamp, sleGponProfile2BridgeIpHostControlReqResult, sleGponProfile2BridgeIpHostControlTName, sleGponProfile2BridgeIpHostControlBridgeId,
				sleGponProfile2BridgeIpHostControlId, sleGponSystemOltVendorId, sleGponSystemOltVersion, sleGponProfile2OnuControlCircuitPackCardConfigCDs1E1J1, sleGponProfileVoIPDetailControlCodecType1st,
				sleGponProfileVoIPDetailControlCodecPeriod1st, sleGponProfileVoIPDetailControlCodecSilenceSuppression1st, sleGponProfileVoIPDetailControlCodecType2nd, sleGponProfileVoIPDetailControlCodecPeriod2nd, sleGponProfileVoIPDetailControlCodecSilenceSuppression2nd,
				sleGponProfileVoIPDetailControlCodecType3rd, sleGponProfileVoIPDetailControlCodecPeriod3rd, sleGponProfileVoIPDetailControlCodecSilenceSuppression3rd, sleGponProfileVoIPDetailControlCodecType4th, sleGponProfileVoIPDetailCodecControlPeriod4th,
				sleGponProfileVoIPDetailControlCodecSilenceSuppression4th, sleGponProfile2VoipSvcVoipProfile, sleGponProfile2VoipSvcControlVoipProfile, sleGponProfile2TdmSvcControlFilterMode, sleGponOnuVoipAvailSignalProtocol,
				sleGponOnuVoipAvailConfigMethod, sleGponOltAntiSpoofingFilter, sleGponOltControlAntiSpoofingFilter, sleGponOltControlAntiSpoofingExpireTime, sleGponIgmpGroupControlRequest,
				sleGponIgmpGroupControlStatus, sleGponIgmpGroupControlTimer, sleGponIgmpGroupControlTimeStamp, sleGponIgmpGroupControlReqResult, sleGponIgmpGroupControlOltId,
				sleGponIgmpGroupControlOnuId, sleGponProfile2PMProfilePMPseduowire, sleGponProfile2PMProfilePMUniCes, sleGponProfile2PMProfileControlPMPseduowire, sleGponProfile2PMProfileControlPMUniCes,
				sleGponProfile2TdmSvcControlFilter, sleGponSystemOltModel, sleGponSystemOltMac, sleGponSystemOltSlot, sleGponSystemOltPort,
				sleGponSystemOltOnuId, sleGponOltMaxOnuCount, sleGponOltControlMaxOnuCount, sleGponOnuPortHookState, sleGponOnuPortSensedType,
				sleGponOnuVoipLineOltId, sleGponOnuVoipLineOnuId, sleGponOnuVoipLineId, sleGponOnuVoipLineStatus, sleGponOnuVoipLineUsedCodec,
				sleGponOnuVoipLineSessionType, sleGponOnuVoipLine1stProtocolPeriod, sleGponOnuVoipLine1stDestAddr, sleGponOnuVoipLine2ndProtocolPeriod, sleGponOnuVoipLine2ndDestAddr,
				sleGponOnuVoipLineControlRequest, sleGponOnuVoipLineControlStatus, sleGponOnuVoipLineControlTimer, sleGponOnuVoipLineControlTimeStamp, sleGponOnuVoipLineControlReqResult,
				sleGponOnuVoipLineControlOltId, sleGponOnuFWAutoUpgradeModelExclude, sleGponOnuFWAutoUpgradeModelControlExclude, sleGponAntiSpoofingOltId, sleGponAntiSpoofingOnuId,
				sleGponAntiSpoofingVlanId, sleGponAntiSpoofingMacIndex, sleGponAntiSpoofingMac, sleGponAntiSpoofingPortId, sleGponAntiSpoofingDupPortId,
				sleGponAntiSpoofingTimerStatus, sleGponAntiSpoofingControlRequest, sleGponAntiSpoofingControlStatus, sleGponAntiSpoofingControlTimer, sleGponAntiSpoofingControlTimeStamp,
				sleGponAntiSpoofingControlReqResult, sleGponAntiSpoofingControlOltId, sleGponAntiSpoofingControlOnuId, sleGponAntiSpoofingControlVlanId, sleGponAntiSpoofingControlMac,
				sleGponAntiSpoofingControlPortId, sleGponAntiSpoofingControlTimerStatus, sleGponOnuHostPriDns, sleGponOnuHostSecDns, sleGponOnuHostIpOption,
				sleGponOnuHostMacAddress, sleGponOnuHostDomainName, sleGponOnuHostHostName, sleGponOnuHostCurIpAddr, sleGponOnuHostCurMask,
				sleGponOnuHostCurGW, sleGponOnuHostCurPriDns, sleGponOnuHostCurSecDns, sleGponAntiSpoofingFilterStatus, sleGponProfileVoIPDetailDialplanCritTimeout,
				sleGponProfileVoIPDetailDialplanPartTimeout, sleGponProfileVoIPDetailDialplanFormat, sleGponProfileVoIPDetailControlDialplanCritTimeout, sleGponProfileVoIPDetailControlDialplanPartTimeout, sleGponProfileVoIPDetailControlDialplanFormat,
				sleGponProfileVoIPDetailDialPlanTableIndex, sleGponProfileVoIPDetailDialPlanTableToken, sleGponProfileVoIPDetailDialPlanControlRequest, sleGponProfileVoIPDetailDialPlanControlStatus, sleGponProfileVoIPDetailDialPlanControlTimer,
				sleGponProfileVoIPDetailDialPlanControlTimeStamp, sleGponProfileVoIPDetailDialPlanControlReqResult, sleGponProfileVoIPDetailDialPlanControlTableIndex, sleGponProfileVoIPDetailDialPlanControlTableToken, sleGponProfileVoIPDetailDialPlanControlProfileIndex,
				sleGponRedGroupStandbyLinkStatus, sleGponRedGroupSlaveOltAdminStatus, sleGponRedGroupControlStandbyOptic, sleGponRedGroupControlStandbyOpticEnableTime, sleGponRedGroupControlSlaveAdminStatus,
				sleGponRedGroupControlTrigger, sleGponRedGroupTrigger, sleGponIgmpGroupVlanId, sleGponOnuPortUniDescription, sleGponOnuPortControlUniDescription,
				sleGponOnuPortConfSpeed, sleGponOnuPortConfDuplex, sleGponOnuPortControlDuplex, sleGponOnuPortMediumMode, sleGponOnuPortControlMediumMode,
				sleGponOnuVoipLineControlOnuId, sleGponOltAntiSpoofingExpireTime, sleGponOnuFWAutoUpgradeBaseRetryCounts, sleGponOnuFWAutoUpgradeControlBaseRequest, sleGponOnuFWAutoUpgradeControlBaseStatus,
				sleGponOnuFWAutoUpgradeControlBaseTimer, sleGponOnuFWAutoUpgradeControlBaseReqResult, sleGponOnuFWAutoUpgradeControlBaseCount, sleGponOltBwBEMethod, sleGponOltDsGemMapping,
				sleGponOltControlBwBEMethod, sleGponOltControlDsGemMapping, sleGponProfile2BridgeUniExtVlanName, sleGponProfile2BridgeUniControlExtVlanName, sleGponProfile2IpHostSvcExtVlanName,
				sleGponProfile2IpHostSvcControlExtVlanName, sleGponVlanGemMappingVid, sleGponVlanGemMappingMapperId, sleGponVlanGemMappingControlRequest, sleGponVlanGemMappingControlStatus,
				sleGponVlanGemMappingControlTimer, sleGponVlanGemMappingControlTimeStamp, sleGponVlanGemMappingControlReqResult, sleGponVlanGemMappingControlOltId, sleGponVlanGemMappingControlOnuId,
				sleGponProfile2ExtVlanIndex, sleGponProfile2ExtVlanName, sleGponProfile2ExtVlanDownStreamMode, sleGponProfile2ExtVlanDscpToCosMapTable, sleGponProfile2ExtVlanTpidInput,
				sleGponProfile2ExtVlanTpidOutput, sleGponProfile2ExtVlanControlRequest, sleGponProfile2ExtVlanControlStatus, sleGponProfile2ExtVlanControlTimer, sleGponProfile2ExtVlanControlTimeStamp,
				sleGponProfile2ExtVlanControlReqResult, sleGponProfile2ExtVlanControlName, sleGponProfile2ExtVlanControlDownStreamMode, sleGponProfile2ExtVlanControlDscpToCosMapTable, sleGponProfile2ExtVlanControlTpidInput,
				sleGponProfile2ExtVlanControlTpidOutput, sleGponProfile2TdmFraming, sleGponOnuPortLoopbackStatus, sleGponOnuPortControlLoopbackStatus, sleGponProfile2ExtVlanTagType,
				sleGponProfile2ExtVlanTagIndex, sleGponProfile2ExtVlanTagFilterEtherType, sleGponProfile2ExtVlanTagTreatInnerCopyVid, sleGponProfile2ExtVlanTagTreatInnerCopyCos, sleGponProfile2ExtVlanTagTreatOuterCopyVid,
				sleGponProfile2ExtVlanTagTreatOuterCopyCos, sleGponProfile2ExtVlanTagTreatTag, sleGponProfile2ExtVlanTagFilterInnerVid, sleGponProfile2ExtVlanTagFilterInnerCos, sleGponProfile2ExtVlanTagFilterInnerTpidDei,
				sleGponProfile2ExtVlanTagFilterOuterVid, sleGponProfile2ExtVlanTagFilterOuterCos, sleGponProfile2ExtVlanTagFilterOuterTpidDei, sleGponProfile2ExtVlanTagControlRequest, sleGponProfile2ExtVlanTagControlStatus,
				sleGponProfile2ExtVlanTagControlTimer, sleGponProfile2ExtVlanTagControlTimeStamp, sleGponProfile2ExtVlanTagControlReqResult, sleGponProfile2ExtVlanTagControlType, sleGponProfile2ExtVlanTagControlIndex,
				sleGponProfile2ExtVlanTagControlFilterEtherType, sleGponProfile2ExtVlanTagControlTreatInnerCopyVid, sleGponProfile2ExtVlanTagControlTreatInnerCopyCos, sleGponProfile2ExtVlanTagControlTreatOuterCopyVid, sleGponProfile2ExtVlanTagControlTreatOuterCopyCos,
				sleGponProfile2ExtVlanTagControlTreatTag, sleGponProfile2ExtVlanTagControlFilterInnerCos, sleGponProfile2ExtVlanTagControlFilterInnerTpidDei, sleGponProfile2ExtVlanTagControlFilterOuterVid, sleGponProfile2ExtVlanTagControlFilterOuterCos,
				sleGponGemPortId, sleGponGemPortMapperId, sleGponGemPortCos, sleGponProfile2ExtVlanTagTreatInnerTpidDei, sleGponProfile2ExtVlanTagTreatOuterTpidDei,
				sleGponProfile2ExtVlanTagControlTreatInnerTpidDei, sleGponProfile2ExtVlanTagControlTreatOuterTpidDei, sleGponGemPortNum, sleGponVlanGemMappingOnuid, sleGponVlanGemMappingGemPort,
				sleGponOnuPMStatsDetailGEMPortIndex, sleGponOnuPMStatsDetailAniPortIndex, sleGponOnuPasswordType, sleGponOnuSupplierSerial, sleGponOnuHWRevision,
				sleGponOnuCPULoad, sleGponOnuCPULoadThreshold, sleGponOnuMemoryUsage, sleGponOnuMemoryThreshold, sleGponOnuTemperature,
				sleGponOnuTemperatureHighThreshold, sleGponOnuTemperatureLowThreshold, sleGponProfile2OnuSWWatchdog, sleGponProfile2OnuLinkPassThrough, sleGponProfile2OnuControlSWWatchdog,
				sleGponProfile2OnuControlLinkPassThrough, sleGponProfile2ExtVlanTagControlFilterOuterTpidDei, sleGponProfile2ExtVlanTagControlName, sleGponOnuPortOpticModuleSpeed, sleGponOnuPortOpticModuleWavelength,
				sleGponOnuPortOpticModuleConnecterType, sleGponOnuPortOpticModuleVendorName, sleGponOnuPortOpticModuleVendorPartName, sleGponOnuPortOpticModuleVendorRevision, sleGponProfile2ExtVlanTagControlFilterInnerVid,
				sleGponOnuPortOpticModuleInstall, sleGponOnuPortOpticModuleTransceiverType, sleGponOnuPortOpticModuleLengthMode, sleGponProfile2OnuCpuLoadThr, sleGponProfile2OnuMemoryUsageThr,
				sleGponProfile2OnuTemperatureHighThr, sleGponProfile2OnuTemperatureLowThr, sleGponProfile2OnuControlCpuLoadThr, sleGponProfile2OnuControlMemoryUsageThr, sleGponProfile2OnuControlTemperatureHighThr,
				sleGponProfile2OnuControlTemperatureLowThr, sleGponOnuPMStatsCurrentDetailGEMPortIndex, sleGponOnuPMStatsCurrentDetailGEMPort, sleGponOnuPMStatsCurrentDetailGEMLostPackets, sleGponOnuPMStatsCurrentDetailGEMMisInsertedPackets,
				sleGponOnuPMStatsCurrentDetailGEMReceivedPackets, sleGponOnuPMStatsCurrentDetailGEMReceivedBlocks, sleGponOnuPMStatsCurrentDetailGEMTransmittedBlocks, sleGponOnuPMStatsCurrentDetailGEMImpairedBlocks, sleGponOnuPMStatsCurrentDetailAniPortIndex,
				sleGponOnuPMStatsCurrentDetailAniPort, sleGponOnuPMStatsCurrentDetailAniDiscardedFrames, sleGponOnuPMStatsCurrentDetailUniEthFrameUpUniPort, sleGponOnuPMStatsCurrentDetailUniEthFrameUpDropEvents, sleGponOnuPMStatsCurrentDetailUniEthFrameUpOctets,
				sleGponOnuPMStatsCurrentDetailUniEthFrameUpPackets, sleGponOnuPMStatsCurrentDetailUniEthFrameUpBcastPackets, sleGponOnuPMStatsCurrentDetailUniEthFrameUpMcastPackets, sleGponOnuPMStatsCurrentDetailUniEthFrameUpUcastPackets, sleGponOnuPMStatsCurrentDetailUniEthFrameUpCRCErroredPackets,
				sleGponOnuPMStatsCurrentDetailUniEthFrameUpUndersizePackets, sleGponOnuPMStatsCurrentDetailUniEthFrameUpOversizePackets, sleGponOnuPMStatsCurrentDetailUniEthFrameUpPkt64Octets, sleGponOnuPMStatsCurrentDetailUniEthFrameUpPkt65To127Octets, sleGponOnuPMStatsCurrentDetailUniEthFrameUpPkt128To255,
				sleGponOnuPMStatsCurrentDetailUniEthFrameUpPkt256To511, sleGponOnuPMStatsCurrentDetailUniEthFrameUpPkt512To1023, sleGponOnuPMStatsCurrentDetailUniEthFrameUpPkt1024To1518, sleGponOnuPMStatsCurrentDetailUniEthFrameDownUniPort, sleGponOnuPMStatsCurrentDetailUniEthFrameDownDropEvents,
				sleGponOnuPMStatsCurrentDetailUniEthFrameDownOctets, sleGponOnuPMStatsCurrentDetailUniEthFrameDownPackets, sleGponOnuPMStatsCurrentDetailUniEthFrameDownBcastPackets, sleGponOnuPMStatsCurrentDetailUniEthFrameDownMcastPackets, sleGponOnuPMStatsCurrentDetailUniEthFrameDownUcastPackets,
				sleGponOnuPMStatsCurrentDetailUniEthFrameDownCRCErroredPackets, sleGponOnuPMStatsCurrentDetailUniEthFrameDownUndersizePackets, sleGponOnuPMStatsCurrentDetailUniEthFrameDownOversizePackets, sleGponOnuPMStatsCurrentDetailUniEthFrameDownPkt64Octets, sleGponOnuPMStatsCurrentDetailUniEthFrameDownPkt65To127Octets,
				sleGponOnuPMStatsCurrentDetailUniEthFrameDownPkt128To255Octets, sleGponOnuPMStatsCurrentDetailUniEthFrameDownmPkt256To511Octets, sleGponOnuPMStatsCurrentDetailUniEthFrameDownmPkt512To1023Octets, sleGponOnuPMStatsCurrentDetailUniEthFrameDownPkt1024To1518Octets, sleGponOnuPMStatsCurrentDetailUniEth3UniPort,
				sleGponOnuPMStatsCurrentDetailUniEth3DropEvents, sleGponOnuPMStatsCurrentDetailUniEth3Octets, sleGponOnuPMStatsCurrentDetailUniEth3Packets, sleGponOnuPMStatsCurrentDetailUniEth3BcastPackets, sleGponOnuPMStatsCurrentDetailUniEth3McastPackets,
				sleGponOnuPMStatsCurrentDetailUniEth3UcastPackets, sleGponOnuPMStatsCurrentDetailUniEth3UndersizePackets, sleGponOnuPMStatsCurrentDetailUniEth3Fragments, sleGponOnuPMStatsCurrentDetailUniEth3Jabbers, sleGponOnuPMStatsCurrentDetailUniEth3Pkt64Octets,
				sleGponOnuPMStatsCurrentDetailUniEth3Pkt65To127Octets, sleGponOnuPMStatsCurrentDetailUniEth3Pkt128To255Octets, sleGponOnuPMStatsCurrentDetailUniEth3Pkt256To511Octets, sleGponOnuPMStatsCurrentDetailUniEth3Pkt512To1023Octets, sleGponOnuPMStatsCurrentDetailUniEth3Pkt1024To1518Octets,
				sleGponRedGroupDbSyncStatus, sleGponOnuPortLinkUpCount, sleGponOnuPortLinkDownCount, sleGponProfileVoIPOmciMgcTerminationId, sleGponProfileVoIPOmciControlMgcTerminationId,
				sleGponOnuPortOpticModuleLength, sleGponOnuPortOpticModuleTransceiverDetailType, sleGponOnuPortOpticModuleVendorSerialNumber, sleGponOnuPortOpticModuleProductDate, sleGponProfile2TcontQueue1Weight,
				sleGponProfile2TcontQueue2Weight, sleGponProfile2TcontQueue3Weight, sleGponProfile2TcontQueue4Weight, sleGponProfile2TcontQueue5Weight, sleGponProfile2TcontQueue6Weight,
				sleGponProfile2TcontQueue7Weight, sleGponProfile2TcontQueue8Weight, sleGponProfile2TcontControlRequest, sleGponProfile2TcontControlStatus, sleGponProfile2TcontControlTimer,
				sleGponProfile2TcontControlTimeStamp, sleGponProfile2TcontControlReqResult, sleGponProfile2TcontControlTName, sleGponProfile2TcontControlID, sleGponProfile2TcontControlDbaProfile,
				sleGponProfile2TcontControlQueue1Weight, sleGponProfile2TcontControlQueue2Weight, sleGponProfile2TcontControlQueue3Weight, sleGponProfile2TcontControlQueue4Weight, sleGponProfile2TcontControlQueue5Weight,
				sleGponProfile2TcontControlQueue6Weight, sleGponProfile2TcontControlQueue7Weight, sleGponProfile2TcontControlQueue8Weight, sleGponProfileVoIPServiceMgcMessageId, sleGponProfileVoIPServiceControlRequest,
				sleGponProfileVoIPServiceControlStatus, sleGponProfileVoIPServiceControlTimer, sleGponProfileVoIPServiceControlTimeStamp, sleGponProfileVoIPServiceControlReqResult, sleGponProfileVoIPServiceControlIndex,
				sleGponOnuLoopDetectStateSupport, sleGponOnuLoopDetectStateDetect, sleGponOnuLoopDetectStateBlock, sleGponOnuLoopDetectUnblockReason, sleGponProfile2OnuLoopDetectStatus,
				sleGponProfile2OnuLoopDetectSendPeriod, sleGponProfile2OnuLoopDetectDetectedAction, sleGponProfile2OnuLoopDetectBlcokTimer, sleGponProfile2OnuControlLoopDetectStatus, sleGponProfile2OnuControlLoopDetectSendPeriod,
				sleGponProfile2OnuControlLoopDetectDetectedAction, sleGponProfile2OnuControlLoopDetectBlcokTimer, sleGponProfileVoIPServiceControlMgcMessageId, sleGponProfileVoIPServiceIndex, sleGponProfileVoIPServiceControlOltId,
				sleGponProfileVoIPServiceControlOnuId, sleGponBaseControlOnuPasswordType, sleGponOnuPortOpticModuleTemper, sleGponOnuPortOpticModuleVoltage, sleGponOnuPortOpticModuleTxbias,
				sleGponOnuPortOpticModuleTxPower, sleGponOnuPortOpticModuleRxPower, sleGponOnuAniId, sleGponOnuAniType, sleGponOnuAniOpticModuleInstall,
				sleGponOnuAniOpticModuleTransceiverType, sleGponOnuAniOpticModuleTransceiverDetailType, sleGponOnuAniOpticModuleLengthMode, sleGponOnuAniOpticModuleLength, sleGponOnuAniOpticModuleSpeed,
				sleGponOnuAniOpticModuleWavelength, sleGponOnuAniOpticModuleConnecterType, sleGponOnuAniOpticModuleVendorName, sleGponOnuAniOpticModuleVendorPartName, sleGponOnuAniOpticModuleVendorRevision,
				sleGponOnuAniOpticModuleVendorSerialNumber, sleGponOnuAniOpticModuleProductDate, sleGponOnuAniOpticModuleTemper, sleGponOnuAniOpticModuleVoltage, sleGponOnuAniOpticModuleTxbias,
				sleGponOnuAniOpticModuleTxPower, sleGponOnuAniOpticModuleRxPower, sleGponOnuAniControlRequest, sleGponOnuAniControlStatus, sleGponOnuAniControlTimer,
				sleGponOnuAniControlTimeStamp, sleGponOnuAniControlReqResult, sleGponOnuAniControlOltId, sleGponOnuAniControlOnuId, sleGponOnuAniControlAniId,
				sleGponProfile2BridgeUniMcastRateLimit, sleGponProfile2BridgeUniControlMcastRateLimit, sleGponOltFixedTcontCount, sleGponOltDynamicTcontCount, sleGponOltPortCount,
				sleGponOltControlFixedTcontCount, sleGponOltControlDynamicTcontCount, sleGponOltControlPortCount, sleGponOltDeactiveMonitorStatus, sleGponOltDeactiveMonitorRaisePercent,
				sleGponOltDeactiveMonitorClearPercent, sleGponOltDeactiveMonitorPeriod, sleGponOltControlDeactiveMonitorStatus, sleGponOltControlDeactiveMonitorRaisePercent, sleGponOltControlDeactiveMonitorClearPercent,
				sleGponOltControlDeactiveMonitorPeriod, sleGponOltDeactiveMonitorActiveOnuCount, sleGponOltDeactiveMonitorCurrentPercent, sleGponOltDeactiveMonitorInAlamStatus, sleGponOnuMcastAclOltId,
				sleGponOnuMcastAclOnuId, sleGponOnuMcastAclMcastIndex, sleGponOnuMcastAclMcastName, sleGponOnuMcastAclTableIndex, sleGponOnuMcastAclVid,
				sleGponOnuMcastAclDstIpStart, sleGponOnuMcastAclDstIpEnd, sleGponOnuMcastAclSrcIp, sleGponOnuMcastAclBandwidth, sleGponOnuMcastAclGem,
				sleGponOnuMcastAclControlRequest, sleGponOnuMcastAclControlStatus, sleGponOnuMcastAclControlTimer, sleGponOnuMcastAclControlTimeStamp, sleGponOnuMcastAclControlReqResult,
				sleGponOnuMcastAclControlOltId, sleGponOnuMcastAclControlOnuId, sleGponOnuMcastAclControlMcastName, sleGponOnuMcastAclControlTableIndex, sleGponOnuMcastAclControlVid,
				sleGponOnuMcastAclControlDstIpStart, sleGponOnuMcastAclControlDstIpEnd, sleGponOnuMcastAclControlSrcIp, sleGponOnuMcastAclControlBandwidth, sleGponOnuMcastAclControlGem,
				sleGponFlowMappingMethodType, sleGponFlowMappingMethodVid, sleGponFlowMappingMethodControlRequest, sleGponFlowMappingMethodControlStatus, sleGponFlowMappingMethodControlTimer,
				sleGponFlowMappingMethodControlTimeStamp, sleGponFlowMappingMethodControlReqResult, sleGponFlowMappingMethodControlOltId, sleGponFlowMappingMethodControlVid, sleGponFlowMappingMethodControlType,
				sleGponProfile2OnuTr069Status, sleGponProfile2OnuControlTr069Status, sleGponProfile2OnuTr069Url, sleGponProfile2OnuControlTr069Url, sleGponOnuFWAutoUpgradeControlBaseTimeStamp,
				sleGponOnuRxPowerUpdateTime, sleGponBaseControlOnuRxPowerUpdateTime, sleGponOnuFWAutoUpgradeMTimeRebootTime, sleGponOnuFWAutoUpgradeMTimeControlRebootTime, sleGponProfile2OnuTr069AccessId,
				sleGponProfile2OnuTr069AccessPassword, sleGponProfile2OnuControlTr069AccessId, sleGponProfile2OnuControlTr069AccessPassword, sleGponOnuSupportFunction, sleGponOltMulticastGem,
				sleGponOltInterworkIgmpSnooping, sleGponBaseControlOltMulticastGem, sleGponBaseControlOltInterworkIgmpSnooping, sleGponOnuUserMacStatus, sleGponStaticMacListId,
				sleGponStaticMacStartAddr, sleGponStaticMacEndAddr, sleGponStaticMacTrafficId, sleGponStaticMacVlanId, sleGponStaticMacPortId,
				sleGponStaticMacCount, sleGponStaticMacControlReqest, sleGponStaticMacControlStatus, sleGponStaticMacControlTimer, sleGponStaticMacControlTimeStamp,
				sleGponStaticMacControlReqResult, sleGponStaticMacControlOltId, sleGponStaticMacControlStartAddr, sleGponStaticMacControlEndAddr, sleGponStaticMacControlTrafficId,
				sleGponStaticMacControlVlanId, sleGponOnuVideoAniIndex, sleGponOnuVideoAniAdminState, sleGponOnuVideoAniOperState, sleGponOnuVideoAniArc,
				sleGponOnuVideoAniArcInterval, sleGponOnuVideoAniFreqRangeLow, sleGponOnuVideoAniFreqRangeHigh, sleGponOnuVideoAniSignalCapability, sleGponOnuVideoAniOpticalSignalLevel,
				sleGponOnuVideoAniPilotSignalLevel, sleGponOnuVideoAniSignalLevelMin, sleGponOnuVideoAniSignalLevelMax, sleGponOnuVideoAniPilotFreq, sleGponOnuVideoAniAgcMode,
				sleGponOnuVideoAniAgcSetting, sleGponOnuVideoAniVideoLowerOpticalThr, sleGponOnuVideoAniVideoUpperOpticalThr, sleGponOnuVideoAniConfAgcSetting, sleGponOnuVideoAniControlRequest,
				sleGponOnuVideoAniControlStatus, sleGponOnuVideoAniControlTimer, sleGponOnuVideoAniControlTimeStamp, sleGponOnuVideoAniControlReqResult, sleGponOnuVideoAniControlOltIndex,
				sleGponOnuVideoAniControlOnuIndex, sleGponOnuVideoAniControlAniIndex, sleGponOnuVideoAniControlConfAgcSetting, sleGponOnuRFPseudowireMode, sleGponOnuRFPseudowireDstMac,
				sleGponBaseControlOnuRFPseudowireMode, sleGponBaseControlOnuRFPseudowireDstMac, sleGponOnuAccountUserName, sleGponOnuAccountPassword, sleGponOnuControlAccountUserName,
				sleGponOnuControlAccountPassword, sleGponOnuMacSlotIndex, sleGponOnuMacPortIndex, sleGponOnuMacIndex, sleGponOnuMacPolicy,
				sleGponOnuMacStatus, sleGponOnuMacAge, sleGponOnuMacControlRequest, sleGponOnuMacControlStatus, sleGponOnuMacControlTimer,
				sleGponOnuMacControlTimeStamp, sleGponOnuMacControlReqResult, sleGponOnuMacControlOltIndex, sleGponOnuMacControlOnuIndex, sleGponOnuMacControlSlotIndex,
				sleGponOnuMacControlPortIndex, sleGponOltBerUpInterval, sleGponOltBerDownInterval, sleGponOltBerSfThreshold, sleGponOltBerSdThreshold,
				sleGponOltControlBerUpInterval, sleGponOltControlBerDownInterval, sleGponOltControlBerSfThreshold, sleGponOltControlBerSdThreshold, sleGponOnuIgmpPmStatisticsSlotType,
				sleGponOnuIgmpPmStatisticsPortIndex, sleGponOnuIgmpPmStatisticsSuccessfulJoins, sleGponOnuIgmpPmStatisticsUnsuccessfulJoins, sleGponOnuIgmpPmStatisticsLeaveMessages, sleGponOnuIgmpPmStatisticsGeneralQueries,
				sleGponOnuIgmpPmStatisticsSpecificQueries, sleGponOnuIgmpPmStatisticsInvalidIGMPMessages, sleGponOnuIgmpPmStatisticsControlRequest, sleGponOnuIgmpPmStatisticsControlStatus, sleGponOnuIgmpPmStatisticsControlTimer,
				sleGponOnuIgmpPmStatisticsControlTimeStamp, sleGponOnuIgmpPmStatisticsControlReqResult, sleGponOnuIgmpPmStatisticsControlOltIndex, sleGponOnuIgmpPmStatisticsControlOnuIndex, sleGponOnuIgmpPmStatisticsControlSlotType,
				sleGponOnuIgmpPmStatisticsControlPortIndex, sleGponOnuMacFilterOltId, sleGponOnuMacFilterOnuId, sleGponOnuMacFilterSlotType, sleGponOnuMacFilterPortId,
				sleGponOnuMacFilterMac, sleGponOnuMacFilterType, sleGponOnuMacFilterControlRequest, sleGponOnuMacFilterControlStatus, sleGponOnuMacFilterControlTimer,
				sleGponOnuMacFilterControlTimeStamp, sleGponOnuMacFilterControlReqResult, sleGponOnuMacFilterControlOltIndex, sleGponOnuMacFilterControlOnuIndex, sleGponOnuMacFilterControlSlotType,
				sleGponOnuMacFilterControlPortIndex, sleGponOnuMacFilterControlMac, sleGponOnuMacFilterControlType, sleGponProfile2BridgeAniMacFilterPreassign, sleGponProfile2BridgeAniControlMacFilterPreassign,
				sleGponProfile2BridgeUniMacFilterPreassign, sleGponProfile2BridgeUniControlMacFilterPreassign, sleGponOnuActiveMode, sleGponbaseControlOnuActiveMode, sleGponOltUsFlowMapping,
				sleGponOltControlUsFlowMapping, sleGponOnuMacAddress, sleGponProfile2MapperIndex, sleGponProfile2OnuControlTr069Tag, sleGponOnuOmciPingTestResult,
				sleGponOnuOmciPingTestResultAvg, sleGponOnuControlOmciPingTestTimeout, sleGponProfile2VoipSvcProtocolPort, sleGponProfile2VoipSvcProtocolTos, sleGponProfile2VoipSvcProtocolType,
				sleGponProfile2VoipSvcControlProtocolPort, sleGponProfile2VoipSvcControlProtocolTos, sleGponProfile2VoipSvcControlProtocolType, sleGponProfile2TdmSvcProtocolPort, sleGponProfile2TdmSvcProtocolTos,
				sleGponProfile2TdmSvcProtocolType, sleGponProfile2TdmSvcControlProtocolPort, sleGponProfile2TdmSvcControlProtocolTos, sleGponProfile2TdmSvcControlProtocolType, sleGponProfile2MapperGemId,
				sleGponProfile2MapperGemRateLimitDownSir, sleGponProfile2MapperGemRateLimitDownPir, sleGponProfile2MapperGemRateLimitUpSir, sleGponProfile2MapperGemRateLimitUpPir, sleGponProfile2MapperGemControlRequest,
				sleGponProfile2MapperGemControlStatus, sleGponProfile2MapperGemControlTimer, sleGponProfile2MapperGemControlTimeStamp, sleGponProfile2MapperGemControlReqResult, sleGponProfile2MapperGemControlIndex,
				sleGponProfile2MapperGemControlGemIndex, sleGponProfile2MapperGemControlRateLimitDownSir, sleGponProfile2MapperGemControlRateLimitDownPir, sleGponProfile2MapperGemControlRateLimitUpSir, sleGponOltStatsOnuAlarmSf,
				sleGponOltStatsOnuAlarmSd, sleGponOltStatsOnuElapsedTimeAfterClear, sleGponOnuRFPseudowireEthType, sleGponOnuRFPseudowireVlanId, sleGponBaseControlOnuRFPseudowireEthType,
				sleGponBaseControlOnuRFPseudowireVlanId, sleGponProfile2MapperActiveEth, sleGponProfile2GemNctpIndex, sleGponProfile2GemNctpServiceId, sleGponProfile2GemNctpServiceType,
				sleGponProfile2GemNctpControlRequest, sleGponProfile2GemNctpControlStatus, sleGponProfile2GemNctpControlTimer, sleGponProfile2GemNctpControlTimeStamp, sleGponProfile2GemNctpControlReqResult,
				sleGponProfile2GemNctpControlTname, sleGponProfile2GemNctpControlIndex, sleGponProfile2GemNctpControlServiceId, sleGponProfile2GemNctpControlServiceType, sleGponProfile2VideoReturnPathSvcIndex,
				sleGponProfile2VideoReturnPathSvcMode, sleGponProfile2VideoReturnPathSvcFrequency, sleGponProfile2VideoReturnPathSvcPhysical, sleGponProfile2VideoReturnPathSvcControlRequest, sleGponProfile2VideoReturnPathSvcControlStatus,
				sleGponProfile2VideoReturnPathSvcControlTimer, sleGponProfile2VideoReturnPathSvcControlTimeStamp, sleGponProfile2VideoReturnPathSvcControlReqResult, sleGponProfile2VideoReturnPathSvcControlTname, sleGponProfile2VideoReturnPathSvcControlIndex,
				sleGponProfile2VideoReturnPathSvcControlMode, sleGponProfile2VideoReturnPathSvcControlFrequency, sleGponProfile2VideoReturnPathSvcControlPhysical, sleGponOnuPortMgmtAdminStatus, sleGponOnuPortMgmtCapability,
				sleGponOnuPortMgmtMethod, sleGponProfile2PortMgmtSlotId, sleGponProfile2PortMgmtPortId, sleGponProfile2PortMgmtMode, sleGponProfile2PotMgmtVirtualEthNum,
				sleGponProfile2PortMgmtControlRequest, sleGponProfile2PortMgmtControlStatus, sleGponProfile2PortMgmtControlTimer, sleGponProfile2PortMgmtControlTimeStamp, sleGponProfile2PortMgmtControlReqResult,
				sleGponProfile2PortMgmtControlTName, sleGponProfile2PortMgmtControlSlotId, sleGponProfile2PortMgmtControlPortId, sleGponProfile2PortMgmtControlMode, sleGponProfile2PortMgmtControlVirtualEthNum,
				sleGponProfileVoIPDetailSpecialLineService, sleGponProfileVoIPDetailWarmLineTimeout, sleGponProfileVoIPDetailLineNumber, sleGponProfileVoIPDetailThreeWaySSWMixing, sleGponProfileVoIPDetailSIPDNSCache,
				sleGponProfileVoIPDetailSIPTimerT1, sleGponProfileVoIPDetailSIPTimerT2, sleGponProfileVoIPDetailSIPTimerTd, sleGponProfileVoIPDetailSIPSessionTimer, sleGponProfileVoIPDetailSIPSessionTimeout,
				sleGponProfileVoIPDetailSIPEndOfDigit, sleGponProfileVoIPDetailSIPEndSharpToken, sleGponProfileVoIPDetailControlSpecialLineService, sleGponProfileVoIPDetailControlWarmLineTimeout, sleGponProfileVoIPDetailControlLineNumber,
				sleGponProfileVoIPDetailControlThreeWaySSWMixing, sleGponProfileVoIPDetailControlSIPDNSCache, sleGponProfileVoIPDetailControlSIPTimerT1, sleGponProfileVoIPDetailControlSIPTimerT2, sleGponProfileVoIPDetailControlSIPTimerTd,
				sleGponProfileVoIPDetailControlSIPSessionTimer, sleGponProfileVoIPDetailControlSIPSessionTimeout, sleGponProfileVoIPDetailControlSIPEndOfDigit, sleGponProfileVoIPDetailControlSIPEndSharpToken, sleGponProfile2OnuSwitchControlUplinkMacLearning,
				sleGponProfile2OnuControlSwitchControlUplinkMacLearning, sleGponProfile2MapperGemControlRateLimitUpPir, sleGponOnuPMStatsCurrentDetailUniEthFrameUpAvgPackets, sleGponOnuPMStatsCurrentDetailUniEthFrameUpAvgBits, sleGponOnuPMStatsCurrentDetailUniEthFrameTotalUpAvgPackets,
				sleGponOnuPMStatsCurrentDetailUniEthFrameTotalUpAvgBits, sleGponOnuPMStatsCurrentDetailUniEthFrameDownAvgPackets, sleGponOnuPMStatsCurrentDetailUniEthFrameDownAvgBits, sleGponOnuPMStatsCurrentDetailUniEthFrameTotalDownAvgPackets, sleGponOnuPMStatsCurrentDetailUniEthFrameTotalDownAvgBits,
				sleGponProfile2McastAccessListIndex, sleGponProfile2McastAccessListName, sleGponProfile2McastAccessListControlRequest, sleGponProfile2McastAccessListControlStatus, sleGponProfile2McastAccessListControlTimer,
				sleGponProfile2McastAccessListControlTimeStamp, sleGponProfile2McastAccessListControlReqResult, sleGponProfile2McastAccessListControlName, sleGponProfile2McastAccessListDynamicIndex, sleGponProfile2McastAccessListDynamicVid,
				sleGponProfile2McastAccessListDynamicDstIpStart, sleGponProfile2McastAccessListDynamicDstIpEnd, sleGponProfile2McastAccessListDynamicSrcIp, sleGponProfile2McastAccessListDynamicBandwidth, sleGponProfile2McastAccessListDynamicGem,
				sleGponProfile2McastAccessListDynamicControlRequest, sleGponProfile2McastAccessListDynamicControlStatus, sleGponProfile2McastAccessListDynamicControlTimer, sleGponProfile2McastAccessListDynamicControlTimeStamp, sleGponProfile2McastAccessListDynamicControlReqResult,
				sleGponProfile2McastAccessListDynamicControlIndex, sleGponProfile2McastAccessListDynamicControlVid, sleGponProfile2McastAccessListDynamicControlName, sleGponProfile2McastAccessListDynamicControlDstIpStart, sleGponProfile2McastAccessListDynamicControlDstIpEnd,
				sleGponProfile2McastAccessListDynamicControlSrcIp, sleGponProfile2McastAccessListDynamicControlBandwidth, sleGponProfile2McastAccessListDynamicControlGem, sleGponProfile2McastAccessListStaticIndex, sleGponProfile2McastAccessListStaticVid,
				sleGponProfile2McastAccessListStaticDstIpStart, sleGponProfile2McastAccessListStaticDstIpEnd, sleGponProfile2McastAccessListStaticSrcIp, sleGponProfile2McastAccessListStaticBandwidth, sleGponProfile2McastAccessListStaticGem,
				sleGponProfile2McastAccessListStaticControlRequest, sleGponProfile2McastAccessListStaticControlStatus, sleGponProfile2McastAccessListStaticControlTimer, sleGponProfile2McastAccessListStaticControlTimeStamp, sleGponProfile2McastAccessListStaticControlReqResult,
				sleGponProfile2McastAccessListStaticControlIndex, sleGponProfile2McastAccessListStaticControlVid, sleGponProfile2McastAccessListStaticControlName, sleGponProfile2McastAccessListStaticControlDstIpStart, sleGponProfile2McastAccessListStaticControlDstIpEnd,
				sleGponProfile2McastAccessListStaticControlSrcIp, sleGponProfile2McastAccessListStaticControlBandwidth, sleGponProfile2McastAccessListStaticControlGem, sleGponOnuMcastAccessListOltId, sleGponOnuMcastAccessListOnuId,
				sleGponOnuMcastAccessListIndex, sleGponOnuMcastAccessListName, sleGponOnuMcastAccessListProfileName, sleGponOnuMcastAccessListControlRequest, sleGponOnuMcastAccessListControlStatus,
				sleGponOnuMcastAccessListControlTimer, sleGponOnuMcastAccessListControlTimeStamp, sleGponOnuMcastAccessListControlReqResult, sleGponOnuMcastAccessListControlOltIndex, sleGponOnuMcastAccessListControlOnuIndex,
				sleGponOnuMcastAccessListControlName, sleGponOnuMcastAccessListControlProfileName, sleGponProfile2MapperGemControlTrafficName, sleGponProfile2OnuTr069Tag, sleGponOnuAniOpticModuleTemperHighThr,
				sleGponOnuAniOpticModuleTemperLowThr, sleGponOnuAniOpticModuleVoltageHighThr, sleGponOnuAniOpticModuleVoltageLowThr, sleGponOnuAniOpticModuleTxbiasHighThr, sleGponOnuAniOpticModuleTxbiasLowThr,
				sleGponOnuAniOpticModuleTxPowerHighThr, sleGponOnuAniOpticModuleTxPowerLowThr, sleGponOnuAniOpticModuleRxPowerHighThr, sleGponOnuAniOpticModuleRxPowerLowThr, sleGponPorifle2OnuAniVoltageHighThr,
				sleGponPorifle2OnuAniVoltageLowThr, sleGponPorifle2OnuAniTemperatureHighThr, sleGponPorifle2OnuAniTemperatureLowThr, sleGponPorifle2OnuAniTxBiasHighThr, sleGponPorifle2OnuAniTxBiasLowThr,
				sleGponPorifle2OnuAniTxpowerHighThr, sleGponPorifle2OnuAniTxpowerLowThr, sleGponPorifle2OnuControlAniVoltageHighThr, sleGponPorifle2OnuControlAniVoltageLowThr, sleGponPorifle2OnuControlAniTemperatureHighThr,
				sleGponPorifle2OnuControlAniTemperatureLowThr, sleGponPorifle2OnuControlAniTxBiasHighThr, sleGponPorifle2OnuControlAniTxBiasLowThr, sleGponPorifle2OnuControlAniTxpowerHighThr, sleGponPorifle2OnuControlAniTxpowerLowThr,
				sleGponProfile2OnuIgmpMaxGroups, sleGponProfile2OnuControlIgmpMaxGroups, sleGponProfile2OnuIgmpUpRateLimit, sleGponProfile2OnuControlIgmpUpRateLimit, sleGponProfile2McastAclCos,
				sleGponProfile2McastAclControlCos, sleGponProfile2McastSAclCos, sleGponProfile2McastSAclControlCos, sleGponProfile2McastAccessListDynamicCos, sleGponProfile2McastAccessListDynamicControlCos,
				sleGponProfile2McastAccessListStaticCos, sleGponProfile2McastAccessListStaticControlCos, sleGponProfile2OnuIgmpHostTracking, sleGponProfile2OnuControlIgmpHostTracking, sleGponOnuPmStatsUniAvgPort,
				sleGponOnuPmStatsUniAvgEthFrameUpPackets, sleGponOnuPmStatsUniAvgEthFrameUpBits, sleGponOnuPmStatsUniAvgEthFrameDownPackets, sleGponOnuPmStatsUniAvgEthFrameDownBits, sleGponOnuPmStatsUniAvgControlRequest,
				sleGponOnuPmStatsUniAvgControlStatus, sleGponOnuPmStatsUniAvgControlTimer, sleGponOnuPmStatsUniAvgControlTimeStamp, sleGponOnuPmStatsUniAvgControlReqResult, sleGponOnuPmStatsUniAvgControlOltindex,
				sleGponOnuPmStatsUniAvgControlOnuIndex, sleGponOnuPmStatsUniAvgControlPort, sleGponOltPortServiceStatus, sleGponProfile2BridgeUniRateLimitProfile, sleGponProfile2BridgeUniControlRateLimitProfile,
				sleGponProfile2MapperGemRateLimitProfile, sleGponProfile2MapperGemControlRateLimitProfile, sleGponProfile2RateLimitIndex, sleGponProfile2RateLimitName, sleGponProfile2RateLimitUpPir,
				sleGponProfile2RateLimitUpSir, sleGponProfile2RateLimitDownPir, sleGponProfile2RateLimitDownSir, sleGponProfile2RateLimitControlRequest, sleGponProfile2RateLimitControlStatus,
				sleGponProfile2RateLimitControlTimer, sleGponProfile2RateLimitControlTimeStamp, sleGponProfile2RateLimitControlReqResult, sleGponProfile2RateLimitControlName, sleGponProfile2RateLimitControlDownSir,
				sleGponProfile2RateLimitControlDownPir, sleGponProfile2RateLimitControlUpSir, sleGponProfile2RateLimitControlUpPir, sleGponProfile2BridgeControlMcastFlag, sleGponProfile2BridgeControlPortBridge,
				sleGponProfile2OnuMacFullPolicy, sleGponProfile2OnuCpuPacketLimitBroadcast, sleGponProfile2OnuCpuPacketLimitMulticast, sleGponProfile2OnuCpuPacketLimitDlf, sleGponProfile2OnuControlMacFullPolicy,
				sleGponProfile2OnuControlCpuPacketLimitBroadcast, sleGponProfile2OnuControlCpuPacketLimitMulticast, sleGponProfile2OnuControlCpuPacketLimitDlf, sleGponOltStatsOnuBipReiErrors, sleGponOnuPMStatsSumAllOnuGemLostPackets,
				sleGponOnuPMStatsSumAllOnuGemMisInsertedPackets, sleGponOnuPMStatsSumAllOnuGemReceivedPackets, sleGponOnuPMStatsSumAllOnuGemReceivedBlocks, sleGponOnuPMStatsSumAllOnuGemTransmittedBlocks, sleGponOnuPMStatsSumAllOnuGemImpairedBlocks,
				sleGponOnuPMStatsSumAllOnuAniDiscardedFrames, sleGponOnuPMStatsSumAllOnuUniEthFrameUpDropEvents, sleGponOnuPMStatsSumAllOnuUniEthFrameUpOctets, sleGponOnuPMStatsSumAllOnuUniEthFrameUpPackets, sleGponOnuPMStatsSumAllOnuUniEthFrameUpBcastPackets,
				sleGponOnuPMStatsSumAllOnuUniEthFrameUpMcastPackets, sleGponOnuPMStatsSumAllOnuUniEthFrameUpUcastPackets, sleGponOnuPMStatsSumAllOnuUniEthFrameUpCRCErroredPackets, sleGponOnuPMStatsSumAllOnuUniEthFrameUpUndersizePackets, sleGponOnuPMStatsSumAllOnuUniEthFrameUpOversizePackets,
				sleGponOnuPMStatsSumAllOnuUniEthFrameUpPkt64Octets, sleGponOnuPMStatsSumAllOnuUniEthFrameUpPkt65To127Octets, sleGponOnuPMStatsSumAllOnuUniEthFrameUpPkt128To255Octets, sleGponOnuPMStatsSumAllOnuUniEthFrameUpPkt256To511Octets, sleGponOnuPMStatsSumAllOnuUniEthFrameUpPkt512To1023Octets,
				sleGponOnuPMStatsSumAllOnuUniEthFrameUpPkt1024To1518Octets, sleGponOnuPMStatsSumAllOnuUniEthFrameDownDropEvents, sleGponOnuPMStatsSumAllOnuUniEthFrameDownOctets, sleGponOnuPMStatsSumAllOnuUniEthFrameDownPackets, sleGponOnuPMStatsSumAllOnuUniEthFrameDownBcastPackets,
				sleGponOnuPMStatsSumAllOnuUniEthFrameDownMcastPackets, sleGponOnuPMStatsSumAllOnuUniEthFrameDownUcastPackets, sleGponOnuPMStatsSumAllOnuUniEthFrameDownCRCErroredPackets, sleGponOnuPMStatsSumAllOnuUniEthFrameDownUndersizePackets, sleGponOnuPMStatsSumAllOnuUniEthFrameDownOversizePackets,
				sleGponOnuPMStatsSumAllOnuUniEthFrameDownPkt64Octets, sleGponOnuPMStatsSumAllOnuUniEthFrameDownPkt65To127Octets, sleGponOnuPMStatsSumAllOnuUniEthFrameDownPkt128To255Octets, sleGponOnuPMStatsSumAllOnuUniEthFrameDownPkt256To511Octets, sleGponOnuPMStatsSumAllOnuUniEthFrameDownPkt512To1023Octets,
				sleGponOnuPMStatsSumAllOnuUniEthFrameDownPkt1024To1518Octets, sleGponOnuPMStatsSumAllOnuUniEth3DropEvents, sleGponOnuPMStatsSumAllOnuUniEth3Octets, sleGponOnuPMStatsSumAllOnuUniEth3Packets, sleGponOnuPMStatsSumAllOnuUniEth3BcastPackets,
				sleGponOnuPMStatsSumAllOnuUniEth3McastPackets, sleGponOnuPMStatsSumAllOnuUniEth3UcastPackets, sleGponOnuPMStatsSumAllOnuUniEth3Fragments, sleGponOnuPMStatsSumAllOnuUniEth3Jabbers, sleGponOnuPMStatsSumAllOnuUniEth3Pkt64Octets,
				sleGponOnuPMStatsSumAllOnuUniEth3Pkt65To127Octets, sleGponOnuPMStatsSumAllOnuUniEth3Pkt128To255Octets, sleGponOnuPMStatsSumAllOnuUniEth3Pkt256To511Octets, sleGponOnuPMStatsSumAllOnuUniEth3Pkt512To1023Octets, sleGponOnuPMStatsSumAllOnuUniEth3Pkt1024To1518Octets,
				sleGponOltAutoOnuBlockContMoveMac, sleGponOltControlAutoOnuBlockContMoveMac, sleGponOltRxPowerUpdateTime, sleGponBaseControlOltRxPowerUpdateTime, sleGponOltRxPowerUpdateMode,
				sleGponOltRxPowerLowThreshold, sleGponOltRxPowerHighThreshold, sleGponOltControlRxPowerUpdateMode, sleGponOltControlRxPowerLowThreshold, sleGponOltControlRxPowerHighThreshold,
				sleGponProfile2OnuRateLimitDownstream, sleGponProfile2OnuControlRateLimitDownstream, sleGponProfile2OnuTrapToCpuDlf, sleGponProfile2OnuControlTrapToCpuDlf, sleGponOnuMcastAccessListProfileIndex,
				sleGponOltDsQosMappingQueueCount, sleGponOltDsQosMappingCos0Queue, sleGponOltDsQosMappingCos1Queue, sleGponOltDsQosMappingCos2Queue, sleGponOltDsQosMappingCos3Queue,
				sleGponOltDsQosMappingCos4Queue, sleGponOltDsQosMappingCos5Queue, sleGponOltDsQosMappingCos6Queue, sleGponOltDsQosMappingCos7Queue, sleGponOltDsQosMappingMode,
				sleGponOltControlDsQosMappingQueueCount, sleGponOltControlDsQosMappingCos0Queue, sleGponOltControlDsQosMappingCos1Queue, sleGponOltControlDsQosMappingCos2Queue, sleGponOltControlDsQosMappingCos3Queue,
				sleGponOltControlDsQosMappingCos4Queue, sleGponOltControlDsQosMappingCos5Queue, sleGponOltControlDsQosMappingCos6Queue, sleGponOltControlDsQosMappingCos7Queue, sleGponOltControlDsQosMappingMode,
				sleGponVlanGemMappingControlVid, sleGponVlanGemMappingControlMapperId, sleGponVlanGemMappingControlVidTo, sleGponProfile2BridgePortBridge, sleGponRedGroupStandbyActTriggerTime,
				sleGponRedGroupControlStandbyActTriggerTime, sleGponOltMcastThreshold, sleGponOltDlfThreshold, sleGponOltControlBcastThreshold, sleGponOltControlMulticastThreshold,
				sleGponOltControlDLFThreshold, sleGponOltBcastThreshold, sleGponOltOnuInactiveAgingTime, sleGponOltControlOnuInactiveAgingTime, sleGponOnuAuthRadiusUserName,
				sleGponBaseControlOnuAuthRadiusUserName, sleGponOltOnuAuthControlMode, sleGponOltControlOnuAuthControlMode, sleGponOnuInactiveTime, sleGponOnuRadiusAuthStatus,
				sleGponOnuRadiusAuthReceiveProfile, sleGponOnuAuthIndex, sleGponOnuAuthAddress, sleGponOnuAuthKey, sleGponOnuAuthPort,
				sleGponOnuAuthControlRequest, sleGponOnuAuthControlStatus, sleGponOnuAuthControlTimer, sleGponOnuAuthControlTimeStamp, sleGponOnuAuthControlReqResult,
				sleGponOnuAuthControlAddress, sleGponOnuAuthControlKey, sleGponOnuAuthControlPort, sleGponProfile2BaseOnuProfileCount, sleGponProfile2BaseDbaProfileCount,
				sleGponProfile2BaseMcastProfileCount, sleGponProfile2BaseMcastAclProfileCount, sleGponProfile2BaseExtVlanProfileCount, sleGponProfile2BaseVoipProfileCount, sleGponProfile2BasePmProfileCount,
				sleGponProfile2BaseTrafficProfileCount, sleGponProfile2BaseTdmPwProfileCount, sleGponProfile2BasePwMetrmsProfileCount, sleGponProfile2BaseRateLimitProfileCount, sleGponOnuMgmtIpPathProtocol,
				sleGponOnuMgmtIpPathId, sleGponOnuMgmtIpPathPassword, sleGponOnuMgmtIpPathUrl, sleGponOnuMgmtIpPathFileName, sleGponOnuMgmtIpPathState,
				sleGponOnuControlMgmtIpPathProtocol, sleGponOnuControlMgmtIpPathId, sleGponOnuControlMgmtIpPathPassword, sleGponOnuControlMgmtIpPathUrl, sleGponOnuControlMgmtIpPathFilename,
				sleGponProfile2OnuMgmtIpPathStatus, sleGponProfile2OnuMgmtIpPathProtocol, sleGponProfile2OnuMgmtIpPathId, sleGponProfile2OnuMgmtIpPathPassword, sleGponProfile2OnuMgmtIpPathUrl,
				sleGponProfile2OnuMgmtIpPathFilename, sleGponProfile2OnuControlMgmtIpPathStatus, sleGponProfile2OnuControlMgmtIpPathProtocol, sleGponProfile2OnuControlMgmtIpPathId, sleGponProfile2OnuControlMgmtIpPathPassword,
				sleGponProfile2OnuControlMgmtIpPathUrl, sleGponProfile2OnuControlMgmtIpPathFilename, sleGponOnuExtVlanTagTreatInnerCopyVid, sleGponOnuExtVlanTagTreatInnerCopyCos, sleGponOnuExtVlanTagControlRequest,
				sleGponOnuExtVlanTagControlStatus, sleGponOnuExtVlanTagControlTimer, sleGponOnuExtVlanTagControlTimeStamp, sleGponOnuExtVlanTagControlReqResult, sleGponOnuExtVlanTagControlOltIndex,
				sleGponOnuExtVlanTagControlOnuIndex, sleGponOnuExtVlanTagControlProfileName, sleGponOnuExtVlanTagControlFrameType, sleGponOnuExtVlanTagControlFrameIndex, sleGponOnuExtVlanTagControlTreatInnerCopyVid,
				sleGponOnuExtVlanTagControlTreatInnerCopyCos, sleGponOnuPMStatsDetailGEMNCTPIndex, sleGponOnuPMStatsDetailGEMNCTP, sleGponOnuPMStatsDetailGEMNCTPPre15mRxGemFrames, sleGponOnuPMStatsDetailGEMNCTPPre15mTxGemFrames,
				sleGponOnuPMStatsDetailGEMNCTPPre15mRxPayloadByte, sleGponOnuPMStatsDetailGEMNCTPPre15mTxPayloadByte, sleGponOnuPMStatsDetailGEMNCTPPre15mEncryptionKeyError, sleGponOnuPMStatsDetailGEMNCTPHourRxGemFrames, sleGponOnuPMStatsDetailGEMNCTPHourTxGemFrames,
				sleGponOnuPMStatsDetailGEMNCTPHourRxPayloadByte, sleGponOnuPMStatsDetailGEMNCTPHourTxPayloadByte, sleGponOnuPMStatsDetailGEMNCTPHourEncryptionKeyError, sleGponOnuPMStatsDetailGEMNCTPDayRxGemFrames, sleGponOnuPMStatsDetailGEMNCTPDayTxGemFrames,
				sleGponOnuPMStatsDetailGEMNCTPDayRxPayloadByte, sleGponOnuPMStatsDetailGEMNCTPDayTxPayloadByte, sleGponOnuPMStatsDetailGEMNCTPDayEncryptionKeyError, sleGponOnuPMStatsDetailGEMNCTPTotalRxGemFrames, sleGponOnuPMStatsDetailGEMNCTPTotalTxGemFrames,
				sleGponOnuPMStatsDetailGEMNCTPTotalRxPayloadByte, sleGponOnuPMStatsDetailGEMNCTPTotalTxPayloadByte, sleGponOnuPMStatsDetailGEMNCTPTotalEncryptionKeyError, sleGponOnuPMStatsDetailGEMNCTPElapsedTimeAfterClear, sleGponOnuPMStatsDetailGEMNCTPElapsedTimeAfterUpdate,
				sleGponOnuPMStatsCurrentDetailGEMNCTPIndex, sleGponOnuPMStatsCurrentDetailGEMNCTP, sleGponOnuPMStatsCurrentDetailGEMNCTPRxGemFrames, sleGponOnuPMStatsCurrentDetailGEMNCTPTxGemFrames, sleGponOnuPMStatsCurrentDetailGEMNCTPRxPayloadByte,
				sleGponOnuPMStatsCurrentDetailGEMNCTPTxPayloadByte, sleGponOnuPMStatsCurrentDetailGEMNCTPEncryptionKeyError, sleGponOnuPMStatsSumAllOnuGemNctpRxGemFrames, sleGponOnuPMStatsSumAllOnuGemNctpTxGemFrames, sleGponOnuPMStatsSumAllOnuGemNctpRxPayloadByte,
				sleGponOnuPMStatsSumAllOnuGemNctpTxPayloadByte, sleGponOnuPMStatsSumAllOnuGemNctpEncryptionKeyError, sleGponOnuPMStatsSumOnuGEMNCTPPre15mRxGemFrames, sleGponOnuPMStatsSumOnuGEMNCTPPre15mTxGemFrames, sleGponOnuPMStatsSumOnuGEMNCTPPre15mRxPayloadByte,
				sleGponOnuPMStatsSumOnuGEMNCTPPre15mTxPayloadByte, sleGponOnuPMStatsSumOnuGEMNCTPPre15mEncryptionKeyError, sleGponOnuPMStatsSumOnuGEMNCTPHourRxGemFrames, sleGponOnuPMStatsSumOnuGEMNCTPHourTxGemFrames, sleGponOnuPMStatsSumOnuGEMNCTPHourRxPayloadByte,
				sleGponOnuPMStatsSumOnuGEMNCTPHourTxPayloadByte, sleGponOnuPMStatsSumOnuGEMNCTPHourEncryptionKeyError, sleGponOnuPMStatsSumOnuGEMNCTPDayRxGemFrames, sleGponOnuPMStatsSumOnuGEMNCTPDayTxGemFrames, sleGponOnuPMStatsSumOnuGEMNCTPDayRxPayloadByte,
				sleGponOnuPMStatsSumOnuGEMNCTPDayTxPayloadByte, sleGponOnuPMStatsSumOnuGEMNCTPDayEncryptionKeyError, sleGponOnuPMStatsSumOnuGEMNCTPTotalRxGemFrames, sleGponOnuPMStatsSumOnuGEMNCTPTotalTxGemFrames, sleGponOnuPMStatsSumOnuGEMNCTPTotalRxPayloadByte,
				sleGponOnuPMStatsSumOnuGEMNCTPTotalTxPayloadByte, sleGponOnuPMStatsSumOnuGEMNCTPTotalEncryptionKeyError, sleGponOnuPMStatsSumOnuGEMNCTPElapsedTimeAfterClear, sleGponOnuPMStatsSumOnuGEMNCTPElapsedTimeAfterUpdate, sleGponProfile2PMProfilePMGemNCTP,
				sleGponProfile2PMProfileControlPMGemNCTP, sleGponCmfMdIndex, sleGponCfmMdName, sleGponCfmMdLevel, sleGponCfmMdControlRequest,
				sleGponCfmMdControlStatus, sleGponCfmMdControlTimer, sleGponCfmMdControlTimeStamp, sleGponCfmMdControlReqResult, sleGponCfmMdControlName,
				sleGponCfmMdControlLevel, sleGponCmfMaKey, sleGponCfmMaNameFormat, sleGponCfmMaName, sleGponCfmMaCcmInterval,
				sleGponCfmMaMdName, sleGponCfmMaControlRequest, sleGponCfmMaControlStatus, sleGponCfmMaControlTimer, sleGponCfmMaControlTimeStamp,
				sleGponCfmMaControlReqResult, sleGponCfmMaControlKey, sleGponCfmMaControlNameFormat, sleGponCfmMaControlName, sleGponCfmMaControlCcmInterval,
				sleGponCfmMaControlMdName, sleGponCfmMepSlotType, sleGponCfmMepPortIndex, sleGponCfmMepMepid, sleGponCfmMepPriVlanid,
				sleGponCfmMepPeerMepid, sleGponCfmMepMaKey, sleGponCfmMepControlRequest, sleGponCfmMepControlStatus, sleGponCfmMepControlTimer,
				sleGponCfmMepControlTimeStamp, sleGponCfmMepControlReqResult, sleGponCfmMepControlOltId, sleGponCfmMepControlOnuId, sleGponCfmMepControlSlotType,
				sleGponCfmMepControlPortIndex, sleGponCfmMepControlMepid, sleGponCfmMepControlPriVlanid, sleGponCfmMepControlPeerMepid, sleGponCfmMepControlMaKey,
				sleGponCfmMepCcm, sleGponCfmMepControlCcm, sleGponCfmMipLevel, sleGponCfmMipVlan, sleGponCfmMipControlRequest,
				sleGponCfmMipControlStatus, sleGponCfmMipControlTimer, sleGponCfmMipControlTimeStamp, sleGponCfmMipControlReqResult, sleGponCfmMipControlOltId,
				sleGponCfmMipControlOnuId, sleGponCfmMipControlLevel, sleGponCfmMipControlVlan, sleGponCfmTestLbResultSlotType, sleGponCfmTestLbResultPortIndex,
				sleGponCfmTestLbResultRate, sleGponCfmTestLbResultAvg, sleGponCfmTestTrResultSlotType, sleGponCfmTestTrResultPortIndex, sleGponCfmTestTrResultReceiveOrder,
				sleGponCfmTestTrResultInfo, sleGponCfmTestControlRequest, sleGponCfmTestControlStatus, sleGponCfmTestControlTimer, sleGponCfmTestControlTimeStamp,
				sleGponCfmTestControlReqResult, sleGponCfmTestControlOltId, sleGponCfmTestControlOnuId, sleGponCfmTestControlSlotType, sleGponCfmTestControlPortindex,
				sleGponCfmTestControlMepid, sleGponCfmTestControlCount, sleGponCfmTestControlPriority, sleGponCfmTestControlLength, sleGponCfmTestControlTtl,
				sleGponProfile2BridgeControlMaxHost, sleGponOnuPMStatsSumOnuGEMPre15mLostPackets, sleGponOnuPMStatsSumOnuGEMPre15mMisInsertedPackets, sleGponOnuPMStatsSumOnuGEMPre15mReceivedPackets, sleGponOnuPMStatsSumOnuGEMPre15mReceivedBlocks,
				sleGponOnuPMStatsSumOnuGEMPre15mTransmittedBlocks, sleGponOnuPMStatsSumOnuGEMPre15mImpairedBlocks, sleGponOnuPMStatsSumOnuGEMHourLostPackets, sleGponOnuPMStatsSumOnuGEMHourMisInsertedPackets, sleGponOnuPMStatsSumOnuGEMHourReceivedPackets,
				sleGponOnuPMStatsSumOnuGEMHourReceivedBlocks, sleGponOnuPMStatsSumOnuGEMHourTransmittedBlocks, sleGponOnuPMStatsSumOnuGEMHourImpairedBlocks, sleGponOnuPMStatsSumOnuGEMDayLostPackets, sleGponOnuPMStatsSumOnuGEMDayMisInsertedPackets,
				sleGponOnuPMStatsSumOnuGEMDayReceivedPackets, sleGponOnuPMStatsSumOnuGEMDayReceivedBlocks, sleGponOnuPMStatsSumOnuGEMDayTransmittedBlocks, sleGponOnuPMStatsSumOnuGEMDayImpairedBlocks, sleGponOnuPMStatsSumOnuGEMTotalLostPackets,
				sleGponOnuPMStatsSumOnuGEMTotalMisInsertedPackets, sleGponOnuPMStatsSumOnuGEMTotalReceivedPackets, sleGponOnuPMStatsSumOnuGEMTotalReceivedBlocks, sleGponOnuPMStatsSumOnuGEMTotalTransmittedBlocks, sleGponOnuPMStatsSumOnuGEMTotalImpairedBlocks,
				sleGponOnuPMStatsSumOnuAniPre15mDiscardedFrames, sleGponOnuPMStatsSumOnuAniHourDiscardedFrames, sleGponOnuPMStatsSumOnuAniDayDiscardedFrames, sleGponOnuPMStatsSumOnuAniTotalDiscardedFrames, sleGponOnuPMStatsSumOnuEthFrameUpPre15mDropEvents,
				sleGponOnuPMStatsSumOnuEthFrameUpPre15mOctets, sleGponOnuPMStatsSumOnuEthFrameUpPre15mPackets, sleGponOnuPMStatsSumOnuEthFrameUpPre15mBcastPackets, sleGponOnuPMStatsSumOnuEthFrameUpPre15mMcastPackets, sleGponOnuPMStatsSumOnuEthFrameUpPre15mUcastPackets,
				sleGponOnuPMStatsSumOnuEthFrameUpPre15mCRCErroredPackets, sleGponOnuPMStatsSumOnuEthFrameUpPre15mUndersizePackets, sleGponOnuPMStatsSumOnuEthFrameUpPre15mOversizePackets, sleGponOnuPMStatsSumOnuEthFrameUpPre15mPkt64Octets, sleGponOnuPMStatsSumOnuEthFrameUpPre15mPkt65To127Octets,
				sleGponOnuPMStatsSumOnuEthFrameUpPre15mPkt128To255Octets, sleGponOnuPMStatsSumOnuEthFrameUpPre15mPkt256To511Octets, sleGponOnuPMStatsSumOnuEthFrameUpPre15mPkt512To1023Octets, sleGponOnuPMStatsSumOnuEthFrameUpPre15mPkt1024To1518Octets, sleGponOnuPMStatsSumOnuEthFrameUpHourDropEvents,
				sleGponOnuPMStatsSumOnuEthFrameUpHourOctets, sleGponOnuPMStatsSumOnuEthFrameUpHourPackets, sleGponOnuPMStatsSumOnuEthFrameUpHourBcastPackets, sleGponOnuPMStatsSumOnuEthFrameUpHourMcastPackets, sleGponOnuPMStatsSumOnuEthFrameUpHourUcastPackets,
				sleGponOnuPMStatsSumOnuEthFrameUpHourCRCErroredPackets, sleGponOnuPMStatsSumOnuEthFrameUpHourUndersizePackets, sleGponOnuPMStatsSumOnuEthFrameUpHourOversizePackets, sleGponOnuPMStatsSumOnuEthFrameUpHourPkt64Octets, sleGponOnuPMStatsSumOnuEthFrameUpHourPkt65To127Octets,
				sleGponOnuPMStatsSumOnuEthFrameUpHourPkt128To255Octets, sleGponOnuPMStatsSumOnuEthFrameUpHourPkt256To511Octets, sleGponOnuPMStatsSumOnuEthFrameUpHourPkt512To1023Octets, sleGponOnuPMStatsSumOnuEthFrameUpHourPkt1024To1518Octets, sleGponOnuPMStatsSumOnuEthFrameUpDayDropEvents,
				sleGponOnuPMStatsSumOnuEthFrameUpDayOctets, sleGponOnuPMStatsSumOnuEthFrameUpDayPackets, sleGponOnuPMStatsSumOnuEthFrameUpDayBcastPackets, sleGponOnuPMStatsSumOnuEthFrameUpDayMcastPackets, sleGponOnuPMStatsSumOnuEthFrameUpDayUcastPackets,
				sleGponOnuPMStatsSumOnuEthFrameUpDayCRCErroredPackets, sleGponOnuPMStatsSumOnuEthFrameUpDayUndersizePackets, sleGponOnuPMStatsSumOnuEthFrameUpDayOversizePackets, sleGponOnuPMStatsSumOnuEthFrameUpDayPkt64Octets, sleGponOnuPMStatsSumOnuEthFrameUpDayPkt65To127Octets,
				sleGponOnuPMStatsSumOnuEthFrameUpDayPkt128To255Octets, sleGponOnuPMStatsSumOnuEthFrameUpDayPkt256To511Octets, sleGponOnuPMStatsSumOnuEthFrameUpDayPkt512To1023Octets, sleGponOnuPMStatsSumOnuEthFrameUpDayPkt1024To1518Octets, sleGponOnuPMStatsSumOnuEthFrameUpTotalDropEvents,
				sleGponOnuPMStatsSumOnuEthFrameUpTotalOctets, sleGponOnuPMStatsSumOnuEthFrameUpTotalPackets, sleGponOnuPMStatsSumOnuEthFrameUpTotalBcastPackets, sleGponOnuPMStatsSumOnuEthFrameUpTotalMcastPackets, sleGponOnuPMStatsSumOnuEthFrameUpTotalUcastPackets,
				sleGponOnuPMStatsSumOnuEthFrameUpTotalCRCErroredPackets, sleGponOnuPMStatsSumOnuEthFrameUpTotalUndersizePackets, sleGponOnuPMStatsSumOnuEthFrameUpTotalOversizePackets, sleGponOnuPMStatsSumOnuEthFrameUpTotalPkt64Octets, sleGponOnuPMStatsSumOnuEthFrameUpTotalPkt65To127Octets,
				sleGponOnuPMStatsSumOnuEthFrameUpTotalPkt128To255Octets, sleGponOnuPMStatsSumOnuEthFrameUpTotalPkt256To511Octets, sleGponOnuPMStatsSumOnuEthFrameUpTotalPkt512To1023Octets, sleGponOnuPMStatsSumOnuEthFrameUpTotalPkt1024To1518Octets, sleGponOnuPMStatsSumOnuEthFrameDownPre15mDropEvents,
				sleGponOnuPMStatsSumOnuEthFrameDownPre15mOctets, sleGponOnuPMStatsSumOnuEthFrameDownPre15mPackets, sleGponOnuPMStatsSumOnuEthFrameDownPre15mBcastPackets, sleGponOnuPMStatsSumOnuEthFrameDownPre15mMcastPackets, sleGponOnuPMStatsSumOnuEthFrameDownPre15mUcastPackets,
				sleGponOnuPMStatsSumOnuEthFrameDownPre15mCRCErroredPackets, sleGponOnuPMStatsSumOnuEthFrameDownPre15mUndersizePackets, sleGponOnuPMStatsSumOnuEthFrameDownPre15mOversizePackets, sleGponOnuPMStatsSumOnuEthFrameDownPre15mPkt64Octets, sleGponOnuPMStatsSumOnuEthFrameDownPre15mPkt65To127Octets,
				sleGponOnuPMStatsSumOnuEthFrameDownPre15mPkt128To255Octets, sleGponOnuPMStatsSumOnuEthFrameDownPre15mPkt256To511Octets, sleGponOnuPMStatsSumOnuEthFrameDownPre15mPkt512To1023Octets, sleGponOnuPMStatsSumOnuEthFrameDownPre15mPkt1024To1518Octets, sleGponOnuPMStatsSumOnuEthFrameDownHourDropEvents,
				sleGponOnuPMStatsSumOnuEthFrameDownHourOctets, sleGponOnuPMStatsSumOnuEthFrameDownHourPackets, sleGponOnuPMStatsSumOnuEthFrameDownHourBcastPackets, sleGponOnuPMStatsSumOnuEthFrameDownHourMcastPackets, sleGponOnuPMStatsSumOnuEthFrameDownHourUcastPackets,
				sleGponOnuPMStatsSumOnuEthFrameDownHourCRCErroredPackets, sleGponOnuPMStatsSumOnuEthFrameDownHourUndersizePackets, sleGponOnuPMStatsSumOnuEthFrameDownHourOversizePackets, sleGponOnuPMStatsSumOnuEthFrameDownHourPkt64Octets, sleGponOnuPMStatsSumOnuEthFrameDownHourPkt65To127Octets,
				sleGponOnuPMStatsSumOnuEthFrameDownHourPkt128To255Octets, sleGponOnuPMStatsSumOnuEthFrameDownHourPkt256To511Octets, sleGponOnuPMStatsSumOnuEthFrameDownHourPkt512To1023Octets, sleGponOnuPMStatsSumOnuEthFrameDownHourPkt1024To1518Octets, sleGponOnuPMStatsSumOnuEthFrameDownDayDropEvents,
				sleGponOnuPMStatsSumOnuEthFrameDownDayOctets, sleGponOnuPMStatsSumOnuEthFrameDownDayPackets, sleGponOnuPMStatsSumOnuEthFrameDownDayBcastPackets, sleGponOnuPMStatsSumOnuEthFrameDownDayMcastPackets, sleGponOnuPMStatsSumOnuEthFrameDownDayUcastPackets,
				sleGponOnuPMStatsSumOnuEthFrameDownDayCRCErroredPackets, sleGponOnuPMStatsSumOnuEthFrameDownDayUndersizePackets, sleGponOnuPMStatsSumOnuEthFrameDownDayOversizePackets, sleGponOnuPMStatsSumOnuEthFrameDownDayPkt64Octets, sleGponOnuPMStatsSumOnuEthFrameDownDayPkt65To127Octets,
				sleGponOnuPMStatsSumOnuEthFrameDownDayPkt128To255Octets, sleGponOnuPMStatsSumOnuEthFrameDownDayPkt256To511Octets, sleGponOnuPMStatsSumOnuEthFrameDownDayPkt512To1023Octets, sleGponOnuPMStatsSumOnuEthFrameDownDayPkt1024To1518Octets, sleGponOnuPMStatsSumOnuEthFrameDownTotalDropEvents,
				sleGponOnuPMStatsSumOnuEthFrameDownTotalOctets, sleGponOnuPMStatsSumOnuEthFrameDownTotalPackets, sleGponOnuPMStatsSumOnuEthFrameDownTotalBcastPackets, sleGponOnuPMStatsSumOnuEthFrameDownTotalMcastPackets, sleGponOnuPMStatsSumOnuEthFrameDownTotalUcastPackets,
				sleGponOnuPMStatsSumOnuEthFrameDownTotalCRCErroredPackets, sleGponOnuPMStatsSumOnuEthFrameDownTotalUndersizePackets, sleGponOnuPMStatsSumOnuEthFrameDownTotalOversizePackets, sleGponOnuPMStatsSumOnuEthFrameDownTotalPkt64Octets, sleGponOnuPMStatsSumOnuEthFrameDownTotalPkt65To127Octets,
				sleGponOnuPMStatsSumOnuEthFrameDownTotalPkt128To255Octets, sleGponOnuPMStatsSumOnuEthFrameDownTotalPkt256To511Octets, sleGponOnuPMStatsSumOnuEthFrameDownTotalPkt512To1023Octets, sleGponOnuPMStatsSumOnuEthFrameDownTotalPkt1024To1518Octets, sleGponOnuPMStatsSumOnuUniEth3Pre15mDropEvents,
				sleGponOnuPMStatsSumOnuUniEth3Pre15mOctets, sleGponOnuPMStatsSumOnuUniEth3Pre15mPackets, sleGponOnuPMStatsSumOnuUniEth3Pre15mBcastPackets, sleGponOnuPMStatsSumOnuUniEth3Pre15mMcastPackets, sleGponOnuPMStatsSumOnuUniEth3Pre15mUcastPackets,
				sleGponOnuPMStatsSumOnuUniEth3Pre15mUndersizePackets, sleGponOnuPMStatsSumOnuUniEth3Pre15mFragments, sleGponOnuPMStatsSumOnuUniEth3Pre15mJabbers, sleGponOnuPMStatsSumOnuUniEth3Pre15mPkt64Octets, sleGponOnuPMStatsSumOnuUniEth3Pre15mPkt65To127Octets,
				sleGponOnuPMStatsSumOnuUniEth3Pre15mPkt128To255Octets, sleGponOnuPMStatsSumOnuUniEth3Pre15mPkt256To511Octets, sleGponOnuPMStatsSumOnuUniEth3Pre15mPkt512To1023Octets, sleGponOnuPMStatsSumOnuUniEth3Pre15mPkt1024To1518Octets, sleGponOnuPMStatsSumOnuUniEth3HourDropEvents,
				sleGponOnuPMStatsSumOnuUniEth3HourOctets, sleGponOnuPMStatsSumOnuUniEth3HourPackets, sleGponOnuPMStatsSumOnuUniEth3HourBcastPackets, sleGponOnuPMStatsSumOnuUniEth3HourMcastPackets, sleGponOnuPMStatsSumOnuUniEth3HourUcastPackets,
				sleGponOnuPMStatsSumOnuUniEth3HourUndersizePackets, sleGponOnuPMStatsSumOnuUniEth3HourFragments, sleGponOnuPMStatsSumOnuUniEth3HourJabbers, sleGponOnuPMStatsSumOnuUniEth3HourPkt64Octets, sleGponOnuPMStatsSumOnuUniEth3HourPkt65To127Octets,
				sleGponOnuPMStatsSumOnuUniEth3HourPkt128To255Octets, sleGponOnuPMStatsSumOnuUniEth3HourPkt256To511Octets, sleGponOnuPMStatsSumOnuUniEth3HourPkt512To1023Octets, sleGponOnuPMStatsSumOnuUniEth3HourPkt1024To1518Octets, sleGponOnuPMStatsSumOnuUniEth3DayDropEvents,
				sleGponOnuPMStatsSumOnuUniEth3DayOctets, sleGponOnuPMStatsSumOnuUniEth3DayPackets, sleGponOnuPMStatsSumOnuUniEth3DayBcastPackets, sleGponOnuPMStatsSumOnuUniEth3DayMcastPackets, sleGponOnuPMStatsSumOnuUniEth3DayUcastPackets,
				sleGponOnuPMStatsSumOnuUniEth3DayUndersizePackets, sleGponOnuPMStatsSumOnuUniEth3DayFragments, sleGponOnuPMStatsSumOnuUniEth3DayJabbers, sleGponOnuPMStatsSumOnuUniEth3DayPkt64Octets, sleGponOnuPMStatsSumOnuUniEth3DayPkt65To127Octets,
				sleGponOnuPMStatsSumOnuUniEth3DayPkt128To255Octets, sleGponOnuPMStatsSumOnuUniEth3DayPkt256To511Octets, sleGponOnuPMStatsSumOnuUniEth3DayPkt512To1023Octets, sleGponOnuPMStatsSumOnuUniEth3DayPkt1024To1518Octets, sleGponOnuPMStatsSumOnuUniEth3TotalDropEvents,
				sleGponOnuPMStatsSumOnuUniEth3TotalOctets, sleGponOnuPMStatsSumOnuUniEth3TotalPackets, sleGponOnuPMStatsSumOnuUniEth3TotalBcastPackets, sleGponOnuPMStatsSumOnuUniEth3TotalMcastPackets, sleGponOnuPMStatsSumOnuUniEth3TotalUcastPackets,
				sleGponOnuPMStatsSumOnuUniEth3TotalUndersizePackets, sleGponOnuPMStatsSumOnuUniEth3TotalFragments, sleGponOnuPMStatsSumOnuUniEth3TotalJabbers, sleGponOnuPMStatsSumOnuUniEth3TotalPkt64Octets, sleGponOnuPMStatsSumOnuUniEth3TotalPkt65To127Octets,
				sleGponOnuPMStatsSumOnuUniEth3TotalPkt128To255Octets, sleGponOnuPMStatsSumOnuUniEth3TotalPkt256To511Octets, sleGponOnuPMStatsSumOnuUniEth3TotalPkt512To1023Octets, sleGponOnuPMStatsSumOnuUniEth3TotalPkt1024To1518Octets, sleGponCfmTestLbResultMepId,
				sleGponCfmTestTrResultMepId, sleGponCfmTestControlRmepid, sleGponCfmTestControlRmac, sleGponCfmRmepSlotType, sleGponCfmRmepPortIndex,
				sleGponCfmRmepIndex, sleGponCfmRmepMepId, sleGponCfmRmepRmepId, sleGponCfmRmepRmac, sleGponCfmRmepState,
				sleGponCfmRmepControlRequest, sleGponCfmRmepControlStatus, sleGponCfmRmepControlTimer, sleGponCfmRmepControlTimeStamp, sleGponCfmRmepControlReqResult,
				sleGponCfmRmepControlOltId, sleGponCfmRmepControlOnuId, sleGponCfmRmepControlSlotType, sleGponCfmRmepControlPortindex, sleGponOnuPortPowerControl,
				sleGponOnuPortControlPowerControl, sleGponOnuPppoeIndex, sleGponOnuPppoeAdminState, sleGponOnuPppoeStatus, sleGponOnuPppoeAuthType,
				sleGponOnuPppoeUsername, sleGponOnuPppoePassword, sleGponOnuPppoeMtu, sleGponOnuPppoeLCPInterval, sleGponOnuPppoeControlRequest,
				sleGponOnuPppoeControlStatus, sleGponOnuPppoeControlTimer, sleGponOnuPppoeiControlTimeStamp, sleGponOnuPppoeControlReqResult, sleGponOnuPppoeControlOltIndex,
				sleGponOnuPppoeControlOnuIndex, sleGponOnuPppoeControlIndex, sleGponOnuHostType, sleGponOnuHostIPv6LinkLocalAddr, sleGponOnuHostIPv6Addr,
				sleGponOnuHostIPv6DefaultRouter, sleGponOnuHostIPv6PriDns, sleGponOnuHostIPv6SecDns, sleGponOnuHostIPv6PrefixLen, sleGponOnuHostControlIPv6Addr,
				sleGponOnuHostControlIPv6PrefixLen, sleGponOnuHostControlIPv6DefaultRouter, sleGponOnuIPv6HostCurAddrOltId, sleGponOnuIPv6HostCurAddrOnuId, sleGponOnuIPv6HostCurAddrHostId,
				sleGponOnuIPv6HostCurAddrId, sleGponOnuIPv6HostCurAddr, sleGponOnuIPv6HostCurDefaultRouterOltId, sleGponOnuIPv6HostCurDefaultRouterOnuId, sleGponOnuIPv6HostCurDefaultRouterHostId,
				sleGponOnuIPv6HostCurDefaultRouterId, sleGponOnuIPv6HostCurDefaultRouter, sleGponOnuIPv6HostCurDnsOltId, sleGponOnuIPv6HostCurDnsOnuId, sleGponOnuIPv6HostCurDnsHostId,
				sleGponOnuIPv6HostCurDnsId, sleGponOnuIPv6HostCurDns, sleGponCfmTestLbResultValidCount, sleGponProfile2BridgeUniIneterDomainName, sleGponProfile2BridgeUniControlInterDomainName,
				sleGponProfile2Ipv6HostSvcSuppressRs, sleGponProfile2Ipv6HostSvcDhcpClient, sleGponProfile2Ipv6HostSvcPriDns, sleGponProfile2Ipv6HostSvcSecDns, sleGponProfile2Ipv6HostSvcControlSuppressRs,
				sleGponProfile2Ipv6HostSvcControlDhcpClient, sleGponProfile2Ipv6HostSvcControlPriDns, sleGponProfile2Ipv6HostSvcControlSecDns, sleGponOltServiceOltIndex, sleGponOltServiceProfileIndex,
				sleGponOltServiceProfileModelName, sleGponOltServiceProfileProfileName, sleGponOltServiceProfileControlRequest, sleGponOltServiceProfileControlStatus, sleGponOltServiceProfileControlTimer,
				sleGponOltServiceProfileControlTimeStamp, sleGponOltServiceProfileControlReqResult, sleGponOltServiceProfileControlOltIndex, sleGponOltServiceProfileControlModelName, sleGponOltServiceProfileControlProfileName,
				sleGponProfile2McastIgmpDsTagCtrl, sleGponProfile2McastIgmpDsTagCtrlVid, sleGponProfile2McastIgmpDsTagCtrlCos, sleGponProfile2McastControlIgmpDsTagCtrl, sleGponProfile2McastControlIgmpDsTagCtrlVid,
				sleGponProfile2McastControlIgmpDsTagCtrlCos, sleGponOnuBootReason, sleGponOnuServiceMode, sleGponOnuServiceStatus, sleGponOnuAutoUpgradeMode,
				sleGponOnuControlServiceMode, sleGponOnuControlAutoUpgradeMode, sleGponOnuAlarmStatus, sleGponOnuHostIPv6CurDefaultRouter, sleGponOnuHostIPv6CurPriDns,
				sleGponOnuHostIPv6CurSecDns, sleGponOnuReauthStartTime, sleGponOnuReauthEndTime, sleGponOnuAuthFailInterval1, sleGponOnuAuthFailInterval2,
				sleGponOnuAuthFailInterval3, sleGponOnuAuthFailInterval4, sleGponOnuAuthFailInterval5, sleGponOnuAuthServerTimeout, sleGponOnuAuthServerRetry,
				sleGponOnuAuthPps, sleGponOnuAuthErrorReport, sleGponBaseControlOnuReauthStartTime, sleGponBaseControlOnuReauthEndTime, sleGponBaseControlOnuAuthFailInterval1,
				sleGponBaseControlOnuAuthFailInterval2, sleGponBaseControlOnuAuthFailInterval3, sleGponBaseControlOnuAuthFailInterval4, sleGponBaseControlOnuAuthFailInterval5, sleGponBaseControlOnuAuthServerTimeout,
				sleGponBaseControlOnuAuthServerRetry, sleGponBaseControlOnuAuthPps, sleGponBaseControlOnuAuthErrorReport, sleGponOnuAuthOnuProfile, sleGponOnuAuthOnuVlan4,
				sleGponOnuAuthOnuVlan6, sleGponOnuAuthOnuIpv4, sleGponOnuAuthOnuIpv6, sleGponOnuAuthOnuUniEthMedium, sleGponOnuAuthOnuUniEthSpeed,
				sleGponOnuAuthOnuUniEthDuplex, sleGponOnuControlAuthOnuProfile, sleGponOnuControlAuthOnuVlan4, sleGponOnuControlAuthOnuVlan6, sleGponOnuControlAuthOnuIpv4,
				sleGponOnuControlAuthOnuIpv6, sleGponOnuControlAuthOnuUniEthMedium, sleGponOnuControlAuthOnuUniEthSpeed, sleGponOnuControlAuthOnuUniEthDuplex, sleGponCfmRmepControlMepid,
				sleGponOnuAuthRadiusUserPassword, sleGponBaseControlOnuAuthRadiusUserPassword, sleGponOnuControlMoveOltId, sleGponProfile2BridgeUniPQId, sleGponProfile2BridgeUniPQGreenMinThreshold,
				sleGponProfile2BridgeUniPQGreenMaxThreshold, sleGponProfile2BridgeUniPQYellowMinThreshold, sleGponProfile2BridgeUniPQYellowMaxThreshold, sleGponProfile2BridgeUniPQGreenProbability, sleGponProfile2BridgeUniPQYellowProbability,
				sleGponProfile2BridgeUniPQAverageCoefficient, sleGponProfile2BridgeUniPQDropPrecedence, sleGponProfile2BridgeUniPQControlRequest, sleGponProfile2BridgeUniPQControlStatus, sleGponProfile2BridgeUniPQControlTimer,
				sleGponProfile2BridgeUniPQControlTimeStamp, sleGponProfile2BridgeUniPQControlReqResult, sleGponProfile2BridgeUniPQControlTName, sleGponProfile2BridgeUniPQControlBridgeId, sleGponProfile2BridgeUniPQControlType,
				sleGponProfile2BridgeUniPQControlUniId, sleGponProfile2BridgeUniPQControlId, sleGponProfile2BridgeUniPQControlGreenMinThreshold, sleGponProfile2BridgeUniPQControlGreenMaxThreshold, sleGponProfile2BridgeUniPQControlYellowMinThreshold,
				sleGponProfile2BridgeUniPQControlYellowMaxThreshold, sleGponProfile2BridgeUniPQControlGreenProbability, sleGponProfile2BridgeUniPQControlYellowProbability, sleGponProfile2BridgeUniPQControlAverageCoefficient, sleGponProfile2BridgeUniPQControlDropPrecedence,
				sleGponOnuHostControlIPppoeAccountUser, sleGponOnuHostControlIPppoeAccountPassword, sleGponOnuControlMoveOnuId, sleGponOnuAuthOnuUniPortAdmin, sleGponOnuAuthOnuErrorReason,
				sleGponOnuControlAuthOnuUniPortAdmin, sleGponProfile2TcontPQId, sleGponProfile2TcontPQGreenMinThreshold, sleGponProfile2TcontPQGreenMaxThreshold, sleGponProfile2TcontPQYellowMinThreshold,
				sleGponProfile2TcontPQYellowMaxThreshold, sleGponProfile2TcontPQGreenProbability, sleGponProfile2TcontPQYellowProbability, sleGponProfile2TcontPQAverageCoefficient, sleGponProfile2TcontPQDropPrecedence,
				sleGponProfile2TcontPQControlRequest, sleGponProfile2TcontPQControlStatus, sleGponProfile2TcontPQControlTimer, sleGponProfile2TcontPQControlTimeStamp, sleGponProfile2TcontPQControlReqResult,
				sleGponProfile2TcontPQControlTName, sleGponProfile2TcontPQTcontId, sleGponProfile2TcontPQControlId, sleGponProfile2TcontPQControlGreenMinThreshold, sleGponProfile2TcontPQControlGreenMaxThreshold,
				sleGponProfile2TcontPQControlYellowMinThreshold, sleGponProfile2TcontPQControlYellowMaxThreshold, sleGponProfile2TcontPQControlGreenProbability, sleGponProfile2TcontPQControlYellowProbability, sleGponProfile2TcontPQControlAverageCoefficient,
				sleGponOnuVideoStatusUpdateTime, sleGponBaseControlOnuVideoStatusUpdateTime, sleGponOnuPppoeStatusUpdateTime, sleGponBaseControlOnuPppoeStatusUpdateTime, sleGponOnuAuthOnuOmccVersion,
				sleGponProfile2OnuGsp, sleGponProfile2OnuGspAvcReportRate, sleGponProfile2OnuControlGsp, sleGponProfile2OnuControlGspAvcReportRate, sleGponOnuGspType,
				sleGponOnuGspIndex, sleGponOnuGspData, sleGponOnuGspControlRequest, sleGponOnuGspControlStatus, sleGponOnuGspControlTimer,
				sleGponOnuGspControlTimeStamp, sleGponOnuGspControlReqResult, sleGponOnuGspControlOltId, sleGponOnuGspControlOnuId, sleGponOnuGspControlType,
				sleGponOnuGspStstusUptime, sleGponOnuGspConfigUptime, sleGponOltTransceiverType, sleGponOltControlTransceiverType, sleGponOltOmccRecovery,
				sleGponOltOmccRecoveryMethod, sleGponOltOmccRecoveryThreshold, sleGponOltControlOmccRecovery, sleGponOltControlOmccRecoveryMethod, sleGponOltControlOmccRecoveryThreshold,
				sleGponProfile2OnuSnmpROCommunity, sleGponProfile2OnuSnmpRWCommunity, sleGponProfile2OnuSnmpAgentAddresHost, sleGponProfile2OnuSnmpTrapHostAddress, sleGponProfile2OnuSnmpTrapHostPort,
				sleGponProfile2OnuSnmpSysName, sleGponProfile2OnuControlSnmpROCommunity, sleGponProfile2OnuControlSnmpRWCommunity, sleGponProfile2OnuControlSnmpAgentAddresHost, sleGponProfile2OnuControlSnmpTrapHostAddress,
				sleGponProfile2OnuControlSnmpTrapHostPort, sleGponProfile2OnuControlSnmpSysName, sleGponProfile2TcontPQControlDropPrecedence, sleGponOnuHostPppoeAccountUser, sleGponOnuHostPppoeAccountPassword,
				sleGponProfile2OnuSnmpSecurityName, sleGponProfile2OnuControlSnmpSecurityName }
			STATUS current
			DESCRIPTION
				"Description."
			::= { sleGpon 53 }


--  1.3.6.1.4.1.6296.101.23.54
		sleGponNotificationGroup NOTIFICATION-GROUP
			NOTIFICATIONS { sleGponProfile2DbaAdded, sleGponProfile2DbaDeleted, sleGponProfile2DbaSlaChanged, sleGponProfile2TrafficAdded, sleGponProfile2TrafficDeleted,
				sleGponProfile2MapperAdded, sleGponProfile2MapperDeleted, sleGponProfile2MapperGemportCountChanged, sleGponProfile2MapperDefaultCoSChanged, sleGponProfile2MapperDscp2BitChanged,
				sleGponProfile2MapperCosGemportChanged, sleGponProfile2BridgeAdded, sleGponProfile2BridgeDeleted, sleGponProfile2BridgeMacLearningChanged, sleGponProfile2BridgeMaxHostChanged,
				sleGponProfile2BridgeMcastChanged, sleGponProfile2BridgeAniAdded, sleGponProfile2BridgeAniDeleted, sleGponProfile2BridgeAniVlanFilterChanged, sleGponProfile2BridgeUniAdded,
				sleGponProfile2BridgeUniDeleted, sleGponProfile2BridgeUniVlanDsOpChanged, sleGponProfile2BridgeUniVlanUsOpChanged, sleGponProfile2BridgeUniPortAdminChanged, sleGponProfile2BridgeUniRateLimitChanged,
				sleGponProfile2BridgeUniIgmpMaxGroupChanged, sleGponProfile2BridgeUniMaxFrameChanged, sleGponProfile2BridgeUniMcastProfileChanged, sleGponProfile2BridgeUniVlanFilterChanged, sleGponProfile2McastProfileAdded,
				sleGponProfile2McastProfileDeleted, sleGponProfile2McastIgmpFuncChanged, sleGponProfile2McastIgmpImmLeaveChanged, sleGponProfile2McastIgmpRobustChanged, sleGponProfile2McastIgmpQuerierInfoChanged,
				sleGponProfile2McastIgmpVersionChanged, sleGponProfile2McastIgmpUpRateLimitChanged, sleGponProfile2McastIgmpTagCtrlChanged, sleGponProfile2McastAclAdded, sleGponProfile2McastAclDeleted,
				sleGponProfile2McastSAclAdded, sleGponProfile2McastSAclDeleted, sleGponBaseCableDownStatusChanged, sleGponBaseCableDownRefCntChanged, sleGponOltDiscoverySerialStarted,
				sleGponOltDiscoverySerialStopped, sleGponOltLinkMaxDistanceChanged, sleGponOltKeyExchangeStarted, sleGponOltKeyExchangeStopped, sleGponOltSignalCheckChanged,
				sleGponOltSignalCheckAutoOnuBlockChanged, sleGponOltDescriptionChanged, sleGponOltAutoToManualChanged, sleGponOltDefaultTcontChanged, sleGponOltDefaultTcontRemoved,
				sleGponOltDefaultProfileChanged, sleGponOltDefaultProfileRemoved, sleGponOnuRegistered, sleGponOnuDeregistered, sleGponOnuProfileChanged,
				sleGponOnuFixed, sleGponOnuUpgradeNosChanged, sleGponOnuNosActiveChanged, sleGponOnuEncModeChanged, sleGponOnuReset,
				sleGponOnuTxOffOpticChanged, sleGponOnuDescriptionChanged, sleGponTcontCreated, sleGponTcontDestroyed, sleGponProfileBaseCreated,
				sleGponProfileBaseModified, sleGponProfileBaseDestroyed, sleGponProfilePortRateLimitChanged, sleGponProfilePortMaxHostChanged, sleGponProfilePortVlanOperChanged,
				sleGponProfilePortVlanFilterChanged, sleGponOnuPortAdminChanged, sleGponOltStatsCleared, sleGponFirmwareUpgradeProfileChanged, sleGponFirmwareDeleted,
				sleGponOnuFWAutoUpgradeModeChanged, sleGponOnuFWAutoUpgradeVersionMatchChanged, sleGponOnuFWAutoUpgradeInvalidVersionMatchChanged, sleGponOnuFWAutoUpgradeStartEndTimeChanged, sleGponOnuFWAutoUpgradeRebootTimeChanged,
				sleGponOnuFWAutoUpgradeModelProfileChanged, gponOntFwDownloaded, gponOntFwUpgraded, gponOntFwOntReseted, gponOntFwDeleted,
				gponOntFwDeleteAll, sleGponOltFecModeUSChanged, sleGponOltFecModeDSChanged, sleGponOltMacAgingTimeChanged, sleGponOltTransceiverPortChanged,
				sleGponOnuFecModeChanged, sleGponOnuIPInfoChanged, sleGponProfileTcontProfileChanged, sleGponProfileBaseVoIPProfileChanged, sleGponProfileDbaCreated,
				sleGponProfileDbaDestroyed, sleGponProfileMultiTcontProfileCreated, sleGponProfileMultiTcontProfileDestroyed, sleGponProfileMultiTcontProfileDscp2PbitChanged, sleGponProfileMultiTcontProfilePriQWeightChanged,
				sleGponProfileMultiTcontProfileGemportChanged, sleGponProfileVoIPProfileCreated, sleGponProfileVoIPProfileDestroyed, sleGponProfilVoIPProfileServiceChanged, sleGponProfileVoIPProfileOmciChanged,
				sleGponProfileVoIPOmciSIPAuthChanged, sleGponProfileVoIPOmciSIPPhoneChnaged, sleGponProfileVoIPIpPathInfoChanged, sleGponOnuFWAutoUpgradeModelDeleted, sleGponOnuPortAutoNegoChanged,
				sleGponProfilePortAdminChanged, sleGponProfilePortDuplexChanged, sleGponProfilePortSpeedChanged, sleGponOnuPortSpeedChanged, sleGponOnuFWAutoUpgradeMTimeDeleted,
				sleGponOnuFWAutoUpgradeModelModifyTargetVer, sleGponOltProtectionChanged, sleGponOnuActivationChanged, sleGponRedGroupChanged, sleGponRedGroupCleared,
				sleGponRedGroupForceSwitchovered, sleGponProfilePorPauseChanged, sleGponProfile2OnuAdded, sleGponProfile2OnuDeleted, sleGponProfile2OnuRogueInfoChanged,
				sleGponProfile2OnuRxPowerChanged, sleGponProfile2OnuTrafficProfileChanged, sleGponOltAuthStatsCleared, sleGponOnuPortStatisticsCleared, sleGponProfileDbaChanged,
				sleGponOltActivateStatusChanged, sleGponOnuFWAutoUpgradeMTimeChanged, sleGponOnuPMProfileChanged, sleGponProfile2PMProfileAdded, sleGponProfile2PMProfileDeleted,
				sleGponProfile2TcontGemportAdded, sleGponProfile2BridgeUniIpInfoChanged, sleGponProfile2BridgeUniVoipProfileChanged, sleGponProfile2TcontGemportDeleted, sleGponOltOpticParamChanged,
				sleGponOnuUpgradeNosPartitionChanged, sleGponOnuUpgradeNosCommited, sleGponOnuUpgradeNosActiveChanged, sleGponOnuPMStatsCleared, sleGponProfile2OnuPmProfileChanged,
				sleGponProfile2OnuUniRateLimitChanged, sleGponProfile2OnuUniVlanDsOperChanged, sleGponProfile2OnuUniVlanUsOperChanged, sleGponProfile2OnuUniIgmpMaxGroupChanged, sleGponProfile2OnuUniPortAdminChanged,
				sleGponProfile2OnuBridgeMaxHostChanged, sleGponOnuHostIPInfoChanged, sleGponBaseDefaultServiceProfileChanged, sleGponOltSrcMacMonitorChanged, sleGponOltTotalUsBwChanged,
				sleGponOnuBlockChanged, sleGponServiceProfileModelChanged, sleGponOnuUserMacOltMacChanged, sleGponOnuUserMacOltMacOnuChanged, sleGponFirmwareDownloadChanged,
				sleGponOnuFWAutoUpgradeModelTargetVerDeleted, sleGponProfileTdmPwMtProfileCreated, sleGponProfileTdmPwMtProfileDeleted, sleGponProfileTdmPwMtMaxDepthChanged, sleGponProfileTdmDesiredDepthChanged,
				sleGponProfileTdmFillPolicyChanged, sleGponProfileTdmMisconnectDeclarePolicyChanged, sleGponProfileTdmMisconnectClearPolicyChanged, sleGponProfileTdmLossDeclarePolicyChanged, sleGponProfileTdmLossClearPolicyChanged,
				sleGponProfileTdmBuffUnderrunDeclarePolicyChanged, sleGponProfileTdmbuffUnderrunClearPolicyChanged, sleGponProfileTdmMalformedDeclarePolicyChanged, sleGponProfileTdmMalformedClearPolicyChanged, sleGponProfileTdmRBitTransmitPolicyChanged,
				sleGponProfileTdmRBitReceivePolicyChanged, sleGponProfileTdmLBitReceivePolicyChanged, sleGponProfileTdmSesThresholdChanged, sleGponProfileTdmPwProfileCreated, sleGponProfileTdmPwProfileDeleted,
				sleGponProfileTdmPwServiceTypeChanged, sleGponProfileTdmPwSignallingChanged, sleGponProfileTdmPwPayloadSizeChanged, sleGponProfileTdmPwPayloadEncapsulationDelayChanged, sleGponProfileTdmPwTimingModeChanged,
				sleGponProfile2TdmSvcTdmServiceCreated, sleGponProfile2TdmSvcTdmServiceDeleted, sleGponProfile2TdmSvcTdmPwProfileChanged, sleGponProfile2TdmSvcTdmVlanFilterChanged, sleGponProfile2TdmSvcTdmEthDestMacChanged,
				sleGponProfile2TdmSvcTdmEthTagPolicyChanged, sleGponProfile2TdmSvcTdmTranEcidChanged, sleGponProfile2TdmSvcTdmRecvEcidChanged, sleGponProfile2TdmSvcTdmExpectEcidChanged, sleGponProfile2TdmSvcTdmUdpPortChanged,
				sleGponProfile2TdmSvcTdmFarEndIpChanged, sleGponProfile2TdmSvcMplsLabelIndicatorChanged, sleGponProfile2TdmSvcMplsPwDirectionChanged, sleGponProfile2TdmSvcMplsPwLabelChanged, sleGponProfile2TdmSvcMplsPwTunnelDirectionChanged,
				sleGponProfile2TdmSvcMplsPwTunnelLabelChanged, sleGponProfile2TdmSvcCesBuffCdvToleranceChanged, sleGponProfile2TdmSvcCesChannelAssociateSignalChanged, sleGponProfileTdmSdhProfileCreated, sleGponProfileTdmSdhProfileDeleted,
				sleGponProfileTdmSdhTuTypeChanged, sleGponProfileTdmSdhGemLossIntergrationPeriodChanged, sleGponProfileTdmSdhTransmitJ1J2Changed, sleGponProfileTdmSdhExpectJ1J2Changed, sleGponProfileTdmSdhreceiveJ1J2Changed,
				sleGponProfileTdmSdhTimMonitorChanged, sleGponProfileTdmSdhTimAisChanged, sleGponProfile2IpHostSvcIpHostSvcCreated, sleGponProfile2IpHostSvcIpHostSvcDeleted, sleGponProfile2IpHostSvcAddressTypeChanged,
				sleGponProfile2IpHostSvcDnsChanged, sleGponProfile2IpHostSvcVlanFilterChanged, sleGponProfile2IpHostSvcVlanDsOperChanged, sleGponProfile2IpHostSvcVlanUsOperChanged, sleGponProfileVoIPProfileIpwayChanged,
				sleGponProfileVoIPDetailProfileCreated, sleGponProfileVoIPDetailProfileDeleted, sleGponProfileVoIPDetailFaxModeChanged, sleGponProfileVoIPDetailOobDtmfChanged, sleGponProfileVoIPDetailAnnouncementTypeChanged,
				sleGponProfileVoIPDetailJitterTargetChanged, sleGponProfileVoIPDetailJitterBuffMaxChanged, sleGponProfileVoIPDetailEchoCancelChanged, sleGponProfileVoIPDetailPstnProtoChanged, sleGponProfileVoIPDetailDtmfDigitChanged,
				sleGponProfileVoIPDetailHookFlashTimeMinChanged, sleGponProfileVoIPDetailHookFlashTimeMaxChanged, sleGponProfileVoIPDetailSignalingCodeChanged, sleGponProfileVoIPDetailRtpLocalPortChanged, sleGponProfileVoIPDetailRtpDscpMarkChanged,
				sleGponProfileVoIPDetailRtpPiggybackEventChanged, sleGponProfileVoIPDetailRtpToneEventChanged, sleGponProfileVoIPDetailRtpDtmfEventChanged, sleGponProfileVoIPDetailRtpCasEventChanged, sleGponProfileVoIPDetailProtocolChanged,
				sleGponProfileVoIPDetailMgcPriServerChanged, sleGponProfileVoIPDetailMgcSecServerChanged, sleGponProfileVoIPDetailMgcVersionChanged, sleGponProfileVoIPDetailMgcFormatChanged, sleGponProfileVoIPDetailMgcMaxRetryTimeChanged,
				sleGponProfileVoIPDetailMgcRetryAttemptsChanged, sleGponProfileVoIPDetailMgcServiceChangeDelayChanged, sleGponProfileVoIPDetailMgcTerminationIdChanged, sleGponProfileVoIPDetailMgcSoftswitchChanged, sleGponProfileVoIPDetailVoicemailServerChanged,
				sleGponProfileVoIPDetailVoicemailExpireTimeChanged, sleGponProfileVoIPDetailReleaseTimeChanged, sleGponProfileVoIPDetailRohTimerChanged, sleGponProfileVoIPDetailProxyServerChanged, sleGponProfileVoIPDetailOutboundProxyServerChanged,
				sleGponProfileVoIPDetailRegisterServerChanged, sleGponProfileVoIPDetailHostpartServerChanged, sleGponProfileVoIPDetailDnsChanged, sleGponProfileVoIPDetailRegExpTimeChanged, sleGponProfileVoIPDetailReregHeadStartTimeChanged,
				sleGponProfileVoIPDetailSoftSwitchChanged, sleGponProfileVoIPDetailSipOptionTransmitCtlChanged, sleGponProfileVoIPDetailSipUriFormatChanged, sleGponProfileVoIPDetailCallerIdChanged, sleGponProfileVoIPDetailCallWaitingChanged,
				sleGponProfileVoIPDetailCallProgressTransferChanged, sleGponProfileVoIPDetailCallPresentChanged, sleGponProfileVoIPDetailDirectConnectChanged, sleGponProfileVoIPDetailDirectConnectUriChanged, sleGponProfileVoIPDetailBridgedLineAgentUriChanged,
				sleGponProfileVoIPDetailConferenceFactoryUriChanged, sleGponProfileVoIPDetailCancelCallWaitChanged, sleGponProfileVoIPDetailCallParkChanged, sleGponProfileVoIPDetailCallerIdActChanged, sleGponProfileVoIPDetailCallerIdDeactChanged,
				sleGponProfileVoIPDetailDoNotDisturbActChanged, sleGponProfileVoIPDetailDoNotDisturbDeactChanged, sleGponProfileVoIPDetailDoNotDisturbPinChangeChanged, sleGponProfileVoIPDetailEmergServiceNumberChanged, sleGponProfileVoIPDetailIntercomServiceChanged,
				sleGponProfile2BridgeGemBridgeGemCreated, sleGponProfile2BridgeGemBridgeGemDeleted, sleGponProfile2BridgeGemVlanFilterChanged, sleGponProfile2BridgeTdmBridgeTdmCreated, sleGponProfile2BridgeTdmBridgeTdmDeleted,
				sleGponProfile2IpHostVoipVoipSvcCreated, sleGponProfile2IpHostVoipVoipSvcDeleted, sleGponProfile2IpHostTdmSvcCreated, sleGponProfile2IpHostTdmSvcDeleted, sleGponProfile2VoipSvcVoipSvcCreated,
				sleGponProfile2VoipSvcVoipSvcDeleted, sleGponProfile2VoipSvcUdpPortChanged, sleGponProfile2VoipSvcManageMethodChanged, sleGponProfile2VoipSvcProtocolChanged, sleGponProfile2VoipSvcIppathUrlChanged,
				sleGponProfile2VoipSvcIppathAuthChanged, sleGponProfile2VoipSvcUniVoipSvcUniCreated, sleGponProfile2VoipSvcUniVoipSvcUniDeleted, sleGponProfile2VoipSvcUniImpedanceChanged, sleGponProfile2VoipSvcUniTransmissionPathChanged,
				sleGponProfile2VoipSvcUniGainChanged, sleGponProfile2VoipSvcUniHoldOverTimeChanged, sleGponProfile2TdmPortCreated, sleGponProfile2TdmPortDeleted, sleGponProfile2TdmExpectedTypeChanged,
				sleGponProfile2TdmFramingChanged, sleGponProfile2TdmEncodingChanged, sleGponProfile2TdmLineLengthPowerFeedChanged, sleGponProfile2TdmDs1ModeChanged, sleGponProfile2TdmLineTypeChanged,
				sleGponProfile2BridgeUniMaxHostChanged, sleGponProfile2OnuTcontDbaProfileChanged, sleGponProfileVoIPPotsAdded, sleGponProfileVoIPPotsDeleted, sleGponProfileTdmPwRtpClockReferenceChanged,
				sleGponProfileTdmPwRtpTimeStampmodeChanged, sleGponProfileTdmPwRtpPayloadTypeChanged, sleGponProfileTdmPwRtpSyncSourceChanged, sleGponProfileTdmPwRtpExpectPayloadTypeChanged, sleGponProfileTdmPwRtpExpectSyncSourceChanged,
				sleGponProfile2OnuCircuitPackChanged, sleGponProfileTdmPwMtProfileChanged, sleGponProfile2BridgeIpHostBridgeIpHostCreated, sleGponProfile2BridgeIpHostBridgeIpHostDeleted, sleGponProfileVoIPDetailCallHoldChanged,
				sleGponProfileVoIPDetailCodec1stChanged, sleGponProfileVoIPDetailCodec2ndChanged, sleGponProfileVoIPDetailCodec3rdChanged, sleGponProfileVoIPDetailCodec4thChanged, sleGponOltAntiSpoofingFilterChanged,
				sleGponProfile2PMProfileChanged, sleGponAntiSpoofingAntiSpoofingStatusChanged, sleGponAntiSpoofingAntiSpoofingOltCleared, sleGponAntiSpoofingAntiSpoofingOnuCleared, sleGponAntiSpoofingAntiSpoofingOneCleared,
				sleGponOnuHostInfoChanged, sleGponProfileVoIPDetailDialPlanCritTimeOutChanged, sleGponProfileVoIPDetailDialPlanPartTimeOutChanged, sleGponProfileVoIPDetailDialPlanFormatChanged, sleGponProfileVoIPDetailDialPlanTableCreated,
				sleGponProfileVoIPDetailDialPlanTableDeleted, sleGponRedGroupStandbyOpticChanged, sleGponRedGroupSlaveAdminStatusChanged, sleGponRedGroupTriggerChanged, sleGponOnuUpdateOltRxPowerChanged,
				sleGponOnuPortUniDescriptionChanged, sleGponOnuPortAutoDetectionChanged, sleGponOnuPortMediumModeChanged, sleGponProfile2VoipSvcVoipProfileChanged, sleGponOltMaxOnuCountChanged,
				sleGponOnuVoipLineVoipInfoChanged, sleGponOltBwBEMethodChanged, sleGponOltDsGemMappingChanged, sleGponProfile2BridgeUniExtendedVlanChanged, sleGponProfile2IpHostSvcExtendedVlanChanged,
				sleGponVlanGemMappingChagned, sleGponVlanGemMappingCleared, sleGponProfile2ExtVlanProfileAdded, sleGponProfile2ExtVlanProfileDeleted, sleGponProfile2ExtVlanDownStreamModeChanged,
				sleGponProfile2ExtVlanDscpToCosMapTableChanged, sleGponProfile2ExtVlanTpidChanged, sleGponOnuFWAutoUpgradeBaseRetryCountChanged, sleGponOnuPortLoopbackStatusChanged, sleGponProfile2ExtVlanTagAdded,
				sleGponProfile2ExtVlanTagDeleted, sleGponProfile2ExtVlanTagFilterEtherTypeChanged, sleGponProfile2ExtVlanTagTreatmentInnerChanged, sleGponOnuVlanGemMappingCleared, sleGponOltVlanGemMappingCleared,
				sleGponBasePasswordTypeChanged, sleGponProfile2OnuSWWatchdogChanged, sleGponProfile2OnuLinkPassThroughChanged, sleGponOnuSystemInfoUpdated, sleGponOnuTxOnOptic,
				sleGponOnuPortOpticModuleInfoUpdated, sleGponProfile2OnuCpuLoadThrChanged, sleGponProfile2OnuMemoryUsageThrChanged, sleGponProfile2OnuTemperatureHighThrChanged, sleGponProfile2OnuTemperatureThrChanged,
				sleGponProfile2ExtVlanTagTreatmentOuterChanged, sleGponProfile2ExtVlanTagTreatmentTag, sleGponProfile2ExtVlanTagFilterInnerChanged, sleGponRedGroupSafeSwitchOverChanged, sleGponRedGroupDbSyncCheckChanged,
				sleGponRedGroupDbResyncChanged, sleGponOnuPortLinkStatisticsUpdated, sleGponProfileVoIPOmciMGCTerminationChanged, sleGponProfileVoIPServiceMgcMessageChanged, sleGponOnuLoopDetectUnblockChanged,
				sleGponProfile2OnuLoopDetectChanged, sleGponProfile2ExtVlanTagFilterOuterChanged, sleGponOnuPMStatsCurrentDetailChanged, sleGponIgmpGroupChanged, sleGponProfile2TcontAdded,
				sleGponProfile2TcontDeleted, sleGponProfile2TcontDbaChanged, sleGponOnuAniOpticModuleInfoUpdated, sleGponProfile2BridgeUniMcastRateLimitChanged, sleGponOltFixedTcontCountChanged,
				sleGponOltDynamicTcontCountChanged, sleGponOltPortCountChanged, sleGponOltDeactiveMonitorStatusChanged, sleGponOltDeactiveMonitorRaisePercentChanged, sleGponOltDeactiveMonitorClearPercentChanged,
				sleGponOltDeactiveMonitorPeriodChanged, sleGponOltDeactiveMonitorAlarmCleared, sleGponOnuMcastAclCreated, sleGponOnuMcastAclCleared, sleGponOnuMcastAclOnuCleared,
				sleGponOnuMcastAclOltCleared, sleGponOnuUserMacCntUpdated, sleGponOnuUserMacOltMacAllChanged, sleGponOnuUserMacOltMacUpdated, sleGponFlowMappingMethodChanged,
				sleGponFlowMappingMethodCleared, sleGponFlowMappingMethodOltCleared, sleGponProfile2OnuTr069UrlCleared, sleGponProfile2OnuTr069StatusChanged, sleGponProfile2OnuTr069AccessChanged,
				sleGponProfile2OnuTr069AccessCleared, sleGponProfile2OnuTr069TagChanged, sleGponProfile2OnuTr069TagCleared, sleGponProfile2TcontQueueWeight, sleGponBaseOnuRxPowerUpdateTimeChanged,
				sleGponOnuFWAutoUpgradeMTimeRebootTimeChanged, sleGponBaseOltMulticastGemChanged, sleGponBaseOltInterworkIgmpSnoopingChanged, sleGponStaticMacCreated, sleGponStaticMacDeleted,
				sleGponOnuVideoAniupdateVideoAniStatusUpdated, sleGponOnuVideoAniControlVideoAniArcChanged, sleGponOltRegisterd, sleGponBaseOnuRFPseudowireDstMacChanged, sleGponOnuAccountUpdated,
				sleGponOnuAccountChanged, sleGponOnuMacUpdated, sleGponOnuIgmpPmStatisticsPmDataChanged, sleGponOnuIgmpPmStatisticsPmDataCleared, sleGponOnuMacFilterChanged,
				sleGponOnuMacFilterDeleted, sleGponProfile2BridgeAniMacFilterPreassignChanged, sleGponProfile2BridgeUniMacFilterPreassignChanged, sleGponBaseOnuActiveModeChanged, sleGponOltUsFlowMappingChanged,
				sleGponProfile2OnuTr069UrlChanged, sleGponBaseOnuRFPseudowireEthTypeChanged, sleGponBaseOnuRFPseudowireVlanIdChanged, sleGponProfile2MapperActiveEthCreated, sleGponProfile2MapperActiveEthDeleted,
				sleGponProfile2GemNctpServiceAdded, sleGponProfile2GemNctpServiceDeleted, sleGponProfile2GemNctpServiceChanged, sleGponProfile2VideoReturnPathSvcAdded, sleGponProfile2VideoReturnPathSvcDeleted,
				sleGponProfile2VideoReturnPathSvcModeChanged, sleGponProfile2VideoReturnPathSvcFrequencyChanged, sleGponProfile2VideoReturnPathSvcPhysicalChanged, sleGponOnuPortMgmtChanged, sleGponProfile2PortMgmtSetted,
				sleGponProfile2PortMgmtUnsetted, sleGponProfileVoIPDetailSpecialLineServiceChanged, sleGponProfileVoIPDetailThreeWaySSWMixingChanged, sleGponProfileVoIPDetailSIPDNSCacheChanged, sleGponProfileVoIPDetailSIPTimerChanged,
				sleGponProfileVoIPDetailSIPSessionTimerChanged, sleGponProfileVoIPDetailSIPEndOfDigitChanged, sleGponProfileVoIPDetailSIPEndSharpTokenChanged, sleGponProfile2OnuSwitchControlChanged, sleGponProfile2McastAccessListAdded,
				sleGponProfile2McastAccessListDeleted, sleGponProfile2McastAccessListDynamicAdded, sleGponProfile2McastAccessListDynamicDeleted, sleGponProfile2McastAccessListStaticControlAdded, sleGponProfile2McastAccessListStaticControlDeleted,
				sleGponOnuMcastAccessListAdded, sleGponOnuMcastAccessListDeleted, sleGponOnuMcastAccessListOnuDeleted, sleGponOnuMcastAccessListOltDeleted, sleGponOltDsQosMappingChanged,
				sleGponOltDsQosMappingCleared, sleGponOltDsQosMappingModeChanged, sleGponProfile2OnuAniVoltageHighThrChanged, sleGponProfile2OnuAniVoltageLowThrChanged, sleGponProfile2OnuAniTemperatureHighThrChanged,
				sleGponProfile2OnuAniTemperatureLowThrChanged, sleGponProfile2OnuAniTxBiasHighThrChanged, sleGponProfile2OnuAniTxBiasLowThrChanged, sleGponProfile2OnuAniTxpowerHighThrChanged, sleGponProfile2OnuAniTxpowerLowThrChanged,
				sleGponProfile2OnuIgmpMaxGroupsChanged, sleGponProfile2OnuIgmpUpRateLimitChanged, sleGponProfile2OnuIgmpHostTrackingChanged, sleGponOnuPmStatsUniAvgUpdated, sleGponProfile2BridgeUniRateLimitProfileChanged,
				sleGponProfile2MapperGemRateLimitProfileChanged, sleGponProfile2RateLimitProfileCreated, sleGponProfile2RateLimitProfileDeleted, sleGponProfile2RateLimitProfileChanged, sleGponProfile2BridgePortBridgeChanged,
				sleGponProfile2OnuMacFullPolicyChanged, sleGponProfile2OnuCpuPacketLimitBroadcastChanged, sleGponProfile2OnuCpuPacketLimitMulticastChanged, sleGponProfile2OnuCpuPacketLimitDlfChanged, sleGponOltAutoOnuBlockContMoveMacChanged,
				sleGponBaseOltRxPowerUpdateTimeChanged, sleGponOltRxPowerUpdateModeChanged, sleGponOltRxPowerThresholdChanged, sleGponOnuSerialNumberRemoved, sleGponProfile2OnuRateLimitDownstreamChanged,
				sleGponProfile2OnuTrapToCpuDlfChanged, sleGponRedGroupStandbyActTriggerTimeChanged, sleGponOltStormControlChanged, sleGponOltStormControlThresholdChanged, sleGponBaseOnuAuthRadiusUserNameChanged,
				sleGponOnuAuthServerChanged, sleGponOnuAuthServerDeleted, sleGponOltControlOnuAuthControlModeChanged, sleGponOnuOmciPingTest, sleGponOltBerUsIntervalChanged,
				sleGponOltBerDsIntervalChanged, sleGponOltBerSfThresholdChanged, sleGponOltBerSdThresholdChanged, sleGponProfile2MapperGemRateLimitChanged, sleGponOnuMgmtIpPathProtocolChanged,
				sleGponOnuMgmtIpPathInfoChanged, sleGponOnuMgmtIpPathCleared, sleGponProfile2OnuIpPathStatusChanged, sleGponProfile2OnuIpPathProtocolChanged, sleGponProfile2OnuIpPathInfoChanged,
				sleGponProfile2OnuIpPathCleared, sleGponOnuExtVlanTagFrameTreatInnerAdded, sleGponOnuExtVlanTagFrameTreatInnerDeleted, sleGponCfmMdChanged, sleGponCfmMdDeleted,
				sleGponCfmMaChanged, sleGponCfmMaDeleted, sleGponCfmMepChanged, sleGponCfmMepDeleted, sleGponCfmMepCleared,
				sleGponCfmMepCcmChanged, sleGponCfmMipChanged, sleGponCfmMipDeleted, sleGponCfmTestLbChanged, sleGponCfmTestTrChanged,
				sleGponCfmRmepUpdated, sleGponBaseOnuAuthRadiusUserPasswordChanged, sleGponOnuPortPowrControlChanged, sleGponOnuPppoeStatusUpdated, sleGponOnuHostIpv6InfoChanged,
				sleGponProfile2BridgeUniInterDomainNameChanged, sleGponProfile2Ipv6HostSvcSuppressRsChanged, sleGponProfile2Ipv6HostSvcDhcpClientChanged, sleGponProfile2Ipv6HostSvcDnsChanged, sleGponOltServiceProfileModelChanged,
				sleGponProfile2McastIgmpDsTagCtrlChanged, sleGponOnuServiceModeChanged, sleGponOnuServiceModeCleared, sleGponOnuAutoUpgradeModeChanged, sleGponOnuMibUpload,
				sleGponOnuReconfig, sleGponOnuRestoreFactoryReset, sleGponOnuMoveChanged, sleGponProfile2BridgeUniPQThresholdChanged, sleGponProfile2BridgeUniPQProbabilityChanged,
				sleGponProfile2BridgeUniPQAverageCoefficientChanged, sleGponProfile2BridgeUniPQDropPrecedenceChanged, sleGponOnuHostPppoeAccountChanged, sleGponOnuPloamReset, sleGponBaseOnuVideoStatusUpdateTimeChanged,
				sleGponBaseOnuPppoeStatusUpdateTimeChanged, sleGponOltActivationStatsCleared, sleGponOltOnuStatsCleared, sleGponOltAlarmStatsCleared, sleGponProfile2OnuGspChanged,
				sleGponOnuGspInfoUpdated, sleGponOltTransceiverTypeChanged, sleGponOltOmccRecoveryChanged, sleGponProfile2OnuSnmpRoCommunityChanged, sleGponProfile2OnuSnmpRwCommunityChanged,
				sleGponProfile2OnuSnmpAgentAddressChanged, sleGponProfile2OnuSnmpTrapHostChanged, sleGponProfile2OnuSnmpSysNameChanged, sleGponOnuAniOpticModuleInfoTestActionUpdated, sleGponProfile2MapperGemRateLimitDeleted,
				sleGponOltControlOnuAuthReauthenChanged, sleGponOnuAuthReauthSpecificChanged, sleGponOnuRadiusAttributeChanged, sleGponProfile2TcontPQThresholdChanged, sleGponProfile2TcontPQProbabilityChanged,
				sleGponProfile2TcontPQAverageCoefficientChanged, sleGponProfile2TcontPQDropPrecedenceChanged, sleGponProfile2OnuSnmpSecurityNameChanged }
			STATUS current
			DESCRIPTION
				"Description."
			::= { sleGpon 54 }



	END

--
-- SLE-GPON-MIB.my
--
