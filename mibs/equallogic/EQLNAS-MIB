-- Mib files packaged on  Wed Mar 12 10:59:55 EDT 2014 for Storage Array Firmware V7.0.3 (R387053)

--  These are from draft-ietf-ops-rfc2851-update-00.txt
--  You will have to work out the details with your own
EQLNAS-MIB DEFINITIONS  ::= BEGIN
IMPORTS
    MODULE-IDENTITY, OBJECT-TYPE, Unsigned32, Counter64, Integer32,TimeTicks,  enterprises, IpAddress, Counter32, Counter64, Gauge32
            FROM SNMPv2-SMI
	 DateAndTime, RowPointer
				FROM SNMPv2-TC
    TruthValue, RowStatus, DisplayString
            FROM SNMPv2-TC
    InetAddressType, InetAddress
            FROM INET-ADDRESS-MIB       -- RFC2851
    equalLogic
            FROM EQUALLOGIC-SMI
--     UTFString
--            FROM EQLGROUP-MIB
    eqlApplianceIndex, eqlApplianceNetworkType, eqlApplianceNetworkID
	    FROM EQLAPPLIANCE-MIB
    StatusDisabledDefault, SiteIndex, SiteIndexOrZero, eqliscsiVolumeReplSiteIndex
       FROM EQLVOLUME-MIB;

eqlNASModule MODULE-IDENTITY
	LAST-UPDATED "201403121459Z"
    ORGANIZATION  "EqualLogic Inc."
    CONTACT-INFO
        "Contact: Customer Support
         Postal:  Dell Inc
                  300 Innovative Way, Suite 301, Nashua, NH 03062
         Tel:     +1 603-579-9762
         E-mail:  US-NH-CS-TechnicalSupport@dell.com
         WEB:     www.equallogic.com"

    DESCRIPTION
        "Appliances information.

        Copyright (c) 2004-2011 by Dell, Inc.

        All rights reserved.  This software may not be copied, disclosed,
        transferred, or used except in accordance with a license granted
        by Dell, Inc.  This software embodies proprietary information
        and trade secrets of Dell, Inc.
        "

    -- Revision history, in reverse chronological order
    REVISION    "200907130000Z"         -- 02-Sep-06
    DESCRIPTION "Initial revision"
    ::= { enterprises equalLogic(12740) 18 }

eqlNASObjects OBJECT IDENTIFIER ::= { eqlNASModule 1 }

--***********************************************************************************
-- Textual conventions

UNIXPermissions ::= TEXTUAL-CONVENTION
    DISPLAY-HINT "o"
    STATUS       current
    DESCRIPTION
            "This textual convention defines a format to display file and directory permissions in UNIX"
    SYNTAX       Unsigned32

ClusterNameType ::= TEXTUAL-CONVENTION
    DISPLAY-HINT "t"
    STATUS          current
    DESCRIPTION     "Name of the Spartan cluster"
    SYNTAX          OCTET STRING (SIZE (1..64))

ClusterIdType ::= TEXTUAL-CONVENTION
    DISPLAY-HINT "t"
    STATUS       current
    DESCRIPTION
            "This textual convention defines string for a cluster-id.
            Get this string from node. Size defined in ClusterIdType in xmlApiObjects.xml"
    SYNTAX        OCTET STRING (SIZE(0..50))

CertificateType ::= TEXTUAL-CONVENTION
    DISPLAY-HINT "t"
    STATUS        current
    DESCRIPTION "RSA Certifcate. Max possible size for the whole certificate is 4096 bytes.
                This type represents a segment of the certificate."
    SYNTAX        OCTET STRING (SIZE (0..1750))

NASContainerNameType ::= TEXTUAL-CONVENTION
    DISPLAY-HINT "t"
    STATUS          current
    DESCRIPTION     "Name used to identify NAS Container. Contains only letters, digits and underscores. Must begin with either letter or an underscore."
    SYNTAX          OCTET STRING (SIZE (1..230))

--***********************************************************************************


eqlNASApplianceTable OBJECT-TYPE
    SYNTAX          SEQUENCE OF EqlNASApplianceEntry
    MAX-ACCESS      not-accessible
    STATUS          current
    DESCRIPTION     "EqualLogic-Persistent Appliance Table.
                     This table contains a list of NAS pools that this group is managing.
                     TimeoutAll:60"
    ::=    { eqlNASObjects 1 }

eqlNASApplianceEntry OBJECT-TYPE
    SYNTAX          EqlNASApplianceEntry
    MAX-ACCESS      not-accessible
    STATUS          current
    DESCRIPTION     "An entry (row) containing NAS Container info."
    INDEX           { eqlApplianceIndex }

    ::=   { eqlNASApplianceTable 1}

EqlNASApplianceEntry ::=
    SEQUENCE {
        eqlNASApplianceRowStatus        RowStatus,
        eqlNASAppliancePoolSize         Unsigned32,
        eqlNASApplianceEQLPoolIndex     Unsigned32,
        eqlNASApplianceReplRemoteUserName     OCTET STRING,
        eqlNASApplianceNFSv4Mode        INTEGER
    }

eqlNASApplianceRowStatus OBJECT-TYPE
    SYNTAX          RowStatus
    MAX-ACCESS      read-create
    STATUS          current
    DESCRIPTION     "This field is used indicate the status of this entry."
    ::= { eqlNASApplianceEntry 1 }

eqlNASAppliancePoolSize OBJECT-TYPE
    SYNTAX          Unsigned32
    MAX-ACCESS      read-create
    STATUS          current
    DESCRIPTION     "This field is used indicate the size of the NAS Container in MB."
    ::= { eqlNASApplianceEntry 2 }

eqlNASApplianceEQLPoolIndex OBJECT-TYPE
    SYNTAX          Unsigned32
    MAX-ACCESS      read-create
    STATUS          current
    DESCRIPTION     "This field is used to indicate the EQL pool used by the NAS appliance."
    ::= { eqlNASApplianceEntry 3 }

eqlNASApplianceReplRemoteUserName OBJECT-TYPE
    SYNTAX        OCTET STRING  (SIZE (0..32))
    MAX-ACCESS    read-write
    STATUS        current
    DESCRIPTION
        "This field is used to indicate the Username EQL will use for NAS replication for all partners."
    ::= { eqlNASApplianceEntry 4 }

eqlNASApplianceNFSv4Mode OBJECT-TYPE
    SYNTAX          INTEGER {
                        disabled (0),
                        enabled  (1)
                    }
    MAX-ACCESS      read-write
    STATUS          current
    DESCRIPTION     "This field enables or disables NFSv4 Access NAS appliance."
    DEFVAL          { disabled }
    ::= { eqlNASApplianceEntry 5 }


-----------------------------------------------------------------------------------------------
eqlNASContainerTable OBJECT-TYPE
    SYNTAX          SEQUENCE OF EqlNASContainerEntry
    MAX-ACCESS      not-accessible
    STATUS          current
    DESCRIPTION     "EqualLogic-Dynamic Appliance Table.
                     This table contains a list of NAS Appliance configurations for containers the group is managing.
                     TimeoutAll:60"
    ::=    { eqlNASObjects 3 }

eqlNASContainerEntry OBJECT-TYPE
    SYNTAX          EqlNASContainerEntry
    MAX-ACCESS      not-accessible
    STATUS          current
    DESCRIPTION     "An entry (row) containing NAS Container info."
    INDEX           { eqlApplianceIndex, eqlNASContainerIndex }

    ::=   { eqlNASContainerTable 1}

EqlNASContainerEntry ::=
    SEQUENCE {
        eqlNASContainerIndex                     Unsigned32,
	eqlNASContainerRowStatus                 RowStatus,
	eqlNASContainerName                      OCTET STRING,
	eqlNASContainerCapacity                  Unsigned32,
	eqlNASContainerUsedSpaceAlert            Unsigned32,
	eqlNASContainerSnapshotHardQuota         Unsigned32,
	eqlNASContainerSnapshotUsedSpaceAlert    Unsigned32,
	eqlNASContainerUnixFilePermissions       UNIXPermissions,
	eqlNASContainerUnixDirPermissions        UNIXPermissions,
	eqlNASContainerQuotaEnabled              TruthValue,
	eqlNASContainerFileAccessSecurity        INTEGER,
        eqlNASContainerAccessTimeManagementGranularity       INTEGER,
        eqlNASContainerOptimizationEnabled       TruthValue,
        eqlNASContainerDedupMethodType           INTEGER,
        eqlNASContainerCompressionEnabled        TruthValue,
        eqlNASContainerModificationTimeFilter    INTEGER,
        eqlNASContainerAccessTimeFilter          INTEGER,
        eqlNASContainerExcludeFilesByNamePattern OCTET STRING,
        eqlNASContainerAction                    INTEGER,
    	eqlNASContainerDefaultUserQuota         Unsigned32,
    	eqlNASContainerDefaultUserQuotaAlert    Unsigned32,
    	eqlNASContainerDefaultGroupQuota        Unsigned32,
    	eqlNASContainerDefaultGroupQuotaAlert   Unsigned32,
        eqlNASContainerOptimizationFilterMode   INTEGER,
        eqlNASContainerRehydrateOnReadEnabled   TruthValue
    }

eqlNASContainerIndex OBJECT-TYPE
    SYNTAX          Unsigned32
    MAX-ACCESS      not-accessible
    STATUS          current
    DESCRIPTION     "Unique Identifier used to create and manage NAS Containers. When creating NAS Containers, value must be retrieved using eqlApplianceUniqueIDValue with eqlApplianceUniqueIDType set to fsid."
    ::= { eqlNASContainerEntry 1 }

eqlNASContainerRowStatus OBJECT-TYPE
    SYNTAX          RowStatus
    MAX-ACCESS      read-create
    STATUS          current
    DESCRIPTION     "Row status variable used to manage this row."
    ::= { eqlNASContainerEntry 2 }

eqlNASContainerName OBJECT-TYPE
    SYNTAX          OCTET STRING (SIZE (1..230))
    MAX-ACCESS      read-create
    STATUS          current
    DESCRIPTION     "Name used to identify NAS Container. Contains only letters, digits and underscores. Must begin with either letter or an underscore. "
    ::=  {  eqlNASContainerEntry 3 }

eqlNASContainerCapacity OBJECT-TYPE
    SYNTAX          Unsigned32
    UNITS           "MB"
    MAX-ACCESS      read-create
    STATUS          current
    DESCRIPTION     "Size of NAS Container in MB."
    ::= { eqlNASContainerEntry 4 }

eqlNASContainerUsedSpaceAlert OBJECT-TYPE
    SYNTAX          Unsigned32
    UNITS           "%"
    MAX-ACCESS      read-create
    STATUS          current
    DESCRIPTION     "Alert user when NAS container used space reaches certain % value of NAS container size.Default value is choosen from eqlNASApplianceConfigUsedSpaceAlert"
    ::= { eqlNASContainerEntry 5 }

eqlNASContainerSnapshotHardQuota OBJECT-TYPE
    SYNTAX          Unsigned32
    UNITS           "%"
    MAX-ACCESS      read-create
    STATUS          current
    DESCRIPTION     "This threshold, represented as a % of NAS container size, triggers auto-deletion of snapshots. The oldest snapshots are deleted first. Default value is choosen from eqlNASApplianceConfigSnapHardQuota"
    ::= { eqlNASContainerEntry 6 }

eqlNASContainerSnapshotUsedSpaceAlert OBJECT-TYPE
    SYNTAX          Unsigned32
    MAX-ACCESS      read-create
    STATUS          current
    DESCRIPTION     "Alert user when NAS container snapshot used space reaches certain % value of NAS container snapshot size.Default value is choosen from eqlNASApplianceConfigSnapSpaceAlert "
    ::= { eqlNASContainerEntry 7 }

eqlNASContainerUnixFilePermissions OBJECT-TYPE
    SYNTAX          UNIXPermissions
    MAX-ACCESS      read-create
    STATUS          current
    DESCRIPTION     " This field is applicable only when Security style is set to NFS"
    ::= { eqlNASContainerEntry 8 }

eqlNASContainerUnixDirPermissions OBJECT-TYPE
    SYNTAX          UNIXPermissions
    MAX-ACCESS      read-create
    STATUS          current
    DESCRIPTION     " This field is applicable only when Security style is set to NFS"
    ::= { eqlNASContainerEntry 9 }

eqlNASContainerQuotaEnabled OBJECT-TYPE
    SYNTAX          TruthValue
    MAX-ACCESS      read-create
    STATUS          current
    DESCRIPTION     ""
    ::= { eqlNASContainerEntry 10 }

eqlNASContainerFileAccessSecurity OBJECT-TYPE
    SYNTAX          INTEGER     {
                    mixed(1),
                    ntfs(2),
                    unix(3)
    }
    MAX-ACCESS      read-create
    STATUS          current
    DESCRIPTION     ""
    DEFVAL          {ntfs}
    ::= { eqlNASContainerEntry 11 }

eqlNASContainerAccessTimeManagementGranularity OBJECT-TYPE
    SYNTAX          INTEGER    {
                    disabled(0),
                    always(1),
                    everyFiveMinutes(2),
                    hourly(3),
                    daily(4),
                    weekly(5)
                    }
    MAX-ACCESS      read-create
    STATUS          current
    DESCRIPTION     "Access time management granularity."
    DEFVAL          {daily}
    ::= { eqlNASContainerEntry 12 }

eqlNASContainerOptimizationEnabled OBJECT-TYPE
    SYNTAX          TruthValue
    MAX-ACCESS      read-create
    STATUS          current
    DESCRIPTION     "Enable or disable optimization"
    DEFVAL          {false}
    ::= { eqlNASContainerEntry 13 }

eqlNASContainerDedupMethodType OBJECT-TYPE
    SYNTAX          INTEGER     {
                    variable-chunk(1),
                    object(2)
    }
    MAX-ACCESS      read-create
    STATUS          current
    DESCRIPTION     "Dedup method to use on this file system when optimization is enabled. Reserved for future use. Currently not supported."
    DEFVAL          {variable-chunk}
    ::= { eqlNASContainerEntry 14 }

eqlNASContainerCompressionEnabled OBJECT-TYPE
    SYNTAX          TruthValue
    MAX-ACCESS      read-create
    STATUS          current
    DESCRIPTION     "enable or disable compression. Restricted by the type of license"
    DEFVAL          {false}
    ::= { eqlNASContainerEntry 15 }

eqlNASContainerModificationTimeFilter OBJECT-TYPE
    SYNTAX          INTEGER (30..365)
    MAX-ACCESS      read-create
    STATUS          current
    DESCRIPTION     "Exclude files modified less than the specified number of days before. 30 to 365 days"
    DEFVAL          {30}
    ::= { eqlNASContainerEntry 16 }

eqlNASContainerAccessTimeFilter OBJECT-TYPE
    SYNTAX          INTEGER (30..365)
    MAX-ACCESS      read-create
    STATUS          current
    DESCRIPTION     "Exclude files accessed less than the specified number of days before. 30 to 365 days"
    DEFVAL          {30}
    ::= { eqlNASContainerEntry 17 }

eqlNASContainerExcludeFilesByNamePattern OBJECT-TYPE
    SYNTAX          OCTET STRING (SIZE (1..256))
    MAX-ACCESS      read-create
    STATUS          deprecated
    DESCRIPTION     "Regular expression identifying the file name pattern to exclude from optimization. Empty string means no exclusion."
    DEFVAL          {""}
    ::=  {  eqlNASContainerEntry 18 }

eqlNASContainerAction OBJECT-TYPE
    SYNTAX          INTEGER     {
                    none(0),
                    delete-host-access-cfg(1)
    }
    MAX-ACCESS      read-create
    STATUS          current
    DESCRIPTION     "Use this column to perform actions on this container."
    DEFVAL          {none}
::= { eqlNASContainerEntry 19 }

eqlNASContainerDefaultUserQuota OBJECT-TYPE
	SYNTAX          Unsigned32
	MAX-ACCESS      read-create
	STATUS          current
	DESCRIPTION     "Default quota per user when quotas are enabled on NAS Containers."
	DEFVAL { 0 } --- 0 for user quota hard limit disabled
::= { eqlNASContainerEntry 20 }

eqlNASContainerDefaultUserQuotaAlert OBJECT-TYPE
	SYNTAX          Unsigned32
	UNITS            "%"
	MAX-ACCESS      read-create
	STATUS          current
	DESCRIPTION     "Specified as a percentage of default group quota as a default for containers in this nas-group.
	This is the amount of used space that triggers user alerts"
	DEFVAL { 0 } --- 0 for user quota warn limit disabled
::= { eqlNASContainerEntry 21 }


eqlNASContainerDefaultGroupQuota OBJECT-TYPE
	SYNTAX          Unsigned32
	MAX-ACCESS      read-create
	STATUS          current
	DESCRIPTION     "Default quota per group when quotas are enabled on NAS Containers."
	DEFVAL { 0 } --- 0 for group quota hard limit disabled
::= { eqlNASContainerEntry 22 }


eqlNASContainerDefaultGroupQuotaAlert OBJECT-TYPE
	SYNTAX          Unsigned32
	UNITS            "%"
	MAX-ACCESS      read-create
	STATUS          current
	DESCRIPTION     "Specified as a percentage of default group quota as a default for containers in this nas-group.
	This is the amount of used space that triggers user alerts"
DEFVAL { 0 } --- 0 for group quota warn limit disabled
::= { eqlNASContainerEntry 23 }

eqlNASContainerOptimizationFilterMode OBJECT-TYPE
    SYNTAX          INTEGER     {
                    use-filters(0),
                    ignore-filters(1)
    }
	MAX-ACCESS      read-create
	STATUS          current
	DESCRIPTION     "Specifies the filter mode to be applied to qualify files for data reduction.
                    user-filters implies files need to meet the access time and modify time filter
                    criteria before they can be considered for data reduction.
                    ignore-filters implies files are considered for data reduction irrespective of
                    the access time and modify time filter criteria, using an access time and modification
					time value of 1 day. This mode is recommended for containers with archive data only."
    DEFVAL { use-filters }
::= { eqlNASContainerEntry 24 }

eqlNASContainerRehydrateOnReadEnabled OBJECT-TYPE
    SYNTAX          TruthValue
    MAX-ACCESS      read-create
    STATUS          current
    DESCRIPTION     "Enable or disable rehydrate on read in a data reduction disabled nas container"
    DEFVAL          {false}
    ::= { eqlNASContainerEntry 25 }


----------------------------------------
eqlNASContainerUniqueIDTable OBJECT-TYPE
    SYNTAX          SEQUENCE OF EqlNASContainerUniqueIDEntry
    MAX-ACCESS      not-accessible
    STATUS          current
    DESCRIPTION     "EqualLogic-Dynamic Unique ID table.
                     This table is used to retrieve Unique ID values when creating new objects.
                     TimeoutAll:60"
    ::=    {  eqlNASContainerTable  2 }

eqlNASContainerUniqueIDEntry OBJECT-TYPE
    SYNTAX          EqlNASContainerUniqueIDEntry
    MAX-ACCESS      not-accessible
    STATUS          current
    DESCRIPTION     "An entry (row) containing unique ID information."
    INDEX           { eqlApplianceIndex, eqlNASContainerIndex, eqlNASContainerUniqueIDType }

    ::=   { eqlNASContainerUniqueIDTable 1}

EqlNASContainerUniqueIDEntry ::=
    SEQUENCE {
	eqlNASContainerUniqueIDType         INTEGER,
	eqlNASContainerUniqueIDValueLen     Unsigned32,
	eqlNASContainerUniqueIDValue        OCTET STRING
    }

eqlNASContainerUniqueIDType OBJECT-TYPE
    SYNTAX          INTEGER {
                    snapshot(1),
                    quota(2)
    }
    MAX-ACCESS      not-accessible
    STATUS          current
    DESCRIPTION     "Indicates the type of the id. For now only Snapshot and quota Ids are needed for at the container scope"
    ::= {eqlNASContainerUniqueIDEntry  1 }

eqlNASContainerUniqueIDValueLen OBJECT-TYPE
    SYNTAX          Unsigned32
    MAX-ACCESS      read-only
    STATUS          current
    DESCRIPTION     "Length of the value represented by column eqlNASContainerUniqueIDValue"
    ::= {eqlNASContainerUniqueIDEntry  2 }

eqlNASContainerUniqueIDValue OBJECT-TYPE
    SYNTAX          OCTET STRING(SIZE(255))
    MAX-ACCESS      read-only
    STATUS          current
    DESCRIPTION     "Value of eqlNASContainerUniqueIDType represented in network byte order."
    ::= {eqlNASContainerUniqueIDEntry  3 }


---***************************************************************

eqlNASApplianceDefaultCfgTable OBJECT-TYPE
    SYNTAX          SEQUENCE OF EqlNASApplianceDefaultCfgEntry
    MAX-ACCESS      not-accessible
    STATUS          current
    DESCRIPTION     "EqualLogic-Dynamic (semi) Appliance Table.
                     This table contains a list of NAS Appliance default configurations for containers the group is managing.
                     TimeoutAll:60"
    ::=    { eqlNASObjects 4 }

eqlNASApplianceDefaultCfgEntry OBJECT-TYPE
    SYNTAX          EqlNASApplianceDefaultCfgEntry
    MAX-ACCESS      not-accessible
    STATUS          current
    DESCRIPTION     "An entry (row) containing NAS Container Status info."
    INDEX           { eqlApplianceIndex }

    ::=   { eqlNASApplianceDefaultCfgTable 1}

EqlNASApplianceDefaultCfgEntry ::=
    SEQUENCE {
        eqlNASApplianceConfigUsedSpaceAlert     Unsigned32,
        eqlNASApplianceConfigSnapSpaceAlert     Unsigned32,
    	eqlNASApplianceConfigSnapHardQuota      Unsigned32,
    	eqlNASApplianceContainerUnixFilePerms   UNIXPermissions,
    	eqlNASApplianceContainerUnixDirPerms    UNIXPermissions,
    	eqlNASApplianceContainerFileSecurity    INTEGER,
    	eqlNASApplianceDefaultUserQuota         Unsigned32,
    	eqlNASApplianceDefaultUserQuotaAlert    Unsigned32,
    	eqlNASApplianceDefaultGroupQuota        Unsigned32,
    	eqlNASApplianceDefaultGroupQuotaAlert   Unsigned32,
    	eqlNASApplianceDefaultCIFSAllowGuestAccess     TruthValue,
    	eqlNASApplianceCIFSAuthenticationMode   INTEGER,
    	eqlNASApplianceDefaultCIFSLockEnforcement      INTEGER,
    	eqlNASApplianceNFSExportReadWrite       INTEGER,
    	eqlNASApplianceNFSExportTrustedUsers    INTEGER,
        eqlNASApplianceAccessTimeManagementGranularity       INTEGER,
        eqlNASApplianceOptimizationEnabled       TruthValue,
        eqlNASApplianceDedupMethodType           INTEGER,
        eqlNASApplianceCompressionEnabled        TruthValue,
        eqlNASApplianceModificationTimeFilter    INTEGER,
        eqlNASApplianceAccessTimeFilter          INTEGER,
        eqlNASApplianceExcludeFilesByNamePattern            OCTET STRING,
        eqlNASApplianceDefaultCIFSAntivirusEnabled          StatusDisabledDefault,
        eqlNASApplianceDefaultCIFSAntivirusPolicy           INTEGER,
        eqlNASApplianceDefaultCIFSAntivirusExtensions       OCTET STRING,
        eqlNASApplianceDefaultCIFSAntivirusExtensionsPolicy INTEGER,
        eqlNASApplianceDefaultCIFSAntivirusExcludeDirPaths  OCTET STRING,
        eqlNASApplianceDefaultCIFSAntivirusLargeFileSize    Unsigned32,
        eqlNASApplianceDefaultCIFSAntivirusLargeFileOpen    INTEGER,
        eqlNASApplianceDefaultNFSExportsFileId32bit         INTEGER
    }

eqlNASApplianceConfigUsedSpaceAlert OBJECT-TYPE
    SYNTAX          Unsigned32
    UNITS            "%"
    MAX-ACCESS      read-create
    STATUS          current
    DESCRIPTION     "Specified as a percentage of NAS container size as a default for containers in this nas-group.
                     This is the amount of used space that triggers user alerts"
    DEFVAL { 80 } --- EXANET has this at 100% aka no alert
    ::= { eqlNASApplianceDefaultCfgEntry 1 }

eqlNASApplianceConfigSnapSpaceAlert OBJECT-TYPE
    SYNTAX          Unsigned32
    UNITS            "%"
    MAX-ACCESS      read-create
    STATUS          current
    DESCRIPTION     "Specified as a percentage of NAS container size as a default for containers in this nas-group.
                     The is the amount of space consumed by snapshots at which user alerts are triggered"
    DEFVAL { 80} ---EXANET has this at 100%
    ::= { eqlNASApplianceDefaultCfgEntry 2 }

eqlNASApplianceConfigSnapHardQuota OBJECT-TYPE
    SYNTAX          Unsigned32
    UNITS           "%"
    MAX-ACCESS      read-create
    STATUS          current
    DESCRIPTION     "Specified as a percentage of NAS container size as a default for containers in this nas-group.
                     This is the threshold that triggers auto-deletion of snapshots. Oldest first."
    DEFVAL { 50}
    ::= { eqlNASApplianceDefaultCfgEntry 3 }

eqlNASApplianceContainerUnixFilePerms OBJECT-TYPE
    SYNTAX          UNIXPermissions
    MAX-ACCESS      read-create
    STATUS          current
    DESCRIPTION     "Define the default UNIX permissions of new files created from Windows clients. Default value is 0744"
    DEFVAL { 484}
    ::= { eqlNASApplianceDefaultCfgEntry 4 }

eqlNASApplianceContainerUnixDirPerms OBJECT-TYPE
    SYNTAX          UNIXPermissions
    MAX-ACCESS      read-create
    STATUS          current
    DESCRIPTION     " Define the default UNIX permissions of new directories created from Windows clients. Default value is 0755"
    DEFVAL { 493}
    ::= { eqlNASApplianceDefaultCfgEntry 5 }

eqlNASApplianceContainerFileSecurity OBJECT-TYPE
    SYNTAX          INTEGER     {
                    mixed(1),
                    ntfs(2),
                    unix(3)
    }
    MAX-ACCESS      read-create
    STATUS          current
    DESCRIPTION     "Used to define how the system will maintain and verify file access security."
    DEFVAL          {ntfs}
    ::= { eqlNASApplianceDefaultCfgEntry 6 }

eqlNASApplianceDefaultUserQuota OBJECT-TYPE
    SYNTAX          Unsigned32
    MAX-ACCESS      read-create
    STATUS          current
    DESCRIPTION     "Default quota per user when quotas are enabled on NAS Containers."
    DEFVAL { 0 } --- EXANET Says Unlimited
    ::= { eqlNASApplianceDefaultCfgEntry 7 }

eqlNASApplianceDefaultUserQuotaAlert OBJECT-TYPE
    SYNTAX          Unsigned32
    UNITS            "%"
    MAX-ACCESS      read-create
    STATUS          current
    DESCRIPTION     "Specified as a percentage of default group quota as a default for containers in this nas-group.
                     This is the amount of used space that triggers user alerts"
    DEFVAL { 0 } --- 0 aka no alert
    ::= { eqlNASApplianceDefaultCfgEntry 8 }


eqlNASApplianceDefaultGroupQuota OBJECT-TYPE
    SYNTAX          Unsigned32
    MAX-ACCESS      read-create
    STATUS          current
    DESCRIPTION     "Default quota per group when quotas are enabled on NAS Containers."
    DEFVAL { 0 } --- EXANET Says Unlimited
    ::= { eqlNASApplianceDefaultCfgEntry 9 }


eqlNASApplianceDefaultGroupQuotaAlert OBJECT-TYPE
    SYNTAX          Unsigned32
    UNITS            "%"
    MAX-ACCESS      read-create
    STATUS          current
    DESCRIPTION     "Specified as a percentage of default group quota as a default for containers in this nas-group.
                     This is the amount of used space that triggers user alerts"
    DEFVAL { 0 } --- 0 aka no alert
    ::= { eqlNASApplianceDefaultCfgEntry 10 }

eqlNASApplianceDefaultCIFSAllowGuestAccess OBJECT-TYPE
    SYNTAX          TruthValue
    MAX-ACCESS      read-create
    STATUS          current
    DESCRIPTION     "Choose whether to allow unknown users to access the share as guests. "
    DEFVAL { false}
    ::= { eqlNASApplianceDefaultCfgEntry 11 }

eqlNASApplianceCIFSAuthenticationMode OBJECT-TYPE
    SYNTAX          INTEGER{
                    allow-everyone(1),
                    active-directory(2),
                    local-users(3)
    }
    MAX-ACCESS      read-create
    STATUS          current
    DESCRIPTION     ""
    DEFVAL          {allow-everyone}
    ::= { eqlNASApplianceDefaultCfgEntry 12 }

eqlNASApplianceDefaultCIFSLockEnforcement OBJECT-TYPE
    SYNTAX          INTEGER{
		all-locks(0),
		share-locks-op-locks(1),
		only-share-locks(2)
}
    MAX-ACCESS      read-create
    STATUS          current
    DESCRIPTION     " Define the types of locks that the system will enforce, in addition to share locks which are always enforced.  Byte range locks allow applications to ensure data integrity.  Opportunistic locks (oplocks) increase the efficiency of client machine caching and improve performance. NOTE: This software release does not support changing the locking enforcement policy. Only the default option (all-locks) is supported."
    DEFVAL{all-locks}
    ::= { eqlNASApplianceDefaultCfgEntry 13 }

eqlNASApplianceNFSExportReadWrite OBJECT-TYPE
    SYNTAX          INTEGER {
		read-write(1),
		read-only(2)
}
    MAX-ACCESS      read-create
    STATUS          current
    DESCRIPTION     "Define the access rights for the NFS export. If the access rights for the NFS export are stricter than those defined for a specific file, the file's access rights will be overridden by those of the NFS export. "
    DEFVAL { read-write}
    ::= { eqlNASApplianceDefaultCfgEntry 14 }

eqlNASApplianceNFSExportTrustedUsers OBJECT-TYPE
    SYNTAX          INTEGER{
		all-except-root(1),
                none(2),
		all(3)
}
    MAX-ACCESS      read-create
    STATUS          current
    DESCRIPTION     " Define which users are trusted. Other users will be identified as guests. "
    DEFVAL {all-except-root}
    ::= { eqlNASApplianceDefaultCfgEntry 15 }

eqlNASApplianceAccessTimeManagementGranularity OBJECT-TYPE
    SYNTAX          INTEGER    {
                    disabled(0),
                    always(1),
                    everyFiveMinutes(2),
                    hourly(3),
                    daily(4),
                    weekly(5)
                    }
    MAX-ACCESS      read-create
    STATUS          current
    DESCRIPTION     "Access time management granularity."
    DEFVAL          {daily}
    ::= { eqlNASApplianceDefaultCfgEntry 16 }

eqlNASApplianceOptimizationEnabled OBJECT-TYPE
    SYNTAX          TruthValue
    MAX-ACCESS      read-create
    STATUS          current
    DESCRIPTION     "Enable or disable optimization. Reserved for future use. Not supported currently."
    DEFVAL          {false}
    ::= { eqlNASApplianceDefaultCfgEntry 17 }

eqlNASApplianceDedupMethodType OBJECT-TYPE
    SYNTAX          INTEGER     {
                    variable-chunk(1),
                    object(2)
    }
    MAX-ACCESS      read-create
    STATUS          current
    DESCRIPTION     "Dedup method to use on this file system when optimization is enabled. Reserved for future use. Currently not supported."
    DEFVAL          {variable-chunk}
    ::= { eqlNASApplianceDefaultCfgEntry 18 }

eqlNASApplianceCompressionEnabled OBJECT-TYPE
    SYNTAX          TruthValue
    MAX-ACCESS      read-create
    STATUS          current
    DESCRIPTION     "enable or disable compression. Restricted by the type of license. Reserved for future use. Not supported currently."
    DEFVAL          {false}
    ::= { eqlNASApplianceDefaultCfgEntry 19 }

eqlNASApplianceModificationTimeFilter OBJECT-TYPE
    SYNTAX          INTEGER (30..365)
    MAX-ACCESS      read-create
    STATUS          current
    DESCRIPTION     "Exclude files modified less than the specified number of days before. 30 to 365 days."
    DEFVAL          {30}
    ::= { eqlNASApplianceDefaultCfgEntry 20 }

eqlNASApplianceAccessTimeFilter OBJECT-TYPE
    SYNTAX          INTEGER (30..365)
    MAX-ACCESS      read-create
    STATUS          current
    DESCRIPTION     "Exclude files accessed less than the specified number of days before. 30 to 365 days."
    DEFVAL          {30}
    ::= { eqlNASApplianceDefaultCfgEntry 21 }

eqlNASApplianceExcludeFilesByNamePattern OBJECT-TYPE
    SYNTAX          OCTET STRING (SIZE (1..256))
    MAX-ACCESS      read-create
    STATUS          deprecated
    DESCRIPTION     "Regular expression identifying the file name pattern to exclude from optimization. Empty string means no exclusion."
    DEFVAL          {""}
    ::=  {  eqlNASApplianceDefaultCfgEntry 22 }

eqlNASApplianceDefaultCIFSAntivirusEnabled OBJECT-TYPE
    SYNTAX          StatusDisabledDefault
    MAX-ACCESS      read-create
    STATUS          current
    DESCRIPTION     "Default which determines whether the antivirus service is disabled or enabled for a CIFS share at the time of creation."
    DEFVAL      { disabled }
    ::= { eqlNASApplianceDefaultCfgEntry 23 }

--------------------------------------------------------------------------------------------
-- eqlNASApplianceDefaultCIFSAntivirusPolicy is deprecated.
-- It will now always be set to quarantine(0).
--------------------------------------------------------------------------------------------
eqlNASApplianceDefaultCIFSAntivirusPolicy OBJECT-TYPE
    SYNTAX          INTEGER {
                            quarantine(0),
                            do-nothing(1),
                            remove(2)
                            }
    MAX-ACCESS      read-create
    STATUS          current
    DESCRIPTION     "Default which determines the action to be taken on a virus-infected file.  This field is deprecated and unsupported.  The value now always will be quarantine(0)."
    DEFVAL      { quarantine }
    ::= { eqlNASApplianceDefaultCfgEntry 24 }

eqlNASApplianceDefaultCIFSAntivirusExtensions OBJECT-TYPE
    SYNTAX          OCTET STRING (SIZE (0..255))
    MAX-ACCESS      read-create
    STATUS          current
    DESCRIPTION     "Default which determines which files should be / should not be scanned for viruses. This is a comma-separated list. The value of the next field determines if the files with the corresponding extensions will be scanned or not for viruses. Cannot contain wild characters * and ?. Extensions are case-insensitive."
    DEFVAL          {""}
    ::= { eqlNASApplianceDefaultCfgEntry 25 }

--------------------------------------------------------------------------------------------
-- eqlNASApplianceDefaultCIFSAntivirusExtensionsPolicy is deprecated.
-- It will now always be set to exclude(0).
--------------------------------------------------------------------------------------------
eqlNASApplianceDefaultCIFSAntivirusExtensionsPolicy OBJECT-TYPE
    SYNTAX          INTEGER {
                            exclude(0),
                            include(1)
                            }
    MAX-ACCESS      read-create
    STATUS          current
    DESCRIPTION     "Default which determines whether the files whose extensions match with those specified in the field above should be scanned OR should not be scanned for viruses.  This field is deprecated and unsupported.  The value now always will be exclude(0)."
    DEFVAL      { exclude }
    ::= { eqlNASApplianceDefaultCfgEntry 26 }

eqlNASApplianceDefaultCIFSAntivirusExcludeDirPaths OBJECT-TYPE
    SYNTAX          OCTET STRING (SIZE (0..512))
    MAX-ACCESS      read-create
    STATUS          current
    DESCRIPTION     "Default which determines the list of the directory paths which should not be scanned for viruses. It is a comma-separated list. Paths can contain wildcards * and ?. NOTE: * will not match several path components. "
    DEFVAL          {""}
    ::= { eqlNASApplianceDefaultCfgEntry 27 }

eqlNASApplianceDefaultCIFSAntivirusLargeFileSize OBJECT-TYPE
    SYNTAX          Unsigned32
    MAX-ACCESS      read-create
    STATUS          current
    DESCRIPTION     "Default which determines the largest file size in MB which is sent to Antivirus server for scanning on the fly. The files larger than the specified size are not scanned. Access to these large files will be allowed or denied based on the CIFS Antivirus Large File Open option."
    DEFVAL          {3072}
    ::= { eqlNASApplianceDefaultCfgEntry 28 }

eqlNASApplianceDefaultCIFSAntivirusLargeFileOpen OBJECT-TYPE
    SYNTAX          INTEGER {
                        deny  (0),
                        allow (1)
                    }
    MAX-ACCESS      read-create
    STATUS          current
    DESCRIPTION     "Default which determines if CIFS clients are allowed to open files larger than the value defined by AntivirusLargeFileSize."
    DEFVAL          { deny }
    ::= { eqlNASApplianceDefaultCfgEntry 29 }

eqlNASApplianceDefaultNFSExportsFileId32bit OBJECT-TYPE
    SYNTAX          INTEGER {
                        enabled  (0),
                        disabled (1)
                    }
    MAX-ACCESS      read-create
    STATUS          current
    DESCRIPTION     "Default option to trigger 32-bit compatibility mode for NFS export. When enabled, reported FileId (inode) information contains only lower 32-bits set. When disabled, reported FileId (inode) information contains full 64-bit values."
    DEFVAL          { enabled }
    ::= { eqlNASApplianceDefaultCfgEntry 30 }

--------------------------------------------------------------------------------------------
eqlNASContainerStatusTable OBJECT-TYPE
    SYNTAX          SEQUENCE OF EqlNASContainerStatusEntry
    MAX-ACCESS      not-accessible
    STATUS          current
    DESCRIPTION     "EqualLogic-Dynamic NAS Container Table.
                     This table contains a list of NAS Appliance configurations for containers the group is managing.
                     TimeoutAll:60"
    ::=    { eqlNASObjects 5 }

eqlNASContainerStatusEntry OBJECT-TYPE
    SYNTAX          EqlNASContainerStatusEntry
    MAX-ACCESS      not-accessible
    STATUS          current
    DESCRIPTION     "An entry (row) containing NAS Container Status info."
    INDEX           { eqlApplianceIndex, eqlNASContainerIndex }

    ::=   { eqlNASContainerStatusTable 1}

EqlNASContainerStatusEntry ::=
    SEQUENCE {
	eqlNASContainerStatusConnections         Unsigned32,
	eqlNASContainerStatusUsedSpace           Unsigned32,
	eqlNASContainerStatusSnapshotSpace       Unsigned32,
	eqlNASContainerStatusNumNFSExports       Unsigned32,
	eqlNASContainerStatusNumCIFSShares       Unsigned32,
	eqlNASContainerStatusAllocatedSpace      Unsigned32,
	eqlNASContainerStatusFreeSpace           Unsigned32,
	eqlNASContainerStatusNumOfSnapshots      Unsigned32,
	eqlNASContainerStatusOptimizationSpaceSavings      Unsigned32,
	eqlNASContainerStatusOptimized      TruthValue,
	eqlNASContainerStatusReplState           INTEGER,
	eqlNASContainerStatusNextSnapshotID      Unsigned32
    }

eqlNASContainerStatusConnections OBJECT-TYPE
    SYNTAX          Unsigned32
    MAX-ACCESS      read-only
    STATUS          current
    DESCRIPTION     ""
    ::= { eqlNASContainerStatusEntry 1 }


eqlNASContainerStatusUsedSpace OBJECT-TYPE
    SYNTAX          Unsigned32
    MAX-ACCESS      read-only
    STATUS          current
    DESCRIPTION     "Space used by NAS Containers including both snapshot space and filesystem usage)"
    ::= { eqlNASContainerStatusEntry 2 }


eqlNASContainerStatusSnapshotSpace OBJECT-TYPE
    SYNTAX          Unsigned32
    MAX-ACCESS      read-only
    STATUS          current
    DESCRIPTION     "Amount of used space in MB used by NAS Containers for storage of snapshot data. This is not snapshot reserve but rather snapshot reserve space currently in use. Initially this value would be 0."
    ::= { eqlNASContainerStatusEntry 3 }


eqlNASContainerStatusNumNFSExports OBJECT-TYPE
    SYNTAX          Unsigned32
    MAX-ACCESS      read-only
    STATUS          current
    DESCRIPTION     ""
    ::= { eqlNASContainerStatusEntry 4 }


eqlNASContainerStatusNumCIFSShares OBJECT-TYPE
    SYNTAX          Unsigned32
    MAX-ACCESS      read-only
    STATUS          current
    DESCRIPTION     ""
    ::= { eqlNASContainerStatusEntry 5 }

eqlNASContainerStatusAllocatedSpace OBJECT-TYPE
    SYNTAX          Unsigned32
    MAX-ACCESS      read-only
    STATUS          current
    DESCRIPTION     "Amount of space in MB allocated by NAS Containers"
    ::= { eqlNASContainerStatusEntry 6 }

eqlNASContainerStatusFreeSpace OBJECT-TYPE
    SYNTAX          Unsigned32
    MAX-ACCESS      read-only
    STATUS          current
    DESCRIPTION     "Amount of total free space in MB including both snapshot and filesystem"
    ::= { eqlNASContainerStatusEntry 7 }

eqlNASContainerStatusNumOfSnapshots OBJECT-TYPE
    SYNTAX          Unsigned32
    MAX-ACCESS      read-only
    STATUS          current
    DESCRIPTION     "Number of snapshots"
    ::= { eqlNASContainerStatusEntry 8 }

eqlNASContainerStatusOptimizationSpaceSavings OBJECT-TYPE
    SYNTAX          Unsigned32
    MAX-ACCESS      read-only
    STATUS          current
    DESCRIPTION     "Amount of space saved in MB due to applying optimization"
    ::= { eqlNASContainerStatusEntry 9 }

eqlNASContainerStatusOptimized OBJECT-TYPE
    SYNTAX          TruthValue
    MAX-ACCESS      read-only
    STATUS          current
    DESCRIPTION     "True if optimization was enabled once, false otherwise"
    ::= { eqlNASContainerStatusEntry 10 }

eqlNASContainerStatusReplState OBJECT-TYPE
    SYNTAX          INTEGER {
                             standalone(0),
                             source(1),
                             destination(2),
                             promoted(3),
							 not-available(4)
                            }
    MAX-ACCESS      read-only
    STATUS          current
    DESCRIPTION     "This column gives information about the replication
                     status of this FileSystem. Standalone means the filesystem
                     is not being replicated. Source means this filesystem is a
                     source to a remote filesystem. Destination means this
                     filesystem is destination for a source filesystem.
                     Promoted means this filesystem used to be a destination
                     but is right now promoted."
    ::= { eqlNASContainerStatusEntry 11 }


eqlNASContainerStatusNextSnapshotID	OBJECT-TYPE
    SYNTAX          Unsigned32
    MAX-ACCESS      read-only
    STATUS          current
    DESCRIPTION     "This column denotes the next SnapshotID avaiable for this particular container."
    ::= { eqlNASContainerStatusEntry 12 }


--------------------------------------------------------------------------------------------
eqlNASApplianceNFSExportsTable OBJECT-TYPE
    SYNTAX	    SEQUENCE OF EqlNASApplianceNFSExportsEntry
    MAX-ACCESS	    not-accessible
    STATUS	    current
    DESCRIPTION	    "Equallogic-Dynamic NAS NFS Exports Table.
		    This table contains a list of NFS exports configuration entry.
                    TimeoutAll:60"
    ::= { eqlNASObjects 6 }

eqlNASApplianceNFSExportsEntry OBJECT-TYPE
    SYNTAX	    EqlNASApplianceNFSExportsEntry
    MAX-ACCESS	    not-accessible
    STATUS	    current
    DESCRIPTION	    "An entry (row) containing NFS exports configuration."
    INDEX	    { eqlApplianceIndex, eqlNASContainerIndex, eqlNASApplianceNFSExportName }
    ::= { eqlNASApplianceNFSExportsTable 1 }

EqlNASApplianceNFSExportsEntry ::=
    SEQUENCE {
	eqlNASApplianceNFSExportName			OCTET STRING,
	eqlNASApplianceNFSExportsRowStatus		RowStatus,
	eqlNASApplianceNFSExportDirectory		OCTET STRING,
	eqlNASApplianceNFSAccess		        INTEGER,
	eqlNASApplianceNFSLimitReportedSize		Unsigned32,
	eqlNASApplianceNFSAccessClientIPType		InetAddressType,
	eqlNASApplianceNFSAccessClientIP		InetAddress,
	eqlNASApplianceNFSAccessClientNetmaskType	InetAddressType,
	eqlNASApplianceNFSAccessClientNetmask		InetAddress,
	eqlNASApplianceNFSTrustUsers			INTEGER,
	eqlNASApplianceNFSExportsFileId32bit	INTEGER
    }

eqlNASApplianceNFSExportName OBJECT-TYPE
    SYNTAX          OCTET STRING (SIZE (1..64))
    MAX-ACCESS      not-accessible
    STATUS          current
    DESCRIPTION     "Contains only letters, digits and underscores. Must begin with a letter."
    ::= { eqlNASApplianceNFSExportsEntry 1 }


eqlNASApplianceNFSExportsRowStatus OBJECT-TYPE
    SYNTAX          RowStatus
    MAX-ACCESS      read-create
    STATUS          current
    DESCRIPTION     "Rowstatus variable used to manage this conceptual row."
    ::= { eqlNASApplianceNFSExportsEntry 2 }

eqlNASApplianceNFSExportDirectory OBJECT-TYPE
    SYNTAX          OCTET STRING (SIZE (1..512)) -- Restricting to 512 characters since eqlNASContainerDirectoryName has a limit of 512 characters. Also, increasing this to 1024 means increasing kRCC_MAX_CMD_LEN to greater than 1024.
    MAX-ACCESS      read-create
    STATUS          current
    DESCRIPTION     "Full path to the Directory to be exported."
    ::= { eqlNASApplianceNFSExportsEntry 3 }

eqlNASApplianceNFSAccess OBJECT-TYPE
    SYNTAX          INTEGER {
			read-write(1),
			read-only(2)
		    }
    MAX-ACCESS      read-create
    STATUS          current
    DESCRIPTION     ""
    DEFVAL	    { read-write }
    ::= { eqlNASApplianceNFSExportsEntry 4 }

eqlNASApplianceNFSLimitReportedSize OBJECT-TYPE
    SYNTAX          Unsigned32
    UNITS           "MB"
    MAX-ACCESS      read-create
    STATUS          current
    DESCRIPTION     "Default value is zero and it means the actual size of NFS export will be returned. When the value is non-zeo, this value will be used instead of actual NFS Export size."
    DEFVAL          {0}
    ::= { eqlNASApplianceNFSExportsEntry 5 }

eqlNASApplianceNFSAccessClientIPType OBJECT-TYPE
    SYNTAX          InetAddressType
    MAX-ACCESS      read-create
    STATUS          current
    DESCRIPTION     "Type of eqlNASApplianceNFSAccessClientIP field."
    ::= { eqlNASApplianceNFSExportsEntry 6 }

eqlNASApplianceNFSAccessClientIP OBJECT-TYPE
    SYNTAX          InetAddress
    MAX-ACCESS      read-create
    STATUS          current
    DESCRIPTION     "Value of this column along with eqlNASApplianceNFSAccessClientNetmask will determine access policy for clients"
    ::= { eqlNASApplianceNFSExportsEntry 7 }

eqlNASApplianceNFSAccessClientNetmaskType OBJECT-TYPE
    SYNTAX          InetAddressType
    MAX-ACCESS      read-create
    STATUS          current
    DESCRIPTION     "Type of eqlNASApplianceNFSAccessClientNetmask field. This value must match with eqlNASApplianceNFSAccessClientIPType field."
    ::= { eqlNASApplianceNFSExportsEntry 8 }

eqlNASApplianceNFSAccessClientNetmask OBJECT-TYPE
    SYNTAX          InetAddress
    MAX-ACCESS      read-create
    STATUS          current
    DESCRIPTION     "Value of this column along with eqlNASApplianceNFSAccessClientIP will determine access policy for clients"
    ::= { eqlNASApplianceNFSExportsEntry 9 }

eqlNASApplianceNFSTrustUsers OBJECT-TYPE
    SYNTAX          INTEGER {
			all-except-root(1),
			none(2),
			all(3)
		    }
    MAX-ACCESS      read-create
    STATUS          current
    DESCRIPTION     " Trusted users who can access the NFS Export"
    DEFVAL	    { all-except-root }
    ::= { eqlNASApplianceNFSExportsEntry 10 }

eqlNASApplianceNFSExportsFileId32bit OBJECT-TYPE
    SYNTAX          INTEGER {
                        enabled  (0),
                        disabled (1)
                    }
    MAX-ACCESS      read-create
    STATUS          current
    DESCRIPTION     "Determines 32-bit compatibility mode for this NFS export. When enabled, reported FileId (inode) information contains only lower 32-bits. When disabled, reported FileId (inode) information contains full 64-bit values."
    DEFVAL          { enabled }
    ::= { eqlNASApplianceNFSExportsEntry 11 }

--------------------------------------------------------------------------------------------
--
-- *** SW: Not yet supported by Exanet ***
--
-- eqlNASApplianceNFSConnectionTable OBJECT-TYPE
--     SYNTAX	    SEQUENCE OF EqlNASApplianceNFSConnectionEntry
--     MAX-ACCESS	    not-accessible
--     STATUS	    current
--     DESCRIPTION	    "Equallogic-Dynamic NAS NFS Connection Table.
-- 		    This table contains a list of NFS connection entries.
--                  TimeoutAll:60"
--     ::= { eqlNASObjects 7 }
--
-- eqlNASApplianceNFSConnectionEntry OBJECT-TYPE
--     SYNTAX	    EqlNASApplianceNFSConnectionEntry
--     MAX-ACCESS	    not-accessible
--     STATUS	    current
--     DESCRIPTION	    "An entry (row) containing NFS connection entry."
--     INDEX	    { eqlApplianceIndex, eqlNASContainerIndex, eqlNASApplianceNFSExportName,
-- 		      eqlNASApplianceNFSSourceIpAddressType, eqlNASApplianceNFSSourceIpAddress,
-- 		      eqlNASApplianceNFSClientSourcePort }
--     ::= { eqlNASApplianceNFSConnectionTable 1 }
--
-- EqlNASApplianceNFSConnectionEntry ::=
--     SEQUENCE {
-- 	eqlNASApplianceNFSSourceIpAddressType		InetAddressType,
-- 	eqlNASApplianceNFSSourceIpAddress		InetAddress,
-- 	eqlNASApplianceNFSClientSourcePort		Unsigned32,
-- 	eqlNASApplianceSpartanMemberIndex		Unsigned32,
-- 	eqlNASApplianceNFSClientVIPaddressType		InetAddressType,
-- 	eqlNASApplianceNFSClientVIPaddress		InetAddress
--     }
--
-- eqlNASApplianceNFSSourceIpAddressType OBJECT-TYPE
--     SYNTAX	    InetAddressType
--     MAX-ACCESS	    not-accessible
--     STATUS	    current
--     DESCRIPTION	    ""
--     ::= { eqlNASApplianceNFSConnectionEntry 1 }
--
-- eqlNASApplianceNFSSourceIpAddress OBJECT-TYPE
--     SYNTAX	    InetAddress
--     MAX-ACCESS	    not-accessible
--     STATUS	    current
--     DESCRIPTION	    ""
--     ::= { eqlNASApplianceNFSConnectionEntry 2 }
--
-- eqlNASApplianceNFSClientSourcePort OBJECT-TYPE
--     SYNTAX	    Unsigned32(1..65535)
--     MAX-ACCESS	    not-accessible
--     STATUS	    current
--     DESCRIPTION	    ""
--     ::= { eqlNASApplianceNFSConnectionEntry 3 }
--
-- eqlNASApplianceSpartanMemberIndex OBJECT-TYPE
--     SYNTAX	    Unsigned32
--     MAX-ACCESS	    read-only
--     STATUS	    current
--     DESCRIPTION	    ""
--     ::= { eqlNASApplianceNFSConnectionEntry 4 }
--
-- eqlNASApplianceNFSClientVIPaddressType OBJECT-TYPE
--     SYNTAX	    InetAddressType
--     MAX-ACCESS	    read-only
--     STATUS	    current
--     DESCRIPTION	    ""
--     ::= { eqlNASApplianceNFSConnectionEntry 5 }
--
-- eqlNASApplianceNFSClientVIPaddress OBJECT-TYPE
--     SYNTAX	    InetAddress
--     MAX-ACCESS	    read-only
--     STATUS	    current
--     DESCRIPTION	    ""
--     ::= { eqlNASApplianceNFSConnectionEntry 6 }
--

--------------------------------------------------------------------------------------------
eqlNASApplianceCIFSTable OBJECT-TYPE
    SYNTAX	    SEQUENCE OF EqlNASApplianceCIFSEntry
    MAX-ACCESS	    not-accessible
    STATUS	    current
    DESCRIPTION	    "Equallogic-Dynamic NAS CIFS Table.
		    This table contains a list of CIFS configuration entry.
                    TimeoutAll:60"
    ::= { eqlNASObjects 8 }

eqlNASApplianceCIFSEntry OBJECT-TYPE
    SYNTAX	    EqlNASApplianceCIFSEntry
    MAX-ACCESS	    not-accessible
    STATUS	    current
    DESCRIPTION	    "An entry (row) containing CIFS configuration."
    INDEX	    { eqlApplianceIndex, eqlNASContainerIndex, eqlNASApplianceCIFSShareName }
    ::= { eqlNASApplianceCIFSTable 1 }

EqlNASApplianceCIFSEntry ::=
    SEQUENCE {
	eqlNASApplianceCIFSShareName			OCTET STRING,
	eqlNASApplianceCIFSRowStatus			RowStatus,
	eqlNASApplianceCIFSExportedDirectory		OCTET STRING,
	eqlNASApplianceCIFSAllowGuestAccess		TruthValue,
	eqlNASApplianceCIFSLockEnforcement		INTEGER,
        eqlNASApplianceCIFSAntivirusEnabled             StatusDisabledDefault,
        eqlNASApplianceCIFSAntivirusPolicy              INTEGER,
        eqlNASApplianceCIFSAntivirusExtensions          OCTET STRING,
        eqlNASApplianceCIFSAntivirusExtensionsPolicy    INTEGER,
        eqlNASApplianceCIFSAntivirusExcludeDirPaths     OCTET STRING,
        eqlNASApplianceCIFSAntivirusLargeFileSize       Unsigned32,
        eqlNASApplianceCIFSAntivirusLargeFileOpen       INTEGER
    }

eqlNASApplianceCIFSShareName OBJECT-TYPE
    SYNTAX	    OCTET STRING (SIZE (1..64))
    MAX-ACCESS	    not-accessible
    STATUS	    current
    DESCRIPTION	    "Contains only letters, digits and underscores."
    ::= { eqlNASApplianceCIFSEntry 1 }


eqlNASApplianceCIFSRowStatus OBJECT-TYPE
    SYNTAX	    RowStatus
    MAX-ACCESS	    read-create
    STATUS	    current
    DESCRIPTION	    " Rowstatus variable used to manage this conceptual row."
    ::= { eqlNASApplianceCIFSEntry 2 }

eqlNASApplianceCIFSExportedDirectory OBJECT-TYPE
    SYNTAX	    OCTET STRING (SIZE (1..512)) -- Restricting to 512 characters since eqlNASContainerDirectoryName has a limit of 512 characters. Also, increasing this to 1024 means increasing kRCC_MAX_CMD_LEN to greater than 1024.
    MAX-ACCESS	    read-create
    STATUS	    current
    DESCRIPTION	    "Full Path to the directory to be exported."
    ::= { eqlNASApplianceCIFSEntry 3 }

eqlNASApplianceCIFSAllowGuestAccess OBJECT-TYPE
    SYNTAX	    TruthValue
    MAX-ACCESS	    read-create
    STATUS	    current
    DESCRIPTION	    "When set to true, guests will be allowed to access this share."
    DEFVAL	    { true }
    ::= { eqlNASApplianceCIFSEntry 4 }

eqlNASApplianceCIFSLockEnforcement OBJECT-TYPE
    SYNTAX	    INTEGER {
			all-locks(0),
			no-byte-range-locks(1),
			only-share-locks(2)
		    }
    MAX-ACCESS	    read-create
    STATUS	    current
    DESCRIPTION	    "Locking enforcement policy for this CIFS Share. This software release does not support changing the locking enforcement policy. Only the default option (all-locks) is supported."
    DEFVAL	    { all-locks }
    ::= { eqlNASApplianceCIFSEntry 5 }

eqlNASApplianceCIFSAntivirusEnabled OBJECT-TYPE
    SYNTAX          StatusDisabledDefault
    MAX-ACCESS      read-create
    STATUS          current
    DESCRIPTION     "When set to enabled, antivirus service will be enabled for this share. Else it will be disabled."
    DEFVAL      { disabled }
    ::= { eqlNASApplianceCIFSEntry 6 }

eqlNASApplianceCIFSAntivirusPolicy OBJECT-TYPE
    SYNTAX          INTEGER {
                            quarantine(0),
                            do-nothing(1),
                            remove(2)
                            }
    MAX-ACCESS      read-create
    STATUS          current
    DESCRIPTION     "Determines the action to take when a file is found to be infected by a virus.  This field is deprecated and unsupported.  The value now always will be quarantine(0)."
    DEFVAL      { quarantine }
    ::= { eqlNASApplianceCIFSEntry 7 }

eqlNASApplianceCIFSAntivirusExtensions OBJECT-TYPE
    SYNTAX          OCTET STRING (SIZE (0..255))
    MAX-ACCESS      read-create
    STATUS          current
    DESCRIPTION     "Comma-separated list of the file extensions which should / should not be virus-scanned. The value of the next field i.e. eqlNASApplianceCIFSAntivirusExtensionsPolicy determines if the files with the corresponding extensions will be scanned or not for viruses. Cannot contain wild characters * and ?. Extensions are case-insensitive."
    ::= { eqlNASApplianceCIFSEntry 8 }

eqlNASApplianceCIFSAntivirusExtensionsPolicy OBJECT-TYPE
    SYNTAX          INTEGER {
                            exclude(0),
                            include(1)
                            }
    MAX-ACCESS      read-create
    STATUS          current
    DESCRIPTION     "Determines whether the files whose extensions match with those specified in the field above i.e. eqlNASApplianceCIFSAntivirusExtensions, should be scanned OR should not be scanned for viruses.  This field is deprecated and unsupported.  The value now always will be exclude(0)."
    DEFVAL      { exclude }
    ::= { eqlNASApplianceCIFSEntry 9 }

eqlNASApplianceCIFSAntivirusExcludeDirPaths OBJECT-TYPE
    SYNTAX          OCTET STRING (SIZE (0..512))
    MAX-ACCESS      read-create
    STATUS          current
    DESCRIPTION     "Comma-separated list of the directory paths which should not be scanned for viruses. Paths can contain wildcards * and ?. NOTE: * will not match several path components. "
    ::= { eqlNASApplianceCIFSEntry 10 }

eqlNASApplianceCIFSAntivirusLargeFileSize OBJECT-TYPE
    SYNTAX          Unsigned32
    MAX-ACCESS      read-create
    STATUS          current
    DESCRIPTION     "Determines the largest file size in MB which is sent to Antivirus server for scanning on the fly. The files larger than the specified size are not scanned. Access to these large files will be allowed or denied based on the CIFS Antivirus Large File Open policy."
    DEFVAL          {3072}
    ::= { eqlNASApplianceCIFSEntry 11 }

eqlNASApplianceCIFSAntivirusLargeFileOpen OBJECT-TYPE
    SYNTAX          INTEGER {
                        deny  (0),
                        allow (1)
                    }
    MAX-ACCESS      read-create
    STATUS          current
    DESCRIPTION     "Determines if CIFS clients are allowed to open files larger than the value defined by CIFSAntivirusLargeFileSize."
    DEFVAL          { deny }
    ::= { eqlNASApplianceCIFSEntry 12 }


--------------------------------------------------------------------------------------------
eqlNASContainerDirectoryOpsTable OBJECT-TYPE
    SYNTAX	    SEQUENCE OF EqlNASContainerDirectoryOpsEntry
    MAX-ACCESS	    not-accessible
    STATUS	    current
    DESCRIPTION	    "Equallogic-Dynamic NAS Container Directory Operations Table. This table is used for directory operations.
                     TimeoutAll:60"
    ::= { eqlNASObjects 9 }

eqlNASContainerDirectoryOpsEntry OBJECT-TYPE
    SYNTAX	    EqlNASContainerDirectoryOpsEntry
    MAX-ACCESS	    not-accessible
    STATUS	    current
    DESCRIPTION	    "An entry for directory operations."
    INDEX	    { eqlApplianceIndex, eqlNASContainerIndex, eqlNASContainerDirectoryOpsIndex}
    ::= { eqlNASContainerDirectoryOpsTable 1 }

EqlNASContainerDirectoryOpsEntry ::=
    SEQUENCE {
    eqlNASContainerDirectoryOpsIndex        Unsigned32,
    eqlNASContainerDirectoryRowStatus	    RowStatus,
    eqlNASContainerDirectoryName            OCTET STRING,
    eqlNASContainerDirectoryCaseInsensitive INTEGER
    }

eqlNASContainerDirectoryOpsIndex OBJECT-TYPE
    SYNTAX          Unsigned32
    MAX-ACCESS      not-accessible
    STATUS          current
    DESCRIPTION     "This field specifies a unique index for identifying a NAS container directory ops entry."
    ::=   { eqlNASContainerDirectoryOpsEntry 1 }

eqlNASContainerDirectoryRowStatus OBJECT-TYPE
    SYNTAX	    RowStatus
    MAX-ACCESS	    read-create
    STATUS	    current
    DESCRIPTION	    " Rowstatus variable used to manage directories. Operations supported will be create and delete. Get and Getnext operations on this table will return error."
    ::= { eqlNASContainerDirectoryOpsEntry 2 }


eqlNASContainerDirectoryName OBJECT-TYPE
    SYNTAX	    OCTET STRING (SIZE (1..512)) -- Increasing this to 1024 will require increasing kRCC_MAX_CMD_LEN to greater than 1024. This increase is being avoided intentionally to reduce memory consumption by netmgtd.
    MAX-ACCESS	    read-create
    STATUS	    current
    DESCRIPTION	    "Full Path to the directory to be created or deleted. Ex: /home/user1. Create directory will fail if parent directory does not exist."
    ::= { eqlNASContainerDirectoryOpsEntry 3 }

eqlNASContainerDirectoryCaseInsensitive OBJECT-TYPE
    SYNTAX	    INTEGER {
                        yes(0),
                        no(1)
                    }
    MAX-ACCESS	    read-create
    STATUS	    current
    DESCRIPTION	    "Determines whether the directory created is case insensitve or not."
    ::= { eqlNASContainerDirectoryOpsEntry 4 }

--************************************************************

eqlNASSnapshotTable OBJECT-TYPE
    SYNTAX          SEQUENCE OF EqlNASSnapshotEntry
    MAX-ACCESS      not-accessible
    STATUS          current
    DESCRIPTION     "EqualLogic-Dynamic snapshot Table
                     This table contains a list of snapshots associated with the associated container.
                     TimeoutAll:60"
    ::=  {  eqlNASContainerTable 3 }

eqlNASSnapshotEntry OBJECT-TYPE
    SYNTAX          EqlNASSnapshotEntry
    MAX-ACCESS      not-accessible
    STATUS          current
    DESCRIPTION     "An entry (row) containing snap shot info."
    INDEX           { eqlApplianceIndex, eqlNASContainerIndex, eqlNASSnapshotIndex }
    ::=    { eqlNASSnapshotTable 1 }

EqlNASSnapshotEntry ::=
    SEQUENCE {
        eqlNASSnapshotIndex           Unsigned32,
        eqlNASSnapshotRowStatus       RowStatus,
        eqlNASSnapshotName            OCTET STRING,
        eqlNASSnapshotSize            Integer32,        -- does exanet return this or do we have to ask for it on each snapshot?(like in the gui)
                                                        -- if its not provided by default do we want to even show it? since its prob the delta size
        eqlNASSnapshotTimestamp       Counter32,
        eqlNASSnapshotRollBack        TruthValue,
	eqlNASSnapshotPolicyIdx       Integer32
    }

eqlNASSnapshotIndex  OBJECT-TYPE
    SYNTAX          Unsigned32
    MAX-ACCESS      not-accessible
    STATUS          current
    DESCRIPTION     "This field specifies a unique index which identifies a NAScontainer SnapShot."
    ::=  {  eqlNASSnapshotEntry 1 }

eqlNASSnapshotRowStatus OBJECT-TYPE
    SYNTAX          RowStatus
    MAX-ACCESS      read-create
    STATUS          current
    DESCRIPTION     "The rowstatus...."
    ::= {   eqlNASSnapshotEntry 2 }


eqlNASSnapshotName OBJECT-TYPE
    SYNTAX          OCTET STRING (SIZE (1..230))
    MAX-ACCESS      read-create
    STATUS          current
    DESCRIPTION     "This field specifies the friendly name used to identify a SnapShot.
                     The name is auto-generated based on the NAScontainer name, optionally it can be
                     provided or changed after the fact by the administrator."
    ::= {   eqlNASSnapshotEntry 3}

eqlNASSnapshotSize OBJECT-TYPE
    SYNTAX          Integer32
    MAX-ACCESS      read-only
    STATUS          current
    DESCRIPTION     "This field specifies the amount of space in MB a SnapShot consumes.
                     Note: Deleting the SnapShot is not guaranteed to return the space specified,
                     since a single block can be associated with multiple SnapShots. This value is xxxxc."
    ::= {   eqlNASSnapshotEntry 4 }

eqlNASSnapshotTimestamp OBJECT-TYPE
    SYNTAX          Counter32
    MAX-ACCESS      read-only
    STATUS          current
    DESCRIPTION     "EQL-SECONDARY-KEY
                     This field specifies the creation date/time for snapshot.
                     Time is represented as the time in seconds since 00:00:00 UTC, 1970-01-01."
    ::= {   eqlNASSnapshotEntry 5 }

eqlNASSnapshotRollBack OBJECT-TYPE
    SYNTAX          TruthValue
    MAX-ACCESS      read-create
    STATUS          current
    DESCRIPTION     "True indicates the NASContainer is to be resotred to the state of this Snapshot."
    DEFVAL          { false }
    ::= {   eqlNASSnapshotEntry 6 }

eqlNASSnapshotPolicyIdx  OBJECT-TYPE
    SYNTAX          Integer32
    MAX-ACCESS      read-only
    STATUS          current
    DESCRIPTION     "This value identifies the snapshot policy for this snapshot."
    DEFVAL          { 0 }
    ::=  {  eqlNASSnapshotEntry 7 }


---*********************************************************************

eqlNASSnapshotPolicyTable OBJECT-TYPE
    SYNTAX  SEQUENCE OF EqlNASSnapshotPolicyEntry
    MAX-ACCESS      not-accessible
    STATUS          current
    DESCRIPTION     "EqualLogic-Persistent NAS SnapSnot Policy Table.
                     TimeoutAll:60"
    ::=  {  eqlNASContainerTable 4 }

eqlNASSnapshotPolicyEntry OBJECT-TYPE
    SYNTAX          EqlNASSnapshotPolicyEntry
    MAX-ACCESS      not-accessible
    STATUS          current
    DESCRIPTION     "An entry (row) containing NAS snapshot scheduling policy
                     information.The policy determines when to create
                     snapshot(s) of a appliance container."
    INDEX           { eqlApplianceIndex, eqlNASContainerIndex, eqlNASSnapshotPolicyIndex }
::=    { eqlNASSnapshotPolicyTable 1 }


EqlNASSnapshotPolicyEntry ::=
    SEQUENCE {
        eqlNASSnapshotPolicyIndex               Integer32,
        eqlNASSnapshotPolicyRowStatus           RowStatus,
        eqlNASSnapshotPolicyName                OCTET STRING,
        eqlNASSnapshotPolicyMaxKeep             Integer32,
        eqlNASSnapshotPolicyType                INTEGER,
        eqlNASSnapshotPolicyRepeatFactor        Integer32,
        eqlNASSnapshotPolicyStartTime           Integer32,
        eqlNASSnapshotPolicyEndTime             Integer32,
        eqlNASSnapshotPolicyTimeFrequency       Integer32,
        eqlNASSnapshotPolicyStartDate           Integer32,
        eqlNASSnapshotPolicyEndDate             Integer32,
        eqlNASSnapshotPolicyWeekMask            Integer32,
        eqlNASSnapshotPolicyMonthMask           Integer32,
        eqlNASSnapshotPolicyOccurence           Integer32,
        eqlNASSnapshotPolicyReplication         SiteIndexOrZero,
        eqlNASSnapshotPolicyAdminStatus         INTEGER,
        eqlNASSnapshotPolicyCategory            INTEGER
    }

eqlNASSnapshotPolicyIndex  OBJECT-TYPE
    SYNTAX          Integer32
    MAX-ACCESS      not-accessible
    STATUS          current
    DESCRIPTION
          "This value uniquely identifies the snapshot policies for a container."

    ::=  {  eqlNASSnapshotPolicyEntry 1 }

eqlNASSnapshotPolicyRowStatus OBJECT-TYPE
    SYNTAX          RowStatus
    MAX-ACCESS      read-create
    STATUS          current
    DESCRIPTION
          "This value is used to manage the conceptual row."

    ::=  {  eqlNASSnapshotPolicyEntry 2 }


eqlNASSnapshotPolicyName  OBJECT-TYPE
    SYNTAX          OCTET STRING (SIZE (1..64))
    MAX-ACCESS      read-create
    STATUS          current
    DESCRIPTION
          "This value specifies user friendly name for the policy.
           It is unique within the context of a volume. Spaces are not allowed."

    ::=   { eqlNASSnapshotPolicyEntry 3}

eqlNASSnapshotPolicyMaxKeep  OBJECT-TYPE
    SYNTAX          Integer32 (1..2147483647)
    UNITS           "snapshots"
    MAX-ACCESS      read-create
    STATUS          current
    DESCRIPTION
          "
           The value of this object determines the maximum no of snapshots
           created by this policy that can exist at a given time. When number
           of snapshots created by this policy reaches this value, for creating
           a new snapshot oldest snapshot created using this policy will be
           deleted.
           In a set operation, if the new value of this object is less than
           the old value, required number of oldest snapshots created by this
           policy will be deleted.
          "
    DEFVAL          { 10 }
    ::=  {  eqlNASSnapshotPolicyEntry 6 }

eqlNASSnapshotPolicyType  OBJECT-TYPE
    SYNTAX          INTEGER     {
                      once    (1),
                      daily   (2),
                      weekly  (3),
                      monthly (4),
                      hourly  (5)
    }
    MAX-ACCESS      read-create
    STATUS          current
    DESCRIPTION
          "
           The value of this object determines the basic type of this policy.
           Except when set to once, the effective repetition period of the
           policy is determined using the value of this object along with
           the value of eqlNASSnapshotPolicyRepeatFactor.
           (See description of eqlNASSnapshotPolicyRepeatFactor
            for more information.)
          "

    DEFVAL          { daily }
    ::=  {  eqlNASSnapshotPolicyEntry 7 }

eqlNASSnapshotPolicyRepeatFactor  OBJECT-TYPE
    SYNTAX          Integer32 (1..2147483647)
    MAX-ACCESS      read-create
    STATUS          current
    DESCRIPTION
          "The value of this object along with eqlNASSnapshotPolicyType
           determines the effective repetition interval for this policy.
           The valid values are

              PolicyType            RepeatFactor
                 once                    1
                 hourly                  1
                 daily                  1-2147483647
                 weekly                 1-2147483647
                 monthly                1-2147483647

           If the policy type is daily and the value of this object is 2,
           snapshots will be taken once in every 2 days.
          "
    ::=  {  eqlNASSnapshotPolicyEntry 8 }


eqlNASSnapshotPolicyStartTime  OBJECT-TYPE
    SYNTAX          Integer32 (0..1439)
    UNITS           "minutes"
    MAX-ACCESS      read-create
    STATUS          current
    DESCRIPTION
          "
            The value of this object represents the time to start creating
            snapshot(s) within a day expressed as number of minutes
            from 12:00AM. The maximum value for this column is 24*60-1 which
            represents 11:59PM.
          "

    DEFVAL          { 0 }
    ::=  {  eqlNASSnapshotPolicyEntry 9 }

eqlNASSnapshotPolicyEndTime  OBJECT-TYPE
    SYNTAX          Integer32 (0..1439)
    UNITS           "minutes"
    MAX-ACCESS      read-create
    STATUS          current
    DESCRIPTION
          "
            The value of this object represents the time to stop creating
            snapshot(s) within a day expressed as number of minutes
            from 12:00AM. The maximum value for this column is 24*60-1 which
            represents 11:59PM.

            If eqlNASSnapshotPolicyType is once, the value of
            this column doesn't have any significance.

            If the value of this column is greater than start time, it
            represents end-time on the same day as start time. If the value
            is less than or equal to start time, it represents end-time on the
            next day of start time.
            This value doesnt have significance when frequency is set to zero.
            Endtime is exclusive when calculating no of snapshots.

            Example:
                     StartTime      EndTime    Frequency    NoofSnapshots
                       1320(10pm)   1380(11pm)    30mins        2
                       1320(10pm)   240(4am)      60mins        6
                       1320(10pm)   1320(10pm)    60mins        24
                       1320(10pm)   1319(9:59pm)  60mins        24
                       1320(10pm)     -            0mins         1
          "
    ::=  {  eqlNASSnapshotPolicyEntry 10 }

eqlNASSnapshotPolicyTimeFrequency  OBJECT-TYPE
    SYNTAX          Integer32 (0..1439)
    UNITS           "minutes"
    MAX-ACCESS      read-create
    STATUS          current
    DESCRIPTION
          "The value of this object determines how frequent snapshots must be
           taken between start time and end time. This value doesn't have
           significance when policy type is set to once. For other policytypes,
           the value of end time is exclusive.
           For example if starttime is 180 (3:00AM) and endtime is
           240(4:00AM), when frequency is set to 30, snapshots will be
           created at 3:00AM, 3:30AM.
           If the value is zero, it represents invalid frequency and
           in such case, end time doesnt have significance.
          "

    ::=  {  eqlNASSnapshotPolicyEntry 11 }

eqlNASSnapshotPolicyStartDate  OBJECT-TYPE
    SYNTAX          Integer32 (0..2147483647)
    UNITS           "days"
    MAX-ACCESS      read-create
    STATUS          current
    DESCRIPTION
          " The value of this object determines the date from which the policy
            will be active. By default, this is the policy creation date.
            The value is expressed as number of days since epoch.
          "

    ::=  {  eqlNASSnapshotPolicyEntry 12 }

eqlNASSnapshotPolicyEndDate  OBJECT-TYPE
    SYNTAX          Integer32 (0..2147483647)
    UNITS           "days"
    MAX-ACCESS      read-create
    STATUS          current
    DESCRIPTION
          " The value of this object determines the date after which the policy
            will be inactive.It doesnt have significance when policy type
            is once. Default value is the mamixum value allowed. When set to maximum
            value, the policy will be active until it gets deleted.
            The value is expressed as number of days since epoch.
          "
    DEFVAL          { 2147483647 }

    ::=  {  eqlNASSnapshotPolicyEntry 13 }


eqlNASSnapshotPolicyWeekMask  OBJECT-TYPE
    SYNTAX          Integer32
    MAX-ACCESS      read-create
    STATUS          current
    DESCRIPTION
          " The value of this column is significant only if policytype is
            set to weekly or monthly.  When the value is 0x7fffffff, it
            represents a special meaning to the value of occurence. See
            the description for occurence below.
            The LSB to LSB+6 bits of the mask are significant.
            Each bit represents a day in the week with LSB being Mon and LSB+6
            being Sun.
            If mask is 0x00000041 - snapshots will be created on Monday and
            Sunday. If mask is 0x0000007f - snapshots will be created on all
            weekdays which is effectively a daily policy. If mask is 0x0000001f,
            it represents week days.If mask is 0x00000060, it represents
            weekend days.
          "

    ::=  {  eqlNASSnapshotPolicyEntry 14 }

eqlNASSnapshotPolicyMonthMask  OBJECT-TYPE
    SYNTAX          Integer32
    MAX-ACCESS      read-create
    STATUS          current
    DESCRIPTION
          " The value of this column is currently not being used."

    ::=  {  eqlNASSnapshotPolicyEntry 15 }

eqlNASSnapshotPolicyOccurence  OBJECT-TYPE
    SYNTAX          Integer32
    MAX-ACCESS      read-create
    STATUS          current
    DESCRIPTION
          "
           The value of this column is significant only if the policy type is
           set to monthly.

           If weekmask is set to 0x7fffffff, the value of this column represents
           the occurence of a day with in a month. Example:If the value of this
           column is 5, it represents 5th day of the month. When the week mask
           is set to a value other than 0x7fffffff, the value of this column
           defines the occurence of a day as defined by weekmask. Example: When
            weekmask is set to 0x00000001 (Monday) and value of this column
           represents the following.

                        Value            Meaning

                          0x1               First monday of the month
                          0x2               Second monday of the month
                          0x3               Third monday of the month
                          0x4               Fourth monday of the month
                          0x7fffffff        Last monday of the month
          "

    DEFVAL  {0}
    ::=  {  eqlNASSnapshotPolicyEntry 17 }

eqlNASSnapshotPolicyReplication    OBJECT-TYPE
   SYNTAX            SiteIndexOrZero
   MAX-ACCESS        read-create
   STATUS            current
   DESCRIPTION       "When a row is created with this object set to a non-zero value, and
                     a replication relationship has been configured for the base
                     volume, the snapshots created will be queued to be replicated to the
                     remote location as defined by the corresponding entry in the site table.
                     The value for this object cannot be changed once the schedule
                     is created."
   ::=   { eqlNASSnapshotPolicyEntry 18 }


eqlNASSnapshotPolicyAdminStatus    OBJECT-TYPE
   SYNTAX            INTEGER {
                        enable(0),
                        disable(1)
   }
   MAX-ACCESS        read-create
   STATUS            current
   DESCRIPTION       "When disabled, the schedule will stop creating snapshots until re-enabled."
   DEFVAL            {enable}
   ::=   { eqlNASSnapshotPolicyEntry 19 }

eqlNASSnapshotPolicyCategory    OBJECT-TYPE
   SYNTAX            INTEGER {
                        snapshot-replication-policy(0),
                        optimization-policy(1),
                        optimization-default-policy(2)
   }
   MAX-ACCESS        read-create
   STATUS            current
   DESCRIPTION       "Set to optimization-policy, if the schedule is for data reduction. Set to optimization-default-policy if the
						schedule is default data reduction policy. Default data reduction policy is created automatically and not
						allowed to be deleted."
   DEFVAL            {snapshot-replication-policy}
   ::=   { eqlNASSnapshotPolicyEntry 20 }


---*********************************************************************

eqlNASSnapshotPolicyStatusTable OBJECT-TYPE
    SYNTAX  SEQUENCE OF EqlNASSnapshotPolicyStatusEntry
    MAX-ACCESS      not-accessible
    STATUS          current
    DESCRIPTION     "EqualLogic-Dynamic NAS SnapSnot Policy Table.
                     TimeoutAll:60"
    ::=  {  eqlNASContainerTable 5 }

eqlNASSnapshotPolicyStatusEntry OBJECT-TYPE
    SYNTAX          EqlNASSnapshotPolicyStatusEntry
    MAX-ACCESS      not-accessible
    STATUS          current
    DESCRIPTION     "An entry containing NAS snapshot scheduling policy
                     information."
    AUGMENTS        { eqlNASSnapshotPolicyEntry }
::=    { eqlNASSnapshotPolicyStatusTable 1 }

EqlNASSnapshotPolicyStatusEntry ::=
    SEQUENCE {
        eqlNASSnapshotPolicyStatusNextCreate          Counter32,
        eqlNASSnapshotPolicyStatusOperStatus          INTEGER
    }

eqlNASSnapshotPolicyStatusNextCreate  OBJECT-TYPE
    SYNTAX          Counter32
    MAX-ACCESS      read-only
    STATUS          current
    DESCRIPTION
          "
           The value of this column represents number of seconds since epoch
           at which the next snapshot by this policy is going to be created.
          "
    ::=  {  eqlNASSnapshotPolicyStatusEntry 1 }

eqlNASSnapshotPolicyStatusOperStatus  OBJECT-TYPE
    SYNTAX          INTEGER {
                    enabled(0),
                    disabled(1),
                    expired(2),
                    active(3)
    }

    MAX-ACCESS      read-only
    STATUS          current
    DESCRIPTION
          "
           The value of this column represents the current operational status of this policy.
           The policy status is set to expired after end date. The policy status is set to active
           for optimization policies which are currently running.
          "

    ::=  {  eqlNASSnapshotPolicyStatusEntry 2 }


---************************************************************

eqlNASQuotaTable OBJECT-TYPE
    SYNTAX          SEQUENCE OF EqlNASQuotaEntry
    MAX-ACCESS      not-accessible
    STATUS          current
    DESCRIPTION     "EqualLogic-Dynamic quota Table
                     This table contains a list of quotas associated with the associated container.
                     TimeoutAll:60"
    ::=  {  eqlNASContainerTable 6 }

eqlNASQuotaEntry OBJECT-TYPE
    SYNTAX          EqlNASQuotaEntry
    MAX-ACCESS      not-accessible
    STATUS          current
    DESCRIPTION     "An entry (row) containing quota info."
    INDEX           { eqlApplianceIndex, eqlNASContainerIndex, eqlNASQuotaTargetType, eqlNASQuotaTargetName }
    ::=    { eqlNASQuotaTable 1 }

EqlNASQuotaEntry ::=
    SEQUENCE {
        eqlNASQuotaRowStatus       RowStatus,
        eqlNASQuotaTargetType      INTEGER,
        eqlNASQuotaTargetName      OCTET STRING,
        eqlNASQuotaWarnLimit       Integer32,
        eqlNASQuotaHardLimit       Unsigned32,
        eqlNASQuotaUsage        Integer32
    }

eqlNASQuotaRowStatus OBJECT-TYPE
    SYNTAX          RowStatus
    MAX-ACCESS      read-create
    STATUS          current
    DESCRIPTION     "The rowstatus...."
    ::= { eqlNASQuotaEntry 1 }

eqlNASQuotaTargetType OBJECT-TYPE
    SYNTAX	    INTEGER {
            unused(0),
		    allofgroup(1),
			anyuseringroup(2),
			user(3),
            defaultuser(4),
            defaultgroup(5),
            allquotas(6)                   -- used by gui to request all quotas with no filtering for type
		    }
    MAX-ACCESS	    read-create
    STATUS	    current
    DESCRIPTION	    "Type of target for this quota definition row"
    ::= { eqlNASQuotaEntry 2 }

eqlNASQuotaTargetName OBJECT-TYPE
    SYNTAX          OCTET STRING (SIZE (1..129))
    MAX-ACCESS      read-create
    STATUS          current
    DESCRIPTION     "The name of the user or group as indicated by the target type. AD groups can be 129 bytes "
    ::= {   eqlNASQuotaEntry 3 }

eqlNASQuotaWarnLimit OBJECT-TYPE
    SYNTAX          Integer32
    MAX-ACCESS      read-create
    STATUS          current
    DESCRIPTION     "This field specifies the amount of space in MB at which an alert is generated."
    ::= {   eqlNASQuotaEntry 4 }

eqlNASQuotaHardLimit OBJECT-TYPE
    SYNTAX          Unsigned32
    UNITS           "MB"
    MAX-ACCESS      read-create
    STATUS          current
    DESCRIPTION     "This field specifies the amount of space in MB at which writes are disallowed."
    ::= {   eqlNASQuotaEntry 5 }


eqlNASQuotaUsage OBJECT-TYPE
    SYNTAX          Integer32
    MAX-ACCESS      read-only
    STATUS          current
    DESCRIPTION     "This field specifies the amount of space in MB currently in use by targetname."
    ::= {   eqlNASQuotaEntry 6 }


---************************************************************


eqlNASReplSiteTable OBJECT-TYPE
    SYNTAX        SEQUENCE OF EqlNASReplSiteEntry
    MAX-ACCESS    not-accessible
    STATUS        current
    DESCRIPTION
     "EqualLogic-Persistent
      TimeoutAll:60"
::= { eqlNASObjects 10 }

eqlNASReplSiteEntry OBJECT-TYPE
    SYNTAX        EqlNASReplSiteEntry
    MAX-ACCESS    not-accessible
    STATUS        current
    DESCRIPTION
      ""
    INDEX           { eqlApplianceIndex, eqlNASReplSitePartnershipId }
::= { eqlNASReplSiteTable 1 }

EqlNASReplSiteEntry ::= SEQUENCE {
   eqlNASReplSitePartnershipId       Unsigned32,
   eqlNASReplSiteRowStatus           RowStatus,
   eqlNASReplSiteVolumeReplSiteIndex SiteIndex,
   eqlNASReplSiteLocalClusterInetAddrType  InetAddressType,
   eqlNASReplSiteLocalClusterInetAddr      InetAddress,
   eqlNASReplSiteRemoteClusterInetAddrType InetAddressType,
   eqlNASReplSiteRemoteClusterInetAddr     InetAddress,
   eqlNASReplSitePartnershipState      INTEGER,
   eqlNASReplSiteUserName              OCTET STRING,
   eqlNASReplSitePassword              OCTET STRING,
   eqlNASReplSiteRemoteClusterName     OCTET STRING,
   eqlNASReplSiteAction                INTEGER,
   eqlNASReplSiteRemoteUserName        OCTET STRING,
   eqlNASReplSiteRemotePassword        OCTET STRING,
   eqlNASReplSiteRemoteClusterId       ClusterIdType,
   eqlNASReplSiteRemoteClusterMPV      Unsigned32,
   eqlNASReplSiteRemoteNetworkAddrType InetAddressType,
   eqlNASReplSiteRemoteNetworkAddr     InetAddress,
   eqlNASReplSiteRemoteNetworkMask     InetAddress
}

eqlNASReplSitePartnershipId OBJECT-TYPE
   SYNTAX        Unsigned32
   MAX-ACCESS    read-only
   STATUS        current
   DESCRIPTION
      "This is the partnership Id used by Exastore to identify the partnership in the XML API"
::= { eqlNASReplSiteEntry 1 }

eqlNASReplSiteRowStatus OBJECT-TYPE
   SYNTAX RowStatus
   MAX-ACCESS    read-create
   STATUS        current
   DESCRIPTION
      "The status of the row"
::= { eqlNASReplSiteEntry 2 }

eqlNASReplSiteVolumeReplSiteIndex    OBJECT-TYPE
   SYNTAX        SiteIndex
   MAX-ACCESS    read-create
   STATUS        current
   DESCRIPTION
      "The value of eqliscsiVolumeReplSiteIndex to index into eqliscsiVolumeReplSiteTable."
::= { eqlNASReplSiteEntry 3 }

eqlNASReplSiteLocalClusterInetAddrType OBJECT-TYPE
   SYNTAX        InetAddressType
   MAX-ACCESS    read-only
   STATUS        current
   DESCRIPTION
      "The IP address type for the LocalCluster SAN VIP"
::= { eqlNASReplSiteEntry 4 }

eqlNASReplSiteLocalClusterInetAddr OBJECT-TYPE
   SYNTAX        InetAddress
   MAX-ACCESS    read-only
   STATUS        current
   DESCRIPTION
      "The IP address for the LocalCluster SAN VIP"
::= { eqlNASReplSiteEntry 5 }

eqlNASReplSiteRemoteClusterInetAddrType OBJECT-TYPE
   SYNTAX        InetAddressType
   MAX-ACCESS    read-write
   STATUS        current
   DESCRIPTION
      "The IP address type for the RemoteCluster SAN VIP"
::= { eqlNASReplSiteEntry 6 }


eqlNASReplSiteRemoteClusterInetAddr OBJECT-TYPE
   SYNTAX        InetAddress
   MAX-ACCESS    read-write
   STATUS        current
   DESCRIPTION
      "The IP address for the RemoteCluster SAN VIP"
::= { eqlNASReplSiteEntry 7 }

eqlNASReplSitePartnershipState OBJECT-TYPE
   SYNTAX        INTEGER {
                 none(0),
                 enabled(1),
                 configured(2)
   }
   MAX-ACCESS    read-write
   STATUS        current
   DESCRIPTION
      "This field gives the state of the partnership. enabled
       means the user has enabled NAS replication for this
       partnership. congiured means that we have configured
       this partnership with exastore. The state will always
       start with enabled, and then convert to configured
       once we push the partnership down to exastore."
::= { eqlNASReplSiteEntry 8 }

eqlNASReplSiteUserName OBJECT-TYPE
    SYNTAX        OCTET STRING  (SIZE (0..255))
    MAX-ACCESS    read-write
    STATUS        current
    DESCRIPTION
        "The replication username for the remote site. This
         is only used for senind messages to spartan agent."
::= { eqlNASReplSiteEntry 9 }

eqlNASReplSitePassword OBJECT-TYPE
    SYNTAX        OCTET STRING  (SIZE (0..255))
    MAX-ACCESS    not-accessible
    STATUS        current
    DESCRIPTION
        "The replication usernames password for the remote site.
         This is only used for senind messages to spartan agent."
::= { eqlNASReplSiteEntry 10 }

eqlNASReplSiteRemoteClusterName OBJECT-TYPE
    SYNTAX          OCTET STRING (SIZE (1..64))
    MAX-ACCESS      read-write
    STATUS          current
    DESCRIPTION     "This field specifies the partners cluster name, which is the remote eqlApplianceName."
::= { eqlNASReplSiteEntry 11 }

eqlNASReplSiteAction OBJECT-TYPE
   SYNTAX        INTEGER {
                 none(0),
                 configure(1),
                 delete(2)
   }
   MAX-ACCESS    read-write
   STATUS        current
   DESCRIPTION
      "This column will be used to perform actions on this partnership.
       The configure action will be used to configure the partnership
       with Exastore. The delete action will be used to delete partnership at Exastore"
::= { eqlNASReplSiteEntry 12 }

eqlNASReplSiteRemoteUserName OBJECT-TYPE
    SYNTAX        OCTET STRING  (SIZE (0..32))
    MAX-ACCESS    not-accessible
    STATUS        current
    DESCRIPTION
        "The replication username at the remote site. This
         is only used for senind messages to spartan agent. This is same as eqlNASApplianceReplRemoteUserName. "
::= { eqlNASReplSiteEntry 13 }

eqlNASReplSiteRemotePassword OBJECT-TYPE
    SYNTAX        OCTET STRING  (SIZE (0..255))
    MAX-ACCESS    not-accessible
    STATUS        current
    DESCRIPTION
        "The replication usernames password at the remote site.
         This is only used for senind messages to spartan agent."
::= { eqlNASReplSiteEntry 14 }

eqlNASReplSiteRemoteClusterId OBJECT-TYPE
    SYNTAX        ClusterIdType
    MAX-ACCESS    read-write
    STATUS        current
    DESCRIPTION "Get this string from node."
::= { eqlNASReplSiteEntry 15 }

eqlNASReplSiteRemoteClusterMPV OBJECT-TYPE
    SYNTAX          Unsigned32
    MAX-ACCESS      read-write
    STATUS          current
    DESCRIPTION     "The Management Protocol Version (MPV) of the remote cluster."
::= { eqlNASReplSiteEntry 16 }

eqlNASReplSiteRemoteNetworkAddrType OBJECT-TYPE
   SYNTAX        InetAddressType
   MAX-ACCESS    read-write
   STATUS        current
   DESCRIPTION
      "The IP address type (IPv4/IPv6) for the network ID
      of the remote cluster. NAS replication traffic is sent
      to this network. This is used for creating route to
      reach the remote cluster."
::= { eqlNASReplSiteEntry 17 }

eqlNASReplSiteRemoteNetworkAddr OBJECT-TYPE
   SYNTAX        InetAddress
   MAX-ACCESS    read-write
   STATUS        current
   DESCRIPTION
      "The network address/ID of the remote cluster.
      The network address/ID to reach the remote cluster
      NAS replication traffic is sent to this network."
::= { eqlNASReplSiteEntry 18 }

eqlNASReplSiteRemoteNetworkMask OBJECT-TYPE
   SYNTAX        InetAddress
   MAX-ACCESS    read-write
   STATUS        current
   DESCRIPTION
      "The netmask of the remote network.
      NAS replication traffic is sent to this network.
      This is used for creating route to reach the
      remote cluster."
::= { eqlNASReplSiteEntry 19 }



---************************************************************

eqlNASReplicationTable OBJECT-TYPE
    SYNTAX        SEQUENCE OF EqlNASReplicationEntry
    MAX-ACCESS    not-accessible
    STATUS        current
    DESCRIPTION
     "EqualLogic-Dynamic
     TimeoutAll:60"
::= { eqlNASObjects 11 }

eqlNASReplicationEntry OBJECT-TYPE
    SYNTAX        EqlNASReplicationEntry
    MAX-ACCESS    not-accessible
    STATUS        current
    DESCRIPTION
      ""
    INDEX           { eqlApplianceIndex, eqlNASContainerIndex, eqlNASReplSitePartnershipId, eqlNASReplicationId }
::= { eqlNASReplicationTable 1 }

EqlNASReplicationStatus ::= INTEGER {
                       unknown(0),
                       idle(1),
                       active(2),
                       waitingretry(3),
                       failed(4),
                       paused(5),
                       cancelled(6),
                       resuming(7),
                       deleting(8),
                       pausing(9),
                       finished(10),
                       cancelling(11),
                       promoted(12),
                       promoting(13),
                       idlewaittoschedule(14),
                       demoting(15)

    }

EqlNASReplicationEntry ::= SEQUENCE {
   eqlNASReplicationId               Unsigned32,
   eqlNASReplicationRowStatus        RowStatus,
   eqlNASReplicationLastRecoveryTime Counter32,
   eqlNASReplicationNextRecoveryTime Counter32,
   eqlNASReplicationSourceClusterName OCTET STRING,
   eqlNASReplicationSourceFSId       Unsigned32,
   eqlNASReplicationSourceFSName     OCTET STRING,
   eqlNASReplicationDestClusterName OCTET STRING,
   eqlNASReplicationDestFSId         Unsigned32,
   eqlNASReplicationDestFSName       OCTET STRING,
   eqlNASReplicationStatus           EqlNASReplicationStatus,
   eqlNASReplicationMinToComplete    Unsigned32,
   eqlNASReplicationTransferredPer   Unsigned32,
   eqlNASReplicationAction           INTEGER
}

eqlNASReplicationId OBJECT-TYPE
   SYNTAX        Unsigned32
   MAX-ACCESS    read-create
   STATUS        current
   DESCRIPTION
      "This is the replication Id used by Exastore to identify the replication in the XML API"
::= { eqlNASReplicationEntry 1 }

eqlNASReplicationRowStatus OBJECT-TYPE
   SYNTAX RowStatus
   MAX-ACCESS    read-create
   STATUS        current
   DESCRIPTION
      "The status of the row"
::= { eqlNASReplicationEntry 2 }

eqlNASReplicationLastRecoveryTime OBJECT-TYPE
    SYNTAX          Counter32
    MAX-ACCESS      read-only
    STATUS          current
    DESCRIPTION     "This field specifies the date/time of the last recovery snapshot
                     that has been copied. Time is represented as the time in seconds
                     since 00:00:00 UTC, 1970-01-01."
::= { eqlNASReplicationEntry 3 }

eqlNASReplicationNextRecoveryTime OBJECT-TYPE
    SYNTAX          Counter32
    MAX-ACCESS      read-only
    STATUS          current
    DESCRIPTION     "This field specifies the date/time of the next recovery snapshot
                     that will be copied. Time is represented as the time in seconds
                     since 00:00:00 UTC, 1970-01-01."
::= { eqlNASReplicationEntry 4 }

eqlNASReplicationSourceClusterName OBJECT-TYPE
    SYNTAX          OCTET STRING (SIZE (1..64))
    MAX-ACCESS      read-only
    STATUS          current
    DESCRIPTION     "This field specifies the source cluster name, which is the
                     eqlApplianceName of the cluster hosting the source FS."
::= { eqlNASReplicationEntry 5 }

eqlNASReplicationSourceFSId       OBJECT-TYPE
    SYNTAX          Unsigned32
    MAX-ACCESS      read-only
    STATUS          current
    DESCRIPTION     "Unique Identifier for the source FileSystem. This is the FSid."
::= { eqlNASReplicationEntry 6 }

eqlNASReplicationSourceFSName     OBJECT-TYPE
    SYNTAX          OCTET STRING (SIZE (1..230))
    MAX-ACCESS      read-create
    STATUS          current
    DESCRIPTION     "Name used to identify the source NAS Container. Contains only
                     letters, digits and underscores. Must begin with either letter
                     or an underscore. "
::= { eqlNASReplicationEntry 7 }

eqlNASReplicationDestClusterName OBJECT-TYPE
    SYNTAX          OCTET STRING (SIZE (1..64))
    MAX-ACCESS      read-only
    STATUS          current
    DESCRIPTION     "This field specifies the destination cluster name, which is the
                     eqlApplianceName of the cluster hosting the destination FS."
::= { eqlNASReplicationEntry 8 }

eqlNASReplicationDestFSId         OBJECT-TYPE
    SYNTAX          Unsigned32
    MAX-ACCESS      read-only
    STATUS          current
    DESCRIPTION     "Unique Identifier for the destination FileSystem. This is the FSid."
::= { eqlNASReplicationEntry 9 }

eqlNASReplicationDestFSName       OBJECT-TYPE
    SYNTAX          OCTET STRING (SIZE (1..230))
    MAX-ACCESS      read-create
    STATUS          current
    DESCRIPTION     "Name used to identify the destination NAS Container. Contains
                     only letters, digits and underscores. Must begin with either
                     letter or an underscore. "
::= { eqlNASReplicationEntry 10 }

eqlNASReplicationStatus OBJECT-TYPE
    SYNTAX EqlNASReplicationStatus
    MAX-ACCESS      read-only
    STATUS          current
    DESCRIPTION     "The status of this replication relationship."
::= { eqlNASReplicationEntry 11 }

eqlNASReplicationMinToComplete    OBJECT-TYPE
    SYNTAX          Unsigned32
    MAX-ACCESS      read-only
    STATUS          current
    DESCRIPTION     "Minutes left in completion of the current replication process."
::= {eqlNASReplicationEntry 12 }

eqlNASReplicationTransferredPer   OBJECT-TYPE
    SYNTAX          Unsigned32
    UNITS            "%"
    MAX-ACCESS      read-only
    STATUS          current
    DESCRIPTION     "Provides a percent transferred for the current replication process."
::= {eqlNASReplicationEntry 13 }

eqlNASReplicationAction           OBJECT-TYPE
    SYNTAX          INTEGER     {
                       none(0),
                      -- following actions will be used by ApplExec/netmgtd to send Action to Libspartan
                       replicate(1),
                       pause(2),
                       resume(3),
                       cancel(4),
                       demote(5),

                     -- Following actions will be used by ApplExec to send action to libspartan
                       promote(6),
                       force-promote(7),
                       delete(8),
                       force-delete(9),
		   -- following Actions are used only by netmgtd to send user action to ApplExec
		       outbound-delete (100),
		       outbound-force-delete (101),
		       inbound-delete (102),
		       inbound-promote (103),
		       inbound-promote-restore-cfg (104),
		       inbound-promote-keep-demote (105),
		       inbound-promote-keep-demote-restore-cfg (106),
		       inbound-delete-failback(107),
		       inbound-delete-failback-restore-cfg(108),
		       restore-cfg(109)
    }
    MAX-ACCESS      read-create
    STATUS          current
    DESCRIPTION     "Use this column to perform actions on this replication relationship."
::= { eqlNASReplicationEntry 14 }

---************************************************************

eqlNASReplPartnerInfoMapTable OBJECT-TYPE
    SYNTAX        SEQUENCE OF EqlNASReplPartnerInfoMapEntry
    MAX-ACCESS    not-accessible
    STATUS        current
    DESCRIPTION
     "EqualLogic-Dynamic
      This table is used to get the NAS cluster name for the replsite provided."
::= { eqlNASObjects 12 }

eqlNASReplPartnerInfoMapEntry OBJECT-TYPE
    SYNTAX        EqlNASReplPartnerInfoMapEntry
    MAX-ACCESS    not-accessible
    STATUS        current
    DESCRIPTION
      ""
    INDEX           { eqlApplianceIndex, eqliscsiVolumeReplSiteIndex }
::= { eqlNASReplPartnerInfoMapTable 1 }

EqlNASReplPartnerInfoMapEntry ::= SEQUENCE {
   eqlNASReplPartnerInfoMapRowStatus         RowStatus,
   eqlNASReplPartnerInfoMapClusterName       OCTET STRING,
   eqlNASReplPartnerInfoMapClusterSanVIPType InetAddressType,
   eqlNASReplPartnerInfoMapClusterSanVIP     InetAddress,
   eqlNASReplPartnerInfoMapClusterId         ClusterIdType,
   eqlNASReplPartnerInfoMapClusterMPV        Unsigned32,
   eqlNASReplPartnerInfoMapNetworkAddrType   InetAddressType,
   eqlNASReplPartnerInfoMapNetworkAddr       InetAddress,
   eqlNASReplPartnerInfoMapNetworkMask       InetAddress
}

eqlNASReplPartnerInfoMapRowStatus OBJECT-TYPE
   SYNTAX RowStatus
   MAX-ACCESS    read-create
   STATUS        current
   DESCRIPTION
      "The status of the row"
::= { eqlNASReplPartnerInfoMapEntry 1 }

eqlNASReplPartnerInfoMapClusterName OBJECT-TYPE
    SYNTAX          OCTET STRING (SIZE (1..64))
    MAX-ACCESS      read-create
    STATUS          current
    DESCRIPTION     "This field specifies the partners cluster name, which is the remotes eqlApplianceName."
::= { eqlNASReplPartnerInfoMapEntry 2 }

eqlNASReplPartnerInfoMapClusterSanVIPType OBJECT-TYPE
    SYNTAX          InetAddressType
    MAX-ACCESS      read-create
    STATUS          current
    DESCRIPTION     "Type of eqlNASReplPartnerInfoMapClusterSanVIP field."
    ::= { eqlNASReplPartnerInfoMapEntry 3 }

eqlNASReplPartnerInfoMapClusterSanVIP OBJECT-TYPE
    SYNTAX          InetAddress
    MAX-ACCESS      read-create
    STATUS          current
    DESCRIPTION     "Value of this column holds the SAN VIP of the remote cluster"
    ::= { eqlNASReplPartnerInfoMapEntry 4 }

eqlNASReplPartnerInfoMapClusterId OBJECT-TYPE
    SYNTAX          ClusterIdType
    MAX-ACCESS      read-only
    STATUS          current
    DESCRIPTION     "String containing local cluster Id. It should be unique within the network.
                     It is generated by IDC code."
    ::= { eqlNASReplPartnerInfoMapEntry 5 }


eqlNASReplPartnerInfoMapClusterMPV OBJECT-TYPE
    SYNTAX          Unsigned32
    MAX-ACCESS      read-only
    STATUS          current
    DESCRIPTION     "The Management Protocol Version (MPV) of the cluster (usually remote)."
    ::= { eqlNASReplPartnerInfoMapEntry 6 }

eqlNASReplPartnerInfoMapNetworkAddrType OBJECT-TYPE
    SYNTAX          InetAddressType
    MAX-ACCESS      read-create
    STATUS          current
    DESCRIPTION     "Type (IPv4 or IPv6) of the network where the partner is reachable."
    ::= { eqlNASReplPartnerInfoMapEntry 7 }

eqlNASReplPartnerInfoMapNetworkAddr OBJECT-TYPE
    SYNTAX          InetAddress
    MAX-ACCESS      read-create
    STATUS          current
    DESCRIPTION     "The address/ID of the network where the partner is reachable."
    ::= { eqlNASReplPartnerInfoMapEntry 8 }

eqlNASReplPartnerInfoMapNetworkMask OBJECT-TYPE
    SYNTAX          InetAddress
    MAX-ACCESS      read-create
    STATUS          current
    DESCRIPTION     "The netmask of the network where the partner is reachable."
    ::= { eqlNASReplPartnerInfoMapEntry 9 }

---************************************************************

eqlNASReplPartnerIdMapTable OBJECT-TYPE
    SYNTAX        SEQUENCE OF EqlNASReplPartnerIdMapEntry
    MAX-ACCESS    not-accessible
    STATUS        current
    DESCRIPTION
     "EqualLogic-Dynamic
      This table is used to get the NAS partnership Id for the given remote NAS cluster name."
::= { eqlNASObjects 13 }

eqlNASReplPartnerIdMapEntry OBJECT-TYPE
    SYNTAX        EqlNASReplPartnerIdMapEntry
    MAX-ACCESS    not-accessible
    STATUS        current
    DESCRIPTION
      ""
    INDEX           { eqlApplianceIndex, eqlNASReplPartnerInfoMapClusterName }
::= { eqlNASReplPartnerIdMapTable 1 }

EqlNASReplPartnerIdMapEntry ::= SEQUENCE {
   eqlNASReplPartnerIdMapRowStatus        RowStatus,
   eqlNASReplPartnerIdMapPartnershipId    Unsigned32
}

eqlNASReplPartnerIdMapRowStatus OBJECT-TYPE
   SYNTAX RowStatus
   MAX-ACCESS    read-create
   STATUS        current
   DESCRIPTION
      "The status of the row"
::= { eqlNASReplPartnerIdMapEntry 1 }

eqlNASReplPartnerIdMapPartnershipId OBJECT-TYPE
   SYNTAX        Unsigned32
   MAX-ACCESS    read-only
   STATUS        current
   DESCRIPTION
      "This is the partnership Id used by Exastore for the given eqlNASReplPartnerInfoMapClusterName."
::= { eqlNASReplPartnerIdMapEntry 2 }

---************************************************************

eqlNASContainerCfgTable OBJECT-TYPE
    SYNTAX        SEQUENCE OF EqlNASContainerCfgEntry
    MAX-ACCESS    not-accessible
    STATUS        current
    DESCRIPTION
     "EqualLogic-Dynamic
      This table is used to restore NAS file system configuration on given filesystem (a.k.a. container)."
::= { eqlNASObjects 14 }

eqlNASContainerCfgEntry OBJECT-TYPE
    SYNTAX        EqlNASContainerCfgEntry
    MAX-ACCESS    not-accessible
    STATUS        current
    DESCRIPTION
      "The index is composed of:
       * eqlApplianceIndex    - appliance index of the cluster hosting the target FS,
       * eqlNASContainerIndex - container index of the target FS,
       * eqlNASContainerCfgIndex - unique identifer for the configuration applicable
                                   to the filesystem."
    INDEX           { eqlApplianceIndex, eqlNASContainerIndex, eqlNASContainerCfgIndex}
::= { eqlNASContainerCfgTable 1 }

EqlNASContainerCfgEntry ::= SEQUENCE {
   eqlNASContainerCfgIndex             Unsigned32,
   eqlNASContainerCfgRowStatus         RowStatus,
   eqlNASContainerCfgSourceClusterName OCTET STRING,
   eqlNASContainerCfgSourceFSName      OCTET STRING,
   eqlNASContainerCfgModules           BITS,
   eqlNASContainerCfgRequestId         Counter64
}

eqlNASContainerCfgIndex         OBJECT-TYPE
    SYNTAX          Unsigned32
    MAX-ACCESS      not-accessible
    STATUS          current
    DESCRIPTION     "Unique identifier of the configuration items set."
::= { eqlNASContainerCfgEntry 1 }

eqlNASContainerCfgRowStatus OBJECT-TYPE
   SYNTAX RowStatus
   MAX-ACCESS    read-create
   STATUS        current
   DESCRIPTION
      "The status of the row"
::= { eqlNASContainerCfgEntry 2 }

eqlNASContainerCfgSourceClusterName OBJECT-TYPE
    SYNTAX          OCTET STRING (SIZE (1..64))
    MAX-ACCESS      read-write
    STATUS          current
    DESCRIPTION     "This field specifies the source cluster name, which is the
                     eqlApplianceName of the cluster hosting the source FS."
::= { eqlNASContainerCfgEntry 3 }

eqlNASContainerCfgSourceFSName     OBJECT-TYPE
    SYNTAX          OCTET STRING (SIZE (1..230))
    MAX-ACCESS  read-write
    STATUS          current
    DESCRIPTION     "Name used to identify the source NAS Container. Contains only
                     letters, digits and underscores. Must begin with either letter
                     or an underscore. "
   ::= { eqlNASContainerCfgEntry 4 }

eqlNASContainerCfgModules OBJECT-TYPE
   SYNTAX BITS {
      nfsExport(0),
      cifsShare(1),
      quotaRule(2),
      snapshotScheduler(3),
      volumeParameters(4),
      -- The following configuration modules are currently not supported.
      volumeName(5),
      volumeSize(6)
   }
   MAX-ACCESS  read-write
   STATUS      current
   DESCRIPTION
       "Bitmap of filesystem configuration modules to be restored. Identifies which filesystem configuration modules to apply to the filesystem."
   ::= { eqlNASContainerCfgEntry 5 }

eqlNASContainerCfgRequestId OBJECT-TYPE
    SYNTAX          Counter64
    MAX-ACCESS      read-only
    STATUS          current
    DESCRIPTION     "The NAS Container configuration request id."
    ::= { eqlNASContainerCfgEntry 6 }

--------------------------------------------------------------------------------------------

eqlNASFSScanTable OBJECT-TYPE
    SYNTAX        SEQUENCE OF EqlNASFSScanEntry
    MAX-ACCESS    not-accessible
    STATUS        current
    DESCRIPTION
     "EqualLogic-Dynamic
      This table is used to control the FS-Scan throttling on Spartan appliances."
::= { eqlNASObjects 15 }

eqlNASFSScanEntry OBJECT-TYPE
    SYNTAX        EqlNASFSScanEntry
    MAX-ACCESS    not-accessible
    STATUS        current
    DESCRIPTION
      "The index is composed of:
       eqlApplianceIndex    - appliance index of the cluster hosting the target FS "
    INDEX           { eqlApplianceIndex }
::= { eqlNASFSScanTable 1 }

EqlNASFSScanEntry ::= SEQUENCE {
        eqlNASFSScanRate          INTEGER
}

eqlNASFSScanRate OBJECT-TYPE
    SYNTAX          INTEGER {
                    normal(0),
                    maintenance(1),
                    off(2)
    }
    MAX-ACCESS      read-write
    STATUS          current
    DESCRIPTION     "This field specifies the rate of FS Scan throttling to apply to a Spartan node."
    DEFVAL          {normal}
    ::=  { eqlNASFSScanEntry 1 }

-----------------------------------------------------------------------------------------------
eqlNASReplicationHistoryTable OBJECT-TYPE
    SYNTAX        SEQUENCE OF EqlNASReplicationHistoryEntry
    MAX-ACCESS    not-accessible
    STATUS        current
    DESCRIPTION
     "EqualLogic-Dynamic
      TImeoutAll:60"
::= { eqlNASObjects 16 }

eqlNASReplicationHistoryEntry OBJECT-TYPE
    SYNTAX        EqlNASReplicationHistoryEntry
    MAX-ACCESS    not-accessible
    STATUS        current
    DESCRIPTION
      "NAS Replication Historical data."
    INDEX           { eqlApplianceIndex, eqlNASContainerIndex, eqlNASReplSitePartnershipId, eqlNASReplicationId, eqlNASReplicationHistorySampleIndex }
::= { eqlNASReplicationHistoryTable 1 }

EqlNASReplicationHistoryEntry ::= SEQUENCE {
   eqlNASReplicationHistorySampleIndex      Unsigned32,
   eqlNASReplicationHistoryStartTime        Integer32,
   eqlNASReplicationHistoryEndTime          Integer32,
   eqlNASReplicationHistoryTransferredMb    Unsigned32,
   eqlNASReplicationHistoryStatus           EqlNASReplicationStatus,
   eqlNASReplicationHistorySrcContainer     OCTET STRING,
   eqlNASReplicationHistoryDestContainer    OCTET STRING
}

eqlNASReplicationHistorySampleIndex OBJECT-TYPE
   SYNTAX        Unsigned32
   MAX-ACCESS    read-only
   STATUS        current
   DESCRIPTION "Index into list of replication history data"
::= { eqlNASReplicationHistoryEntry 1 }

eqlNASReplicationHistoryStartTime OBJECT-TYPE
   SYNTAX        Integer32
   MAX-ACCESS    read-only
   STATUS        current
   DESCRIPTION "32 bit binary start time for transfer in seconds from start of Unix epoch"
::= { eqlNASReplicationHistoryEntry 2 }

eqlNASReplicationHistoryEndTime OBJECT-TYPE
   SYNTAX        Integer32
   MAX-ACCESS    read-only
   STATUS        current
   DESCRIPTION "32 bit binary end time for transfer in seconds from start of Unix epoch"
::= { eqlNASReplicationHistoryEntry 3 }

eqlNASReplicationHistoryTransferredMb OBJECT-TYPE
   SYNTAX        Unsigned32
   MAX-ACCESS    read-only
   STATUS        current
   DESCRIPTION "Megabytes transferred"
::= { eqlNASReplicationHistoryEntry 4 }

eqlNASReplicationHistoryStatus OBJECT-TYPE
   SYNTAX        EqlNASReplicationStatus
   MAX-ACCESS    read-only
   STATUS        current
   DESCRIPTION "transfer status"
::= { eqlNASReplicationHistoryEntry 5 }


eqlNASReplicationHistorySrcContainer OBJECT-TYPE
    SYNTAX        OCTET STRING  (SIZE (1..230))
    MAX-ACCESS    read-only
    STATUS        current
    DESCRIPTION "Name of replication source container (alias 'file system')"
    ::= { eqlNASReplicationHistoryEntry 6 }

eqlNASReplicationHistoryDestContainer OBJECT-TYPE
    SYNTAX        OCTET STRING  (SIZE (1..230))
    MAX-ACCESS    read-only
    STATUS        current
    DESCRIPTION "Name of replication destination container (alias 'file system')"
    ::= { eqlNASReplicationHistoryEntry 7 }

-----------------------------------------------------------------------------------------------

eqlNASApplianceAntivirusHostTable OBJECT-TYPE
    SYNTAX          SEQUENCE OF EqlNASApplianceAntivirusHostEntry
    MAX-ACCESS      not-accessible
    STATUS          current
    DESCRIPTION     "EqualLogic-Dynamic table used to store information of the antivirus hosts for a
NAS appliance.
                     TimeoutAll:60"
    ::=    { eqlNASObjects 17 }

eqlNASApplianceAntivirusHostEntry OBJECT-TYPE
    SYNTAX          EqlNASApplianceAntivirusHostEntry
    MAX-ACCESS      not-accessible
    STATUS          current
    DESCRIPTION     "An entry contains the antivirus host information for a NAS appliance."
    INDEX          { eqlApplianceIndex, eqlNASApplianceAntivirusHostIndex }
    ::=   { eqlNASApplianceAntivirusHostTable 1}

EqlNASApplianceAntivirusHostEntry ::=
    SEQUENCE {
        eqlNASApplianceAntivirusHostIndex               Unsigned32,
        eqlNASApplianceAntivirusHostRowStatus           RowStatus,
        eqlNASApplianceAntivirusHostName                OCTET STRING,
        eqlNASApplianceAntivirusHostPortNumber          Unsigned32,
        eqlNASApplianceAntivirusHostTransactionState    INTEGER
    }

eqlNASApplianceAntivirusHostIndex  OBJECT-TYPE
    SYNTAX          Unsigned32
    MAX-ACCESS      not-accessible
    STATUS          current
    DESCRIPTION     "This field specifies an index that uniquely identifies the antivirus host
entry."
    ::=  {  eqlNASApplianceAntivirusHostEntry 1 }

eqlNASApplianceAntivirusHostRowStatus OBJECT-TYPE
    SYNTAX          RowStatus
    MAX-ACCESS      read-create
    STATUS          current
    DESCRIPTION     "This field is used to manage the conceptual row entry."
    ::= { eqlNASApplianceAntivirusHostEntry  2 }

eqlNASApplianceAntivirusHostName OBJECT-TYPE
    SYNTAX          OCTET STRING(SIZE(1..256))
    MAX-ACCESS      read-create
    STATUS          current
    DESCRIPTION     "Hostname/ip address of the antivirus host. "
    ::= { eqlNASApplianceAntivirusHostEntry  3 }

eqlNASApplianceAntivirusHostPortNumber OBJECT-TYPE
    SYNTAX          Unsigned32(1..65535)
    MAX-ACCESS      read-create
    STATUS          current
    DESCRIPTION     "Port number to be used for the antivirus service on the antivirus host. "
    DEFVAL        { 1344 }
    ::= { eqlNASApplianceAntivirusHostEntry  4 }

eqlNASApplianceAntivirusHostTransactionState OBJECT-TYPE
    SYNTAX          INTEGER     {
                    configStart(0),
                    configInProgress (1),
                    configCommit  (2),
		    configStartCommit (3)
    }
    MAX-ACCESS      read-create
    STATUS          current
    DESCRIPTION     "This field denotes the transaction state of the operations on the eqlNASApplianceAntivirusHostTable."
    DEFVAL          {configStart}
    ::=  {  eqlNASApplianceAntivirusHostEntry 5 }

-----------------------------------------------------------------------------------------------

eqlNASChassisTable OBJECT-TYPE
    SYNTAX          SEQUENCE OF EqlNASChassisEntry
    MAX-ACCESS      not-accessible
    STATUS          current
    DESCRIPTION     "EqualLogic-Dynamic NAS chassis table.
                     TimeoutAll:60"
    ::=    { eqlNASObjects 18 }

eqlNASChassisEntry OBJECT-TYPE
    SYNTAX          EqlNASChassisEntry
    MAX-ACCESS      not-accessible
    STATUS          current
    DESCRIPTION     "An entry (row) containing the NAS chassis information."
    INDEX          { eqlApplianceIndex, eqlNASChassisIndex }
    ::=   { eqlNASChassisTable 1 }

EqlNASChassisEntry ::=
    SEQUENCE {
        eqlNASChassisIndex               Unsigned32,
        eqlNASChassisRowStatus           RowStatus,
        eqlNASChassisName                OCTET STRING,
        eqlNASChassisRequestId           Counter64,
        eqlNASChassisFileSystemMember    TruthValue,
        eqlNASChassisModelName           OCTET STRING
    }

eqlNASChassisIndex  OBJECT-TYPE
    SYNTAX          Unsigned32
    MAX-ACCESS      not-accessible
    STATUS          current
    DESCRIPTION     "The NAS Chassis index."
    ::=  {  eqlNASChassisEntry 1 }

eqlNASChassisRowStatus OBJECT-TYPE
    SYNTAX          RowStatus
    MAX-ACCESS      read-create
    STATUS          current
    DESCRIPTION     "This field is used to manage the conceptual row entry."
    ::= { eqlNASChassisEntry  2 }

eqlNASChassisName OBJECT-TYPE
    SYNTAX          OCTET STRING(SIZE(1..256))
    MAX-ACCESS      read-create
    STATUS          current
    DESCRIPTION     "The NAS chassis name."
    ::= { eqlNASChassisEntry  3 }

eqlNASChassisRequestId OBJECT-TYPE
    SYNTAX          Counter64
    MAX-ACCESS      read-only
    STATUS          current
    DESCRIPTION     "The NAS Chassis create operation request id."
    ::= { eqlNASChassisEntry 4 }

eqlNASChassisFileSystemMember OBJECT-TYPE
    SYNTAX          TruthValue
    MAX-ACCESS      read-only
    STATUS          current
    DESCRIPTION     "The NAS Chassis filesystem participation state."
    ::= { eqlNASChassisEntry 5 }

eqlNASChassisModelName OBJECT-TYPE
    SYNTAX          OCTET STRING(SIZE(1..32))
    MAX-ACCESS      read-create
    STATUS          current
    DESCRIPTION     "The NAS chassis model name."
    ::= { eqlNASChassisEntry  6 }

-----------------------------------------------------------------------------------------------

eqlNASChassisStatusTable OBJECT-TYPE
    SYNTAX          SEQUENCE OF EqlNASChassisStatusEntry
    MAX-ACCESS      not-accessible
    STATUS          current
    DESCRIPTION     "EqualLogic-Dynamic NAS chassis status table.
                     TimeoutAll:60"
    ::=    { eqlNASObjects 19 }

eqlNASChassisStatusEntry OBJECT-TYPE
    SYNTAX          EqlNASChassisStatusEntry
    MAX-ACCESS      not-accessible
    STATUS          current
    DESCRIPTION     "An entry (row) containing the NAS chassis status."
    INDEX           { eqlApplianceIndex, eqlNASChassisIndex }

    ::=   { eqlNASChassisStatusTable 1}

EqlNASChassisComponentStatus ::= INTEGER {
                       optimal(0),
                       not-optimal(1),
                       critical(2),
                       not-available(3)
    }

EqlNASChassisACPowerStatus ::= INTEGER {
                       redundant(0),
                       partial(1),
                       not-available(2)
    }

EqlNASChassisControllerState ::= INTEGER {
                       standby(0),
                       unformatted(1),
                       formatted(2),
                       detached(3),
                       down(4),
                       not-available(5)
    }

EqlNASChassisSanType ::= INTEGER {
                       iscsi(0),
                       eql(1),
                       fc(2),
                       not-available(3)
    }

EqlNASChassisNetworkSpeed ::= INTEGER {
                       one-gb-ethernet(0),
                       ten-gb-ethernet(1),
                       twenty-gb-ethernet(2),
                       one-gb-fibre-channel(3),
                       two-gb-fibre-channel(4),
                       four-gb-fibre-channel(5),
                       eight-gb-fibre-channel(6),
                       not-available(7)
    }

EqlNASChassisControllerLocation ::= INTEGER {
                       one(0),
                       two(1),
                       irrelevant(2),
                       not-available(3)
    }

EqlNASChassisStatusEntry ::=
    SEQUENCE {
        eqlNASChassisOverallStatus              EqlNASChassisComponentStatus,
        eqlNASChassisChassisTag                 OCTET STRING,
        eqlNASChassisModel                      OCTET STRING,
        eqlNASChassisSanType                    EqlNASChassisSanType,
        eqlNASChassisOverallControllerStatus    EqlNASChassisComponentStatus,
        eqlNASChassisClientNetworkSpeed         EqlNASChassisNetworkSpeed,
        eqlNASChassisBackplaneNetworkSpeed      EqlNASChassisNetworkSpeed,
        eqlNASChassisInternalNetworkSpeed       EqlNASChassisNetworkSpeed,
        eqlNASChassisSanNetworkSpeed            EqlNASChassisNetworkSpeed,
        eqlNASChassisClientNetworkStatus        EqlNASChassisComponentStatus,
        eqlNASChassisBackplaneNetworkStatus     EqlNASChassisComponentStatus,
        eqlNASChassisInternalNetworkStatus      EqlNASChassisComponentStatus,
        eqlNASChassisSanNetworkStatus           EqlNASChassisComponentStatus,
        eqlNASChassisOverallFanStatus           EqlNASChassisComponentStatus,
        eqlNASChassisOverallPowerSupplyStatus   EqlNASChassisACPowerStatus
    }

eqlNASChassisOverallStatus OBJECT-TYPE
    SYNTAX          EqlNASChassisComponentStatus
    MAX-ACCESS      read-only
    STATUS          current
    DESCRIPTION     "The overall NAS chassis status."
    ::=   { eqlNASChassisStatusEntry 1 }

eqlNASChassisChassisTag OBJECT-TYPE
    SYNTAX          OCTET STRING(SIZE(1..32))
    MAX-ACCESS      read-only
    STATUS          current
    DESCRIPTION     "The NAS chassis tag."
    ::= { eqlNASChassisStatusEntry  2 }

eqlNASChassisModel OBJECT-TYPE
    SYNTAX          OCTET STRING(SIZE(1..64))
    MAX-ACCESS      read-only
    STATUS          current
    DESCRIPTION     "The NAS chassis model."
    ::= { eqlNASChassisStatusEntry  3 }

eqlNASChassisSanType OBJECT-TYPE
    SYNTAX          EqlNASChassisSanType
    MAX-ACCESS      read-only
    STATUS          current
    DESCRIPTION     "The NAS chassis san type."
    ::= { eqlNASChassisStatusEntry  4 }

eqlNASChassisOverallControllerStatus OBJECT-TYPE
    SYNTAX          EqlNASChassisComponentStatus
    MAX-ACCESS      read-only
    STATUS          current
    DESCRIPTION     "The NAS chassis overall controller status."
    ::= { eqlNASChassisStatusEntry  5 }

eqlNASChassisClientNetworkSpeed OBJECT-TYPE
    SYNTAX          EqlNASChassisNetworkSpeed
    MAX-ACCESS      read-only
    STATUS          current
    DESCRIPTION     "The lowest network speed among the NAS chassis client network interfaces."
    ::= { eqlNASChassisStatusEntry  6 }

eqlNASChassisBackplaneNetworkSpeed OBJECT-TYPE
    SYNTAX          EqlNASChassisNetworkSpeed
    MAX-ACCESS      read-only
    STATUS          current
    DESCRIPTION     "The lowest network speed among the NAS chassis backplane network interfaces."
    ::= { eqlNASChassisStatusEntry  7 }

eqlNASChassisInternalNetworkSpeed OBJECT-TYPE
    SYNTAX          EqlNASChassisNetworkSpeed
    MAX-ACCESS      read-only
    STATUS          current
    DESCRIPTION     "The lowest network speed among the NAS chassis internal network interfaces."
    ::= { eqlNASChassisStatusEntry  8 }

eqlNASChassisSanNetworkSpeed OBJECT-TYPE
    SYNTAX          EqlNASChassisNetworkSpeed
    MAX-ACCESS      read-only
    STATUS          current
    DESCRIPTION     "The lowest network speed among the NAS chassis san network interfaces."
    ::= { eqlNASChassisStatusEntry  9 }

eqlNASChassisClientNetworkStatus OBJECT-TYPE
    SYNTAX          EqlNASChassisComponentStatus
    MAX-ACCESS      read-only
    STATUS          current
    DESCRIPTION     "The NAS chassis client network status."
    ::= { eqlNASChassisStatusEntry  10 }

eqlNASChassisBackplaneNetworkStatus OBJECT-TYPE
    SYNTAX          EqlNASChassisComponentStatus
    MAX-ACCESS      read-only
    STATUS          current
    DESCRIPTION     "The NAS chassis backplane network status."
    ::= { eqlNASChassisStatusEntry  11 }

eqlNASChassisInternalNetworkStatus OBJECT-TYPE
    SYNTAX          EqlNASChassisComponentStatus
    MAX-ACCESS      read-only
    STATUS          current
    DESCRIPTION     "The NAS chassis internal network status."
    ::= { eqlNASChassisStatusEntry  12 }

eqlNASChassisSanNetworkStatus OBJECT-TYPE
    SYNTAX          EqlNASChassisComponentStatus
    MAX-ACCESS      read-only
    STATUS          current
    DESCRIPTION     "The NAS chassis san network status."
    ::= { eqlNASChassisStatusEntry  13 }

eqlNASChassisOverallFanStatus OBJECT-TYPE
    SYNTAX          EqlNASChassisComponentStatus
    MAX-ACCESS      read-only
    STATUS          current
    DESCRIPTION     "The NAS chassis overall fan status."
    ::= { eqlNASChassisStatusEntry  14 }

eqlNASChassisOverallPowerSupplyStatus OBJECT-TYPE
    SYNTAX          EqlNASChassisACPowerStatus
    MAX-ACCESS      read-only
    STATUS          current
    DESCRIPTION     "The NAS chassis overall power supply status."
    ::= { eqlNASChassisStatusEntry  15 }

-----------------------------------------------------------------------------------------------

eqlNASChassisFanStatusTable OBJECT-TYPE
    SYNTAX          SEQUENCE OF EqlNASChassisFanStatusEntry
    MAX-ACCESS      not-accessible
    STATUS          current
    DESCRIPTION     "EqualLogic-Dynamic NAS chassis fan status table.
                     TimeoutAll:60"
    --::=    { eqlNASObjects 20 }
    ::=   { eqlNASChassisStatusTable 2 }

eqlNASChassisFanStatusEntry OBJECT-TYPE
    SYNTAX          EqlNASChassisFanStatusEntry
    MAX-ACCESS      not-accessible
    STATUS          current
    DESCRIPTION     "An entry (row) containing the NAS chassis fan status."
    INDEX           { eqlApplianceIndex, eqlNASChassisIndex, eqlNASChassisFanName }
    ::=   { eqlNASChassisFanStatusTable 1}

EqlNASChassisFanStatusEntry ::=
    SEQUENCE {
        eqlNASChassisFanName          OCTET STRING,
        eqlNASChassisFanStatus        EqlNASChassisComponentStatus,
        eqlNASChassisFanRpm           Unsigned32,
        eqlNASChassisFanRpmRange      OCTET STRING
    }

eqlNASChassisFanName OBJECT-TYPE
    SYNTAX          OCTET STRING(SIZE(1..64))
    MAX-ACCESS      read-only
    STATUS          current
    DESCRIPTION     "The NAS chassis fan name."
    ::= { eqlNASChassisFanStatusEntry  1 }

eqlNASChassisFanStatus OBJECT-TYPE
    SYNTAX          EqlNASChassisComponentStatus
    MAX-ACCESS      read-only
    STATUS          current
    DESCRIPTION     "The NAS chassis fan status."
    ::= { eqlNASChassisFanStatusEntry  2 }

eqlNASChassisFanRpm  OBJECT-TYPE
    SYNTAX          Unsigned32
    MAX-ACCESS      read-only
    STATUS          current
    DESCRIPTION     "The NAS Chassis fan RPM."
    ::=  {  eqlNASChassisFanStatusEntry 3 }

eqlNASChassisFanRpmRange  OBJECT-TYPE
    SYNTAX          OCTET STRING(SIZE(1..50))
    MAX-ACCESS      read-only
    STATUS          current
    DESCRIPTION     "The NAS Chassis fan RPM range."
    ::=  {  eqlNASChassisFanStatusEntry 4 }

-----------------------------------------------------------------------------------------------

eqlNASChassisPowerSupplyStatusTable OBJECT-TYPE
    SYNTAX          SEQUENCE OF EqlNASChassisPowerSupplyStatusEntry
    MAX-ACCESS      not-accessible
    STATUS          current
    DESCRIPTION     "EqualLogic-Dynamic NAS chassis power supply status table.
                     TimeoutAll:60"
    -- ::=    { eqlNASObjects 21 }
    ::=   { eqlNASChassisStatusTable 3 }

eqlNASChassisPowerSupplyStatusEntry OBJECT-TYPE
    SYNTAX          EqlNASChassisPowerSupplyStatusEntry
    MAX-ACCESS      not-accessible
    STATUS          current
    DESCRIPTION     "An entry (row) containing the NAS chassis power supply status."
    INDEX           { eqlApplianceIndex, eqlNASChassisIndex, eqlNASChassisPowerSupplyName }
    ::=   { eqlNASChassisPowerSupplyStatusTable 1}

EqlNASChassisPowerSupplyStatusEntry ::=
    SEQUENCE {
        eqlNASChassisPowerSupplyName        OCTET STRING,
        eqlNASChassisPowerSupplyStatus      EqlNASChassisComponentStatus
    }

eqlNASChassisPowerSupplyName OBJECT-TYPE
    SYNTAX          OCTET STRING(SIZE(1..64))
    MAX-ACCESS      read-only
    STATUS          current
    DESCRIPTION     "The NAS chassis power supply name."
    ::= { eqlNASChassisPowerSupplyStatusEntry  1 }

eqlNASChassisPowerSupplyStatus OBJECT-TYPE
    SYNTAX          EqlNASChassisComponentStatus
    MAX-ACCESS      read-only
    STATUS          current
    DESCRIPTION     "The NAS chassis power supply status."
    ::= { eqlNASChassisPowerSupplyStatusEntry  2 }

-----------------------------------------------------------------------------------------------

eqlNASChassisControllerStatusTable OBJECT-TYPE
    SYNTAX          SEQUENCE OF EqlNASChassisControllerStatusEntry
    MAX-ACCESS      not-accessible
    STATUS          current
    DESCRIPTION     "EqualLogic-Dynamic NAS chassis controller status table.
                     TimeoutAll:60"
    ::=    { eqlNASObjects 20 }

eqlNASChassisControllerStatusEntry OBJECT-TYPE
    SYNTAX          EqlNASChassisControllerStatusEntry
    MAX-ACCESS      not-accessible
    STATUS          current
    DESCRIPTION     "An entry (row) containing the NAS chassis controller status."
    INDEX           { eqlApplianceIndex, eqlNASChassisControllerIndex }
    ::=   { eqlNASChassisControllerStatusTable 1}

EqlNASChassisControllerStatusEntry ::=
    SEQUENCE {
        eqlNASChassisControllerIndex                        Unsigned32,
        eqlNASChassisControllerStatus                       EqlNASChassisComponentStatus,
        eqlNASChassisControllerState                        EqlNASChassisControllerState,
        eqlNASChassisControllerLocation                     EqlNASChassisControllerLocation,
        eqlNASChassisControllerAmbientTemperatureStatus     EqlNASChassisComponentStatus,
        eqlNASChassisControllerAmbientTemperatureValue      Integer32,
        eqlNASChassisControllerSystemControllerId           OCTET STRING,
        eqlNASChassisControllerBPSStatus                    EqlNASChassisComponentStatus,
        eqlNASChassisControllerBPSIsAccessible              TruthValue,
        eqlNASChassisControllerBPSModel                     OCTET STRING,
        eqlNASChassisControllerBPSCharge                    Unsigned32,
        eqlNASChassisControllerCPUOverallStatus             EqlNASChassisComponentStatus,
        eqlNASChassisControllerCPUCurrentCoresCount         Unsigned32,
        eqlNASChassisControllerOverallFanStatus             EqlNASChassisComponentStatus,
        eqlNASChassisControllerOverallLocalDiskStatus       EqlNASChassisComponentStatus,
        eqlNASChassisControllerOverallRaidControllerStatus  EqlNASChassisComponentStatus,
        eqlNASChassisControllerOverallVirtualDiskStatus     EqlNASChassisComponentStatus,
        eqlNASChassisControllerMemoryStatus                 EqlNASChassisComponentStatus,
        eqlNASChassisControllerMemorySize                   Unsigned32,
        eqlNASChassisControllerBackplaneNetworkStatus       EqlNASChassisComponentStatus,
        eqlNASChassisControllerBackplaneNetworkSpeed        EqlNASChassisNetworkSpeed,
        eqlNASChassisControllerClientNetworkStatus          EqlNASChassisComponentStatus,
        eqlNASChassisControllerClientNetworkSpeed           EqlNASChassisNetworkSpeed,
        eqlNASChassisControllerInternalNetworkStatus        EqlNASChassisComponentStatus,
        eqlNASChassisControllerInternalNetworkSpeed         EqlNASChassisNetworkSpeed,
        eqlNASChassisControllerSanNetworkStatus             EqlNASChassisComponentStatus,
        eqlNASChassisControllerSanNetworkSpeed              EqlNASChassisNetworkSpeed,
        eqlNASChassisControllerOverallPowerSupplyStatus     EqlNASChassisACPowerStatus
    }

eqlNASChassisControllerIndex  OBJECT-TYPE
    SYNTAX          Unsigned32
    MAX-ACCESS      read-only
    STATUS          current
    DESCRIPTION     "The NAS Chassis controller index."
    ::=  {  eqlNASChassisControllerStatusEntry 1 }

eqlNASChassisControllerStatus  OBJECT-TYPE
    SYNTAX          EqlNASChassisComponentStatus
    MAX-ACCESS      read-only
    STATUS          current
    DESCRIPTION     "The NAS Chassis controller status."
    ::=  {  eqlNASChassisControllerStatusEntry 2 }

eqlNASChassisControllerState  OBJECT-TYPE
    SYNTAX          EqlNASChassisControllerState
    MAX-ACCESS      read-only
    STATUS          current
    DESCRIPTION     "The NAS Chassis controller state."
    ::=  {  eqlNASChassisControllerStatusEntry 3 }

eqlNASChassisControllerLocation  OBJECT-TYPE
    SYNTAX          EqlNASChassisControllerLocation
    MAX-ACCESS      read-only
    STATUS          current
    DESCRIPTION     "The NAS Chassis controller location."
    ::=  {  eqlNASChassisControllerStatusEntry 4 }

eqlNASChassisControllerAmbientTemperatureStatus  OBJECT-TYPE
    SYNTAX          EqlNASChassisComponentStatus
    MAX-ACCESS      read-only
    STATUS          current
    DESCRIPTION     "The NAS Chassis controller ambient temperaure status."
    ::=  {  eqlNASChassisControllerStatusEntry 5 }

eqlNASChassisControllerAmbientTemperatureValue  OBJECT-TYPE
    SYNTAX          Integer32
    MAX-ACCESS      read-only
    STATUS          current
    DESCRIPTION     "The NAS Chassis controller ambient temperaure value."
    ::=  {  eqlNASChassisControllerStatusEntry 6 }

eqlNASChassisControllerSystemControllerId  OBJECT-TYPE
    SYNTAX          OCTET STRING(SIZE(1..64))
    MAX-ACCESS      read-only
    STATUS          current
    DESCRIPTION     "The NAS Chassis controller system controller id."
    ::=  {  eqlNASChassisControllerStatusEntry 7 }

eqlNASChassisControllerBPSStatus  OBJECT-TYPE
    SYNTAX          EqlNASChassisComponentStatus
    MAX-ACCESS      read-only
    STATUS          current
    DESCRIPTION     "The NAS Chassis controller BPS status."
    ::=  {  eqlNASChassisControllerStatusEntry 8 }

eqlNASChassisControllerBPSIsAccessible  OBJECT-TYPE
    SYNTAX          TruthValue
    MAX-ACCESS      read-only
    STATUS          current
    DESCRIPTION     "The NAS Chassis controller BPS accessibility."
    ::=  {  eqlNASChassisControllerStatusEntry 9 }

eqlNASChassisControllerBPSModel  OBJECT-TYPE
    SYNTAX          OCTET STRING(SIZE(1..64))
    MAX-ACCESS      read-only
    STATUS          current
    DESCRIPTION     "The NAS Chassis controller BPS model."
    ::=  {  eqlNASChassisControllerStatusEntry 10 }

eqlNASChassisControllerBPSCharge  OBJECT-TYPE
    SYNTAX          Unsigned32
    UNITS            "%"
    MAX-ACCESS      read-only
    STATUS          current
    DESCRIPTION     "The NAS Chassis controller BPS charge percentage."
    ::=  {  eqlNASChassisControllerStatusEntry 11 }

eqlNASChassisControllerCPUOverallStatus  OBJECT-TYPE
    SYNTAX          EqlNASChassisComponentStatus
    MAX-ACCESS      read-only
    STATUS          current
    DESCRIPTION     "The NAS Chassis controller overall CPU status."
    ::=  {  eqlNASChassisControllerStatusEntry 12 }

eqlNASChassisControllerCPUCurrentCoresCount  OBJECT-TYPE
    SYNTAX          Unsigned32
    MAX-ACCESS      read-only
    STATUS          current
    DESCRIPTION     "The NAS Chassis controller current CPU cores count."
    ::=  {  eqlNASChassisControllerStatusEntry 13 }

eqlNASChassisControllerOverallFanStatus  OBJECT-TYPE
    SYNTAX          EqlNASChassisComponentStatus
    MAX-ACCESS      read-only
    STATUS          current
    DESCRIPTION     "The NAS Chassis controller overall fan status."
    ::=  {  eqlNASChassisControllerStatusEntry 14 }

eqlNASChassisControllerOverallLocalDiskStatus  OBJECT-TYPE
    SYNTAX          EqlNASChassisComponentStatus
    MAX-ACCESS      read-only
    STATUS          current
    DESCRIPTION     "The NAS Chassis controller overall local disk status."
    ::=  {  eqlNASChassisControllerStatusEntry 15 }

eqlNASChassisControllerOverallRaidControllerStatus  OBJECT-TYPE
    SYNTAX          EqlNASChassisComponentStatus
    MAX-ACCESS      read-only
    STATUS          current
    DESCRIPTION     "The NAS Chassis controller overall raid controller status."
    ::=  {  eqlNASChassisControllerStatusEntry 16 }

eqlNASChassisControllerOverallVirtualDiskStatus  OBJECT-TYPE
    SYNTAX          EqlNASChassisComponentStatus
    MAX-ACCESS      read-only
    STATUS          current
    DESCRIPTION     "The NAS Chassis controller overall virtual disk status."
    ::=  {  eqlNASChassisControllerStatusEntry 17 }

eqlNASChassisControllerMemoryStatus  OBJECT-TYPE
    SYNTAX          EqlNASChassisComponentStatus
    MAX-ACCESS      read-only
    STATUS          current
    DESCRIPTION     "The NAS Chassis controller memory status."
    ::=  {  eqlNASChassisControllerStatusEntry 18 }

eqlNASChassisControllerMemorySize  OBJECT-TYPE
    SYNTAX          Unsigned32
    MAX-ACCESS      read-only
    STATUS          current
    DESCRIPTION     "The NAS Chassis controller total memory size."
    ::=  {  eqlNASChassisControllerStatusEntry 19 }

eqlNASChassisControllerBackplaneNetworkStatus  OBJECT-TYPE
    SYNTAX          EqlNASChassisComponentStatus
    MAX-ACCESS      read-only
    STATUS          current
    DESCRIPTION     "The NAS Chassis controller backplane network status."
    ::=  {  eqlNASChassisControllerStatusEntry 20 }

eqlNASChassisControllerBackplaneNetworkSpeed  OBJECT-TYPE
    SYNTAX          EqlNASChassisNetworkSpeed
    MAX-ACCESS      read-only
    STATUS          current
    DESCRIPTION     "The lowest network speed among the NAS chassis backplane network interfaces."
    ::=  {  eqlNASChassisControllerStatusEntry 21 }

eqlNASChassisControllerClientNetworkStatus  OBJECT-TYPE
    SYNTAX          EqlNASChassisComponentStatus
    MAX-ACCESS      read-only
    STATUS          current
    DESCRIPTION     "The NAS Chassis controller client network status."
    ::=  {  eqlNASChassisControllerStatusEntry 22 }

eqlNASChassisControllerClientNetworkSpeed  OBJECT-TYPE
    SYNTAX          EqlNASChassisNetworkSpeed
    MAX-ACCESS      read-only
    STATUS          current
    DESCRIPTION     "The lowest network speed among the NAS chassis client network interfaces."
    ::=  {  eqlNASChassisControllerStatusEntry 23 }

eqlNASChassisControllerInternalNetworkStatus  OBJECT-TYPE
    SYNTAX          EqlNASChassisComponentStatus
    MAX-ACCESS      read-only
    STATUS          current
    DESCRIPTION     "The NAS Chassis controller internal network status."
    ::=  {  eqlNASChassisControllerStatusEntry 24 }

eqlNASChassisControllerInternalNetworkSpeed  OBJECT-TYPE
    SYNTAX          EqlNASChassisNetworkSpeed
    MAX-ACCESS      read-only
    STATUS          current
    DESCRIPTION     "The lowest network speed among the NAS chassis internal network interfaces."
    ::=  {  eqlNASChassisControllerStatusEntry 25 }

eqlNASChassisControllerSanNetworkStatus  OBJECT-TYPE
    SYNTAX          EqlNASChassisComponentStatus
    MAX-ACCESS      read-only
    STATUS          current
    DESCRIPTION     "The NAS Chassis controller san network status."
    ::=  {  eqlNASChassisControllerStatusEntry 26 }

eqlNASChassisControllerSanNetworkSpeed  OBJECT-TYPE
    SYNTAX          EqlNASChassisNetworkSpeed
    MAX-ACCESS      read-only
    STATUS          current
    DESCRIPTION     "The lowest network speed among the NAS chassis san network interfaces."
    ::=  {  eqlNASChassisControllerStatusEntry 27 }

eqlNASChassisControllerOverallPowerSupplyStatus  OBJECT-TYPE
    SYNTAX          EqlNASChassisACPowerStatus
    MAX-ACCESS      read-only
    STATUS          current
    DESCRIPTION     "The NAS Chassis controller overall power supply status."
    ::=  {  eqlNASChassisControllerStatusEntry 28 }

-----------------------------------------------------------------------------------------------

eqlNASChassisControllerFanStatusTable OBJECT-TYPE
    SYNTAX          SEQUENCE OF EqlNASChassisControllerFanStatusEntry
    MAX-ACCESS      not-accessible
    STATUS          current
    DESCRIPTION     "EqualLogic-Dynamic NAS chassis controller fan status table.
                     TimeoutAll:60"
    -- ::=    { eqlNASObjects 23 }
    ::=    { eqlNASChassisControllerStatusTable 2 }

eqlNASChassisControllerFanStatusEntry OBJECT-TYPE
    SYNTAX          EqlNASChassisControllerFanStatusEntry
    MAX-ACCESS      not-accessible
    STATUS          current
    DESCRIPTION     "An entry (row) containing the NAS chassis controller fan status."
    INDEX           { eqlApplianceIndex, eqlNASChassisControllerIndex, eqlNASChassisControllerFanName }
    ::=   { eqlNASChassisControllerFanStatusTable 1}

EqlNASChassisControllerFanStatusEntry ::=
    SEQUENCE {
        eqlNASChassisControllerFanName          OCTET STRING,
        eqlNASChassisControllerFanStatus        EqlNASChassisComponentStatus,
        eqlNASChassisControllerFanRpm           Unsigned32,
        eqlNASChassisControllerFanRpmRange      OCTET STRING
    }

eqlNASChassisControllerFanName OBJECT-TYPE
    SYNTAX          OCTET STRING(SIZE(1..64))
    MAX-ACCESS      read-only
    STATUS          current
    DESCRIPTION     "The NAS chassis controller fan name."
    ::= { eqlNASChassisControllerFanStatusEntry  1 }

eqlNASChassisControllerFanStatus OBJECT-TYPE
    SYNTAX          EqlNASChassisComponentStatus
    MAX-ACCESS      read-only
    STATUS          current
    DESCRIPTION     "The NAS chassis controller fan status."
    ::= { eqlNASChassisControllerFanStatusEntry  2 }

eqlNASChassisControllerFanRpm  OBJECT-TYPE
    SYNTAX          Unsigned32
    MAX-ACCESS      read-only
    STATUS          current
    DESCRIPTION     "The NAS chassis controller fan RPM."
    ::=  {  eqlNASChassisControllerFanStatusEntry 3 }

eqlNASChassisControllerFanRpmRange  OBJECT-TYPE
    SYNTAX          OCTET STRING(SIZE(1..50))
    MAX-ACCESS      read-only
    STATUS          current
    DESCRIPTION     "The NAS chassis controller fan RPM range."
    ::=  {  eqlNASChassisControllerFanStatusEntry 4 }

-----------------------------------------------------------------------------------------------

eqlNASChassisControllerPowerSupplyStatusTable OBJECT-TYPE
    SYNTAX          SEQUENCE OF EqlNASChassisControllerPowerSupplyStatusEntry
    MAX-ACCESS      not-accessible
    STATUS          current
    DESCRIPTION     "EqualLogic-Dynamic NAS chassis controller power supply status table.
                     TimeoutAll:60"
    -- ::=    { eqlNASObjects 24 }
    ::=    { eqlNASChassisControllerStatusTable 3 }

eqlNASChassisControllerPowerSupplyStatusEntry OBJECT-TYPE
    SYNTAX          EqlNASChassisControllerPowerSupplyStatusEntry
    MAX-ACCESS      not-accessible
    STATUS          current
    DESCRIPTION     "An entry (row) containing the NAS chassis controller power supply status."
    INDEX           { eqlApplianceIndex, eqlNASChassisControllerIndex, eqlNASChassisControllerPowerSupplyName }
    ::=   { eqlNASChassisControllerPowerSupplyStatusTable 1}

EqlNASChassisControllerPowerSupplyStatusEntry ::=
    SEQUENCE {
        eqlNASChassisControllerPowerSupplyName        OCTET STRING,
        eqlNASChassisControllerPowerSupplyStatus      EqlNASChassisComponentStatus
    }

eqlNASChassisControllerPowerSupplyName OBJECT-TYPE
    SYNTAX          OCTET STRING(SIZE(1..64))
    MAX-ACCESS      read-only
    STATUS          current
    DESCRIPTION     "The NAS chassis controller power supply name."
    ::= { eqlNASChassisControllerPowerSupplyStatusEntry  1 }

eqlNASChassisControllerPowerSupplyStatus OBJECT-TYPE
    SYNTAX          EqlNASChassisComponentStatus
    MAX-ACCESS      read-only
    STATUS          current
    DESCRIPTION     "The NAS chassis controller power supply status."
    ::= { eqlNASChassisControllerPowerSupplyStatusEntry  2 }

-----------------------------------------------------------------------------------------------

eqlNASChassisControllerDiskStatusTable OBJECT-TYPE
    SYNTAX          SEQUENCE OF EqlNASChassisControllerDiskStatusEntry
    MAX-ACCESS      not-accessible
    STATUS          current
    DESCRIPTION     "EqualLogic-Dynamic NAS chassis controller physical disk status table.
                     TimeoutAll:60"
    -- ::=    { eqlNASObjects 25 }
    ::=    { eqlNASChassisControllerStatusTable 4 }

eqlNASChassisControllerDiskStatusEntry OBJECT-TYPE
    SYNTAX          EqlNASChassisControllerDiskStatusEntry
    MAX-ACCESS      not-accessible
    STATUS          current
    DESCRIPTION     "An entry (row) containing the NAS chassis controller physical disk status."
    INDEX           { eqlApplianceIndex, eqlNASChassisControllerIndex, eqlNASChassisControllerDiskName }
    ::=   { eqlNASChassisControllerDiskStatusTable 1}

EqlNASChassisControllerDiskStatusEntry ::=
    SEQUENCE {
        eqlNASChassisControllerDiskName          OCTET STRING,
        eqlNASChassisControllerDiskStatus        EqlNASChassisComponentStatus
    }

eqlNASChassisControllerDiskName OBJECT-TYPE
    SYNTAX          OCTET STRING(SIZE(1..64))
    MAX-ACCESS      read-only
    STATUS          current
    DESCRIPTION     "The NAS chassis controller physical disk name."
    ::= { eqlNASChassisControllerDiskStatusEntry  1 }

eqlNASChassisControllerDiskStatus OBJECT-TYPE
    SYNTAX          EqlNASChassisComponentStatus
    MAX-ACCESS      read-only
    STATUS          current
    DESCRIPTION     "The NAS chassis controller physical disk status."
    ::= { eqlNASChassisControllerDiskStatusEntry  2 }

-----------------------------------------------------------------------------------------------

eqlNASChassisControllerNicStatusTable OBJECT-TYPE
    SYNTAX          SEQUENCE OF EqlNASChassisControllerNicStatusEntry
    MAX-ACCESS      not-accessible
    STATUS          current
    DESCRIPTION     "EqualLogic-Dynamic NAS chassis controller nic status table.
                     TimeoutAll:60"
    --::=    { eqlNASObjects 26 }
    ::=    { eqlNASChassisControllerStatusTable 5 }

eqlNASChassisControllerNicStatusEntry OBJECT-TYPE
    SYNTAX          EqlNASChassisControllerNicStatusEntry
    MAX-ACCESS      not-accessible
    STATUS          current
    DESCRIPTION     "An entry (row) containing the NAS chassis controller nic status."
    INDEX           { eqlApplianceIndex, eqlNASChassisControllerIndex, eqlApplianceNetworkType,
                      eqlNASChassisControllerNicName }
    ::=   { eqlNASChassisControllerNicStatusTable 1}

EqlNASChassisControllerNicStatusEntry ::=
    SEQUENCE {
        eqlNASChassisControllerNicName          OCTET STRING,
        eqlNASChassisControllerNicState         INTEGER,
        eqlNASChassisControllerNicSpeed         EqlNASChassisNetworkSpeed,
        eqlNASChassisControllerNicSlot          OCTET STRING,
        eqlNASChassisControllerNicPort          Unsigned32,
        eqlNASChassisControllerNicDuplex        INTEGER,
        eqlNASChassisControllerNicFlowControl   INTEGER
    }

eqlNASChassisControllerNicName OBJECT-TYPE
    SYNTAX          OCTET STRING(SIZE(1..64))
    MAX-ACCESS      read-only
    STATUS          current
    DESCRIPTION     "The NAS chassis controller nic name."
    ::= { eqlNASChassisControllerNicStatusEntry  1 }

eqlNASChassisControllerNicState OBJECT-TYPE
    SYNTAX          INTEGER {
                    on(0),
                    off(1),
                    not-available(2)
    }
    MAX-ACCESS      read-only
    STATUS          current
    DESCRIPTION     "The NAS chassis controller nic state."
    ::= { eqlNASChassisControllerNicStatusEntry 2 }

eqlNASChassisControllerNicSpeed OBJECT-TYPE
    SYNTAX          EqlNASChassisNetworkSpeed
    MAX-ACCESS      read-only
    STATUS          current
    DESCRIPTION     "The NAS chassis controller nic speed."
    ::= { eqlNASChassisControllerNicStatusEntry 3 }

eqlNASChassisControllerNicSlot OBJECT-TYPE
    SYNTAX          OCTET STRING(SIZE(1..30))
    MAX-ACCESS      read-only
    STATUS          current
    DESCRIPTION     "The NAS chassis controller nic slot."
    ::= { eqlNASChassisControllerNicStatusEntry 4 }

eqlNASChassisControllerNicPort OBJECT-TYPE
    SYNTAX          Unsigned32
    MAX-ACCESS      read-only
    STATUS          current
    DESCRIPTION     "The NAS chassis controller nic port."
    ::= { eqlNASChassisControllerNicStatusEntry 5 }

eqlNASChassisControllerNicDuplex OBJECT-TYPE
    SYNTAX          INTEGER {
                    full(0),
                    half(1),
                    unknown(2)
    }
    MAX-ACCESS      read-only
    STATUS          current
    DESCRIPTION     "The NAS chassis controller nic duplex mode."
    ::= { eqlNASChassisControllerNicStatusEntry 6 }

eqlNASChassisControllerNicFlowControl OBJECT-TYPE
    SYNTAX          INTEGER {
                    on(0),
                    off(1),
                    unknown(2)
    }
    MAX-ACCESS      read-only
    STATUS          current
    DESCRIPTION     "The NAS chassis controller nic flow control state."
    ::= { eqlNASChassisControllerNicStatusEntry 7 }

-----------------------------------------------------------------------------------------------

eqlNASDiagsTable OBJECT-TYPE
    SYNTAX          SEQUENCE OF EqlNASDiagsEntry
    MAX-ACCESS      not-accessible
    STATUS          current
    DESCRIPTION     "EqualLogic-Dynamic table controlling the NAS diags."
    ::=    { eqlNASObjects 21 }

eqlNASDiagsEntry OBJECT-TYPE
    SYNTAX          EqlNASDiagsEntry
    MAX-ACCESS      not-accessible
    STATUS          current
    DESCRIPTION     "An entry (row) containing the diags information."
    INDEX           { eqlApplianceIndex }

    ::=   { eqlNASDiagsTable 1}

EqlNASDiagsEntry ::=
    SEQUENCE {
        eqlNASDiagsStart        INTEGER,
        eqlNASDiagsCaseNumber   OCTET STRING,
        eqlNASDiagsStatus       INTEGER
    }

eqlNASDiagsStart OBJECT-TYPE
    SYNTAX          INTEGER {
                    general(1),
                    file(2),
                    network(3),
                    performance(4),
                    clientconnectivity(5),
                    fileaccessibility(6),
                    protocolslog(7),
                    logs(8)
    }
    MAX-ACCESS      read-write
    STATUS          current
    DESCRIPTION     "This field selects the diagnostic to start."
    ::=  {  eqlNASDiagsEntry 1 }

eqlNASDiagsCaseNumber OBJECT-TYPE
    SYNTAX          OCTET STRING (SIZE (1..10))
    MAX-ACCESS      read-write
    STATUS          current
    DESCRIPTION     "This field holds the OPTIONAL Dell Support case number for the
                     NAS diagnostics."
    ::=  {  eqlNASDiagsEntry 2 }

eqlNASDiagsStatus OBJECT-TYPE
    SYNTAX          INTEGER {
                    idle(1),
                    running(2)
    }
    MAX-ACCESS      read-only
    STATUS          current
    DESCRIPTION     "This field holds the status of the NAS diagnostics
                     operation."
    ::=  {  eqlNASDiagsEntry 3 }

---------------------------------------------------------------------------------------------------

eqlNASClientStaticRouteTable OBJECT-TYPE
    SYNTAX          SEQUENCE OF EqlNASClientStaticRouteEntry
    MAX-ACCESS      not-accessible
    STATUS          current
    DESCRIPTION     "EqualLogic-Dynamic table controlling the NAS client static routes. The static
                    route entries are used to route the CLIENT traffic from the cluster members to
                    gateways on the CLIENT network."
    ::=    { eqlNASObjects 22 }

eqlNASClientStaticRouteEntry OBJECT-TYPE
    SYNTAX          EqlNASClientStaticRouteEntry
    MAX-ACCESS      not-accessible
    STATUS          current
    DESCRIPTION     "An entry (row) containing the NAS static route information for a subnet of the client network."
    INDEX           { eqlApplianceIndex, eqlApplianceNetworkID,
                      eqlNASClientStaticRouteNetworkAddrType, eqlNASClientStaticRouteNetworkAddr,
                      eqlNASClientStaticRouteNetworkMaskType, eqlNASClientStaticRouteNetworkMask}

    ::=   { eqlNASClientStaticRouteTable 1 }

EqlNASClientStaticRouteEntry ::=
    SEQUENCE {
        eqlNASClientStaticRouteRowStatus                RowStatus,
        eqlNASClientStaticRouteNetworkAddrType          InetAddressType,
        eqlNASClientStaticRouteNetworkAddr              InetAddress,
        eqlNASClientStaticRouteNetworkMaskType          InetAddressType,
        eqlNASClientStaticRouteNetworkMask              InetAddress,
        eqlNASClientStaticRouteGatewayAddrType          InetAddressType,
        eqlNASClientStaticRouteGatewayAddr              InetAddress
    }

eqlNASClientStaticRouteRowStatus OBJECT-TYPE
    SYNTAX          RowStatus
    MAX-ACCESS      read-create
    STATUS          current
    DESCRIPTION     "SNMP Row Status"
    ::=  {  eqlNASClientStaticRouteEntry 1 }

eqlNASClientStaticRouteNetworkAddrType OBJECT-TYPE
    SYNTAX          InetAddressType
    MAX-ACCESS      read-create
    STATUS          current
    DESCRIPTION     "This field specifies the type (v4/v6) for the network address of the
                    static route."
    ::=  {  eqlNASClientStaticRouteEntry 2 }

eqlNASClientStaticRouteNetworkAddr OBJECT-TYPE
    SYNTAX          InetAddress
    MAX-ACCESS      read-create
    STATUS          current
    DESCRIPTION     "This field contains the network IP address for the static route
                    (e.g. 200.200.200.0)."
    ::=  {  eqlNASClientStaticRouteEntry 3 }

eqlNASClientStaticRouteNetworkMaskType OBJECT-TYPE
    SYNTAX          InetAddressType
    MAX-ACCESS      read-create
    STATUS          current
    DESCRIPTION     "This field specifies the type (v4/v6) for the network mask of the
                    static route.The IP address of the network mask is assumed to be the
                    same as that of the network address."
    ::=  {  eqlNASClientStaticRouteEntry 4 }

eqlNASClientStaticRouteNetworkMask OBJECT-TYPE
    SYNTAX          InetAddress
    MAX-ACCESS      read-create
    STATUS          current
    DESCRIPTION     "This field contains the network mask for the static route
                    (e.g. 255.255.255.0)."
    ::=  {  eqlNASClientStaticRouteEntry 5 }

eqlNASClientStaticRouteGatewayAddrType OBJECT-TYPE
    SYNTAX          InetAddressType
    MAX-ACCESS      read-create
    STATUS          current
    DESCRIPTION     "This field specifies the type (v4/v6) of the gateway IP address."
    ::=  {  eqlNASClientStaticRouteEntry 6 }

eqlNASClientStaticRouteGatewayAddr OBJECT-TYPE
    SYNTAX          InetAddress
    MAX-ACCESS      read-create
    STATUS          current
    DESCRIPTION     "This field contains the gateway IP address for the static route
                    (e.g. 10.127.20.30)."
    ::=  {  eqlNASClientStaticRouteEntry 7 }

-----------------------------------------------------------------------------------------------

eqlNASClusterUpdateTable OBJECT-TYPE
    SYNTAX          SEQUENCE OF EqlNASClusterUpdateEntry
    MAX-ACCESS      not-accessible
    STATUS          current
    DESCRIPTION     "EqualLogic-Dynamic table to update NAS Cluster Firmware.
                     TimeoutAll:60"
    ::=    { eqlNASObjects 23 }

eqlNASClusterUpdateEntry OBJECT-TYPE
    SYNTAX          EqlNASClusterUpdateEntry
    MAX-ACCESS      not-accessible
    STATUS          current
    DESCRIPTION     "An entry (row) containing the NAS Cluster firmware update information."
    INDEX           { eqlApplianceIndex }

    ::=   { eqlNASClusterUpdateTable 1 }

EqlNASClusterUpdateEntry ::=
    SEQUENCE {
        eqlNASClusterUpdateRowStatus                RowStatus,
        eqlNASClusterUpdateFilename                 OCTET STRING,
        eqlNASClusterUpdateEQLGroupMPV              Unsigned32,
        eqlNASClusterUpdateClusterMPV               Unsigned32,
        eqlNASClusterUpdateEQLGroupCurrentCompLevel Unsigned32,
        eqlNASClusterUpdateRequestId                Counter64
    }

eqlNASClusterUpdateRowStatus OBJECT-TYPE
    SYNTAX          RowStatus
    MAX-ACCESS      read-create
    STATUS          current
    DESCRIPTION     "Rowstatus variable used to manage this conceptual row."
    ::= { eqlNASClusterUpdateEntry 1 }

eqlNASClusterUpdateFilename OBJECT-TYPE
    SYNTAX          OCTET STRING (SIZE (1..261))
    MAX-ACCESS      read-create
    STATUS          current
    DESCRIPTION     "This field holds the NAS Cluster firmware update script filename."
    ::=  {  eqlNASClusterUpdateEntry 2 }

eqlNASClusterUpdateEQLGroupMPV OBJECT-TYPE
    SYNTAX          Unsigned32
    MAX-ACCESS      read-create
    STATUS          current
    DESCRIPTION     "The Management Protocol Version (MPV) of the EQL Group."
    DEFVAL          {0}
    ::=   { eqlNASClusterUpdateEntry 3}

eqlNASClusterUpdateClusterMPV OBJECT-TYPE
    SYNTAX          Unsigned32
    MAX-ACCESS      read-create
    STATUS          current
    DESCRIPTION     "The Management Protocol Version (MPV) of the NAS Appliance Cluster."
    DEFVAL          {0}
    ::=   { eqlNASClusterUpdateEntry 4}

eqlNASClusterUpdateEQLGroupCurrentCompLevel OBJECT-TYPE
    SYNTAX          Unsigned32
    MAX-ACCESS      read-create
    STATUS          current
    DESCRIPTION     "This field represents the current compatibility level of the EQL group."
    DEFVAL          {0}
    ::=  { eqlNASClusterUpdateEntry  5 }

eqlNASClusterUpdateRequestId OBJECT-TYPE
    SYNTAX          Counter64
    MAX-ACCESS      read-create
    STATUS          current
    DESCRIPTION     "This field represents the the NAS cluster update operation request identifier."
    DEFVAL          {0}
    ::= { eqlNASClusterUpdateEntry 6 }

-----------------------------------------------------------------------------------------------

eqlNASClusterInfoTable OBJECT-TYPE
    SYNTAX          SEQUENCE OF EqlNASClusterInfoEntry
    MAX-ACCESS      not-accessible
    STATUS          current
    DESCRIPTION     "EqualLogic-Dynamic(semi) table used to get local or remote NAS cluster's id and certificate
                     TimeoutAll:60"
    ::=    { eqlNASObjects 24 }

eqlNASClusterInfoEntry OBJECT-TYPE
    SYNTAX          EqlNASClusterInfoEntry
    MAX-ACCESS      not-accessible
    STATUS          current
    DESCRIPTION     "An entry contains the cluster Id and certificate"
    INDEX          { eqlApplianceIndex, eqlNASClusterInfoSiteType, eqliscsiVolumeReplSiteIndex,  eqlNASClusterInfoSegmentId }
    ::=   { eqlNASClusterInfoTable 1 }

EqlNASClusterInfoEntry ::=
    SEQUENCE {
    eqlNASClusterInfoRowStatus                      RowStatus,
    eqlNASClusterInfoSiteType                       INTEGER,
    eqlNASClusterInfoSegmentId                      Unsigned32,
    eqlNASClusterInfoSegmentSize                    Unsigned32,
    eqlNASClusterInfoMoreSegment                    TruthValue,
    eqlNASClusterInfoCertificate                    CertificateType,
    eqlNASClusterInfoClusterId                      ClusterIdType
    }

eqlNASClusterInfoRowStatus OBJECT-TYPE
    SYNTAX          RowStatus
    MAX-ACCESS      read-create
    STATUS          current
    DESCRIPTION     "This field is used indicate the status of this entry."
    ::= { eqlNASClusterInfoEntry 1 }


eqlNASClusterInfoSiteType OBJECT-TYPE
    SYNTAX          INTEGER   {
                      local(1),
		      remote(2)
    }
    MAX-ACCESS      not-accessible
    STATUS          current
    DESCRIPTION     "This field specifies whether the Certificate request is for local or
                     from remote replication partner site."
    ::= { eqlNASClusterInfoEntry 2 }

eqlNASClusterInfoSegmentId OBJECT-TYPE
   SYNTAX        Unsigned32
   MAX-ACCESS    not-accessible
   STATUS        current
   DESCRIPTION  "Index into list Certificate data"
   ::= { eqlNASClusterInfoEntry 3 }

eqlNASClusterInfoSegmentSize OBJECT-TYPE
   SYNTAX        Unsigned32
   MAX-ACCESS    read-only
   STATUS        current
   DESCRIPTION  "Size of the Certificate data segment"
   ::= { eqlNASClusterInfoEntry 4 }


eqlNASClusterInfoMoreSegment OBJECT-TYPE
    SYNTAX          TruthValue
    MAX-ACCESS      read-only
    STATUS          current
    DESCRIPTION     "True returned if there is are more segment to be feteched for
                    the certificate"
    ::= { eqlNASClusterInfoEntry 5 }


eqlNASClusterInfoCertificate OBJECT-TYPE
    SYNTAX          CertificateType
    MAX-ACCESS      read-only
    STATUS          current
    DESCRIPTION     "String containing RSA certificate for local cluster."
    ::= { eqlNASClusterInfoEntry 6 }

eqlNASClusterInfoClusterId OBJECT-TYPE
    SYNTAX          ClusterIdType
    MAX-ACCESS      read-only
    STATUS          current
    DESCRIPTION     "String containing local cluster Id. It should be unique within the network.
                     It is generated by IDC code."
    ::= { eqlNASClusterInfoEntry 7 }


------------------------------------------------------------------------------------------------

eqlNASReplPartnerClusterIdMapTable OBJECT-TYPE
    SYNTAX        SEQUENCE OF EqlNASReplPartnerClusterIdMapEntry
    MAX-ACCESS    not-accessible
    STATUS        current
    DESCRIPTION
     "EqualLogic-Dynamic
      This table is used to get the NAS Cluster Id for the given remote NAS SAN VIP."
::= { eqlNASObjects 25 }

eqlNASReplPartnerClusterIdMapEntry OBJECT-TYPE
    SYNTAX        EqlNASReplPartnerClusterIdMapEntry
    MAX-ACCESS    not-accessible
    STATUS        current
    DESCRIPTION
      ""
    INDEX           { eqlApplianceIndex, eqlNASReplPartnerClusterIdMapSanVIPType, eqlNASReplPartnerClusterIdMapSanVIP }
::= { eqlNASReplPartnerClusterIdMapTable 1 }

EqlNASReplPartnerClusterIdMapEntry ::= SEQUENCE {

   eqlNASReplPartnerClusterIdMapSanVIPType                   InetAddressType,
   eqlNASReplPartnerClusterIdMapSanVIP                       InetAddress,
   eqlNASReplPartnerClusterIdMapClusterId                    ClusterIdType
}


eqlNASReplPartnerClusterIdMapSanVIPType OBJECT-TYPE
   SYNTAX InetAddressType
   MAX-ACCESS    not-accessible
   STATUS        current
   DESCRIPTION
      "The SAN VIP type of the cluster."
::= { eqlNASReplPartnerClusterIdMapEntry 1 }

eqlNASReplPartnerClusterIdMapSanVIP OBJECT-TYPE
   SYNTAX InetAddress
   MAX-ACCESS    not-accessible
   STATUS        current
   DESCRIPTION
      "The SAN VIP address of the cluster."
::= { eqlNASReplPartnerClusterIdMapEntry 2 }


eqlNASReplPartnerClusterIdMapClusterId OBJECT-TYPE
   SYNTAX ClusterIdType
   MAX-ACCESS    read-only
   STATUS        current
   DESCRIPTION
      "Cluster Id, a unique identifier of the cluster assingned at the
       time of cluster creation."
::= { eqlNASReplPartnerClusterIdMapEntry 3 }


-----------------------------------------------------------------------------------------------

eqlNASReplPartnerConfigTable OBJECT-TYPE
    SYNTAX          SEQUENCE OF EqlNASReplPartnerConfigEntry
    MAX-ACCESS      not-accessible
    STATUS          current
    DESCRIPTION     "EqualLogic-Dynamic
                     This table is used to configure NAS replication partnership
                     (Trust) with a remote NAS cluster.
                     TimeoutAll:60"
        --  using "eqlNASObjects 32" was causing a conflict in BASE opcodes with  eqlNASContainerUniqueIDTable
        ::=    { eqlNASObjects 26 }

eqlNASReplPartnerConfigEntry OBJECT-TYPE
    SYNTAX          EqlNASReplPartnerConfigEntry
    MAX-ACCESS      not-accessible
    STATUS          current
    DESCRIPTION     "An entry contains some of the information needed to create
                     replication partnership with a remote NAS cluster.
                     The combination of index and entry provides the information
                     needed to create partnership/trust with the remote cluster."
    INDEX          { eqlApplianceIndex, eqlNASClusterInfoClusterId, eqlNASClusterInfoSegmentId }
    ::=   { eqlNASReplPartnerConfigTable 1 }

EqlNASReplPartnerConfigEntry ::=
    SEQUENCE {
    eqlNASReplPartnerConfigRowStatus     RowStatus,
    eqlNASReplPartnerConfigCertificate   CertificateType,
    eqlNASReplPartnerConfigInetAddrType  InetAddressType,
    eqlNASReplPartnerConfigInetAddr      InetAddress
    }

eqlNASReplPartnerConfigRowStatus OBJECT-TYPE
    SYNTAX          RowStatus
    MAX-ACCESS      read-create
    STATUS          current
    DESCRIPTION     "This field is used indicate the status of this entry."
    ::= { eqlNASReplPartnerConfigEntry 1 }

eqlNASReplPartnerConfigCertificate OBJECT-TYPE
    SYNTAX          CertificateType
    MAX-ACCESS      read-only
    STATUS          current
    DESCRIPTION     "String containing all or a portion of the certificate
                     used in authenticating the remote cluster."
    ::= { eqlNASReplPartnerConfigEntry 2 }


eqlNASReplPartnerConfigInetAddrType OBJECT-TYPE
   SYNTAX        InetAddressType
   MAX-ACCESS    read-write
   STATUS        current
   DESCRIPTION
      "The address type for the RemoteCluster SAN VIP"
::= { eqlNASReplPartnerConfigEntry 3 }


eqlNASReplPartnerConfigInetAddr OBJECT-TYPE
   SYNTAX        InetAddress
   MAX-ACCESS    read-write
   STATUS        current
   DESCRIPTION
      "The RemoteCluster SAN VIP"
::= { eqlNASReplPartnerConfigEntry 4 }

-----------------------------------------------------------------------------------------------

eqlNASReplTable OBJECT-TYPE
    SYNTAX        SEQUENCE OF EqlNASReplEntry
    MAX-ACCESS    not-accessible
    STATUS        current
    DESCRIPTION
     "EqualLogic-Dynamic
     TimeoutAll:60
     This table is used to configure and monitor NAS replication relationships
     in FluidFS versions 3.0 and later. Prior versions used eqlNASReplicationTable
     for that purpose."
::= { eqlNASObjects 27 }


EqlNASReplicationError ::= INTEGER {
     -- TODO: change terminology (e.g., pri and sec) ??
        none(0),
        disconnected(1),
        internal(2),
        fs-down(3),
        config(4),
        not-sec(5),
        sec-busy(6),
        sec-fs-down(7),
        versions-dont-match(8),
        no-space(9),
        sec-cur-not-empty(10),
        no-base-found(11),
        pri-vol-reclaim(12),
        sec-vol-reclaim(13),
        fs-pri-not-optimal(14),
        fs-sec-not-optimal(15),
        fs-pri-not-available-threads(16),
        fs-sec-not-available-threads(17),
        jumbo-frame(18),
        dest-repl-disabled(19),
        snap-clone-base(20)
    }

EqlNASReplicationRole ::= INTEGER {
       unknown(0),
       source(1),
       destination(2)
   }

eqlNASReplEntry OBJECT-TYPE
    SYNTAX        EqlNASReplEntry
    MAX-ACCESS    not-accessible
    STATUS        current
    DESCRIPTION
      ""
    INDEX           { eqlApplianceIndex, eqlNASContainerIndex, eqlNASReplSiteRemoteClusterId, eqlNASReplRemoteFSId }
::= { eqlNASReplTable 1 }

EqlNASReplEntry ::= SEQUENCE {
   eqlNASReplRowStatus            RowStatus,
   eqlNASReplRemoteFSId           Unsigned32,
   eqlNASReplVolumeReplSiteIndex  SiteIndex,
   eqlNASReplRemoteClusterName    OCTET STRING,
   eqlNASReplRemoteFSName         OCTET STRING,
   eqlNASReplAchievedRecoveryTime Counter32,
   eqlNASReplNextRecoveryTime     Counter32,
   eqlNASReplTargetRecoveryTime   Counter32,
   eqlNASReplTransferredPercent   Unsigned32,
   eqlNASReplTransferredMB        Unsigned32,
   eqlNASReplStatus               EqlNASReplicationStatus,
   eqlNASReplAction               INTEGER,
   eqlNASReplRole                 EqlNASReplicationRole,
   eqlNASReplSecsToComplete       Unsigned32,
   eqlNASReplError                EqlNASReplicationError,
   eqlNASReplCurrentXferRateKbps  Unsigned32
}

eqlNASReplRowStatus OBJECT-TYPE
   SYNTAX RowStatus
   MAX-ACCESS    read-create
   STATUS        current
   DESCRIPTION
      "The status of the row"
::= { eqlNASReplEntry 1 }

eqlNASReplRemoteFSId         OBJECT-TYPE
    SYNTAX          Unsigned32
    MAX-ACCESS      read-only
    STATUS          current
    DESCRIPTION     "Unique Identifier for the remote container. This is the FSid."
::= { eqlNASReplEntry 2 }

eqlNASReplVolumeReplSiteIndex OBJECT-TYPE
    SYNTAX          SiteIndex
    MAX-ACCESS      read-create
    STATUS          current
    DESCRIPTION     "The value of eqliscsiVolumeReplSiteIndex to index into
                     eqliscsiVolumeReplSiteTable."
::= { eqlNASReplEntry 3 }


eqlNASReplRemoteClusterName OBJECT-TYPE
    SYNTAX          OCTET STRING (SIZE (1..64))
    MAX-ACCESS      read-only
    STATUS          current
    DESCRIPTION     "This field specifies the remote cluster name, which is the
                     eqlApplianceName of the remote cluster."
::= { eqlNASReplEntry 4 }

eqlNASReplRemoteFSName       OBJECT-TYPE
    SYNTAX          OCTET STRING (SIZE (1..230))
    MAX-ACCESS      read-create
    STATUS          current
    DESCRIPTION     "Name used to identify the remote NAS Container. Contains
                     only letters, digits and underscores. Must begin with either
                     letter or an underscore. "
::= { eqlNASReplEntry 5 }

eqlNASReplAchievedRecoveryTime OBJECT-TYPE
    SYNTAX          Counter32
    MAX-ACCESS      read-only
    STATUS          current
    DESCRIPTION     "This field specifies the date/time of the last recovery snapshot
                     that has been copied. Time is represented as the time in seconds
                     since 00:00:00 UTC, 1970-01-01."
::= { eqlNASReplEntry 6 }

eqlNASReplNextRecoveryTime OBJECT-TYPE
    SYNTAX          Counter32
    MAX-ACCESS      read-only
    STATUS          current
    DESCRIPTION     "This field specifies the date/time of the next recovery snapshot
                     that will be copied. Time is represented as the time in seconds
                     since 00:00:00 UTC, 1970-01-01."
::= { eqlNASReplEntry 7 }

eqlNASReplTargetRecoveryTime OBJECT-TYPE
    SYNTAX          Counter32
    MAX-ACCESS      read-only
    STATUS          current
    DESCRIPTION     "This field specifies the date/time of the target/goal for
                     next recovery snapshot to be copied. This is N/A to EQL.
                     Time is represented as the time in seconds since 00:00:00 UTC,
                     1970-01-01."
::= { eqlNASReplEntry 8 }

eqlNASReplTransferredPercent   OBJECT-TYPE
    SYNTAX          Unsigned32
    UNITS            "%"
    MAX-ACCESS      read-only
    STATUS          current
    DESCRIPTION     "Provides a percent transferred for the current replication process."
::= {eqlNASReplEntry 9 }

eqlNASReplTransferredMB   OBJECT-TYPE
    SYNTAX          Unsigned32
    MAX-ACCESS      read-only
    STATUS          current
    DESCRIPTION     "Provides data transferred (in MB) for the current replication process."
::= {eqlNASReplEntry 10 }

eqlNASReplStatus OBJECT-TYPE
    SYNTAX EqlNASReplicationStatus
    MAX-ACCESS      read-only
    STATUS          current
    DESCRIPTION     "The status of this replication relationship."
::= { eqlNASReplEntry 11 }

eqlNASReplAction  OBJECT-TYPE
    SYNTAX        INTEGER {

       none(0),
      -- following actions will be used by ApplExec/netmgtd to send Action to Libspartan
       replicate(1),
       pause(2),
       resume(3),
       cancel(4),
       demote(5),

     -- Following actions will be used by ApplExec to send action to libspartan
       promote(6),
       force-promote(7),
       delete(8),
       force-delete(9),

       -- following Actions are used only by netmgtd to send user action to ApplExec
       outbound-delete(100),
       outbound-force-delete(101),
       inbound-delete(102),
       inbound-promote(103),
       inbound-promote-restore-cfg(104),
       inbound-promote-keep-demote(105),
       inbound-promote-keep-demote-restore-cfg(106),
       inbound-delete-failback(107),
       inbound-delete-failback-restore-cfg(108),
       restore-cfg(109),
       inbound-pause(110),
       inbound-resume(111),

       -- Following Action is used for promote before deleting replication
       internal-promote(112)
    }

    MAX-ACCESS      read-create
    STATUS          current
    DESCRIPTION     "Use this column to perform actions on this replication relationship."
::= { eqlNASReplEntry 12 }

eqlNASReplSecsToComplete    OBJECT-TYPE
    SYNTAX          Unsigned32
    MAX-ACCESS      read-only
    STATUS          current
    DESCRIPTION     "Seconds left in completion of the current replication process."
::= {eqlNASReplEntry 13 }

eqlNASReplError           OBJECT-TYPE
    SYNTAX EqlNASReplicationError
    MAX-ACCESS      read-only
    STATUS          current
    DESCRIPTION     "Error encountered during replication."
::= { eqlNASReplEntry 14 }

eqlNASReplRole           OBJECT-TYPE
    SYNTAX EqlNASReplicationRole
    MAX-ACCESS      read-only
    STATUS          current
    DESCRIPTION     "The role(src/dest) of this container in the relication relationship."
::= { eqlNASReplEntry 15 }

eqlNASReplCurrentXferRateKbps OBJECT-TYPE
    SYNTAX          Unsigned32
    MAX-ACCESS      read-only
    STATUS          current
    DESCRIPTION     "The current rate of data transfer(kbps) for the replication under
    progress."
::= {eqlNASReplEntry 16 }

---************************************************************

eqlNASQuotaUsageTable OBJECT-TYPE
    SYNTAX          SEQUENCE OF EqlNASQuotaUsageEntry
    MAX-ACCESS      not-accessible
    STATUS          current
    DESCRIPTION     "EqualLogic-Dynamic quota Table
                     This table contains a list of quota usages associated with the associated container.
                     TimeoutAll:60"
    ::=  {  eqlNASContainerTable 7 }

eqlNASQuotaUsageEntry OBJECT-TYPE
    SYNTAX          EqlNASQuotaUsageEntry
    MAX-ACCESS      not-accessible
    STATUS          current
    DESCRIPTION     "An entry (row) containing quota info."
    INDEX           { eqlApplianceIndex, eqlNASContainerIndex, eqlNASQuotaUsageTargetType, eqlNASQuotaUsageTargetName }
    ::=    { eqlNASQuotaUsageTable 1 }

EqlNASQuotaUsageEntry ::=
    SEQUENCE {
        eqlNASQuotaUsageRowStatus       RowStatus,
        eqlNASQuotaUsageTargetType      INTEGER,
        eqlNASQuotaUsageTargetName      OCTET STRING,
        eqlNASQuotaUsageMB        		Integer32
    }

eqlNASQuotaUsageRowStatus OBJECT-TYPE
    SYNTAX          RowStatus
    MAX-ACCESS      read-only
    STATUS          current
    DESCRIPTION     "The rowstatus...."
    ::= { eqlNASQuotaUsageEntry 1 }

eqlNASQuotaUsageTargetType OBJECT-TYPE
    SYNTAX	    INTEGER {
            unused(0),
		    allofgroup(1),
			anyuseringroup(2),
			user(3)
		    }
    MAX-ACCESS	    read-only
    STATUS	    current
    DESCRIPTION	    "Type of target for this quota definition row"
    ::= { eqlNASQuotaUsageEntry 2 }

eqlNASQuotaUsageTargetName OBJECT-TYPE
    SYNTAX          OCTET STRING (SIZE (1..129))
    MAX-ACCESS      read-only
    STATUS          current
    DESCRIPTION     "The name of the user or group as indicated by the target type. AD groups can be 129 bytes "
    ::= {   eqlNASQuotaUsageEntry 3 }

eqlNASQuotaUsageMB OBJECT-TYPE
    SYNTAX          Integer32
    MAX-ACCESS      read-only
    STATUS          current
    DESCRIPTION     "This field specifies the amount of space in MB currently in use by targetname."
    ::= {   eqlNASQuotaUsageEntry 4 }


---************************************************************

---************************************************************

eqlNASGroupQuotaEffectiveRuleTable OBJECT-TYPE
    SYNTAX          SEQUENCE OF EqlNASGroupQuotaEffectiveRuleEntry
    MAX-ACCESS      not-accessible
    STATUS          current
    DESCRIPTION     "EqualLogic-Dynamic quota Table
                     This table contains a list of group quota effective rules associated with the associated container.
                     TimeoutAll:60"
    ::=  {  eqlNASContainerTable 8 }

eqlNASGroupQuotaEffectiveRuleEntry OBJECT-TYPE
    SYNTAX          EqlNASGroupQuotaEffectiveRuleEntry
    MAX-ACCESS      not-accessible
    STATUS          current
    DESCRIPTION     "An entry (row) containing quota info."
    INDEX           { eqlApplianceIndex, eqlNASContainerIndex, eqlNASGroupQuotaEffectiveRuleTargetName }
    ::=    { eqlNASGroupQuotaEffectiveRuleTable 1 }

EqlNASGroupQuotaEffectiveRuleEntry ::=
    SEQUENCE {
        eqlNASGroupQuotaEffectiveRuleTargetName      		OCTET STRING,
        eqlNASGroupQuotaEffectiveRuleRowStatus       		RowStatus,
        eqlNASGroupQuotaEffectiveRuleSoftLimit     			Integer32,
        eqlNASGroupQuotaEffectiveRuleHardLimit     			Integer32,
        eqlNASGroupQuotaEffectiveRuleSoftLimitEnabled		TruthValue,
        eqlNASGroupQuotaEffectiveRuleHardLimitEnabled     	TruthValue
    }

eqlNASGroupQuotaEffectiveRuleTargetName OBJECT-TYPE
    SYNTAX          OCTET STRING (SIZE (1..129))
    MAX-ACCESS      read-only
    STATUS          current
    DESCRIPTION     "The name of the group. AD groups can be 129 bytes "
    ::= {   eqlNASGroupQuotaEffectiveRuleEntry 1 }

eqlNASGroupQuotaEffectiveRuleRowStatus OBJECT-TYPE
    SYNTAX          RowStatus
    MAX-ACCESS      read-only
    STATUS          current
    DESCRIPTION     "The rowstatus...."
    ::= { eqlNASGroupQuotaEffectiveRuleEntry 2 }

eqlNASGroupQuotaEffectiveRuleSoftLimit OBJECT-TYPE
    SYNTAX          Integer32
    MAX-ACCESS      read-only
    STATUS          current
    DESCRIPTION     "This is the amount of used space that triggers user alerts"
    ::= {   eqlNASGroupQuotaEffectiveRuleEntry 3 }

eqlNASGroupQuotaEffectiveRuleHardLimit OBJECT-TYPE
    SYNTAX          Integer32
    MAX-ACCESS      read-only
    STATUS          current
    DESCRIPTION     "This field specifies the amount of space in MB at which writes are disallowed."
    ::= {   eqlNASGroupQuotaEffectiveRuleEntry 4 }

eqlNASGroupQuotaEffectiveRuleSoftLimitEnabled OBJECT-TYPE
    SYNTAX          TruthValue
    MAX-ACCESS      read-only
    STATUS          current
    DESCRIPTION     "Specifies whether alerts based on softlimit are enabled."
    DEFVAL          {false}
    ::= {   eqlNASGroupQuotaEffectiveRuleEntry 5 }

eqlNASGroupQuotaEffectiveRuleHardLimitEnabled OBJECT-TYPE
    SYNTAX          TruthValue
    MAX-ACCESS      read-only
    STATUS          current
    DESCRIPTION     "This field specifies whether hard limit is enforced"
    DEFVAL          {false}
    ::= {   eqlNASGroupQuotaEffectiveRuleEntry 6 }


---************************************************************

---************************************************************

eqlNASUserQuotaEffectiveRuleTable OBJECT-TYPE
    SYNTAX          SEQUENCE OF EqlNASUserQuotaEffectiveRuleEntry
    MAX-ACCESS      not-accessible
    STATUS          current
    DESCRIPTION     "EqualLogic-Dynamic quota Table
                     This table contains a list of user quota effective rules associated with the associated container.
                     TimeoutAll:60"
    ::=  {  eqlNASContainerTable 9 }

eqlNASUserQuotaEffectiveRuleEntry OBJECT-TYPE
    SYNTAX          EqlNASUserQuotaEffectiveRuleEntry
    MAX-ACCESS      not-accessible
    STATUS          current
    DESCRIPTION     "An entry (row) containing quota info."
    INDEX           { eqlApplianceIndex, eqlNASContainerIndex, eqlNASUserQuotaEffectiveRuleTargetName }
    ::=    { eqlNASUserQuotaEffectiveRuleTable 1 }

EqlNASUserQuotaEffectiveRuleEntry ::=
    SEQUENCE {
        eqlNASUserQuotaEffectiveRuleTargetName      		OCTET STRING,
        eqlNASUserQuotaEffectiveRuleRowStatus       		RowStatus,
        eqlNASUserQuotaEffectiveRuleUserSoftLimit     		Integer32,
        eqlNASUserQuotaEffectiveRuleUserHardLimit     		Integer32,
        eqlNASUserQuotaEffectiveRuleGroupName      			OCTET STRING,
        eqlNASUserQuotaEffectiveRuleGroupSoftLimit     		Integer32,
        eqlNASUserQuotaEffectiveRuleGroupHardLimit     		Integer32,
        eqlNASUserQuotaEffectiveRuleUserSoftLimitEnabled   	TruthValue,
        eqlNASUserQuotaEffectiveRuleUserHardLimitEnabled   	TruthValue,
        eqlNASUserQuotaEffectiveRuleGroupSoftLimitEnabled  	TruthValue,
        eqlNASUserQuotaEffectiveRuleGroupHardLimitEnabled  	TruthValue
    }

eqlNASUserQuotaEffectiveRuleTargetName OBJECT-TYPE
    SYNTAX          OCTET STRING (SIZE (1..129))
    MAX-ACCESS      read-only
    STATUS          current
    DESCRIPTION     "The name of the user."
    ::= {   eqlNASUserQuotaEffectiveRuleEntry 1 }

eqlNASUserQuotaEffectiveRuleRowStatus OBJECT-TYPE
    SYNTAX          RowStatus
    MAX-ACCESS      read-only
    STATUS          current
    DESCRIPTION     "The rowstatus...."
    ::= { eqlNASUserQuotaEffectiveRuleEntry 2 }

eqlNASUserQuotaEffectiveRuleUserSoftLimit OBJECT-TYPE
    SYNTAX          Integer32
    MAX-ACCESS      read-only
    STATUS          current
    DESCRIPTION     "This is the amount of used space that triggers user alerts"
    ::= {   eqlNASUserQuotaEffectiveRuleEntry 3 }

eqlNASUserQuotaEffectiveRuleUserHardLimit OBJECT-TYPE
    SYNTAX          Integer32
    MAX-ACCESS      read-only
    STATUS          current
    DESCRIPTION     "This field specifies the amount of space in MB at which writes are disallowed."
    ::= {   eqlNASUserQuotaEffectiveRuleEntry 4 }

eqlNASUserQuotaEffectiveRuleGroupName OBJECT-TYPE
    SYNTAX          OCTET STRING (SIZE (1..129))
    MAX-ACCESS      read-only
    STATUS          current
    DESCRIPTION     "The name of the primary group of the user"
    ::= {   eqlNASUserQuotaEffectiveRuleEntry 5 }

eqlNASUserQuotaEffectiveRuleGroupSoftLimit OBJECT-TYPE
    SYNTAX          Integer32
    MAX-ACCESS      read-only
    STATUS          current
    DESCRIPTION     "This is the amount of used space that triggers user alerts based on primary group's warn level"
    ::= {   eqlNASUserQuotaEffectiveRuleEntry 6 }

eqlNASUserQuotaEffectiveRuleGroupHardLimit OBJECT-TYPE
    SYNTAX          Integer32
    MAX-ACCESS      read-only
    STATUS          current
    DESCRIPTION     "This field specifies the amount of space in MB at which writes are disallowed based on primary group's hard limit."
    ::= {   eqlNASUserQuotaEffectiveRuleEntry 7 }

eqlNASUserQuotaEffectiveRuleUserSoftLimitEnabled OBJECT-TYPE
    SYNTAX          TruthValue
    MAX-ACCESS      read-only
    STATUS          current
    DESCRIPTION     "Specifies whether alerts based on user softlimit are enabled."
    DEFVAL          {false}
    ::= {   eqlNASUserQuotaEffectiveRuleEntry 8 }

eqlNASUserQuotaEffectiveRuleUserHardLimitEnabled OBJECT-TYPE
    SYNTAX          TruthValue
    MAX-ACCESS      read-only
    STATUS          current
    DESCRIPTION     "This field specifies whether user hard limit is enforced"
    DEFVAL          {false}
    ::= {   eqlNASUserQuotaEffectiveRuleEntry 9 }

eqlNASUserQuotaEffectiveRuleGroupSoftLimitEnabled OBJECT-TYPE
    SYNTAX          TruthValue
    MAX-ACCESS      read-only
    STATUS          current
    DESCRIPTION     "Specifies whether alerts based on primary group's softlimit are enabled."
    DEFVAL          {false}
    ::= {   eqlNASUserQuotaEffectiveRuleEntry 10 }

eqlNASUserQuotaEffectiveRuleGroupHardLimitEnabled OBJECT-TYPE
    SYNTAX          TruthValue
    MAX-ACCESS      read-only
    STATUS          current
    DESCRIPTION     "This field specifies whether primary group's hard limit is enforced"
    DEFVAL          {false}
    ::= {   eqlNASUserQuotaEffectiveRuleEntry 11 }

---************************************************************


eqlNASConfigStateTable OBJECT-TYPE
    SYNTAX          SEQUENCE OF EqlNASConfigStateEntry
    MAX-ACCESS      not-accessible
    STATUS          current
    DESCRIPTION     "EqualLogic-Dynamic table controlling the NAS cluster configuration state."
    ::=    { eqlNASObjects 28 }

eqlNASConfigStateEntry OBJECT-TYPE
    SYNTAX          EqlNASConfigStateEntry
    MAX-ACCESS      not-accessible
    STATUS          current
    DESCRIPTION     "An entry (row) containing the NAS Cluster configuration state information."
    INDEX           { eqlApplianceIndex }

    ::=   { eqlNASConfigStateTable 1 }

EqlNASConfigStateEntry ::=
    SEQUENCE {
        eqlNASConfigStateConfigFinished            TruthValue,
        eqlNASConfigStateHardwareReplaceInProgress TruthValue
    }

eqlNASConfigStateConfigFinished OBJECT-TYPE
    SYNTAX          TruthValue
    MAX-ACCESS      read-write
    STATUS          current
    DESCRIPTION     "True if NAS Cluster configuration is completed."
    DEFVAL          { false }
    ::= { eqlNASConfigStateEntry 1 }

eqlNASConfigStateHardwareReplaceInProgress OBJECT-TYPE
    SYNTAX          TruthValue
    MAX-ACCESS      read-write
    STATUS          current
    DESCRIPTION     "True if NAS Cluster hardware replacement is in progress."
    DEFVAL          { false }
    ::= { eqlNASConfigStateEntry 2 }
-----------------------------------------------------------------------------------------------

eqlNASClientTable OBJECT-TYPE
    SYNTAX          SEQUENCE OF EqlNASClientEntry
    MAX-ACCESS      not-accessible
    STATUS          current
    DESCRIPTION     "EqualLogic-Dynamic
                     This table contains NAS Client information.
                     TimeoutAll:60"
    ::=    { eqlNASObjects 29 }

eqlNASClientEntry OBJECT-TYPE
    SYNTAX          EqlNASClientEntry
    MAX-ACCESS      not-accessible
    STATUS          current
    DESCRIPTION     "An entry (row) containing NAS client information."
    INDEX           { eqlApplianceIndex, eqlNASClientNodeIndex,
                      eqlNASClientIPAddressType, eqlNASClientIPAddress,
                      eqlNASClientUserName, eqlNASClientProtocol }

    ::=   { eqlNASClientTable 1 }

EqlNASClientEntry ::=
    SEQUENCE {
        eqlNASClientNodeIndex           Unsigned32,
        eqlNASClientIPAddressType       InetAddressType,
        eqlNASClientIPAddress           InetAddress,
        eqlNASClientUserName            OCTET STRING,
        eqlNASClientProtocol            INTEGER,
        eqlNASClientConnectedTime       Counter32,
        eqlNASClientIdleTime            Counter32,
        eqlNASClientNumOpenFiles        Unsigned32,
        eqlNASClientIsGuest             TruthValue
    }

eqlNASClientNodeIndex   OBJECT-TYPE
    SYNTAX          Unsigned32
    MAX-ACCESS      read-only
    STATUS          current
    DESCRIPTION     "NAS client node index."
    ::= { eqlNASClientEntry 1 }

eqlNASClientIPAddressType OBJECT-TYPE
    SYNTAX          InetAddressType
    MAX-ACCESS      read-only
    STATUS          current
    DESCRIPTION     "This field specifies the type of address (v4/v6) of this IP address entry."
    ::= { eqlNASClientEntry  2 }

eqlNASClientIPAddress   OBJECT-TYPE
    SYNTAX          InetAddress
    MAX-ACCESS      read-only
    STATUS          current
    DESCRIPTION     "NAS client IPv4 address."
    ::= { eqlNASClientEntry 3 }

eqlNASClientUserName   OBJECT-TYPE
    SYNTAX          OCTET STRING (SIZE (1..85))
    MAX-ACCESS      read-only
    STATUS          current
    DESCRIPTION     "NAS client user name."
    ::= { eqlNASClientEntry 4 }

eqlNASClientProtocol OBJECT-TYPE
    SYNTAX          INTEGER {
                             cifs(1)
                            }
    MAX-ACCESS    read-only
    STATUS        current
    DESCRIPTION   "NAS client protocol."
    ::= { eqlNASClientEntry 5 }

eqlNASClientConnectedTime OBJECT-TYPE
    SYNTAX          Counter32
    MAX-ACCESS      read-only
    STATUS          current
    DESCRIPTION     "The time in seconds that has elapsed since this client connection was first
                     established with the NAS controller."
    ::= { eqlNASClientEntry  6 }

eqlNASClientIdleTime OBJECT-TYPE
    SYNTAX          Counter32
    MAX-ACCESS      read-only
    STATUS          current
    DESCRIPTION     "The time in seconds that has elapsed since this client connection is idle."
    ::= { eqlNASClientEntry  7 }

eqlNASClientNumOpenFiles OBJECT-TYPE
    SYNTAX          Unsigned32
    MAX-ACCESS      read-only
    STATUS          current
    DESCRIPTION     "The number of open files from this client connection."
    ::= { eqlNASClientEntry  8 }

eqlNASClientIsGuest OBJECT-TYPE
    SYNTAX          TruthValue
    MAX-ACCESS      read-only
    STATUS          current
    DESCRIPTION     "True if the client initiating this connection is a guest."
    ::= { eqlNASClientEntry 9 }

-----------------------------------------------------------------------------------------------

eqlNASStatsClusterTrafficRateTable OBJECT-TYPE
    SYNTAX          SEQUENCE OF EqlNASStatsClusterTrafficRateEntry
    MAX-ACCESS      not-accessible
    STATUS          current
    DESCRIPTION     "EqualLogic-Dynamic
                     This table contains NAS traffic rate statistics for the NAS cluster.
                     TimeoutAll:60"
    ::=    { eqlNASObjects 30 }

eqlNASStatsClusterTrafficRateEntry OBJECT-TYPE
    SYNTAX          EqlNASStatsClusterTrafficRateEntry
    MAX-ACCESS      not-accessible
    STATUS          current
    DESCRIPTION     "An entry (row) containing peristent NAS cluster traffic rate statistics."
    INDEX           { eqlApplianceIndex }

    ::=   { eqlNASStatsClusterTrafficRateTable 1}

EqlNASStatsClusterTrafficRateEntry ::=
    SEQUENCE {
    eqlNASStatsClusterTrafficRateTimestamp                        Counter32,
    eqlNASStatsClusterTrafficRateNfsReadMBsPerSec                 Unsigned32,
    eqlNASStatsClusterTrafficRateNfsWriteMBsPerSec                Unsigned32,
    eqlNASStatsClusterTrafficRateNdmpReadMBsPerSec                Unsigned32,
    eqlNASStatsClusterTrafficRateNdmpWriteMBsPerSec               Unsigned32,
    eqlNASStatsClusterTrafficRateCifsReadMBsPerSec                Unsigned32,
    eqlNASStatsClusterTrafficRateCifsWriteMBsPerSec               Unsigned32,
    eqlNASStatsClusterTrafficRateReplicationReadMBsPerSec         Unsigned32,
    eqlNASStatsClusterTrafficRateReplicationWriteMBsPerSec        Unsigned32,
    eqlNASStatsClusterTrafficRateStorageSubSystemReadMBsPerSec    Unsigned32,
    eqlNASStatsClusterTrafficRateStorageSubSystemWriteMBsPerSec   Unsigned32,
    eqlNASStatsClusterTrafficRateNetworkOverheadReadMBsPerSec     Unsigned32,
    eqlNASStatsClusterTrafficRateNetworkOverheadWriteMBsPerSec    Unsigned32,
    eqlNASStatsClusterTrafficRateNetworkPacketDropsPerSec         Unsigned32,
    eqlNASStatsClusterTrafficRateNfsIOPSRead                      Unsigned32,
    eqlNASStatsClusterTrafficRateNfsIOPSWrite                     Unsigned32,
    eqlNASStatsClusterTrafficRateNfsIOPSOther                     Unsigned32,
    eqlNASStatsClusterTrafficRateCifsIOPSRead                     Unsigned32,
    eqlNASStatsClusterTrafficRateCifsIOPSWrite                    Unsigned32,
    eqlNASStatsClusterTrafficRateCifsIOPSOther                    Unsigned32,
    eqlNASStatsClusterTrafficRateTotalPrimaryMBsPerSec            Unsigned32,
    eqlNASStatsClusterTrafficRateTotalSecondaryMBsPerSec          Unsigned32
    }

eqlNASStatsClusterTrafficRateTimestamp OBJECT-TYPE
    SYNTAX          Counter32
    MAX-ACCESS      read-only
    STATUS          current
    DESCRIPTION     "This field specifies the date/time when the statistics were collected.
                     Time is represented as the time in seconds since 00:00:00 UTC, 1970-01-01."
    ::= { eqlNASStatsClusterTrafficRateEntry 1 }

eqlNASStatsClusterTrafficRateNfsReadMBsPerSec OBJECT-TYPE
    SYNTAX          Unsigned32
    MAX-ACCESS      read-only
    STATUS          current
    DESCRIPTION     "The number of MBs read per second via NFS per cluster."
    ::= { eqlNASStatsClusterTrafficRateEntry 2 }


eqlNASStatsClusterTrafficRateNfsWriteMBsPerSec OBJECT-TYPE
    SYNTAX          Unsigned32
    MAX-ACCESS      read-only
    STATUS          current
    DESCRIPTION     "The number of MBs written per second via NFS per cluster."
    ::= { eqlNASStatsClusterTrafficRateEntry 3 }

eqlNASStatsClusterTrafficRateNdmpReadMBsPerSec OBJECT-TYPE
    SYNTAX          Unsigned32
    MAX-ACCESS      read-only
    STATUS          current
    DESCRIPTION     "The number of MBs read per second via NDMP per cluster."
    ::= { eqlNASStatsClusterTrafficRateEntry 4 }

eqlNASStatsClusterTrafficRateNdmpWriteMBsPerSec OBJECT-TYPE
    SYNTAX          Unsigned32
    MAX-ACCESS      read-only
    STATUS          current
    DESCRIPTION     "The number of MBs written per second via NDMP per cluster."
    ::= { eqlNASStatsClusterTrafficRateEntry 5 }

eqlNASStatsClusterTrafficRateCifsReadMBsPerSec OBJECT-TYPE
    SYNTAX          Unsigned32
    MAX-ACCESS      read-only
    STATUS          current
    DESCRIPTION     "The number of MBs read per second via CIFS per cluster."
    ::= { eqlNASStatsClusterTrafficRateEntry 6 }

eqlNASStatsClusterTrafficRateCifsWriteMBsPerSec OBJECT-TYPE
    SYNTAX          Unsigned32
    MAX-ACCESS      read-only
    STATUS          current
    DESCRIPTION     "The number of MBs written per second via CIFS per second per cluster."
    ::= { eqlNASStatsClusterTrafficRateEntry 7 }

eqlNASStatsClusterTrafficRateReplicationReadMBsPerSec OBJECT-TYPE
    SYNTAX          Unsigned32
    MAX-ACCESS      read-only
    STATUS          current
    DESCRIPTION     "The number of replication MBs read per second per cluster."
    ::= { eqlNASStatsClusterTrafficRateEntry 8 }

eqlNASStatsClusterTrafficRateReplicationWriteMBsPerSec OBJECT-TYPE
    SYNTAX          Unsigned32
    MAX-ACCESS      read-only
    STATUS          current
    DESCRIPTION     "The number of replication MBs written per second per cluster."
    ::= { eqlNASStatsClusterTrafficRateEntry 9 }

eqlNASStatsClusterTrafficRateStorageSubSystemReadMBsPerSec OBJECT-TYPE
    SYNTAX          Unsigned32
    MAX-ACCESS      read-only
    STATUS          current
    DESCRIPTION     "The number of storage subsystem MBs read per second per cluster."
    ::= { eqlNASStatsClusterTrafficRateEntry 10 }

eqlNASStatsClusterTrafficRateStorageSubSystemWriteMBsPerSec OBJECT-TYPE
    SYNTAX          Unsigned32
    MAX-ACCESS      read-only
    STATUS          current
    DESCRIPTION     "The number of storage subsystem MBs written per second per cluster."
    ::= { eqlNASStatsClusterTrafficRateEntry 11 }

eqlNASStatsClusterTrafficRateNetworkOverheadReadMBsPerSec OBJECT-TYPE
    SYNTAX          Unsigned32
    MAX-ACCESS      read-only
    STATUS          current
    DESCRIPTION     "The number of network overhead MBs read per second per cluster."
    ::= { eqlNASStatsClusterTrafficRateEntry 12 }

eqlNASStatsClusterTrafficRateNetworkOverheadWriteMBsPerSec OBJECT-TYPE
    SYNTAX          Unsigned32
    MAX-ACCESS      read-only
    STATUS          current
    DESCRIPTION     "The number of network overhead MBs written per second per cluster."
    ::= { eqlNASStatsClusterTrafficRateEntry 13 }

eqlNASStatsClusterTrafficRateNetworkPacketDropsPerSec OBJECT-TYPE
    SYNTAX          Unsigned32
    MAX-ACCESS      read-only
    STATUS          current
    DESCRIPTION     "The number of network packet drops per second per cluster."
    ::= { eqlNASStatsClusterTrafficRateEntry 14 }

eqlNASStatsClusterTrafficRateNfsIOPSRead OBJECT-TYPE
    SYNTAX          Unsigned32
    MAX-ACCESS      read-only
    STATUS          current
    DESCRIPTION     "The number of NFS IO read operations per second per cluster."
    ::= { eqlNASStatsClusterTrafficRateEntry 15 }

eqlNASStatsClusterTrafficRateNfsIOPSWrite OBJECT-TYPE
    SYNTAX          Unsigned32
    MAX-ACCESS      read-only
    STATUS          current
    DESCRIPTION     "The number of NFS IO write operations per second per cluster."
    ::= { eqlNASStatsClusterTrafficRateEntry 16 }

eqlNASStatsClusterTrafficRateNfsIOPSOther OBJECT-TYPE
    SYNTAX          Unsigned32
    MAX-ACCESS      read-only
    STATUS          current
    DESCRIPTION     "The number of NFS IO other operations per second per cluster."
    ::= { eqlNASStatsClusterTrafficRateEntry 17 }

eqlNASStatsClusterTrafficRateCifsIOPSRead OBJECT-TYPE
    SYNTAX          Unsigned32
    MAX-ACCESS      read-only
    STATUS          current
    DESCRIPTION     "The number of CIFS IO read operations per second per cluster."
    ::= { eqlNASStatsClusterTrafficRateEntry 18 }

eqlNASStatsClusterTrafficRateCifsIOPSWrite OBJECT-TYPE
    SYNTAX          Unsigned32
    MAX-ACCESS      read-only
    STATUS          current
    DESCRIPTION     "The number of CIFS IO write operations per second per cluster."
    ::= { eqlNASStatsClusterTrafficRateEntry 19 }

eqlNASStatsClusterTrafficRateCifsIOPSOther OBJECT-TYPE
    SYNTAX          Unsigned32
    MAX-ACCESS      read-only
    STATUS          current
    DESCRIPTION     "The number of CIFS IO other operations per second per cluster."
    ::= { eqlNASStatsClusterTrafficRateEntry 20 }

eqlNASStatsClusterTrafficRateTotalPrimaryMBsPerSec OBJECT-TYPE
    SYNTAX          Unsigned32
    MAX-ACCESS      read-only
    STATUS          current
    DESCRIPTION     "The total number of primary MBs per second per cluster."
    ::= { eqlNASStatsClusterTrafficRateEntry 21 }

eqlNASStatsClusterTrafficRateTotalSecondaryMBsPerSec OBJECT-TYPE
    SYNTAX          Unsigned32
    MAX-ACCESS      read-only
    STATUS          current
    DESCRIPTION     "The total number of secondary MBs per second per cluster."
    ::= { eqlNASStatsClusterTrafficRateEntry 22 }

-----------------------------------------------------------------------------------------------

eqlNASStatsControllerTrafficRateTable OBJECT-TYPE
    SYNTAX          SEQUENCE OF EqlNASStatsControllerTrafficRateEntry
    MAX-ACCESS      not-accessible
    STATUS          current
    DESCRIPTION     "EqualLogic-Dynamic
                     This table contains NAS traffic rate statistics for the NAS controller.
                     TimeoutAll:60"
    ::=    {  eqlNASObjects 31 }

eqlNASStatsControllerTrafficRateEntry OBJECT-TYPE
    SYNTAX          EqlNASStatsControllerTrafficRateEntry
    MAX-ACCESS      not-accessible
    STATUS          current
    DESCRIPTION     "An entry (row) containing NAS controller traffic rate statistics."
    INDEX           { eqlApplianceIndex, eqlNASStatsControllerTrafficRateIndex }

    ::=   { eqlNASStatsControllerTrafficRateTable 1}

EqlNASStatsControllerTrafficRateEntry ::=
    SEQUENCE {
        eqlNASStatsControllerTrafficRateIndex                            Unsigned32,
        eqlNASStatsControllerTrafficRateTimestamp                        Counter32,
        eqlNASStatsControllerTrafficRateNfsReadMBsPerSec                 Unsigned32,
        eqlNASStatsControllerTrafficRateNfsWriteMBsPerSec                Unsigned32,
        eqlNASStatsControllerTrafficRateNdmpReadMBsPerSec                Unsigned32,
        eqlNASStatsControllerTrafficRateNdmpWriteMBsPerSec               Unsigned32,
        eqlNASStatsControllerTrafficRateCifsReadMBsPerSec                Unsigned32,
        eqlNASStatsControllerTrafficRateCifsWriteMBsPerSec               Unsigned32,
        eqlNASStatsControllerTrafficRateReplicationReadMBsPerSec         Unsigned32,
        eqlNASStatsControllerTrafficRateReplicationWriteMBsPerSec        Unsigned32,
        eqlNASStatsControllerTrafficRateStorageSubSystemReadMBsPerSec    Unsigned32,
        eqlNASStatsControllerTrafficRateStorageSubSystemWriteMBsPerSec   Unsigned32,
        eqlNASStatsControllerTrafficRateNetworkOverheadReadMBsPerSec     Unsigned32,
        eqlNASStatsControllerTrafficRateNetworkOverheadWriteMBsPerSec    Unsigned32,
        eqlNASStatsControllerTrafficRateNetworkPacketDropsPerSec         Unsigned32,
        eqlNASStatsControllerTrafficRateNfsIOPSRead                      Unsigned32,
        eqlNASStatsControllerTrafficRateNfsIOPSWrite                     Unsigned32,
        eqlNASStatsControllerTrafficRateNfsIOPSOther                     Unsigned32,
        eqlNASStatsControllerTrafficRateCifsIOPSRead                     Unsigned32,
        eqlNASStatsControllerTrafficRateCifsIOPSWrite                    Unsigned32,
        eqlNASStatsControllerTrafficRateCifsIOPSOther                    Unsigned32,
        eqlNASStatsControllerTrafficRateTotalPrimaryMBsPerSec            Unsigned32,
        eqlNASStatsControllerTrafficRateTotalPrimaryMBsPerSecToAverage   Unsigned32,
        eqlNASStatsControllerTrafficRateTotalSecondaryMBsPerSec          Unsigned32
    }

eqlNASStatsControllerTrafficRateIndex   OBJECT-TYPE
    SYNTAX          Unsigned32
    MAX-ACCESS      read-only
    STATUS          current
    DESCRIPTION     "NAS controller index."
    ::= { eqlNASStatsControllerTrafficRateEntry 1 }

eqlNASStatsControllerTrafficRateTimestamp OBJECT-TYPE
    SYNTAX          Counter32
    MAX-ACCESS      read-only
    STATUS          current
    DESCRIPTION     "This field specifies the date/time when the statistics were collected.
                     Time is represented as the time in seconds since 00:00:00 UTC, 1970-01-01."
    ::= { eqlNASStatsControllerTrafficRateEntry 2 }

eqlNASStatsControllerTrafficRateNfsReadMBsPerSec OBJECT-TYPE
    SYNTAX          Unsigned32
    MAX-ACCESS      read-only
    STATUS          current
    DESCRIPTION     "The number of MBs read per second via NFS per controller."
    ::= { eqlNASStatsControllerTrafficRateEntry 3 }


eqlNASStatsControllerTrafficRateNfsWriteMBsPerSec OBJECT-TYPE
    SYNTAX          Unsigned32
    MAX-ACCESS      read-only
    STATUS          current
    DESCRIPTION     "The number of MBs written per second via NFS per controller."
    ::= { eqlNASStatsControllerTrafficRateEntry 4 }

eqlNASStatsControllerTrafficRateNdmpReadMBsPerSec OBJECT-TYPE
    SYNTAX          Unsigned32
    MAX-ACCESS      read-only
    STATUS          current
    DESCRIPTION     "The number of MBs read per second via NDMP per controller."
    ::= { eqlNASStatsControllerTrafficRateEntry 5 }

eqlNASStatsControllerTrafficRateNdmpWriteMBsPerSec OBJECT-TYPE
    SYNTAX          Unsigned32
    MAX-ACCESS      read-only
    STATUS          current
    DESCRIPTION     "The number of MBs written per second via NDMP per controller."
    ::= { eqlNASStatsControllerTrafficRateEntry 6 }

eqlNASStatsControllerTrafficRateCifsReadMBsPerSec OBJECT-TYPE
    SYNTAX          Unsigned32
    MAX-ACCESS      read-only
    STATUS          current
    DESCRIPTION     "The number of MBs read per second via CIFS per controller."
    ::= { eqlNASStatsControllerTrafficRateEntry 7 }

eqlNASStatsControllerTrafficRateCifsWriteMBsPerSec OBJECT-TYPE
    SYNTAX          Unsigned32
    MAX-ACCESS      read-only
    STATUS          current
    DESCRIPTION     "The number of MBs written per second via CIFS per controller"
    ::= { eqlNASStatsControllerTrafficRateEntry 8 }

eqlNASStatsControllerTrafficRateReplicationReadMBsPerSec OBJECT-TYPE
    SYNTAX          Unsigned32
    MAX-ACCESS      read-only
    STATUS          current
    DESCRIPTION     "The number of replication MBs read per second per controller."
    ::= { eqlNASStatsControllerTrafficRateEntry 9 }

eqlNASStatsControllerTrafficRateReplicationWriteMBsPerSec OBJECT-TYPE
    SYNTAX          Unsigned32
    MAX-ACCESS      read-only
    STATUS          current
    DESCRIPTION     "The number of replication MBs written per second per controller."
    ::= { eqlNASStatsControllerTrafficRateEntry 10 }

eqlNASStatsControllerTrafficRateStorageSubSystemReadMBsPerSec OBJECT-TYPE
    SYNTAX          Unsigned32
    MAX-ACCESS      read-only
    STATUS          current
    DESCRIPTION     "The number of storage subsytem MBs read per second per controller."
    ::= { eqlNASStatsControllerTrafficRateEntry 11 }

eqlNASStatsControllerTrafficRateStorageSubSystemWriteMBsPerSec OBJECT-TYPE
    SYNTAX          Unsigned32
    MAX-ACCESS      read-only
    STATUS          current
    DESCRIPTION     "The number of storage subsystem MBs written per second per controller."
    ::= { eqlNASStatsControllerTrafficRateEntry 12 }

eqlNASStatsControllerTrafficRateNetworkOverheadReadMBsPerSec OBJECT-TYPE
    SYNTAX          Unsigned32
    MAX-ACCESS      read-only
    STATUS          current
    DESCRIPTION     "The number of network overhead MBs per second per controller."
    ::= { eqlNASStatsControllerTrafficRateEntry 13 }

eqlNASStatsControllerTrafficRateNetworkOverheadWriteMBsPerSec OBJECT-TYPE
    SYNTAX          Unsigned32
    MAX-ACCESS      read-only
    STATUS          current
    DESCRIPTION     "The number of network overhead MBs per second per controller."
    ::= { eqlNASStatsControllerTrafficRateEntry 14 }

eqlNASStatsControllerTrafficRateNetworkPacketDropsPerSec OBJECT-TYPE
    SYNTAX          Unsigned32
    MAX-ACCESS      read-only
    STATUS          current
    DESCRIPTION     "The number of network packet drops per second per controller."
    ::= { eqlNASStatsControllerTrafficRateEntry 15 }

eqlNASStatsControllerTrafficRateNfsIOPSRead OBJECT-TYPE
    SYNTAX          Unsigned32
    MAX-ACCESS      read-only
    STATUS          current
    DESCRIPTION     "The number of NFS IO read operations per second per controller."
    ::= { eqlNASStatsControllerTrafficRateEntry 16 }

eqlNASStatsControllerTrafficRateNfsIOPSWrite OBJECT-TYPE
    SYNTAX          Unsigned32
    MAX-ACCESS      read-only
    STATUS          current
    DESCRIPTION     "The number of NFS IO write operations per second per controller."
    ::= { eqlNASStatsControllerTrafficRateEntry 17 }

eqlNASStatsControllerTrafficRateNfsIOPSOther OBJECT-TYPE
    SYNTAX          Unsigned32
    MAX-ACCESS      read-only
    STATUS          current
    DESCRIPTION     "The number of NFS IO other operations per second per controller."
    ::= { eqlNASStatsControllerTrafficRateEntry 18 }

eqlNASStatsControllerTrafficRateCifsIOPSRead OBJECT-TYPE
    SYNTAX          Unsigned32
    MAX-ACCESS      read-only
    STATUS          current
    DESCRIPTION     "The number of CIFS IO read operations per second per controller."
    ::= { eqlNASStatsControllerTrafficRateEntry 19 }

eqlNASStatsControllerTrafficRateCifsIOPSWrite OBJECT-TYPE
    SYNTAX          Unsigned32
    MAX-ACCESS      read-only
    STATUS          current
    DESCRIPTION     "The number of CIFS IO write operations per second per controller."
    ::= { eqlNASStatsControllerTrafficRateEntry 20 }

eqlNASStatsControllerTrafficRateCifsIOPSOther OBJECT-TYPE
    SYNTAX          Unsigned32
    MAX-ACCESS      read-only
    STATUS          current
    DESCRIPTION     "The number of CIFS IO other operations per second per controller."
    ::= { eqlNASStatsControllerTrafficRateEntry 21 }

eqlNASStatsControllerTrafficRateTotalPrimaryMBsPerSec OBJECT-TYPE
    SYNTAX          Unsigned32
    MAX-ACCESS      read-only
    STATUS          current
    DESCRIPTION     "The total primary MBs per second per controller."
    ::= { eqlNASStatsControllerTrafficRateEntry 22 }


eqlNASStatsControllerTrafficRateTotalPrimaryMBsPerSecToAverage OBJECT-TYPE
    SYNTAX          Unsigned32
    MAX-ACCESS      read-only
    STATUS          current
    DESCRIPTION     "The total primary MBs per second average per controller."
    ::= { eqlNASStatsControllerTrafficRateEntry 23 }

eqlNASStatsControllerTrafficRateTotalSecondaryMBsPerSec OBJECT-TYPE
    SYNTAX          Unsigned32
    MAX-ACCESS      read-only
    STATUS          current
    DESCRIPTION     "The total secondary MBs per second per controller."
    ::= { eqlNASStatsControllerTrafficRateEntry 24 }



--------------------------------------------------------------------------------------------

eqlNASStatsControllerLoadBalancingTable OBJECT-TYPE
    SYNTAX          SEQUENCE OF EqlNASStatsControllerLoadBalancingEntry
    MAX-ACCESS      not-accessible
    STATUS          current
    DESCRIPTION     "EqualLogic-Dynamic
                     NAS controller load balancing statistics table.
                     TimeoutAll:60"
    ::=    { eqlNASStatsControllerTrafficRateTable 2 }

eqlNASStatsControllerLoadBalancingEntry OBJECT-TYPE
    SYNTAX          EqlNASStatsControllerLoadBalancingEntry
    MAX-ACCESS      not-accessible
    STATUS          current
    DESCRIPTION     "An entry (row) containing controller load balancing statistics."
    INDEX           { eqlApplianceIndex, eqlNASStatsControllerLoadBalancingIndex }

    ::=   { eqlNASStatsControllerLoadBalancingTable 1 }

EqlNASStatsControllerLoadBalancingEntry ::=
    SEQUENCE {
        eqlNASStatsControllerLoadBalancingIndex            Unsigned32,
    	eqlNASStatsControllerLoadBalancingTimestamp        Counter32,
        eqlNASStatsControllerCPULoadPercent                Unsigned32,
	eqlNASStatsControllerTotalCifsConnections          Unsigned32
    }

eqlNASStatsControllerLoadBalancingIndex   OBJECT-TYPE
    SYNTAX          Unsigned32
    MAX-ACCESS      read-only
    STATUS          current
    DESCRIPTION     "NAS controller index."
    ::= { eqlNASStatsControllerLoadBalancingEntry 1 }

eqlNASStatsControllerLoadBalancingTimestamp OBJECT-TYPE
    SYNTAX          Counter32
    MAX-ACCESS      read-only
    STATUS          current
    DESCRIPTION     "This field specifies the date/time when the statistics were collected.
                     Time is represented as the time in seconds since 00:00:00 UTC, 1970-01-01."
    ::= { eqlNASStatsControllerLoadBalancingEntry 2 }

eqlNASStatsControllerCPULoadPercent   OBJECT-TYPE
    SYNTAX          Unsigned32
    UNITS            "%"
    MAX-ACCESS      read-only
    STATUS          current
    DESCRIPTION     "The percentage of time the CPU is executing instructions."
    ::= { eqlNASStatsControllerLoadBalancingEntry 3 }

eqlNASStatsControllerTotalCifsConnections OBJECT-TYPE
    SYNTAX          Unsigned32
    MAX-ACCESS      read-only
    STATUS          current
    DESCRIPTION     "The total number of CIFS connections terminated on the controller."
    ::= { eqlNASStatsControllerLoadBalancingEntry 4 }

-----------------------------------------------------------------------------------------------

eqlNASCacheInfoTable OBJECT-TYPE
    SYNTAX          SEQUENCE OF EqlNASCacheInfoEntry
    MAX-ACCESS      not-accessible
    STATUS          current
    DESCRIPTION     "EqualLogic-Dynamic
                     This table contains NAS Cache information.
                     TimeoutAll:60"
    ::=    { eqlNASObjects 40 }

eqlNASCacheInfoEntry OBJECT-TYPE
    SYNTAX          EqlNASCacheInfoEntry
    MAX-ACCESS      not-accessible
    STATUS          current
    DESCRIPTION     "An entry (row) containing NAS cache information."
    INDEX           { eqlApplianceIndex, eqlNASCacheInfoIndex }

    ::=   { eqlNASCacheInfoTable 1 }

EqlNASCacheInfoEntry ::=
    SEQUENCE {
        eqlNASCacheInfoIndex                    Unsigned32,
        eqlNASCacheInfoCacheObjectName          OCTET STRING,
        eqlNASCacheInfoCacheObjectExpiryTime    Unsigned32,
        eqlNASCacheInfoCacheObjectState         OCTET STRING,
        eqlNASCacheInfoAction                   INTEGER
    }

eqlNASCacheInfoIndex   OBJECT-TYPE
    SYNTAX          Unsigned32
    MAX-ACCESS      read-only
    STATUS          current
    DESCRIPTION     "Cache index of the cached index."
    ::= { eqlNASCacheInfoEntry 1 }

eqlNASCacheInfoCacheObjectName  OBJECT-TYPE
    SYNTAX          OCTET STRING (SIZE (1..64))
    MAX-ACCESS      read-only
    STATUS          current
    DESCRIPTION     "Name of the cached object."
    ::= { eqlNASCacheInfoEntry  2 }

eqlNASCacheInfoCacheObjectExpiryTime   OBJECT-TYPE
    SYNTAX          Unsigned32
    MAX-ACCESS      read-write
    STATUS          current
    DESCRIPTION     "Cache refresh time in seconds. A value of 0 means this is a persistent cache."
    ::= { eqlNASCacheInfoEntry 3 }

eqlNASCacheInfoCacheObjectState  OBJECT-TYPE
    SYNTAX          OCTET STRING (SIZE (1..64))
    MAX-ACCESS      read-write
    STATUS          current
    DESCRIPTION     "Current cached object state."
    ::= { eqlNASCacheInfoEntry  4 }

eqlNASCacheInfoAction OBJECT-TYPE
    SYNTAX          INTEGER{
                    none          (0),
                    refresh-all   (1), --refresh all the cached objects
                    refresh       (2), --refresh this cache object
                    restart-agent (3)  --restart NAS agent
    }
    MAX-ACCESS      read-write
    STATUS          current
    DESCRIPTION     "Action on this NAS cache."
    ::=   { eqlNASCacheInfoEntry 5 }
---------------------------------------------------------------------------------------------------
eqlNASReplHistoryTable OBJECT-TYPE
    SYNTAX          SEQUENCE OF EqlNASReplHistoryEntry
    MAX-ACCESS      not-accessible
    STATUS          current
    DESCRIPTION     "EqualLogic-Dynamic table used to hold NAS replication history data.
                    Used with FluidFS version 3.0 and later versions. For FluidFS version 2.0
                    the table eqlNASReplicationHistory is used instead."
    ::= { eqlNASObjects 41 }

eqlNASReplHistoryEntry OBJECT-TYPE
    SYNTAX          EqlNASReplHistoryEntry
    MAX-ACCESS      not-accessible
    STATUS          current
    DESCRIPTION     "An entry (row) containing the NAS Replication history information."
    INDEX           { eqlApplianceIndex, eqlNASContainerIndex, eqlNASReplHistoryUniqueId }
    ::=   { eqlNASReplHistoryTable 1 }

EqlNASReplHistoryEntry ::=
    SEQUENCE {
        eqlNASReplHistoryUniqueId            Unsigned32,
        eqlNASReplHistoryEventTime           Integer32,
        eqlNASReplHistorySourceContainerName NASContainerNameType,
        eqlNASReplHistorySourceClusterName   ClusterNameType,
        eqlNASReplHistoryDestContainerName   NASContainerNameType,
        eqlNASReplHistoryDestClusterName     ClusterNameType,
        eqlNASReplHistoryStartTime           Integer32,
        eqlNASReplHistoryEndTime             Integer32,
        eqlNASReplHistoryTransferredMb       Counter32,
        eqlNASReplHistoryStatus              EqlNASReplicationStatus
    }

eqlNASReplHistoryUniqueId OBJECT-TYPE
   SYNTAX        Unsigned32
   MAX-ACCESS    read-only
   STATUS        current
   DESCRIPTION "Unique ID assigned by Fluid FS 3.0 software"
::= { eqlNASReplHistoryEntry 1 }

eqlNASReplHistoryEventTime   OBJECT-TYPE
   SYNTAX        Integer32
   MAX-ACCESS    read-only
   STATUS        current
   DESCRIPTION "Time when event was recorded by the FluidFS. Often the same as the end time."
::= { eqlNASReplHistoryEntry 2 }

eqlNASReplHistorySourceContainerName OBJECT-TYPE
    SYNTAX          NASContainerNameType
    MAX-ACCESS      read-only
    STATUS          current
    DESCRIPTION     "Name of source NAS container being replicated."
    ::= { eqlNASReplHistoryEntry 3 }

eqlNASReplHistorySourceClusterName OBJECT-TYPE
    SYNTAX          ClusterNameType
    MAX-ACCESS      read-only
    STATUS          current
    DESCRIPTION     "Name of source cluster where source container exists. This is not currenlty required
                    so if memory is limited, this could be deleted from the MIB."
    ::= { eqlNASReplHistoryEntry 4 }

eqlNASReplHistoryDestContainerName OBJECT-TYPE
    SYNTAX          NASContainerNameType
    MAX-ACCESS      read-only
    STATUS          current
    DESCRIPTION     "Name of destination NAS container receiving replication data"
    ::= { eqlNASReplHistoryEntry 5 }

eqlNASReplHistoryDestClusterName OBJECT-TYPE
    SYNTAX          ClusterNameType
    MAX-ACCESS      read-only
    STATUS          current
    DESCRIPTION     "Name of destination cluster where destionation container exists"
    ::= { eqlNASReplHistoryEntry 6 }

eqlNASReplHistoryStartTime       OBJECT-TYPE
    SYNTAX          Integer32
    MAX-ACCESS      read-only
    STATUS          current
    DESCRIPTION     "Start time for replication"
    ::= { eqlNASReplHistoryEntry 7 }

eqlNASReplHistoryEndTime       OBJECT-TYPE
    SYNTAX          Integer32
    MAX-ACCESS      read-only
    STATUS          current
    DESCRIPTION     "End time for replication"
    ::= { eqlNASReplHistoryEntry 8 }

eqlNASReplHistoryTransferredMb OBJECT-TYPE
    SYNTAX          Counter32
    MAX-ACCESS      read-only
    STATUS          current
    DESCRIPTION     "Number of megabytes transferred."
    ::= { eqlNASReplHistoryEntry 9 }

eqlNASReplHistoryStatus OBJECT-TYPE
    SYNTAX EqlNASReplicationStatus
    MAX-ACCESS      read-only
    STATUS          current
    DESCRIPTION     "The status of this replication relationship. Mainly use value 'finished' or 'failed'."
    ::= { eqlNASReplHistoryEntry 10 }

---------------------------------------------------------------------------------------------------

eqlNASTaskTable OBJECT-TYPE
    SYNTAX  SEQUENCE OF EqlNASTaskEntry
    MAX-ACCESS      not-accessible
    STATUS          current
    DESCRIPTION     "EqualLogic-Persistent task table.
                     A row in this table represents a task currently executing in the NAS."
    ::=    { eqlNASObjects 42 }

eqlNASTaskEntry OBJECT-TYPE
    SYNTAX          EqlNASTaskEntry
    MAX-ACCESS      not-accessible
    STATUS          current
    DESCRIPTION     "A row in the table represents a task. Any given task will have multiple sub tasks. Each sub task involves executing a management operation.  The system will execute each sub task one after another until the task is completed."
    INDEX           { eqlApplianceIndex, eqlNASTaskIndex }
    ::=    { eqlNASTaskTable 1 }

EqlNASTaskEntry ::=
    SEQUENCE {
        eqlNASTaskIndex             Unsigned32,
        eqlNASTaskRowStatus         RowStatus,
        eqlNASTaskType              INTEGER,
        eqlNASTaskContext           OCTET STRING,
        eqlNASTaskNumSubTasks       Unsigned32,
        eqlNASTaskSubTaskInProgress INTEGER,
        eqlNASTaskSubtaskStatus     Unsigned32,
        eqlNASTaskStatus            INTEGER,
        eqlNASTaskUserAction        INTEGER,
        eqlNASTaskStartTime         Counter32
        }

eqlNASTaskIndex OBJECT-TYPE
    SYNTAX          Unsigned32
    MAX-ACCESS      not-accessible
    STATUS          current
    DESCRIPTION     "This field specifies an index that uniquely identifies a task."
    ::=  {  eqlNASTaskEntry 1 }


eqlNASTaskRowStatus OBJECT-TYPE
    SYNTAX          RowStatus
    MAX-ACCESS      read-create
    STATUS          current
    DESCRIPTION     "This field is used to manage the conceptual row."
    ::=  {  eqlNASTaskEntry 2 }
eqlNASTaskType OBJECT-TYPE
    SYNTAX          INTEGER {
                    resync(1),
                    failback(2)
                    }
    MAX-ACCESS      read-create
    STATUS          current
    DESCRIPTION     "This field represents the type of the task."
    ::=  {  eqlNASTaskEntry 3 }

eqlNASTaskContext OBJECT-TYPE
    SYNTAX          OCTET STRING(SIZE(1..256))
    MAX-ACCESS      read-create
    STATUS          current
    DESCRIPTION     "A generic task context"
    ::= { eqlNASTaskEntry 4 }

eqlNASTaskNumSubTasks OBJECT-TYPE
    SYNTAX          Unsigned32
    MAX-ACCESS      read-create
    STATUS          current
    DESCRIPTION     "Number of subtasks in this task."
    ::= { eqlNASTaskEntry 5 }

eqlNASTaskSubTaskInProgress OBJECT-TYPE
    SYNTAX          INTEGER {
                    none(0),
                    -- subtasks involved in resync (Replicate to Partner) task
                    resync-primaryContainerPromote(100),
                    resync-primaryContainerReplicationDelete(110),
                    resync-recoveryContainerReplicationConfigure(120),
                    resync-recoveryContainerReplicate(130),
                    resync-recoveryContainerSourcePromote(140),
		            resync-recoveryContainerReplicationDelete(150),
		            resync-primaryContainerReplicationConfigure(160),
		            resync-recoveryContainerPromote(170),
                    -- subtasks involved in failback task
                    failback-primaryContainerPromote(300),
                    failback-primaryContainerReplicationDelete(310),
                    failback-recoveryContainerReplicationConfigure(320),
                    failback-recoveryContainerDisableSchedules(330),
		            failback-recoveryContainerReplicate(340),
                    failback-recoveryContainerFinalReplication(350),
                    failback-recoveryContainerPromote(360),
                    failback-recoveryContainerReplicationDelete(370),
                    failback-primaryContainerReplicationConfigure(380),
		            complete(10000)
                    }
    MAX-ACCESS      read-create
    STATUS          current
    DESCRIPTION     "Subtask that is currently in progress for this task."
    ::= { eqlNASTaskEntry 6 }


eqlNASTaskSubtaskStatus OBJECT-TYPE
    SYNTAX          Unsigned32
    MAX-ACCESS      read-create
    STATUS          current
    DESCRIPTION     "Status of currently executing subtask."
    ::= { eqlNASTaskEntry 7 }

eqlNASTaskStatus OBJECT-TYPE
    SYNTAX          INTEGER {
            user-action-required(1),
            in-progress(2),
            complete(3)
    }
    MAX-ACCESS      read-create
    STATUS          current
    DESCRIPTION     "set to true if user action is required for the task to proceed further."
    ::= { eqlNASTaskEntry 8 }

eqlNASTaskUserAction OBJECT-TYPE
    SYNTAX          INTEGER{
                    retry(1)
    }
    MAX-ACCESS      read-create
    STATUS          current
    DESCRIPTION     "user action on the task."
    ::= { eqlNASTaskEntry 9 }

eqlNASTaskStartTime OBJECT-TYPE
    SYNTAX          Counter32
    UNITS           "seconds"
    MAX-ACCESS      read-create
    STATUS          current
    DESCRIPTION     "time at which this task started represented as number of seconds since epoch."
    ::= { eqlNASTaskEntry 10 }



---------------------------------------------------------------------------------------------------

eqlNASTaskContainerReplInfoTable OBJECT-TYPE
    SYNTAX        SEQUENCE OF EqlNASTaskContainerReplInfoEntry
    MAX-ACCESS    not-accessible
    STATUS        current
    DESCRIPTION
     "EqualLogic-Persistent
     TimeoutAll:60
     This table is used to track the replication relationship on the NAS Container which has a NAS task"
::= { eqlNASObjects 43 }

eqlNASTaskContainerReplInfoEntry OBJECT-TYPE
    SYNTAX        EqlNASTaskContainerReplInfoEntry
    MAX-ACCESS    not-accessible
    STATUS        current
    DESCRIPTION
      ""
    INDEX           { eqlApplianceIndex, eqlNASContainerIndex, eqlNASReplSiteRemoteClusterId, eqlNASTaskContainerReplInfoRemoteFSId }
::= { eqlNASTaskContainerReplInfoTable 1 }

EqlNASTaskContainerReplInfoEntry  ::= SEQUENCE {
   eqlNASTaskContainerReplInfoRowStatus            RowStatus,
   eqlNASTaskContainerReplInfoRemoteFSId           Unsigned32,
   eqlNASTaskContainerReplInfoVolumeReplSiteIndex  SiteIndex,
   eqlNASTaskContainerReplInfoRemoteClusterName    OCTET STRING,
   eqlNASTaskContainerReplInfoLocalFSName          OCTET STRING,
   eqlNASTaskContainerReplInfoRemoteFSName         OCTET STRING,
   eqlNASTaskContainerReplInfoLocalClusterId       ClusterIdType,
   eqlNASTaskContainerReplInfoTaskId               Unsigned32
}

eqlNASTaskContainerReplInfoRowStatus OBJECT-TYPE
   SYNTAX RowStatus
   MAX-ACCESS    read-create
   STATUS        current
   DESCRIPTION
      "The status of the row"
::= { eqlNASTaskContainerReplInfoEntry 1 }

eqlNASTaskContainerReplInfoRemoteFSId OBJECT-TYPE
    SYNTAX          Unsigned32
    MAX-ACCESS      read-only
    STATUS          current
    DESCRIPTION     "Unique Identifier for the remote container. This is the FSid."
::= { eqlNASTaskContainerReplInfoEntry 2 }

eqlNASTaskContainerReplInfoVolumeReplSiteIndex OBJECT-TYPE
    SYNTAX          SiteIndex
    MAX-ACCESS      read-create
    STATUS          current
    DESCRIPTION     "The value of eqliscsiVolumeReplSiteIndex to index into
                     eqliscsiVolumeReplSiteTable."
::= { eqlNASTaskContainerReplInfoEntry 3 }

eqlNASTaskContainerReplInfoRemoteClusterName OBJECT-TYPE
    SYNTAX          OCTET STRING (SIZE (1..64))
    MAX-ACCESS      read-only
    STATUS          current
    DESCRIPTION     "This field specifies the remote cluster name, which is the
                     eqlApplianceName of the remote cluster."
::= { eqlNASTaskContainerReplInfoEntry 4 }

eqlNASTaskContainerReplInfoLocalFSName       OBJECT-TYPE
    SYNTAX          OCTET STRING (SIZE (1..230))
    MAX-ACCESS      read-create
    STATUS          current
    DESCRIPTION     "Name used to identify the local NAS Container. Contains
                     only letters, digits and underscores. Must begin with either
                     letter or an underscore. "
::= { eqlNASTaskContainerReplInfoEntry 5 }


eqlNASTaskContainerReplInfoRemoteFSName       OBJECT-TYPE
    SYNTAX          OCTET STRING (SIZE (1..230))
    MAX-ACCESS      read-create
    STATUS          current
    DESCRIPTION     "Name used to identify the remote NAS Container. Contains
                     only letters, digits and underscores. Must begin with either
                     letter or an underscore. "
::= { eqlNASTaskContainerReplInfoEntry 6 }

eqlNASTaskContainerReplInfoLocalClusterId OBJECT-TYPE
    SYNTAX        ClusterIdType
    MAX-ACCESS    read-write
    STATUS        current
    DESCRIPTION "Local Cluster Id."
::= { eqlNASTaskContainerReplInfoEntry 7 }


eqlNASTaskContainerReplInfoTaskId OBJECT-TYPE
    SYNTAX          Unsigned32
    MAX-ACCESS      read-create
    STATUS          current
    DESCRIPTION     "This field specifies an Id that uniquely identifies a task."
    ::=  {  eqlNASTaskContainerReplInfoEntry 8 }

-----------------------------------------------------------------------------------------------

eqlNASLostContainerTable OBJECT-TYPE
    SYNTAX          SEQUENCE OF EqlNASLostContainerEntry
    MAX-ACCESS      not-accessible
    STATUS          current
    DESCRIPTION     "EqualLogic-Dynamic Appliance Table.
                     This table contains a list of NAS Appliance configurations for containers lost during a configuration restore.
                     TimeoutAll:60"
    ::=    { eqlNASObjects 44 }

eqlNASLostContainerEntry OBJECT-TYPE
    SYNTAX          EqlNASLostContainerEntry
    MAX-ACCESS      not-accessible
    STATUS          current
    DESCRIPTION     "An entry (row) containing NAS Lost Container info."
    INDEX           { eqlApplianceIndex, eqlNASContainerIndex }

    ::=   { eqlNASLostContainerTable 1}

EqlNASLostContainerEntry ::=
    SEQUENCE {
	eqlNASLostContainerRowStatus                 RowStatus,
	eqlNASLostContainerName                      OCTET STRING,
	eqlNASLostContainerCapacity                  Unsigned32,
	eqlNASLostContainerUsedSpaceAlert            Unsigned32,
	eqlNASLostContainerSnapshotUsedSpaceAlert    Unsigned32
    }

eqlNASLostContainerRowStatus OBJECT-TYPE
    SYNTAX          RowStatus
    MAX-ACCESS      read-create
    STATUS          current
    DESCRIPTION     "Row status variable used to manage this row."
    ::= { eqlNASLostContainerEntry 1 }

eqlNASLostContainerName OBJECT-TYPE
    SYNTAX          OCTET STRING (SIZE (1..230))
    MAX-ACCESS      read-create
    STATUS          current
    DESCRIPTION     "Name used to identify NAS Container. Contains only letters, digits and underscores. Must begin with either letter or an underscore. "
    ::=  {  eqlNASLostContainerEntry 2 }

eqlNASLostContainerCapacity OBJECT-TYPE
    SYNTAX          Unsigned32
    UNITS           "MB"
    MAX-ACCESS      read-create
    STATUS          current
    DESCRIPTION     "Size of NAS Container in MB."
    ::= { eqlNASLostContainerEntry 3 }

eqlNASLostContainerUsedSpaceAlert OBJECT-TYPE
    SYNTAX          Unsigned32
    UNITS           "%"
    MAX-ACCESS      read-create
    STATUS          current
    DESCRIPTION     "Alert user when NAS container used space reaches certain % value of NAS container size.Default value is choosen from eqlNASApplianceConfigUsedSpaceAlert"
    ::= { eqlNASLostContainerEntry 4 }

eqlNASLostContainerSnapshotUsedSpaceAlert OBJECT-TYPE
    SYNTAX          Unsigned32
    UNITS           "%"
    MAX-ACCESS      read-create
    STATUS          current
    DESCRIPTION     "Alert user when NAS container snapshot used space reaches certain % value of NAS container snapshot size.Default value is choosen from eqlNASApplianceConfigSnapSpaceAlert "
    ::= { eqlNASLostContainerEntry 5 }

-----------------------------------------------------------------------------------------------
eqlNASSanStaticRouteTable OBJECT-TYPE
    SYNTAX        SEQUENCE OF EqlNASSanStaticRouteEntry
    MAX-ACCESS    not-accessible
    STATUS        current
    DESCRIPTION
     "EqualLogic-Dynamic
      This table is used to manage static route entries on NAS cluster. The
      static route entries are used to route SAN traffic from cluster members
      to gateways on the SAN network.
      TimeoutAll:60"
::= { eqlNASObjects 45 }

eqlNASSanStaticRouteEntry OBJECT-TYPE
    SYNTAX        EqlNASSanStaticRouteEntry
    MAX-ACCESS    not-accessible
    STATUS        current
    DESCRIPTION
      ""
    INDEX           { eqlApplianceIndex, eqlApplianceNetworkID,
                      eqlNASSanStaticRouteNetworkAddrType, eqlNASSanStaticRouteNetworkAddr,
                      eqlNASSanStaticRouteNetworkMaskType, eqlNASSanStaticRouteNetworkMask}
::= { eqlNASSanStaticRouteTable 1 }

EqlNASSanStaticRouteEntry ::= SEQUENCE {
   eqlNASSanStaticRouteRowStatus       RowStatus,
   eqlNASSanStaticRouteNetworkAddrType InetAddressType,
   eqlNASSanStaticRouteNetworkAddr     InetAddress,
   eqlNASSanStaticRouteNetworkMaskType InetAddressType,
   eqlNASSanStaticRouteNetworkMask     InetAddress,
   eqlNASSanStaticRouteGatewayAddrType InetAddressType,
   eqlNASSanStaticRouteGatewayAddr     InetAddress
}

eqlNASSanStaticRouteRowStatus OBJECT-TYPE
   SYNTAX RowStatus
   MAX-ACCESS    read-create
   STATUS        current
   DESCRIPTION
      "The status of the row"
::= { eqlNASSanStaticRouteEntry 1 }

eqlNASSanStaticRouteNetworkAddrType OBJECT-TYPE
   SYNTAX          InetAddressType
   MAX-ACCESS      read-create
   STATUS          current
   DESCRIPTION     "This field specifies the type of address (v4/v6) for the
                    Network address of the static route."
::= { eqlNASSanStaticRouteEntry 2 }

eqlNASSanStaticRouteNetworkAddr OBJECT-TYPE
   SYNTAX          InetAddress
   MAX-ACCESS      read-create
   STATUS          current
   DESCRIPTION     "This field contains the Network IP address for the static
                    route (e.g., 200.200.200.0)"
::= { eqlNASSanStaticRouteEntry 3 }

eqlNASSanStaticRouteNetworkMaskType OBJECT-TYPE
   SYNTAX          InetAddressType
   MAX-ACCESS      read-create
   STATUS          current
   DESCRIPTION     "This field specifies the type (v4/v6) for the
                    Network mask of the static route."
::= { eqlNASSanStaticRouteEntry 4 }

eqlNASSanStaticRouteNetworkMask OBJECT-TYPE
   SYNTAX          InetAddress
   MAX-ACCESS      read-create
   STATUS          current
   DESCRIPTION     "This field contains the Network mask for the static route
                    (e.g., 255.255.255.0). The IP address type of the mask is
                    assumed to be the same as that of the network address"
::= { eqlNASSanStaticRouteEntry 5 }

eqlNASSanStaticRouteGatewayAddrType OBJECT-TYPE
   SYNTAX          InetAddressType
   MAX-ACCESS      read-create
   STATUS          current
   DESCRIPTION     "This field specifies the type of address (v4/v6) of the
                    gateway IP address."
::= { eqlNASSanStaticRouteEntry 6 }

eqlNASSanStaticRouteGatewayAddr OBJECT-TYPE
   SYNTAX          InetAddress
   MAX-ACCESS      read-create
   STATUS          current
   DESCRIPTION     "This field contains the gateway IP address for the static
                    route (e.g., 10.127.20.30)"
::= { eqlNASSanStaticRouteEntry 7 }

END
