-- *****************************************************************
-- FS-ND-MIB.mib:  FS ND MIB file
--
--  2013.12.30, huangguohua@fs.com.cn
--
-- Copyright (c) 2013 by FS Networks .
-- All rights reserved.
--
-- *****************************************************************
--

FS-ND-MIB DEFINITIONS ::= BEGIN

IMPORTS
        MODULE-IDENTITY,
        OBJECT-TYPE,
        NOTIFICATION-TYPE
                FROM SNMPv2-SMI
        Integer32
                FROM SNMPv2-SMI
        MODULE-COMPLIANCE,
        OBJECT-GROUP,
        NOTIFICATION-GROUP
                FROM SNMPv2-CONF
        fsMgmt
                FROM FS-SMI;

fsNDMIB MODULE-IDENTITY
        LAST-UPDATED "201312300000Z"
        ORGANIZATION "FS Networks."
        CONTACT-INFO
                "
                Tel: 400-865-2852

                E-mail: https://www.fs.com/live_chat_service_mail.html"
        DESCRIPTION
                "This module defines fs ND mibs."
        REVISION      "201312300000Z"
        DESCRIPTION
                "Initial version of this MIB module."
        ::= { fsMgmt 125}

fsNDMIBObjects OBJECT IDENTIFIER ::= { fsNDMIB 1 }

   fsNDTotalActiveNeighbors OBJECT-TYPE
        SYNTAX Counter32
        MAX-ACCESS read-only
        STATUS current
        DESCRIPTION
            "Total active neighbors This system have"
        ::= { fsNDMIBObjects 1 }

  fsNDTotalActiveDynamicNeighbors OBJECT-TYPE
          SYNTAX Counter32
          MAX-ACCESS read-only
          STATUS current
          DESCRIPTION
            "Total active dynamic neighbors This system have"
          ::= { fsNDMIBObjects 2}

   fsNDTotalStaticNeighbors OBJECT-TYPE
        SYNTAX Counter32
        MAX-ACCESS read-only
        STATUS current
        DESCRIPTION
            "Total static neighbors This system configure"
        ::= { fsNDMIBObjects 3 }

   fsNDTotalActiveStaticNeighbors OBJECT-TYPE
        SYNTAX Counter32
        MAX-ACCESS read-only
        STATUS current
        DESCRIPTION
            "Total active static neighbors This system have"
        ::= { fsNDMIBObjects 4 }


fsNDMIBConformance OBJECT IDENTIFIER ::= { fsNDMIB 2}
fsNDMIBCompliances OBJECT IDENTIFIER ::= { fsNDMIBConformance 1 }
fsNDMIBGroups      OBJECT IDENTIFIER ::= { fsNDMIBConformance 2 }

-- compliance statements

fsNDMIBCompliance MODULE-COMPLIANCE
        STATUS  current
        DESCRIPTION
                "The compliance statement for entities which implement
                the FS ND MIB"
        MODULE  -- this module
                MANDATORY-GROUPS {
                        fsNDObjectsGroup
                 }
         ::= { fsNDMIBCompliances 1 }

-- units of conformance

fsNDObjectsGroup OBJECT-GROUP
       OBJECTS {
	       fsNDTotalActiveNeighbors,
           fsNDTotalActiveDynamicNeighbors,
		   fsNDTotalStaticNeighbors,
		   fsNDTotalActiveStaticNeighbors
       }
       STATUS  current
       DESCRIPTION
                "A collection of objects providing ND information to a
                FS agent."
       ::= { fsNDMIBGroups 1 }

END
