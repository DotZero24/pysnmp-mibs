-- *****************************************************************
-- FS-MPLS-SIGNAL-MIB.mib:  FS MPLS Signal MIB file
--
-- MAY 2011, Liujinhui
--
-- Copyright (c) 2011 by FS.COM Inc..
-- All rights reserved.
--
-- *****************************************************************
--

FS-MPLS-SIGNAL-MIB DEFINITIONS ::= BEGIN


IMPORTS
        MODULE-IDENTITY,
        OBJECT-TYPE,
        TimeTicks,
        IpAddress,
        Unsigned32,
        Gauge32,
        Counter32
                FROM SNMPv2-SMI
        TruthValue,
        DisplayString,
        RowStatus
                FROM SNMPv2-TC
        TimeStamp
                FROM SNMPv2-TC          -- [RFC2579]
        InetAddressPrefixLength,
        InetAddressType,
        InetAddress,
        InetPortNumber
             FROM INET-ADDRESS-MIB      --  [RFC3291]
        MODULE-COMPLIANCE,
        OBJECT-GROUP
                FROM SNMPv2-CONF
        ConfigStatus
                FROM FS-TC
        EnabledStatus
                FROM P-BRIDGE-MIB
        AreaID,
        Status,
        PositiveInteger,
        DesignatedRouterPriority,
        RouterID,
        HelloRange
                FROM OSPF-MIB
        fsMgmt
                FROM FS-SMI;

fsMplsSignalMIB MODULE-IDENTITY
        LAST-UPDATED "201105150000Z"
        ORGANIZATION "FS.COM Inc.."
        CONTACT-INFO
                "
                Tel: 400-865-2852

                E-mail: https://www.fs.com/live_chat_service_mail.html"
        DESCRIPTION
                "This module defines fs mpls signal mibs."
        REVISION      "201105150000Z"
        DESCRIPTION
                "Initial version of this MIB module."
        ::= { fsMgmt 98}

fsMplsSignalMIBObjects OBJECT IDENTIFIER ::= { fsMplsSignalMIB 1 }
--****************************************************************

fsMplsSignalObjects       OBJECT IDENTIFIER ::= { fsMplsSignalMIBObjects 1 }
fsMplsSignalConformance   OBJECT IDENTIFIER ::= { fsMplsSignalMIBObjects 2 }

--****************************************************************
-- MPLS Signale Objects
--****************************************************************

fsMplsSignalmplsGernalMibObjects  OBJECT IDENTIFIER ::= { fsMplsSignalObjects 1 }
fsMplsSignalConfigMibObjects      OBJECT IDENTIFIER ::= { fsMplsSignalObjects 2 }

fsMplsVersion OBJECT-TYPE
    SYNTAX  Unsigned32
    MAX-ACCESS read-only
    STATUS current
    DESCRIPTION
           "Current mpls version used."
     ::={ fsMplsSignalmplsGernalMibObjects 1 }
fsMPLSSignal    OBJECT-TYPE
    SYNTAX  INTEGER {
                     ldp(1),
                     rsvp-te(2),
                     cr-ldp(3),
                     other(4)
                       }
    MAX-ACCESS read-only
    STATUS current
    DESCRIPTION
           "MPLS signal we support."
     ::={ fsMplsSignalmplsGernalMibObjects 2 }
fsMPLSTESignal     OBJECT-TYPE
    SYNTAX      TruthValue
    MAX-ACCESS read-only
    STATUS current
    DESCRIPTION
          "Enable TE or not."
    ::={ fsMplsSignalmplsGernalMibObjects 3 }

fsMPLSConfigLspNum  OBJECT-TYPE
    SYNTAX  Unsigned32
    MAX-ACCESS read-only
    STATUS current
    DESCRIPTION
           "The number of static LSP configuration."
     ::={ fsMplsSignalConfigMibObjects 1 }

fsMPLSActiveLspNum  OBJECT-TYPE
    SYNTAX  Unsigned32
    MAX-ACCESS read-only
    STATUS current
    DESCRIPTION
           "Total number of active LSP."
     ::={ fsMplsSignalConfigMibObjects 2 }

fsMPLSAdministrativeGroupTable OBJECT-TYPE
    SYNTAX SEQUENCE OF FSMPLSAdministrativeGroupEntry
    MAX-ACCESS not-accessible
    STATUS current
    DESCRIPTION
        "Information describing the configured  parame-ters
         and cumulative statistics of the LSP Administrative Group."
    ::= { fsMplsSignalObjects 3}

fsMPLSAdministrativeGroupEntry OBJECT-TYPE
    SYNTAX FSMPLSAdministrativeGroupEntry
    MAX-ACCESS not-accessible
    STATUS current
    DESCRIPTION
            "The entry of fsMPLSAdministrativeGroupTable."
    INDEX { fsMPLSFecIndex }
    ::= { fsMPLSAdministrativeGroupTable 1 }

FSMPLSAdministrativeGroupEntry ::=
    SEQUENCE {
      fsMPLSFecIndex                INTEGER,
      fsMPLSLSPName                 DisplayString,
      fsMPLSLSPStates               INTEGER,
      fsMPLSLSPForwardBytes         INTEGER,
      fsMPLSLSPForwardPackets       INTEGER,
      fsMPLSLSPActiveTime           TimeStamp,
      fsMPLSLSPCreationTime         TimeStamp,
      fsMPLSLSPPrimaryCreationTime  TimeStamp,
      fsMPLSLSPSwitchTimes          INTEGER,
      fsMPLSLSPLatestSwitchTime     TimeStamp,
      fsMPLSLSPPathchangeTime       TimeStamp,
      fsMPLSLSPConfigChangeTime     TimeStamp,
      fsMPLSLSPBackupPath           DisplayString,
      fsMPLSLSPOperationPath        INTEGER,
      fsMPLSLSPIngress              InetAddressType,
      fsMPLSLSPDestination          InetAddressType,
      fsMPLSLSPAdministrativeGroupName DisplayString
    }

fsMPLSFecIndex OBJECT-TYPE
    SYNTAX  INTEGER
    MAX-ACCESS not-accessible
    STATUS current
    DESCRIPTION
           "The index which uniquely identifies this entry."
     ::={ fsMPLSAdministrativeGroupEntry 1 }

fsMPLSLSPName       OBJECT-TYPE
    SYNTAX  DisplayString
    MAX-ACCESS read-only
    STATUS current
    DESCRIPTION
           "LSP name."
     ::={ fsMPLSAdministrativeGroupEntry 2 }
fsMPLSLSPStates          OBJECT-TYPE
    SYNTAX                 INTEGER {
                                    active(1),
                                    inactive(2)
                                   }
    MAX-ACCESS read-only
    STATUS current
    DESCRIPTION
      "LSP states"
      ::= { fsMPLSAdministrativeGroupEntry 3 }
fsMPLSLSPForwardBytes       OBJECT-TYPE
    SYNTAX  INTEGER
    MAX-ACCESS read-only
    STATUS current
    DESCRIPTION
           "Forwarding bytes by LSP,where 0 means does not support."
     ::={ fsMPLSAdministrativeGroupEntry 4 }

fsMPLSLSPForwardPackets       OBJECT-TYPE
    SYNTAX  INTEGER
    MAX-ACCESS read-only
    STATUS current
    DESCRIPTION
           "Forwarding packets by LSP,where 0 means does not support"
     ::={ fsMPLSAdministrativeGroupEntry 5 }

fsMPLSLSPActiveTime      OBJECT-TYPE
    SYNTAX  TimeStamp
    MAX-ACCESS read-only
    STATUS current
    DESCRIPTION
           "Total LSP Active time."
     ::={ fsMPLSAdministrativeGroupEntry 6 }

fsMPLSLSPCreationTime      OBJECT-TYPE
    SYNTAX  TimeStamp
    MAX-ACCESS read-only
    STATUS current
    DESCRIPTION
           "LSP creation time."
     ::={ fsMPLSAdministrativeGroupEntry 7 }

fsMPLSLSPPrimaryCreationTime      OBJECT-TYPE
    SYNTAX  TimeStamp
    MAX-ACCESS read-only
    STATUS current
    DESCRIPTION
           "Primary LSP creation time."
     ::={ fsMPLSAdministrativeGroupEntry 8 }

fsMPLSLSPSwitchTimes    OBJECT-TYPE
    SYNTAX  INTEGER
    MAX-ACCESS read-only
    STATUS current
    DESCRIPTION
           "Total primary-standby switching times."
     ::={ fsMPLSAdministrativeGroupEntry 9 }

fsMPLSLSPLatestSwitchTime      OBJECT-TYPE
    SYNTAX  TimeStamp
    MAX-ACCESS read-only
    STATUS current
    DESCRIPTION
           "The latest switching time"
     ::={ fsMPLSAdministrativeGroupEntry 10 }

fsMPLSLSPPathchangeTime      OBJECT-TYPE
    SYNTAX  TimeStamp
    MAX-ACCESS read-only
    STATUS current
    DESCRIPTION
           "The latest LSP change time."
     ::={ fsMPLSAdministrativeGroupEntry 11 }

fsMPLSLSPConfigChangeTime      OBJECT-TYPE
    SYNTAX  TimeStamp
    MAX-ACCESS read-only
    STATUS current
    DESCRIPTION
           "The Latest LSP configuration change time."
     ::={ fsMPLSAdministrativeGroupEntry 12 }

fsMPLSLSPBackupPath      OBJECT-TYPE
    SYNTAX  DisplayString
    MAX-ACCESS read-only
    STATUS current
    DESCRIPTION
           "Backup path name."
     ::={ fsMPLSAdministrativeGroupEntry 13 }

fsMPLSLSPOperationPath      OBJECT-TYPE
    SYNTAX  INTEGER {
                    primary(1),
                    backup(2),
                    none(3)
                    }
    MAX-ACCESS read-only
    STATUS current
    DESCRIPTION
           "Operational path which is used"
     ::={ fsMPLSAdministrativeGroupEntry 14 }

fsMPLSLSPIngress        OBJECT-TYPE
    SYNTAX  InetAddressType
    MAX-ACCESS read-only
    STATUS current
    DESCRIPTION
           "LSP ingress."
     ::={ fsMPLSAdministrativeGroupEntry 15 }

fsMPLSLSPDestination        OBJECT-TYPE
    SYNTAX  InetAddressType
    MAX-ACCESS read-only
    STATUS current
    DESCRIPTION
           "LSP egress."
     ::={ fsMPLSAdministrativeGroupEntry 16 }

fsMPLSLSPAdministrativeGroupName     OBJECT-TYPE
    SYNTAX  DisplayString
    MAX-ACCESS read-only
    STATUS current
    DESCRIPTION
           "LSP Administrative Group name."
     ::={ fsMPLSAdministrativeGroupEntry 17 }
END
