-- *****************************************************************
-- FS-OSPF-MIB.mib:  FS Ospf MIB file
--
-- November 2002, ChenXingBin
--
-- Copyright (c) 2002 by FS.COM Inc..
-- All rights reserved.
--
-- *****************************************************************
--

FS-OSPF-MIB DEFINITIONS ::= BEGIN

IMPORTS
        MODULE-IDENTITY,
        OBJECT-TYPE,
        TimeTicks,
        IpAddress,
        Unsigned32,
        Gauge32,
        Counter32
                FROM SNMPv2-SMI
        TruthValue,
        RowStatus
                FROM SNMPv2-TC
        MODULE-COMPLIANCE,
        OBJECT-GROUP
                FROM SNMPv2-CONF
        ConfigStatus
                FROM FS-TC
        EnabledStatus
                FROM P-BRIDGE-MIB
        AreaID,
        Status,
        PositiveInteger,
        DesignatedRouterPriority,
        RouterID,
        HelloRange
                FROM OSPF-MIB
        fsMgmt
                FROM FS-SMI;

fsOspfMIB MODULE-IDENTITY
        LAST-UPDATED "200211200000Z"
        ORGANIZATION "FS.COM Inc.."
        CONTACT-INFO
                "
                Tel: 400-865-2852

                E-mail: https://www.fs.com/live_chat_service_mail.html"
        DESCRIPTION
                "This module defines fs Ospf mibs."
        REVISION      "200211200000Z"
        DESCRIPTION
                "Initial version of this MIB module."
        ::= { fsMgmt 30}

fsOspfMIBObjects OBJECT IDENTIFIER ::= { fsOspfMIB 1 }

-- general mib
fsOspfGeneralMibsGroup OBJECT IDENTIFIER ::= { fsOspfMIBObjects 1 }

--Minimum LSA interval
fsOspfMiniLsaInterval  OBJECT-TYPE
    SYNTAX  Unsigned32
    MAX-ACCESS read-only
    STATUS current
    DESCRIPTION
           "Minimum LSA interval that the two LSA generate."
     ::={ fsOspfGeneralMibsGroup 1 }

--Minimum LSA arrival
fsOspfMiniLsaArrival  OBJECT-TYPE
    SYNTAX  Unsigned32
    MAX-ACCESS read-only
    STATUS current
    DESCRIPTION
           "Minimum LSA Interval of the two LSA arrival."
     ::={ fsOspfGeneralMibsGroup 2 }

--Number of areas in this router
fsOspfAreasNum OBJECT-TYPE
    SYNTAX  Unsigned32
    MAX-ACCESS read-only
    STATUS current
    DESCRIPTION
           "Number of areas in this router"
         ::={ fsOspfGeneralMibsGroup 3 }

fsOspfNormalAreasNum OBJECT-TYPE
    SYNTAX  Unsigned32
    MAX-ACCESS read-only
    STATUS current
    DESCRIPTION
           "Number of normal areas in this router"
         ::={ fsOspfGeneralMibsGroup 4}

fsOspfStubAreasNum OBJECT-TYPE
    SYNTAX  Unsigned32
    MAX-ACCESS read-only
    STATUS current
    DESCRIPTION
           "Number of stub areas in this router"
         ::={ fsOspfGeneralMibsGroup 5 }

fsOspfNssaAreasNum OBJECT-TYPE
    SYNTAX  Unsigned32
    MAX-ACCESS read-only
    STATUS current
    DESCRIPTION
           "Number of nssa areas in this router"
         ::={ fsOspfGeneralMibsGroup 6 }

fsOspfSpfDelay OBJECT-TYPE
    SYNTAX  Unsigned32(0..2147483647)
    MAX-ACCESS read-write
    STATUS current
    DESCRIPTION
           "Ospf Spf shedule time, an integer from 0 to 65535. The default is 5
           seconds,0 means no delay."
    DEFVAL {5}
         ::={ fsOspfGeneralMibsGroup 7 }

fsOspfSpfHoldTime OBJECT-TYPE
    SYNTAX  Unsigned32(0..2147483647)
    MAX-ACCESS read-write
    STATUS current
    DESCRIPTION
           "hold time between two Spfs.an integer from 0 to 65535. The default is
            10 seconds; 0 means no delay."
    DEFVAL {10}
         ::={ fsOspfGeneralMibsGroup 8 }

fsOspfAutoCostRefBandWidthRef OBJECT-TYPE
    SYNTAX  Unsigned32(0..2147483647)
    MAX-ACCESS read-write
    STATUS current
    DESCRIPTION
           "Set AutoCost bandwidth referenc value in unit of Mbits.
            Setting this value to 0 indicate that disable the feature of
            autocost bandwidth referenc."
    DEFVAL {100}
         ::={ fsOspfGeneralMibsGroup 9 }

fsOspfLsaGroupPacing OBJECT-TYPE
    SYNTAX  Unsigned32(10..1800)
    MAX-ACCESS read-write
    STATUS current
    DESCRIPTION
           "set  the group pacing of LSAs."
    DEFVAL {240}
         ::={ fsOspfGeneralMibsGroup 10}

fsOspfInterDistance OBJECT-TYPE
     SYNTAX   Unsigned32(1..255)
     MAX-ACCESS   read-write
     STATUS   current
     DESCRIPTION
        "Set  inter-area distance."
     DEFVAL {110}
    ::= { fsOspfGeneralMibsGroup 11 }

fsOspfIntraDistance OBJECT-TYPE
     SYNTAX   Unsigned32(1..255)
     MAX-ACCESS   read-write
     STATUS   current
     DESCRIPTION
        "Set  intra-area distance."
     DEFVAL {110}
    ::= { fsOspfGeneralMibsGroup 12 }

fsOspfExternDistance OBJECT-TYPE
     SYNTAX   Unsigned32(1..255)
     MAX-ACCESS   read-write
     STATUS   current
     DESCRIPTION
        "Set  extern distance."
     DEFVAL {110}
    ::= { fsOspfGeneralMibsGroup 13 }

--LogAdjChangeNotify
fsOspfLogAdjChangeNotify OBJECT-TYPE
     SYNTAX   EnabledStatus
     MAX-ACCESS   read-write
     STATUS   current
     DESCRIPTION
        "if enabled status is setted,
        Send syslog message when a neighbor state changes."
     DEFVAL {enabled}
     ::= { fsOspfGeneralMibsGroup 14 }

fsOspfPassiveStatus  OBJECT-TYPE
    SYNTAX EnabledStatus
    MAX-ACCESS read-write
    STATUS current
    DESCRIPTION
          "The fsOspfIfPassiveStatus of a interface equal to this object value
           when this interface is created. If you change this object value to 'enabled'
           or 'disabled'all interfaces which have exist will also change their
           fsOspfIfPassiveStatus to 'enabled' or 'disabled'."
    DEFVAL { disabled }
    ::={ fsOspfGeneralMibsGroup 15 }

fsOspfRFC1583Compatibility  OBJECT-TYPE
    SYNTAX EnabledStatus
    MAX-ACCESS read-write
    STATUS current
    DESCRIPTION
         "Controls the preference rules used in calculating AS external routes
         (RFC2328 Section 16.4) when choosing among multiple AS-external-LSAs
         advertising the same destination. When set to 'enabled', the preference
         rules remain those specified by RFC 1583 ([Ref9]). When set
         to 'disabled', the preference rules are those stated in
         'RFC2328 Section 16.4.1' which prevent routing loops when AS-
         external-LSAs for the same destination have been originated
         from different areas. Set to 'enabled' by default."
    REFERENCE
       "OSPF Version 2(RFC2328), C.1 Global parameters"
    DEFVAL { enabled }
    ::={ fsOspfGeneralMibsGroup 16 }

fsOspfRouteRedisDefMetricVal OBJECT-TYPE
     SYNTAX   Unsigned32(1..16777214)
     MAX-ACCESS   read-write
     STATUS   current
     DESCRIPTION
        "When this value is setted,Cause the current routing protocol(ospf)
         to use the same metricvalue for all redistributed routes (BGP, RIP, and OSPF)."
     DEFVAL {20}
    ::= { fsOspfGeneralMibsGroup 17}

fsOspfAdminiDistance OBJECT-TYPE
     SYNTAX   Unsigned32(1..255)
     MAX-ACCESS   read-write
     STATUS   current
     DESCRIPTION
        "ospf Administrative distance."
     DEFVAL {110}
    ::= { fsOspfGeneralMibsGroup 18}


--table mib

--fsOspfAreaTable
fsOspfAreaTable OBJECT-TYPE
        SYNTAX SEQUENCE OF FSOspfAreaEntry
        MAX-ACCESS not-accessible
        STATUS current
        DESCRIPTION
            "Information describing the configured  parame-
             ters  and cumulative statistics of the router's
             attached areas.This table is superset of ospfAreaTable"
    ::= { fsOspfMIBObjects 2}

fsOspfAreaEntry OBJECT-TYPE
        SYNTAX FSOspfAreaEntry
        MAX-ACCESS not-accessible
        STATUS current
        DESCRIPTION
            "The entry of fsOspfAreaTable."
        INDEX { fsOspfAreaId}
    ::= { fsOspfAreaTable 1 }

FSOspfAreaEntry ::=
        SEQUENCE {
         fsOspfAreaId
                AreaID,
         fsOspfAuthType
                INTEGER,
         fsOspfImportAsExtern
                INTEGER,
         fsOspfSpfRuns
                Counter32,
         fsOspfAreaBdrRtrCount
                Gauge32,
         fsOspfAsBdrRtrCount
                Gauge32,
         fsOspfAreaLsaCount
                Gauge32,
         fsOspfAreaLsaCksumSum
                Unsigned32,
         fsOspfAreaSummary
                INTEGER,
         fsOspfAreaStatus
                RowStatus,
-- extend parts
         fsOspfAreaInterfaceNum
                Unsigned32,
         fsOspfAreaNssaIsRedistribution
                TruthValue,
         fsOspfAreaNssaIsDefInfoOriginate
                TruthValue
         }
    fsOspfAreaId OBJECT-TYPE
        SYNTAX   AreaID
        MAX-ACCESS   read-only
        STATUS   current
        DESCRIPTION
           "A 32-bit integer uniquely identifying an area.
           Area ID 0.0.0.0 is used for the OSPF backbone."
       REFERENCE
          "OSPF Version 2, Appendix C.2 Area parameters"
      ::= { fsOspfAreaEntry 1 }


    fsOspfAuthType OBJECT-TYPE
        SYNTAX   INTEGER{
                    none(0),
                    simplePassword(1),
                    md5 (2)
                    -- reserved for specification by IANA (> 2)
                    }
        MAX-ACCESS   read-create
        STATUS   current
        DESCRIPTION
           "The authentication type specified for an area.
           Additional authentication types may be assigned
           locally on a per Area basis."
       REFERENCE
          "OSPF Version 2, Appendix E Authentication"
      DEFVAL { 0 }        -- no authentication, by default
      ::= { fsOspfAreaEntry 2 }

    fsOspfImportAsExtern OBJECT-TYPE
        SYNTAX   INTEGER    {
                    importExternal (1), --normal area
                    importNoExternal (2), -- stub area
                    importNssa (3)        -- NSSA area
                  }
        MAX-ACCESS   read-create
        STATUS   current
        DESCRIPTION
           "The area's support for importing  AS  external
           link- state advertisements."
       REFERENCE
          "OSPF Version 2, Appendix C.2 Area parameters"
      DEFVAL { importExternal }
      ::= { fsOspfAreaEntry 3 }


    fsOspfSpfRuns OBJECT-TYPE
        SYNTAX   Counter32
        MAX-ACCESS   read-only
        STATUS   current
        DESCRIPTION
           "The number of times that the intra-area  route
           table  has  been  calculated  using this area's
           link-state database.  This  is  typically  done
           using Dijkstra's algorithm."
       ::= { fsOspfAreaEntry 4 }

    fsOspfAreaBdrRtrCount OBJECT-TYPE
        SYNTAX   Gauge32
        MAX-ACCESS   read-only
        STATUS   current
        DESCRIPTION
           "The total number of area border routers reach-
           able within this area.  This is initially zero,
           and is calculated in each SPF Pass."
       ::= { fsOspfAreaEntry 5 }

    fsOspfAsBdrRtrCount OBJECT-TYPE
        SYNTAX   Gauge32
        MAX-ACCESS   read-only
        STATUS   current
        DESCRIPTION
           "The total number of Autonomous  System  border
           routers  reachable  within  this area.  This is
           initially zero, and is calculated in  each  SPF
           Pass."
       ::= { fsOspfAreaEntry 6 }


    fsOspfAreaLsaCount OBJECT-TYPE
        SYNTAX   Gauge32
        MAX-ACCESS   read-only
        STATUS   current
        DESCRIPTION
           "The total number of link-state  advertisements
           in  this  area's link-state database, excluding
           AS External LSA's."
       ::= { fsOspfAreaEntry 7 }


    fsOspfAreaLsaCksumSum OBJECT-TYPE
        SYNTAX   Unsigned32
        MAX-ACCESS   read-only
        STATUS   current
        DESCRIPTION
           "The 32-bit unsigned sum of the link-state  ad-
           vertisements'  LS  checksums  contained in this
           area's link-state database.  This sum  excludes
           external (LS type 5) link-state advertisements.
           The sum can be used to determine if  there  has
           been  a  change  in a router's link state data-
           base, and to compare the link-state database of
           two routers."
       DEFVAL   { 0 }
       ::= { fsOspfAreaEntry 8 }

    fsOspfAreaSummary OBJECT-TYPE
        SYNTAX   INTEGER    {
                    noAreaSummary (1),
                    sendAreaSummary (2)
                  }
        MAX-ACCESS   read-create
        STATUS   current
        DESCRIPTION
           "The variable ospfAreaSummary controls the  im-
           port  of  summary LSAs into stub areas.  It has
           no effect on other areas.

           If it is noAreaSummary, the router will neither
           originate  nor  propagate summary LSAs into the
           stub area.  It will rely entirely  on  its  de-
           fault route.

           If it is sendAreaSummary, the router will  both
           summarize and propagate summary LSAs."
       DEFVAL   { sendAreaSummary }
       ::= { fsOspfAreaEntry 9 }


    fsOspfAreaStatus OBJECT-TYPE
        SYNTAX   RowStatus
        MAX-ACCESS   read-create
        STATUS   current
        DESCRIPTION
           "This variable displays the status of  the  en-
           try.  Setting it to 'invalid' has the effect of
           rendering it inoperative.  The internal  effect
           (row removal) is implementation dependent."
       ::= { fsOspfAreaEntry 10 }

   fsOspfAreaInterfaceNum OBJECT-TYPE   --for command "show
        SYNTAX Unsigned32
        MAX-ACCESS read-only
        STATUS current
        DESCRIPTION
            " the interface number of this area"
    ::= { fsOspfAreaEntry 11 }

   fsOspfAreaNssaIsRedistribution OBJECT-TYPE
        SYNTAX TruthValue
        MAX-ACCESS read-create
        STATUS current
        DESCRIPTION
            " if it's disabled , when the router is an NSSA ABR and
            you want the redistribute command to import routes into normal
            areas, but not into the NSSA,
            this field is vaild for nssa area"
        DEFVAL {true}
    ::= { fsOspfAreaEntry 12}

   fsOspfAreaNssaIsDefInfoOriginate OBJECT-TYPE
        SYNTAX TruthValue
        MAX-ACCESS read-create
        STATUS current
        DESCRIPTION
            "if it's enabled it meaning that on an ABR to allow
            importing type 7 LSAs into the NSSA,
            this field is valid for nssa area"
        DEFVAL {false}
    ::= { fsOspfAreaEntry 13}


--network address scope table
fsOspfAddressScopeTable OBJECT-TYPE
        SYNTAX SEQUENCE OF FSOspfAddressScopeEntry
        MAX-ACCESS not-accessible
        STATUS current
        DESCRIPTION
            "Define an interface on which OSPF runs and the area ID for that
            interface. You can use the wildcard-mask to use a single
            command to define one or more multiple interfaces to be
            associated with a specific OSPF area. "
    ::= { fsOspfMIBObjects 3 }

fsOspfAddressScopeEntry OBJECT-TYPE
        SYNTAX FSOspfAddressScopeEntry
        MAX-ACCESS not-accessible
        STATUS current
        DESCRIPTION
            "the entry define an scope of address for ospf routing."
        INDEX { fsOspfNetWorkAreaID,fsOspfNetWorkAddress, fsOspfNetWorkMask}
    ::= { fsOspfAddressScopeTable 1 }


FSOspfAddressScopeEntry ::=
        SEQUENCE {
        fsOspfNetWorkAreaID
                IpAddress,
        fsOspfNetWorkAddress
                IpAddress,
        fsOspfNetWorkMask
                IpAddress,
        fsOspfNetWorkStatus
                 RowStatus

        }

fsOspfNetWorkAreaID OBJECT-TYPE
        SYNTAX IpAddress
        MAX-ACCESS read-only
        STATUS current
        DESCRIPTION
            "area ID"
    ::= { fsOspfAddressScopeEntry 1 }

fsOspfNetWorkAddress OBJECT-TYPE
        SYNTAX IpAddress
        MAX-ACCESS read-only
        STATUS current
        DESCRIPTION
            " Routing for Networks Ipaddress"
    ::= { fsOspfAddressScopeEntry 2 }

fsOspfNetWorkMask OBJECT-TYPE
        SYNTAX IpAddress
        MAX-ACCESS read-only
        STATUS current
        DESCRIPTION
            " Routing for Networks mask"
    ::= { fsOspfAddressScopeEntry 3 }

fsOspfNetWorkStatus    OBJECT-TYPE
        SYNTAX RowStatus
        MAX-ACCESS read-create
        STATUS current
        DESCRIPTION
            " when this value is destroy,the
            entry will be deleted"
    ::= { fsOspfAddressScopeEntry 4 }


-- The Ospf Interface Configuration Table

fsOspfIfTable OBJECT-TYPE
        SYNTAX   SEQUENCE OF FSOspfIfEntry
        MAX-ACCESS   not-accessible
        STATUS   current
        DESCRIPTION
           "The OSPF Interface Table describes the  interfaces
           from the viewpoint of OSPF."
       REFERENCE
          "ospfIfTable in rfc1850"
       ::= { fsOspfMIBObjects  4 }

fsOspfIfEntry OBJECT-TYPE
       SYNTAX   FSOspfIfEntry
       MAX-ACCESS   not-accessible
       STATUS   current
       DESCRIPTION
          "The OSPF Interface Entry describes one  inter-
           face configuration of OSPF."
      INDEX { fsOspfIfIpAddress, fsOspfAddressLessIf  }
      ::= { fsOspfIfTable 1 }

FSOspfIfEntry ::=
        SEQUENCE {
         fsOspfIfIpAddress
            IpAddress,
         fsOspfAddressLessIf
            Unsigned32,
         fsOspfIfAreaId
            AreaID,
         fsOspfIfType
            INTEGER,
         fsOspfIfAdminStat
            Status,
         fsOspfIfRtrPriority
            DesignatedRouterPriority,
         fsOspfIfTransitDelay
            Unsigned32,
         fsOspfIfRetransInterval
            Unsigned32,
         fsOspfIfHelloInterval
            HelloRange,
         fsOspfIfRtrDeadInterval
            PositiveInteger,
         fsOspfIfPollInterval
            PositiveInteger,
         fsOspfIfState
            INTEGER,
         fsOspfIfDesignatedRouter
            IpAddress,
         fsOspfIfBackupDesignatedRouter
            IpAddress,
         fsOspfIfEvents
            Counter32,
         fsOspfIfAuthType
            INTEGER,
         fsOspfIfAuthKey
            OCTET STRING,
         fsOspfIfStatus
            RowStatus,
         fsOspfIfMulticastForwarding
            INTEGER,
         fsOspfIfDemand
            TruthValue,
         fsOspfIfDatabaseFilterAllOut
                EnabledStatus,
         fsOspfIfDesignateRouterId
                IpAddress,
         fsOspfIfBackupDesignateRouterId
                IpAddress,
         fsOspfIfWaitInternal
                TimeTicks,
         fsOspfIfPassiveStatus
                EnabledStatus,
         fsOspfIfCurrentUsedMd5AuthKeyId
                Unsigned32
                 }
fsOspfIfIpAddress OBJECT-TYPE
        SYNTAX   IpAddress
        MAX-ACCESS   read-only
        STATUS   current
        DESCRIPTION
           "The IP address of this OSPF interface."
       ::= { fsOspfIfEntry 1 }

fsOspfAddressLessIf OBJECT-TYPE
        SYNTAX   Unsigned32
        MAX-ACCESS   read-only
        STATUS   current
        DESCRIPTION
           "For the purpose of easing  the  instancing  of
           addressed   and  addressless  interfaces;  This
           variable takes the value 0 on  interfaces  with
           IP  Addresses,  and  the corresponding value of
           ifIndex for interfaces having no IP Address."
       ::= { fsOspfIfEntry 2 }


fsOspfIfAreaId OBJECT-TYPE
        SYNTAX   AreaID
        MAX-ACCESS   read-only
        STATUS   current
        DESCRIPTION
           "A 32-bit integer uniquely identifying the area
           to  which  the  interface  connects.   Area  ID
           0.0.0.0 is used for the OSPF backbone."
       DEFVAL   { '00000000'H }    -- 0.0.0.0
       ::= { fsOspfIfEntry 3 }

fsOspfIfType OBJECT-TYPE
        SYNTAX   INTEGER    {
                    broadcast (1),
                    nbma (2),
                    pointToPoint (3),
                    pointToMultipoint (5),
                    loopback(6)
                  }
        MAX-ACCESS   read-write
        STATUS   current
        DESCRIPTION
           "The OSPF interface type.

           By way of a default, this field may be intuited
           from the corresponding value of ifType.  Broad-
           cast LANs, such as  Ethernet  and  IEEE  802.5,
           take  the  value  'broadcast', X.25 and similar
           technologies take the value 'nbma',  and  links
           that  are  definitively point to point take the
           value 'pointToPoint'."
       ::= { fsOspfIfEntry 4 }


fsOspfIfAdminStat OBJECT-TYPE
        SYNTAX   Status
        MAX-ACCESS   read-only
        STATUS   current
        DESCRIPTION
           "The OSPF  interface's  administrative  status.
           The  value formed on the interface, and the in-
           terface will be advertised as an internal route
           to  some  area.   The  value 'disabled' denotes
           that the interface is external to OSPF."
       ::= { fsOspfIfEntry 5 }

fsOspfIfRtrPriority OBJECT-TYPE
        SYNTAX   DesignatedRouterPriority
        MAX-ACCESS   read-write
        STATUS   current
        DESCRIPTION
           "The  priority  of  this  interface.   Used  in
           multi-access  networks,  this  field is used in
           the designated router election algorithm.   The
           value 0 signifies that the router is not eligi-
           ble to become the  designated  router  on  this
           particular  network.   In the event of a tie in
           this value, routers will use their Router ID as
           a tie breaker."
       DEFVAL { 1 }
       ::= { fsOspfIfEntry 6 }


fsOspfIfTransitDelay OBJECT-TYPE
        SYNTAX   Unsigned32 (1..65535)
        MAX-ACCESS   read-write
        STATUS   current
        DESCRIPTION
           "The estimated number of seconds  it  takes  to
           transmit  a  link state update packet over this
           interface."
       DEFVAL { 1 }
       ::= { fsOspfIfEntry 7 }


fsOspfIfRetransInterval OBJECT-TYPE
        SYNTAX   Unsigned32 (1..65535)
        MAX-ACCESS   read-write
        STATUS   current
        DESCRIPTION
           "The number of seconds between  link-state  ad-
           vertisement  retransmissions,  for  adjacencies
           belonging to this  interface.   This  value  is
           also used when retransmitting database descrip-
           tion and link-state request packets."
       DEFVAL { 5 }
       ::= { fsOspfIfEntry 8 }


fsOspfIfHelloInterval OBJECT-TYPE
        SYNTAX   HelloRange
        MAX-ACCESS   read-write
        STATUS   current
        DESCRIPTION
           "The length of time, in  seconds,  between  the
           Hello  packets that the router sends on the in-
           terface.  This value must be the same  for  all
           routers attached to a common network."
       DEFVAL { 10 }
       ::= { fsOspfIfEntry 9 }


fsOspfIfRtrDeadInterval OBJECT-TYPE
        SYNTAX   PositiveInteger
        MAX-ACCESS   read-write
        STATUS   current
        DESCRIPTION
           "The number of seconds that  a  router's  Hello
           packets  have  not been seen before it's neigh-
           bors declare the router down.  This  should  be
           some  multiple  of  the  Hello  interval.  This
           value must be the same for all routers attached
           to a common network."
       DEFVAL { 40 }
       ::= { fsOspfIfEntry 10 }


fsOspfIfPollInterval OBJECT-TYPE
        SYNTAX   PositiveInteger
        MAX-ACCESS   read-only
        STATUS   current
        DESCRIPTION
           "The larger time interval, in seconds,  between
           the  Hello  packets  sent  to  an inactive non-
           broadcast multi- access neighbor."
       ::= { fsOspfIfEntry 11 }


fsOspfIfState OBJECT-TYPE
        SYNTAX   INTEGER    {
                    down (1),
                    loopback (2),
                    waiting (3),
                    pointToPoint (4),
                    designatedRouter (5),
                    backupDesignatedRouter (6),
                    otherDesignatedRouter (7)
                  }
        MAX-ACCESS   read-only
        STATUS   current
        DESCRIPTION
           "The OSPF Interface State."
       DEFVAL { down }
       ::= { fsOspfIfEntry 12 }


fsOspfIfDesignatedRouter OBJECT-TYPE
        SYNTAX   IpAddress
        MAX-ACCESS   read-only
        STATUS   current
        DESCRIPTION
           "The IP Address of the interface which connected the local router in
            the Designated Router."
       DEFVAL   { '00000000'H }    -- 0.0.0.0
       ::= { fsOspfIfEntry 13 }


fsOspfIfBackupDesignatedRouter OBJECT-TYPE
        SYNTAX   IpAddress
        MAX-ACCESS   read-only
        STATUS   current
        DESCRIPTION
           "The IP Address of the interface which connected the local router in
            the Backup Designated Router."
       DEFVAL   { '00000000'H }    -- 0.0.0.0
       ::= { fsOspfIfEntry 14 }

fsOspfIfEvents OBJECT-TYPE
        SYNTAX   Counter32
        MAX-ACCESS   read-only
        STATUS   current
        DESCRIPTION
           "The number of times this  OSPF  interface  has
           changed its state, or an error has occurred."
       ::= { fsOspfIfEntry 15 }


fsOspfIfAuthKey OBJECT-TYPE
        SYNTAX   OCTET STRING (SIZE (0..256))
        MAX-ACCESS   read-write
        STATUS   current
        DESCRIPTION
           "The Authentication Key.  If the Area's Author-
           ization  Type  is  simplePassword,  and the key
           length is shorter than 8 octets, the agent will
           left adjust and zero fill to 8 octets.

           Note that unauthenticated  interfaces  need  no
           authentication key, and simple password authen-
           tication cannot use a key of more  than  8  oc-
           tets.  Larger keys are useful only with authen-
           tication mechanisms not specified in this docu-
           ment.

           When read, fsOspfIfAuthKey always returns an  Oc-
           tet String of length zero."
       REFERENCE
          "OSPF Version 2, Section 9  The  Interface  Data
          Structure"
      DEFVAL   { '0000000000000000'H }    -- 0.0.0.0.0.0.0.0
      ::= { fsOspfIfEntry 16 }

fsOspfIfStatus OBJECT-TYPE
        SYNTAX   RowStatus
        MAX-ACCESS   read-only
        STATUS   current
        DESCRIPTION
           "This value will be  active(1) always."
       ::= { fsOspfIfEntry 17 }


fsOspfIfMulticastForwarding OBJECT-TYPE
        SYNTAX   INTEGER    {
                            blocked (1),        -- no multicast forwarding
                            multicast (2),        -- using multicast address
                            unicast (3)        -- to each OSPF neighbor
                  }
        MAX-ACCESS   read-only
        STATUS   current
        DESCRIPTION
           "The way multicasts should  forwarded  on  this
           interface;  not  forwarded,  forwarded  as data
           link multicasts, or forwarded as data link uni-
           casts.   Data link multicasting is not meaning-
           ful on point to point and NBMA interfaces,  and
           setting ospfMulticastForwarding to 0 effective-
           ly disables all multicast forwarding."
       DEFVAL { blocked }
       ::= { fsOspfIfEntry 18 }


fsOspfIfDemand OBJECT-TYPE
        SYNTAX   TruthValue
        MAX-ACCESS   read-only
        STATUS   current
        DESCRIPTION
           "Indicates whether Demand OSPF procedures (hel-
           lo supression to FULL neighbors and setting the
           DoNotAge flag on proogated LSAs) should be per-
           formed on this interface."
       DEFVAL { false }
       ::= { fsOspfIfEntry 19 }


fsOspfIfAuthType OBJECT-TYPE
        SYNTAX   INTEGER (0..255)
                    -- none (0),
                    -- simplePassword (1)
                    -- md5 (2)
                    -- default (3)
                    -- reserved for specification by IANA (> 2)
        MAX-ACCESS   read-write
        STATUS   current
        DESCRIPTION
           "The authentication type specified for  an  interface. Setting this value to
            'default' means using default authentication type referenced to Area Authentication,
            this value only for set,not be read. Additional  authentication types may
            be assigned locally."
       REFERENCE
          "OSPF Version 2, Appendix E Authentication"
      DEFVAL { 0 }        -- no authentication, by default
      ::= { fsOspfIfEntry 20 }

fsOspfIfDatabaseFilterAllOut OBJECT-TYPE
        SYNTAX   EnabledStatus
        MAX-ACCESS   read-write
        STATUS   current
        DESCRIPTION
           "Block flooding of OSPF LSA packets to the interface. By
           default, OSPF floods new LSAs over all interfaces in the same area,
           except the interface on which the LSA arrives."
        DEFVAL {disabled}
       ::= { fsOspfIfEntry 21 }

fsOspfIfDesignateRouterId OBJECT-TYPE
        SYNTAX   IpAddress
        MAX-ACCESS   read-only
        STATUS   current
        DESCRIPTION
           "DR RouterID of this interface,
           when DR does not selected,DR Id is 0.0.0.0"
        DEFVAL {'00000000'H}
       ::= { fsOspfIfEntry 22 }

fsOspfIfBackupDesignateRouterId OBJECT-TYPE
        SYNTAX   IpAddress
        MAX-ACCESS   read-only
        STATUS   current
        DESCRIPTION
           "Backup DR RouterId of this interface ,
           when Backup DR does not selected,BDR Id is 0.0.0.0"
        DEFVAL {'00000000'H}
       ::= { fsOspfIfEntry 23 }

fsOspfIfWaitInternal OBJECT-TYPE
        SYNTAX  TimeTicks
        MAX-ACCESS   read-only
        STATUS   current
        DESCRIPTION
           "The wait time of hello generate"
       ::= { fsOspfIfEntry 24 }

fsOspfIfPassiveStatus OBJECT-TYPE
        SYNTAX   EnabledStatus
        MAX-ACCESS   read-write
        STATUS   current
        DESCRIPTION
               "Setting this object value to 'enabled' ,the interface will
               become a passive interface."
        DEFVAL { disabled }
        ::= { fsOspfIfEntry 25 }
fsOspfIfCurrentUsedMd5AuthKeyId     OBJECT-TYPE
       SYNTAX   Unsigned32 (0..255)
        MAX-ACCESS   read-write
        STATUS   current
        DESCRIPTION
           "key-id which current used for md5 authentication,this value is
            valid from 1 to 255, the value 0 is default value.."
        DEFVAL {0}
       ::= { fsOspfIfEntry 26 }


-- The Ospf Interface MD5 authentication key configuration table

fsOspfIfMd5AuthKeyTable OBJECT-TYPE
        SYNTAX   SEQUENCE OF FSOspfIfMd5AuthKeyEntry
        MAX-ACCESS   not-accessible
        STATUS   current
        DESCRIPTION
           "Configuration table of the key-id for md5 authentication for OSPF protocol."
       ::= { fsOspfMIBObjects  5 }

fsOspfIfMd5AuthKeyEntry OBJECT-TYPE
       SYNTAX   FSOspfIfMd5AuthKeyEntry
       MAX-ACCESS   not-accessible
       STATUS   current
       DESCRIPTION
          "Configuration entry of the key-id for md5 authentication for OSPF protocol"
      INDEX {fsOspfIfMd5AuthKeyIf, fsOspfIfMd5AuthKeyId }
      ::= { fsOspfIfMd5AuthKeyTable 1 }

FSOspfIfMd5AuthKeyEntry ::=
        SEQUENCE {
         fsOspfIfMd5AuthKeyIf
            Unsigned32,
         fsOspfIfMd5AuthKeyId
            Unsigned32,
         fsOspfIfMd5AuthKey
            OCTET STRING,
         fsOspfIfMd5AuthKeySt
            ConfigStatus
                 }

fsOspfIfMd5AuthKeyIf OBJECT-TYPE
        SYNTAX   Unsigned32
        MAX-ACCESS   read-only
        STATUS   current
        DESCRIPTION
           "Corresponding value of ifIndex for interfaces."
       ::= { fsOspfIfMd5AuthKeyEntry 1 }

fsOspfIfMd5AuthKeyId     OBJECT-TYPE
        SYNTAX   Unsigned32 (1..255)
        MAX-ACCESS   read-only
        STATUS   current
        DESCRIPTION
           "the key-id for md5 authentication."
       ::= { fsOspfIfMd5AuthKeyEntry 2 }

fsOspfIfMd5AuthKey OBJECT-TYPE
        SYNTAX   OCTET STRING (SIZE (0..256))
        MAX-ACCESS   read-create
        STATUS   current
        DESCRIPTION
           "The Authentication Key for MD5.

           When read, fsOspfIfMd5AuthKey always returns an  Oc-
           tet String of length zero."
       REFERENCE
          "OSPF Version 2, Section 9  The  Interface  Data
          Structure"
      ::= { fsOspfIfMd5AuthKeyEntry 3 }

fsOspfIfMd5AuthKeySt OBJECT-TYPE
        SYNTAX   ConfigStatus
        MAX-ACCESS   read-create
        STATUS   current
        DESCRIPTION
           "Setting this value to 'invalid' will delete this entry.
            Setting this value to 'valid' will have no effect."
      ::= { fsOspfIfMd5AuthKeyEntry 4 }



-- The FS Ospf Virtual Link Table

fsOspfVirtTable OBJECT-TYPE
        SYNTAX   SEQUENCE OF FSOspfVirtEntry
        MAX-ACCESS   not-accessible
        STATUS   current
        DESCRIPTION
           "Information about this router's virtual inter-
            faces.Include ospfVirtIfTable in rfc1850"
        REFERENCE
          "ospfVirtIfTable in rfc1850"
       ::= { fsOspfMIBObjects  6 }

fsOspfVirtEntry OBJECT-TYPE
       SYNTAX   FSOspfVirtEntry
       MAX-ACCESS   not-accessible
       STATUS   current
       DESCRIPTION
          "Information about a single Virtual Interface"
      INDEX {fsOspfVirtIfAreaId, fsOspfVirtIfNeighbor}
      ::= { fsOspfVirtTable 1 }

FSOspfVirtEntry ::=
        SEQUENCE {
      fsOspfVirtIfAreaId
         AreaID,
      fsOspfVirtIfNeighbor
         RouterID,
      fsOspfVirtIfTransitDelay
         Unsigned32,
      fsOspfVirtIfRetransInterval
         Unsigned32,
      fsOspfVirtIfHelloInterval
         HelloRange,
      fsOspfVirtIfRtrDeadInterval
         PositiveInteger,
      fsOspfVirtIfState
         INTEGER,
      fsOspfVirtIfEvents
         Counter32,
      fsOspfVirtIfAuthType
         INTEGER,
      fsOspfVirtIfAuthKey
         OCTET STRING,
      fsOspfVirtIfStatus
         RowStatus,
      fsOspfVirtCost
            Unsigned32,
      fsOspfVirtNativeIfIndex
            INTEGER,
      fsOspfVirtLinkState
            INTEGER,
      fsOspfVirtHelloDueIn
            TimeTicks,
     fsOspfVirtCurrentUsedMd5AuthKeyId
            Unsigned32
                 }

    fsOspfVirtIfAreaId OBJECT-TYPE
        SYNTAX   AreaID
        MAX-ACCESS   read-only
        STATUS   current
        DESCRIPTION
           "The  Transit  Area  that  the   Virtual   Link
           traverses.  By definition, this is not 0.0.0.0"
       ::= { fsOspfVirtEntry 1 }


    fsOspfVirtIfNeighbor OBJECT-TYPE
        SYNTAX   RouterID
        MAX-ACCESS   read-only
        STATUS   current
        DESCRIPTION
           "The Router ID of the Virtual Neighbor."
       ::= { fsOspfVirtEntry 2 }


    fsOspfVirtIfTransitDelay OBJECT-TYPE
        SYNTAX   Unsigned32 (1..65535)
        MAX-ACCESS   read-create
        STATUS   current
        DESCRIPTION
           "The estimated number of seconds  it  takes  to
           transmit  a link- state update packet over this
           interface."
       DEFVAL { 1 }
       ::= { fsOspfVirtEntry 3 }


    fsOspfVirtIfRetransInterval OBJECT-TYPE
        SYNTAX   Unsigned32 (1..65535)
        MAX-ACCESS   read-create
        STATUS   current
        DESCRIPTION
           "The number of seconds between  link-state  ad-
           vertisement  retransmissions,  for  adjacencies
           belonging to this  interface.   This  value  is
           also used when retransmitting database descrip-
           tion  and  link-state  request  packets.   This
           value  should  be well over the expected round-
           trip time."
       DEFVAL { 5 }
       ::= { fsOspfVirtEntry 4 }


    fsOspfVirtIfHelloInterval OBJECT-TYPE
        SYNTAX   HelloRange
        MAX-ACCESS   read-create
        STATUS   current
        DESCRIPTION
           "The length of time, in  seconds,  between  the
           Hello  packets that the router sends on the in-
           terface.  This value must be the same  for  the
           virtual neighbor."
       DEFVAL { 10 }
       ::= { fsOspfVirtEntry 5 }


    fsOspfVirtIfRtrDeadInterval OBJECT-TYPE
        SYNTAX   PositiveInteger
        MAX-ACCESS   read-create
        STATUS   current
        DESCRIPTION
           "The number of seconds that  a  router's  Hello
           packets  have  not been seen before it's neigh-
           bors declare the router down.  This  should  be
           some  multiple  of  the  Hello  interval.  This
           value must be the same for the  virtual  neigh-
           bor."
       DEFVAL { 40 }
       ::= { fsOspfVirtEntry 6 }


    fsOspfVirtIfState OBJECT-TYPE
        SYNTAX   INTEGER    {
                    down (1),            -- these use the same encoding
                    pointToPoint (4)     -- as the ospfIfTable
                  }
        MAX-ACCESS   read-only
        STATUS   current
        DESCRIPTION
           "OSPF virtual interface states."
       DEFVAL   { down }
       ::= { fsOspfVirtEntry 7 }


    fsOspfVirtIfEvents OBJECT-TYPE
        SYNTAX   Counter32
        MAX-ACCESS   read-only
        STATUS   current
        DESCRIPTION
           "The number of state changes or error events on
           this Virtual Link"
       ::= { fsOspfVirtEntry 8 }


    fsOspfVirtIfAuthKey OBJECT-TYPE
        SYNTAX   OCTET STRING (SIZE(0..256))
        MAX-ACCESS   read-create
        STATUS   current
        DESCRIPTION
           "If Authentication Type is simplePassword,  the
           device  will left adjust and zero fill to 8 oc-
           tets.

           Note that unauthenticated  interfaces  need  no
           authentication key, and simple password authen-
           tication cannot use a key of more  than  8  oc-
           tets.  Larger keys are useful only with authen-
           tication mechanisms not specified in this docu-
           ment.

           When  read,  ospfVifAuthKey  always  returns  a
           string of length zero."
       REFERENCE
          "OSPF Version 2, Section 9  The  Interface  Data
          Structure"
      DEFVAL   { '0000000000000000'H }    -- 0.0.0.0.0.0.0.0
      ::= { fsOspfVirtEntry 9 }


    fsOspfVirtIfStatus OBJECT-TYPE
        SYNTAX   RowStatus
        MAX-ACCESS   read-create
        STATUS   current
        DESCRIPTION
           "This variable displays the status of  the  en-
           try.  Setting it to 'invalid' has the effect of
           rendering it inoperative.  The internal  effect
           (row removal) is implementation dependent."
       ::= { fsOspfVirtEntry 10 }


    fsOspfVirtIfAuthType OBJECT-TYPE
        SYNTAX   INTEGER (0..255)
                    -- none (0),
                    -- simplePassword (1),
                    -- md5 (2),
                    -- default (3)
                    -- reserved for specification by IANA (> 2)
        MAX-ACCESS   read-create
        STATUS   current
        DESCRIPTION
           "The authentication type specified for a virtual  interface. Setting this value
           'default' means using default authentication type referenced to Area Authentication,
            this value only for set,not be read. Additional authentication types
            may be assigned locally."
       REFERENCE
          "OSPF Version 2, Appendix E Authentication"
      DEFVAL { 0 }        -- no authentication, by default
      ::= { fsOspfVirtEntry 11 }


   fsOspfVirtCost OBJECT-TYPE
        SYNTAX   Unsigned32
        MAX-ACCESS   read-only
        STATUS   current
        DESCRIPTION
               "Explicitly specify the cost of sending a packet on the
                interface."
        ::= { fsOspfVirtEntry 12 }

    fsOspfVirtNativeIfIndex OBJECT-TYPE
        SYNTAX   INTEGER
        MAX-ACCESS   read-only
        STATUS   current
        DESCRIPTION
               " the Interface's Index that The Virtual Link
                 via this interface."
        ::= { fsOspfVirtEntry 13 }

    fsOspfVirtLinkState OBJECT-TYPE
        SYNTAX  INTEGER{
          		         up(1),
                        down(2)
                       }
        MAX-ACCESS   read-only
        STATUS   current
        DESCRIPTION
           "The  Virtual Link State is up or down."
       ::= { fsOspfVirtEntry 14 }

    fsOspfVirtHelloDueIn OBJECT-TYPE
        SYNTAX   TimeTicks
        MAX-ACCESS   read-only
        STATUS   current
        DESCRIPTION
               " the time when hello due in."
        ::= { fsOspfVirtEntry 15 }

    fsOspfVirtCurrentUsedMd5AuthKeyId     OBJECT-TYPE
       SYNTAX   Unsigned32 (0..255)
       MAX-ACCESS   read-create
        STATUS   current
        DESCRIPTION
           "the key-id which current used for md5 authentication,this value is
            valid from 1 to 255, the value 0 is default value."
        DEFVAL {0}
       ::= { fsOspfVirtEntry 16 }


-- The Ospf Virtual Interface MD5 authentication key configuration table

fsOspfVirtIfMd5AuthKeyTable OBJECT-TYPE
        SYNTAX   SEQUENCE OF FSOspfVirtIfMd5AuthKeyEntry
        MAX-ACCESS   not-accessible
        STATUS   current
        DESCRIPTION
           "Configuration table of the key-id for md5 authentication in VirtIf
            for OSPF protocol."
       ::= { fsOspfMIBObjects  7 }

fsOspfVirtIfMd5AuthKeyEntry OBJECT-TYPE
       SYNTAX   FSOspfVirtIfMd5AuthKeyEntry
       MAX-ACCESS   not-accessible
       STATUS   current
       DESCRIPTION
          "Configuration entry of the key-id for md5 authentication in VirtIf
           for OSPF protocol"
      INDEX {fsOspfVirtIfMd5AuthKeyAreaId, fsOspfVirtIfMd5AuthKeyNeighbor,
             fsOspfVirtIfMd5AuthKeyId }
      ::= { fsOspfVirtIfMd5AuthKeyTable 1 }

FSOspfVirtIfMd5AuthKeyEntry ::=
        SEQUENCE {
         fsOspfVirtIfMd5AuthKeyAreaId
            AreaID,
         fsOspfVirtIfMd5AuthKeyNeighbor
            RouterID,
         fsOspfVirtIfMd5AuthKeyId
            Unsigned32,
         fsOspfVirtIfMd5AuthKey
            OCTET STRING,
         fsOspfVirtIfMd5AuthKeySt
            ConfigStatus
                 }

fsOspfVirtIfMd5AuthKeyAreaId OBJECT-TYPE
        SYNTAX   AreaID
        MAX-ACCESS   read-only
        STATUS   current
        DESCRIPTION
           "The  Transit  Area  that  the   Virtual   Link
           traverses.  By definition, this is not 0.0.0.0"
       ::= { fsOspfVirtIfMd5AuthKeyEntry 1 }

fsOspfVirtIfMd5AuthKeyNeighbor OBJECT-TYPE
        SYNTAX   RouterID
        MAX-ACCESS   read-only
        STATUS   current
        DESCRIPTION
           "The Router ID of the Virtual Neighbor."
       ::= { fsOspfVirtIfMd5AuthKeyEntry 2 }

fsOspfVirtIfMd5AuthKeyId     OBJECT-TYPE
        SYNTAX   Unsigned32 (1..255)
        MAX-ACCESS   read-only
        STATUS   current
        DESCRIPTION
           "the key-id for md5 authentication."
       ::= { fsOspfVirtIfMd5AuthKeyEntry 3 }

fsOspfVirtIfMd5AuthKey OBJECT-TYPE
        SYNTAX   OCTET STRING (SIZE (0..256))
        MAX-ACCESS   read-create
        STATUS   current
        DESCRIPTION
           "The Authentication Key for MD5.

           When read, fsOspfVirtIfMd5AuthKey always returns an  Oc-
           tet String of length zero."
       REFERENCE
          "OSPF Version 2, Section 9  The  Interface  Data
          Structure"
      ::= { fsOspfVirtIfMd5AuthKeyEntry 4 }

fsOspfVirtIfMd5AuthKeySt OBJECT-TYPE
        SYNTAX   ConfigStatus
        MAX-ACCESS   read-create
        STATUS   current
        DESCRIPTION
           "Setting this value to 'invalid' will delete this entry.
            Setting this value to 'valid' will have no effect."
      ::= { fsOspfVirtIfMd5AuthKeyEntry 5 }


fsOspfLsaDetailInfoMibsGroup OBJECT IDENTIFIER ::= { fsOspfMIBObjects 8 }


--  OSPF Link State Database

--      The Link State Database contains the Link State
--      Advertisements from throughout the areas that the
--      device is attached to.


fsOspfLsdbTable OBJECT-TYPE
     SYNTAX   SEQUENCE OF FSOspfLsdbEntry
     MAX-ACCESS   not-accessible
     STATUS   current
     DESCRIPTION
        "The OSPF Process's Link State Database."
    REFERENCE
       "OSPF Version 2, Section 12  Link  State  Adver-
       tisements"
   ::= { fsOspfLsaDetailInfoMibsGroup 1 }


fsOspfLsdbEntry OBJECT-TYPE
     SYNTAX   FSOspfLsdbEntry
     MAX-ACCESS   not-accessible
     STATUS   current
     DESCRIPTION
        "A single Link State Advertisement."
    INDEX { fsOspfLsdbAreaId, fsOspfLsdbType,
            fsOspfLsdbLsid, fsOspfLsdbRouterId }
    ::= { fsOspfLsdbTable 1 }

FSOspfLsdbEntry ::=
    SEQUENCE {
        fsOspfLsdbAreaId
            AreaID,
        fsOspfLsdbType
            INTEGER,
        fsOspfLsdbLsid
            IpAddress,
        fsOspfLsdbRouterId
            RouterID,
        fsOspfLsdbSequence
            Unsigned32,
        fsOspfLsdbAge
            Unsigned32,
        fsOspfLsdbChecksum
            Unsigned32,
        fsOspfLsdbAdvertisement
            OCTET STRING,
        fsOspfLsdbLinkNum  --equal LinkCount
            Unsigned32,
        fsOspfLsdbPacketLength
            Unsigned32,
        fsOspfSummaryLsaNetworkMask
            IpAddress,
        fsOspfSummaryLsaTos0Metric
            Unsigned32,
        fsOspfNssaLsaDetailMetricType
            INTEGER,
        fsOspfNssaLsaDetailForwardAddr
            IpAddress,
        fsOspfNssaLsaDetailRouteTag
            Unsigned32,
        fsOspfLsdbOption
            Unsigned32
              }
fsOspfLsdbAreaId OBJECT-TYPE
        SYNTAX   AreaID
        MAX-ACCESS   read-only
        STATUS   current
        DESCRIPTION
           "The 32 bit identifier of the Area  from  which
           the LSA was received."
       REFERENCE
          "OSPF Version 2, Appendix C.2 Area parameters"
      ::= { fsOspfLsdbEntry 1 }

-- External Link State Advertisements are permitted
-- for backward compatibility, but should be displayed in
-- the ospfExtLsdbTable rather than here.

fsOspfLsdbType OBJECT-TYPE
        SYNTAX   INTEGER    {
                    routerLink (1),
                    networkLink (2),
                    summaryLink (3),
                    asSummaryLink (4),
                    asExternalLink (5), -- but see fsOspfExtLsdbTable
                    multicastLink (6),
                    nssaExternalLink (7)
                  }
        MAX-ACCESS   read-only
        STATUS   current
        DESCRIPTION
           "The type  of  the  link  state  advertisement.
           Each  link state type has a separate advertise-
           ment format."
       REFERENCE
          "OSPF Version 2, Appendix A.4.1 The  Link  State
          Advertisement header"
      ::= { fsOspfLsdbEntry 2 }

fsOspfLsdbLsid OBJECT-TYPE
        SYNTAX   IpAddress
        MAX-ACCESS   read-only
        STATUS   current
        DESCRIPTION
           "The Link State ID is an LS Type Specific field
           containing either a Router ID or an IP Address;
           it identifies the piece of the  routing  domain
           that is being described by the advertisement."
       REFERENCE
          "OSPF Version 2, Section 12.1.4 Link State ID"
      ::= { fsOspfLsdbEntry 3 }

fsOspfLsdbRouterId OBJECT-TYPE
        SYNTAX   RouterID
        MAX-ACCESS   read-only
        STATUS   current
        DESCRIPTION
           "The 32 bit number that uniquely identifies the
           originating router in the Autonomous System."
       REFERENCE
          "OSPF Version 2, Appendix C.1 Global parameters"
      ::= { fsOspfLsdbEntry 4 }

--  Note that the OSPF Sequence Number is a 32 bit signed
--  integer.  It fss with the value '80000001'h,
--  or -'7FFFFFFF'h, and increments until '7FFFFFFF'h
--  Thus, a typical sequence number will be very negative.

fsOspfLsdbSequence OBJECT-TYPE
        SYNTAX   Unsigned32
        MAX-ACCESS   read-only
        STATUS   current
        DESCRIPTION
           "The sequence number field is a  signed  32-bit
           integer.   It  is used to detect old and dupli-
           cate link state advertisements.  The  space  of
           sequence  numbers  is  linearly  ordered.   The
           larger the sequence number the more recent  the
           advertisement."
       REFERENCE
          "OSPF Version  2,  Section  12.1.6  LS  sequence
          number"
      ::= { fsOspfLsdbEntry 5 }

fsOspfLsdbAge OBJECT-TYPE
        SYNTAX   Unsigned32    -- Should be 0..MaxAge
        MAX-ACCESS   read-only
        STATUS   current
        DESCRIPTION
           "This field is the age of the link state adver-
           tisement in seconds."
       REFERENCE
          "OSPF Version 2, Section 12.1.1 LS age"
      ::= { fsOspfLsdbEntry 6 }

fsOspfLsdbChecksum OBJECT-TYPE
        SYNTAX   Unsigned32
        MAX-ACCESS   read-only
        STATUS   current
        DESCRIPTION
           "This field is the  checksum  of  the  complete
           contents  of  the  advertisement, excepting the
           age field.  The age field is excepted  so  that
           an   advertisement's  age  can  be  incremented
           without updating the  checksum.   The  checksum
           used  is  the same that is used for ISO connec-
           tionless datagrams; it is commonly referred  to
           as the Fletcher checksum."
       REFERENCE
          "OSPF Version 2, Section 12.1.7 LS checksum"
      ::= { fsOspfLsdbEntry 7 }

fsOspfLsdbAdvertisement OBJECT-TYPE
        SYNTAX   OCTET STRING (SIZE (1..512))
        MAX-ACCESS   read-only
        STATUS   current
        DESCRIPTION
           "The entire Link State Advertisement, including
           its header."
       REFERENCE
          "OSPF Version 2, Section 12  Link  State  Adver-
          tisements"
      ::= { fsOspfLsdbEntry 8 }

 fsOspfLsdbLinkNum   OBJECT-TYPE
        SYNTAX   Unsigned32(0..4294967295)
        MAX-ACCESS   read-only
        STATUS   current
        DESCRIPTION
           "  the link count of this Router Link Lsa ,
              this field is only valid for Router Link Lsa（type 1 LSA)"
       ::= { fsOspfLsdbEntry 9 }

fsOspfLsdbPacketLength   OBJECT-TYPE
        SYNTAX   Unsigned32(0..65535)
        MAX-ACCESS   read-only
        STATUS   current
        DESCRIPTION
           "the  lsa packet  length   ."
       ::= { fsOspfLsdbEntry 10 }

fsOspfSummaryLsaNetworkMask  OBJECT-TYPE
        SYNTAX   IpAddress
        MAX-ACCESS   read-only
        STATUS   current
        DESCRIPTION
           "this field is only useful when  ospfLsdbType is type-3 or
           type-4 or type-7,it's the Lsa's network mask  ."
       ::= { fsOspfLsdbEntry 11 }

fsOspfSummaryLsaTos0Metric OBJECT-TYPE
        SYNTAX   Unsigned32(0..65535)
        MAX-ACCESS   read-only
        STATUS   current
        DESCRIPTION
           "this field is only useful when  ospfLsdbType is type-3 or
           type-4 or type-7,it's the  Lsa's tos0 metric  ."
       ::= { fsOspfLsdbEntry 12 }

fsOspfNssaLsaDetailMetricType   OBJECT-TYPE
        SYNTAX   INTEGER
                       { type1(1),
                         type2(2)
                        }
        MAX-ACCESS   read-only
        STATUS   current
        DESCRIPTION
           "    this field is valid when Lsa is a type-7 LSA.
	        The type of Nssa ernal metric.  If bit E is set, the metric
	        specified is a Type 2 external metric.  This means the metric is
	        considered larger than any link state path.  If bit E is zero,
	        the specified metric is a Type 1 external metric.  This means
	        that it is expressed in the same units as the link state metric
	        (i.e., the same units as interface cost).  "
       ::= { fsOspfLsdbEntry 13 }

 fsOspfNssaLsaDetailForwardAddr   OBJECT-TYPE
        SYNTAX   IpAddress
        MAX-ACCESS   read-only
        STATUS   current
        DESCRIPTION
           "this field is valid when Lsa is a type-7 LSA.
            Data traffic for the advertised destination will be forwarded to
            this address.  If the Forwarding address is set to 0.0.0.0, data
            traffic will be forwarded instead to the LSA's originator (i.e.,
            the responsible AS boundary router)  ."
       ::= { fsOspfLsdbEntry 14 }

 fsOspfNssaLsaDetailRouteTag   OBJECT-TYPE
        SYNTAX   Unsigned32
        MAX-ACCESS   read-only
        STATUS   current
        DESCRIPTION
           " this field is valid when Lsa is a type-7 LSA.
             A 32-bit field attached to each external route.  This is not
             used by the OSPF protocol itself.  It may be used to communicate
             information between AS boundary routers; the precise nature of
             such information is outside the scope of this specification."
       ::= { fsOspfLsdbEntry 15 }

 fsOspfLsdbOption   OBJECT-TYPE
        SYNTAX   Unsigned32
        MAX-ACCESS   read-only
        STATUS   current
        DESCRIPTION
           "the option field indicate which optional capabilities
            area associated with the LSA. "
        REFERENCE
          "OSPF Version 2, Appendix A.2, the Options Field"
       ::= { fsOspfLsdbEntry 16 }

--  OSPF Link State Database, External

--      The Link State Database contains the Link State
--      Advertisements from throughout the areas that the
--      device is attached to.

--             This table is identical to the OSPF LSDB Table in
--      format, but contains only External Link State
--             Advertisements.  The purpose is to allow external
--      LSAs to be displayed once for the router rather
--      than once in each non-stub area.

fsOspfExtLsdbTable OBJECT-TYPE
        SYNTAX   SEQUENCE OF FSOspfExtLsdbEntry
        MAX-ACCESS   not-accessible
        STATUS   current
        DESCRIPTION
           "The OSPF Process's Links State Database."
        REFERENCE
          "OSPF Version 2, Section 12  Link  State  Adver-
          tisements"
       ::= { fsOspfLsaDetailInfoMibsGroup  2 }

fsOspfExtLsdbEntry OBJECT-TYPE
       SYNTAX   FSOspfExtLsdbEntry
       MAX-ACCESS   not-accessible
       STATUS   current
       DESCRIPTION
           "A single Link State Advertisement."
       INDEX { fsOspfExtLsdbType, fsOspfExtLsdbLsid, fsOspfExtLsdbRouterId }
      ::= { fsOspfExtLsdbTable 1 }

FSOspfExtLsdbEntry ::=
     SEQUENCE{
        fsOspfExtLsdbType
            INTEGER,
        fsOspfExtLsdbLsid
            IpAddress,
        fsOspfExtLsdbRouterId
            RouterID,
        fsOspfExtLsdbSequence
            Unsigned32,
        fsOspfExtLsdbAge
            Unsigned32,
        fsOspfExtLsdbChecksum
            Unsigned32,
        fsOspfExtLsdbAdvertisement
            OCTET STRING,
        fsOspfExtLsdbNetworkMask
            IpAddress,
        fsOspfExtLsdbMetricType
            INTEGER,
        fsOspfExtLsdbForwardAddr
            IpAddress,
        fsOspfExtLsdbRouteTag
            Unsigned32,
        fsOspfExtLsdbMetric
            INTEGER,
        fsOspfExtLsdbOption
            Unsigned32,
        fsOspfExtLsdbPacketLength
            Unsigned32
              }

 fsOspfExtLsdbType OBJECT-TYPE
        SYNTAX   INTEGER    {
                    asExternalLink (5)
                  }
        MAX-ACCESS   read-only
        STATUS   current
        DESCRIPTION
           "The type  of  the  link  state  advertisement.
           Each  link state type has a separate advertise-
           ment format."
       REFERENCE
          "OSPF Version 2, Appendix A.4.1 The  Link  State
          Advertisement header"
      ::= { fsOspfExtLsdbEntry 1 }


 fsOspfExtLsdbLsid OBJECT-TYPE
        SYNTAX   IpAddress
        MAX-ACCESS   read-only
        STATUS   current
        DESCRIPTION
           "The Link State ID is an LS Type Specific field
           containing either a Router ID or an IP Address;
           it identifies the piece of the  routing  domain
           that is being described by the advertisement."
       REFERENCE
          "OSPF Version 2, Section 12.1.4 Link State ID"
      ::= { fsOspfExtLsdbEntry 2 }


 fsOspfExtLsdbRouterId OBJECT-TYPE
        SYNTAX   RouterID
        MAX-ACCESS   read-only
        STATUS   current
        DESCRIPTION
           "The 32 bit number that uniquely identifies the
           originating router in the Autonomous System."
       REFERENCE
          "OSPF Version 2, Appendix C.1 Global parameters"
      ::= { fsOspfExtLsdbEntry 3 }

--  Note that the OSPF Sequence Number is a 32 bit signed
--  integer.  It fss with the value '80000001'h,
--  or -'7FFFFFFF'h, and increments until '7FFFFFFF'h
--  Thus, a typical sequence number will be very negative.

 fsOspfExtLsdbSequence OBJECT-TYPE
        SYNTAX   Unsigned32
        MAX-ACCESS   read-only
        STATUS   current
        DESCRIPTION
           "The sequence number field is a  signed  32-bit
           integer.   It  is used to detect old and dupli-
           cate link state advertisements.  The  space  of
           sequence  numbers  is  linearly  ordered.   The
           larger the sequence number the more recent  the
           advertisement."
       REFERENCE
          "OSPF Version  2,  Section  12.1.6  LS  sequence
          number"
      ::= { fsOspfExtLsdbEntry 4 }


 fsOspfExtLsdbAge OBJECT-TYPE
        SYNTAX   Unsigned32    -- Should be 0..MaxAge
        MAX-ACCESS   read-only
        STATUS   current
        DESCRIPTION
           "This field is the age of the link state adver-
           tisement in seconds."
       REFERENCE
          "OSPF Version 2, Section 12.1.1 LS age"
      ::= { fsOspfExtLsdbEntry 5 }


 fsOspfExtLsdbChecksum OBJECT-TYPE
        SYNTAX   Unsigned32
        MAX-ACCESS   read-only
        STATUS   current
        DESCRIPTION
           "This field is the  checksum  of  the  complete
           contents  of  the  advertisement, excepting the
           age field.  The age field is excepted  so  that
           an   advertisement's  age  can  be  incremented
           without updating the  checksum.   The  checksum
           used  is  the same that is used for ISO connec-
           tionless datagrams; it is commonly referred  to
           as the Fletcher checksum."
       REFERENCE
          "OSPF Version 2, Section 12.1.7 LS checksum"
      ::= { fsOspfExtLsdbEntry 6 }


 fsOspfExtLsdbAdvertisement OBJECT-TYPE
        SYNTAX   OCTET STRING (SIZE(36))
        MAX-ACCESS   read-only
        STATUS   current
        DESCRIPTION
           "The entire Link State Advertisement, including
           its header."
       REFERENCE
          "OSPF Version 2, Section 12  Link  State  Adver-
          tisements"
      ::= { fsOspfExtLsdbEntry 7 }

 fsOspfExtLsdbNetworkMask   OBJECT-TYPE
        SYNTAX   IpAddress
        MAX-ACCESS   read-only
        STATUS   current
        DESCRIPTION
           "The IP address mask for the advertised destination.  For
            example, when advertising a class A network the mask 0xff000000
            would be used."
       ::= { fsOspfExtLsdbEntry 8 }

 fsOspfExtLsdbMetric   OBJECT-TYPE
        SYNTAX   INTEGER
        MAX-ACCESS   read-only
        STATUS   current
        DESCRIPTION
           " The cost of this route.  Interpretation depends on the external
             type indication.  "
       ::= { fsOspfExtLsdbEntry 9 }

 fsOspfExtLsdbMetricType   OBJECT-TYPE
        SYNTAX   INTEGER
                       { type1(1),
                         type2(2)
                        }
        MAX-ACCESS   read-only
        STATUS   current
        DESCRIPTION
           " The type of external metric.  If bit E is set, the metric
            specified is a Type 2 external metric.  This means the metric is
            considered larger than any link state path.  If bit E is zero,
            the specified metric is a Type 1 external metric.  This means
            that it is expressed in the same units as the link state metric
            (i.e., the same units as interface cost).  "
       ::= { fsOspfExtLsdbEntry 10 }

 fsOspfExtLsdbForwardAddr   OBJECT-TYPE
        SYNTAX   IpAddress
        MAX-ACCESS   read-only
        STATUS   current
        DESCRIPTION
           "  Data traffic for the advertised destination will be forwarded to
              this address.  If the Forwarding address is set to 0.0.0.0, data
              traffic will be forwarded instead to the LSA's originator (i.e.,
              the responsible AS boundary router)  ."
       ::= { fsOspfExtLsdbEntry 11 }

 fsOspfExtLsdbRouteTag   OBJECT-TYPE
        SYNTAX   Unsigned32
        MAX-ACCESS   read-only
        STATUS   current
        DESCRIPTION
           "A 32-bit field attached to each external route.  This is not
           used by the OSPF protocol itself.  It may be used to communicate
           information between AS boundary routers; the precise nature of
           such information is outside the scope of this specification."
       ::= { fsOspfExtLsdbEntry 12 }



 fsOspfExtLsdbOption   OBJECT-TYPE
        SYNTAX   Unsigned32
        MAX-ACCESS   read-only
        STATUS   current
        DESCRIPTION
           "the option field indicate which optional capabilities
            area associated with the LSA. "
        REFERENCE
          "OSPF Version 2, Appendix A.2, the Options Field"
       ::= { fsOspfExtLsdbEntry 13 }

fsOspfExtLsdbPacketLength   OBJECT-TYPE
        SYNTAX   Unsigned32(0..65535)
        MAX-ACCESS   read-only
        STATUS   current
        DESCRIPTION
           "the  lsa packet  length   ."
       ::= { fsOspfExtLsdbEntry 14 }

--Router Lsa's detail information table

fsOspfRouterLsaDetailTable OBJECT-TYPE
        SYNTAX   SEQUENCE OF FSOspfRouterLsaDetailEntry
        MAX-ACCESS   not-accessible
        STATUS   current
        DESCRIPTION
           "the router Lsa's detail Infromtion."
       ::= { fsOspfLsaDetailInfoMibsGroup  3 }

fsOspfRouterLsaDetailEntry OBJECT-TYPE
       SYNTAX   FSOspfRouterLsaDetailEntry
       MAX-ACCESS   not-accessible
       STATUS   current
       DESCRIPTION
          "the entry of this table."
      INDEX {fsOspfLsdbAreaId, fsOspfLsdbType,
             fsOspfLsdbLsid, fsOspfLsdbRouterId,
             fsOspfRouterLsaDetailLinkID
             }
      ::= { fsOspfRouterLsaDetailTable 1 }

FSOspfRouterLsaDetailEntry ::=
     SEQUENCE{
        fsOspfRouterLsaDetailLinkID
            IpAddress,
        fsOspfRouterLsaDetailLinkType
            INTEGER,
        fsOspfRouterLsaDetailLinkData
            IpAddress,
        fsOspfRouterLsaDetailTos0Metric
            Unsigned32
              }

 fsOspfRouterLsaDetailLinkID   OBJECT-TYPE
        SYNTAX   IpAddress
        MAX-ACCESS   read-only
        STATUS   current
        DESCRIPTION
           "router lsa's link ID Identifies the object that this router
            link connects to.  Value  depends on the link's Type.
            When connecting to an object that  also originates an
            LSA (i.e., another router or a transit  network) the
            Link ID is equal to the neighboring LSA's Link
           State ID.  This provides the key for looking up the neighboring
           LSA in the link state database during the routing table
           calculation. See Section 12.2 for more details.
                       Type   Link ID
                       ________________________________________
                       1      Neighboring router's Router ID
                       2      IP address of Designated Router
                       3      IP network/subnet number
                       4      Neighboring router's Router ID
           "
       ::= { fsOspfRouterLsaDetailEntry 1 }

 fsOspfRouterLsaDetailLinkType   OBJECT-TYPE
        SYNTAX   INTEGER{
                         pointtopointConnectionToAnotherRouter(1),
                         connectionToaTransitNetwork(2),
                         connectionToaStubNetwork(3),
                         virtualLink(4)
                        }
        MAX-ACCESS   read-only
        STATUS   current
        DESCRIPTION
           "router lsa's link type
            A quick description of the router link.  One of the following.
           Note that host routes are classified as links to stub networks
           with network mask of 0xffffffff."
       ::= { fsOspfRouterLsaDetailEntry 2 }

 fsOspfRouterLsaDetailLinkData   OBJECT-TYPE
        SYNTAX   IpAddress
        MAX-ACCESS   read-only
        STATUS   current
        DESCRIPTION
           " Value again depends on the link's Type field. For connections to
             stub networks, Link Data specifies the network's IP address
             mask. For unnumbered point-to-point connections, it specifies
             the interface's MIB-II  ifIndex value. For the other link
             types it specifies the router interface's IP address. This
            latter piece of information is needed during the routing table
            build process, when calculating the IP address of the next hop.            "
       ::= { fsOspfRouterLsaDetailEntry 3 }

fsOspfRouterLsaDetailTos0Metric   OBJECT-TYPE
        SYNTAX   Unsigned32
        MAX-ACCESS   read-only
        STATUS   current
        DESCRIPTION
           "TOS0-specific metric information."
       ::= { fsOspfRouterLsaDetailEntry 4 }


--NetWork Lsa's detail information table

fsOspfNetWorkLsaDetailTable OBJECT-TYPE
        SYNTAX   SEQUENCE OF FSOspfNetWorkLsaDetailEntry
        MAX-ACCESS   not-accessible
        STATUS   current
        DESCRIPTION
           "the NetWork Lsa's detail Infromtion."
       ::= { fsOspfLsaDetailInfoMibsGroup  4 }

fsOspfNetWorkLsaDetailEntry OBJECT-TYPE
       SYNTAX   FSOspfNetWorkLsaDetailEntry
       MAX-ACCESS   not-accessible
       STATUS   current
       DESCRIPTION
          "the entry of this table."
      INDEX {fsOspfLsdbAreaId, fsOspfLsdbType,
             fsOspfLsdbLsid, fsOspfLsdbRouterId,
             fsOspfNetWorkLsaDetailAttachedRouter
             }
      ::= { fsOspfNetWorkLsaDetailTable 1 }

FSOspfNetWorkLsaDetailEntry ::=
     SEQUENCE{
        fsOspfNetWorkLsaDetailAttachedRouter
            IpAddress,
        fsOspfNetWorkLsaDetailNetworkMask
            IpAddress
              }
 fsOspfNetWorkLsaDetailAttachedRouter   OBJECT-TYPE
        SYNTAX   IpAddress
        MAX-ACCESS   read-only
        STATUS   current
        DESCRIPTION
           " The Router IDs of each of the routers attached to the network.
             Actually, only those routers that are fully adjacent to the
             Designated Router are listed.  The Designated Router includes
             itself in this list.  The number of routers included can be
             deduced from the LSA header's length field.  "
       ::= { fsOspfNetWorkLsaDetailEntry 1 }

 fsOspfNetWorkLsaDetailNetworkMask   OBJECT-TYPE
        SYNTAX   IpAddress
        MAX-ACCESS   read-only
        STATUS   current
        DESCRIPTION
           "The IP address mask for the network.  For example, a class A
            network would have the mask 0xff000000."
       ::= { fsOspfNetWorkLsaDetailEntry 2 }


--fs Ospf Area Lsa Database Summary Table

fsOspfAreaLsaDBSumTable OBJECT-TYPE
        SYNTAX   SEQUENCE OF FSOspfAreaLsaDBSumEntry
        MAX-ACCESS   not-accessible
        STATUS   current
        DESCRIPTION
           "The OSPF Area LSA database summary Infromtion."
       ::= { fsOspfLsaDetailInfoMibsGroup  5 }

fsOspfAreaLsaDBSumEntry OBJECT-TYPE
       SYNTAX   FSOspfAreaLsaDBSumEntry
       MAX-ACCESS   not-accessible
       STATUS   current
       DESCRIPTION
          "the entry of this table."
      INDEX {fsOspfAreaLsaDBSumAreaId,
             fsOspfAreaLsaDBSumLsaType
             }
      ::= { fsOspfAreaLsaDBSumTable 1 }

FSOspfAreaLsaDBSumEntry ::=
     SEQUENCE{
        fsOspfAreaLsaDBSumAreaId
            IpAddress,
        fsOspfAreaLsaDBSumLsaType
            INTEGER,
        fsOspfAreaLsaDBSumCounts
            Counter32,
        fsOspfAreaLsaDBSumDeletes
            Counter32,
        fsOspfAreaLsaDBSumMaxage
            Counter32
            }
 fsOspfAreaLsaDBSumAreaId   OBJECT-TYPE
        SYNTAX   IpAddress
        MAX-ACCESS   read-only
        STATUS   current
        DESCRIPTION
           "The area Id."
       ::= { fsOspfAreaLsaDBSumEntry 1 }

 fsOspfAreaLsaDBSumLsaType   OBJECT-TYPE
        SYNTAX   INTEGER
        	{ routerLink (1),
           networkLink (2),
           summaryLink (3),
           asSummaryLink (4),
           --asExternalLink (5), because in each area,type 5 lsa is no meaning
                                 --it's only meaning in one router
           -- multicastLink (6),  not implement
           nssaExternalLink (7),
           subtotal(8)
           --subtotal is use for total counter for all type LSA in this area.
           }
        MAX-ACCESS   read-only
        STATUS   current
        DESCRIPTION
           "the entry's entry type."
       ::= { fsOspfAreaLsaDBSumEntry 2 }

 fsOspfAreaLsaDBSumCounts   OBJECT-TYPE
        SYNTAX   Counter32
        MAX-ACCESS   read-only
        STATUS   current
        DESCRIPTION
           " number os this type Lsa in this area ,
             if this type Lsa does not exist,this field is 0."
       ::= { fsOspfAreaLsaDBSumEntry 3 }

fsOspfAreaLsaDBSumDeletes    OBJECT-TYPE
        SYNTAX   Counter32
        MAX-ACCESS   read-only
        STATUS   current
        DESCRIPTION
           " number os this type Lsa which has been delete in this area ,
             if this type Lsa is not been deleted,this field is 0"
       ::= { fsOspfAreaLsaDBSumEntry 4 }

 fsOspfAreaLsaDBSumMaxage   OBJECT-TYPE
        SYNTAX   Counter32
        MAX-ACCESS   read-only
        STATUS   current
        DESCRIPTION
           " number of this type Lsa which has up to Maxage,
             if this type Lsa which has up to Maxage does not exist,
             this field is 0"
       ::= { fsOspfAreaLsaDBSumEntry 5 }


--fs Ospf Lsa Database total summary table

fsOspfLsaDBSumTable OBJECT-TYPE
        SYNTAX   SEQUENCE OF FSOspfLsaDBSumEntry
        MAX-ACCESS   not-accessible
        STATUS   current
        DESCRIPTION
           "LSA database total summary infromtion in the all areas ."
       ::= { fsOspfLsaDetailInfoMibsGroup  6 }

fsOspfLsaDBSumEntry OBJECT-TYPE
       SYNTAX   FSOspfLsaDBSumEntry
       MAX-ACCESS   not-accessible
       STATUS   current
       DESCRIPTION
          "the entry of this table."
      INDEX {
               fsOspfLsaDBSumLsaType
            }
      ::= { fsOspfLsaDBSumTable 1 }

FSOspfLsaDBSumEntry ::=
     SEQUENCE{
        fsOspfLsaDBSumLsaType
            INTEGER,
        fsOspfLsaDBSumCounts
            Counter32,
        fsOspfLsaDBSumDeletes
            Counter32,
        fsOspfLsaDBSumMaxage
            Counter32
              }

 fsOspfLsaDBSumLsaType   OBJECT-TYPE
        SYNTAX   INTEGER
        	{ routerLink (1),
           networkLink (2),
           summaryTotalLink (3),
           asSummaryTotalLink (4),
           asExternalLink (5),
           -- multicastLink (6),  not implement
           nssaExternalLink (7),
           total(8)
           --subtotal is use for total counter for all type LSA in this router.
                 }
        MAX-ACCESS   read-only
        STATUS   current
        DESCRIPTION
           "the table's entry type."
       ::= { fsOspfLsaDBSumEntry 1 }

 fsOspfLsaDBSumCounts   OBJECT-TYPE
        SYNTAX   Counter32
        MAX-ACCESS   read-only
        STATUS   current
        DESCRIPTION
           "total number of this type Lsa in all area ."
       ::= { fsOspfLsaDBSumEntry 2 }

fsOspfLsaDBSumDeletes    OBJECT-TYPE
        SYNTAX   Counter32
        MAX-ACCESS   read-only
        STATUS   current
        DESCRIPTION
           " total number of this type Lsa deleted in all area ."
       ::= { fsOspfLsaDBSumEntry 3 }

fsOspfLsaDBSumMaxage   OBJECT-TYPE
        SYNTAX   Counter32
        MAX-ACCESS   read-only
        STATUS   current
        DESCRIPTION
           "total number of this type Lsa which has been up to max age in all area "
       ::= { fsOspfLsaDBSumEntry 4 }


--      The OSPF Neighbor Table describes all neighbors in
--      the locality of the subject router.

fsOspfNeighborTable OBJECT-TYPE
        SYNTAX   SEQUENCE OF FSOspfNeighborEntry
        MAX-ACCESS   not-accessible
        STATUS   current
        DESCRIPTION
           "the neighbor detail infomation ."
       REFERENCE
          "ospfNbrTable in rfc1850"
       ::= { fsOspfMIBObjects  9 }

fsOspfNeighborEntry OBJECT-TYPE
       SYNTAX   FSOspfNeighborEntry
       MAX-ACCESS   not-accessible
       STATUS   current
       DESCRIPTION
          "the entry of this table."
      INDEX {   fsOspfNbrIpAddr,
                fsOspfNbrAddressLessIndex
             }
      ::= { fsOspfNeighborTable 1 }

FSOspfNeighborEntry ::=
     SEQUENCE{
        fsOspfNbrIpAddr
            IpAddress,
        fsOspfNbrAddressLessIndex
            Unsigned32,
        fsOspfNbrRtrId
            RouterID,
        fsOspfNbrOptions
            Unsigned32,
        fsOspfNbrPriority
            DesignatedRouterPriority,
        fsOspfNbrState
            INTEGER,
        fsOspfNbrEvents
            Counter32,
        fsOspfNbrLsRetransQLen
            Gauge32,
        fsOspfNbmaNbrStatus
            RowStatus,
        fsOspfNbmaNbrPermanence
            INTEGER,
        fsOspfNbrHelloSuppressed
            TruthValue,
        fsOspfNbrDeadTimeDueIn
            TimeTicks,
        fsOspfNbrNeighborUpTime
            TimeTicks,
        fsOspfNbrDR
            IpAddress,
        fsOspfNbrBDR
            IpAddress,
        fsOspfNbrArea
            IpAddress,
        fsOspfNbrRetransmissionNum
            Counter32,
        fsOspfNbrIfState
            INTEGER
              }
fsOspfNbrIpAddr OBJECT-TYPE
        SYNTAX   IpAddress
        MAX-ACCESS   read-only
        STATUS   current
        DESCRIPTION
           "The IP address this neighbor(neighbor's interface IP address)
           is using  in  its IP  Source  Address.  Note that, on addressless
           links, this will not be 0.0.0.0,  but  the  ad-
           dress of another of the neighbor's interfaces."
       ::= { fsOspfNeighborEntry 1 }


fsOspfNbrAddressLessIndex OBJECT-TYPE
        SYNTAX   Unsigned32
        MAX-ACCESS   read-only
        STATUS   current
        DESCRIPTION
           "On an interface having an  IP  Address,  zero.
           On  addressless  interfaces,  the corresponding
           value of ifIndex in the Internet Standard  MIB.
           On  row  creation, this can be derived from the
           instance."
       ::= { fsOspfNeighborEntry 2 }


fsOspfNbrRtrId OBJECT-TYPE
        SYNTAX   RouterID
        MAX-ACCESS   read-only
        STATUS   current
        DESCRIPTION
           "A 32-bit integer (represented as a type  IpAd-
           dress)  uniquely  identifying  the  neighboring
           router in the Autonomous System."
       ::= { fsOspfNeighborEntry 3 }


fsOspfNbrOptions OBJECT-TYPE
        SYNTAX   Unsigned32
        MAX-ACCESS   read-only
        STATUS   current
        DESCRIPTION
           "A Bit Mask corresponding to the neighbor's op-
           tions field.

           Bit 0, if set, indicates that the  system  will
           operate  on  Type of Service metrics other than
           TOS 0.  If zero, the neighbor will  ignore  all
           metrics except the TOS 0 metric.

           Bit 1, if set, indicates  that  the  associated
           area  accepts and operates on external informa-
           tion; if zero, it is a stub area.

           Bit 2, if set, indicates that the system is ca-
           pable  of routing IP Multicast datagrams; i.e.,
           that it implements the Multicast Extensions  to
           OSPF.

           Bit 3, if set, indicates  that  the  associated
           area  is  an  NSSA.  These areas are capable of
           carrying type 7 external advertisements,  which
           are  translated into type 5 external advertise-
           ments at NSSA borders."
       REFERENCE
          "OSPF Version 2, Section 12.1.2 Options"
      ::= { fsOspfNeighborEntry 4 }


fsOspfNbrPriority OBJECT-TYPE
        SYNTAX   DesignatedRouterPriority
        MAX-ACCESS   read-only
        STATUS   current
        DESCRIPTION
           "The priority of this neighbor in the designat-
           ed router election algorithm.  The value 0 sig-
           nifies that the neighbor is not eligible to be-
           come  the  designated router on this particular
           network."
       ::= { fsOspfNeighborEntry 5 }


fsOspfNbrState OBJECT-TYPE
        SYNTAX   INTEGER    {
                    down (1),
                    attempt (2),
                    init (3),
                    twoWay (4),
                    exchangeFS (5),
                    exchange (6),
                    loading (7),
                    full (8)
                  }
        MAX-ACCESS   read-only
        STATUS   current
        DESCRIPTION
           "The State of the relationship with this Neigh-
           bor."
       REFERENCE
          "OSPF Version 2, Section 10.1 Neighbor States"
      ::= { fsOspfNeighborEntry 6 }


fsOspfNbrEvents OBJECT-TYPE
        SYNTAX   Counter32
        MAX-ACCESS   read-only
        STATUS   current
        DESCRIPTION
           "The number of times this neighbor relationship
           has changed state, or an error has occurred."
       ::= { fsOspfNeighborEntry 7 }


fsOspfNbrLsRetransQLen OBJECT-TYPE
        SYNTAX   Gauge32
        MAX-ACCESS   read-only
        STATUS   current
        DESCRIPTION
           "The  current  length  of  the   retransmission
           queue."
       ::= { fsOspfNeighborEntry 8 }


fsOspfNbmaNbrStatus OBJECT-TYPE
        SYNTAX   RowStatus
        MAX-ACCESS   read-only
        STATUS   current
        DESCRIPTION
           "This variable displays the status of  the  en-
           try.  Setting it to 'invalid' has the effect of
           rendering it inoperative.  The internal  effect
           (row removal) is implementation dependent."
       ::= { fsOspfNeighborEntry 9 }


fsOspfNbmaNbrPermanence OBJECT-TYPE
        SYNTAX   INTEGER    {
                    dynamic (1),        -- learned through protocol
                    permanent (2)       -- configured address
                  }
        MAX-ACCESS   read-only
        STATUS   current
        DESCRIPTION
           "This variable displays the status of  the  en-
           try.   'dynamic'  and  'permanent' refer to how
           the neighbor became known."
       ::= { fsOspfNeighborEntry 10 }


fsOspfNbrHelloSuppressed OBJECT-TYPE
        SYNTAX   TruthValue
        MAX-ACCESS   read-only
        STATUS   current
        DESCRIPTION
           "Indicates whether Hellos are being  suppressed
           to the neighbor"
       ::= { fsOspfNeighborEntry 11 }

fsOspfNbrDeadTimeDueIn OBJECT-TYPE
        SYNTAX   TimeTicks
        MAX-ACCESS   read-only
        STATUS   current
        DESCRIPTION
           "if in this interval ,hello packet is not been received ,
            the neighbor is recognized dead.if received,it
            will recovery the dead time which has been setted."
       ::= { fsOspfNeighborEntry 12 }

fsOspfNbrNeighborUpTime OBJECT-TYPE
        SYNTAX   TimeTicks
        MAX-ACCESS   read-only
        STATUS   current
        DESCRIPTION
           "the time that the neighbor has been up."
       ::= { fsOspfNeighborEntry 13 }

fsOspfNbrDR OBJECT-TYPE
        SYNTAX   IpAddress
        MAX-ACCESS   read-only
        STATUS   current
        DESCRIPTION
           "the Designated Router of this neighbor."
       ::= { fsOspfNeighborEntry 14 }

fsOspfNbrBDR OBJECT-TYPE
        SYNTAX   IpAddress
        MAX-ACCESS   read-only
        STATUS   current
        DESCRIPTION
           "the Backup Designated Router of this neighbor."
       ::= { fsOspfNeighborEntry 15 }

fsOspfNbrArea  OBJECT-TYPE
	SYNTAX   IpAddress
        MAX-ACCESS   read-only
        STATUS   current
        DESCRIPTION
           "the area where the neighbor is in."
       ::= { fsOspfNeighborEntry 16 }

fsOspfNbrRetransmissionNum  OBJECT-TYPE
        SYNTAX   Counter32
        MAX-ACCESS   read-only
        STATUS   current
        DESCRIPTION
           "the Retransmission times."
       ::= { fsOspfNeighborEntry 17 }

fsOspfNbrIfState OBJECT-TYPE
        SYNTAX   INTEGER    {
                    other(0),
                    designatedRouter (1),
                    backupDesignatedRouter (2),
                    otherDesignatedRouter (3)
                  }
        MAX-ACCESS   read-only
        STATUS   current
        DESCRIPTION
           "The neighbor's interface State which connected to local router."
        ::= { fsOspfNeighborEntry 18 }

--OSPF border routing information
fsOspfRouteTable OBJECT-TYPE
    SYNTAX   SEQUENCE OF FSOspfRouteEntry
    MAX-ACCESS not-accessible
    STATUS   current
    DESCRIPTION
       "This entity's OSPF border routing table."
    ::= { fsOspfMIBObjects  10 }

fsOspfRouteEntry OBJECT-TYPE
    SYNTAX   FSOspfRouteEntry
    MAX-ACCESS not-accessible
    STATUS   current
    DESCRIPTION
       "A  route to  a  destination."
    INDEX {
        fsOspfRouteDest,
        fsOspfRouteArea,
        fsOspfRouteNextHop
        }
    ::= { fsOspfRouteTable 1 }

FSOspfRouteEntry ::=
    SEQUENCE {
        fsOspfRouteDest
            IpAddress,
        fsOspfRouteArea
            IpAddress,
        fsOspfRouteNextHop
             IpAddress,
        fsOspfRouteCost
            Unsigned32,
        fsOspfRouteType
            INTEGER,
        fsOspfRouteDRType
            INTEGER,
        fsOspfRouteSpfNo
            Counter32
   }

fsOspfRouteDest OBJECT-TYPE
    SYNTAX   IpAddress
    MAX-ACCESS read-only
    STATUS   current
    DESCRIPTION
       "Router ID of the destination."
    ::= { fsOspfRouteEntry 1 }

fsOspfRouteArea OBJECT-TYPE
    SYNTAX   IpAddress
    MAX-ACCESS read-only
    STATUS   current
    DESCRIPTION
       "The area ID of the area from which this route is learned."
    ::= { fsOspfRouteEntry 2 }

fsOspfRouteNextHop OBJECT-TYPE
    SYNTAX   IpAddress
    MAX-ACCESS read-only
    STATUS   current
    DESCRIPTION
       "Next hop toward the destination."
    ::= { fsOspfRouteEntry 3 }

fsOspfRouteCost OBJECT-TYPE
    SYNTAX   Unsigned32
    MAX-ACCESS read-only
    STATUS   current
    DESCRIPTION
       " Cost of using this route."

    ::= { fsOspfRouteEntry 4 }

fsOspfRouteDRType OBJECT-TYPE
    SYNTAX   INTEGER {
                      abr(1),
                      asbr(2),
                      both(3) --abr and asbr
                     }
    MAX-ACCESS read-only
    STATUS   current
    DESCRIPTION
       "The router type of the destination;
        it is either an ABR or ASBR or both."
    ::= { fsOspfRouteEntry 5 }

fsOspfRouteType  OBJECT-TYPE
    SYNTAX   INTEGER {
                       intral-area-route(1),
                       inter-area-route(2)
                       }
    MAX-ACCESS read-only
    STATUS   current
    DESCRIPTION
              "this field indicate this route is an intral area route
               or inter area route."
      ::= { fsOspfRouteEntry 6 }

fsOspfRouteSpfNo OBJECT-TYPE
    SYNTAX   Counter32
    MAX-ACCESS read-only
    STATUS   current
    DESCRIPTION
       " The internal number of the shortest path first (SPF) calculation that
         installs this route."
    ::= { fsOspfRouteEntry 7 }

-- conformance information

fsOspfMIBConformance OBJECT IDENTIFIER ::= { fsOspfMIB 2 }
fsOspfMIBCompliances OBJECT IDENTIFIER ::= { fsOspfMIBConformance 1 }
fsOspfMIBGroups      OBJECT IDENTIFIER ::= { fsOspfMIBConformance 2 }


-- compliance statements

fsOspfMIBCompliance MODULE-COMPLIANCE
        STATUS  current
        DESCRIPTION
                "The compliance statement for entities which implement
                the FS OSPF MIB"
        MODULE  -- this module
                MANDATORY-GROUPS {
                     fsOspfBaseMIBGroup,
                     fsOspfAreaMIBGroup,
                     fsOspfLsaMIBGroup,
                     fsOspfIfMIBGroup,
                     fsOspfVirtMIBGroup,
                     fsOspfNeighborMIBGroup,
                     fsOspfRouteInfoMIBGroup
                 }
        ::= { fsOspfMIBCompliances 1 }

-- units of conformance

fsOspfBaseMIBGroup OBJECT-GROUP
        OBJECTS {
               fsOspfMiniLsaInterval         ,
               fsOspfMiniLsaArrival          ,
               fsOspfAreasNum                ,
               fsOspfNormalAreasNum          ,
               fsOspfStubAreasNum            ,
               fsOspfNssaAreasNum            ,
               fsOspfSpfDelay                ,
               fsOspfSpfHoldTime             ,
               fsOspfAutoCostRefBandWidthRef ,
               fsOspfLsaGroupPacing          ,
               fsOspfInterDistance           ,
               fsOspfIntraDistance           ,
               fsOspfExternDistance          ,
               fsOspfLogAdjChangeNotify      ,
               fsOspfPassiveStatus           ,
               fsOspfRFC1583Compatibility    ,
               fsOspfRouteRedisDefMetricVal

        }
        STATUS  current
        DESCRIPTION
                "A collection of general objects providing OSPF managment."
        ::= { fsOspfMIBGroups 1 }

fsOspfAreaMIBGroup OBJECT-GROUP
        OBJECTS {
               fsOspfAreaId,
               fsOspfAuthType,
               fsOspfImportAsExtern,
               fsOspfSpfRuns,
               fsOspfAreaBdrRtrCount,
               fsOspfAsBdrRtrCount,
               fsOspfAreaLsaCount,
               fsOspfAreaLsaCksumSum,
               fsOspfAreaSummary,
               fsOspfAreaStatus,
               fsOspfAreaInterfaceNum,
               fsOspfAreaNssaIsRedistribution,
               fsOspfAreaNssaIsDefInfoOriginate,
               fsOspfNetWorkAreaID,
               fsOspfNetWorkAddress,
               fsOspfNetWorkMask,
               fsOspfNetWorkStatus
        }
        STATUS  current
        DESCRIPTION
                "A collection of area objects providing OSPF managment."
        ::= { fsOspfMIBGroups 2 }

fsOspfLsaMIBGroup OBJECT-GROUP
        OBJECTS {
           fsOspfLsdbAreaId,
           fsOspfLsdbType,
           fsOspfLsdbLsid,
           fsOspfLsdbRouterId,
           fsOspfLsdbSequence,
           fsOspfLsdbAge,
           fsOspfLsdbChecksum,
           fsOspfLsdbAdvertisement,
           fsOspfLsdbLinkNum,
           fsOspfLsdbPacketLength,
           fsOspfSummaryLsaNetworkMask,
           fsOspfSummaryLsaTos0Metric,
           fsOspfNssaLsaDetailMetricType,
           fsOspfNssaLsaDetailForwardAddr ,
           fsOspfNssaLsaDetailRouteTag ,
           fsOspfLsdbOption,

           fsOspfExtLsdbType,
           fsOspfExtLsdbLsid,
           fsOspfExtLsdbRouterId,
           fsOspfExtLsdbSequence,
           fsOspfExtLsdbAge,
           fsOspfExtLsdbChecksum,
           fsOspfExtLsdbAdvertisement,
           fsOspfExtLsdbNetworkMask,
           fsOspfExtLsdbMetricType,
           fsOspfExtLsdbForwardAddr,
           fsOspfExtLsdbRouteTag,
           fsOspfExtLsdbMetric,
           fsOspfExtLsdbOption,
           fsOspfExtLsdbPacketLength,

           fsOspfRouterLsaDetailLinkID,
           fsOspfRouterLsaDetailLinkType,
           fsOspfRouterLsaDetailLinkData,
           fsOspfRouterLsaDetailTos0Metric,

           fsOspfNetWorkLsaDetailAttachedRouter,
           fsOspfNetWorkLsaDetailNetworkMask,

           fsOspfAreaLsaDBSumAreaId,
           fsOspfAreaLsaDBSumLsaType,
           fsOspfAreaLsaDBSumCounts   ,
           fsOspfAreaLsaDBSumDeletes,
           fsOspfAreaLsaDBSumMaxage,

           fsOspfLsaDBSumLsaType,
           fsOspfLsaDBSumCounts,
           fsOspfLsaDBSumDeletes,
           fsOspfLsaDBSumMaxage

        }
        STATUS  current
        DESCRIPTION
                "A collection of OSPF Link State Database objects providing OSPF managment."
        ::= { fsOspfMIBGroups 3 }

fsOspfIfMIBGroup OBJECT-GROUP
        OBJECTS {
         fsOspfIfIpAddress,
         fsOspfAddressLessIf,
         fsOspfIfAreaId,
         fsOspfIfType,
         fsOspfIfAdminStat,
         fsOspfIfRtrPriority,
         fsOspfIfTransitDelay,
         fsOspfIfRetransInterval,
         fsOspfIfHelloInterval,
         fsOspfIfRtrDeadInterval,
         fsOspfIfPollInterval,
         fsOspfIfState,
         fsOspfIfDesignatedRouter,
         fsOspfIfBackupDesignatedRouter,
         fsOspfIfEvents,
         fsOspfIfAuthType,
         fsOspfIfAuthKey,
         fsOspfIfStatus,
         fsOspfIfMulticastForwarding,
         fsOspfIfDemand,
         fsOspfIfDatabaseFilterAllOut,
         fsOspfIfDesignateRouterId     ,
         fsOspfIfBackupDesignateRouterId ,
--         fsOspfIfMd5AuthKeyId,
         fsOspfIfWaitInternal,
         fsOspfIfPassiveStatus,
         fsOspfIfCurrentUsedMd5AuthKeyId,

         fsOspfIfMd5AuthKeyIf,
         fsOspfIfMd5AuthKeyId,
         fsOspfIfMd5AuthKey,
         fsOspfIfMd5AuthKeySt

        }
        STATUS  current
        DESCRIPTION
                "A collection of OSPF interface managment."
        ::= { fsOspfMIBGroups 4 }


fsOspfVirtMIBGroup OBJECT-GROUP
        OBJECTS {
        fsOspfVirtIfAreaId,
        fsOspfVirtIfNeighbor,
        fsOspfVirtIfTransitDelay,
        fsOspfVirtIfRetransInterval,
        fsOspfVirtIfHelloInterval,
        fsOspfVirtIfRtrDeadInterval,
        fsOspfVirtIfState,
        fsOspfVirtIfEvents,
        fsOspfVirtIfAuthType,
        fsOspfVirtIfAuthKey,
        fsOspfVirtIfStatus,
        fsOspfVirtCost,
        fsOspfVirtNativeIfIndex,
        fsOspfVirtLinkState,
        fsOspfVirtHelloDueIn,

        fsOspfVirtIfMd5AuthKeyAreaId,
        fsOspfVirtIfMd5AuthKeyNeighbor,
        fsOspfVirtIfMd5AuthKeyId,
        fsOspfVirtIfMd5AuthKey,
        fsOspfVirtIfMd5AuthKeySt,
        fsOspfVirtCurrentUsedMd5AuthKeyId
        }
        STATUS  current
        DESCRIPTION
                "A collection of OSPF Virtual Link managment."
        ::= { fsOspfMIBGroups 5 }

fsOspfNeighborMIBGroup OBJECT-GROUP
        OBJECTS {
        fsOspfNbrIpAddr,
        fsOspfNbrAddressLessIndex,
        fsOspfNbrRtrId,
        fsOspfNbrOptions,
        fsOspfNbrPriority,
        fsOspfNbrState,
        fsOspfNbrEvents,
        fsOspfNbrLsRetransQLen,
        fsOspfNbmaNbrStatus,
        fsOspfNbmaNbrPermanence,
        fsOspfNbrHelloSuppressed,
        fsOspfNbrDeadTimeDueIn,
        fsOspfNbrNeighborUpTime,
        fsOspfNbrDR,
        fsOspfNbrBDR,
        fsOspfNbrArea,
        fsOspfNbrRetransmissionNum
        }
        STATUS  current
        DESCRIPTION
                "A collection of OSPF Neighbor information."
        ::= { fsOspfMIBGroups 6 }

fsOspfRouteInfoMIBGroup OBJECT-GROUP
        OBJECTS {
        fsOspfRouteType,
        fsOspfRouteDest,
        fsOspfRouteNextHop,
        fsOspfRouteCost,
        fsOspfRouteDRType,
        fsOspfRouteArea,
        fsOspfRouteSpfNo
        }
        STATUS  current
        DESCRIPTION
                "A collection of OSPF route information."
        ::= { fsOspfMIBGroups 7 }

-- -------------------------------------------------------------
-- Compliance statements
-- -------------------------------------------------------------
ospfMIBConformance OBJECT IDENTIFIER ::= { fsOspfMIB 3 }
ospfMIBCompliances OBJECT IDENTIFIER ::= { ospfMIBConformance 1 }

ospfExternCompliance MODULE-COMPLIANCE
    STATUS      current
    DESCRIPTION
        "The compliance statement for device support of OSPF
         services."

    MODULE
--        OBJECT           ospfASBdrRtrStatus
--        MIN-ACCESS       read-only
--        DESCRIPTION     "Write access is not required."
--
--        OBJECT           ospfTOSSupport
--        MIN-ACCESS       read-only
--        DESCRIPTION     "Write access is not required."
--
--        OBJECT           ospfExtLsdbLimit
--        MIN-ACCESS       read-only
--        DESCRIPTION     "Write access is not required."
--
--        OBJECT           ospfMulticastExtensions
--        MIN-ACCESS       read-only
--        DESCRIPTION     "Write access is not required."
--
--        OBJECT           ospfExitOverflowInterval
--        MIN-ACCESS       read-only
--        DESCRIPTION     "Write access is not required."
--
--        OBJECT           ospfDemandExtensions
--        MIN-ACCESS       read-only
--        DESCRIPTION     "Write access is not required."
--
--        OBJECT           ospfIfAreaId
--        MIN-ACCESS       read-only
--        DESCRIPTION     "Write access is not required."
--
--        OBJECT           ospfIfStatus
--        MIN-ACCESS       read-only
--        DESCRIPTION     "Create access is not required."
--
--
--        OBJECT           ospfStubMetric
--        MIN-ACCESS       read-write
--        DESCRIPTION     "Create access is not required."
--
--        OBJECT           ospfStubStatus
--        MIN-ACCESS       read-only
--        DESCRIPTION     "Write access is not required."
--
--        OBJECT           ospfStubMetricType
--        MIN-ACCESS       read-write
--        DESCRIPTION     "Create access is not required."
--
--        OBJECT           ospfIfAdminStat
--        MIN-ACCESS       read-only
--        DESCRIPTION     "Write access is not required."
--
--        OBJECT           ospfNbmaNbrStatus
--        MIN-ACCESS       read-only
--        DESCRIPTION     "Read-create access is not required."
--
--        OBJECT           ospfNbrPriority
--        MIN-ACCESS       read-only
--        DESCRIPTION     "Read-create access is not required."
--
--        OBJECT           ospfIfPollInterval
--        MIN-ACCESS       read-only
--        DESCRIPTION     "Read-create access is not required."
--
--        OBJECT           ospfIfTransitDelay
--        SYNTAX           Unsigned32 (1..65535)
--        DESCRIPTION     "Range of value is changed."
--
--        OBJECT           ospfIfRetransInterval
--        SYNTAX           Unsigned32 (1..65535)
--        DESCRIPTION     "Range of value is changed."
--
--        OBJECT           ospfVirtIfTransitDelay
--        SYNTAX           Unsigned32 (1..65535)
--        DESCRIPTION     "Range of value is changed."
--
--        OBJECT           ospfIfType
--        SYNTAX           INTEGER    {
--                             broadcast (1),
--                             nbma (2),
--                             pointToPoint (3),
--                             pointToMultipoint (5),
--                             loopback(6)
--                         }
--        DESCRIPTION     "add type 'loopback'."
--
--        OBJECT           ospfVirtIfRetransInterval
--        SYNTAX           Unsigned32 (1..65535)
--        DESCRIPTION     "Range of value is changed."

        OBJECT           fsOspfVirtIfRtrDeadInterval
        SYNTAX           PositiveInteger
        DESCRIPTION     "default value change from 60 to 40."

    ::= { ospfMIBCompliances 1 }


END
