-- *****************************************************************
-- FS-GATEWAY-SMI.mib: FS GATEWAY SMI File
--
-- May. 2010, panshiyong
--
-- Copyright (c) 2010 by FS.COM Inc..
-- All rights reserved.
--
-- *****************************************************************
--

FS-GATEWAY-SMI DEFINITIONS ::= BEGIN

IMPORTS
        MODULE-IDENTITY,
        OBJECT-IDENTITY
                FROM SNMPv2-SMI
        products
                FROM FS-SMI;

gateway          OBJECT IDENTIFIER ::= { products 5 }

gatewayMib MODULE-IDENTITY
        LAST-UPDATED "201005250000Z"
        ORGANIZATION "FS.COM Inc.."
        CONTACT-INFO
                "
                Tel: 400-865-2852

                E-mail: https://www.fs.com/live_chat_service_mail.html"
        DESCRIPTION
                "The Structure of Management Information for the
                 FS enterprise."
        REVISION      "201005250000Z"
        DESCRIPTION
                "Initial version of this MIB module."
        ::= { gateway 1 }

fsGatewayProducts OBJECT-IDENTITY
        STATUS  current
        DESCRIPTION
                "fsGatewayProducts is the root OBJECT IDENTIFIER from
                 which sysObjectID values are assigned for gateway.  Actual
                 values are defined in FS-PRODUCTS-MIB."
        ::= { gatewayMib 1 }

END
