-- *****************************************************************
-- FS-PFXV6-MIB.mib:  FS PFXv6 MIB file
--
--  2015.01.13, huangguohua@fs.com.cn
--
-- Copyright (c) 2002 by FS.COM Inc..
-- All rights reserved.
--
-- *****************************************************************
--

FS-PFXV6-MIB DEFINITIONS ::= BEGIN

IMPORTS
        MODULE-IDENTITY,
        OBJECT-TYPE,
        IpAddress,
        Integer32,
        Counter32
                FROM SNMPv2-SMI
        RowStatus,
        DisplayString,
        PhysAddress
                FROM SNMPv2-TC
        MODULE-COMPLIANCE,
        OBJECT-GROUP
                FROM SNMPv2-CONF
        IfIndex
                FROM FS-TC
        fsMgmt
                FROM FS-SMI;

fsPFXv6MIB MODULE-IDENTITY
        LAST-UPDATED "201501130000Z"
        ORGANIZATION "FS.COM Inc.."
        CONTACT-INFO
                "
                Tel: 400-865-2852

                E-mail: https://www.fs.com/live_chat_service_mail.html"
        DESCRIPTION
                "This module defines fs pfxv6 mibs."
        REVISION      "201501130000Z"
        DESCRIPTION
                "Initial version of this MIB module."
        ::= { fsMgmt 134}

fsPFXv6MIBObjects OBJECT IDENTIFIER ::= { fsPFXv6MIB 1 }


 -- IPv6 local pool table

 fsPFXv6Table OBJECT-TYPE
     SYNTAX  SEQUENCE OF FSPFXv6Entry
     MAX-ACCESS  not-accessible
     STATUS  current
     DESCRIPTION
             "The IPv6 local pool statistics."
     ::= { fsPFXv6MIBObjects 1 }

 fsPFXv6Entry OBJECT-TYPE
     SYNTAX  FSPFXv6Entry
     MAX-ACCESS  not-accessible
     STATUS  current
     DESCRIPTION
             "Each pool entry statistics."
     INDEX   { fsPFXv6Name }
     ::= { fsPFXv6Table 1 }

 FSPFXv6Entry ::=
     SEQUENCE {
         fsPFXv6Name
             DisplayString,
         fsPFXv6Total
             Integer32,
         fsPFXv6Rejects
             Integer32,
         fsPFXv6Accepts
             Integer32,
         fsPFXv6Frees
             Integer32,
         fsPFXv6Userate
             INTEGER
     }

 fsPFXv6Name OBJECT-TYPE
     SYNTAX  DisplayString (SIZE (0..32))
     MAX-ACCESS  read-only
     STATUS  current
     DESCRIPTION
             "The pool name."
     ::= { fsPFXv6Entry 1 }

 fsPFXv6Total OBJECT-TYPE
     SYNTAX  Integer32
     MAX-ACCESS  read-only
     STATUS  current
     DESCRIPTION
             "The total prefix number of pool."
     ::= { fsPFXv6Entry 2 }

 fsPFXv6Rejects OBJECT-TYPE
     SYNTAX  Integer32
     MAX-ACCESS  read-only
     STATUS  current
     DESCRIPTION
             "Rejects number of pool."
     ::= { fsPFXv6Entry 3 }

 fsPFXv6Accepts OBJECT-TYPE
     SYNTAX  Integer32
     MAX-ACCESS  read-only
     STATUS  current
     DESCRIPTION
             "Accepts number of pool."
     ::= { fsPFXv6Entry 4 }

 fsPFXv6Frees OBJECT-TYPE
     SYNTAX  Integer32
     MAX-ACCESS  read-only
     STATUS  current
     DESCRIPTION
             "Frees number of pool."
     ::= { fsPFXv6Entry 5 }

 fsPFXv6Userate OBJECT-TYPE
     SYNTAX  INTEGER (0..100)
     MAX-ACCESS  read-only
     STATUS  current
     DESCRIPTION
             "Use rate of pool."
     ::= { fsPFXv6Entry 6 }


 --  Interface configure pool for SLAAC

 fsPFXv6IfTable OBJECT-TYPE
     SYNTAX  SEQUENCE OF FSPFXv6IfEntry
     MAX-ACCESS  not-accessible
     STATUS  current
     DESCRIPTION
             "Interface configure pool for SLAAC."
     ::= { fsPFXv6MIBObjects 2 }

 fsPFXv6IfEntry OBJECT-TYPE
     SYNTAX  FSPFXv6IfEntry
     MAX-ACCESS  not-accessible
     STATUS  current
     DESCRIPTION
             "Each pool entry statistics"
     INDEX   { fsPFXv6IfIfIndex}
     ::= { fsPFXv6IfTable 1 }

 FSPFXv6IfEntry ::=
     SEQUENCE {
         fsPFXv6IfIfIndex
             IfIndex,
         fsPFXv6IfName
             DisplayString,
         fsPFXv6IfTotal
             Integer32,
         fsPFXv6IfRejects
             Integer32,
         fsPFXv6IfAccepts
             Integer32,
         fsPFXv6IfFrees
             Integer32,
         fsPFXv6IfUserate
             INTEGER
     }

 fsPFXv6IfIfIndex OBJECT-TYPE
     SYNTAX  IfIndex
     MAX-ACCESS  read-only
     STATUS  current
     DESCRIPTION
             "The interface on which this entry's equivalence
             is effective.  The interface identified by a
             particular value of this index is the same
             interface as identified by the same value of
             ifIndex."
     ::= { fsPFXv6IfEntry 1 }

 fsPFXv6IfName OBJECT-TYPE
     SYNTAX  DisplayString (SIZE (0..32))
     MAX-ACCESS  read-only
     STATUS  current
     DESCRIPTION
             "The pool name."
     ::= { fsPFXv6IfEntry 2 }

 fsPFXv6IfTotal OBJECT-TYPE
     SYNTAX  Integer32
     MAX-ACCESS  read-only
     STATUS  current
     DESCRIPTION
             "The total prefix number of pool."
     ::= { fsPFXv6IfEntry 3 }

 fsPFXv6IfRejects OBJECT-TYPE
     SYNTAX  Integer32
     MAX-ACCESS  read-only
     STATUS  current
     DESCRIPTION
             "Rejects number of pool."
     ::= { fsPFXv6IfEntry 4 }

 fsPFXv6IfAccepts OBJECT-TYPE
     SYNTAX  Integer32
     MAX-ACCESS  read-only
     STATUS  current
     DESCRIPTION
             "Accepts number of pool."
     ::= { fsPFXv6IfEntry 5 }

 fsPFXv6IfFrees OBJECT-TYPE
     SYNTAX  Integer32
     MAX-ACCESS  read-only
     STATUS  current
     DESCRIPTION
             "Frees number of pool."
     ::= { fsPFXv6IfEntry 6 }

 fsPFXv6IfUserate OBJECT-TYPE
     SYNTAX  INTEGER (0..100)
     MAX-ACCESS  read-only
     STATUS  current
     DESCRIPTION
             "Use rate of pool."
     ::= { fsPFXv6IfEntry 7 }

 --  Counter for PFXv6

 fsSlaacRequestNumber OBJECT-TYPE
        SYNTAX Counter32
        MAX-ACCESS read-only
        STATUS current
        DESCRIPTION
            "Number of SLAAC request this system have"
       ::= { fsPFXv6MIBObjects 3 }

 fsSlaacRequestSuccessNumber OBJECT-TYPE
        SYNTAX Counter32
        MAX-ACCESS read-only
        STATUS current
        DESCRIPTION
            "Success Number of SLAAC request this system have"
        ::= { fsPFXv6MIBObjects 4 }

fsPFXv6MIBConformance OBJECT IDENTIFIER ::= { fsPFXv6MIB 2 }
fsPFXv6MIBCompliances OBJECT IDENTIFIER ::= { fsPFXv6MIBConformance 1 }
fsPFXv6MIBGroups      OBJECT IDENTIFIER ::= { fsPFXv6MIBConformance 2 }


-- compliance statements

fsPFXv6MIBCompliance MODULE-COMPLIANCE
        STATUS  current
        DESCRIPTION
                "The compliance statement for entities which implement
                the FS PFXv6 MIB"
        MODULE  -- this module
                MANDATORY-GROUPS { fsPFXv6MIBGroup
                 }
        ::= { fsPFXv6MIBCompliances 1 }

-- units of conformance

fsPFXv6MIBGroup OBJECT-GROUP
        OBJECTS {
         fsPFXv6Name,
         fsPFXv6Total,
         fsPFXv6Rejects,
         fsPFXv6Accepts,
         fsPFXv6Frees,
		 fsPFXv6Userate,
         fsPFXv6IfIfIndex,
         fsPFXv6IfName,
         fsPFXv6IfTotal,
         fsPFXv6IfRejects,
         fsPFXv6IfAccepts,
         fsPFXv6IfFrees,
		 fsPFXv6IfUserate,
         fsSlaacRequestNumber,
         fsSlaacRequestSuccessNumber
        }
        STATUS  current
        DESCRIPTION
                "A collection of objects providing pfxv6 management and
                opertion to a FS agent."
        ::= { fsPFXv6MIBGroups 1 }

END
