-- *******************************************************************
-- FS-FRAME-RELAY-MIB.mib
--        FS Frame Relay MIB file, providing Frame Relay specific
--        information that are either excluded by RFC 1315 (FR DTE MIB)
--        or specific to FS products.
--
-- May 2009, juncheng hong
--
-- Copyright (c) 2009 by FS.COM Inc..
-- All rights reserved.
--
-- *******************************************************************

-- Note:
-- Until future change, it is no intention for this MIB to cover
-- every Frame Relay related feature, configuration statement, or
-- exec command display. The focus is to provide key information
-- that are unavailable in any of the existing MIB's, but are
-- currently available through the Frame Relay show commands and/or
-- configuration displays.


FS-FRAME-RELAY-MIB DEFINITIONS ::= BEGIN

IMPORTS
        MODULE-IDENTITY,
        OBJECT-TYPE,
        Counter32,
        Integer32,
        IpAddress
                FROM SNMPv2-SMI
        MODULE-COMPLIANCE,
        OBJECT-GROUP
                FROM SNMPv2-CONF
        TEXTUAL-CONVENTION,
        DisplayString,
        TruthValue
                FROM SNMPv2-TC
        fsMgmt
                FROM FS-SMI
        InterfaceIndex,
        ifIndex
                FROM IF-MIB
        frDlcmiEntry,
        frCircuitEntry,
        frCircuitIfIndex,
        frCircuitDlci
                FROM FRAME-RELAY-DTE-MIB;

-- All table indicies in this MIB that involve interface index and
-- DLCI are derived from frCircuitIfIndex and frCircuitDlci
-- respectively from RFC 1315.

fsFrameRelayMIB     MODULE-IDENTITY
        LAST-UPDATED   "200010130000Z"
        ORGANIZATION   "FS.COM Inc.."
        CONTACT-INFO
                "
                Tel: 400-865-2852

                E-mail: https://www.fs.com/live_chat_service_mail.html"
        DESCRIPTION
                "FS Frame Relay MIB"

        REVISION        "200010130000Z"
        DESCRIPTION
                "(1) Added objects of FR Switching, FR Fragmentation
                and FR/ATM Interworking.
                (2) Objects for per PVC I/O rate is added to
                cfrExtCircuitTable"

        REVISION        "200005220000Z"
        DESCRIPTION
                "(1) Added  ELMI subgroup for ELMI objects."

        REVISION        "200005160000Z"
        DESCRIPTION
                "(1) Added Traffic Shaping parameter objects to
                fsfrExtCircuitTable.
                (2) Deprecated fsfrSvcMinThruputOut and
                fsfrSvcMinThruputIn. Added fsfrExtCircuitMinThruputOut
                and fsfrExtCircuitMinThruputIn in fsfrExtCircuitTable
                inorder to make them applicable to both PVC/SVC.
                (3) Added fsfrExtCircuitBandwidth object to
                fsfrExtCircuitTable."

        REVISION        "200905180000Z"
        DESCRIPTION
                "(1) add an integer value for fsfrMapPayloadCompressType;
                (2) reword the Description statements for
                      { fsfrMapPayloadCompressType,
                      fsfrExtCircuitUncompressIns,
                      fsfrExtCircuitUncompressOuts }
                so that they are not limited to software compression."

        REVISION        "9908210000Z"
        DESCRIPTION
                "(1) Added fsfrExtCircuitUncompressOuts and
                fsfrExtCircuitUncompressIns to the circuit subgroup;
                (2) Added fsfrMapRtpHdrCompress and fsfrMapPayloadCompressType
                to the mapping subgroup;
                (3) fsfrMapPayloadCompress becomes deprecated, obsoleted
                by fsfrMapPayloadCompressType;
                (4) frCircuitSentOctets and frCircuitReceivedOctets
                per RFC1315 will reflect the number of bytes in Frame Relay
                frames sent to and received from the physical layer. Same
                effect is applied to ifOutOctets and ifInOctets as well
                when ifIndex refers to a Frame Relay subinterface."

        REVISION        "9608150000Z"
        DESCRIPTION
                "Initial version of this MIB module."

        ::= { fsMgmt 50 }


fsFrMIBObjects OBJECT IDENTIFIER ::= { fsFrameRelayMIB 1 }

-- Subgroups:
-- The objects include four subgroups on the topics of
--        o LMI (Local Management Interface, see ANSI T1.617 Annex D and
--          the Frame Relay Specification with Extensions by DEC,
--          NT, StrataCom, and FS.),
--        o Virtual circuits,
--        o Circuit mapping information,
--        o SVC (switched virtual circuits, see CCITT/ITU Q.933 and
--           Q.922.),
--        o ELMI (Enhanced Link Management Interface) objects,
--        o Fragmentation objects,
--        o Frame Relay/ATM Network Interworking objects,
--        o Frame Relay/ATM PVC Service Interworking objects, and
--        o Frame Relay Switching objects.

fsfrLmiObjs        OBJECT IDENTIFIER ::= { fsFrMIBObjects 1 }

fsfrCircuitObjs    OBJECT IDENTIFIER ::= { fsFrMIBObjects 2 }

fsfrMapObjs        OBJECT IDENTIFIER ::= { fsFrMIBObjects 3 }

fsfrSvcObjs        OBJECT IDENTIFIER ::= { fsFrMIBObjects 4 }

fsfrElmiObjs       OBJECT IDENTIFIER ::= { fsFrMIBObjects 5 }

fsfrFragObjs       OBJECT IDENTIFIER ::= { fsFrMIBObjects 6 }

fsfrConnectionObjs  OBJECT IDENTIFIER ::= { fsFrMIBObjects 7 }

DlciNumber ::= TEXTUAL-CONVENTION
        STATUS  current
        DESCRIPTION
                "Numerical format of Data Link Connection Identifier
                (DLCI) in decimal, identical to the 'DLCI' as INTEGER
                of 0..DLCINumber in RFC1315. The maximum value depends
                on Frame Relay implementation, which is currently set
                to be 1023 for 2-octet address format per UNI
                Implementation Agreement FRF.1."
        SYNTAX        INTEGER (0..1023)

FSfrMapProtocols ::= TEXTUAL-CONVENTION
        STATUS  current
        DESCRIPTION
                "FS link types (network protocols) that run
                over Frame Relay. Associated values, except for
                wildcard, match assigned values of internal software
                respectively."
        SYNTAX  INTEGER
        {
                arp(1),
                serialArp(6),
                ip(7),
                xns(10),
                novell(11),
                apollo(12),
                vines(13),
                appletalk(16),
                ieeeSpanning(18),
                decnet(22),
                clns(25),
                rsrb(37),
                bridge(38),
                stun(39),
                frArp(40),
                uncompressedTcp(47),
                compressedTcp(48),
                llc2(49),
                frSwitch(53),
                dlsw(63),
                nhrp(74),
                compressedRtp(83),
                wildcard(999)        -- either means no applicable type for
                                -- the circuit or means point-to-point
        }


-- LMI sub-group {

fsfrLmiTable OBJECT-TYPE
        SYNTAX      SEQUENCE OF FSfrLmiEntry
        MAX-ACCESS  not-accessible
        STATUS      current
        DESCRIPTION
                "Table of Frame Relay LMI information that are
                either supplemental to the frDlcmiTable of RFC 1315
                or specific to FS's implementation."
        REFERENCE
                "American National Standard T1.617-1991, Annex D"
        ::= { fsfrLmiObjs 1 }

fsfrLmiEntry OBJECT-TYPE
        SYNTAX      FSfrLmiEntry
        MAX-ACCESS  not-accessible
        STATUS      current
        DESCRIPTION
                "Each entry of the table contains information
                of Frame Relay LMI over one physical interface.
                They are mostly FR generic and some FS specific."
        AUGMENTS { frDlcmiEntry }
        ::= { fsfrLmiTable 1 }

FSfrLmiEntry ::=
        SEQUENCE {
            fsfrLmiLinkstatus             INTEGER,
            fsfrLmiLinkType               INTEGER,
            fsfrLmiEnquiryIns             Counter32,
            fsfrLmiEnquiryOuts            Counter32,
            fsfrLmiStatusIns              Counter32,
            fsfrLmiStatusOuts             Counter32,
            fsfrLmiUpdateStatusIns        Counter32,
            fsfrLmiUpdateStatusOuts       Counter32,
            fsfrLmiStatusTimeouts         Counter32,
            fsfrLmiStatusEnqTimeouts      Counter32,
            fsfrLmiN392Dce                INTEGER,
            fsfrLmiN393Dce                INTEGER,
            fsfrLmiT392Dce                INTEGER
        }

-- Note: for LMI type, i.e. ANSI or cisco, see frDlcmiState
-- of RFC 1315. Also, for LMI parameters for DTE not listed here,
-- e.g. T391, N391, N392, and N393, see RFC 1315.
--
-- Although based on the current logic the value for
-- cfrLmiDLstatus is equivalent to ifOperStatus, the object
-- remains herein for future possible development change.

fsfrLmiLinkstatus OBJECT-TYPE
        SYNTAX  INTEGER {
                    up(1),
                    down(2)
                }
        MAX-ACCESS  read-only
        STATUS      current
        DESCRIPTION
                "Data link status via LMI."
        ::= { fsfrLmiEntry 1 }

fsfrLmiLinkType OBJECT-TYPE
        SYNTAX  INTEGER {
                    dte(1),
                    dce(2),
                    nni(3)
                }
        MAX-ACCESS  read-only
        STATUS      current
        DESCRIPTION
                "Frame Relay link type."
        ::= { fsfrLmiEntry 2 }


fsfrLmiEnquiryIns OBJECT-TYPE
        SYNTAX      Counter32
        UNITS       "messages"
        MAX-ACCESS  read-only
        STATUS      current
        DESCRIPTION
                "Number of Status Enquiry messages received."
        ::= { fsfrLmiEntry 3 }

fsfrLmiEnquiryOuts OBJECT-TYPE
        SYNTAX      Counter32
        UNITS       "messages"
        MAX-ACCESS  read-only
        STATUS      current
        DESCRIPTION
                "Number of Status Enquiry messages sent."
        ::= { fsfrLmiEntry 4 }

fsfrLmiStatusIns OBJECT-TYPE
        SYNTAX      Counter32
        UNITS       "messages"
        MAX-ACCESS  read-only
        STATUS      current
        DESCRIPTION
                "Number of Status messages received."
        ::= { fsfrLmiEntry 5 }

fsfrLmiStatusOuts OBJECT-TYPE
        SYNTAX      Counter32
        UNITS       "messages"
        MAX-ACCESS  read-only
        STATUS      current
        DESCRIPTION
                "Number of Status messages sent."
        ::= { fsfrLmiEntry 6 }

fsfrLmiUpdateStatusIns OBJECT-TYPE
        SYNTAX      Counter32
        UNITS       "messages"
        MAX-ACCESS  read-only
        STATUS      current
        DESCRIPTION
                "Number of Update Status messages received."
        ::= { fsfrLmiEntry 7 }

fsfrLmiUpdateStatusOuts OBJECT-TYPE
        SYNTAX      Counter32
        UNITS       "messages"
        MAX-ACCESS  read-only
        STATUS      current
        DESCRIPTION
                "Number of Update Status messages sent"
        ::= { fsfrLmiEntry 8 }

fsfrLmiStatusTimeouts OBJECT-TYPE
        SYNTAX      Counter32
        UNITS       "times"
        MAX-ACCESS  read-only
        STATUS      current
        DESCRIPTION
                "Number of times when timeout occurred on waiting
                for Status message"
        ::= { fsfrLmiEntry 9 }

fsfrLmiStatusEnqTimeouts OBJECT-TYPE
        SYNTAX      Counter32
        UNITS       "times"
        MAX-ACCESS  read-only
        STATUS      current
        DESCRIPTION
                "Number of times when timeout occurred on waiting
                for Status Enquiry message"
        ::= { fsfrLmiEntry 10 }

fsfrLmiN392Dce OBJECT-TYPE
        SYNTAX      INTEGER (0..10)
        MAX-ACCESS  read-only
        STATUS      current
        DESCRIPTION
                "LMI error threshold for DCE interface.
                For DTE, value becomes 0."
        ::= { fsfrLmiEntry 11 }

fsfrLmiN393Dce OBJECT-TYPE
        SYNTAX      INTEGER (0..10)
        MAX-ACCESS  read-only
        STATUS      current
        DESCRIPTION
                "LMI monitored event count for DCE interface.
                For DTE, value becomes zero (0)."
        ::= { fsfrLmiEntry 12 }

fsfrLmiT392Dce OBJECT-TYPE
        SYNTAX      INTEGER (0..30)
        UNITS       "seconds"
        MAX-ACCESS  read-only
        STATUS      current
        DESCRIPTION
                "DCE polling verification timer for DCE interface
                For DTE, the value becomes zero (0)."
        ::= { fsfrLmiEntry 13 }

-- end LMI subgroup }

-- Circut sub-group {

fsfrCircuitTable OBJECT-TYPE
        SYNTAX      SEQUENCE OF FSfrCircuitEntry
        MAX-ACCESS  not-accessible
        STATUS      current
        DESCRIPTION
                "Table of descriptive and statistics information
                that are generic to Frame Relay virtual circuits."
        ::= { fsfrCircuitObjs 1 }

fsfrCircuitEntry OBJECT-TYPE
        SYNTAX      FSfrCircuitEntry
        MAX-ACCESS  not-accessible
        STATUS      current
        DESCRIPTION
                "Each entry of the table contains information of a
                circuit that are not included in frCircuitTable of
                RFC1315 but are generic to Frame Relay."
        AUGMENTS { frCircuitEntry }
                -- indexed by { frCircuitIfIndex, frCircuitDlci }
        ::= { fsfrCircuitTable 1 }

FSfrCircuitEntry ::=
        SEQUENCE {
            fsfrCircuitDEins              Counter32,
            fsfrCircuitDEouts             Counter32,
            fsfrCircuitDropPktsOuts       Counter32,
            fsfrCircuitType               INTEGER
        }

fsfrCircuitDEins OBJECT-TYPE
        SYNTAX      Counter32
        UNITS       "packets"
        MAX-ACCESS  read-only
        STATUS      current
        DESCRIPTION
                "Number of packets received with the Discarded
                Eligibility indictor (the DE bit) set."
        ::= { fsfrCircuitEntry 1 }

fsfrCircuitDEouts OBJECT-TYPE
        SYNTAX      Counter32
        UNITS       "packets"
        MAX-ACCESS  read-only
        STATUS      current
        DESCRIPTION
                "Number of packets transmitted with DE bit set."
        ::= { fsfrCircuitEntry 2 }

fsfrCircuitDropPktsOuts OBJECT-TYPE
        SYNTAX      Counter32
        UNITS       "packets"
        MAX-ACCESS  read-only
        STATUS      current
        DESCRIPTION
                "Number of discarded packets that were to be sent."
        ::= { fsfrCircuitEntry 3 }

fsfrCircuitType OBJECT-TYPE
        SYNTAX  INTEGER
                {
                    pvc(1),        -- permanent virtual circuit
                    svc(2)        -- switched virtual circuit
                }
        MAX-ACCESS  read-only
        STATUS      current
        DESCRIPTION
                "Basic circuit type"
        ::= { fsfrCircuitEntry 4 }

-- FS specific circuit information:

fsfrExtCircuitTable  OBJECT-TYPE
        SYNTAX      SEQUENCE OF FSfrExtCircuitEntry
        MAX-ACCESS  not-accessible
        STATUS      current
        DESCRIPTION
                "Table of FS implementation specific FR
                circuit information. This is a FS extension
                for the frCircuitTable of RFC 1315."
        ::= { fsfrCircuitObjs 2 }

fsfrExtCircuitEntry  OBJECT-TYPE
        SYNTAX      FSfrExtCircuitEntry
        MAX-ACCESS  not-accessible
        STATUS      current
        DESCRIPTION
                "Each entry of the table contains information
                of a Frame Relay virtual circuit that are specific
                to FS implementation."
        AUGMENTS { frCircuitEntry }
                -- indexed by { frCircuitIfIndex, frCircuitDlci }
        ::= { fsfrExtCircuitTable 1 }

FSfrExtCircuitEntry ::=
        SEQUENCE {
            fsfrExtCircuitIfName             DisplayString,
            fsfrExtCircuitIfType             INTEGER,
            fsfrExtCircuitSubifIndex         InterfaceIndex,
            fsfrExtCircuitMapStatus          INTEGER,
            fsfrExtCircuitCreateType         INTEGER,
            fsfrExtCircuitMulticast          TruthValue,
            fsfrExtCircuitRoutedDlci         DlciNumber,
            fsfrExtCircuitRoutedIf           InterfaceIndex,
            fsfrExtCircuitUncompressIns      Counter32,
            fsfrExtCircuitUncompressOuts     Counter32,
            fsfrExtCircuitFECNOuts           Counter32,
            fsfrExtCircuitBECNOuts           Counter32,
            fsfrExtCircuitMinThruputOut      Integer32,
            fsfrExtCircuitMinThruputIn       Integer32,
            fsfrExtCircuitBcastPktOuts       Counter32,
            fsfrExtCircuitBcastByteOuts      Counter32,
            fsfrExtCircuitBandwidth          Integer32,
            fsfrExtCircuitShapeByteLimit     Integer32,
            fsfrExtCircuitShapeInterval      Integer32,
            fsfrExtCircuitShapeByteIncrement Integer32,
            fsfrExtCircuitShapePkts          Counter32,
            fsfrExtCircuitShapeBytes         Counter32,
            fsfrExtCircuitShapePktsDelay     Counter32,
            fsfrExtCircuitShapeBytesDelay    Counter32,
            fsfrExtCircuitShapeActive        TruthValue,
            fsfrExtCircuitShapeAdapting      INTEGER,
            fsfrExtCircuitTxDataRate         INTEGER,
            fsfrExtCircuitTxPktRate          INTEGER,
            fsfrExtCircuitRcvDataRate        INTEGER,
            fsfrExtCircuitRcvPktRate         INTEGER
        }

fsfrExtCircuitIfName  OBJECT-TYPE
        SYNTAX       DisplayString
        MAX-ACCESS   read-only
        STATUS       current
        DESCRIPTION
                "The textual name of the main interface or the
                subinterface that this DLCI is associated with.
                This is the same name string of an interface used
                in the configuration and all console displays,
                such as 'serial 0', 'serial 3/0.3', etc."
        ::= { fsfrExtCircuitEntry 1 }

fsfrExtCircuitIfType  OBJECT-TYPE
        SYNTAX  INTEGER {
                  mainInterface(1),
                  pointToPoint(2),        -- subinterface
                  multipoint(3)           -- subinterface
                }
        MAX-ACCESS  read-only
        STATUS      current
        DESCRIPTION
                "Type of the subinterface this DLCI is associated
                with, if configured."
        ::= { fsfrExtCircuitEntry 2 }

fsfrExtCircuitSubifIndex OBJECT-TYPE
        SYNTAX      InterfaceIndex
        MAX-ACCESS  read-only
        STATUS      current
        DESCRIPTION
                "For value greater than zero (0), it indicates
                the network management interface index
                for the subinterface associated with
                this DLCI. Value 0 means the DLCI is not
                associated with any subinterface."
        ::= { fsfrExtCircuitEntry 3 }

fsfrExtCircuitMapStatus OBJECT-TYPE
        SYNTAX      INTEGER (0..2047)
        MAX-ACCESS  read-only
        STATUS      current
        DESCRIPTION
                "The mapping protocols (internally considered as
                the 'link type') applied on this circuit.
                The value ranges from 0 to 2047.
                For point-to-point DLCI, the value stays zero.
                Otherwise, the value is a sum. It initially takes
                the value zero, then, for each type of Protocol,
                2 raised to a power is added to the sum.
                The following table presents respective power and
                equivalent value for each applicable type:

                        Protocol        Power    Value
                        --------        -----    -----
                        IP              0        1
                        IPX             1        2
                        Appletalk       2        4
                        XNS             3        8
                        VINES           4        16
                        DECnet          5        32
                        CLNS            6        64
                        Bridging        7        128
                        RSRB            8        256
                        STUN            9        512
                        LLC2            10       1024

                For example, value 3 means the circuit's mapping
                protocols include IP and IPX. (3 = 2**1 + 2**0,
                where 0 corresponds to IP and 1 to IPX.) Value 0
                means there is currently no mapping protocol for
                the circuit.
                See fsfrMapTable for more mapping information."
        ::= { fsfrExtCircuitEntry 4 }

fsfrExtCircuitCreateType OBJECT-TYPE
        SYNTAX  INTEGER
                {
                    dynamic(1),      -- PVC established through LMI
                                     -- or an SVC established through
                                     -- SVC signalling
                    static(2)        -- circuit was configured
                }
        MAX-ACCESS  read-only
        STATUS      current
        DESCRIPTION
                "Identify the last source of the circuit's creation."
        ::= { fsfrExtCircuitEntry 5 }

fsfrExtCircuitMulticast  OBJECT-TYPE
        SYNTAX      TruthValue
        MAX-ACCESS  read-only
        STATUS      current
        DESCRIPTION
                "Indicate if this DLCI is a multicast DLCI."
        ::= { fsfrExtCircuitEntry 6 }

fsfrExtCircuitRoutedDlci OBJECT-TYPE
        SYNTAX      DlciNumber
        MAX-ACCESS  read-only
        STATUS      current
        DESCRIPTION
                "The routed DLCI to pair up with this DLCI
                for switching function. NOTE: Value zero (0)
                indicates that there is no such routed DLCI
                corresponding to this DLCI."
        ::= { fsfrExtCircuitEntry 7 }

fsfrExtCircuitRoutedIf OBJECT-TYPE
        SYNTAX      InterfaceIndex
        MAX-ACCESS  read-only
        STATUS      current
        DESCRIPTION
                "The interface for the routed DLCI that pairs up
                with this DLCI for switching. Value greater than 0
                is the InterfaceIndex for that interface. Value
                zero (0) indicates that there is no such routed DLCI
                corresponding to this DLCI."
        ::= { fsfrExtCircuitEntry 8 }

fsfrExtCircuitUncompressIns OBJECT-TYPE
        SYNTAX      Counter32
        UNITS       "octets"
        MAX-ACCESS  read-only
        STATUS      current
        DESCRIPTION
                "Number of inbound octets of the data packets,
                accounted at Frame Relay level after FRF.9
                payload decompression is applied. In the case of
                non-FRF.9, this value could be identical to
                frCircuitReceivedOctets, unless otherwise noted."
        ::= { fsfrExtCircuitEntry 9 }

fsfrExtCircuitUncompressOuts OBJECT-TYPE
        SYNTAX      Counter32
        UNITS       "octets"
        MAX-ACCESS  read-only
        STATUS      current
        DESCRIPTION
                "Number of outbound octets of the data packets,
                accounted at Frame Relay level before FRF.9
                payload compression is applied. In the case of
                non-FRF.9, this value could be identical to
                frCircuitSentOctets, unless otherwise noted."
        ::= { fsfrExtCircuitEntry 10 }

fsfrExtCircuitFECNOuts OBJECT-TYPE
        SYNTAX      Counter32
        MAX-ACCESS  read-only
        STATUS      current
        DESCRIPTION
                "Total number of frames sent out to the network
                indicating forward congestion."
        ::= { fsfrExtCircuitEntry 11 }

fsfrExtCircuitBECNOuts OBJECT-TYPE
        SYNTAX      Counter32
        MAX-ACCESS  read-only
        STATUS      current
        DESCRIPTION
                "Total number of frames sent out to the network
                indicating backward congestion."
        ::= { fsfrExtCircuitEntry 12 }

fsfrExtCircuitMinThruputOut OBJECT-TYPE
        SYNTAX      Integer32 (9600..1544000)
        UNITS       "bits per second"
        MAX-ACCESS  read-only
        STATUS      current
        DESCRIPTION
                "Circuit's outgoing minimal Throughput based on
                configuration."
        ::= { fsfrExtCircuitEntry 13 }

fsfrExtCircuitMinThruputIn  OBJECT-TYPE
        SYNTAX      Integer32 (9600..1544000)
        UNITS       "bits per second"
        MAX-ACCESS  read-only
        STATUS      current
        DESCRIPTION
                "Circuit's incoming minimal Throughput based on
                configuration."
        ::= { fsfrExtCircuitEntry 14 }

fsfrExtCircuitBcastPktOuts OBJECT-TYPE
        SYNTAX      Counter32
        MAX-ACCESS  read-only
        STATUS      current
        DESCRIPTION
                "Total number of broadcast packets sent out to the
                 network."
        ::= { fsfrExtCircuitEntry 15 }

fsfrExtCircuitBcastByteOuts OBJECT-TYPE
        SYNTAX      Counter32
        MAX-ACCESS  read-only
        STATUS      current
        DESCRIPTION
                "Total number of bytes sent out to the network in
                broadcast packets."
        ::= { fsfrExtCircuitEntry 16 }

fsfrExtCircuitBandwidth OBJECT-TYPE
        SYNTAX      Integer32 (0..16777215)
        UNITS       "bits per second"
        MAX-ACCESS  read-only
        STATUS      current
        DESCRIPTION
                "Bandwidth of the virtual circuit, acquired from
                FS typed LMI Full Status message."
        ::= { fsfrExtCircuitEntry 17 }

fsfrExtCircuitShapeByteLimit OBJECT-TYPE
        SYNTAX      Integer32 (125..2147483647)
        UNITS       "octets"
        MAX-ACCESS  read-only
        STATUS      current
        DESCRIPTION
                "Maximum number of tokens a token bucket can hold in any
                time interval in case of traffic shaping."
        ::= { fsfrExtCircuitEntry 18 }

fsfrExtCircuitShapeInterval OBJECT-TYPE
        SYNTAX      Integer32 (10..125)
        UNITS       "milliseconds"
        MAX-ACCESS  read-only
        STATUS      current
        DESCRIPTION
                "Committed rate measurement interval."
        ::= { fsfrExtCircuitEntry 19 }

fsfrExtCircuitShapeByteIncrement OBJECT-TYPE
        SYNTAX      Integer32 (125..2147483647)
        UNITS       "octets"
        MAX-ACCESS  read-only
        STATUS      current
        DESCRIPTION
                "Number of tokens added into the token bucket per time
                interval in case of traffic shaping."
        ::= { fsfrExtCircuitEntry 20 }

fsfrExtCircuitShapePkts OBJECT-TYPE
        SYNTAX      Counter32
        MAX-ACCESS  read-only
        STATUS      current
        DESCRIPTION
                "Total number of packets that went through traffic
                shaping."
        ::= { fsfrExtCircuitEntry 21 }

fsfrExtCircuitShapeBytes OBJECT-TYPE
        SYNTAX      Counter32
        UNITS       "octets"
        MAX-ACCESS  read-only
        STATUS      current
        DESCRIPTION
                "Total number of bytes that went through traffic
                shaping."
        ::= { fsfrExtCircuitEntry 22 }

fsfrExtCircuitShapePktsDelay OBJECT-TYPE
        SYNTAX      Counter32
        MAX-ACCESS  read-only
        STATUS      current
        DESCRIPTION
                "Total number of packets that were delayed by the
                traffic shaper."
        ::= { fsfrExtCircuitEntry 23 }

fsfrExtCircuitShapeBytesDelay OBJECT-TYPE
        SYNTAX      Counter32
        UNITS       "octets"
        MAX-ACCESS  read-only
        STATUS      current
        DESCRIPTION
                "Total number of bytes that were delayed by the
                traffic shaper."
        ::= { fsfrExtCircuitEntry 24 }

fsfrExtCircuitShapeActive OBJECT-TYPE
        SYNTAX      TruthValue
        MAX-ACCESS  read-only
        STATUS      current
        DESCRIPTION
                "Shows whether shaping is active or not."
        ::= { fsfrExtCircuitEntry 25 }

fsfrExtCircuitShapeAdapting  OBJECT-TYPE
        SYNTAX  INTEGER {
                  none(1),
                  becn(2),
                  foreSight(3)
                }
        MAX-ACCESS  read-only
        STATUS      current
        DESCRIPTION
                "Type of Adaptive Shaping configured.
                none(1)      - No adaptive shaping configured
                becn(2)      - Backward Explicit Congestion Notification
                foreSight(3) - ForeSight is the network traffic control
                               software used in FS WAN switches"
        ::= { fsfrExtCircuitEntry 26 }

fsfrExtCircuitTxDataRate OBJECT-TYPE
        SYNTAX       INTEGER (1..45000000)
        MAX-ACCESS   read-only
        STATUS       current
        DESCRIPTION
               "The average rate (bytes/second) at which data is
               transmitted in this circuit. "
        ::= { fsfrExtCircuitEntry 27 }

fsfrExtCircuitTxPktRate OBJECT-TYPE
        SYNTAX       INTEGER (1..45000000)
        MAX-ACCESS   read-only
        STATUS       current
        DESCRIPTION
              "The average number of packets sent in a second in this
              circuit."
        ::= { fsfrExtCircuitEntry 28 }

fsfrExtCircuitRcvDataRate OBJECT-TYPE
        SYNTAX       INTEGER (1..45000000)
        MAX-ACCESS   read-only
        STATUS       current
        DESCRIPTION
               "The average rate (bytes/second) at which data is
               received in this circuit. "
        ::= { fsfrExtCircuitEntry 29 }

fsfrExtCircuitRcvPktRate OBJECT-TYPE
        SYNTAX       INTEGER (1..45000000)
        MAX-ACCESS   read-only
        STATUS       current
        DESCRIPTION
               "The average number of packets received in a second in
               this circuit. "
       ::= { fsfrExtCircuitEntry 30 }

-- end circuit subgroup }

-- Mapping sub-group {

fsfrMapTable OBJECT-TYPE
        SYNTAX      SEQUENCE OF FSfrMapEntry
        MAX-ACCESS  not-accessible
        STATUS      current
        DESCRIPTION
                "Table of protocols and addresses mapping
                information of FR virtual circuit."
        ::= { fsfrMapObjs 1 }

fsfrMapEntry OBJECT-TYPE
        SYNTAX      FSfrMapEntry
        MAX-ACCESS  not-accessible
        STATUS     current
        DESCRIPTION
                "Each entry of the table contains one mapping
                information of a Frame Relay virtual circuit."
        INDEX { frCircuitIfIndex, frCircuitDlci, fsfrMapIndex }
        ::= { fsfrMapTable 1 }

FSfrMapEntry ::=
        SEQUENCE {
            fsfrMapIndex                 INTEGER,
            fsfrMapProtocol              FSfrMapProtocols,
            fsfrMapAddress               OCTET STRING (SIZE(0..64)),
            fsfrMapType                  INTEGER,
            fsfrMapEncaps                INTEGER,
            fsfrMapBroadcast             TruthValue,
            fsfrMapPayloadCompress       TruthValue,
            fsfrMapTcpHdrCompress        INTEGER,
            fsfrMapRtpHdrCompress        INTEGER,
            fsfrMapPayloadCompressType   INTEGER
        }

fsfrMapIndex OBJECT-TYPE
        SYNTAX      INTEGER (1..999)
        MAX-ACCESS  read-only
        STATUS      current
        DESCRIPTION
                "An arbitrary Index to the mapping information
                associated with a certain circuit. The maximum
                value is arbitrarily picked which is considered
                sufficient for usual configuration."
        ::= { fsfrMapEntry 1 }

fsfrMapProtocol OBJECT-TYPE
        SYNTAX      FSfrMapProtocols
        MAX-ACCESS  read-only
        STATUS      current
        DESCRIPTION
                "Mapping protocol for this circuit."
        ::= { fsfrMapEntry 2 }

fsfrMapAddress OBJECT-TYPE
        SYNTAX      OCTET STRING (SIZE(0..64))
        MAX-ACCESS  read-only
        STATUS      current
        DESCRIPTION
                "Mapping protocol address at remote end for
                this DLCI.
                NOTE: For point-to-point DLCI, the string is fixed
                to be point-to-point."
        ::= { fsfrMapEntry 3 }

fsfrMapType OBJECT-TYPE
        SYNTAX  INTEGER
                {
                    static(1),
                    dynamic(2),
                    svc(3)
                }
        MAX-ACCESS  read-only
        STATUS      current
        DESCRIPTION
                "Type for the map creation."
        ::= { fsfrMapEntry 4 }

fsfrMapEncaps OBJECT-TYPE
        SYNTAX  INTEGER
                {
                    ietf(1),    -- following IETF specifications
                                -- (RFC 1490 as up to date)
                    cisco(2)
                }
        MAX-ACCESS  read-only
        STATUS      current
        DESCRIPTION
                "Indication of the encapsulation type for this
                mapping protocol."
        ::= { fsfrMapEntry 5 }

fsfrMapBroadcast OBJECT-TYPE
        SYNTAX      TruthValue
        MAX-ACCESS  read-only
        STATUS      current
        DESCRIPTION
                "Broadcast enabled or disabled."
        ::= { fsfrMapEntry 6 }

fsfrMapPayloadCompress OBJECT-TYPE
        SYNTAX      TruthValue
        MAX-ACCESS  read-only
        STATUS      deprecated
                    -- obsoleted by fsfrMapPayloadCompressType
        DESCRIPTION
                "Indicate if payload compression is enabled."
        ::= { fsfrMapEntry 7 }

fsfrMapTcpHdrCompress OBJECT-TYPE
        SYNTAX  INTEGER
                {
                    inapplicable(1),
                    passive(2),
                    active(3)
                }
        MAX-ACCESS  read-only
        STATUS      current
        DESCRIPTION
                "TCP header compression type, if applicable."
        ::= { fsfrMapEntry 8 }

fsfrMapRtpHdrCompress OBJECT-TYPE
        SYNTAX  INTEGER
                {
                    inapplicable(1),
                    passive(2),
                    active(3)
                }
        MAX-ACCESS  read-only
        STATUS      current
        DESCRIPTION
                "RTP header compression type, if applicable.
                The value 'passive' means that the header of an
                outgoing RTP/IP packet is compressed only if an
                incoming RTP/IP packet had a compressed header.
                The value 'active' means the header of every outgoing
                RTP/IP packet is compressed."
        ::= { fsfrMapEntry 9 }

fsfrMapPayloadCompressType OBJECT-TYPE
        SYNTAX  INTEGER
             {
                inapplicable(1),
                cisco(2),         -- cisco proprietary FR packet-
                                  -- by-packet payload compression
                frf9Software(3),  -- FRF.9 software payload compression
                frf9Hardware(4)   -- FRF.9 hardware payload compression
             }
        MAX-ACCESS  read-only
        STATUS      current
        DESCRIPTION
                "FR payload compression type, if applicable.
                FRF.9 is the Frame Relay Forum Implementation Agreement
                on FR payload compression. The compression can be done
                by either software or hardware (when equipped with the
                supporting hardware), depending on configuration."
        REFERENCE
                "Frame Relay Forum document number FRF.9"
        ::= { fsfrMapEntry 10 }

-- end mapping subgroup }

-- SVC sub-group {
--        containing SVC spcific information

fsfrSvcTable OBJECT-TYPE
        SYNTAX      SEQUENCE OF FSfrSvcEntry
        MAX-ACCESS  not-accessible
        STATUS      current
        DESCRIPTION
                "Table of FR SVC specific, descriptive
                and statistics information."
        ::= { fsfrSvcObjs 1 }

fsfrSvcEntry OBJECT-TYPE
        SYNTAX      FSfrSvcEntry
        MAX-ACCESS  not-accessible
        STATUS      current
        DESCRIPTION
                "Each entry of the table contains circuit information
                specific to a Frame Relay Switched Virtual Circuit."
        INDEX { frCircuitIfIndex, frCircuitDlci }
        ::= { fsfrSvcTable 1 }

FSfrSvcEntry ::=
        SEQUENCE {
            fsfrSvcAddrLocal           OCTET STRING (SIZE(0..64)),
            fsfrSvcAddrRemote          OCTET STRING (SIZE(0..64)),
            fsfrSvcThroughputIn        Integer32,
            fsfrSvcMinThruputOut       Integer32,
            fsfrSvcMinThruputIn        Integer32,
            fsfrSvcCommitBurstIn       Integer32,
            fsfrSvcExcessBurstIn       Integer32,
            fsfrSvcIdleTime            Integer32
        }

-- For circuit (DLCI) outbound throughput and outbound Committed
-- and Excess Burst size, please refer to the following from
-- RFC1315 respectively:
--        frCircuitThroughput,
--        frCircuitCommittedBurst, and
--        frCircuitExcessBurst


fsfrSvcAddrLocal OBJECT-TYPE
        SYNTAX      OCTET STRING (SIZE(0..64))
        MAX-ACCESS  read-only
        STATUS      current
        DESCRIPTION
                "Local E.164/X.125 address for the circuit."
        ::= { fsfrSvcEntry 1 }

fsfrSvcAddrRemote OBJECT-TYPE
        SYNTAX      OCTET STRING (SIZE(0..64))
        MAX-ACCESS  read-only
        STATUS      current
        DESCRIPTION
                "Remote E.164/X.125 address for the circuit."
        ::= { fsfrSvcEntry 2 }

fsfrSvcThroughputIn OBJECT-TYPE
        SYNTAX      Integer32 (9600..1544000)
        UNITS       "bits per second"
        MAX-ACCESS  read-only
        STATUS      current
        DESCRIPTION
                "Circuit's incoming throughput. For outgoing
                throughput (commonly referred to as CIR) see
                frCircuitThroughput per RFC1315."
        ::= { fsfrSvcEntry 3 }

fsfrSvcMinThruputOut OBJECT-TYPE
        SYNTAX      Integer32 (9600..1544000)
        UNITS       "bits per second"
        MAX-ACCESS  read-only
        STATUS      deprecated -- deprecated by
                               -- cfrExtCircuitMinThruputOut
        DESCRIPTION
                "Circuit's outgoing minimal Throughput."
        ::= { fsfrSvcEntry 4 }

fsfrSvcMinThruputIn  OBJECT-TYPE
        SYNTAX      Integer32 (9600..1544000)
        UNITS       "bits per second"
        MAX-ACCESS  read-only
        STATUS      deprecated -- deprecated by
                               -- cfrExtCircuitMinThruputIn
        DESCRIPTION
                "Circuit's incoming minimal Throughput."
        ::= { fsfrSvcEntry 5 }

fsfrSvcCommitBurstIn OBJECT-TYPE
        SYNTAX      Integer32 (9600..1544000)
        MAX-ACCESS  read-only
        STATUS      current
        DESCRIPTION
                "Circuit's incoming Committed Burst Rate.
                See ANSI and/or ITU specifications for
                definition and calculations. For outgoing
                CBR, see frCircuitCommittedBurst per RFC 1315."
        ::= { fsfrSvcEntry 6 }

fsfrSvcExcessBurstIn OBJECT-TYPE
        SYNTAX      Integer32 (9600..2440000)
        MAX-ACCESS  read-only
        STATUS      current
        DESCRIPTION
                "Circuit's incoming Excess Burst Rate.
                See ANSI and/or ITU specifications for
                definition and calculations. For outgoing
                EBR, see frCircuitExcessBurst per RFC 1315."
        ::= { fsfrSvcEntry 7 }

fsfrSvcIdleTime      OBJECT-TYPE
        SYNTAX      Integer32
        UNITS       "seconds"
        MAX-ACCESS  read-only
        STATUS      current
        DESCRIPTION
                "Circuit's idle time period. If expires, the
                circuit is cleared."
        ::= { fsfrSvcEntry 8 }

-- end SVC subgroup }

-- Enhanced Link Management Interface(ELMI) sub-group {
-- ELMI is the protocol that learns QOS parameters(CIR,Bc,Be etc)
-- of a VC from the switch.
-- This sub group contains ELMI specific information.

fsfrElmiIpAddr      OBJECT-TYPE
        SYNTAX     IpAddress
        MAX-ACCESS read-only
        STATUS     current
        DESCRIPTION
                "This object represents the Management address of the
                 device used for address registration.
                 Network management station can send management
                 messages to this IP address. This can be
                 user configured address or the address of one of the
                 interfaces on the device. If address registration is
                 disabled then this will have a value of 0.0.0.0.
                 This object is accessible only if the ELMI protocol
                 is supported on the device"
        ::= { fsfrElmiObjs 1 }

fsfrElmiTable       OBJECT-TYPE
        SYNTAX     SEQUENCE OF FSfrElmiEntry
        MAX-ACCESS not-accessible
        STATUS     current
        DESCRIPTION
                "Table of FS Frame Relay ELMI information that is
                 specific to FS implementation"
        ::= { fsfrElmiObjs 2 }

fsfrElmiEntry       OBJECT-TYPE
        SYNTAX     FSfrElmiEntry
        MAX-ACCESS not-accessible
        STATUS     current
        DESCRIPTION
                "Each entry of the table contains information about a
                 physical interface. The table can be accessible only
                 if the device supports ELMI protocol and if LMI is
                 enabled on the interface."
        INDEX { ifIndex }
        ::= { fsfrElmiTable 1 }

FSfrElmiEntry ::=
        SEQUENCE {
            fsfrElmiLinkStatus
                INTEGER,
            fsfrElmiArStatus
                INTEGER,
            fsfrElmiRemoteStatus
                INTEGER
        }

fsfrElmiLinkStatus  OBJECT-TYPE
        SYNTAX     INTEGER {
                       enabled(1),
                       disabled(2)
                   }
        MAX-ACCESS read-only
        STATUS     current
        DESCRIPTION
                "This variable states whether Enhanced Link Management
                 Interface(ELMI) protocol is enabled or not on a
                 frame relay interface."
        ::= { fsfrElmiEntry 1 }

fsfrElmiArStatus    OBJECT-TYPE
        SYNTAX     INTEGER {
                       enabled(1),
                       disabled(2)
                   }
        MAX-ACCESS read-only
        STATUS     current
        DESCRIPTION
                "This variable states whether the Enhanced Link
                 Management Interface(ELMI) address registration(AR)
                 mechanism is enabled or not on a frame relay
                 interface. A value of 1 indicates ELMI AR is
                 supported on the interface. A value of 2 indicates
                 ELMI AR is supported but the user disabled the
                 exchange of IP address and ifIndex with the
                 neighboring device. This object doesn't have any
                 significance if cfrElmiLinkStatus is disabled
                 on the interface."
        ::= { fsfrElmiEntry 2 }

fsfrElmiRemoteStatus OBJECT-TYPE
        SYNTAX      INTEGER {
                        enabled(1),
                        disabled(2)
                    }
        MAX-ACCESS  read-only
        STATUS      current
        DESCRIPTION
                "This variable states the Enhanced Link
                 Management(ELMI) status on the other end of the
                 interface. If cfrElmiLinkStatus is enabled on the
                 other end a value of 1 will be returned,
                 else 2 will be returned. This object doesn't have any
                 significance if cfrElmiLinkStatus is disabled on the
                 interface"
        ::= { fsfrElmiEntry 3 }

fsfrElmiNeighborTable    OBJECT-TYPE
        SYNTAX          SEQUENCE OF FSfrElmiNeighborEntry
        MAX-ACCESS      not-accessible
        STATUS          current
        DESCRIPTION
                "Table of FS Frame Relay Neighbor ELMI information
                 that is specific to FS implementation."
        ::= { fsfrElmiObjs 3 }

fsfrElmiNeighborEntry OBJECT-TYPE
        SYNTAX       FSfrElmiNeighborEntry
        MAX-ACCESS   not-accessible
        STATUS       current
        DESCRIPTION
                "Each entry of the table contains information of the
                 neighboring device connected to a physical interface.
                 The entry will be present only if ELMI is enabled on
                 the neighboring device interface. If the value of the
                 fsfrElmiRemoteStatus in the fsfrElmiEntry is 1 then a
                 valid entry exists for the interface. If ELMI is not
                 supported on the remote end then, the neighbor
                 information for the interface will not be present"
        INDEX { ifIndex }
        ::= { fsfrElmiNeighborTable 1 }

FSfrElmiNeighborEntry ::=
        SEQUENCE {
            fsfrElmiNeighborArStatus
                INTEGER,
            fsfrElmiNeighborIpAddress
                IpAddress,
            fsfrElmiNeighborIfIndex
                InterfaceIndex,
            fsfrElmiNeighborVendorName
                DisplayString,
            fsfrElmiNeighborPlatformName
                DisplayString,
            fsfrElmiNeighborDeviceName
                DisplayString
        }


fsfrElmiNeighborArStatus OBJECT-TYPE
        SYNTAX          INTEGER {
                            notsupported(1),
                            enabled(2),
                            disabled(3)
                        }
        MAX-ACCESS      read-only
        STATUS          current
        DESCRIPTION
                "This variable indicates the status of ELMI Address
                 registration(AR) on the neighboring device. A value
                 of 1 indicates ELMI AR is not supported on the
                 neighboring device. A value of 2 indicates ELMI AR is
                 enabled on the interface. A value of 3 indicates AR is
                 supported, but user disabled the exchange of IP
                 address and ifIndex with the neighbor."
        ::= { fsfrElmiNeighborEntry 1 }

fsfrElmiNeighborIpAddress OBJECT-TYPE
        SYNTAX           IpAddress
        MAX-ACCESS       read-only
        STATUS           current
        DESCRIPTION
                "The Management IP address of the neighboring device
                 to which the other end of this interface is
                 connected. Network management system can use this
                 address to send management messages to the device.
                 If address registration is not supported on the
                 remote end then the value will be 0.0.0.0.
                 NMS uses this object in the topology discovery of the
                 network."
        ::= { fsfrElmiNeighborEntry 2 }

fsfrElmiNeighborIfIndex   OBJECT-TYPE
        SYNTAX           InterfaceIndex
        MAX-ACCESS       read-only
        STATUS           current
        DESCRIPTION
                "The Interface index of the neighboring device to
                 which this interface is connected. If the value of
                 fsfrElmiNeighborArStatus is 2 then this will have a
                 valid value. If the value of fsfrElmiNeighborArStatus
                 is 3 or 1 then value of this object will be 0. NMS
                 uses this object in the topology discovery of the
                 network."
        ::= { fsfrElmiNeighborEntry 3 }

fsfrElmiNeighborVendorName OBJECT-TYPE
        SYNTAX            DisplayString
        MAX-ACCESS        read-only
        STATUS            current
        DESCRIPTION
                "Vendor name of the neighboring device to which the
                 other end of this interface is connected."
        ::= { fsfrElmiNeighborEntry 4 }

fsfrElmiNeighborPlatformName OBJECT-TYPE
        SYNTAX              DisplayString
        MAX-ACCESS          read-only
        STATUS              current
        DESCRIPTION
                "Platform name of the neighboring device to which the
                 other end of this interface is connected."
        ::= { fsfrElmiNeighborEntry 5 }

fsfrElmiNeighborDeviceName   OBJECT-TYPE
        SYNTAX              DisplayString
        MAX-ACCESS          read-only
        STATUS              current
        DESCRIPTION
                "Device name of the neighboring device to which the
                 other end of this interface is connected."
        ::= { fsfrElmiNeighborEntry 6 }

-- end ELMI sub-group }

-- Fragmentation sub-group {

fsfrFragTable OBJECT-TYPE
        SYNTAX      SEQUENCE OF FSfrFragEntry
        MAX-ACCESS  not-accessible
        STATUS      current
        DESCRIPTION
                "Table of Frame Relay Fragmentation information.
                These are specific to FS's implementation."
        ::= { fsfrFragObjs 1 }

fsfrFragEntry OBJECT-TYPE
        SYNTAX      FSfrFragEntry
        MAX-ACCESS  not-accessible
        STATUS      current
        DESCRIPTION
                "Each entry of the table contains details of
                fragmentation configured on  this circuit. "
        INDEX { frCircuitIfIndex, frCircuitDlci}
        ::= { fsfrFragTable 1 }

FSfrFragEntry ::=
        SEQUENCE {
            fsfrFragSize                       INTEGER,
            fsfrFragType                       DisplayString,
            fsfrFragInPkts                     Counter32,
            fsfrFragOutPkts                    Counter32,
            fsfrFragInOctets                   Counter32,
            fsfrFragOutOctets                  Counter32,
            fsfrFragNotInPkts                  Counter32,
            fsfrFragNotOutPkts                 Counter32,
            fsfrFragNotInOctets                Counter32,
            fsfrFragNotOutOctets               Counter32,
            fsfrFragAssembledInPkts            Counter32,
            fsfrFragAssembledInOctets          Counter32,
            fsfrFragPreOutPkts                 Counter32,
            fsfrFragPreOutOctets               Counter32,
            fsfrFragDroppedReAssembledInPkts   Counter32,
            fsfrFragDroppedFragmentedOutPkts   Counter32,
            fsfrFragTimeoutsIn                 INTEGER,
            fsfrFragOutOfSeqFragPkts           Counter32,
            fsfrFragUnexpectedBBitSetPkts      Counter32,
            fsfrFragSeqMissedPkts              Counter32,
            fsfrFragInterleavedOutPkts         Counter32
        }

fsfrFragSize OBJECT-TYPE
        SYNTAX      INTEGER (16..1600)
        UNITS       "octets"
        MAX-ACCESS  read-only
        STATUS      current
        DESCRIPTION
                "fsfrFragSize defines the payload size of a fragment
                and it excludes the FR headers and any FR fragmentation
                header."

        ::= { fsfrFragEntry 1 }
fsfrFragType OBJECT-TYPE
        SYNTAX  DisplayString
        MAX-ACCESS  read-only
        STATUS      current
        DESCRIPTION
                "Fragmentation type configured by the user. The types
                supported are end-to-end, VoFR-fs and VoFR."
        ::= { fsfrFragEntry 2 }

fsfrFragInPkts  OBJECT-TYPE
        SYNTAX      Counter32
        UNITS       "packets"
        MAX-ACCESS  read-only
        STATUS      current
        DESCRIPTION
                "Total number of frames received that have a
                fragmentation header."
        ::= { fsfrFragEntry 3 }

fsfrFragOutPkts OBJECT-TYPE
        SYNTAX      Counter32
        UNITS       "packets"
        MAX-ACCESS  read-only
        STATUS      current
        DESCRIPTION
                "Total number of fragments that are transmitted with a
                fragmenation header."
        ::= { fsfrFragEntry 4 }

fsfrFragInOctets OBJECT-TYPE
        SYNTAX      Counter32
        UNITS       "octets"
        MAX-ACCESS  read-only
        STATUS      current
        DESCRIPTION
                "Total number of bytes received in frames that have a
                fragmentation header. The number of bytes include the
                FR header."
        ::= { fsfrFragEntry 5}

fsfrFragOutOctets OBJECT-TYPE
        SYNTAX      Counter32
        UNITS       "octets"
        MAX-ACCESS  read-only
        STATUS      current
        DESCRIPTION
                "Total number of bytes that are transmitted in frames
                with a fragmenation header. The number of bytes also
                includes the FR header."
        ::= { fsfrFragEntry 6}

fsfrFragNotInPkts OBJECT-TYPE
        SYNTAX      Counter32
        UNITS       "packets"
        MAX-ACCESS  read-only
        STATUS      current
        DESCRIPTION
                "Total number of frames received that do not require
                reassembly and therefore will not contain the
                fragmentation header. This counter is valid only when
                end-to-end fragmentation type is set."
        ::= { fsfrFragEntry 7}

fsfrFragNotOutPkts  OBJECT-TYPE
        SYNTAX      Counter32
        UNITS       "packets"
        MAX-ACCESS  read-only
        STATUS      current
        DESCRIPTION
                "Total number of frames transmitted without fragmenting
                and therefore will not contain the fragmentation header.
                This counter is valid only when end-to-end fragmentation
                type is set."
        ::= { fsfrFragEntry 8}

fsfrFragNotInOctets  OBJECT-TYPE
        SYNTAX      Counter32
        UNITS       "octets"
        MAX-ACCESS  read-only
        STATUS      current
        DESCRIPTION
                "Total number of bytes received in frames that do not
                require reassembly and therefore will not contain the
                fragmentation header. This counter is valid only when
                end-to-end fragmentation type is set."
        ::= { fsfrFragEntry 9}

fsfrFragNotOutOctets OBJECT-TYPE
        SYNTAX      Counter32
        UNITS       "octets"
        MAX-ACCESS  read-only
        STATUS      current
        DESCRIPTION
                "Total number of bytes transmitted in frames that are
                not fragmented and therefore will not contain the
                fragmentation header. This counter is valid only when
                end-to-end fragmentation type is set."
        ::= { fsfrFragEntry 10}

fsfrFragAssembledInPkts OBJECT-TYPE
        SYNTAX      Counter32
        UNITS       "packets"
        MAX-ACCESS  read-only
        STATUS      current
        DESCRIPTION
                "Total number of fully reassembled frames. It also
                counts the number of packets received without FR
                fragmentation header (i.e. in un-fragmentated pkts)."
        ::= { fsfrFragEntry 11}

fsfrFragAssembledInOctets OBJECT-TYPE
        SYNTAX      Counter32
        UNITS       "octets"
        MAX-ACCESS  read-only
        STATUS      current
        DESCRIPTION
                "Total number of bytes received in fully reassembled
                frames. It also counts the number of packets received
                without FR fragmentation header (i.e.in un-fragmentated
                pkts)."
        ::= { fsfrFragEntry 12}

fsfrFragPreOutPkts OBJECT-TYPE
        SYNTAX      Counter32
        UNITS       "packets"
        MAX-ACCESS  read-only
        STATUS      current
        DESCRIPTION
                "Total number of frames fragmented and trasmitted. It
                also counts the number of packets trasmitted without FR
                fragmentation header (i.e. in un-fragmentated pkts)."
        ::= { fsfrFragEntry 13}

fsfrFragPreOutOctets OBJECT-TYPE
        SYNTAX      Counter32
        UNITS       "octets"
        MAX-ACCESS  read-only
        STATUS      current
        DESCRIPTION
                "Total number of bytes transmitted in fragmented frames.
                It also counts the number of bytes trasmitted in frames
                without FR fragmentation header (i.e. in un-fragmentated
                pkts)."
        ::= { fsfrFragEntry 14}

fsfrFragDroppedReAssembledInPkts OBJECT-TYPE
        SYNTAX      Counter32
        UNITS       "packets"
        MAX-ACCESS  read-only
        STATUS      current
        DESCRIPTION
                "Number of received fragments dropped for reasons such
                as : running out of memory, receiving segments out of
                sequence, receiving an unexpected frame with a B bit
                set, timing out on a reassembling frame."
        ::= { fsfrFragEntry 15}

fsfrFragDroppedFragmentedOutPkts OBJECT-TYPE
        SYNTAX      Counter32
        UNITS       "packets"
        MAX-ACCESS  read-only
        STATUS      current
        DESCRIPTION
                "Number of fragments dropped because of running
                out of memory."
        ::= { fsfrFragEntry 16}

fsfrFragTimeoutsIn OBJECT-TYPE
        SYNTAX      INTEGER (0..1000)
        MAX-ACCESS  read-only
        STATUS      current
        DESCRIPTION
                "Number of reassemble timer timeouts for this circuit.
                A frame requiring more than two minutes to fully
                reassemble is dropped and timeout will be incremented
                by one."
        ::= { fsfrFragEntry 17}

fsfrFragOutOfSeqFragPkts OBJECT-TYPE
        SYNTAX      Counter32
        UNITS       "packets"
        MAX-ACCESS  read-only
        STATUS      current
        DESCRIPTION
                "Indicates the total number of packets received with an
                unexpected sequence number. All fragments being
                reassembled are dropped. Start a new packet with the
                received segment only if the B bit is set on the
                segment. Otherwise the new segment is also dropped."
        ::= { fsfrFragEntry 18}

fsfrFragUnexpectedBBitSetPkts OBJECT-TYPE
        SYNTAX      Counter32
        UNITS       "packets"
        MAX-ACCESS  read-only
        STATUS      current
        DESCRIPTION
                "Number of fragments received in this circuit with
                a B bit set. All fragments being reassembled are dropped
                and a new packet is started with this segment."
        ::= { fsfrFragEntry 19}

fsfrFragSeqMissedPkts OBJECT-TYPE
        SYNTAX      Counter32
        UNITS       "packets"
        MAX-ACCESS  read-only
        STATUS      current
        DESCRIPTION
                "Number of fragments received in this circuit with
                skipped sequence number."
        ::= { fsfrFragEntry 20}

fsfrFragInterleavedOutPkts OBJECT-TYPE
        SYNTAX      Counter32
        UNITS       "packets"
        MAX-ACCESS  read-only
        STATUS      current
        DESCRIPTION
                "Number of packets that have been interleaved between
                segments."
        ::= { fsfrFragEntry 21}

-- end Fragmentation sub-group }


-- Connect sub-group {

fsfrConnectionTable OBJECT-TYPE
        SYNTAX      SEQUENCE OF FSfrConnectionEntry
        MAX-ACCESS  not-accessible
        STATUS      current
        DESCRIPTION
                "Table of Frame Relay/Frame Relay and Frame Relay/ATM
                Network/Service Interworking connection information.
                These are specific to FS's implementation."
        ::= { fsfrConnectionObjs 1 }

fsfrConnectionEntry OBJECT-TYPE
        SYNTAX      FSfrConnectionEntry
        MAX-ACCESS  not-accessible
        STATUS      current
        DESCRIPTION
                "Each entry of the table contains information of a
                connection that is established for Frame Relay/Frame
                Relay and Frame Relay/ATM Network/Service Interworking."
        INDEX { frCircuitIfIndex, frCircuitDlci}
        ::= { fsfrConnectionTable 1 }

FSfrConnectionEntry ::=
        SEQUENCE {
            fsfrConnName               DisplayString,
            fsfrConnID                 INTEGER,
            fsfrConnState              DisplayString,
            fsfrConnSegment1Name       DisplayString,
            fsfrConnSegment1VCGroup    DisplayString,
            fsfrConnSegment1Dlci       DlciNumber,
            fsfrConnSegment2Name       DisplayString,
            fsfrConnSegment2Vpi        INTEGER,
            fsfrConnSegment2Vci        INTEGER,
            fsfrConnServiceTranslation INTEGER,
            fsfrConnFrSscsDlci         DlciNumber,
            fsfrConnEfciBit            INTEGER,
            fsfrConnDeBit              INTEGER,
            fsfrConnClpBit             INTEGER
        }

fsfrConnName OBJECT-TYPE
        SYNTAX       DisplayString
        MAX-ACCESS   read-only
        STATUS       current
        DESCRIPTION
               "The textual name of a for FR/FR or FR/ATM
               Network/Service Interworking connection."
        ::= { fsfrConnectionEntry 1 }

fsfrConnID OBJECT-TYPE
        SYNTAX       INTEGER (1..2000)
        MAX-ACCESS   read-only
        STATUS       current
        DESCRIPTION
               "The numerical identifier of a FR/FR or FR/ATM
               Network/Service Interworking connection."
        ::= { fsfrConnectionEntry 2 }

fsfrConnState OBJECT-TYPE
        SYNTAX      DisplayString
        MAX-ACCESS  read-only
        STATUS      current
        DESCRIPTION
                "Status of a FR/FR or FR/ATM  Network/Service
                Interworking connection."
        ::= { fsfrConnectionEntry 3}

fsfrConnSegment1Name OBJECT-TYPE
        SYNTAX       DisplayString
        MAX-ACCESS   read-only
        STATUS       current
        DESCRIPTION
               "The textual name used to identify the first segment of
               a FR/FR or FR/ATM  Network/Service Interworking
               connection."
        ::= { fsfrConnectionEntry 4}

fsfrConnSegment1VCGroup OBJECT-TYPE
        SYNTAX       DisplayString
        MAX-ACCESS   read-only
        STATUS       current
        DESCRIPTION
               "The textual name used to identify the VC-Group in the
               first segment of a Frame Relay/ATM  Network Interworking
               (FRF.5)connection.
               This field is not applicabe in case of,
                        FRF.8 (Frame Relay/ATM  Service Interworking)
                        and
                        FR-FR connectione. "
       ::= { fsfrConnectionEntry 5}

fsfrConnSegment1Dlci OBJECT-TYPE
        SYNTAX       DlciNumber
        MAX-ACCESS   read-only
        STATUS       current
        DESCRIPTION
               "The DLCI used as the first segment of a FR-FR or FR-ATM
               Network/Service Interworking connection."
        ::= { fsfrConnectionEntry 6}

fsfrConnSegment2Name OBJECT-TYPE
        SYNTAX       DisplayString
        MAX-ACCESS   read-only
        STATUS       current
        DESCRIPTION
               "The interface on which second segment of a FR-FR or
               FR-ATM  Network/Service Interworking connection is
               configured."
        ::= { fsfrConnectionEntry 7}

fsfrConnSegment2Vpi OBJECT-TYPE
        SYNTAX       INTEGER (0..4095)
        MAX-ACCESS   read-only
        STATUS       current
        DESCRIPTION
               "The value of  VPI, in the ATM connection, used as the
               second segment of a FR-ATM  Network/Service Interworking
               connection. In case of FR-FR connection, the same will
               be used to display the DLCI used as the second segment."
        ::= { fsfrConnectionEntry 8}

fsfrConnSegment2Vci OBJECT-TYPE
        SYNTAX       INTEGER (0..4095)
        MAX-ACCESS   read-only
        STATUS       current
        DESCRIPTION
               "The value of  VCI, in the ATM connection, used as the
               second segment of a FR-ATM  Network/Service Interworking
               connection. In case of FR-FR connection, this is not
               supported."
       ::= { fsfrConnectionEntry 9}

fsfrConnServiceTranslation OBJECT-TYPE
        SYNTAX       INTEGER {
                        serviceTranslationEnabled(1),
                        serviceTranslationNotEnabled(2)
                     }
        MAX-ACCESS   read-only
        STATUS       current
        DESCRIPTION
               "Shows whether Service Translation Mode is supported or
               not. Translation Mode is the interworking of
               internetworking (routed and/or bridged) protocols used
               in FR-ATM  Service PVC Interworking(FRF.8).
               This is not supported in case of FRF.5 (FR-ATM network
               Interworking) and FR-FR connections."
       ::= { fsfrConnectionEntry 10}

fsfrConnFrSscsDlci OBJECT-TYPE
        SYNTAX       DlciNumber
        MAX-ACCESS   read-only
        STATUS       current
        DESCRIPTION
               "The DLCI value used at the FR-SSCS layer. This is one of
               connection multiplexing methods used in Frame Relay/ATM
               Network Interworking.
               Not supported in case of FRF.8 (FR-ATM Service PVC
               Interworking) and FR-FR connections"
        ::= { fsfrConnectionEntry 11}

fsfrConnEfciBit OBJECT-TYPE
        SYNTAX       INTEGER  {
                         mapFecn(1),
                         notMapFecn(2)
                     }
        MAX-ACCESS   read-only
        STATUS       current
        DESCRIPTION
               "Shows whether the FECN field in the FR frame is mapped
               to the ATM EFCI field of every cell generated out of the
               FR frame. This is used to indicate congestion in FR to
               ATM direction in case of Frame Relay/ATM  Service PVC
               Interworking.
               Not supported in FRF.5 (Frame Relay/ATM Network
               Interworking and FR-FR connections."
::= { fsfrConnectionEntry 12}

fsfrConnDeBit OBJECT-TYPE
        SYNTAX       INTEGER {
                         noMapClp(1),
                         mapClp(2),
                         setDe0(3),
                         setDe1(4)
                     }
        MAX-ACCESS   read-only
        STATUS       current
        DESCRIPTION
               "The method of operation for loss priority mapping in the
               B-ISDN to FR direction..
               Not supported in case of FR-FR connection."
        ::= { fsfrConnectionEntry 13}

fsfrConnClpBit OBJECT-TYPE
        SYNTAX  INTEGER {
                  setClpTo0AndCopyDeToFrsscsDe(1),
                  setClpTo1AndCopyDeToFrsscsDe(2),
                  copyDeToFrsscsDeAndClp(3),
                  copyDeToClp(4),
                  setClp1(5),
                  setClp0(6)
                }
        MAX-ACCESS   read-only
        STATUS       current
        DESCRIPTION
               "The method of operation used to map loss priority
               mapping in the FR to ATM direction.
               Not supported in case of FR-FR connection."
        ::= { fsfrConnectionEntry 14}

-- end Conn subgroup }

fsFrMIBConformance OBJECT IDENTIFIER ::= { fsFrameRelayMIB 3 }
fsFrMIBCompliances OBJECT IDENTIFIER ::= { fsFrMIBConformance 1 }
fsFrMIBGroups      OBJECT IDENTIFIER ::= { fsFrMIBConformance 2 }

fsFrMIBCompliance MODULE-COMPLIANCE
        STATUS  obsolete  -- obsoleted by fsFrMIBCompliancesRev2
        DESCRIPTION
                "The compliance statement for entities which implement
                this FS Frame Relay MIB."
        MODULE  -- this module
                MANDATORY-GROUPS { fsFrMIBGroup }
        ::= { fsFrMIBCompliances 1 }

fsFrMIBCompliancesRev1 MODULE-COMPLIANCE
        STATUS  obsolete  -- obsoleted by fsFrMIBCompliancesRev2
        DESCRIPTION
                "The compliance statement for entities which implement
                this FS Frame Relay MIB."
        MODULE  -- this module
                MANDATORY-GROUPS { fsFrMIBGroupRev1 }
        ::= { fsFrMIBCompliances 2 }

fsFrMIBCompliancesRev2 MODULE-COMPLIANCE
        STATUS  obsolete  -- obsoleted by fsFrMIBCompliancesRev3
        DESCRIPTION
                "The compliance statement for entities which implement
                this FS Frame Relay MIB."
        MODULE  -- this module
                MANDATORY-GROUPS { fsFrLmiMIBGroup,
                                   fsFrCircuitMIBGroup,
                                   fsExtCircuitMIBGroup,
                                   fsFrTsMIBGroup,
                                   fsFrMapMIBGroup,
                                   fsFrSvcMIBGroup }
        ::= { fsFrMIBCompliances 3 }

fsFrMIBCompliancesRev3 MODULE-COMPLIANCE
        STATUS  deprecated  -- deprecated by fsFrMIBCompliancesRev4
        DESCRIPTION
                "The compliance statement for entities which implement
                this FS Frame Relay MIB."
        MODULE  -- this module
                MANDATORY-GROUPS { fsFrLmiMIBGroup,
                                   fsFrCircuitMIBGroup,
                                   fsExtCircuitMIBGroup,
                                   fsFrTsMIBGroup,
                                   fsFrMapMIBGroup,
                                   fsFrSvcMIBGroup,
                                   fsFrElmiMIBGroup}
        ::= { fsFrMIBCompliances 4 }

fsFrMIBCompliancesRev4 MODULE-COMPLIANCE
        STATUS  current
        DESCRIPTION
                "The compliance statement for entities which implement
                this fs Frame Relay MIB."
        MODULE  -- this module
                MANDATORY-GROUPS { fsFrLmiMIBGroup,
                                   fsFrCircuitMIBGroup,
                                   fsExtCircuitMIBGroup1,
                                   fsFrTsMIBGroup,
                                   fsFrMapMIBGroup,
                                   fsFrSvcMIBGroup,
                                   fsFrElmiMIBGroup1,
                                   fsFrFragMIBGroup,
                                   fsFrConnMIBGroup}
        ::= { fsFrMIBCompliances 5 }

-- units of conformance:

fsFrMIBGroup OBJECT-GROUP
        OBJECTS {
            fsfrLmiLinkstatus,
            fsfrLmiLinkType,
            fsfrLmiEnquiryIns,
            fsfrLmiEnquiryOuts,
            fsfrLmiStatusIns,
            fsfrLmiStatusOuts,
            fsfrLmiUpdateStatusIns,
            fsfrLmiUpdateStatusOuts,
            fsfrLmiStatusTimeouts,
            fsfrLmiStatusEnqTimeouts,
            fsfrLmiN392Dce,
            fsfrLmiN393Dce,
            fsfrLmiT392Dce,
            fsfrCircuitDEins,
            fsfrCircuitDEouts,
            fsfrCircuitDropPktsOuts,
            fsfrCircuitType,
            fsfrExtCircuitIfName,
            fsfrExtCircuitIfType,
            fsfrExtCircuitSubifIndex,
            fsfrExtCircuitMapStatus,
            fsfrExtCircuitCreateType,
            fsfrExtCircuitMulticast,
            fsfrExtCircuitRoutedDlci,
            fsfrExtCircuitRoutedIf,
            fsfrMapIndex,
            fsfrMapProtocol,
            fsfrMapAddress,
            fsfrMapType,
            fsfrMapEncaps,
            fsfrMapBroadcast,
            fsfrMapPayloadCompress,
            fsfrMapTcpHdrCompress,
            fsfrSvcAddrLocal,
            fsfrSvcAddrRemote,
            fsfrSvcThroughputIn,
            fsfrSvcMinThruputOut,
            fsfrSvcMinThruputIn,
            fsfrSvcCommitBurstIn,
            fsfrSvcExcessBurstIn,
            fsfrSvcIdleTime
        }
        STATUS  deprecated       -- obsoleted by fsFrMIBGroupRev1
        DESCRIPTION
                "The compliance statement for entities which implement
                this FS Frame Relay MIB."
        ::= { fsFrMIBGroups 1 }

fsFrMIBGroupRev1 OBJECT-GROUP
        OBJECTS {
            fsfrLmiLinkstatus,
            fsfrLmiLinkType,
            fsfrLmiEnquiryIns,
            fsfrLmiEnquiryOuts,
            fsfrLmiStatusIns,
            fsfrLmiStatusOuts,
            fsfrLmiUpdateStatusIns,
            fsfrLmiUpdateStatusOuts,
            fsfrLmiStatusTimeouts,
            fsfrLmiStatusEnqTimeouts,
            fsfrLmiN392Dce,
            fsfrLmiN393Dce,
            fsfrLmiT392Dce,
            fsfrCircuitDEins,
            fsfrCircuitDEouts,
            fsfrCircuitDropPktsOuts,
            fsfrCircuitType,
            fsfrExtCircuitIfName,
            fsfrExtCircuitIfType,
            fsfrExtCircuitSubifIndex,
            fsfrExtCircuitMapStatus,
            fsfrExtCircuitCreateType,
            fsfrExtCircuitMulticast,
            fsfrExtCircuitRoutedDlci,
            fsfrExtCircuitRoutedIf,
            fsfrExtCircuitUncompressIns,
            fsfrExtCircuitUncompressOuts,
            fsfrMapIndex,
            fsfrMapProtocol,
            fsfrMapAddress,
            fsfrMapType,
            fsfrMapEncaps,
            fsfrMapBroadcast,
-- removed  fsfrMapPayloadCompress, obsoleted by fsfrMapPayloadCompressType
            fsfrMapTcpHdrCompress,
            fsfrMapRtpHdrCompress,
            fsfrMapPayloadCompressType,
            fsfrSvcAddrLocal,
            fsfrSvcAddrRemote,
            fsfrSvcThroughputIn,
            fsfrSvcMinThruputOut,
            fsfrSvcMinThruputIn,
            fsfrSvcCommitBurstIn,
            fsfrSvcExcessBurstIn,
            fsfrSvcIdleTime
        }
        STATUS  deprecated
        DESCRIPTION
                "A collection of objects providing router's
                Frame Relay configuration and statistics
                information that are additional to the IETF
                standard Frame Relay DTE MIB."
        ::= { fsFrMIBGroups 2 }

fsFrLmiMIBGroup    OBJECT-GROUP
        OBJECTS {
            fsfrLmiLinkstatus, fsfrLmiLinkType, fsfrLmiEnquiryIns,
            fsfrLmiEnquiryOuts, fsfrLmiStatusIns, fsfrLmiStatusOuts,
            fsfrLmiUpdateStatusIns, fsfrLmiUpdateStatusOuts,
            fsfrLmiStatusTimeouts, fsfrLmiStatusEnqTimeouts,
            fsfrLmiN392Dce, fsfrLmiN393Dce, fsfrLmiT392Dce
        }
        STATUS current
        DESCRIPTION
                "A collection of objects providing router's
                 Frame Relay LMI configuration and statistics
                 information either supplemental to the
                 frDlcmiTable of RFC 1315 or specific to fs's
                 implementation."
        ::= { fsFrMIBGroups 3 }

fsFrCircuitMIBGroup    OBJECT-GROUP
        OBJECTS {
            fsfrCircuitDEins, fsfrCircuitDEouts,
            fsfrCircuitDropPktsOuts, fsfrCircuitType
        }
        STATUS current
        DESCRIPTION
                "A collection of objects providing information of a
                circuit that are not included in frCircuitTable of
                RFC1315 but are generic to Frame Relay."
        ::= { fsFrMIBGroups 4 }

fsExtCircuitMIBGroup    OBJECT-GROUP
        OBJECTS {
            fsfrExtCircuitIfName, fsfrExtCircuitIfType,
            fsfrExtCircuitSubifIndex, fsfrExtCircuitMapStatus,
            fsfrExtCircuitCreateType, fsfrExtCircuitMulticast,
            fsfrExtCircuitRoutedDlci, fsfrExtCircuitRoutedIf,
            fsfrExtCircuitUncompressIns, fsfrExtCircuitUncompressOuts,
            fsfrExtCircuitFECNOuts, fsfrExtCircuitBECNOuts,
            fsfrExtCircuitMinThruputOut, fsfrExtCircuitMinThruputIn,
            fsfrExtCircuitBcastPktOuts, fsfrExtCircuitBcastByteOuts,
            fsfrExtCircuitBandwidth
        }
        STATUS  deprecated
        DESCRIPTION
                "A collection of objects that provide fs
                implementation specific FR circuit information.
                This is a fs extension for the frCircuitTable
                of RFC 1315."
        ::= { fsFrMIBGroups 5 }

fsExtCircuitMIBGroup1    OBJECT-GROUP
        OBJECTS {
            fsfrExtCircuitIfName, fsfrExtCircuitIfType,
            fsfrExtCircuitSubifIndex, fsfrExtCircuitMapStatus,
            fsfrExtCircuitCreateType, fsfrExtCircuitMulticast,
            fsfrExtCircuitRoutedDlci, fsfrExtCircuitRoutedIf,
            fsfrExtCircuitUncompressIns, fsfrExtCircuitUncompressOuts,
            fsfrExtCircuitFECNOuts, fsfrExtCircuitBECNOuts,
            fsfrExtCircuitMinThruputOut, fsfrExtCircuitMinThruputIn,
            fsfrExtCircuitBcastPktOuts, fsfrExtCircuitBcastByteOuts,
            fsfrExtCircuitBandwidth, fsfrExtCircuitTxDataRate,
            fsfrExtCircuitTxPktRate, fsfrExtCircuitRcvDataRate,
            fsfrExtCircuitRcvPktRate
        }
        STATUS current
        DESCRIPTION
                "A collection of objects that provide fs
                implementation specific FR circuit information.
                This is a fs extension for the frCircuitTable
                of RFC 1315."
        ::= { fsFrMIBGroups 13 }


fsFrTsMIBGroup    OBJECT-GROUP
        OBJECTS {
            fsfrExtCircuitShapeByteLimit, fsfrExtCircuitShapeInterval,
            fsfrExtCircuitShapeByteIncrement, fsfrExtCircuitShapePkts,
            fsfrExtCircuitShapeBytes, fsfrExtCircuitShapePktsDelay,
            fsfrExtCircuitShapeBytesDelay, fsfrExtCircuitShapeActive,
            fsfrExtCircuitShapeAdapting
        }
        STATUS current
        DESCRIPTION
                "A collection of objects that provide information
                about Frame Relay Traffic Shaping. These are
                additional to the IETF standard Frame Relay DTE MIB."
        ::= { fsFrMIBGroups 6 }

fsFrMapMIBGroup    OBJECT-GROUP
        OBJECTS {
            fsfrMapIndex, fsfrMapProtocol, fsfrMapAddress,
            fsfrMapType, fsfrMapEncaps, fsfrMapBroadcast,
            fsfrMapTcpHdrCompress, fsfrMapRtpHdrCompress,
            fsfrMapPayloadCompressType
        }
        STATUS current
        DESCRIPTION
                "A collection of objects to provide mapping
                information of a Frame Relay virtual circuit.
                These are additional to the IETF standard
                Frame Relay DTE MIB."
        ::= { fsFrMIBGroups 7 }

fsFrSvcMIBGroup    OBJECT-GROUP
        OBJECTS {
            fsfrSvcAddrLocal,
            fsfrSvcAddrRemote,
            fsfrSvcThroughputIn,
            fsfrSvcCommitBurstIn,
            fsfrSvcExcessBurstIn,
            fsfrSvcIdleTime
        }
        STATUS current
        DESCRIPTION
                "A collection of objects to provide circuit
                information specific to a Frame Relay Switched
                Virtual Circuit.This is in addition to the IETF
                standard Frame Relay DTE MIB."
        ::= { fsFrMIBGroups 8 }

fsFrElmiMIBGroup    OBJECT-GROUP
        OBJECTS {
            fsfrElmiIpAddr, fsfrElmiArStatus, fsfrElmiRemoteStatus,
            fsfrElmiNeighborArStatus, fsfrElmiNeighborIpAddress,
            fsfrElmiNeighborIfIndex, fsfrElmiNeighborVendorName,
            fsfrElmiNeighborPlatformName, fsfrElmiNeighborDeviceName
        }
        STATUS deprecated
        DESCRIPTION
                "A collection of objects providing router's
                ELMI information."
        ::= { fsFrMIBGroups 9 }

fsFrElmiMIBGroup1    OBJECT-GROUP
        OBJECTS {
            fsfrElmiIpAddr, fsfrElmiArStatus, fsfrElmiRemoteStatus,
            fsfrElmiNeighborArStatus, fsfrElmiNeighborIpAddress,
            fsfrElmiNeighborIfIndex, fsfrElmiNeighborVendorName,
            fsfrElmiNeighborPlatformName, fsfrElmiNeighborDeviceName,
            fsfrElmiLinkStatus
        }
        STATUS current
        DESCRIPTION
                "A collection of objects providing router's
                ELMI information."
        ::= { fsFrMIBGroups 10 }

fsFrFragMIBGroup    OBJECT-GROUP
        OBJECTS {
            fsfrFragSize, fsfrFragType, fsfrFragInPkts, fsfrFragOutPkts,
            fsfrFragInOctets, fsfrFragOutOctets, fsfrFragNotInPkts,
            fsfrFragNotOutPkts, fsfrFragNotInOctets, fsfrFragNotOutOctets,
            fsfrFragAssembledInPkts, fsfrFragAssembledInOctets,
            fsfrFragPreOutPkts, fsfrFragPreOutOctets,
            fsfrFragDroppedReAssembledInPkts,
            fsfrFragDroppedFragmentedOutPkts,
            fsfrFragTimeoutsIn, fsfrFragOutOfSeqFragPkts,
            fsfrFragUnexpectedBBitSetPkts, fsfrFragSeqMissedPkts,
            fsfrFragInterleavedOutPkts
        }
        STATUS current
        DESCRIPTION
                "A collection of objects providing router's
                fragmentation information."
        ::= { fsFrMIBGroups 11 }

fsFrConnMIBGroup    OBJECT-GROUP
        OBJECTS {
            fsfrConnName, fsfrConnID, fsfrConnState, fsfrConnSegment1Name,
            fsfrConnSegment1VCGroup, fsfrConnSegment1Dlci,
            fsfrConnSegment2Name, fsfrConnSegment2Vpi,
            fsfrConnSegment2Vci, fsfrConnServiceTranslation,
            fsfrConnFrSscsDlci, fsfrConnEfciBit,
            fsfrConnDeBit, fsfrConnClpBit
        }
        STATUS current
        DESCRIPTION
                "A collection of objects providing router's
                fragmentation information."
        ::= { fsFrMIBGroups 12 }


END
