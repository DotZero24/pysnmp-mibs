-- ====================================================================
-- Copyright (c) 2011 by FS.COM Inc.. All rights reserved.
--
-- Description: The MIB is designed to get 3G wireless safenet solution statistic information.
-- Reference: fs Enterprise MIB
-- =====================================================================

FS-3G-MIB DEFINITIONS ::= BEGIN

    IMPORTS
        DisplayString,TEXTUAL-CONVENTION,TimeStamp
            FROM SNMPv2-TC
        IpAddress, Integer32, Counter32, Counter64, OBJECT-TYPE,
        MODULE-IDENTITY, Gauge32, NOTIFICATION-TYPE, Unsigned32
            FROM SNMPv2-SMI
        MODULE-COMPLIANCE, OBJECT-GROUP, NOTIFICATION-GROUP
            FROM SNMPv2-CONF
        fsMgmt
            FROM FS-SMI;

    fs3GMonitor MODULE-IDENTITY
        LAST-UPDATED "201102220000Z"
        ORGANIZATION
            "FS.COM Inc.."
        CONTACT-INFO
            "Tel: 400-865-2852
             E-mail: https://www.fs.com/live_chat_service_mail.html"
        DESCRIPTION
            "The MIB is designed to get statistic information of
             3G wireless safenet. With this MIB, we can get information of a certain
             3G user or all users."
        REVISION      "201102220000Z"
        DESCRIPTION
                "Initial version of this MIB module."
        ::= { fsMgmt 95 }


-- ========================================================================
-- Node definitions
-- ========================================================================
--Begin the node of fs3GObjects.

    fs3GObjects OBJECT IDENTIFIER ::= { fs3GMonitor 1 }

-- ===============================================
-- Begin the table of fs3GTable.
-- ===============================================

    fs3GTable OBJECT-TYPE
        SYNTAX SEQUENCE OF FS3GEntry
        MAX-ACCESS not-accessible
        STATUS current
        DESCRIPTION
            "The 3G connection infomation fot every user. There is one
             entry in this table for each active 3G connection."
        ::= { fs3GObjects 1 }

    fs3GEntry OBJECT-TYPE
        SYNTAX FS3GEntry
        MAX-ACCESS not-accessible
        STATUS current
        DESCRIPTION
            "Information about fs3GTunnelTable."
        INDEX { fs3GIPAddr }
        ::= { fs3GTable 1 }

    FS3GEntry ::=
        SEQUENCE {
            fs3gUsername
                DisplayString,
            fs3GOnlineStatus
            	INTEGER,
            fs3GIMEI
                DisplayString,
            fs3GIPAddrType
            	INTEGER,
            fs3GIPAddr
            	IpAddress,
            fs3GUplineTime
                TimeStamp,
            fs3GActiveTime
           	    Integer32,
            fs3GSignalStrength
           	    Integer32,
            fs3GISP
           	    INTEGER,
            fs3GSysMode
           	    INTEGER,
            fs3GServiceStatus
            	INTEGER,
            fs3GRoamingStatus
                INTEGER,
            fs3GDomain
            	INTEGER,
            fs3GSIMStatus
                INTEGER,
   	    fs3GSignalStrengthPercent
                Integer32,
            fs3GApn
                DisplayString,
            fs3GCellID
                Integer32,
            fs3GLAC
                Integer32,
            fs3GBSID
                Integer32,
            fs3GSID
                Integer32,
            fs3GNID
                Integer32,
            fs3GIMSI
                DisplayString,
            fs3GESN
                DisplayString,
            fs3GPhoneNumber
                DisplayString,
            fs3GifIndex
                INTEGER,
            fs3GBSLONG
                Integer32,
            fs3GBSLAT
                Integer32,
	    fs3GBackupInfo
	            INTEGER,
            fs3GSerialNumber
                DisplayString,
	    fs3GBackupIMSI
                DisplayString,
            fs3GGatewayIPAddr
            	IpAddress,
	    fs3GLineDownCause
	            Integer32,
	    fs3GModemType
	            INTEGER
        }

    fs3gUsername OBJECT-TYPE
        SYNTAX DisplayString
        MAX-ACCESS read-only
        STATUS current
        DESCRIPTION
            "The Username  of 3G User."
        ::= { fs3GEntry 1 }

    fs3GOnlineStatus OBJECT-TYPE
        SYNTAX INTEGER
            {
                lpm(0),
		online(1),
                offline(4),
		ftm(5),
		reset(6),
		rfOff(7)
            }
        MAX-ACCESS read-only
        STATUS current
        DESCRIPTION
            "the status of 3G user. online or offline"
        ::= { fs3GEntry 2 }

    fs3GIMEI OBJECT-TYPE
        SYNTAX DisplayString
        MAX-ACCESS read-only
        STATUS current
        DESCRIPTION
            "the IMEI number of 3G user."
        ::= { fs3GEntry 3 }

    fs3GIPAddrType OBJECT-TYPE
         SYNTAX INTEGER {
            ipv4Addr(1),
            ipv6Addr(2)
         }
        MAX-ACCESS read-only
        STATUS current
        DESCRIPTION
            "The IP Address type of remote user."
        ::= { fs3GEntry 4 }

    fs3GIPAddr OBJECT-TYPE
        SYNTAX IpAddress
        MAX-ACCESS read-only
        STATUS current
        DESCRIPTION
            "The 3G remote users's IP address."
        ::= { fs3GEntry 5 }

    fs3GUplineTime OBJECT-TYPE
        SYNTAX TimeStamp
        MAX-ACCESS read-only
        STATUS current
        DESCRIPTION
            "The value of up line time for this 3G user."
        ::= { fs3GEntry 6 }


        -- 1.3.6.1.4.1.52642.1.1.10.2.95.1.1.1.7
        fs3GActiveTime OBJECT-TYPE
			SYNTAX Integer32 (0..2147483647)
			MAX-ACCESS read-only
			STATUS current
			DESCRIPTION
				"The duration of the 3G connection has been active for one user.
				2147483647 is defined as invalid value."
			::= { fs3GEntry 7 }


		-- 1.3.6.1.4.1.52642.1.1.10.2.95.1.1.1.8
		fs3GSignalStrength OBJECT-TYPE
			SYNTAX Integer32 (-150..0)
			MAX-ACCESS read-only
			STATUS current
			DESCRIPTION
				"The signal strength of the 3G connection for this user."
			::= { fs3GEntry 8 }


		-- 1.3.6.1.4.1.52642.1.1.10.2.95.1.1.1.9
		fs3GISP OBJECT-TYPE
			SYNTAX INTEGER
				{
				chinaUnicom(1),
				chinaTelecom(2),
				chinaMobile(3)
				}
			MAX-ACCESS read-only
			STATUS current
			DESCRIPTION
				"the ISP of 3G networsk."
			::= { fs3GEntry 9 }


		-- 1.3.6.1.4.1.52642.1.1.10.2.95.1.1.1.10
		fs3GSysMode OBJECT-TYPE
			SYNTAX INTEGER
				{
				noService(0),
				amps(1),
				cdma(2),
				gsmGprs(3),
				hdr(4),
				wcdma(5),
				gps(6),
				gsmCdma(7),
				cdmaHdrHybrid(8),
				tdscdma(15),
				td-1te(100),
				fdd-lte(101)
				}
			MAX-ACCESS read-only
			STATUS current
			DESCRIPTION
				"the system mode of 3G networsk."
			::= { fs3GEntry 10 }


		-- 1.3.6.1.4.1.52642.1.1.10.2.95.1.1.1.11
		fs3GServiceStatus OBJECT-TYPE
			SYNTAX INTEGER
				{
				noService(0),
				restricted(1),
				valid(2),
				restrictedRegional(3),
				powerSavingAndDeepSleepState(4)
				}
			MAX-ACCESS read-only
			STATUS current
			DESCRIPTION
				"the sevice status of 3G user."
			::= { fs3GEntry 11 }


		-- 1.3.6.1.4.1.52642.1.1.10.2.95.1.1.1.12
		fs3GRoamingStatus OBJECT-TYPE
			SYNTAX INTEGER
				{
				noRoaming(0),
				roaming(1)
				}
			MAX-ACCESS read-only
			STATUS current
			DESCRIPTION
				"the roaming status of 3G  user."
			::= { fs3GEntry 12 }


		-- 1.3.6.1.4.1.52642.1.1.10.2.95.1.1.1.13
		fs3GDomain OBJECT-TYPE
			SYNTAX INTEGER
				{
				noService(0),
				onlyCS(1),
				onlyPS(2),
				pSCS(3),
				pSCSnotRegistered(4),
				ePSService(100),
				cdmaNotSupport(255)
				}
			MAX-ACCESS read-only
			STATUS current
			DESCRIPTION
				"the Domain status of 3G user ."
			::= { fs3GEntry 13 }


		-- 1.3.6.1.4.1.52642.1.1.10.2.95.1.1.1.14
		fs3GSIMStatus OBJECT-TYPE
			SYNTAX INTEGER
				{
				invalidUsimCard(0),
				validUsimCard(1),
				invalidForCS(2),
				invalidForPS(3),
				invalidForCSPS(4),
				noUsimCard(255)
				}
			MAX-ACCESS read-only
			STATUS current
			DESCRIPTION
				"the SIM card status of 3G user."
			::= { fs3GEntry 14 }


		-- 1.3.6.1.4.1.52642.1.1.10.2.95.1.1.1.15
		fs3GSignalStrengthPercent OBJECT-TYPE
			SYNTAX Integer32 (0..100)
			MAX-ACCESS read-only
			STATUS current
			DESCRIPTION
				"The percent of signal strength of the 3G connection for this user."
			::= { fs3GEntry 15 }


		-- 1.3.6.1.4.1.52642.1.1.10.2.95.1.1.1.16
		fs3GApn OBJECT-TYPE
			SYNTAX DisplayString
			MAX-ACCESS read-only
			STATUS current
			DESCRIPTION
				"The access-point  of 3G User(only used in TD-SCDMA and WCDMA)."
			::= { fs3GEntry 16 }


		-- 1.3.6.1.4.1.52642.1.1.10.2.95.1.1.1.17
		fs3GCellID OBJECT-TYPE
			SYNTAX Integer32 (0..100)
			MAX-ACCESS read-only
			STATUS current
			DESCRIPTION
				"The access Cell id  of 3G User(only used in TD-SCDMA and WCDMA)."
			::= { fs3GEntry 17 }


		-- 1.3.6.1.4.1.52642.1.1.10.2.95.1.1.1.18
		fs3GLAC OBJECT-TYPE
			SYNTAX Integer32 (0..100)
			MAX-ACCESS read-only
			STATUS current
			DESCRIPTION
				"The Location Area Code  of 3G User(only used in TD-SCDMA and WCDMA)."
			::= { fs3GEntry 18 }


		-- 1.3.6.1.4.1.52642.1.1.10.2.95.1.1.1.19
		fs3GBSID OBJECT-TYPE
			SYNTAX Integer32 (0..100)
			MAX-ACCESS read-only
			STATUS current
			DESCRIPTION
				"The Base Station ID  of 3G User(only used in CDMA2000)."
			::= { fs3GEntry 19 }


		-- 1.3.6.1.4.1.52642.1.1.10.2.95.1.1.1.20
		fs3GNID OBJECT-TYPE
			SYNTAX Integer32 (0..100)
			MAX-ACCESS read-only
			STATUS current
			DESCRIPTION
				"The Network ID  of 3G User(only used in CDMA2000)."
			::= { fs3GEntry 20 }


		-- 1.3.6.1.4.1.52642.1.1.10.2.95.1.1.1.21
		fs3GSID OBJECT-TYPE
			SYNTAX Integer32 (0..100)
			MAX-ACCESS read-only
			STATUS current
			DESCRIPTION
				"The System ID  of 3G User(only used in CDMA2000)."
			::= { fs3GEntry 21 }


		-- 1.3.6.1.4.1.52642.1.1.10.2.95.1.1.1.22
		fs3GIMSI OBJECT-TYPE
			SYNTAX DisplayString
			MAX-ACCESS read-only
			STATUS current
			DESCRIPTION
				"The IMSI  of 3G User."
			::= { fs3GEntry 22 }


		-- 1.3.6.1.4.1.52642.1.1.10.2.95.1.1.1.23
		fs3GESN OBJECT-TYPE
			SYNTAX DisplayString
			MAX-ACCESS read-only
			STATUS current
			DESCRIPTION
				"The ESN  of 3G User(only used in CDMA2000)."
			::= { fs3GEntry 23 }


		-- 1.3.6.1.4.1.52642.1.1.10.2.95.1.1.1.24
		fs3GPhoneNumber OBJECT-TYPE
			SYNTAX DisplayString
			MAX-ACCESS read-only
			STATUS current
			DESCRIPTION
				"The Phone Number of 3G User."
			::= { fs3GEntry 24 }


		-- 1.3.6.1.4.1.52642.1.1.10.2.95.1.1.1.25
		fs3GifIndex OBJECT-TYPE
			SYNTAX INTEGER
			MAX-ACCESS read-only
			STATUS current
			DESCRIPTION
				"The Index of 3G Interface."
			::= { fs3GEntry 25 }


		-- 1.3.6.1.4.1.52642.1.1.10.2.95.1.1.1.26
		fs3GBSLONG OBJECT-TYPE
			SYNTAX Integer32
			MAX-ACCESS read-only
			STATUS current
			DESCRIPTION
				"The longitude of 3G User(only used in CDMA2000)."
			::= { fs3GEntry 26 }


		-- 1.3.6.1.4.1.52642.1.1.10.2.95.1.1.1.27
		fs3GBSLAT OBJECT-TYPE
			SYNTAX Integer32
			MAX-ACCESS read-only
			STATUS current
			DESCRIPTION
				"The latitude of 3G User(only used in CDMA2000)."
			::= { fs3GEntry 27 }


		-- 1.3.6.1.4.1.52642.1.1.10.2.95.1.1.1.28
		fs3GBackupInfo OBJECT-TYPE
			SYNTAX INTEGER
				{
				no-backup(0),
				myself(1),
				master(2),
				slave(3)
				}
			MAX-ACCESS read-only
			STATUS current
			DESCRIPTION
				"The backup info of 3G line."
			::= { fs3GEntry 28 }


		-- 1.3.6.1.4.1.52642.1.1.10.2.95.1.1.1.29
		fs3GSerialNumber OBJECT-TYPE
			SYNTAX DisplayString
			MAX-ACCESS read-only
			STATUS current
			DESCRIPTION
				"The serial number of 3G router."
			::= { fs3GEntry 29 }


		-- 1.3.6.1.4.1.52642.1.1.10.2.95.1.1.1.30
		fs3GBackupIMSI OBJECT-TYPE
			SYNTAX DisplayString
			MAX-ACCESS read-only
			STATUS current
			DESCRIPTION
				"The IMSI of 3G backup line."
			::= { fs3GEntry 30 }


		-- 1.3.6.1.4.1.52642.1.1.10.2.95.1.1.1.31
		fs3GGatewayIPAddr OBJECT-TYPE
			SYNTAX IpAddress
			MAX-ACCESS read-only
			STATUS current
			DESCRIPTION
				"The IP address of the 3g gateway."
			::= { fs3GEntry 31 }


		-- 1.3.6.1.4.1.52642.1.1.10.2.95.1.1.1.32
		fs3GLineDownCause OBJECT-TYPE
			SYNTAX Integer32
			MAX-ACCESS read-only
			STATUS current
			DESCRIPTION
				"The cause of line down."
			::= { fs3GEntry 32 }

	       fs3GModemType OBJECT-TYPE
			SYNTAX INTEGER
				{
				modem-type-3G(1),
				modem-type-4G(2)
				}
			MAX-ACCESS read-only
			STATUS current
			DESCRIPTION
				"the type of modem used in router."
			::= { fs3GEntry 33 }


-- ===============================================
-- Begin the table of fs3GstatTable.
-- ===============================================

    fs3GStatTable OBJECT-TYPE
        SYNTAX SEQUENCE OF FS3GStatEntry
        MAX-ACCESS not-accessible
        STATUS current
        DESCRIPTION
            "The 3G connection infomation fot every user. There is one
             entry in this table for each active 3G connection."
        ::= { fs3GObjects 2 }

    fs3GStatEntry OBJECT-TYPE
        SYNTAX FS3GStatEntry
        MAX-ACCESS not-accessible
        STATUS current
        DESCRIPTION
            "Information about fs3GTunnelTable."
        INDEX { fs3GIPAddr }
        ::= { fs3GStatTable 1 }

    FS3GStatEntry ::=
        SEQUENCE {
            fs3GInOctets
                Counter64,
            fs3GOutOctets
                Counter64,
            fs3GInSpeed
                Counter64,
            fs3GOutSpeed
                Counter64,
            fs3G2IMSI
                DisplayString,
            fs3G2ifIndex
                INTEGER
        }

    fs3GInOctets OBJECT-TYPE
        SYNTAX Counter64
        MAX-ACCESS read-only
        STATUS current
        DESCRIPTION
            "The total number of octets received by this 3G user."
        ::= { fs3GStatEntry 1 }

    fs3GOutOctets OBJECT-TYPE
        SYNTAX Counter64
        MAX-ACCESS read-only
        STATUS current
        DESCRIPTION
            "The total number of octets sent by this 3G user."
        ::= { fs3GStatEntry 2 }

    fs3GInSpeed OBJECT-TYPE
        SYNTAX Counter64
        MAX-ACCESS read-only
        STATUS current
        DESCRIPTION
            "The Speed(bps) of packets received by this 3G user."
        ::= { fs3GStatEntry 3 }

    fs3GOutSpeed OBJECT-TYPE
        SYNTAX Counter64
        MAX-ACCESS read-only
        STATUS current
        DESCRIPTION
            "The Speed(bps) of packets snet by this 3G user."
        ::= { fs3GStatEntry 4 }

    fs3G2IMSI OBJECT-TYPE
        SYNTAX DisplayString
        MAX-ACCESS read-only
        STATUS current
        DESCRIPTION
            "The IMSI  of 3G User."
        ::= { fs3GStatEntry 5 }

    fs3G2ifIndex OBJECT-TYPE
    SYNTAX  INTEGER
    MAX-ACCESS  read-only
    STATUS  current
    DESCRIPTION
            "The Index of 3G Interface."
    ::= { fs3GStatEntry 6 }

-- ===============================================
-- Begin the fs3GTrapObject.
-- ===============================================

    fs3GTrap OBJECT IDENTIFIER ::= { fs3GObjects 3 }

    fs3GNotifications OBJECT IDENTIFIER ::= { fs3GTrap 1 }

    fs3GSignalThreshold NOTIFICATION-TYPE
        OBJECTS {
                fs3GIPAddr,
                fs3GSignalStrength,
                fs3GSignalStrengthPercent,
                fs3GIMSI
        }
        STATUS current
        DESCRIPTION
            "This notification is generated when 3G signal is lower
            than the specific Threshold value."
        ::= { fs3GNotifications 1 }

    fs3GUpLine NOTIFICATION-TYPE
        OBJECTS {
                fs3GIPAddr,
        	fs3gUsername,
        	fs3GIMSI,
                fs3GBackupInfo,
                fs3GSerialNumber,
                fs3GGatewayIPAddr
        }
        STATUS current
        DESCRIPTION
            "This notification is generated when 3G user up line."
        ::= { fs3GNotifications 2 }

    fs3GDownLine NOTIFICATION-TYPE
        OBJECTS {
                fs3GLineDownCause,
		fs3GIPAddr,
                fs3gUsername,
                fs3GIMSI
        	}
        STATUS current
        DESCRIPTION
            "This notification is generated when 3G user down line."
        ::= { fs3GNotifications 3 }

      fs3GChangeAccessPoint NOTIFICATION-TYPE
        OBJECTS {
                fs3GIPAddr,
                fs3GApn,
                fs3gUsername,
                fs3GIMSI
                }
        STATUS current
        DESCRIPTION
            "This notification is generated when 3G change access point."
        ::= { fs3GNotifications 4 }

       fs3GBackupIntfSwitch NOTIFICATION-TYPE
        OBJECTS {
                fs3GIPAddr,
                fs3gUsername,
                fs3GIMSI,
                fs3GSerialNumber,
                fs3GBackupIMSI
                }
        STATUS current
        DESCRIPTION
            "This notification is generated when 3G switch to backup interface
            in double card backup configuration."
        ::= { fs3GNotifications 5 }

       fs3GBaseSationSwitch NOTIFICATION-TYPE
           OBJECTS {
                   fs3GISP,
                   fs3GCellID,
                   fs3GLAC,
                   fs3GBSID,
                   fs3GSID,
                   fs3GNID,
                   fs3GIMSI,
                   fs3GPhoneNumber
                }
        STATUS current
        DESCRIPTION
            "This notification is generated when the access base station changes."
        ::= { fs3GNotifications 6 }

	fs3GTrafficInformation NOTIFICATION-TYPE
        OBJECTS {
                fs3GIPAddr,
		fs3GIMSI,
		fs3GSerialNumber,
		fs3GInOctets,
		fs3GOutOctets
	}
        STATUS current
        DESCRIPTION
            "This notification is used for reporting the traffic information of 3G user regularly. "
        ::= { fs3GNotifications 7 }

-- ===============================================
-- Begin the scalar parameters
-- ===============================================
    fs3GBsNumber OBJECT-TYPE
        SYNTAX Integer32
        MAX-ACCESS  read-only
        STATUS  current
        DESCRIPTION
            "The number of Base Station available on the system"
        ::= { fs3GObjects 4 }

-- ===============================================
-- Begin the table of fs3GBsTable.
-- ===============================================

    fs3GBsTable OBJECT-TYPE
        SYNTAX SEQUENCE OF FS3GBsEntry
        MAX-ACCESS not-accessible
        STATUS current
        DESCRIPTION
            "The Base Station Information."
        ::= { fs3GObjects 5 }

    fs3GBsEntry OBJECT-TYPE
        SYNTAX FS3GBsEntry
        MAX-ACCESS not-accessible
        STATUS current
        DESCRIPTION
            "Information about Base Station."
        INDEX { fs3GBsSN }
        ::= { fs3GBsTable 1 }

    FS3GBsEntry ::=
        SEQUENCE {
            fs3GBsSN
                Integer32,
            fs3GBsISP
           	    INTEGER,
            fs3GBsMode
           	    INTEGER,
            fs3GBsIMSI
                DisplayString,
 	        fs3GBsLAC
                Integer32,
            fs3GBsCellID
                Integer32,
            fs3GBsBSID
                Integer32,
            fs3GBsSID
                Integer32,
            fs3GBsNID
                Integer32,
            fs3GBsRssi
                Integer32,
            fs3GBsBSLONG
                Integer32,
            fs3GBsBSLAT
                Integer32
        }

    fs3GBsSN OBJECT-TYPE
        SYNTAX Integer32
        MAX-ACCESS read-only
        STATUS current
        DESCRIPTION
            "the Sequence Of The Base Station."
        ::= { fs3GBsEntry 1 }

    fs3GBsISP OBJECT-TYPE
        SYNTAX INTEGER
            {
            chinaUnicom(1),
            chinaTelecom(2),
            chinaMobile(3)
            }
        MAX-ACCESS read-only
        STATUS current
        DESCRIPTION
            "the ISP of 3G networsk."
        ::= { fs3GBsEntry 2 }

    fs3GBsMode OBJECT-TYPE
        SYNTAX INTEGER
            {
            sys2GMode(1),
            sys3GMode(2)
            }
        MAX-ACCESS read-only
        STATUS current
        DESCRIPTION
            "the sys mode of 3G networsk."
        ::= { fs3GBsEntry 3 }

     fs3GBsIMSI OBJECT-TYPE
        SYNTAX DisplayString
        MAX-ACCESS read-only
        STATUS current
        DESCRIPTION
            "The IMSI of 3G User."
        ::= { fs3GBsEntry 4 }

    fs3GBsLAC OBJECT-TYPE
        SYNTAX Integer32
        MAX-ACCESS read-only
        STATUS current
        DESCRIPTION
            "The Location Area Code  of 3G User(only used in TD-SCDMA and WCDMA)."
        ::= { fs3GBsEntry 5 }

     fs3GBsCellID OBJECT-TYPE
        SYNTAX Integer32
        MAX-ACCESS read-only
        STATUS current
        DESCRIPTION
            "The access Cell id  of 3G User(only used in TD-SCDMA and WCDMA)."
        ::= { fs3GBsEntry 6 }

    fs3GBsBSID OBJECT-TYPE
        SYNTAX Integer32
        MAX-ACCESS read-only
        STATUS current
        DESCRIPTION
            "The Base Station ID  of 3G User(only used in CDMA2000)."
        ::= { fs3GBsEntry 7 }

     fs3GBsSID OBJECT-TYPE
        SYNTAX Integer32
        MAX-ACCESS read-only
        STATUS current
        DESCRIPTION
            "The System ID  of 3G User(only used in CDMA2000)."
        ::= { fs3GBsEntry 8 }

     fs3GBsNID OBJECT-TYPE
        SYNTAX Integer32
        MAX-ACCESS read-only
        STATUS current
        DESCRIPTION
            "The Network ID  of 3G User(only used in CDMA2000)."
        ::= { fs3GBsEntry 9 }

    fs3GBsRssi OBJECT-TYPE
        SYNTAX Integer32
        MAX-ACCESS read-only
        STATUS current
        DESCRIPTION
            "the strength of the connection."
        ::= { fs3GBsEntry 10 }

	fs3GBsBSLONG OBJECT-TYPE
        SYNTAX Integer32
        MAX-ACCESS read-only
        STATUS current
        DESCRIPTION
            "The longitude of 3G User(only used in CDMA2000)."
        ::= { fs3GBsEntry 11 }

	fs3GBsBSLAT OBJECT-TYPE
        SYNTAX Integer32
        MAX-ACCESS read-only
        STATUS current
        DESCRIPTION
            "The latitude of 3G User(only used in CDMA2000)."
        ::= { fs3GBsEntry 12 }

--  ===============================================
-- Begin the table of fs3GDeviceManagementTable.
-- ===============================================
		-- 1.3.6.1.4.1.52642.1.1.10.2.95.1.6
		fs3GDeviceManagementTable OBJECT-TYPE
			SYNTAX SEQUENCE OF FS3GDeviceManagementEntry
			MAX-ACCESS not-accessible
			STATUS current
			DESCRIPTION
				"The 3G equipment infomation."
			::= { fs3GObjects 6 }

		-- 1.3.6.1.4.1.52642.1.1.10.2.95.1.6.1
		fs3GDeviceManagementEntry OBJECT-TYPE
			SYNTAX FS3GDeviceManagementEntry
			MAX-ACCESS not-accessible
			STATUS current
			DESCRIPTION
				"Information about fs3GDeviceManagementTable."
			INDEX { fs3GRouterSlotNumber }
			::= { fs3GDeviceManagementTable 1 }

            FS3GDeviceManagementEntry ::=
                SEQUENCE {
                    fs3GRouterType
                        DisplayString,
                    fs3GRouterSN
                        DisplayString,
                    fs3GRouterSlotNumber
                        DisplayString,
                    fs3GLineCardType
                        DisplayString,
                    fs3GCardIMSI
                        DisplayString,
                    fs3GModemIMEI
                        DisplayString,
                    fs3GIntfIPAddr
                        IpAddress,
                    fs3GCardPhoneNumber
                        DisplayString,
                    fs3GLineDetected
                        Unsigned32,
                    fs3GLineDetectedResult
                        INTEGER,
                    fs3GLineDetectedMainCause
                        INTEGER,
                    fs3GLineDetectedSubCause
                        INTEGER,
                    fs3GDeviceBackupInfo
                        INTEGER,
                    fs3GRssiStrength
                        Integer32,
      	            fs3GRssiStrengthPercent
                        Integer32,
                    fs3GNetworkISPMode
                        INTEGER,
       	            fs3GNetworkSysMode
                        INTEGER,
                    fs3GNetworkServiceStatus
                        INTEGER,
                    fs3GSIMCardStatus
                        INTEGER,
                    fs3GDailMode
                        INTEGER,
                    fs3GDeviceBackupIMSI
                        DisplayString,
                    fs3GLineDetectedMode
                        INTEGER,
                    fs3GPppUsername
                        DisplayString,
                    fs3GUserApn
                        DisplayString,
                    fs3GModemOnlineStatus
                        INTEGER,
                    fs3GIntfIPAddrType
                        INTEGER,
                    fs3GUserUplineTime
                        TimeStamp,
                    fs3GUserActiveTime
                        Integer32,
                    fs3GSIMRoamingStatus
                        INTEGER,
                    fs3GAcessBSCellID
                        Integer32,
                    fs3GAcessBSLAC
                        Integer32,
                    fs3GAcessBSLONG
                        Integer32,
                    fs3GAcessBSLAT
                        Integer32,
                    fs3GDialOnDemandIfIndex
                        Integer32,
                    fs3GTrafficPreventMode
                        INTEGER,
                    fs3GTrafficPreventIfIndex
                        INTEGER,
                    fs3GTrafficPreventListID
                        INTEGER,
                    fs3GTrafficPreventListName
                        DisplayString,
                    fs3GDeviceModemType
                        INTEGER,
                    fs3GTrafficTrapInterval
                        Integer32,
                    fs3GRssiThreshold
                        Integer32,
                    fs3GTrapFilterMode
                        INTEGER,
                    fs3GISPtimeout
                        Integer32,
                    fs3GEncrypt_type
                        INTEGER,
                    fs3GPassword
                        DisplayString,
                    fs3GNetworkISPName
                        DisplayString
                }

		-- 1.3.6.1.4.1.52642.1.1.10.2.95.1.6.1.1
		fs3GRouterType OBJECT-TYPE
			SYNTAX DisplayString
			MAX-ACCESS read-only
			STATUS current
			DESCRIPTION
				"Equipment tpye of 3G router."
			::= { fs3GDeviceManagementEntry 1 }


		-- 1.3.6.1.4.1.52642.1.1.10.2.95.1.6.1.2
		fs3GRouterSN OBJECT-TYPE
			SYNTAX DisplayString
			MAX-ACCESS read-only
			STATUS current
			DESCRIPTION
				"The serial number of 3G router."
			::= { fs3GDeviceManagementEntry 2 }


		-- 1.3.6.1.4.1.52642.1.1.10.2.95.1.6.1.3
		fs3GRouterSlotNumber OBJECT-TYPE
			SYNTAX DisplayString
			MAX-ACCESS read-only
			STATUS current
			DESCRIPTION
				"The number of the activity slot in 3G router."
			::= { fs3GDeviceManagementEntry 3 }


		-- 1.3.6.1.4.1.52642.1.1.10.2.95.1.6.1.4
		fs3GLineCardType OBJECT-TYPE
			SYNTAX DisplayString
			MAX-ACCESS read-only
			STATUS current
			DESCRIPTION
				"The tpye of 3G router line card."
			::= { fs3GDeviceManagementEntry 4 }


		-- 1.3.6.1.4.1.52642.1.1.10.2.95.1.6.1.5
		fs3GCardIMSI OBJECT-TYPE
			SYNTAX DisplayString
			MAX-ACCESS read-only
			STATUS current
			DESCRIPTION
				"The IMSI  of 3G User."
			::= { fs3GDeviceManagementEntry 5 }


		-- 1.3.6.1.4.1.52642.1.1.10.2.95.1.6.1.6
		fs3GModemIMEI OBJECT-TYPE
			SYNTAX DisplayString
			MAX-ACCESS read-only
			STATUS current
			DESCRIPTION
				"The IMEI number of 3G user."
			::= { fs3GDeviceManagementEntry 6 }


		-- 1.3.6.1.4.1.52642.1.1.10.2.95.1.6.1.7
		fs3GIntfIPAddr OBJECT-TYPE
			SYNTAX IpAddress
			MAX-ACCESS read-only
			STATUS current
			DESCRIPTION
				"The IP Address of 3G interface."
			::= { fs3GDeviceManagementEntry 7 }


		-- 1.3.6.1.4.1.52642.1.1.10.2.95.1.6.1.8
		fs3GCardPhoneNumber OBJECT-TYPE
			SYNTAX DisplayString
			MAX-ACCESS read-only
			STATUS current
			DESCRIPTION
				"The Phone Number of 3G User."
			::= { fs3GDeviceManagementEntry 8 }


		-- 1.3.6.1.4.1.52642.1.1.10.2.95.1.6.1.9
		fs3GLineDetected OBJECT-TYPE
			SYNTAX Unsigned32
			MAX-ACCESS read-write
			STATUS current
			DESCRIPTION
				"The command is used for Detecting 3G line."
			::= { fs3GDeviceManagementEntry 9 }


		-- 1.3.6.1.4.1.52642.1.1.10.2.95.1.6.1.10
		fs3GLineDetectedResult OBJECT-TYPE
			SYNTAX INTEGER
				{
				noRsponse(0),
				pass(1),
				failed(2),
				using(3),
				detecting(4)
				}
			MAX-ACCESS read-only
			STATUS current
			DESCRIPTION
				"The result of 3G line detection."
			::= { fs3GDeviceManagementEntry 10 }


		-- 1.3.6.1.4.1.52642.1.1.10.2.95.1.6.1.11
		fs3GLineDetectedMainCause OBJECT-TYPE
			SYNTAX INTEGER
				{
				noGivenReason(0),
				dialFailed(1),
				pppFailed(2),
				ipsecSetupFailed(3)
				}
			MAX-ACCESS read-only
			STATUS current
			DESCRIPTION
				"The main cause of 3G line detection filed."
			::= { fs3GDeviceManagementEntry 11 }


		-- 1.3.6.1.4.1.52642.1.1.10.2.95.1.6.1.12
		fs3GLineDetectedSubCause OBJECT-TYPE
			SYNTAX INTEGER
				{
				noGivenReason(0),
				simCardInvalid(1),
				aPNInvalid(2),
				powerlower(3),
				userInfoError(4),
				ipsecSetupFailed(5)
				}
			MAX-ACCESS read-only
			STATUS current
			DESCRIPTION
				"The details cause of 3G line detection filed."
			::= { fs3GDeviceManagementEntry 12 }


		-- 1.3.6.1.4.1.52642.1.1.10.2.95.1.6.1.13
		fs3GDeviceBackupInfo OBJECT-TYPE
			SYNTAX INTEGER
				{
				no-backup(0),
				myself(1),
				master(2),
				slave(3)
				}
			MAX-ACCESS read-only
			STATUS current
			DESCRIPTION
				"The backup info of 3G line."
			::= { fs3GDeviceManagementEntry 13 }


		-- 1.3.6.1.4.1.52642.1.1.10.2.95.1.6.1.14
		fs3GRssiStrength OBJECT-TYPE
			SYNTAX Integer32 (-150..0)
			MAX-ACCESS read-only
			STATUS current
			DESCRIPTION
				"The signal strength of the 3G connection for this user."
			::= { fs3GDeviceManagementEntry 14 }


		-- 1.3.6.1.4.1.52642.1.1.10.2.95.1.6.1.15
		fs3GRssiStrengthPercent OBJECT-TYPE
			SYNTAX Integer32 (0..100)
			MAX-ACCESS read-only
			STATUS current
			DESCRIPTION
				"The percent of signal strength of the 3G connection for this user."
			::= { fs3GDeviceManagementEntry 15 }


		-- 1.3.6.1.4.1.52642.1.1.10.2.95.1.6.1.16
		fs3GNetworkISPMode OBJECT-TYPE
			SYNTAX INTEGER
				{
				chinaUnicom(1),
				chinaTelecom(2),
				chinaMobile(3)
				}
			MAX-ACCESS read-only
			STATUS current
			DESCRIPTION
				"the ISP of 3G networsk."
			::= { fs3GDeviceManagementEntry 16 }


		-- 1.3.6.1.4.1.52642.1.1.10.2.95.1.6.1.17
		fs3GNetworkSysMode OBJECT-TYPE
			SYNTAX INTEGER
				{
				noService(0),
				amps(1),
				cdma(2),
				gsmGprs(3),
				hdr(4),
				wcdma(5),
				gps(6),
				gsmCdma(7),
				cdmaHdrHybrid(8),
				td-scdma(15),
				td-1te(100),
				fdd-lte(101)
				}
			MAX-ACCESS read-write
			STATUS current
			DESCRIPTION
				"the system mode of 3G networsk."
			::= { fs3GDeviceManagementEntry 17 }


		-- 1.3.6.1.4.1.52642.1.1.10.2.95.1.6.1.18
		fs3GNetworkServiceStatus OBJECT-TYPE
			SYNTAX INTEGER
				{
				noService(0),
				restricted(1),
				valid(2),
				restrictedRegional(3),
				powerSavingAndDeepSleepState(4)
				}
			MAX-ACCESS read-only
			STATUS current
			DESCRIPTION
				"the sevice status of 3G user."
			::= { fs3GDeviceManagementEntry 18 }


		-- 1.3.6.1.4.1.52642.1.1.10.2.95.1.6.1.19
		fs3GSIMCardStatus OBJECT-TYPE
			SYNTAX INTEGER
				{
				invalidUsimCard(0),
				validUsimCard(1),
				invalidForCS(2),
				invalidForPS(3),
				invalidForCSPS(4),
				noUsimCard(255)
				}
			MAX-ACCESS read-only
			STATUS current
			DESCRIPTION
				"the SIM card status of 3G user."
			::= { fs3GDeviceManagementEntry 19 }


		-- 1.3.6.1.4.1.52642.1.1.10.2.95.1.6.1.20
		fs3GDailMode OBJECT-TYPE
			SYNTAX INTEGER
				{
				dialOnDemand(0),
				autoDail(1)
				}
			MAX-ACCESS read-write
			STATUS current
			DESCRIPTION
				"the dial mode of 3G user."
			::= { fs3GDeviceManagementEntry 20 }


		-- 1.3.6.1.4.1.52642.1.1.10.2.95.1.6.1.21
		fs3GDeviceBackupIMSI OBJECT-TYPE
			SYNTAX DisplayString
			MAX-ACCESS read-only
			STATUS current
			DESCRIPTION
				"The IMSI of 3G backup line."
			::= { fs3GDeviceManagementEntry 21 }


		-- 1.3.6.1.4.1.52642.1.1.10.2.95.1.6.1.22
		fs3GLineDetectedMode OBJECT-TYPE
			SYNTAX INTEGER
				{
				vpdnMode(0),
				ipsecMode(1)
				}
			MAX-ACCESS read-write
			STATUS current
			DESCRIPTION
				"The mode of 3G backup line detected."
			::= { fs3GDeviceManagementEntry 22 }


		-- 1.3.6.1.4.1.52642.1.1.10.2.95.1.6.1.23
		fs3GPppUsername OBJECT-TYPE
			SYNTAX DisplayString
			MAX-ACCESS read-write
			STATUS current
			DESCRIPTION
				"The Username of 3G or 4G User."
			::= { fs3GDeviceManagementEntry 23 }


		-- 1.3.6.1.4.1.52642.1.1.10.2.95.1.6.1.24
		fs3GUserApn OBJECT-TYPE
			SYNTAX DisplayString
			MAX-ACCESS read-write
			STATUS current
			DESCRIPTION
				"The access-point of 3G or 4G User."
			::= { fs3GDeviceManagementEntry 24 }


		-- 1.3.6.1.4.1.52642.1.1.10.2.95.1.6.1.25
		fs3GModemOnlineStatus OBJECT-TYPE
			SYNTAX INTEGER
				{
				minimum-function(0),
				fully-function(1),
				offline-mode(2),
				sim-activate(3),
				sim-deactivate(4)
				}
			MAX-ACCESS read-only
			STATUS current
			DESCRIPTION
				"The status of 3G or 4G user. online or offline."
			::= { fs3GDeviceManagementEntry 25 }


		-- 1.3.6.1.4.1.52642.1.1.10.2.95.1.6.1.26
		fs3GIntfIPAddrType OBJECT-TYPE
			SYNTAX INTEGER
				{
				ipv4Addr(1),
				ipv6Addr(2)
				}
			MAX-ACCESS read-only
			STATUS current
			DESCRIPTION
				"The IP Address type of remote user"
			::= { fs3GDeviceManagementEntry 26 }


		-- 1.3.6.1.4.1.52642.1.1.10.2.95.1.6.1.27
		fs3GUserUplineTime OBJECT-TYPE
			SYNTAX TimeStamp
			MAX-ACCESS read-only
			STATUS current
			DESCRIPTION
				"The upline time of the 3G or 4G user  after system start"
			::= { fs3GDeviceManagementEntry 27 }


		-- 1.3.6.1.4.1.52642.1.1.10.2.95.1.6.1.28
		fs3GUserActiveTime OBJECT-TYPE
			SYNTAX Integer32 (0..2147483647)
			MAX-ACCESS read-only
			STATUS current
			DESCRIPTION
				"The duration of the 3G or 4g connection has been active for one user."
			::= { fs3GDeviceManagementEntry 28 }


		-- 1.3.6.1.4.1.52642.1.1.10.2.95.1.6.1.29
		fs3GSIMRoamingStatus OBJECT-TYPE
			SYNTAX INTEGER
				{
				noRoaming(0),
				roaming(1)
				}
			MAX-ACCESS read-only
			STATUS current
			DESCRIPTION
				"the romain status of 3G user ."
			::= { fs3GDeviceManagementEntry 29 }


		-- 1.3.6.1.4.1.52642.1.1.10.2.95.1.6.1.30
		fs3GAcessBSCellID OBJECT-TYPE
			SYNTAX Integer32 (0..100)
			MAX-ACCESS read-only
			STATUS current
			DESCRIPTION
				"The access Cell id  of 3G or 4g User."
			::= { fs3GDeviceManagementEntry 30 }


		-- 1.3.6.1.4.1.52642.1.1.10.2.95.1.6.1.31
		fs3GAcessBSLAC OBJECT-TYPE
			SYNTAX Integer32 (0..100)
			MAX-ACCESS read-only
			STATUS current
			DESCRIPTION
				"The Location Area Code  of 3G User."
			::= { fs3GDeviceManagementEntry 31 }


		-- 1.3.6.1.4.1.52642.1.1.10.2.95.1.6.1.32
		fs3GAcessBSLONG OBJECT-TYPE
			SYNTAX Integer32
			MAX-ACCESS read-only
			STATUS current
			DESCRIPTION
				"The longitude of 3G User."
			::= { fs3GDeviceManagementEntry 32 }


		-- 1.3.6.1.4.1.52642.1.1.10.2.95.1.6.1.33
		fs3GAcessBSLAT OBJECT-TYPE
			SYNTAX Integer32
			MAX-ACCESS read-only
			STATUS current
			DESCRIPTION
				"The latitude of 3G User."
			::= { fs3GDeviceManagementEntry 33 }


		-- 1.3.6.1.4.1.52642.1.1.10.2.95.1.6.1.34
		fs3GDialOnDemandIfIndex OBJECT-TYPE
			SYNTAX Integer32
			MAX-ACCESS read-only
			STATUS current
			DESCRIPTION
				"The Index of trigger dial-up interface."
			::= { fs3GDeviceManagementEntry 34 }


		-- 1.3.6.1.4.1.52642.1.1.10.2.95.1.6.1.35
		fs3GTrafficPreventMode OBJECT-TYPE
			SYNTAX INTEGER
				{
				disable(0),
				enable(1)
				}
			MAX-ACCESS read-only
			STATUS current
			DESCRIPTION
				"The status of the traffic prevent function appliled currently "
			::= { fs3GDeviceManagementEntry 35 }


		-- 1.3.6.1.4.1.52642.1.1.10.2.95.1.6.1.36
		fs3GTrafficPreventIfIndex OBJECT-TYPE
			SYNTAX INTEGER
			MAX-ACCESS read-only
			STATUS current
			DESCRIPTION
				"The Index of traffic-prevent interface."
			::= { fs3GDeviceManagementEntry 36 }


		-- 1.3.6.1.4.1.52642.1.1.10.2.95.1.6.1.37
		fs3GTrafficPreventListID OBJECT-TYPE
			SYNTAX INTEGER
			MAX-ACCESS read-only
			STATUS current
			DESCRIPTION
				"The Index of traffic-prevent Acl list id."
			::= { fs3GDeviceManagementEntry 37 }


		-- 1.3.6.1.4.1.52642.1.1.10.2.95.1.6.1.38
		fs3GTrafficPreventListName OBJECT-TYPE
			SYNTAX DisplayString
			MAX-ACCESS read-only
			STATUS current
			DESCRIPTION
				"The Index of traffic-prevent Acl list name."
			::= { fs3GDeviceManagementEntry 38 }


		-- 1.3.6.1.4.1.52642.1.1.10.2.95.1.6.1.39
		fs3GDeviceModemType OBJECT-TYPE
			SYNTAX INTEGER
				{
				modem-type-3G(1),
				modem-type-4G(2)
				}
			MAX-ACCESS read-only
			STATUS current
			DESCRIPTION
				"the type of modem used in router."
			::= { fs3GDeviceManagementEntry 39 }

		-- 1.3.6.1.4.1.52642.1.1.10.2.95.1.6.1.40
		fs3GTrafficTrapInterval OBJECT-TYPE
			SYNTAX Integer32 (1..1440)
			MAX-ACCESS read-write
			STATUS current
			DESCRIPTION
				"The interval of traffic-info notification appliled currently."
			::= { fs3GDeviceManagementEntry 40 }

	        -- 1.3.6.1.4.1.52642.1.1.10.2.95.1.6.1.41
		fs3GRssiThreshold OBJECT-TYPE
			SYNTAX Integer32 (-150..0)
			MAX-ACCESS read-write
			STATUS current
			DESCRIPTION
				"the threshold value of rssi notification appliled currently."
			::= { fs3GDeviceManagementEntry 41 }

		-- 1.3.6.1.4.1.52642.1.1.10.2.95.1.6.1.42
		fs3GTrapFilterMode OBJECT-TYPE
			SYNTAX INTEGER
				{
				disable(0),
				enable(1)
				}
			MAX-ACCESS read-write
			STATUS current
			DESCRIPTION
				"The status of the trap filter function appliled currently."
			::= { fs3GDeviceManagementEntry 42 }

	        -- 1.3.6.1.4.1.52642.1.1.10.2.95.1.6.1.43
		fs3GISPtimeout OBJECT-TYPE
			SYNTAX Integer32 (1..36000)
			MAX-ACCESS read-write
			STATUS current
			DESCRIPTION
				"The timeout parameter of trap filter function appliled currently."
			::= { fs3GDeviceManagementEntry 43 }

		-- 1.3.6.1.4.1.52642.1.1.10.2.95.1.6.1.44
		fs3GEncrypt_type OBJECT-TYPE
			SYNTAX INTEGER
				{
				encrypt_none(0),
				encrypt_temp(7)
				}
			MAX-ACCESS read-write
			STATUS current
			DESCRIPTION
				"The Encrypt type appliled currently."
			::= { fs3GDeviceManagementEntry 44 }

		-- 1.3.6.1.4.1.52642.1.1.10.2.95.1.6.1.45
		fs3GPassword OBJECT-TYPE
			SYNTAX DisplayString
			MAX-ACCESS read-write
			STATUS current
			DESCRIPTION
				"The password appliled currently."
			::= { fs3GDeviceManagementEntry 45 }

		-- 1.3.6.1.4.1.52642.1.1.10.2.95.1.6.1.46
		fs3GNetworkISPName OBJECT-TYPE
			SYNTAX DisplayString
			MAX-ACCESS read-only
			STATUS current
			DESCRIPTION
				"The name of Internet Service Provider."
			::= { fs3GDeviceManagementEntry 46 }

--  ===============================================
-- ADD new fs3GTrapObject.
-- ===============================================

    fs3GTrapNew OBJECT IDENTIFIER ::= { fs3GMonitor 2 }

    fs3GNotificationsNew OBJECT IDENTIFIER ::= { fs3GTrapNew 1 }

    fs3GLineDetectedNotification NOTIFICATION-TYPE
        OBJECTS {
                fs3GRouterSN,
	            fs3GCardIMSI,
                fs3GIntfIPAddr,
		        fs3GLineDetected,
        	    fs3GLineDetectedResult,
        	    fs3GLineDetectedMainCause,
		        fs3GLineDetectedSubCause,
		        fs3GDeviceBackupInfo,
		        fs3GRssiStrength,
		        fs3GDeviceBackupIMSI
        	  }
        STATUS current
        DESCRIPTION
            "This notification is generated when user detecting 3g line."
        ::= { fs3GNotificationsNew 1 }


		-- 1.3.6.1.4.1.52642.1.1.10.2.95.2.1.2
		fs3GUserUpLine NOTIFICATION-TYPE
			OBJECTS {
			        fs3GRouterSlotNumber,
			        fs3GCardIMSI,
			        fs3GIntfIPAddr,
			        fs3GTrafficPreventListName,
			        fs3GTrafficPreventListID,
                                fs3GTrafficPreventIfIndex,
                                fs3GTrafficPreventMode,
                                fs3GPppUsername,
                                fs3GRouterSN,
                                fs3GCardPhoneNumber,
                                fs3GDailMode,
                                fs3GDialOnDemandIfIndex,
                                fs3GDeviceModemType
				}
			STATUS current
			DESCRIPTION
				"This notification is generated when 4G user up line."
			::= { fs3GNotificationsNew 2 }


		-- 1.3.6.1.4.1.52642.1.1.10.2.95.2.1.3
		fs3GUserDownLine NOTIFICATION-TYPE
			OBJECTS {
			        fs3GRouterSlotNumber,
			        fs3GCardIMSI,
			        fs3GIntfIPAddr,
			        fs3GTrafficPreventListName,
			        fs3GTrafficPreventListID,
                                fs3GTrafficPreventIfIndex,
                                fs3GTrafficPreventMode,
                                fs3GPppUsername, fs3GRouterSN,
                                fs3GCardPhoneNumber,
                                fs3GDailMode,
                                fs3GDialOnDemandIfIndex,
                                fs3GDeviceModemType }
			STATUS current
			DESCRIPTION
				"This notification is generated when 4G user down line."
			::= { fs3GNotificationsNew 3 }


		-- 1.3.6.1.4.1.52642.1.1.10.2.95.2.1.4
		fs3GRssiNotification NOTIFICATION-TYPE
			OBJECTS {
			        fs3GRouterSlotNumber,
			        fs3GCardIMSI,
			        fs3GRouterSN,
			        fs3GIntfIPAddr,
			        fs3GRssiStrengthPercent,
				fs3GRssiStrength,
				fs3GDeviceModemType
			}
			STATUS current
			DESCRIPTION
				"This notification is generated when 4G signal is lower
				than the specific threshold value."
			::= { fs3GNotificationsNew 4 }


		-- 1.3.6.1.4.1.52642.1.1.10.2.95.2.1.5
		fs3GTrafficInfoNotification NOTIFICATION-TYPE
			OBJECTS {
			        fs3GRouterSlotNumber,
			        fs3GCardIMSI,
			        fs3GRouterSN,
			        fs3GIntfIPAddr,
			        fs3GOutOctets,
				    fs3GInOctets,
				    fs3GDeviceModemType,
				    fs3GLineCardType,
				    fs3GModemIMEI,
				    fs3GCardPhoneNumber,
                    fs3GDeviceBackupInfo,
                    fs3GRssiStrength,
                    fs3GRssiStrengthPercent,
                    fs3GNetworkISPMode,
				    fs3GNetworkSysMode,
				    fs3GSIMCardStatus,
				    fs3GDailMode,
				    fs3GPppUsername,
				    fs3GUserActiveTime,
				    fs3GAcessBSCellID,
				    fs3GAcessBSLAC,
				    fs3GAcessBSLONG,
				    fs3GAcessBSLAT,
				    fs3GInSpeed,
				    fs3GOutSpeed,
				    fs3G2ifIndex,
				    fs3GTrafficTrapInterval,
				    fs3GRssiThreshold,
				    fs3GTrapFilterMode,
				    fs3GISPtimeout,
				    fs3GNetworkISPName
				    }
			STATUS current
			DESCRIPTION
				"This notification is used for reporting the traffic information of 4G user regularly. "
			::= { fs3GNotificationsNew 5 }


		-- 1.3.6.1.4.1.52642.1.1.10.2.95.2.1.6
		fs3GBackupMaster NOTIFICATION-TYPE
			OBJECTS {
			        fs3GRouterSlotNumber,
			        fs3GCardIMSI,
			        fs3GIntfIPAddr,
			        fs3GTrafficPreventListName,
			        fs3GTrafficPreventListID,
				    fs3GTrafficPreventIfIndex,
				    fs3GTrafficPreventMode,
                    fs3GPppUsername,
                    fs3GRouterSN,
                    fs3GCardPhoneNumber,
                    fs3GDailMode,
                    fs3GDialOnDemandIfIndex,
                    fs3GDeviceModemType
                    }
			STATUS current
			DESCRIPTION
				"This notification is generated when 4G is switching to master line."
			::= { fs3GNotificationsNew 6 }


		-- 1.3.6.1.4.1.52642.1.1.10.2.95.2.1.7
		fs3GBackupSlave NOTIFICATION-TYPE
			OBJECTS {
			        fs3GRouterSlotNumber,
			        fs3GCardIMSI,
			        fs3GIntfIPAddr,
			        fs3GTrafficPreventListName,
			        fs3GTrafficPreventListID,
				    fs3GTrafficPreventIfIndex,
				    fs3GTrafficPreventMode,
				    fs3GPppUsername,
				    fs3GRouterSN,
				    fs3GCardPhoneNumber,
				    fs3GDailMode,
				    fs3GDialOnDemandIfIndex,
				    fs3GDeviceModemType }
			STATUS current
			DESCRIPTION
				"This notification is generated when 4G is switching to slave line."
			::= { fs3GNotificationsNew 7 }

	END

--
-- FS-3G-MIB.mib
--
