-- *------------------------------------------------------------------
-- * FS-SYNC-STATS-MIB.mib
-- *   FS Sync Statistics MIB.
-- *
-- * May 2009, yingde tan
-- *
-- * Copyright (c) 2009 by FS.COM Inc..
-- * All rights reserved.
-- *
-- *------------------------------------------------------------------

FS-SYNC-STATS-MIB DEFINITIONS ::= BEGIN

   IMPORTS
      MODULE-IDENTITY,
      OBJECT-TYPE,
      Integer32,
      Counter32
         FROM SNMPv2-SMI
      RowStatus
         FROM SNMPv2-TC
      OBJECT-GROUP,
      MODULE-COMPLIANCE
         FROM SNMPv2-CONF
      fsMgmt
         FROM FS-SMI
      InterfaceIndex
         FROM IF-MIB;

   fsSyncStatsMIB MODULE-IDENTITY
      LAST-UPDATED   "200905201456Z"
      ORGANIZATION   "FS.COM Inc.."
      CONTACT-INFO
                "
                Tel: 400-865-2852

                E-mail: https://www.fs.com/live_chat_service_mail.html"

      DESCRIPTION
         "FS Sync Statistics MIB.

          Acronyms
          The following acronyms are used in this document:

            CRC:        Cyclic Redundancy Check

            HDLC:       High-level Data Link Control

            MIB:        Management Information Base

            MTU:        Maximum Transmission Unit

         "

        REVISION "200905201456Z"
        DESCRIPTION
                "Added module compliance."

      ::= { fsMgmt 51 }

-- +++++++++++++++++++++++++++++++++++++++++++++++++++++++
-- MIB Objects
-- +++++++++++++++++++++++++++++++++++++++++++++++++++++++

fsSyncStatsMibObjects OBJECT IDENTIFIER ::= { fsSyncStatsMIB 1 }

fsStatsSyncGlobal OBJECT IDENTIFIER ::= { fsSyncStatsMibObjects 1 }

fsSyncStatsTable     OBJECT-TYPE
   SYNTAX         SEQUENCE OF FSSyncStatsEntry
   MAX-ACCESS     not-accessible
   STATUS         current
   DESCRIPTION
      "The SYNC interface statistics MIB."
   ::= { fsSyncStatsMibObjects 2 }

fsSyncStatsEntry     OBJECT-TYPE
   SYNTAX         FSSyncStatsEntry
   MAX-ACCESS     not-accessible
   STATUS         current
   DESCRIPTION
      "An entry the fsSyncStatsTable."
   INDEX    { fsSyncStatsSlot, fsSyncStatsConn, fsSyncStatsChannel }
   ::= { fsSyncStatsTable 1 }

FSSyncStatsEntry ::= SEQUENCE {
   fsSyncStatsRowStatus                RowStatus,
   fsSyncStatsSlot                     Integer32,
   fsSyncStatsConn                     Integer32,
   fsSyncStatsChannel                  Integer32,
   fsSyncStatsIfIndex                  InterfaceIndex,
   fsSyncStatsPortState                INTEGER,
   fsSyncStatsRxFrames                 Counter32,
   fsSyncStatsRxOctets                 Counter32,
   fsSyncStatsRxReplenFails            Counter32,
   fsSyncStatsRxClockErrors            Counter32,
   fsSyncStatsRxDpllErrors             Counter32,
   fsSyncStatsRxFrameTooLongErrors     Counter32,
   fsSyncStatsRxFrameOctetAlignErrors  Counter32,
   fsSyncStatsRxAbortErrors            Counter32,
   fsSyncStatsRxCrcErrors              Counter32,
   fsSyncStatsRxRcvrOverrunErrors      Counter32,
   fsSyncStatsTxFrames                 Counter32,
   fsSyncStatsTxOctets                 Counter32,
   fsSyncStatsTxRingFullDropsErrors    Counter32,
   fsSyncStatsTxClockErrors            Counter32,
   fsSyncStatsTxFrameTooLongErrors     Counter32,
   fsSyncStatsTxUnderrunErrors         Counter32
}

fsSyncStatsRowStatus    OBJECT-TYPE
   SYNTAX         RowStatus
   MAX-ACCESS     read-create
   STATUS         current
   DESCRIPTION
      "The status of this row."
   ::= { fsSyncStatsEntry 1 }

fsSyncStatsSlot         OBJECT-TYPE
   SYNTAX         Integer32 (0..2147483647)
   MAX-ACCESS     read-only
   STATUS         current
   DESCRIPTION
      "The physical slot for this Sync port. Part of the index."
   ::= { fsSyncStatsEntry 2 }

fsSyncStatsConn         OBJECT-TYPE
   SYNTAX         Integer32 (0..2147483647)
   MAX-ACCESS     read-only
   STATUS         current
   DESCRIPTION
      "The physical connector for this Sync port. Part of the index."
   ::= { fsSyncStatsEntry 3 }

fsSyncStatsChannel      OBJECT-TYPE
   SYNTAX         Integer32 (0..2147483647)
   MAX-ACCESS     read-only
   STATUS         current
   DESCRIPTION
      "The virtual channel for this Sync port. Part of the index."
   ::= { fsSyncStatsEntry 4 }

fsSyncStatsIfIndex      OBJECT-TYPE
   SYNTAX         InterfaceIndex
   MAX-ACCESS     read-only
   STATUS         current
   DESCRIPTION
      "The IfIndex of this SYNC slot/conn/channel. This is
       configured, but configuration is not available via
       SNMP."
   ::= { fsSyncStatsEntry 5 }

fsSyncStatsPortState OBJECT-TYPE
   SYNTAX         INTEGER {
                     init(1),      -- port is coming up
                     running(2),   -- port has finished initialization
                                   -- and is waiting to transition to
                                   -- data state
                     up(3),        -- ready to pass packets
                     down(4)       -- port is down, unable to pass
                                   -- packets
                  }
   MAX-ACCESS     read-only
   STATUS         current
   DESCRIPTION
      "The current operational state of the interface.
       The init(1) state indicates the port is in the state
       of trying to come up. It will transition to running(2)
       once initialization is complete. up(3) indicates the
       interface is capable of passing packets. down(4) indicates
       the interface is no longer capable of passing packets."
   ::= { fsSyncStatsEntry 6 }

fsSyncStatsRxFrames     OBJECT-TYPE
   SYNTAX         Counter32
   MAX-ACCESS     read-only
   STATUS         current
   DESCRIPTION
      "The number of frames received on this HDLC interface."
   ::= { fsSyncStatsEntry 7 }

fsSyncStatsRxOctets     OBJECT-TYPE
   SYNTAX         Counter32
   MAX-ACCESS     read-only
   STATUS         current
   DESCRIPTION
      "The number of octets received on this HDLC interface."
   ::= { fsSyncStatsEntry 8 }

fsSyncStatsRxReplenFails   OBJECT-TYPE
   SYNTAX         Counter32
   MAX-ACCESS     read-only
   STATUS         current
   DESCRIPTION
      "The number of times receive buffers could not be allocated
      on this HDLC interface."
   ::= { fsSyncStatsEntry 9 }

fsSyncStatsRxClockErrors   OBJECT-TYPE
   SYNTAX         Counter32
   MAX-ACCESS     read-only
   STATUS         current
   DESCRIPTION
      "The number of clock errors on this HDLC interface."
   ::= { fsSyncStatsEntry 10 }

fsSyncStatsRxDpllErrors OBJECT-TYPE
   SYNTAX         Counter32
   MAX-ACCESS     read-only
   STATUS         current
   DESCRIPTION
      "The number of DPLL errors received on this HDLC interface."
   ::= { fsSyncStatsEntry 11 }

fsSyncStatsRxFrameTooLongErrors     OBJECT-TYPE
   SYNTAX         Counter32
   MAX-ACCESS     read-only
   STATUS         current
   DESCRIPTION
      "The number of received long frame errors received on this
       HDLC interface."
   ::= { fsSyncStatsEntry 12 }

fsSyncStatsRxFrameOctetAlignErrors     OBJECT-TYPE
   SYNTAX         Counter32
   MAX-ACCESS     read-only
   STATUS         current
   DESCRIPTION
      "The number of received long frame errors received on
       this HDLC interface."
   ::= { fsSyncStatsEntry 13 }

fsSyncStatsRxAbortErrors      OBJECT-TYPE
   SYNTAX         Counter32
   MAX-ACCESS     read-only
   STATUS         current
   DESCRIPTION
      "The number of received abort errors received on
       this HDLC interface."
   ::= { fsSyncStatsEntry 14 }

fsSyncStatsRxCrcErrors     OBJECT-TYPE
   SYNTAX         Counter32
   MAX-ACCESS     read-only
   STATUS         current
   DESCRIPTION
      "The number of received CRC errors received on
       this HDLC interface."
   ::= { fsSyncStatsEntry 15 }

fsSyncStatsRxRcvrOverrunErrors      OBJECT-TYPE
   SYNTAX         Counter32
   MAX-ACCESS     read-only
   STATUS         current
   DESCRIPTION
      "The number of received CRC errors received on
       this HDLC interface."
   ::= { fsSyncStatsEntry 16 }

fsSyncStatsTxFrames     OBJECT-TYPE
   SYNTAX         Counter32
   MAX-ACCESS     read-only
   STATUS         current
   DESCRIPTION
      "The number of transmitted frames on this HDLC interface."
   ::= { fsSyncStatsEntry 17 }

fsSyncStatsTxOctets     OBJECT-TYPE
   SYNTAX         Counter32
   MAX-ACCESS     read-only
   STATUS         current
   DESCRIPTION
      "The number of transmitted frames on this HDLC interface."
   ::= { fsSyncStatsEntry 18 }

fsSyncStatsTxRingFullDropsErrors    OBJECT-TYPE
   SYNTAX         Counter32
   MAX-ACCESS     read-only
   STATUS         current
   DESCRIPTION
      "The number of frames dropped on this HDLC interface because
       the transmit ring was full."
   ::= { fsSyncStatsEntry 19 }

fsSyncStatsTxClockErrors      OBJECT-TYPE
   SYNTAX         Counter32
   MAX-ACCESS     read-only
   STATUS         current
   DESCRIPTION
      "The number of transmit clock errors on this HDLC interface."
   ::= { fsSyncStatsEntry 20 }

fsSyncStatsTxFrameTooLongErrors     OBJECT-TYPE
   SYNTAX         Counter32
   MAX-ACCESS     read-only
   STATUS         current
   DESCRIPTION
      "The number of frames dropped this HDLC interface because they
       were long than the interface's MTU."
   ::= { fsSyncStatsEntry 21 }

fsSyncStatsTxUnderrunErrors      OBJECT-TYPE
   SYNTAX         Counter32
   MAX-ACCESS     read-only
   STATUS         current
   DESCRIPTION
      "The number of transmitter underruns on this HDLC interface."
   ::= { fsSyncStatsEntry 22 }

fsSyncStatsMibConformance OBJECT IDENTIFIER ::= { fsSyncStatsMIB 2 }

fsSyncStatsMibCompliances OBJECT IDENTIFIER ::= { fsSyncStatsMibConformance 1 }
fsSyncStatsMibGroups OBJECT IDENTIFIER ::= { fsSyncStatsMibConformance 2 }

fsSyncStatsMibCompliance MODULE-COMPLIANCE
   STATUS         current
   DESCRIPTION
      "The compliance statement for agents which
       implement the FS Sync Statistics MIB."
   MODULE
   MANDATORY-GROUPS {
      fsSyncStatsGroup
   }
   ::= { fsSyncStatsMibCompliances 1 }

fsSyncStatsGroup OBJECT-GROUP
   OBJECTS
   {
      fsSyncStatsRowStatus,
      fsSyncStatsSlot,
      fsSyncStatsConn,
      fsSyncStatsChannel,
      fsSyncStatsIfIndex,
      fsSyncStatsPortState,
      fsSyncStatsRxFrames,
      fsSyncStatsRxOctets,
      fsSyncStatsRxReplenFails,
      fsSyncStatsRxClockErrors,
      fsSyncStatsRxDpllErrors,
      fsSyncStatsRxFrameTooLongErrors,
      fsSyncStatsRxFrameOctetAlignErrors,
      fsSyncStatsRxAbortErrors,
      fsSyncStatsRxCrcErrors,
      fsSyncStatsRxRcvrOverrunErrors,
      fsSyncStatsTxFrames,
      fsSyncStatsTxOctets,
      fsSyncStatsTxRingFullDropsErrors,
      fsSyncStatsTxClockErrors,
      fsSyncStatsTxFrameTooLongErrors,
      fsSyncStatsTxUnderrunErrors
   }
   STATUS   current
   DESCRIPTION
          "The objects for SYNC configuration."
   ::= { fsSyncStatsMibGroups 1 }

END
