-- *****************************************************************
-- FS-SYSTEM-MIB.mib:  FS System MIB file
--
-- Feb 2012, HuangY
--
-- Copyright (c) 2012 by FS.COM Inc..
-- All rights reserved.
--
-- *****************************************************************
--

FS-TEMP-FAN-MIB DEFINITIONS ::= BEGIN

IMPORTS
        MODULE-IDENTITY,
        OBJECT-TYPE,
        NOTIFICATION-TYPE,
        Integer32
               FROM SNMPv2-SMI
        MODULE-COMPLIANCE
               FROM SNMPv2-CONF
        fsMgmt
                FROM FS-SMI
        fsSystemTemperatureCurrent
                FROM FS-SYSTEM-MIB;

fsTempFanMIB MODULE-IDENTITY
        LAST-UPDATED "200203200000Z"
        ORGANIZATION "FS.COM Inc.."
        CONTACT-INFO
                "
                Tel: 400-865-2852

                E-mail: https://www.fs.com/live_chat_service_mail.html"
        DESCRIPTION
                "This module defines fs system mibs."
        REVISION      "200203200000Z"
        DESCRIPTION
                "Initial version of this MIB module."
        ::= { fsMgmt 109}

fsTempFanTraps OBJECT IDENTIFIER ::= { fsTempFanMIB 1 }

--Temperature Too High Trap
temperatureTooHighTrap NOTIFICATION-TYPE
        OBJECTS   {fsSystemTemperatureCurrent}
        STATUS     current
        DESCRIPTION
                "Temperature Too High warning and report the current temperature."
        ::= { fsTempFanTraps 1 }

--Temperature Too High Recover Trap
temperTooHighRecovTrap NOTIFICATION-TYPE
        OBJECTS   {fsSystemTemperatureCurrent}
        STATUS     current
        DESCRIPTION
                "Clear the warning of temperature too high and report the current temperature."
        ::= { fsTempFanTraps 2 }

--Fan Failure Trap
fanFailure NOTIFICATION-TYPE
        STATUS     current
        DESCRIPTION
                "Fan stopped warning."
        ::= { fsTempFanTraps 3 }

END
