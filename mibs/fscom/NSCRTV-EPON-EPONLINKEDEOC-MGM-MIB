NSCRTV-EPON-EPONLINKEDEOC-MGM-MIB DEFINITIONS ::= BEGIN

IMPORTS
    MODULE-IDENTITY, OBJECT-TYPE,Counter32, Unsigned32, TimeTicks
        FROM SNMPv2-SMI
    DateAndTime, MacAddress, TimeStamp, RowStatus, TruthValue, DisplayString, TEXTUAL-CONVENTION
        FROM SNMPv2-TC
    EponDeviceIndex, EponCardIndex, EponPortIndex, EponAlarmCode, EponAlarmInstance, EponSeverityType,
    AutoNegotiationTechAbility, TAddress, EponStats15MinRecordType, EponStats24HourRecordType, EponStatsThresholdType
		FROM NSCRTV-EPONEOC-EPON-MIB
    eponLinkedEoCManagementObjects
        FROM NSCRTV-EPONEOC-EPON-MIB;

--------------------------------------------------------------------------------
--  eponLinkedEoCManagementObjects[EPON/EoC网管互通管理项](1.3.6.1.4.1.17409.2.3.11)
--------------------------------------------------------------------------------

    eocDevInfoTable OBJECT-TYPE
      SYNTAX SEQUENCE OF EocDevInfoEntry
      MAX-ACCESS not-accessible
      STATUS current
      DESCRIPTION
        "EoC设备信息表"
      ::= { eponLinkedEoCManagementObjects 1 }

    eocDevInfoEntry OBJECT-TYPE
      SYNTAX EocDevInfoEntry
      MAX-ACCESS not-accessible
      STATUS current
      DESCRIPTION     " "
      INDEX { eDeviceIndex, eCardIndex, ePortIndex }
      ::= { eocDevInfoTable 1 }
    EocDevInfoEntry ::=
      SEQUENCE {
        eDeviceIndex
          EponDeviceIndex,
        eCardIndex
          EponCardIndex,
        ePortIndex
          EponPortIndex,
        eocDeviceTechnologyProject
          OCTET STRING,
        eocDeviceVendorName
          OCTET STRING,
        eocDeviceProductType
          OCTET STRING,
        eocDeviceSoftwareVersion
          OCTET STRING,
        eocDeviceHardwareVersion
          OCTET STRING,
        eocSeriesNumber
          OCTET STRING,
        eocDeviceIpAddress
          IpAddress,
        eocDeviceMacAddress
          MacAddress,
        eocDeviceMibVersion
          OCTET STRING,
        eocDeviceSnmpVersion
          INTEGER,
        eocDeviceMngVlan
          INTEGER,
        eocDeviceGateWay
          IpAddress,
        eocDeviceSubnetMask
          IpAddress,
        eocDeviceReadCommunity
          DisplayString,
        eocDeviceWriteCommunity
          DisplayString
       }

    eDeviceIndex OBJECT-TYPE
      SYNTAX EponDeviceIndex
      MAX-ACCESS not-accessible
      STATUS current
      DESCRIPTION
        "
        板卡索引号"
      ::= { eocDevInfoEntry 1 }

    eCardIndex OBJECT-TYPE
      SYNTAX EponCardIndex
      MAX-ACCESS not-accessible
      STATUS current
      DESCRIPTION
        "
        板卡索引号"
      ::= { eocDevInfoEntry 2 }

    ePortIndex  OBJECT-TYPE
      SYNTAX EponPortIndex
      MAX-ACCESS not-accessible
      STATUS current
      DESCRIPTION
        "
        uni端口索引号"
      ::= { eocDevInfoEntry 3 }

    eocDeviceTechnologyProject OBJECT-TYPE
      SYNTAX OCTET STRING (SIZE (0..16))
      MAX-ACCESS read-only
      STATUS current
      DESCRIPTION
        "
        EoC设备技术方案"
      ::= { eocDevInfoEntry 4 }

    eocDeviceVendorName OBJECT-TYPE
      SYNTAX OCTET STRING (SIZE (0..64))
      MAX-ACCESS read-only
      STATUS current
      DESCRIPTION
        "
        EoC设备生产商名称"
      ::= { eocDevInfoEntry 5 }

    eocDeviceProductType OBJECT-TYPE
      SYNTAX OCTET STRING (SIZE (0..64))
      MAX-ACCESS read-only
      STATUS current
      DESCRIPTION
        "
        EoC设备产品类型"
      ::= { eocDevInfoEntry 6 }

    eocDeviceSoftwareVersion OBJECT-TYPE
      SYNTAX OCTET STRING (SIZE (0..64))
      MAX-ACCESS read-only
      STATUS current
      DESCRIPTION
        "
        EoC设备软件版本"
      ::= { eocDevInfoEntry 7 }

    eocDeviceHardwareVersion OBJECT-TYPE
      SYNTAX OCTET STRING (SIZE (0..64))
      MAX-ACCESS read-only
      STATUS current
      DESCRIPTION
        "
        EoC设备硬件版本"
      ::= { eocDevInfoEntry 8 }

    eocSeriesNumber OBJECT-TYPE
      SYNTAX OCTET STRING (SIZE (0..64))
      MAX-ACCESS read-only
      STATUS current
      DESCRIPTION
        "
        EoC局端设备SN"
      ::= { eocDevInfoEntry 9 }

    eocDeviceIpAddress OBJECT-TYPE
      SYNTAX IpAddress
      MAX-ACCESS read-write
      STATUS current
      DESCRIPTION
        "
        EoC设备IP地址"
      ::= { eocDevInfoEntry 10 }

    eocDeviceMacAddress OBJECT-TYPE
      SYNTAX MacAddress
      MAX-ACCESS read-only
      STATUS current
      DESCRIPTION
        "
        EoC设备Mac地址"
      ::= { eocDevInfoEntry 11 }

    eocDeviceMibVersion OBJECT-TYPE
      SYNTAX OCTET STRING (SIZE (0..16))
      MAX-ACCESS read-only
      STATUS current
      DESCRIPTION
        "
        EoC设备 MIB version"
      ::= { eocDevInfoEntry 12 }

    eocDeviceSnmpVersion OBJECT-TYPE
      SYNTAX INTEGER
        { v1(1),v2c(2),v3(3)  }
      MAX-ACCESS read-only
      STATUS current
      DESCRIPTION
        "
        EoC设备支持的SNMP协议版本"
      ::= { eocDevInfoEntry 13 }

    eocDeviceMngVlan OBJECT-TYPE
      SYNTAX INTEGER
      MAX-ACCESS read-write
      STATUS current
      DESCRIPTION
        "
        EoC设备管理VLAN"
      ::= { eocDevInfoEntry 14 }

    eocDeviceGateWay OBJECT-TYPE
      SYNTAX IpAddress
      MAX-ACCESS read-write
      STATUS current
      DESCRIPTION
        "
        EoC设备网关地址"
      ::= { eocDevInfoEntry 15 }

    eocDeviceSubnetMask OBJECT-TYPE
      SYNTAX IpAddress
      MAX-ACCESS read-write
      STATUS current
      DESCRIPTION
        "
        EOC设备子网掩码"
      ::= { eocDevInfoEntry 16 }

    eocDeviceReadCommunity OBJECT-TYPE
      SYNTAX DisplayString
      MAX-ACCESS read-write
      STATUS current
      DESCRIPTION
        "
        EOC设备读共同体"
      ::= { eocDevInfoEntry 17 }

    eocDeviceWriteCommunity OBJECT-TYPE
      SYNTAX DisplayString
      MAX-ACCESS read-write
      STATUS current
      DESCRIPTION
        "
        EOC设备写共同体"
      ::= { eocDevInfoEntry 18 }

--
-- END of NSCRTV-EPON-EPONLINKEDEOC-MGM-MIB
--

END
