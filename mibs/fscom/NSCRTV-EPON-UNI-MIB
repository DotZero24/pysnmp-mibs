NSCRTV-EPON-UNI-MIB DEFINITIONS ::= BEGIN

IMPORTS
    MODULE-IDENTITY, OBJECT-TYPE, Counter32, Unsigned32, TimeTicks
        FROM SNMPv2-SMI
    DateAndTime, MacAddress, TimeStamp, RowStatus, TruthValue, DisplayString, TEXTUAL-CONVENTION
        FROM SNMPv2-TC
    EponDeviceIndex, EponCardIndex, EponPortIndex, EponAlarmCode, EponAlarmInstance, EponSeverityType,
    AutoNegotiationTechAbility, TAddress, EponStats15MinRecordType, EponStats24HourRecordType, EponStatsThresholdType
		FROM NSCRTV-EPONEOC-EPON-MIB
    uniObjects
        FROM NSCRTV-EPONEOC-EPON-MIB;

--------------------------------------------------------------------------------
--  uniObjects[UNI用户端口属性管理项](1.3.6.1.4.1.17409.2.3.5)
--------------------------------------------------------------------------------

 uniAttributeTable  OBJECT-TYPE
        SYNTAX      SEQUENCE OF UniAttributeEntry
        MAX-ACCESS  not-accessible
        STATUS      current
        DESCRIPTION
            "A list of uniAttributeTable entries."
        ::= {uniObjects 1 }

    uniAttributeEntry  OBJECT-TYPE
        SYNTAX      UniAttributeEntry
        MAX-ACCESS  not-accessible
        STATUS      current
        DESCRIPTION
            "The uniAttributeEntry Information"
        INDEX       { uniAttributeDeviceIndex, uniAttributeCardIndex,uniAttributePortIndex }
        ::={uniAttributeTable 1 }

    UniAttributeEntry ::= SEQUENCE {
        uniAttributeDeviceIndex              EponDeviceIndex,
        uniAttributeCardIndex                EponCardIndex,
        uniAttributePortIndex                EponPortIndex,
        uniAdminStatus              INTEGER,
        uniOperationStatus          INTEGER,
        uniAutoNegotiationEnable    TruthValue,
        uniAutoNegotiationLocalTechAbility      AutoNegotiationTechAbility,
        uniAutoNegotiationRestart   INTEGER
      }

    uniAttributeDeviceIndex  OBJECT-TYPE
        SYNTAX      EponDeviceIndex
        MAX-ACCESS  not-accessible
        STATUS      current
        DESCRIPTION
            "Device Index

            For OLT, set to corresponding ONU ID
            For ONU, set to 0
            "
        ::= {uniAttributeEntry 1 }

    uniAttributeCardIndex  OBJECT-TYPE
        SYNTAX      EponCardIndex
        MAX-ACCESS  not-accessible
        STATUS      current
        DESCRIPTION
            "Card Index
            The value of this cardIndex depends on onuType.
      fixed(1)        - set to 0, to indicate slot num is meaningless.
      chassisBased(2) - MUST NOT be zero
            "
        ::= {uniAttributeEntry 2 }

    uniAttributePortIndex  OBJECT-TYPE
        SYNTAX      EponPortIndex
        MAX-ACCESS  not-accessible
        STATUS      current
        DESCRIPTION
            "Port Index"
        ::= {uniAttributeEntry 3 }

    uniAdminStatus  OBJECT-TYPE
        SYNTAX      INTEGER {
            up(1),
            down(2),
            testing(3)
            }
        MAX-ACCESS  read-write
        STATUS      current
        DESCRIPTION
            "Admin Status"
        ::= {uniAttributeEntry 4 }

    uniOperationStatus  OBJECT-TYPE
        SYNTAX  INTEGER {
            up(1),
            down(2),
            testing(3)
            }
        MAX-ACCESS  read-only
        STATUS      current
        DESCRIPTION
            "Operation Status"
        ::= {uniAttributeEntry 5 }

    uniAutoNegotiationEnable  OBJECT-TYPE
        SYNTAX      TruthValue
        MAX-ACCESS  read-write
        STATUS      current
        DESCRIPTION
            "Whether or not to enable auto negotiation on the uni port"
        ::= {uniAttributeEntry 6 }

    uniAutoNegotiationLocalTechAbility  OBJECT-TYPE
        SYNTAX      AutoNegotiationTechAbility
        MAX-ACCESS  read-only
        STATUS      current
        DESCRIPTION
            "This indicates the technology ability of the local device"
        ::= {uniAttributeEntry 7 }

    uniAutoNegotiationRestart OBJECT-TYPE
        SYNTAX      INTEGER {
            restart(1)
            }
        MAX-ACCESS  read-write
        STATUS      current
        DESCRIPTION
            "Restart the autonegotiation"
        ::= {uniAttributeEntry 9 }

   uniMacAddressManagement OBJECT-IDENTITY
    STATUS current
    DESCRIPTION
      ""
    ::= { uniObjects 2 }

    uniMacAddressManagementNode  OBJECT-IDENTITY
        STATUS      current
        DESCRIPTION
            " MacAddressManagement global parameters. "
        ::= { uniMacAddressManagement 1 }

    uniMacAddrAgingTime   OBJECT-TYPE
        SYNTAX      INTEGER
        UNITS   "Seconds"
        MAX-ACCESS  read-write
        STATUS      current
        DESCRIPTION
            "Mac Address Table Aging Time"
        ::= { uniMacAddressManagementNode 1 }

    uniMacAddrClear OBJECT-TYPE
        SYNTAX      INTEGER { allDynamic(1) }
        MAX-ACCESS  read-write
        STATUS      current
        DESCRIPTION
            "Mac Address Table Clear"
        ::= { uniMacAddressManagementNode 2 }


    uniMacAddressTable OBJECT-TYPE
        SYNTAX  SEQUENCE OF UniMacAddressEntry
        MAX-ACCESS  not-accessible
        STATUS      current
        DESCRIPTION
            "A list of MacAddress entries."
        ::= { uniMacAddressManagement 2 }

    uniMacAddressEntry OBJECT-TYPE
        SYNTAX      UniMacAddressEntry
        MAX-ACCESS  not-accessible
        STATUS      current
        DESCRIPTION
            "The Mac Address Information"
        INDEX   { uniMacAddrIndex,  uniMacAddrVlanIdIndex }
        ::= { uniMacAddressTable 1 }

    UniMacAddressEntry ::=
        SEQUENCE {
        uniMacAddrIndex        MacAddress,
        uniMacAddrVlanIdIndex  INTEGER,
        uniMacAddrType         INTEGER,
        uniMacAddrPortId       OCTET STRING,
        uniMacAddrRowStatus    RowStatus
        }

    uniMacAddrIndex   OBJECT-TYPE
        SYNTAX      MacAddress
        MAX-ACCESS  not-accessible
        STATUS      current
        DESCRIPTION
            "Mac Address Index"
        ::= { uniMacAddressEntry 1 }

    uniMacAddrVlanIdIndex   OBJECT-TYPE
        SYNTAX      INTEGER
        MAX-ACCESS  not-accessible
        STATUS      current
        DESCRIPTION
            "Mac Address Vlan Id Index"
        ::= { uniMacAddressEntry 2 }

    uniMacAddrType  OBJECT-TYPE
        SYNTAX  INTEGER {
            static(1),
            dynamic(2),
            other(3)}
        MAX-ACCESS  read-create
        STATUS    current
        DESCRIPTION
            "Mac Address Type"
        ::= { uniMacAddressEntry 3 }

    uniMacAddrPortId OBJECT-TYPE
        SYNTAX       OCTET STRING (SIZE (2))
        MAX-ACCESS   read-create
        STATUS       current
        DESCRIPTION
            "Mac Address Port Id
            The first octet is slot ID, the second octet is port ID.
            If the device is fixed (not modulized), set slot ID to 0.
            Note that, slot here shall follow the last byte definition of
            EponCardIndex to indicate the main-slot and sub-slot index.
            For example, for modulized port 10/3, set to 0x0A 03
            For fix box port 3, set to 0x00 03
            "
        ::=  {  uniMacAddressEntry 4 }

    uniMacAddrRowStatus  OBJECT-TYPE
        SYNTAX      RowStatus
        MAX-ACCESS  read-create
        STATUS      current
        DESCRIPTION
            "delete,create. Update is not supported"
        ::= { uniMacAddressEntry 5 }

    uniTrunkManagement  OBJECT-IDENTITY
    STATUS current
    DESCRIPTION
      ""
    ::= { uniObjects 3 }


    uniTrunkGroupConfigTable  OBJECT-TYPE
        SYNTAX      SEQUENCE OF UniTrunkGroupConfigEntry
        MAX-ACCESS  not-accessible
        STATUS      current
        DESCRIPTION
            "A list of uniTrunkGroupConfigTable entries."
        ::= {uniTrunkManagement 1 }

    uniTrunkGroupConfigEntry  OBJECT-TYPE
        SYNTAX      UniTrunkGroupConfigEntry
        MAX-ACCESS  not-accessible
        STATUS      current
        DESCRIPTION
            "The uniTrunk Group Config Entry Information"
        INDEX       { uniTrunkGroupConfigIndex }
        ::={uniTrunkGroupConfigTable 1 }
    UniTrunkGroupConfigEntry ::= SEQUENCE {
        uniTrunkGroupConfigIndex      INTEGER,
        uniTrunkGroupConfigName       DisplayString,
        uniTrunkGroupConfigMember     OCTET STRING,
        uniTrunkGroupConfigPolicy     INTEGER,
        uniTrunkGroupConfigRowstatus  RowStatus
      }

    uniTrunkGroupConfigIndex  OBJECT-TYPE
        SYNTAX      INTEGER
        MAX-ACCESS  not-accessible
        STATUS      current
        DESCRIPTION
            "Trunk Group Config Index"
        ::= {uniTrunkGroupConfigEntry 1 }

    uniTrunkGroupConfigName  OBJECT-TYPE
        SYNTAX      DisplayString
        MAX-ACCESS  read-create
        STATUS      current
        DESCRIPTION
            "Trunk Group Config Name"
        ::= {uniTrunkGroupConfigEntry 2 }

    uniTrunkGroupConfigMember  OBJECT-TYPE
        SYNTAX      OCTET STRING
        MAX-ACCESS  read-create
        STATUS      current
        DESCRIPTION
            "Trunk Group Config Member.
      It is presented by member port list. Each member port is identified
      by 2-byte format, One for slot ID, the last for port ID. The actual
      length of this string depends of the number of member ports in the
      trunk group. If the ONU is fixed (not modulized), set slot ID to 0,
      the NMS could ignore the slot info.
      Note that, slot here shall follow the last byte definition of
      EponCardIndex to indicate the main-slot and sub-slot index.
      The relationship is:
      Length of the string = 2 * (NUM of member ports)
      For example, if port 1/2 and 3/4 is the member ports of the
      trunk, then the object is presented as:
      01 02 03 04
            "
        ::= {uniTrunkGroupConfigEntry 3 }

    uniTrunkGroupConfigPolicy  OBJECT-TYPE
        SYNTAX      INTEGER
            {
      srcMac(1),
      destMac(2),
      srcMacNDestMac(3),
      srcIp(4),
      destIp(5),
      srcIpNDestIp(6)
             }
        MAX-ACCESS  read-create
        STATUS      current
        DESCRIPTION
            "Trunk Group Config Policy"
        ::= {uniTrunkGroupConfigEntry 4 }

    uniTrunkGroupConfigRowstatus  OBJECT-TYPE
        SYNTAX      RowStatus
        MAX-ACCESS  read-create
        STATUS      current
        DESCRIPTION
            "Trunk Group Config Rowstatus"
        ::= {uniTrunkGroupConfigEntry 5 }

    uniTrunkGroupTable  OBJECT-TYPE
        SYNTAX      SEQUENCE OF UniTrunkGroupEntry
        MAX-ACCESS  not-accessible
        STATUS      current
        DESCRIPTION
            "a list of uniTrunkGroupConfigTable entries."
        ::= {uniTrunkManagement 2 }

    uniTrunkGroupEntry  OBJECT-TYPE
        SYNTAX      UniTrunkGroupEntry
        MAX-ACCESS  not-accessible
        STATUS      current
        DESCRIPTION
            "Trunk Group Entry"
        INDEX       { uniTrunkGroupIndex }
        ::={uniTrunkGroupTable 1 }

    UniTrunkGroupEntry ::= SEQUENCE {
        uniTrunkGroupIndex            INTEGER,
        uniTrunkGroupOperationStatus  INTEGER,
        uniTrunkGroupActualSpeed      INTEGER,
        uniTrunkGroupAdminStatus      INTEGER
      }

    uniTrunkGroupIndex  OBJECT-TYPE
        SYNTAX      INTEGER
        MAX-ACCESS  not-accessible
        STATUS      current
        DESCRIPTION
            "Trunk Group Index"
        ::= {uniTrunkGroupEntry 1 }

    uniTrunkGroupOperationStatus  OBJECT-TYPE
        SYNTAX  INTEGER {
            up(1),
            down(2),
            testing(3)
            }
        MAX-ACCESS  read-only
        STATUS      current
        DESCRIPTION
            "Trunk Group Operation Status"
        ::= {uniTrunkGroupEntry 2 }

    uniTrunkGroupActualSpeed  OBJECT-TYPE
        SYNTAX      INTEGER
        UNITS   "Mbps"
        MAX-ACCESS  read-only
        STATUS      current
        DESCRIPTION
            "Trunk Group Actual Speed.
            The speed is the aggregated rates of all operational UP member
            ports of the trunk.
            For example, 4 member ports of the trunk, two are UP, each is 1000M
            then the SUN is 2000M. As a result, the return of the MIB shall be
            2000Mbps"
        ::= {uniTrunkGroupEntry 3 }


    uniTrunkGroupAdminStatus  OBJECT-TYPE
        SYNTAX      INTEGER {
            up(1),
            down(2),
            testing(3)
            }
        MAX-ACCESS  read-write
        STATUS      current
        DESCRIPTION
            "Trunk Group AdminStatus"
        ::= {uniTrunkGroupEntry 4 }


    uniPortRateLimitTable OBJECT-TYPE
        SYNTAX      SEQUENCE OF UniPortRateLimitEntry
        MAX-ACCESS  not-accessible
        STATUS      current
        DESCRIPTION
            "A list of PortRateLimit entries."
        ::= { uniObjects 4 }

    uniPortRateLimitEntry OBJECT-TYPE
        SYNTAX      UniPortRateLimitEntry
        MAX-ACCESS  not-accessible
        STATUS      current
        DESCRIPTION
            "The Port Rate Limit Information"
        INDEX       { uniPortRateLimitDeviceIndex, uniPortRateLimitCardIndex, uniPortRateLimitPortIndex }
        ::= { uniPortRateLimitTable 1 }

    UniPortRateLimitEntry ::=
        SEQUENCE {
            uniPortRateLimitDeviceIndex  EponDeviceIndex,
            uniPortRateLimitCardIndex    EponCardIndex,
            uniPortRateLimitPortIndex    EponPortIndex,
            uniPortInCIR    INTEGER,
            uniPortInCBS    INTEGER,
            uniPortInEBS    INTEGER,
            uniPortOutCIR   INTEGER,
            uniPortOutPIR   INTEGER,
            uniPortInRateLimitEnable  TruthValue,
            uniPortOutRateLimitEnable TruthValue
            }
    uniPortRateLimitDeviceIndex OBJECT-TYPE
        SYNTAX      EponDeviceIndex
        MAX-ACCESS  not-accessible
        STATUS      current
        DESCRIPTION
            "device Index

            For OLT, set to corresponding ONU ID
            For ONU, set to 0
            "
        ::= { uniPortRateLimitEntry 1 }

    uniPortRateLimitCardIndex OBJECT-TYPE
        SYNTAX      EponCardIndex
        MAX-ACCESS  not-accessible
        STATUS      current
        DESCRIPTION
            "card Index
            The value of this cardIndex depends on onuType.
      fixed(1)        - set to 0, to indicate slot num is meaningless.
      chassisBased(2) - MUST NOT be zero
            "
        ::= { uniPortRateLimitEntry 2 }

    uniPortRateLimitPortIndex OBJECT-TYPE
        SYNTAX      EponPortIndex
        MAX-ACCESS  not-accessible
        STATUS      current
        DESCRIPTION
            "port Index"
        ::= { uniPortRateLimitEntry 3 }

    uniPortInCIR OBJECT-TYPE
        SYNTAX      INTEGER
        UNITS       "kbps"
        MAX-ACCESS  read-write
        STATUS      current
        DESCRIPTION
            "Committed Information Rate(CIR) in kbps."
        ::= { uniPortRateLimitEntry 4 }

    uniPortInCBS OBJECT-TYPE
        SYNTAX      INTEGER
        UNITS   "Kbytes"
        MAX-ACCESS  read-write
        STATUS      current
        DESCRIPTION
            "Committed Burst Rate(CBS) in kbyte."
        ::= { uniPortRateLimitEntry 5 }

    uniPortInEBS OBJECT-TYPE
        SYNTAX      INTEGER
        UNITS   "Kbytes"
        MAX-ACCESS  read-write
        STATUS      current
        DESCRIPTION
            "ebs in kbytes."
        ::= { uniPortRateLimitEntry 6 }

    uniPortOutCIR OBJECT-TYPE
        SYNTAX      INTEGER
        UNITS       "Kbps"
        MAX-ACCESS  read-write
        STATUS      current
        DESCRIPTION
            "Committed Information Rate(CIR) in kbps."
        ::= { uniPortRateLimitEntry 7 }

    uniPortOutPIR OBJECT-TYPE
        SYNTAX      INTEGER
        UNITS   "Kbps"
        MAX-ACCESS  read-write
        STATUS      current
        DESCRIPTION
            "PIR in kbps."
        ::= { uniPortRateLimitEntry 8 }

    uniPortInRateLimitEnable OBJECT-TYPE
        SYNTAX      TruthValue
        MAX-ACCESS  read-write
        STATUS      current
        DESCRIPTION
            "Whether or not to enable or disable ingress rate limit for the UNI."
        ::= { uniPortRateLimitEntry 9 }

    uniPortOutRateLimitEnable OBJECT-TYPE
        SYNTAX      TruthValue
        MAX-ACCESS  read-write
        STATUS      current
        DESCRIPTION
            "Whether or not to enable or disable egress rate limit for the UNI."
        ::= { uniPortRateLimitEntry 10 }

    uniMirrorTable  OBJECT-TYPE
        SYNTAX      SEQUENCE OF UniMirrorEntry
        MAX-ACCESS  not-accessible
        STATUS      current
        DESCRIPTION
            "a list of uniMirrorTable entries."
        ::= {uniObjects 5 }

    uniMirrorEntry  OBJECT-TYPE
        SYNTAX      UniMirrorEntry
        MAX-ACCESS  not-accessible
        STATUS      current
        DESCRIPTION
            "The Mirror Information."
        INDEX       { uniMirrorGroupIndex }
        ::={uniMirrorTable 1 }

    UniMirrorEntry ::= SEQUENCE {
        uniMirrorGroupIndex           INTEGER,
        uniMirrorGroupName            DisplayString,
        uniMirrorGroupDstPortList     OCTET STRING,
        uniMirrorGroupSrcInPortList   OCTET STRING,
        uniMirrorGroupSrcOutPortList  OCTET STRING,
        uniMirrorGroupRowstatus       RowStatus
      }

    uniMirrorGroupIndex  OBJECT-TYPE
        SYNTAX      INTEGER
        MAX-ACCESS  not-accessible
        STATUS      current
        DESCRIPTION
            "Mirror Group Index"
        ::= {uniMirrorEntry 1 }

    uniMirrorGroupName  OBJECT-TYPE
        SYNTAX      DisplayString
        MAX-ACCESS  read-create
        STATUS      current
        DESCRIPTION
            "Mirror Group Name"
        ::= {uniMirrorEntry 2 }

    uniMirrorGroupDstPortList  OBJECT-TYPE
        SYNTAX      OCTET STRING
        MAX-ACCESS  read-create
        STATUS      current
        DESCRIPTION
            "Mirror Group Dst Port List.
            It is presented by port list. Each port is identified by
            2-byte format, One for slot ID, the last for port ID. The
            actual length of this string depends of the number of
            ports in destination port list of the mirror group,
            If the ONU is fixed (not modulized), set slot ID to 0,
            the NMS could ignore the slot info.
            Note that, slot here shall follow the last byte definition of
            EponCardIndex to indicate the main-slot and sub-slot index.
            The relationship is:
            Length of the string = 2 * (NUM of ports)
            For example, if port 1/2 and 3/4 is the destination ports of
            the mirror group, then the object is presented as:
            01 02 03 04
            "
        ::= {uniMirrorEntry 3 }

    uniMirrorGroupSrcInPortList  OBJECT-TYPE
        SYNTAX      OCTET STRING
        MAX-ACCESS  read-create
        STATUS      current
        DESCRIPTION
            "Mirror Group Src In Port List.
            It is presented by port list. Each port is identified by
            2-byte format, One for slot ID, the last for port ID. The
            actual length of this string depends of the number of
            ports in source ingress list of the mirror group,
            If the ONU is fixed (not modulized), set slot ID to 0,
            the NMS could ignore the slot info.
            Note that, slot here shall follow the last byte definition of
            EponCardIndex to indicate the main-slot and sub-slot index.
            The relationship is:
            Length of the string = 2 * (NUM of ports)
            For example, if port 1/2 and 3/4 is the source ingress ports of
            the mirror group, then the object is presented as:
            01 02 03 04
            "
        ::= {uniMirrorEntry 4 }

    uniMirrorGroupSrcOutPortList  OBJECT-TYPE
        SYNTAX      OCTET STRING
        MAX-ACCESS  read-create
        STATUS      current
        DESCRIPTION
            "Mirror Group Src Out Port List.
            It is presented by port list. Each port is identified by
            2-byte format, One for slot ID, the last for port ID. The
            actual length of this string depends of the number of
            ports in source egress list of the mirror group,
            If the ONU is fixed (not modulized), set slot ID to 0,
            the NMS could ignore the slot info.
          Note that, slot here shall follow the last byte definition of
          EponCardIndex to indicate the main-slot and sub-slot index.
          The relationship is:
          Length of the string = 2 * (NUM of ports)
          For example, if port 1/2 and 3/4 is the source egress ports of
          the mirror group, then the object is presented as:
          01 02 03 04
            "
        ::= {uniMirrorEntry 5 }

    uniMirrorGroupRowstatus  OBJECT-TYPE
        SYNTAX      RowStatus
        MAX-ACCESS  read-create
        STATUS      current
        DESCRIPTION
            "Mirror Group Rowstatus"
        ::= {uniMirrorEntry 6 }


    uniBroadcastStormSuppressionTable OBJECT-TYPE
        SYNTAX      SEQUENCE OF UniBroadcastStormSuppressionEntry
        MAX-ACCESS  not-accessible
        STATUS      current
        DESCRIPTION
            "A list of BroadcastStormSuppression entries."
        ::= { uniObjects 6 }

    uniBroadcastStormSuppressionEntry OBJECT-TYPE
        SYNTAX      UniBroadcastStormSuppressionEntry
        MAX-ACCESS  not-accessible
        STATUS      current
        DESCRIPTION
            "The Broadcast Storm Suppression Information"
        INDEX   { uniBroadcastStormSuppressionCardIndex,  uniBroadcastStormSuppressionPortIndex  }
        ::= { uniBroadcastStormSuppressionTable 1 }

    UniBroadcastStormSuppressionEntry ::=
        SEQUENCE {
            uniBroadcastStormSuppressionCardIndex                    EponCardIndex,
            uniBroadcastStormSuppressionPortIndex                    EponPortIndex,
            uniUnicastStormEnable               TruthValue,
            uniUnicastStormInPacketRate        INTEGER,
            uniUnicastStormOutPacketRate       INTEGER,
            uniMulticastStormEnable         TruthValue,
            uniMulticastStormInPacketRate   INTEGER,
            uniMulticastStormOutPacketRate  INTEGER,
            uniBroadcastStormEnable         TruthValue,
            uniBroadcastStormInPacketRate   INTEGER,
            uniBroadcastStormOutPacketRate  INTEGER
        }

    uniBroadcastStormSuppressionCardIndex OBJECT-TYPE
        SYNTAX      EponCardIndex
        MAX-ACCESS  not-accessible
        STATUS      current
        DESCRIPTION
            "card Index

            The value of this cardIndex depends on onuType.
            fixed(1)        - set to 0, to indicate slot num is meaningless.
            chassisBased(2) - MUST NOT be zero
            "
        ::= { uniBroadcastStormSuppressionEntry 1 }


    uniBroadcastStormSuppressionPortIndex  OBJECT-TYPE
        SYNTAX      EponPortIndex
        MAX-ACCESS  not-accessible
        STATUS      current
        DESCRIPTION
            "port Index"
        ::= { uniBroadcastStormSuppressionEntry 2 }

    uniUnicastStormEnable  OBJECT-TYPE
        SYNTAX      TruthValue
        MAX-ACCESS  read-write
        STATUS      current
        DESCRIPTION
            "Cast Storm Enable"
        ::= { uniBroadcastStormSuppressionEntry 3 }

    uniUnicastStormInPacketRate  OBJECT-TYPE
        SYNTAX      INTEGER
        UNITS   "pps"
        MAX-ACCESS  read-write
        STATUS      current
        DESCRIPTION
            "Cast Storm In Packet Rate"
        ::= { uniBroadcastStormSuppressionEntry 4 }

    uniUnicastStormOutPacketRate  OBJECT-TYPE
        SYNTAX      INTEGER
        UNITS   "pps"
        MAX-ACCESS  read-write
        STATUS      current
        DESCRIPTION
            "Cast Storm Out Packet Rate"
        ::= { uniBroadcastStormSuppressionEntry 5 }

    uniMulticastStormEnable  OBJECT-TYPE
        SYNTAX      TruthValue
        MAX-ACCESS  read-write
        STATUS      current
        DESCRIPTION
            "true(1) false(2)"
        ::= { uniBroadcastStormSuppressionEntry 6 }

    uniMulticastStormInPacketRate  OBJECT-TYPE
        SYNTAX      INTEGER
        UNITS   "pps"
        MAX-ACCESS  read-write
        STATUS      current
        DESCRIPTION
            "Multicast Storm In Packet Rate"
        ::= { uniBroadcastStormSuppressionEntry 7 }

    uniMulticastStormOutPacketRate  OBJECT-TYPE
        SYNTAX      INTEGER
        UNITS   "pps"
        MAX-ACCESS  read-write
        STATUS      current
        DESCRIPTION
            "Multicast Storm Out Packet Rate"
        ::= { uniBroadcastStormSuppressionEntry 8 }

    uniBroadcastStormEnable  OBJECT-TYPE
        SYNTAX      TruthValue
        MAX-ACCESS  read-write
        STATUS      current
        DESCRIPTION
            "true(1) false(2)"
        ::= { uniBroadcastStormSuppressionEntry 9 }

    uniBroadcastStormInPacketRate  OBJECT-TYPE
        SYNTAX      INTEGER
        UNITS   "pps"
        MAX-ACCESS  read-write
        STATUS      current
        DESCRIPTION
            "Broadcast Storm In Packet Rate"
        ::= { uniBroadcastStormSuppressionEntry 10 }

    uniBroadcastStormOutPacketRate  OBJECT-TYPE
        SYNTAX      INTEGER
        UNITS   "pps"
        MAX-ACCESS  read-write
        STATUS      current
        DESCRIPTION
            "Broadcast Storm Out Packet Rate"
        ::= { uniBroadcastStormSuppressionEntry 11 }

    uniExtAttributeTable  OBJECT-TYPE
        SYNTAX      SEQUENCE OF UniExtAttributeEntry
        MAX-ACCESS  not-accessible
        STATUS      current
        DESCRIPTION
            "The extended attribute list for each UNI. "
        ::= { uniObjects 7 }

    uniExtAttributeEntry OBJECT-TYPE
        SYNTAX      UniExtAttributeEntry
        MAX-ACCESS  not-accessible
        STATUS      current
        DESCRIPTION
            ""
        INDEX   { uniExtAttributeCardIndex,  uniExtAttributePortIndex  }
        ::= { uniExtAttributeTable 1 }

    UniExtAttributeEntry ::= SEQUENCE {
        uniExtAttributeCardIndex    EponCardIndex,
        uniExtAttributePortIndex    EponPortIndex,
        uniPerfStats15minuteEnable  TruthValue,
        uniPerfStats24hourEnable    TruthValue,
        uniLastChangeTime           TimeTicks,
        uniIsolationEnable          TruthValue,
        uniMacAddrLearnMaxNum       INTEGER,
        uniAutoNegotiationAdvertisedTechAbility AutoNegotiationTechAbility,
        uniMacAddrClearByPort       INTEGER
       }

    uniExtAttributeCardIndex  OBJECT-TYPE
        SYNTAX      EponCardIndex
        MAX-ACCESS  not-accessible
        STATUS      current
        DESCRIPTION
            "Card index
            The value of this cardIndex depends on onuType.
      fixed(1)        - set to 0, to indicate slot num is meaningless.
            chassisBased(2) - MUST NOT be zero
            "
        ::= {uniExtAttributeEntry 1 }

    uniExtAttributePortIndex  OBJECT-TYPE
        SYNTAX      EponPortIndex
        MAX-ACCESS  not-accessible
        STATUS      current
        DESCRIPTION
            ""
        ::= {uniExtAttributeEntry 2 }

    uniPerfStats15minuteEnable  OBJECT-TYPE
        SYNTAX      TruthValue
        MAX-ACCESS  read-write
        STATUS      current
        DESCRIPTION
            "true(1) false(2)"
        ::= {uniExtAttributeEntry 3 }

    uniPerfStats24hourEnable  OBJECT-TYPE
        SYNTAX      TruthValue
        MAX-ACCESS  read-write
        STATUS      current
        DESCRIPTION
            "true(1) false(2)"
        ::= {uniExtAttributeEntry 4 }

    uniLastChangeTime OBJECT-TYPE
        SYNTAX  TimeTicks
        MAX-ACCESS  read-only
        STATUS  current
        DESCRIPTION
              "Last Change Time"
        ::= {uniExtAttributeEntry 5 }

    uniIsolationEnable  OBJECT-TYPE
        SYNTAX      TruthValue
        MAX-ACCESS  read-write
        STATUS      current
        DESCRIPTION
            "true(1) false(2)"
        ::= {uniExtAttributeEntry 6 }

    uniMacAddrLearnMaxNum  OBJECT-TYPE
        SYNTAX      INTEGER
        MAX-ACCESS  read-write
        STATUS      current
        DESCRIPTION
            "Mac Address Learn Max Num"
        ::= {uniExtAttributeEntry 7 }
    uniAutoNegotiationAdvertisedTechAbility  OBJECT-TYPE
        SYNTAX      AutoNegotiationTechAbility
        MAX-ACCESS  read-write
        STATUS      current
        DESCRIPTION
            "Refer to clause 30.6.1.1.6 of IEEE 802.3 2005 edition"
        ::= {uniExtAttributeEntry 8 }

    uniMacAddrClearByPort  OBJECT-TYPE
        SYNTAX      INTEGER { clearDynamic(1) }
        MAX-ACCESS  read-write
        STATUS      current
        DESCRIPTION
            "Clear MAC address by UNI port.
            clearDynamic(1) - Clear all dynamic MAC address learned on the UNI port"
        ::= {uniExtAttributeEntry 9 }

--
-- END of NSCRTV-EPON-UNI-MIB
--

END
