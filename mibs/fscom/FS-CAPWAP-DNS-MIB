-- *******************************************************************
-- FS-CAPWAP-DNS-MIB.mib : FS DNS MIB
--
-- Jun 2010, chenfg1
--
-- Copyright (c) 2010 by FS.COM Inc..
-- All rights reserved.
-- *******************************************************************
--
FS-CAPWAP-DNS-MIB DEFINITIONS ::= BEGIN

IMPORTS
        MODULE-IDENTITY,
        OBJECT-TYPE,
		    Integer32,
	      NOTIFICATION-TYPE,
        Unsigned32,
        IpAddress
                FROM SNMPv2-SMI
        OBJECT-GROUP,
        MODULE-COMPLIANCE
                FROM SNMPv2-CONF
        TruthValue,
        RowStatus,
        DisplayString
                FROM SNMPv2-TC
        fsMgmt
                FROM FS-SMI
        fsIfIndex
                FROM FS-INTERFACE-MIB;


fsCapwapDnsMIB   MODULE-IDENTITY
       LAST-UPDATED    "201007090000Z"
       ORGANIZATION    "FS.COM Inc.."
       CONTACT-INFO
                "
                Tel: 400-865-2852

                E-mail: https://www.fs.com/live_chat_service_mail.html"

        DESCRIPTION
                "This is DNS MIB"

        REVISION      "201007090000Z"
        DESCRIPTION
                "Initial version of this MIB module. "
        ::= { fsMgmt 88 }


fsCapwapDnsMIBObjects OBJECT IDENTIFIER
    ::= { fsCapwapDnsMIB 0 }

fsCapwapDnsGlobalConfig OBJECT IDENTIFIER
	::= { fsCapwapDnsMIBObjects 1 }


--*************************************************
--DNS Global Config
--*************************************************

fsLDnsFirstServer     OBJECT-TYPE
	SYNTAX	                IpAddress
	MAX-ACCESS              read-write
	STATUS	                current
	DESCRIPTION
	     "The first dns server address."
	::= { fsCapwapDnsGlobalConfig  1 }

fsLDnsSecondServer    OBJECT-TYPE
	SYNTAX	                IpAddress
	MAX-ACCESS              read-write
	STATUS	                current
	DESCRIPTION
	     "The second dns server address."
	::= { fsCapwapDnsGlobalConfig  2 }



fsCapwapDnsMIBConformance OBJECT IDENTIFIER ::= { fsCapwapDnsMIB 2 }
fsCapwapDnsMIBCompliances OBJECT IDENTIFIER ::= { fsCapwapDnsMIBConformance 1 }
fsCapwapDnsMIBGroups      OBJECT IDENTIFIER ::= { fsCapwapDnsMIBConformance 2 }

-- compliance statements

fsCapwapDnsMIBCompliance MODULE-COMPLIANCE
        STATUS  current
        DESCRIPTION
                "The compliance statement for entities which implement
                the FS Capwap Dns MIB"
        MODULE  -- this module
        MANDATORY-GROUPS {
              fsCapwapDnsMIBGroup
        }
        ::= { fsCapwapDnsMIBCompliances 1 }

-- units of conformance

fsCapwapDnsMIBGroup OBJECT-GROUP
        OBJECTS {
              fsLDnsFirstServer,
	      fsLDnsSecondServer
        }
        STATUS  current
        DESCRIPTION
                "A collection of objects providing capwap dns information and
                opertion to a FS agent."
        ::= { fsCapwapDnsMIBGroups 1 }

END
