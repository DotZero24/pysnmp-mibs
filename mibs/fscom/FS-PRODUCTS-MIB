-- *****************************************************************
-- FS-PRODUCTS-MIB.mib:  FS Product Object Identifier Assignments
--
-- March 2002, Wuzg
--
-- Copyright (c) 2002 by FS.COM Inc..
-- All rights reserved.
--
-- *****************************************************************
--

FS-PRODUCTS-MIB DEFINITIONS ::= BEGIN

IMPORTS
        MODULE-IDENTITY
                FROM SNMPv2-SMI
        fsModules,
        fsSwitchProducts
                FROM FS-SMI
        fsRouterProducts
                FROM FS-ROUTER-SMI
        fsGatewayProducts
                FROM FS-GATEWAY-SMI
        fsWirelessProducts
                FROM FS-WIRELESS-SMI
        fsSoftwareProducts
                FROM FS-SOFTWARE-SMI
        fsSmartClassProducts
                FROM FS-SMARTCLASS-SMI;

fsProductsMIB MODULE-IDENTITY
        LAST-UPDATED "200203200000Z"
        ORGANIZATION "FS.COM Inc.."
        CONTACT-INFO
                "
                Tel: 400-865-2852

                E-mail: https://www.fs.com/live_chat_service_mail.html"
        DESCRIPTION
                "This module defines the object identifiers that are
            		assigned to various hardware platforms, and hence are
            		returned as values for sysObjectID"
        REVISION      "200203200000Z"
        DESCRIPTION
                "Initial version of this MIB module."
        ::= { fsModules 1}

-- devices return a sysObjectID value that corresponds to the
-- device model number

-- ****************************** switch ***********************************

S5860-20SQ OBJECT IDENTIFIER ::= { fsSwitchProducts 1 }
S5860-24XB-U OBJECT IDENTIFIER ::= { fsSwitchProducts 2 }

END
