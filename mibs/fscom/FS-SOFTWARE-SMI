-- *****************************************************************
-- FS-SOFTWARE-SMI.mib: FS SOFTWARE SMI File
--
-- Aug. 2014, panshiyong
--
-- Copyright (c) 2014 by FS.COM Inc..
-- All rights reserved.
--
-- *****************************************************************
--

FS-SOFTWARE-SMI DEFINITIONS ::= BEGIN

IMPORTS
        MODULE-IDENTITY,
        OBJECT-IDENTITY
                FROM SNMPv2-SMI
        products
                FROM FS-SMI;

software OBJECT IDENTIFIER ::= { products 7 }

softwareMib MODULE-IDENTITY
        LAST-UPDATED "201408190000Z"
        ORGANIZATION "FS.COM Inc.."
        CONTACT-INFO
                "
                Tel: 400-865-2852

                E-mail: https://www.fs.com/live_chat_service_mail.html"
        DESCRIPTION
                "The Structure of Management Information for the
                 FS enterprise."
        REVISION      "201005250000Z"
        DESCRIPTION
                "Initial version of this MIB module."
        ::= { software 1 }

fsSoftwareProducts OBJECT-IDENTITY
        STATUS  current
        DESCRIPTION
                "fsSoftwareProducts is the root OBJECT IDENTIFIER from
                 which sysObjectID values are assigned for software.  Actual
                 values are defined in FS-PRODUCTS-MIB."
        ::= { softwareMib 1 }

END
