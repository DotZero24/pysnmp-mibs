-- *****************************************************************
-- FS-DHCP-RELAY-MIB.mib:  FS DHCP relay MIB file
--
-- Oct 2011, yangchanghua
--
-- Copyright (c) 2011 by FS.COM Inc..
-- All rights reserved.
-- *****************************************************************
--

FS-DHCP-RELAY-MIB DEFINITIONS ::= BEGIN

IMPORTS
        MODULE-IDENTITY,
        OBJECT-TYPE,
        NOTIFICATION-TYPE,
        Integer32,
        Counter32
                FROM SNMPv2-SMI
        TruthValue,
        DisplayString,
        RowStatus,
        MacAddress
                FROM SNMPv2-TC
        MODULE-COMPLIANCE,
        OBJECT-GROUP,
        NOTIFICATION-GROUP
                FROM SNMPv2-CONF
        fsMgmt
                FROM FS-SMI;

fsDhcpMIB  MODULE-IDENTITY
    LAST-UPDATED "201111280000Z"
    ORGANIZATION "FS.COM Inc.."
    CONTACT-INFO
        				"
                Tel: 400-865-2852

                E-mail: https://www.fs.com/live_chat_service_mail.html"
    DESCRIPTION
        "This module defines fs DHCP mibs."
    -- Revision History
    REVISION    "201111280000Z"
    DESCRIPTION
        "Initial version of this MIB module."
    ::= { fsMgmt 104 }

--
-- Declare top-level DHCP relay MIB objects
--
fsDhcpMIBObjects OBJECT-IDENTITY
    STATUS      current
    DESCRIPTION
        "DHCP Relay MIB objects are defined in this branch."
    ::= { fsDhcpMIB 1 }

--
-- DHCP Relay
--
fsDhcpRelayMIBObjects OBJECT-IDENTITY
    STATUS      current
    DESCRIPTION
        "DHCP Relay MIB identification objects are all defined
        in this branch."
    ::= { fsDhcpMIBObjects 1 }

--
-- DHCP Relay Status
--
fsDHCPRelayCycleStatus OBJECT-TYPE
    SYNTAX      INTEGER {
                             on(0), -- DHCP relay cycle mode status is on
                             off(1) -- DHCP relay cycle mode status is off
                        }
    MAX-ACCESS  read-write
    STATUS      current
    DESCRIPTION
        "Status of DHCP relay cycle mode,
         when the value is 0, cycle with the serveral DHCP servers addresses,
         when the value is 1, use one same DHCP server."
    ::= { fsDhcpRelayMIBObjects 1 }

fsDhcpRelayCounters OBJECT-IDENTITY
    STATUS      current
    DESCRIPTION
        "Group of objects that count various DHCP Relay events."
 ::= { fsDhcpRelayMIBObjects 2 }

--
-- DHCP Relay Counters
--
fsDHCPRRxBadPktNum OBJECT-TYPE
    SYNTAX      Integer32
    MAX-ACCESS  read-only
    STATUS      current
    DESCRIPTION
        "The total number of the bad packets received by
            DHCP relay."
    ::= { fsDhcpRelayCounters 1 }

fsDHCPRRxServerPktNum OBJECT-TYPE
    SYNTAX      Integer32
    MAX-ACCESS  read-only
    STATUS      current
    DESCRIPTION
        "The total number of the packets received from
            DHCP servers by DHCP relay module."
    ::= { fsDhcpRelayCounters 2 }

fsDHCPRTxServerPktNum OBJECT-TYPE
    SYNTAX      Integer32
    MAX-ACCESS  read-only
    STATUS      current
    DESCRIPTION
        "The total number of the packets transmited to
            DHCP servers by DHCP relay module."
    ::= { fsDhcpRelayCounters 3 }

fsDHCPRRxClientPktNum OBJECT-TYPE
    SYNTAX      Integer32
    MAX-ACCESS  read-only
    STATUS      current
    DESCRIPTION
        "The total number of the packets received form DHCP
            clients by DHCP relay."
    ::= { fsDhcpRelayCounters 4 }

fsDHCPRTxClientPktNum OBJECT-TYPE
    SYNTAX      Integer32
    MAX-ACCESS  read-only
    STATUS      current
    DESCRIPTION
        "The total number of the packets transmited
            to DHCP clients by DHCP relay."
    ::= { fsDhcpRelayCounters 5 }

fsDHCPRRxClientUniPktNum OBJECT-TYPE
    SYNTAX      Integer32
    MAX-ACCESS  read-only
    STATUS      current
    DESCRIPTION
        "The total number of the unicast packets received form DHCP
            clients by DHCP relay."
    ::= { fsDhcpRelayCounters 6 }

fsDHCPRRxClientBroPktNum OBJECT-TYPE
    SYNTAX      Integer32
    MAX-ACCESS  read-only
    STATUS      current
    DESCRIPTION
        "The total number of the broadcast packets received form DHCP
            clients by DHCP relay."
    ::= { fsDhcpRelayCounters 7 }

fsDHCPRTxClientUniPktNum OBJECT-TYPE
    SYNTAX      Integer32
    MAX-ACCESS  read-only
    STATUS      current
    DESCRIPTION
        "The total number of the unicast packets transmited
            to DHCP clients by DHCP relay."
    ::= { fsDhcpRelayCounters 8 }

fsDHCPRTxClientBroPktNum OBJECT-TYPE
    SYNTAX      Integer32
    MAX-ACCESS  read-only
    STATUS      current
    DESCRIPTION
        "The total number of the broadcast packets transmited
            to DHCP clients by DHCP relay."
    ::= { fsDhcpRelayCounters 9 }

fsDHCPRelayDiscoverPktNum OBJECT-TYPE
    SYNTAX      Integer32
    MAX-ACCESS  read-only
    STATUS      current
    DESCRIPTION
        "The total number of the DHCP Discover packets handled
            by DHCP relay."
    ::= { fsDhcpRelayCounters 10 }

fsDHCPRelayRequestPktNum OBJECT-TYPE
    SYNTAX      Integer32
    MAX-ACCESS  read-only
    STATUS      current
    DESCRIPTION
        "The total number of the DHCP Request packets handled
            by DHCP relay."
    ::= { fsDhcpRelayCounters 11 }

fsDHCPRelayDeclinePktNum OBJECT-TYPE
    SYNTAX      Integer32
    MAX-ACCESS  read-only
    STATUS      current
    DESCRIPTION
        "The total number of the DHCP Decline packets handled
            by DHCP relay."
    ::= { fsDhcpRelayCounters 12 }

fsDHCPRelayReleasePktNum OBJECT-TYPE
    SYNTAX      Integer32
    MAX-ACCESS  read-only
    STATUS      current
    DESCRIPTION
        "The total number of the DHCP Release packets handled
            by DHCP relay."
    ::= { fsDhcpRelayCounters 13 }

fsDHCPRelayInformPktNum OBJECT-TYPE
    SYNTAX      Integer32
    MAX-ACCESS  read-only
    STATUS      current
    DESCRIPTION
        "The total number of the DHCP Inform packets handled
            by DHCP relay."
    ::= { fsDhcpRelayCounters 14 }

fsDHCPRelayOfferPktNum OBJECT-TYPE
    SYNTAX      Integer32
    MAX-ACCESS  read-only
    STATUS      current
    DESCRIPTION
        "The total number of the DHCP Offer packets handled
            by DHCP server."
    ::= { fsDhcpRelayCounters 15 }

fsDHCPRelayAckPktNum OBJECT-TYPE
    SYNTAX      Integer32
    MAX-ACCESS  read-only
    STATUS      current
    DESCRIPTION
        "The total number of the DHCP Ack packets handled
            by DHCP relay."
    ::= { fsDhcpRelayCounters 16 }

fsDHCPRelayNakPktNum OBJECT-TYPE
    SYNTAX      Integer32
    MAX-ACCESS  read-only
    STATUS      current
    DESCRIPTION
        "The total number of the DHCP Nak packets handled
            by DHCP relay."
    ::= { fsDhcpRelayCounters 17 }

--
-- Conformance
--
fsDhcpMIBConformance   OBJECT-IDENTITY
    STATUS      current
    DESCRIPTION
        "DHCP relay conformance objects are all defined in this
        branch."
    ::= { fsDhcpMIB 2 }

fsDhcpMIBCompliances   OBJECT IDENTIFIER ::= { fsDhcpMIBConformance 1 }
fsDhcpMIBGroups        OBJECT IDENTIFIER ::= { fsDhcpMIBConformance 2 }

--
-- Compliance groups
--
fsDhcpRelayCompliance MODULE-COMPLIANCE
    STATUS      current
    DESCRIPTION
        "This group describes the requirements for conformance to the
        DHCP Relay MIB."
    MODULE  -- this module
    MANDATORY-GROUPS {
        fsDhcpRelayCountersObjects
    }
    ::= { fsDhcpMIBCompliances 1 }

--
-- Object groups
--
fsDhcpRelayCountersObjects  OBJECT-GROUP
    OBJECTS {
        fsDHCPRelayCycleStatus,
        fsDHCPRRxBadPktNum,
        fsDHCPRRxServerPktNum,
        fsDHCPRTxServerPktNum,
        fsDHCPRRxClientPktNum,
        fsDHCPRTxClientPktNum,
        fsDHCPRRxClientUniPktNum,
        fsDHCPRRxClientBroPktNum,
        fsDHCPRTxClientUniPktNum,
        fsDHCPRTxClientBroPktNum,
        fsDHCPRelayDiscoverPktNum,
        fsDHCPRelayRequestPktNum,
        fsDHCPRelayDeclinePktNum,
        fsDHCPRelayReleasePktNum,
        fsDHCPRelayInformPktNum,
        fsDHCPRelayOfferPktNum,
		    fsDHCPRelayAckPktNum,
		    fsDHCPRelayNakPktNum }
    STATUS      current
    DESCRIPTION
        "The basic collection of objects providing management of DHCP
        Relay functionality."
    ::= { fsDhcpMIBGroups 1 }

END
