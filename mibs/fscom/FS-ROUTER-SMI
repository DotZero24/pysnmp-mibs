-- *****************************************************************
-- FS-ROUTER-SMI.mib: FS Router SMI File
--
-- Jan. 2005, Wuzg
--
-- Copyright (c) 2005 by FS.COM Inc..
-- All rights reserved.
--
-- *****************************************************************
--

FS-ROUTER-SMI DEFINITIONS ::= BEGIN

IMPORTS
        MODULE-IDENTITY,
        OBJECT-IDENTITY
                FROM SNMPv2-SMI
        products
                FROM FS-SMI;

router          OBJECT IDENTIFIER ::= { products 2 }

routerMib MODULE-IDENTITY
        LAST-UPDATED "200501060000Z"
        ORGANIZATION "FS.COM Inc.."
        CONTACT-INFO
                "
                Tel: 400-865-2852

                E-mail: https://www.fs.com/live_chat_service_mail.html"
        DESCRIPTION
                "The Structure of Management Information for the
                 FS enterprise."
        REVISION      "200501060000Z"
        DESCRIPTION
                "Initial version of this MIB module."
        ::= { router 1 }

fsRouterProducts OBJECT-IDENTITY
        STATUS  current
        DESCRIPTION
                "fsRouterProducts is the root OBJECT IDENTIFIER from
                which sysObjectID values are assigned for router.  Actual
                values are defined in FS-PRODUCTS-MIB."
        ::= { routerMib 1 }

END
