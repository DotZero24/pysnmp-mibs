-----------------------------------------------------------------------------
--  File         : gbnL2QACL-MIB.mi2
--  Description  : ADMIN  Enterprise MIB
--  Version      : 0.01
--  Date         : sep 26, 2003
--
--  Copyright (c) 2002-2005 admin Systems, Inc.  All Rights Reserved.
------------------------------------------------------------------------------
------------------------------------------------------------------------------

    GBNL2QACL-MIB DEFINITIONS ::= BEGIN

    IMPORTS
        MODULE-IDENTITY, OBJECT-TYPE,
        Integer32, Counter64,IpAddress                    FROM SNMPv2-SMI

        DisplayString, TruthValue,MacAddress,RowStatus    FROM SNMPv2-TC

        MODULE-COMPLIANCE, OBJECT-GROUP         FROM SNMPv2-CONF

        gbnL2                              FROM ADMIN-MASTER-MIB

        PortList                                FROM Q-BRIDGE-MIB

        mib-2                                   FROM RFC1213-MIB

        VlanId                                  FROM  Q-BRIDGE-MIB

        TOSType                                 FROM  OSPF-MIB;

    gbnL2QACL MODULE-IDENTITY
        LAST-UPDATED    "0309260001Z"  -- sep 26,2003
        ORGANIZATION    "admin Systems, Inc."
        CONTACT-INFO    "admin Systems, Inc.
                         E-mail: support@admin.com.cn"

        DESCRIPTION     "GBN Enterprise MIB definition."

        REVISION        "0309260001Z"  -- sep 26,2003
        DESCRIPTION     "Initial MIB creation."

        ::= { gbnL2 4 }

InetAddressIPv6 ::= TEXTUAL-CONVENTION
    DISPLAY-HINT "2x:2x:2x:2x:2x:2x:2x:2x"
    STATUS       current
    DESCRIPTION
        "Represents an IPv6 network address:

           Octets   Contents         Encoding
            1-16    IPv6 address     network-byte order

         The corresponding InetAddressType value is ipv6(2).

         This textual convention SHOULD NOT be used directly in object
         definitions, as it restricts addresses to a specific format.
         However, if it is used, it MAY be used either on its own or in
         conjunction with InetAddressType, as a pair."
    SYNTAX       DisplayString(SIZE (16))

AdminStatus ::= TEXTUAL-CONVENTION
    STATUS      current
    DESCRIPTION
       "The AdminStatus of an item: 'valid' indicates that
       it is running,while 'invalid' indicates that it is not."
    SYNTAX      INTEGER { active (1), inactive (2) }

Action ::= TEXTUAL-CONVENTION
    STATUS      current
    DESCRIPTION
       "permit or deny"
    SYNTAX      INTEGER { permit (101), deny (100) }

Dscp ::= TEXTUAL-CONVENTION
    STATUS      current
    DESCRIPTION
       "dscp priority"
    SYNTAX      Integer32 (0..63)

AclType ::= TEXTUAL-CONVENTION
    STATUS      current
    DESCRIPTION
       "standard、extend、link、user"
    SYNTAX      INTEGER { standard(1), extend (2),link(3), user (4) }

PacketFlowType ::= TEXTUAL-CONVENTION
    STATUS      current
    DESCRIPTION
       "broadcast、multicast、unicast"
    SYNTAX      INTEGER { broadcast(1), multicast(2), unicast(3) }

   -----------------------------------------------------
   -- the quene-scheduer QOS
   -----------------------------------------------------

   qosQueueSchedulerGroup  OBJECT IDENTIFIER ::= { gbnL2QACL 1 }

   qosWrrQueue1Weight OBJECT-TYPE
       SYNTAX  INTEGER (1..97)
       ACCESS  read-write
       STATUS  current
       DESCRIPTION
               "Weight of 1th queue(%)."
               --队列1的权重
       ::= { qosQueueSchedulerGroup 1 }

   qosWrrQueue2Weight OBJECT-TYPE
       SYNTAX  INTEGER (1..97)
       ACCESS  read-write
       STATUS  current
       DESCRIPTION
               "Weight of 2th queue(%)."
               --队列2的权重
       ::= { qosQueueSchedulerGroup 2 }


   qosWrrQueue3Weight OBJECT-TYPE
       SYNTAX  INTEGER (1..97)
       ACCESS  read-write
       STATUS  current
       DESCRIPTION
               "Weight of 3th queue(%)."
               --队列3的权重
       ::= { qosQueueSchedulerGroup 3 }


   qosWrrQueue4Weight OBJECT-TYPE
       SYNTAX  INTEGER (1..97)
       ACCESS  read-write
       STATUS  current
       DESCRIPTION
            "Weight of 4th queue(%)."
            --队列4的权重
       ::= { qosQueueSchedulerGroup 4 }

   qosWrrMaxDelayValue OBJECT-TYPE
       SYNTAX  INTEGER (1..255)
       ACCESS  read-write
       STATUS  current
       DESCRIPTION
            "Max delay time of queue shcedule."
            --"队列调度时最高优先级的队列最长等待时间 "
       ::= { qosQueueSchedulerGroup 5 }

   qosQueueSchedulerMode OBJECT-TYPE
       SYNTAX  INTEGER  {
                        strictPriority (1),
                        wrr(2),
                        wrrMaxDelay(3) }
       ACCESS  read-write
       STATUS  current
       DESCRIPTION
            "Queue schedule mode."
            --"队列调度模式:绝对优先级、加权轮循调度、最大延时的加权轮循调度  "
       DEFVAL  { strictPriority }
       ::= { qosQueueSchedulerGroup 6 }

   qosWrrQueue5Weight OBJECT-TYPE
       SYNTAX  INTEGER (1..97)
       ACCESS  read-write
       STATUS  current
       DESCRIPTION
               "Weight of 5th queue(%)."
               --队列5的权重
       ::= { qosQueueSchedulerGroup 7 }

   qosWrrQueue6Weight OBJECT-TYPE
       SYNTAX  INTEGER (1..97)
       ACCESS  read-write
       STATUS  current
       DESCRIPTION
               "Weight of 6th queue(%)."
               --队列6的权重
       ::= { qosQueueSchedulerGroup 8 }

   qosWrrQueue7Weight OBJECT-TYPE
       SYNTAX  INTEGER (1..97)
       ACCESS  read-write
       STATUS  current
       DESCRIPTION
               "Weight of 7th queue(%)."
               --队列7的权重
       ::= { qosQueueSchedulerGroup 9 }

   qosWrrQueue8Weight OBJECT-TYPE
       SYNTAX  INTEGER (1..97)
       ACCESS  read-write
       STATUS  current
       DESCRIPTION
               "Weight of 8th queue(%)."
               --队列8的权重
       ::= { qosQueueSchedulerGroup 10 }

--  ACL table Variables

--      These parameters apply globally to the swicth's

 aclNumTable OBJECT-TYPE
        SYNTAX   SEQUENCE OF AclNumEntry
        MAX-ACCESS   not-accessible
        STATUS   current
        DESCRIPTION
            "Number-based ACL table."
            --基于数字的访问控制列表，它一共由五种类型：基于数字的标准访问控制列表、
            --基于数字的扩展访问列表、基于数字的二层访问控制列表、基于数字的自定义访
            --问控制列表和基于数字的接口访问控制列表。其中标准访问控制列表的取值为1-99，
            --扩展访问控制列表的取值为100-199，二层访问控制列表的取值为200-299，自定义
            --访问控制列表的取值为300-399.
       ::= { gbnL2QACL 2 }

    aclNumEntry OBJECT-TYPE
        SYNTAX   AclNumEntry
        MAX-ACCESS   not-accessible
        STATUS   current
        DESCRIPTION
            "The entry of number-based ACL table."
            --"定义一条基于数字的访问控制列表."
       INDEX { aclNumNumber }
       ::= { aclNumTable 1 }

    AclNumEntry ::=
        SEQUENCE {
            aclNumNumber
                Integer32,
            aclNumType
                AclType,
            aclNumMatchOrder
                INTEGER,
            aclNumTotleSubitems
                Integer32,
            aclNumRowStatus
                RowStatus
                  }

    aclNumNumber OBJECT-TYPE
        SYNTAX   Integer32
        MAX-ACCESS   read-only
        STATUS   current
        DESCRIPTION
            "The number of number-based ACL."
            --基于数字的访问控制列表的标号，它的取值范围为1－399.
            --它的取值可以代表此条访问控制列表是属于何种类型。
        ::= { aclNumEntry 1 }

    aclNumType OBJECT-TYPE
        SYNTAX   AclType
        MAX-ACCESS   read-only
        STATUS   current
        DESCRIPTION
             "The type of number-based ACL: standard, extended or link-based."
             --基于数字的访问控制列表的类型，其中number为1-99为标准ACL，
             --100-199为扩展ACL，200-299为二层ACL，300-399为用户自定义ACL.
        ::= { aclNumEntry 2 }

    aclNumMatchOrder OBJECT-TYPE
        SYNTAX   INTEGER    {
                    config (0),
                    auto (1)
                    }
        MAX-ACCESS   read-write
        STATUS   current
        DESCRIPTION
            "The match order of number-based ACL."
            --"定义一条访问控制列表的配置顺序，auto 所用的“深度优先“
            --原则是指：把指定数据包范围最小的语句排在最前面。这一点可以
            --通过比较地址的通配符来实现，通配符越小，则指定的主机的范围
            --就越小。比如129.102.1.1 0.0.0.0 指定了一台主机：129.102.1.1
            --而129.102.1.1 0.0.255.255 则指定了一个网段： 129.102.1.1 ～
            --129.102.255.255，显然前者在访问控制规则中排在前面。具体标准
            --为：对于标准访问控制规则的语句，直接比较源地址通配符，通配符
            --相同的则按配置顺序；对于基于接口过滤的访问控制规则，配置了'any'
            --的规则排在后面，其它按配置顺序；对于扩展访问控制规则，首先比
            --较源地址通配符，相同的再比较目的地址通配符，仍相同的则比较端
            --口号的范围，范围小的排在前面，如果端口号范围也相同则按配置顺序，
            --默认按照用户的配置顺序即config。"
        DEFVAL { config }
      ::= { aclNumEntry 3 }

    aclNumTotleSubitems OBJECT-TYPE
        SYNTAX   Integer32
        MAX-ACCESS   read-only
        STATUS   current
        DESCRIPTION
            "The total subitems of number-based ACL."
            --"一条访问控制列表可以定义多条子规则，这些子规则按照一定的顺序排列
            --成一条访问控制列表，每条ACL最多可以定义128项子规则。"
        ::= { aclNumEntry 4 }

    aclNumRowStatus OBJECT-TYPE
        SYNTAX   RowStatus
        MAX-ACCESS   read-write
        STATUS   current
        DESCRIPTION
            "The row status of number-based ACL entry."
            --"表示当前ACL的状态，添加或删除。"
        ::= { aclNumEntry 5 }


 --ACL子项定义，基于数字的标准访问控制列表子项。

  aclNumStdSubitemTable OBJECT-TYPE
        SYNTAX   SEQUENCE OF AclNumStdSubitemEntry
        MAX-ACCESS   not-accessible
        STATUS   current
        DESCRIPTION
            "Standard and number-based ACL subitem table."
            --"定义一条标准访问控制列表子项。它是通过目的地址进行过滤的。"
       ::= { gbnL2QACL 3 }

    aclNumStdSubitemEntry OBJECT-TYPE
        SYNTAX   AclNumStdSubitemEntry
        MAX-ACCESS   not-accessible
        STATUS   current
        DESCRIPTION
            "The entry of standard and number-based ACL subitem table."
            --"定义一条标准访问控制列表子项."
       INDEX { aclNumStdNum, aclNumStdSubNum }
       ::= { aclNumStdSubitemTable 1 }

    AclNumStdSubitemEntry ::=
        SEQUENCE {
            aclNumStdNum
                Integer32,
            aclNumStdSubNum
                Integer32,
            aclNumStdSubitemAdminStatus
                AdminStatus,
            aclNumStdSubitemAction
                Action,
            aclNumStdSubitemSrcAddr
                IpAddress,
            aclNumStdSubitemSrcAddrWldmsk
                IpAddress,
            aclNumStdFragments
                TruthValue,
            aclNumStdTimeRange
                OCTET STRING,
            aclNumStdSubitemRowStatus
                RowStatus,
            aclNumStdAddressType
                Integer32,
            aclNumStdSrcAddrV6
               InetAddressIPv6,
            aclNumStdSrcAddrV6Wldmsk
               InetAddressIPv6,
            aclNumStdDefaultRoute
            	 TruthValue,
            aclNumStdL3IntfId
                Integer32,
            }

    aclNumStdNum OBJECT-TYPE
        SYNTAX   Integer32  (1..99)
        MAX-ACCESS   read-only
        STATUS   current
        DESCRIPTION
            "The number of standard and number-based ACL subitem."
            --"基于数字的访问控制列表的标号，它的取值范围为1－399，1000-1999.
            --它的取值可以代表此条访问控制列表是属于何种类型。"
        ::= { aclNumStdSubitemEntry 1 }

    aclNumStdSubNum OBJECT-TYPE
        SYNTAX   Integer32 (0..127)
        MAX-ACCESS   read-only
        STATUS   current
        DESCRIPTION
            "The sequence number of standard and number-based ACL subitem."
            --"访问控制列表的子项号，0－127。"
        ::= { aclNumStdSubitemEntry 2 }

    aclNumStdSubitemAdminStatus OBJECT-TYPE
        SYNTAX   AdminStatus
        MAX-ACCESS   read-only
        STATUS   current
        DESCRIPTION
            "The admin status of standard and number-based ACL subitem."
            --"当此项为valid时激活一条访问控制列表，invalid表示只配置了此项
            --ACL但并没有下发到硬件开始执行。"
        DEFVAL { invalid }
       ::= { aclNumStdSubitemEntry 3 }

    aclNumStdSubitemAction OBJECT-TYPE
        SYNTAX   Action
        MAX-ACCESS   read-write
        STATUS   current
        DESCRIPTION
            "The action of standard and number-based ACL subitem."
            --"定义一条访问列表子项的动作，允许或拒绝。"
       ::= { aclNumStdSubitemEntry 4 }

    aclNumStdSubitemSrcAddr OBJECT-TYPE
        SYNTAX   IpAddress
        MAX-ACCESS   read-write
        STATUS   current
        DESCRIPTION
            "The source ip-address of standard and number-based ACL subitem."
            --"标准访问控制列表子项的原地址"
       ::= { aclNumStdSubitemEntry 5 }

    aclNumStdSubitemSrcAddrWldmsk OBJECT-TYPE
        SYNTAX   IpAddress
        MAX-ACCESS   read-write
        STATUS   current
        DESCRIPTION
            "The source ip-address mask of standard and number-based ACL subitem."
            --"标准访问控制列表子项的原地址通配符"
       ::= { aclNumStdSubitemEntry 6 }

    aclNumStdFragments OBJECT-TYPE
        SYNTAX   TruthValue
        MAX-ACCESS   read-write
        STATUS   current
        DESCRIPTION
            "The ip fragments of standard and number-based ACL subitem."
        DEFVAL { false }
       ::= { aclNumStdSubitemEntry 7 }


    aclNumStdTimeRange OBJECT-TYPE
        SYNTAX   OCTET STRING (SIZE (0..32))
        MAX-ACCESS   read-write
        STATUS   current
        DESCRIPTION
            "The referred time range of standard and number-based ACL subitem."
            --"访问列表子项起作用的时间段"
        ::= { aclNumStdSubitemEntry 8 }

    aclNumStdSubitemRowStatus OBJECT-TYPE
        SYNTAX   RowStatus
        MAX-ACCESS   read-write
        STATUS   current
        DESCRIPTION
            "The row status of standard and number-based ACL subitem entry."
            --"表示当前ACL子项的状态，添加或删除。"
        ::= { aclNumStdSubitemEntry 9 }

    aclNumStdAddressType OBJECT-TYPE
        SYNTAX   Integer32 {
              ipv4(1),
              ipv6(2)
            }
        MAX-ACCESS   read-write
        STATUS   current
        DESCRIPTION
            "The ip-address type of standard and number-based ACL subitem."
            --"表示当前ACL子项的ip地址的类型。"
        ::= { aclNumStdSubitemEntry 10 }

    aclNumStdSrcAddrV6 OBJECT-TYPE
        SYNTAX   InetAddressIPv6
        MAX-ACCESS   read-write
        STATUS   current
        DESCRIPTION
            "The source ipv6-address of standard and number-based ACL subitem."
            --"表示当前ACL子项的源ipv6地址"
        ::= { aclNumStdSubitemEntry 11 }

    aclNumStdSrcAddrV6Wldmsk OBJECT-TYPE
        SYNTAX   InetAddressIPv6
        MAX-ACCESS   read-write
        STATUS   current
        DESCRIPTION
            "The source ipv6-address mask of standard and number-based ACL subitem."
            --"表示当前ACL子项的源ipv6地址的通配符"
        ::= { aclNumStdSubitemEntry 12 }

    aclNumStdDefaultRoute OBJECT-TYPE
        SYNTAX   TruthValue
        MAX-ACCESS   read-write
        STATUS   current
        DESCRIPTION
            "The default route of standard and number-based ACL subitem."
        DEFVAL { false }
       ::= { aclNumStdSubitemEntry 13 }

    aclNumStdL3IntfId OBJECT-TYPE
        SYNTAX   Integer32
        MAX-ACCESS   read-write
        STATUS   current
        DESCRIPTION
            "The L3 interface type of standard and number-based ACL subitem."
       ::= { aclNumStdSubitemEntry 14 }

--ACL子项定义，基于数字的扩展访问控制列表子项。

  aclNumExdSubitemTable OBJECT-TYPE
        SYNTAX   SEQUENCE OF AclNumExdSubitemEntry
        MAX-ACCESS   not-accessible
        STATUS   current
        DESCRIPTION
            "Extended and number-based ACL subitem table."
            --"定义一条扩展访问控制列表子项。它是通过对标准访问控制列表的补充。"
       ::= { gbnL2QACL 4 }

    aclNumExdSubitemEntry OBJECT-TYPE
        SYNTAX   AclNumExdSubitemEntry
        MAX-ACCESS   not-accessible
        STATUS   current
        DESCRIPTION
            "The entry of extended and number-based ACL subitem table."
            --"定义一条标准访问控制列表子项."
       INDEX { aclNumExdNum, aclNumExdSubNum}
       ::= { aclNumExdSubitemTable 1 }

    AclNumExdSubitemEntry ::=
        SEQUENCE {
            aclNumExdNum
                Integer32,
            aclNumExdSubNum
                Integer32,
            aclNumExdSubitemAdminStatus
                AdminStatus,
            aclNumExdSubitemAction
                Action,
            aclNumExdSubitemProtocal
                Integer32,
            aclNumExdSubitemSrcAddr
                IpAddress,
            aclNumExdSubitemSrcAddrWldmsk
                IpAddress,
            aclNumExdSubitemDstAddr
                IpAddress,
            aclNumExdSubitemDstAddrWldmsk
                IpAddress,
            aclNumExdSubitemSrcPort
                Integer32,
            aclNumExdSubitemSrcPortWldmsk
                Integer32,
            aclNumExdSubitemDstPort
                Integer32,
            aclNumExdSubitemDstPortWldmsk
                Integer32,
            aclNumExdSubitemIcmpType
                Integer32,
            aclNumExdSubitemIcmpCode
                Integer32,
            aclNumExdSubitemTcpEstablished
                TruthValue,
            aclNumExdSubitemPrecedence
                Integer32,
            aclNumExdSubitemTos
                TOSType,
            aclNumExdSubitemDscp
                Dscp,
            aclNumExdSubitemFragments
                TruthValue,
            aclNumExdSubitemTimeRange
                OCTET STRING,
            aclNumExdSubitemRowStatus
                RowStatus,
            aclNumExdAddressType
                Integer32,
            aclNumExdSrcAddrV6
                InetAddressIPv6,
            aclNumExdSrcAddrV6Wldmsk
                InetAddressIPv6,
            aclNumExdDstAddrV6
                InetAddressIPv6,
            aclNumExdDstAddrV6Wldmsk
               InetAddressIPv6,
            aclNumExdSubitemIgmpType
               Integer32,
            aclNumExdSubitemDefaultRoute
               TruthValue,
            aclNumExdSubitemL3IntfId
               Integer32
            }

    aclNumExdNum OBJECT-TYPE
        SYNTAX   Integer32  (100..199)
        MAX-ACCESS   read-only
        STATUS   current
        DESCRIPTION
            "The number of extended and number-based ACL subitem."
            --"基于数字的访问控制列表的标号，它的取值范围为1－399，1000-1999.
            --它的取值可以代表此条访问控制列表是属于何种类型。"
        ::= { aclNumExdSubitemEntry 1 }

    aclNumExdSubNum OBJECT-TYPE
        SYNTAX   Integer32 (0..127)
        MAX-ACCESS   read-only
        STATUS   current
        DESCRIPTION
            "The sequence number of extended and number-based ACL subitem."
            --"访问控制列表的子项号，0－127。"
        ::= { aclNumExdSubitemEntry 2 }

    aclNumExdSubitemAdminStatus OBJECT-TYPE
        SYNTAX   AdminStatus
        MAX-ACCESS   read-only
        STATUS   current
        DESCRIPTION
            "The admin status of extended and number-based ACL subitem."
            --"当此项为valid时激活一条访问控制列表，invalid表示只配置了此项
            --ACL但并没有下发到硬件开始执行。"
        DEFVAL { invalid }        -- invalid
       ::= { aclNumExdSubitemEntry 3 }

    aclNumExdSubitemAction OBJECT-TYPE
        SYNTAX   Action
        MAX-ACCESS   read-write
        STATUS   current
        DESCRIPTION
            "The action of extended and number-based ACL subitem."
            --"定义一条访问列表子项的动作，允许或拒绝。"
       ::= { aclNumExdSubitemEntry 4 }

    aclNumExdSubitemProtocal OBJECT-TYPE
        SYNTAX   Integer32 (1..255)
        MAX-ACCESS   read-write
        STATUS   current
        DESCRIPTION
            "The ip protocol type of extended and number-based ACL subitem."
            --"过滤某种协议类型的报文"
        ::= { aclNumExdSubitemEntry 5 }

    aclNumExdSubitemSrcAddr OBJECT-TYPE
        SYNTAX   IpAddress
        MAX-ACCESS   read-write
        STATUS   current
        DESCRIPTION
            "The source ip-address of extended and number-based ACL subitem."
            --"扩展访问控制列表子项的原地址"
       ::= { aclNumExdSubitemEntry 6 }

    aclNumExdSubitemSrcAddrWldmsk OBJECT-TYPE
        SYNTAX   IpAddress
        MAX-ACCESS   read-write
        STATUS   current
        DESCRIPTION
            "The source ip-address mask of extended and number-based ACL subitem."
            --"扩展访问控制列表子项的原地址通配符"
       ::= { aclNumExdSubitemEntry 7 }

    aclNumExdSubitemDstAddr OBJECT-TYPE
        SYNTAX   IpAddress
        MAX-ACCESS   read-write
        STATUS   current
        DESCRIPTION
            "The destination ip-address of extended and number-based ACL subitem."
            --"扩展访问控制列表子项的目的地址"
       ::= { aclNumExdSubitemEntry 8 }

    aclNumExdSubitemDstAddrWldmsk OBJECT-TYPE
        SYNTAX   IpAddress
        MAX-ACCESS   read-write
        STATUS   current
        DESCRIPTION
            "The destination ip-address mask of extended and number-based ACL subitem."
            --"扩展访问控制列表子项的目的地址通配符"
       ::= { aclNumExdSubitemEntry 9 }

    aclNumExdSubitemSrcPort OBJECT-TYPE
        SYNTAX   Integer32  (0..65535)
        MAX-ACCESS   read-write
        STATUS   current
        DESCRIPTION
            "The source TCP/UDP port of extended and number-based ACL subitem."
            --对UDP或TCP报文特定端口号的包进行过滤
       ::= { aclNumExdSubitemEntry 10 }

    aclNumExdSubitemSrcPortWldmsk OBJECT-TYPE
        SYNTAX   Integer32  (0..65535)
        MAX-ACCESS   read-write
        STATUS   current
        DESCRIPTION
            "The source TCP/UDP port mask of extended and number-based ACL subitem."
            --扩展访问控制列表子项的源端口号通配符
       ::= { aclNumExdSubitemEntry 11 }

    aclNumExdSubitemDstPort OBJECT-TYPE
        SYNTAX   Integer32  (0..65535)
        MAX-ACCESS   read-write
        STATUS   current
        DESCRIPTION
            "The destination TCP/UDP port of extended and number-based ACL subitem."
            --对UDP或TCP报文特定端口号的包进行过滤
       ::= { aclNumExdSubitemEntry 12 }

    aclNumExdSubitemDstPortWldmsk OBJECT-TYPE
        SYNTAX   Integer32  (0..65535)
        MAX-ACCESS   read-write
        STATUS   current
        DESCRIPTION
            "The destination TCP/UDP port mask of extended and number-based ACL subitem."
            --扩展访问控制列表子项的源端口号通配符
       ::= { aclNumExdSubitemEntry 13 }

    aclNumExdSubitemIcmpType OBJECT-TYPE
        SYNTAX   Integer32 (0..255)
        MAX-ACCESS   read-write
        STATUS   current
        DESCRIPTION
            "The ICMP type of extended and number-based ACL subitem."
            --"对ICMP的特定类型的包进行过滤"
       ::= { aclNumExdSubitemEntry 14 }

    aclNumExdSubitemIcmpCode OBJECT-TYPE
        SYNTAX   Integer32 (0..255)
        MAX-ACCESS   read-write
        STATUS   current
        DESCRIPTION
            "The ICMP code of extended and number-based ACL subitem."
            --"对ICMP的特定类型，特定代码的包进行过滤"
       ::= { aclNumExdSubitemEntry 15 }

    aclNumExdSubitemTcpEstablished OBJECT-TYPE
        SYNTAX   TruthValue
        MAX-ACCESS   read-write
        STATUS   current
        DESCRIPTION
            "The established TCP of extended and number-based ACL subitem."
            --"对TCP第一个建链的包进行过滤"
        DEFVAL { false }
       ::= { aclNumExdSubitemEntry 16 }

    aclNumExdSubitemPrecedence OBJECT-TYPE
        SYNTAX   Integer32 (0..7)
        MAX-ACCESS   read-write
        STATUS   current
        DESCRIPTION
            "The ip precedence of extended and number-based ACL subitem."
            --"对特定IP优先级的包进行过滤"
       ::= { aclNumExdSubitemEntry 17 }

    aclNumExdSubitemTos OBJECT-TYPE
        SYNTAX   TOSType
        MAX-ACCESS   read-write
        STATUS   current
        DESCRIPTION
            "The ip TOS of extended and number-based ACL subitem."
            --"对数据包中TOS字段等于特定值的包进行过滤"
       ::= { aclNumExdSubitemEntry 18 }

    aclNumExdSubitemDscp OBJECT-TYPE
        SYNTAX   Dscp
        MAX-ACCESS   read-write
        STATUS   current
        DESCRIPTION
            "The ip DSCP of extended and number-based ACL subitem."
            --"对数据包中DSCP字段等于特定值的包进行过滤"
       ::= { aclNumExdSubitemEntry 19 }

    aclNumExdSubitemFragments OBJECT-TYPE
        SYNTAX   TruthValue
        MAX-ACCESS   read-write
        STATUS   current
        DESCRIPTION
            "The ip fragments of extended and number-based ACL subitem."
            --"扩展访问控制列表子项的目的地址通配符"
        DEFVAL { false }        -- invalid
       ::= { aclNumExdSubitemEntry 20 }


    aclNumExdSubitemTimeRange OBJECT-TYPE
        SYNTAX   OCTET STRING (SIZE (0..32))
        MAX-ACCESS   read-write
        STATUS   current
        DESCRIPTION
            "The referred time range of extended and number-based ACL subitem."
            --"访问列表子项起作用的时间段"
        ::= { aclNumExdSubitemEntry 21 }

    aclNumExdSubitemRowStatus OBJECT-TYPE
        SYNTAX   RowStatus
        MAX-ACCESS   read-write
        STATUS   current
        DESCRIPTION
            "The row status of extended and number-based ACL subitem entry."
            --"表示当前ACL子项的状态，添加或删除。"
        ::= { aclNumExdSubitemEntry 22 }

    aclNumExdAddressType OBJECT-TYPE
        SYNTAX   Integer32 {
              ipv4(1),
              ipv6(2)
            }
        MAX-ACCESS   read-write
        STATUS   current
        DESCRIPTION
            "The ip-address type of extended and number-based ACL subitem."
            --"表示当前ACL子项的ip地址的类型。"
        ::= { aclNumExdSubitemEntry 23 }

    aclNumExdSrcAddrV6 OBJECT-TYPE
        SYNTAX   InetAddressIPv6
        MAX-ACCESS   read-write
        STATUS   current
        DESCRIPTION
            "The source ipv6-address of extended and number-based ACL subitem."
            --"表示当前ACL子项的源ipv6地址"
        ::= { aclNumExdSubitemEntry 24 }

    aclNumExdSrcAddrV6Wldmsk OBJECT-TYPE
        SYNTAX   InetAddressIPv6
        MAX-ACCESS   read-write
        STATUS   current
        DESCRIPTION
            "The source ipv6-address mask of extended and number-based ACL subitem."
            --"表示当前ACL子项的源ipv6地址的通配符"
        ::= { aclNumExdSubitemEntry 25 }

    aclNumExdDstAddrV6 OBJECT-TYPE
        SYNTAX   InetAddressIPv6
        MAX-ACCESS   read-write
        STATUS   current
        DESCRIPTION
            "The destination ipv6-address of extended and number-based ACL subitem."
            --"表示当前ACL子项的目的ipv6地址"
        ::= { aclNumExdSubitemEntry 26 }

    aclNumExdDstAddrV6Wldmsk OBJECT-TYPE
        SYNTAX   InetAddressIPv6
        MAX-ACCESS   read-write
        STATUS   current
        DESCRIPTION
            "The destination ipv6-address mask of extended and number-based ACL subitem."
            --"表示当前ACL子项的目的ipv6地址的通配符"
        ::= { aclNumExdSubitemEntry 27 }

     aclNumExdSubitemIgmpType OBJECT-TYPE
        SYNTAX   Integer32 (0..34)
        MAX-ACCESS   read-write
        STATUS   current
        DESCRIPTION
            "The IGMP type of extended and number-based ACL subitem."
        ::= { aclNumExdSubitemEntry 28 }

    aclNumExdSubitemDefaultRoute OBJECT-TYPE
        SYNTAX   TruthValue
        MAX-ACCESS   read-write
        STATUS   current
        DESCRIPTION
            "The default route of extended and number-based ACL subitem."
            --"扩展访问控制列表子项的默认路由"
        DEFVAL { false }        -- invalid
       ::= { aclNumExdSubitemEntry 29 }

    aclNumExdSubitemL3IntfId OBJECT-TYPE
        SYNTAX   Integer32
        MAX-ACCESS   read-write
        STATUS   current
        DESCRIPTION
            "The L3 interface type of extended and number-based ACL subitem."
       ::= { aclNumExdSubitemEntry 30 }

--ACL子项定义，基于数字的二层访问控制列表子项。

  aclNumLnkSubitemTable OBJECT-TYPE
        SYNTAX   SEQUENCE OF AclNumLnkSubitemEntry
        MAX-ACCESS   not-accessible
        STATUS   current
        DESCRIPTION
            "Link-based and number-based ACL subitem table."
            --"定义一条二层访问控制列表子项。"
       ::= { gbnL2QACL 5 }

    aclNumLnkSubitemEntry OBJECT-TYPE
        SYNTAX   AclNumLnkSubitemEntry
        MAX-ACCESS   not-accessible
        STATUS   current
        DESCRIPTION
            "The entry of link-based and number-based ACL subitem table."
            --"定义一条二层访问控制列表子项."
       INDEX { aclNumLnkNum, aclNumLnkSubNum}
       ::= { aclNumLnkSubitemTable 1 }

    AclNumLnkSubitemEntry ::=
        SEQUENCE {
            aclNumLnkNum
                Integer32,
            aclNumLnkSubNum
                Integer32,
            aclNumLnkSubitemAdminStatus
                AdminStatus,
            aclNumLnkSubitemAction
                Action,
            aclNumLnkSubitemProtocal
                Integer32,
            aclNumLnkSubitemCos
                Integer32,
            aclNumLnkSubitemSrcVlanID
                VlanId,
            aclNumLnkSubitemSrcMacAddr
                MacAddress,
            aclNumLnkSubitemSrcMacWldmsk
                MacAddress,
            aclNumLnkSubitemDstMacAddr
                MacAddress,
            aclNumLnkSubitemDstMacWldmsk
                MacAddress,
            aclNumLnkSubitemSrcPortNum
                Integer32,
            aclNumLnkSubitemDstPortNum
                Integer32,
            aclNumLnkSubitemTimeRange
                OCTET STRING,
            aclNumLnkSubitemRowStatus
                RowStatus,
            aclNumLnkSubitemSrcInnerTag
                Integer32,
            aclNumLnkSubitemSrcInnerVlanID
                VlanId,
            aclNumLnkSubitemSrcEndVlanID
                VlanId,
            }

    aclNumLnkNum OBJECT-TYPE
        SYNTAX   Integer32 (200..299)
        MAX-ACCESS   read-only
        STATUS   current
        DESCRIPTION
            "The number of link-based and number-based ACL subitem."
            --"基于数字的访问控制列表的标号，它的取值范围为1－399，1000-1999.
            --它的取值可以代表此条访问控制列表是属于何种类型。"
        ::= { aclNumLnkSubitemEntry 1 }

    aclNumLnkSubNum OBJECT-TYPE
        SYNTAX   Integer32 (0..127)
        MAX-ACCESS   read-only
        STATUS   current
        DESCRIPTION
            "The sequence number of link-based and number-based ACL subitem."
            --"访问控制列表的子项号，0－127。"
        ::= { aclNumLnkSubitemEntry 2 }

    aclNumLnkSubitemAdminStatus OBJECT-TYPE
        SYNTAX   AdminStatus
        MAX-ACCESS   read-only
        STATUS   current
        DESCRIPTION
            "The admin status of link-based and number-based ACL subitem."
            --"当此项为valid时激活一条访问控制列表，invalid表示只配置了此项
            --ACL但并没有下发到硬件开始执行。"
        DEFVAL { invalid }        -- invalid
       ::= { aclNumLnkSubitemEntry 3 }

    aclNumLnkSubitemAction OBJECT-TYPE
        SYNTAX   Action
        MAX-ACCESS   read-write
        STATUS   current
        DESCRIPTION
            "The action of link-based and number-based ACL subitem."
            --"定义一条访问列表子项的动作，允许或拒绝。"
       ::= { aclNumLnkSubitemEntry 4 }

    aclNumLnkSubitemProtocal OBJECT-TYPE
        SYNTAX   Integer32 (1..255)
        MAX-ACCESS   read-write
        STATUS   current
        DESCRIPTION
            "The ethernet protocal type of link-based and number-based ACL subitem."
            --"过滤某种协议类型的报文"
        ::= { aclNumLnkSubitemEntry 5 }

    aclNumLnkSubitemCos OBJECT-TYPE
        SYNTAX   Integer32 (0..7)
        MAX-ACCESS   read-write
        STATUS   current
        DESCRIPTION
            "The 802.1x COS type of link-based and number-based ACL subitem."
            --"802.1x优先级"
        ::= { aclNumLnkSubitemEntry 6 }

    aclNumLnkSubitemSrcVlanID OBJECT-TYPE
        SYNTAX   VlanId
        MAX-ACCESS   read-write
        STATUS   current
        DESCRIPTION
            "The source vlan of link-based and number-based ACL subitem."
            --"对VLAN ID为特定值的数据包进行过滤"
       ::= { aclNumLnkSubitemEntry 7 }

    aclNumLnkSubitemSrcMacAddr OBJECT-TYPE
        SYNTAX   MacAddress
        MAX-ACCESS   read-write
        STATUS   current
        DESCRIPTION
            "The source mac-address of link-based and number-based ACL subitem."
            --"它于MAC通配符共同作用得到感兴趣的源MAC地址，并对这些
            --MAC地址作处理。"
       ::= { aclNumLnkSubitemEntry 8 }

    aclNumLnkSubitemSrcMacWldmsk OBJECT-TYPE
        SYNTAX   MacAddress
        MAX-ACCESS   read-write
        STATUS   current
        DESCRIPTION
            "The source mac-address mask of link-based and number-based ACL subitem."
            --"它于MAC地址共同作用得到感兴趣的源MAC地址，并对这些
            --MAC地址作处理。"
       ::= { aclNumLnkSubitemEntry 9 }

    aclNumLnkSubitemDstMacAddr OBJECT-TYPE
        SYNTAX   MacAddress
        MAX-ACCESS   read-write
        STATUS   current
        DESCRIPTION
            "The destination mac-address of link-based and number-based ACL subitem."
            --"它于MAC通配符共同作用得到感兴趣的目的MAC地址，并对这些
            --MAC地址作处理。"
       ::= { aclNumLnkSubitemEntry 10 }

    aclNumLnkSubitemDstMacWldmsk OBJECT-TYPE
        SYNTAX   MacAddress
        MAX-ACCESS   read-write
        STATUS   current
        DESCRIPTION
            "The destination mac-address mask of link-based and number-based ACL subitem."
            --"它于MAC地址共同作用得到感兴趣的目的MAC地址，并对这些
            --MAC地址作处理。"
       ::= { aclNumLnkSubitemEntry 11 }

    aclNumLnkSubitemSrcPortNum OBJECT-TYPE
        SYNTAX   Integer32   (1..26)
        MAX-ACCESS   read-write
        STATUS   current
        DESCRIPTION
            "The source port of link-based and number-based ACL subitem."
       ::= { aclNumLnkSubitemEntry 12 }

    aclNumLnkSubitemDstPortNum OBJECT-TYPE
        SYNTAX   Integer32   (1..29)
        MAX-ACCESS   read-write
        STATUS   current
        DESCRIPTION
            "The destination port of link-based and number-based ACL subitem."
       ::= { aclNumLnkSubitemEntry 13 }

    aclNumLnkSubitemTimeRange OBJECT-TYPE
        SYNTAX   OCTET STRING (SIZE (0..32))
        MAX-ACCESS   read-write
        STATUS   current
        DESCRIPTION
            "The referred time range of link-based and number-based ACL subitem."
            --"访问列表子项起作用的时间段"
        ::= { aclNumLnkSubitemEntry 14 }

    aclNumLnkSubitemRowStatus OBJECT-TYPE
        SYNTAX   RowStatus
        MAX-ACCESS   read-write
        STATUS   current
        DESCRIPTION
            "The row status of link-based and number-based ACL subitem entry."
            --"表示当前ACL子项的状态，添加或删除。"
        ::= { aclNumLnkSubitemEntry 15 }

    aclNumLnkSubitemSrcInnerTag OBJECT-TYPE
        SYNTAX   Integer32 (0..65535)
        MAX-ACCESS   read-write
        STATUS   current
        DESCRIPTION
            "The source inner tag of link-based and number-based ACL subitem."
            --"对inner tag为特定值的数据包进行过滤"
       ::= { aclNumLnkSubitemEntry 16 }

    aclNumLnkSubitemSrcInnerVlanID OBJECT-TYPE
        SYNTAX   VlanId
        MAX-ACCESS   read-write
        STATUS   current
        DESCRIPTION
            "The source inner vlan of link-based and number-based ACL subitem."
            --"对inner VLAN ID为特定值的数据包进行过滤"
       ::= { aclNumLnkSubitemEntry 17 }

    aclNumLnkSubitemSrcEndVlanID OBJECT-TYPE
        SYNTAX   VlanId
        MAX-ACCESS   read-write
        STATUS   current
        DESCRIPTION
            "The source end vlan of link-based and number-based ACL subitem."
            --"对VLAN ID为特定值的数据包进行过滤"
       ::= { aclNumLnkSubitemEntry 18 }

 --ACL子项定义，基于数字的自定义访问控制列表子项。

  aclNumUserSubitemTable OBJECT-TYPE
        SYNTAX   SEQUENCE OF AclNumUserSubitemEntry
        MAX-ACCESS   not-accessible
        STATUS   current
        DESCRIPTION
            "User defined and number-based ACL subitem table."
            --"定义一条自定义访问控制列表子项。它是通过目的地址进行过滤的。"
       ::= { gbnL2QACL 6 }

    aclNumUserSubitemEntry OBJECT-TYPE
        SYNTAX   AclNumUserSubitemEntry
        MAX-ACCESS   not-accessible
        STATUS   current
        DESCRIPTION
            "The entry of user defined and number-based ACL subitem table."
            --"定义一条标准访问控制列表子项."
       INDEX { aclNumUserNum, aclNumUserSubNum }
       ::= { aclNumUserSubitemTable 1 }

    AclNumUserSubitemEntry ::=
        SEQUENCE {
            aclNumUserNum
                Integer32,
            aclNumUserSubNum
                Integer32,
            aclNumUserSubitemAdminStatus
                AdminStatus,
            aclNumUserSubitemAction
                Action,
            aclNumUserSubitemSrcPortNum
                Integer32,
            aclNumUserSubitemDstPortNum
                Integer32,
            aclNumUserSubitemRule
                OCTET STRING,
            aclNumUserSubitemMask
                OCTET STRING,
            aclNumUserTimeRange
                OCTET STRING,
            aclNumUserSubitemRowStatus
                RowStatus
            }

    aclNumUserNum OBJECT-TYPE
        SYNTAX   Integer32  (300..399)
        MAX-ACCESS   read-only
        STATUS   current
        DESCRIPTION
            "The number of user defined and number-based ACL subitem."
            --"基于数字的访问控制列表的标号，它的取值范围为1－399，1000-1999.
            --它的取值可以代表此条访问控制列表是属于何种类型。"
        ::= { aclNumUserSubitemEntry 1 }

    aclNumUserSubNum OBJECT-TYPE
        SYNTAX   Integer32 (0..127)
        MAX-ACCESS   read-only
        STATUS   current
        DESCRIPTION
            "The sequence number of user defined and number-based ACL subitem."
            --"访问控制列表的子项号，0－127。"
        ::= { aclNumUserSubitemEntry 2 }

    aclNumUserSubitemAdminStatus OBJECT-TYPE
        SYNTAX   AdminStatus
        MAX-ACCESS   read-only
        STATUS   current
        DESCRIPTION
            "The admin status of user defined and number-based ACL subitem."
            --"当此项为valid时激活一条访问控制列表，invalid表示只配置了此项
            --ACL但并没有下发到硬件开始执行。"
        DEFVAL { invalid }        -- invalid
       ::= { aclNumUserSubitemEntry 3 }

    aclNumUserSubitemAction OBJECT-TYPE
        SYNTAX   Action
        MAX-ACCESS   read-write
        STATUS   current
        DESCRIPTION
            "The action of user defined and number-based ACL subitem."
            --"定义一条访问列表子项的动作，允许或拒绝。"
       ::= { aclNumUserSubitemEntry 4 }

    aclNumUserSubitemSrcPortNum OBJECT-TYPE
        SYNTAX   Integer32
        MAX-ACCESS   read-write
        STATUS   current
        DESCRIPTION
            "The source port of user defined and number-based ACL subitem."
       ::= { aclNumUserSubitemEntry 5 }

    aclNumUserSubitemDstPortNum OBJECT-TYPE
        SYNTAX   Integer32   (1..29)
        MAX-ACCESS   read-write
        STATUS   current
        DESCRIPTION
            "The destination port of user defined and number-based ACL subitem."
       ::= { aclNumUserSubitemEntry 6 }

    aclNumUserSubitemRule OBJECT-TYPE
        SYNTAX   OCTET STRING (SIZE (0..160))
        MAX-ACCESS   read-write
        STATUS   current
        DESCRIPTION
            "The match rule of user defined and number-based ACL subitem."
            --"用户自定义访问控制列表子项的匹配字符串"
       ::= { aclNumUserSubitemEntry 7 }

    aclNumUserSubitemMask OBJECT-TYPE
        SYNTAX   OCTET STRING (SIZE (0..160))
        MAX-ACCESS   read-write
        STATUS   current
        DESCRIPTION
            "The match mask of user defined and number-based ACL subitem."
            --"用户自定义访问控制列表子项的匹配字符串掩码"
       ::= { aclNumUserSubitemEntry 8 }

    aclNumUserTimeRange OBJECT-TYPE
        SYNTAX   OCTET STRING (SIZE (0..32))
        MAX-ACCESS   read-write
        STATUS   current
        DESCRIPTION
            "The referred time range of user defined and number-based ACL subitem."
            --"访问列表子项起作用的时间段"
        ::= { aclNumUserSubitemEntry 9 }

    aclNumUserSubitemRowStatus OBJECT-TYPE
        SYNTAX   RowStatus
        MAX-ACCESS   read-write
        STATUS   current
        DESCRIPTION
            "The row status of user defined and number-based ACL subitem entry."
            --"表示当前ACL子项的状态，添加或删除。"
        ::= { aclNumUserSubitemEntry 10 }

--基于名字的访问控制列表定义
 aclNamedTable OBJECT-TYPE
        SYNTAX   SEQUENCE OF AclNamedEntry
        MAX-ACCESS   not-accessible
        STATUS   current
        DESCRIPTION
            "Name-based ACL table."
            --"基于名字的访问控制列表，它一共由四种类型：基于名字的标准访问控制列表、
            --基于数名字的扩展访问列表、基于名字的二层访问控制列表、基于名字的自定义访
            --问控制列表."
       ::= { gbnL2QACL 7 }

    aclNamedEntry OBJECT-TYPE
        SYNTAX   AclNamedEntry
        MAX-ACCESS   not-accessible
        STATUS   current
        DESCRIPTION
            "The entry of name-based ACL table."
            --"定义一条基于名字的访问控制列表."
       INDEX { aclNamedName }
       ::= { aclNamedTable 1 }

    AclNamedEntry ::=
        SEQUENCE {
            aclNamedName
                OCTET STRING,
            aclNamedType
                AclType,
            aclNamedMatchOrder
                INTEGER,
            aclNamedTotleSubitems
                Integer32,
            aclNamedRowStatus
                RowStatus
                  }

    aclNamedName OBJECT-TYPE
        SYNTAX   OCTET STRING (SIZE (0..32))
        MAX-ACCESS   read-only
        STATUS   current
        DESCRIPTION
            "The name of name-based ACL."
            --"基于名字的访问控制列表的名字，各个访问控制列表（包括不同类
            --型的访问控制列表）不能重名。"
        ::= { aclNamedEntry 1 }

    aclNamedType OBJECT-TYPE
        SYNTAX   AclType
        MAX-ACCESS   read-write
        STATUS   current
        DESCRIPTION
            "The type of name-based ACL: standard, extended or link-based."
            --"基于名字的访问控制列表的类型，同基于数字的ACL，但它的类型不由名字决定"
        ::= { aclNamedEntry 2 }


    aclNamedMatchOrder OBJECT-TYPE
        SYNTAX   INTEGER    {
                    config (0),
                    auto (1)
                    }
        MAX-ACCESS   read-write
        STATUS   current
        DESCRIPTION
            "The match order of name-based ACL."
            --"定义一条访问控制列表的配置顺序，auto 所用的“深度优先“
            --原则是指：把指定数据包范围最小的语句排在最前面。这一点可以
            --通过比较地址的通配符来实现，通配符越小，则指定的主机的范围
            --就越小。比如129.102.1.1 0.0.0.0 指定了一台主机：129.102.1.1
            --而129.102.1.1 0.0.255.255 则指定了一个网段： 129.102.1.1 ～
            --129.102.255.255，显然前者在访问控制规则中排在前面。具体标准
            --为：对于标准访问控制规则的语句，直接比较源地址通配符，通配符
            --相同的则按配置顺序；对于基于接口过滤的访问控制规则，配置了'any'
            --的规则排在后面，其它按配置顺序；对于扩展访问控制规则，首先比
            --较源地址通配符，相同的再比较目的地址通配符，仍相同的则比较端
            --口号的范围，范围小的排在前面，如果端口号范围也相同则按配置顺序，
            --默认按照用户的配置顺序即config。"
        DEFVAL { config }        -- config
      ::= { aclNamedEntry 3 }

    aclNamedTotleSubitems OBJECT-TYPE
        SYNTAX   Integer32
        MAX-ACCESS   read-only
        STATUS   current
        DESCRIPTION
            "The total subitems of name-based ACL."
            --"一条访问控制列表可以定义多条子规则，这些子规则按照一定的顺序排列
            --成一条访问控制列表，每条ACL最多可以定义128项子规则。"
        ::= { aclNamedEntry 4 }

    aclNamedRowStatus OBJECT-TYPE
        SYNTAX   RowStatus
        MAX-ACCESS   read-write
        STATUS   current
        DESCRIPTION
            "The row status of name-based ACL."
            --"表示当前ACL的状态，添加或删除。"
        ::= { aclNamedEntry 5 }

 --ACL子项定义，基于名字的标准访问控制列表子项。

  aclNamedStdSubitemTable OBJECT-TYPE
        SYNTAX   SEQUENCE OF AclNamedStdSubitemEntry
        MAX-ACCESS   not-accessible
        STATUS   current
        DESCRIPTION
            "Standard and name-based ACL subitem table."
            --"定义一条标准访问控制列表子项。它是通过目的地址进行过滤的。"
       ::= { gbnL2QACL 8 }

    aclNamedStdSubitemEntry OBJECT-TYPE
        SYNTAX   AclNamedStdSubitemEntry
        MAX-ACCESS   not-accessible
        STATUS   current
        DESCRIPTION
            "The entry of standard and name-based ACL subitem table."
            --"定义一条标准访问控制列表子项."
       INDEX { aclNamedStdName, aclNamedStdSubNum }
       ::= { aclNamedStdSubitemTable 1 }

    AclNamedStdSubitemEntry ::=
        SEQUENCE {
            aclNamedStdName
                OCTET STRING,
            aclNamedStdSubNum
                Integer32,
            aclNamedStdSubitemAdminStatus
                AdminStatus,
            aclNamedStdSubitemAction
                Action,
            aclNamedStdSubitemSrcAddr
                IpAddress,
            aclNamedStdSubitemSrcAddrWldmsk
                IpAddress,
            aclNamedStdFragments
                TruthValue,
            aclNamedStdTimeRange
                OCTET STRING,
            aclNamedStdSubitemRowStatus
                RowStatus,
            aclNamedStdAddressType
                Integer32,
            aclNamedStdSrcAddrV6
               InetAddressIPv6,
            aclNamedStdSrcAddrV6Wldmsk
               InetAddressIPv6,
            aclNamedStdDefaultRoute
                TruthValue,
            aclNamedStdL3IntfId
                Integer32
            }

    aclNamedStdName OBJECT-TYPE
        SYNTAX   OCTET STRING (SIZE (0..32))
        MAX-ACCESS   read-only
        STATUS   current
        DESCRIPTION
            "The name of standard and name-based ACL subitem."
            --"基于名字的访问控制列表的名字，它是一个最多32个字符组成的字符串"
        ::= { aclNamedStdSubitemEntry 1 }

    aclNamedStdSubNum OBJECT-TYPE
        SYNTAX   Integer32 (0..127)
        MAX-ACCESS   read-only
        STATUS   current
        DESCRIPTION
            "The sequence number of standard and name-based ACL subitem."
            --"访问控制列表的子项号，0－127。"
        ::= { aclNamedStdSubitemEntry 2 }

    aclNamedStdSubitemAdminStatus OBJECT-TYPE
        SYNTAX   AdminStatus
        MAX-ACCESS   read-only
        STATUS   current
        DESCRIPTION
            "The admin status of standard and name-based ACL subitem."
            --"当此项为valid时激活一条访问控制列表，invalid表示只配置了此项
            --ACL但并没有下发到硬件开始执行。"
        DEFVAL { invalid }        -- invalid
       ::= { aclNamedStdSubitemEntry 3 }

    aclNamedStdSubitemAction OBJECT-TYPE
        SYNTAX   Action
        MAX-ACCESS   read-write
        STATUS   current
        DESCRIPTION
            "The action of standard and name-based ACL subitem."
            --"定义一条访问列表子项的动作，允许或拒绝。"
       ::= { aclNamedStdSubitemEntry 4 }

    aclNamedStdSubitemSrcAddr OBJECT-TYPE
        SYNTAX   IpAddress
        MAX-ACCESS   read-write
        STATUS   current
        DESCRIPTION
            "The source ip-address of standard and name-based ACL subitem."
            --"标准访问控制列表子项的原地址"
       ::= { aclNamedStdSubitemEntry 5 }

    aclNamedStdSubitemSrcAddrWldmsk OBJECT-TYPE
        SYNTAX   IpAddress
        MAX-ACCESS   read-write
        STATUS   current
        DESCRIPTION
            "The source ip-address mask of standard and name-based ACL subitem."
            --"标准访问控制列表子项的原地址通配符"
       ::= { aclNamedStdSubitemEntry 6 }

    aclNamedStdFragments OBJECT-TYPE
        SYNTAX   TruthValue
        MAX-ACCESS   read-write
        STATUS   current
        DESCRIPTION
            "The ip fragments of standard and name-based ACL subitem."
            --"标准访问控制列表子项的原地址通配符"
        DEFVAL { false }        -- invalid
       ::= { aclNamedStdSubitemEntry 7 }


    aclNamedStdTimeRange OBJECT-TYPE
        SYNTAX   OCTET STRING (SIZE (0..256))
        MAX-ACCESS   read-write
        STATUS   current
        DESCRIPTION
            "The referred time range of standard and name-based ACL subitem."
            --"访问列表子项起作用的时间段"
        ::= { aclNamedStdSubitemEntry 8 }

    aclNamedStdSubitemRowStatus OBJECT-TYPE
        SYNTAX   RowStatus
        MAX-ACCESS   read-write
        STATUS   current
        DESCRIPTION
            "The row status of standard and name-based ACL subitem entry."
            --"表示当前ACL子项的状态，添加或删除。"
        ::= { aclNamedStdSubitemEntry 9 }

    aclNamedStdAddressType OBJECT-TYPE
        SYNTAX   Integer32 {
              ipv4(1),
              ipv6(2)
            }
        MAX-ACCESS   read-write
        STATUS   current
        DESCRIPTION
            "The ip-address type of standard and name-based ACL subitem."
            --"表示当前ACL子项的ip地址的类型。"
        ::= { aclNamedStdSubitemEntry 10 }

    aclNamedStdSrcAddrV6 OBJECT-TYPE
        SYNTAX   InetAddressIPv6
        MAX-ACCESS   read-write
        STATUS   current
        DESCRIPTION
            "The source ipv6-address of standard and name-based ACL subitem."
            --"表示当前ACL子项的源ipv6地址"
        ::= { aclNamedStdSubitemEntry 11 }

    aclNamedStdSrcAddrV6Wldmsk OBJECT-TYPE
        SYNTAX   InetAddressIPv6
        MAX-ACCESS   read-write
        STATUS   current
        DESCRIPTION
            "The source ipv6-address mask of standard and name-based ACL subitem."
            --"表示当前ACL子项的源ipv6地址的通配符"
        ::= { aclNamedStdSubitemEntry 12 }

    aclNamedStdDefaultRoute OBJECT-TYPE
        SYNTAX   TruthValue
        MAX-ACCESS   read-write
        STATUS   current
        DESCRIPTION
            "The default route of standard and name-based ACL subitem."
            --"标准访问控制列表子项的默认路由"
        DEFVAL { false }        -- invalid
       ::= { aclNamedStdSubitemEntry 13 }

    aclNamedStdL3IntfId OBJECT-TYPE
        SYNTAX   Integer32
        MAX-ACCESS   read-write
        STATUS   current
        DESCRIPTION
            "The L3 interface type of standard and name-based ACL subitem."
       ::= { aclNamedStdSubitemEntry 14 }

--ACL子项定义，基于名字的扩展访问控制列表子项。

  aclNamedExdSubitemTable OBJECT-TYPE
        SYNTAX   SEQUENCE OF AclNamedExdSubitemEntry
        MAX-ACCESS   not-accessible
        STATUS   current
        DESCRIPTION
            "Extended and name-based ACL subitem table."
            --"定义一条扩展访问控制列表子项。它是通过对标准访问控制列表的补充。"
       ::= { gbnL2QACL 9 }

    aclNamedExdSubitemEntry OBJECT-TYPE
        SYNTAX   AclNamedExdSubitemEntry
        MAX-ACCESS   not-accessible
        STATUS   current
        DESCRIPTION
            "The entry of extended and name-based ACL subitem table."
            --"定义一条标准访问控制列表子项."
       INDEX { aclNamedExdName, aclNamedExdSubNum}
       ::= { aclNamedExdSubitemTable 1 }

    AclNamedExdSubitemEntry ::=
        SEQUENCE {
            aclNamedExdName
                OCTET STRING,
            aclNamedExdSubNum
                Integer32,
            aclNamedExdSubitemAdminStatus
                AdminStatus,
            aclNamedExdSubitemAction
                Action,
            aclNamedExdSubitemProtocal
                Integer32,
            aclNamedExdSubitemSrcAddr
                IpAddress,
            aclNamedExdSubitemSrcAddrWldmsk
                IpAddress,
            aclNamedExdSubitemDstAddr
                IpAddress,
            aclNamedExdSubitemDstAddrWldmsk
                IpAddress,
            aclNamedExdSubitemSrcPort
                Integer32,
            aclNamedExdSubitemSrcPortWldmsk
                Integer32,
            aclNamedExdSubitemDstPort
                Integer32,
            aclNamedExdSubitemDstPortWldmsk
                Integer32,
            aclNamedExdSubitemIcmpType
                Integer32,
            aclNamedExdSubitemIcmpCode
                Integer32,
            aclNamedExdSubitemTcpEstablished
                TruthValue,
            aclNamedExdSubitemPrecedence
                Integer32,
            aclNamedExdSubitemTos
                TOSType,
            aclNamedExdSubitemDscp
                Dscp,
            aclNamedExdSubitemFragments
                TruthValue,
            aclNamedExdSubitemTimeRange
                OCTET STRING,
            aclNamedExdSubitemRowStatus
                RowStatus,
            aclNamedExdAddressType
                Integer32,
            aclNamedExdSrcAddrV6
                InetAddressIPv6,
            aclNamedExdSrcAddrV6Wldmsk
                InetAddressIPv6,
            aclNamedExdDstAddrV6
                InetAddressIPv6,
            aclNamedExdDstAddrV6Wldmsk
               InetAddressIPv6,
            aclNamedExdSubitemIgmpType
               Integer32,
            aclNamedExdSubitemDefaultRoute
               TruthValue,
            aclNamedExdSubitemL3IntfId
            	 Integer32
            }

    aclNamedExdName OBJECT-TYPE
        SYNTAX   OCTET STRING (SIZE (0..32))
        MAX-ACCESS   read-only
        STATUS   current
        DESCRIPTION
            "The name of extended and name-based ACL subitem."
            --"基于名字的访问控制列表的名字，它是一个最多32个字符组成的字符串"
        ::= { aclNamedExdSubitemEntry 1 }

    aclNamedExdSubNum OBJECT-TYPE
        SYNTAX   Integer32 (0..127)
        MAX-ACCESS   read-only
        STATUS   current
        DESCRIPTION
            "The sequence number of extended and name-based ACL subitem."
            --"访问控制列表的子项号，0－127。"
        ::= { aclNamedExdSubitemEntry 2 }

    aclNamedExdSubitemAdminStatus OBJECT-TYPE
        SYNTAX   AdminStatus
        MAX-ACCESS   read-only
        STATUS   current
        DESCRIPTION
            "The admin status of extended and name-based ACL subitem."
            --"当此项为valid时激活一条访问控制列表，invalid表示只配置了此项
            --ACL但并没有下发到硬件开始执行。"
        DEFVAL { invalid }        -- invalid
       ::= { aclNamedExdSubitemEntry 3 }

    aclNamedExdSubitemAction OBJECT-TYPE
        SYNTAX   Action
        MAX-ACCESS   read-write
        STATUS   current
        DESCRIPTION
            "The action of extended and name-based ACL subitem."
            --"定义一条访问列表子项的动作，允许或拒绝。"
       ::= { aclNamedExdSubitemEntry 4 }

    aclNamedExdSubitemProtocal OBJECT-TYPE
        SYNTAX   Integer32 (1..255)
        MAX-ACCESS   read-write
        STATUS   current
        DESCRIPTION
            "The ip protocol type of extended and name-based ACL subitem."
            --"过滤某种协议类型的报文"
        ::= { aclNamedExdSubitemEntry 5 }

    aclNamedExdSubitemSrcAddr OBJECT-TYPE
        SYNTAX   IpAddress
        MAX-ACCESS   read-write
        STATUS   current
        DESCRIPTION
            "The source ip-address of extended and name-based ACL subitem."
            --"扩展访问控制列表子项的原地址"
       ::= { aclNamedExdSubitemEntry 6 }

    aclNamedExdSubitemSrcAddrWldmsk OBJECT-TYPE
        SYNTAX   IpAddress
        MAX-ACCESS   read-write
        STATUS   current
        DESCRIPTION
            "The source ip-address mask of extended and name-based ACL subitem."
            --"扩展访问控制列表子项的原地址通配符"
       ::= { aclNamedExdSubitemEntry 7 }

    aclNamedExdSubitemDstAddr OBJECT-TYPE
        SYNTAX   IpAddress
        MAX-ACCESS   read-write
        STATUS   current
        DESCRIPTION
            "The destination ip-address of extended and name-based ACL subitem."
            --"扩展访问控制列表子项的目的地址"
       ::= { aclNamedExdSubitemEntry 8 }

    aclNamedExdSubitemDstAddrWldmsk OBJECT-TYPE
        SYNTAX   IpAddress
        MAX-ACCESS   read-write
        STATUS   current
        DESCRIPTION
            "The destination ip-address mask of extended and name-based ACL subitem."
            --"扩展访问控制列表子项的目的地址通配符"
       ::= { aclNamedExdSubitemEntry 9 }

    aclNamedExdSubitemSrcPort OBJECT-TYPE
        SYNTAX   Integer32  (0..65535)
        MAX-ACCESS   read-write
        STATUS   current
        DESCRIPTION
            "The source TCP/UDP port of extended and name-based ACL subitem."
            --对UDP或TCP报文特定端口号的包进行过滤
       ::= { aclNamedExdSubitemEntry 10 }

    aclNamedExdSubitemSrcPortWldmsk OBJECT-TYPE
        SYNTAX   Integer32  (0..65535)
        MAX-ACCESS   read-write
        STATUS   current
        DESCRIPTION
            "The source TCP/UDP port mask of extended and name-based ACL subitem."
            --扩展访问控制列表子项的源端口号通配符
       ::= { aclNamedExdSubitemEntry 11 }

    aclNamedExdSubitemDstPort OBJECT-TYPE
        SYNTAX   Integer32  (0..65535)
        MAX-ACCESS   read-write
        STATUS   current
        DESCRIPTION
            "The destination TCP/UDP port of extended and name-based ACL subitem."
            --对UDP或TCP报文特定端口号的包进行过滤
       ::= { aclNamedExdSubitemEntry 12 }

    aclNamedExdSubitemDstPortWldmsk OBJECT-TYPE
        SYNTAX   Integer32  (0..65535)
        MAX-ACCESS   read-write
        STATUS   current
        DESCRIPTION
            "The destination TCP/UDP port mask of extended and name-based ACL subitem."
            --扩展访问控制列表子项的目的端口号通配符
       ::= { aclNamedExdSubitemEntry 13 }

    aclNamedExdSubitemIcmpType OBJECT-TYPE
        SYNTAX   Integer32 (0..255)
        MAX-ACCESS   read-write
        STATUS   current
        DESCRIPTION
            "The ICMP type of extended and name-based ACL subitem."
            --"对ICMP的特定类型的包进行过滤"
       ::= { aclNamedExdSubitemEntry 14 }

    aclNamedExdSubitemIcmpCode OBJECT-TYPE
        SYNTAX   Integer32 (0..255)
        MAX-ACCESS   read-write
        STATUS   current
        DESCRIPTION
            "The ICMP code of extended and name-based ACL subitem."
            --"对ICMP的特定类型，特定代码的包进行过滤"
       ::= { aclNamedExdSubitemEntry 15 }

    aclNamedExdSubitemTcpEstablished OBJECT-TYPE
        SYNTAX   TruthValue
        MAX-ACCESS   read-write
        STATUS   current
        DESCRIPTION
            "The established TCP of extended and name-based ACL subitem."
            --"对TCP第一个建链的包进行过滤"
        DEFVAL { false }        -- invalid
       ::= { aclNamedExdSubitemEntry 16 }

    aclNamedExdSubitemPrecedence OBJECT-TYPE
        SYNTAX   Integer32 (0..7)
        MAX-ACCESS   read-write
        STATUS   current
        DESCRIPTION
            "The ip precedence of extended and name-based ACL subitem."
            --"对特定IP优先级的包进行过滤"
       ::= { aclNamedExdSubitemEntry 17 }

    aclNamedExdSubitemTos OBJECT-TYPE
        SYNTAX   TOSType
        MAX-ACCESS   read-write
        STATUS   current
        DESCRIPTION
            "The ip TOS of extended and name-based ACL subitem."
            --"对数据包中TOS字段等于特定值的包进行过滤"
       ::= { aclNamedExdSubitemEntry 18 }

    aclNamedExdSubitemDscp OBJECT-TYPE
        SYNTAX   Dscp
        MAX-ACCESS   read-write
        STATUS   current
        DESCRIPTION
            "The ip DSCP of extended and name-based ACL subitem."
            --"对数据包中DSCP字段等于特定值的包进行过滤"
       ::= { aclNamedExdSubitemEntry 19 }

    aclNamedExdSubitemFragments OBJECT-TYPE
        SYNTAX   TruthValue
        MAX-ACCESS   read-write
        STATUS   current
        DESCRIPTION
            "The ip fragments of extended and name-based ACL subitem."
        DEFVAL { false }
       ::= { aclNamedExdSubitemEntry 20 }


    aclNamedExdSubitemTimeRange OBJECT-TYPE
        SYNTAX   OCTET STRING (SIZE (0..256))
        MAX-ACCESS   read-write
        STATUS   current
        DESCRIPTION
            "The referred time range of extended and name-based ACL subitem."
            --"访问列表子项起作用的时间段"
        ::= { aclNamedExdSubitemEntry 21 }

    aclNamedExdSubitemRowStatus OBJECT-TYPE
        SYNTAX   RowStatus
        MAX-ACCESS   read-write
        STATUS   current
        DESCRIPTION
            "The row status of extended and name-based ACL subitem entry."
            --"表示当前ACL子项的状态，添加或删除。"
        ::= { aclNamedExdSubitemEntry 22 }

    aclNamedExdAddressType OBJECT-TYPE
        SYNTAX   Integer32 {
              ipv4(1),
              ipv6(2)
            }
        MAX-ACCESS   read-write
        STATUS   current
        DESCRIPTION
            "The ip-address type of extended and name-based ACL subitem."
            --"表示当前ACL子项的ip地址的类型。"
        ::= { aclNamedExdSubitemEntry 23 }

    aclNamedExdSrcAddrV6 OBJECT-TYPE
        SYNTAX   InetAddressIPv6
        MAX-ACCESS   read-write
        STATUS   current
        DESCRIPTION
            "The source ipv6-address of extended and name-based ACL subitem."
            --"表示当前ACL子项的源ipv6地址"
        ::= { aclNamedExdSubitemEntry 24 }

    aclNamedExdSrcAddrV6Wldmsk OBJECT-TYPE
        SYNTAX   InetAddressIPv6
        MAX-ACCESS   read-write
        STATUS   current
        DESCRIPTION
            "The source ipv6-address mask of extended and name-based ACL subitem."
            --"表示当前ACL子项的源ipv6地址的通配符"
        ::= { aclNamedExdSubitemEntry 25 }

    aclNamedExdDstAddrV6 OBJECT-TYPE
        SYNTAX   InetAddressIPv6
        MAX-ACCESS   read-write
        STATUS   current
        DESCRIPTION
            "The destination ipv6-address of extended and name-based ACL subitem."
            --"表示当前ACL子项的目的ipv6地址"
        ::= { aclNamedExdSubitemEntry 26 }

    aclNamedExdDstAddrV6Wldmsk OBJECT-TYPE
        SYNTAX   InetAddressIPv6
        MAX-ACCESS   read-write
        STATUS   current
        DESCRIPTION
            "The destination ipv6-address mask of extended and name-based ACL subitem."
            --"表示当前ACL子项的目的ipv6地址的通配符"
        ::= { aclNamedExdSubitemEntry 27 }

    aclNamedExdSubitemIgmpType OBJECT-TYPE
        SYNTAX   Integer32 (0..34)
        MAX-ACCESS   read-write
        STATUS   current
        DESCRIPTION
           "The IGMP type of extended and name-based ACL subitem."
        ::= { aclNamedExdSubitemEntry 28 }

    aclNamedExdSubitemDefaultRoute OBJECT-TYPE
        SYNTAX   TruthValue
        MAX-ACCESS   read-write
        STATUS   current
        DESCRIPTION
            "The default route of extended and name-based ACL subitem."
        DEFVAL { false }
       ::= { aclNamedExdSubitemEntry 29 }

    aclNamedExdSubitemL3IntfId OBJECT-TYPE
        SYNTAX   Integer32
        MAX-ACCESS   read-write
        STATUS   current
        DESCRIPTION
            "The L3 interface type of extended and name-based ACL subitem."
       ::= { aclNamedExdSubitemEntry 30 }

--ACL子项定义，基于名字的二层访问控制列表子项。

  aclNamedLnkSubitemTable OBJECT-TYPE
        SYNTAX   SEQUENCE OF AclNamedLnkSubitemEntry
        MAX-ACCESS   not-accessible
        STATUS   current
        DESCRIPTION
            "Link-based and name-based ACL subitem table."
            --"定义一条二层访问控制列表子项。"
       ::= { gbnL2QACL 10 }

    aclNamedLnkSubitemEntry OBJECT-TYPE
        SYNTAX   AclNamedLnkSubitemEntry
        MAX-ACCESS   not-accessible
        STATUS   current
        DESCRIPTION
            "The entry of link-based and name-based ACL subitem table."
            --"定义一条二层访问控制列表子项."
       INDEX { aclNamedLnkName, aclNamedLnkSubNum}
       ::= { aclNamedLnkSubitemTable 1 }

    AclNamedLnkSubitemEntry ::=
        SEQUENCE {
            aclNamedLnkName
                OCTET STRING,
            aclNamedLnkSubNum
                Integer32,
            aclNamedLnkSubitemAdminStatus
                AdminStatus,
            aclNamedLnkSubitemAction
                Action,
            aclNamedLnkSubitemProtocal
                Integer32,
            aclNamedLnkSubitemCos
                Integer32,
            aclNamedLnkSubitemSrcVlanID
                VlanId,
            aclNamedLnkSubitemSrcMacAddr
                MacAddress,
            aclNamedLnkSubitemSrcMacWldmsk
                MacAddress,
            aclNamedLnkSubitemDstMacAddr
                MacAddress,
            aclNamedLnkSubitemDstMacWldmsk
                MacAddress,
            aclNamedLnkSubitemSrcPortNum
                Integer32,
            aclNamedLnkSubitemDstPortNum
                Integer32,
            aclNamedLnkSubitemTimeRange
                OCTET STRING,
            aclNamedLnkSubitemRowStatus
                RowStatus,
            aclNamedLnkSubitemSrcInnerTag
                Integer32,
            aclNamedLnkSubitemSrcInnerVlanID
                VlanId,
            aclNamedLnkSubitemSrcEndVlanID
                VlanId,
            }

    aclNamedLnkName OBJECT-TYPE
        SYNTAX   OCTET STRING (SIZE (0..32))
        MAX-ACCESS   read-only
        STATUS   current
        DESCRIPTION
            "The name of link-based and name-based ACL subitem."
            --"基于名字的访问控制列表的名字，它是一个最多32个字符组成的字符串"
        ::= { aclNamedLnkSubitemEntry 1 }

    aclNamedLnkSubNum OBJECT-TYPE
        SYNTAX   Integer32 (0..127)
        MAX-ACCESS   read-only
        STATUS   current
        DESCRIPTION
            "The sequence number of link-based and name-based ACL subitem."
            --"访问控制列表的子项号，0－127。"
        ::= { aclNamedLnkSubitemEntry 2 }

    aclNamedLnkSubitemAdminStatus OBJECT-TYPE
        SYNTAX   AdminStatus
        MAX-ACCESS   read-only
        STATUS   current
        DESCRIPTION
            "The admin status of link-based and name-based ACL subitem."
            --"当此项为valid时激活一条访问控制列表，invalid表示只配置了此项
            --ACL但并没有下发到硬件开始执行。"
        DEFVAL { invalid }        -- invalid
       ::= { aclNamedLnkSubitemEntry 3 }

    aclNamedLnkSubitemAction OBJECT-TYPE
        SYNTAX   Action
        MAX-ACCESS   read-write
        STATUS   current
        DESCRIPTION
            "The action of link-based and name-based ACL subitem."
            --"定义一条访问列表子项的动作，允许或拒绝。"
       ::= { aclNamedLnkSubitemEntry 4 }

    aclNamedLnkSubitemProtocal OBJECT-TYPE
        SYNTAX   Integer32 (1..255)
        MAX-ACCESS   read-write
        STATUS   current
        DESCRIPTION
            "The protocol type of link-based and name-based ACL subitem."
            --"过滤某种协议类型的报文"
        ::= { aclNamedLnkSubitemEntry 5 }

    aclNamedLnkSubitemCos OBJECT-TYPE
        SYNTAX   Integer32 (0..7)
        MAX-ACCESS   read-write
        STATUS   current
        DESCRIPTION
            "The cos type of link-based and name-based ACL subitem."
            --"过滤某种协议类型的报文"
        ::= { aclNamedLnkSubitemEntry 6 }

    aclNamedLnkSubitemSrcVlanID OBJECT-TYPE
        SYNTAX   VlanId
        MAX-ACCESS   read-write
        STATUS   current
        DESCRIPTION
            "The source vlan of link-based and name-based ACL subitem."
            --"对VLAN ID为特定值的数据包进行过滤"
       ::= { aclNamedLnkSubitemEntry 7 }

    aclNamedLnkSubitemSrcMacAddr OBJECT-TYPE
        SYNTAX   MacAddress
        MAX-ACCESS   read-write
        STATUS   current
        DESCRIPTION
            "The source mac-address of link-based and name-based ACL subitem."
            --"它于MAC通配符共同作用得到感兴趣的源MAC地址，并对这些MAC地址作处理。"
       ::= { aclNamedLnkSubitemEntry 8 }

    aclNamedLnkSubitemSrcMacWldmsk OBJECT-TYPE
        SYNTAX   MacAddress
        MAX-ACCESS   read-write
        STATUS   current
        DESCRIPTION
            "The source mac-address mask of link-based and name-based ACL subitem."
            --"它于MAC地址共同作用得到感兴趣的源MAC地址，并对这些MAC地址作处理。"
       ::= { aclNamedLnkSubitemEntry 9 }

    aclNamedLnkSubitemDstMacAddr OBJECT-TYPE
        SYNTAX   MacAddress
        MAX-ACCESS   read-write
        STATUS   current
        DESCRIPTION
            "The destination mac-address of link-based and name-based ACL subitem."
            --"它于MAC通配符共同作用得到感兴趣的目的MAC地址，并对这些MAC地址作处理。"
       ::= { aclNamedLnkSubitemEntry 10 }

    aclNamedLnkSubitemDstMacWldmsk OBJECT-TYPE
        SYNTAX   MacAddress
        MAX-ACCESS   read-write
        STATUS   current
        DESCRIPTION
            "The destination mac-address mask of link-based and name-based ACL subitem."
            --"它于MAC地址共同作用得到感兴趣的目的MAC地址，并对这些MAC地址作处理。"
       ::= { aclNamedLnkSubitemEntry 11 }

    aclNamedLnkSubitemSrcPortNum OBJECT-TYPE
        SYNTAX   Integer32    (1..26)
        MAX-ACCESS   read-write
        STATUS   current
        DESCRIPTION
            "The source port of link-based and name-based ACL subitem."
       ::= { aclNamedLnkSubitemEntry 12 }

    aclNamedLnkSubitemDstPortNum OBJECT-TYPE
        SYNTAX   Integer32       (1..29)
        MAX-ACCESS   read-write
        STATUS   current
        DESCRIPTION
            "The destination port of link-based and name-based ACL subitem."
       ::= { aclNamedLnkSubitemEntry 13 }

    aclNamedLnkSubitemTimeRange OBJECT-TYPE
        SYNTAX   OCTET STRING (SIZE (0..32))
        MAX-ACCESS   read-write
        STATUS   current
        DESCRIPTION
            "The referred time range of link-based and name-based ACL subitem."
            --"访问列表子项起作用的时间段"
        ::= { aclNamedLnkSubitemEntry 14 }

    aclNamedLnkSubitemRowStatus OBJECT-TYPE
        SYNTAX   RowStatus
        MAX-ACCESS   read-write
        STATUS   current
        DESCRIPTION
            "The row status of link-based and name-based ACL subitem entry."
            --"表示当前ACL子项的状态，添加或删除。"
        ::= { aclNamedLnkSubitemEntry 15 }

    aclNamedLnkSubitemSrcInnerTag OBJECT-TYPE
        SYNTAX   Integer32 (0..65535)
        MAX-ACCESS   read-write
        STATUS   current
        DESCRIPTION
            "The source inner tag of link-based and name-based ACL subitem."
            --"对inner tag为特定值的数据包进行过滤"
       ::= { aclNamedLnkSubitemEntry 16 }

    aclNamedLnkSubitemSrcInnerVlanID OBJECT-TYPE
        SYNTAX   VlanId
        MAX-ACCESS   read-write
        STATUS   current
        DESCRIPTION
            "The source inner vlan of link-based and name-based ACL subitem."
            --"对inner VLAN ID为特定值的数据包进行过滤"
       ::= { aclNamedLnkSubitemEntry 17 }

    aclNamedLnkSubitemSrcEndVlanID OBJECT-TYPE
        SYNTAX   VlanId
        MAX-ACCESS   read-write
        STATUS   current
        DESCRIPTION
            "The source end vlan of link-based and name-based ACL subitem."
            --"对VLAN ID为特定值的数据包进行过滤"
       ::= { aclNamedLnkSubitemEntry 18 }

 --ACL子项定义，基于名字的自定义访问控制列表子项。

  aclNamedUserSubitemTable OBJECT-TYPE
        SYNTAX   SEQUENCE OF AclNamedUserSubitemEntry
        MAX-ACCESS   not-accessible
        STATUS   current
        DESCRIPTION
            "User defined and name-based ACL subitem table."
            --"定义一条自定义访问控制列表子项。它是通过目的地址进行过滤的。"
       ::= { gbnL2QACL 11 }

    aclNamedUserSubitemEntry OBJECT-TYPE
        SYNTAX   AclNamedUserSubitemEntry
        MAX-ACCESS   not-accessible
        STATUS   current
        DESCRIPTION
            "The entry of user defined and name-based ACL subitem table."
            --"定义一条标准访问控制列表子项."
       INDEX { aclNamedUserName, aclNamedUserSubNum }
       ::= { aclNamedUserSubitemTable 1 }

    AclNamedUserSubitemEntry ::=
        SEQUENCE {
            aclNamedUserName
                OCTET STRING,
            aclNamedUserSubNum
                Integer32,
            aclNamedUserSubitemAdminStatus
                AdminStatus,
            aclNamedUserSubitemAction
                Action,
            aclNamedUserSubitemSrcPortNum
                Integer32,
            aclNamedUserSubitemDstPortNum
                Integer32,
            aclNamedUserSubitemRule
                OCTET STRING,
            aclNamedUserSubitemMask
                OCTET STRING,
            aclNamedUserTimeRange
                OCTET STRING,
            aclNamedUserSubitemRowStatus
                RowStatus
            }

    aclNamedUserName OBJECT-TYPE
        SYNTAX   OCTET STRING (SIZE (0..32))
        MAX-ACCESS   read-only
        STATUS   current
        DESCRIPTION
            "The name of user defined and name-based ACL subitem."
            --"基于名字的访问控制列表的名字，它是一个最多32个字符组成的字符串"
        ::= { aclNamedUserSubitemEntry 1 }

    aclNamedUserSubNum OBJECT-TYPE
        SYNTAX   Integer32 (0..127)
        MAX-ACCESS   read-only
        STATUS   current
        DESCRIPTION
            "The sequence number of user defined and name-based ACL subitem."
            --"访问控制列表的子项号，0－127。"
        ::= { aclNamedUserSubitemEntry 2 }

    aclNamedUserSubitemAdminStatus OBJECT-TYPE
        SYNTAX   AdminStatus
        MAX-ACCESS   read-only
        STATUS   current
        DESCRIPTION
            "The admin status of user defined and name-based ACL subitem."
            --"当此项为valid时激活一条访问控制列表，invalid表示只配置了此项
            --ACL但并没有下发到硬件开始执行。"
        DEFVAL { invalid }        -- invalid
       ::= { aclNamedUserSubitemEntry 3 }

    aclNamedUserSubitemAction OBJECT-TYPE
        SYNTAX   Action
        MAX-ACCESS   read-write
        STATUS   current
        DESCRIPTION
            "The action of user defined and name-based ACL subitem."
            --"定义一条访问列表子项的动作，允许或拒绝。"
       ::= { aclNamedUserSubitemEntry 4 }

    aclNamedUserSubitemSrcPortNum OBJECT-TYPE
        SYNTAX   Integer32
        MAX-ACCESS   read-write
        STATUS   current
        DESCRIPTION
            "The source port of user defined and name-based ACL subitem."
       ::= { aclNamedUserSubitemEntry 5 }

    aclNamedUserSubitemDstPortNum OBJECT-TYPE
        SYNTAX   Integer32   (1..29)
        MAX-ACCESS   read-write
        STATUS   current
        DESCRIPTION
            "The destination port of user defined and name-based ACL subitem."
       ::= { aclNamedUserSubitemEntry 6 }

    aclNamedUserSubitemRule OBJECT-TYPE
        SYNTAX   OCTET STRING (SIZE (0..160))
        MAX-ACCESS   read-write
        STATUS   current
        DESCRIPTION
            "The match rule of user defined and name-based ACL subitem."
            --"用户自定义访问控制列表子项的匹配字符串"
       ::= { aclNamedUserSubitemEntry 7 }

    aclNamedUserSubitemMask OBJECT-TYPE
        SYNTAX   OCTET STRING (SIZE (0..160))
        MAX-ACCESS   read-write
        STATUS   current
        DESCRIPTION
            "The match mask of user defined and name-based ACL subitem."
            --"用户自定义访问控制列表子项的匹配字符串掩码"
       ::= { aclNamedUserSubitemEntry 8 }

    aclNamedUserTimeRange OBJECT-TYPE
        SYNTAX   OCTET STRING (SIZE (0..256))
        MAX-ACCESS   read-write
        STATUS   current
        DESCRIPTION
            "The referred time range of user defined and name-based ACL subitem."
            --"访问列表子项起作用的时间段"
        ::= { aclNamedUserSubitemEntry 9 }

    aclNamedUserSubitemRowStatus OBJECT-TYPE
        SYNTAX   RowStatus
        MAX-ACCESS   read-write
        STATUS   current
        DESCRIPTION
            "The row status of user defined and name-based ACL subitem entry."
            --"表示当前ACL子项的状态，添加或删除。"
        ::= { aclNamedUserSubitemEntry 10 }

--时间段定义
 aclTimeRangeTable OBJECT-TYPE
        SYNTAX   SEQUENCE OF AclTimeRangeEntry
        MAX-ACCESS   not-accessible
        STATUS   current
        DESCRIPTION
            "Time range table."
       ::= { gbnL2QACL 12 }

    aclTimeRangeEntry OBJECT-TYPE
        SYNTAX   AclTimeRangeEntry
        MAX-ACCESS   not-accessible
        STATUS   current
        DESCRIPTION
            "The entry of time range table."
            --"定义一条时间段."
       INDEX { aclTimeRangeName }
       ::= { aclTimeRangeTable 1 }

    AclTimeRangeEntry ::=
        SEQUENCE {
            aclTimeRangeName
                OCTET STRING,
            aclTimeRangeTotleAbsolutes
                Integer32,
            aclTimeRangeTotlePeriods
                Integer32,
            aclTimeRangeActive
                TruthValue,
            aclTimeRangeRowStatus
                RowStatus
                  }

    aclTimeRangeName OBJECT-TYPE
        SYNTAX   OCTET STRING (SIZE (0..32))
        MAX-ACCESS   read-only
        STATUS   current
        DESCRIPTION
            "The name of time range."
            --"时间段的名字"
        ::= { aclTimeRangeEntry 1 }

    aclTimeRangeTotleAbsolutes OBJECT-TYPE
      SYNTAX   Integer32
        MAX-ACCESS   read-only
        STATUS   current
        DESCRIPTION
            "The total number of absolute time ranges."
            --"一个时间段最多可以配置12个绝对时间段，这里为已经配置的绝对时间段的数目"
        DEFVAL { invalid }        -- invalid
       ::= { aclTimeRangeEntry 2 }

    aclTimeRangeTotlePeriods OBJECT-TYPE
        SYNTAX   Integer32
        MAX-ACCESS   read-only
        STATUS   current
        DESCRIPTION
            "The total number of period time ranges."
            --"一个时间段最多可以配置32个周期时间段，这里为已经配置的周期时间段的数目"
        ::= { aclTimeRangeEntry 3 }

    aclTimeRangeActive OBJECT-TYPE
       SYNTAX   TruthValue
       MAX-ACCESS   read-only
       STATUS   current
       DESCRIPTION
            "The active status of time range."
            --"时间段的激活状态"
      ::= { aclTimeRangeEntry 4 }

    aclTimeRangeRowStatus OBJECT-TYPE
        SYNTAX   RowStatus
        MAX-ACCESS   read-write
        STATUS   current
        DESCRIPTION
            "The row status of time range entry."
            --"表示当前时间段的状态，添加或删除。"
        ::= { aclTimeRangeEntry 5 }

 --绝对时间段定义。

  aclTimeRangeAbsoluteTable OBJECT-TYPE
        SYNTAX   SEQUENCE OF AclTimeRangeAbsoluteEntry
        MAX-ACCESS   not-accessible
        STATUS   current
        DESCRIPTION
            "Absolute time range table."
            --"定义一个绝对时间段"
       ::= { gbnL2QACL 13 }

    aclTimeRangeAbsoluteEntry OBJECT-TYPE
        SYNTAX   AclTimeRangeAbsoluteEntry
        MAX-ACCESS   not-accessible
        STATUS   current
        DESCRIPTION
            "The entry of absolute time range table."
            --"定义一条绝对时间段."
       INDEX { aclTimeRangeAbsoluteName, aclTimeRangeAbsoluteStartTime,
               aclTimeRangeAbsoluteEndTime }
       ::= { aclTimeRangeAbsoluteTable 1 }

    AclTimeRangeAbsoluteEntry ::=
        SEQUENCE {
            aclTimeRangeAbsoluteName
                OCTET STRING,
            aclTimeRangeAbsoluteStartTime
                Unsigned32,
            aclTimeRangeAbsoluteEndTime
                Unsigned32,
            aclTimeRangeAbsoluteRowStatus
                RowStatus
            }

    aclTimeRangeAbsoluteName OBJECT-TYPE
        SYNTAX   OCTET STRING (SIZE (0..32))
        MAX-ACCESS   read-only
        STATUS   current
        DESCRIPTION
            "The name of absolute time range."
            --"时间段的名字"
        ::= { aclTimeRangeAbsoluteEntry 1 }

    aclTimeRangeAbsoluteStartTime OBJECT-TYPE
        SYNTAX   Unsigned32
        MAX-ACCESS   read-only
        STATUS   current
        DESCRIPTION
            "The start time of absolute time range."
            --"绝对时间段起始时间(日历时间)"
        ::= { aclTimeRangeAbsoluteEntry 2 }

    aclTimeRangeAbsoluteEndTime OBJECT-TYPE
        SYNTAX   Unsigned32
        MAX-ACCESS   read-only
        STATUS   current
        DESCRIPTION
            "The end time of absolute time range."
            --"绝对时间段终止时间的年份"
        ::= { aclTimeRangeAbsoluteEntry 3 }

    aclTimeRangeAbsoluteRowStatus OBJECT-TYPE
        SYNTAX   RowStatus
        MAX-ACCESS   read-write
        STATUS   current
        DESCRIPTION
            "The row status of absolute time range entry."
            --"绝对时间段的当前状态"
        ::= { aclTimeRangeAbsoluteEntry 4 }

 --周期时间段定义。

  aclTimeRangePeriodTable OBJECT-TYPE
        SYNTAX   SEQUENCE OF AclTimeRangePeriodEntry
        MAX-ACCESS   not-accessible
        STATUS   current
        DESCRIPTION
            "Period time range table."
            --"定义一个周期时间段"
       ::= { gbnL2QACL 14 }

    aclTimeRangePeriodEntry OBJECT-TYPE
        SYNTAX   AclTimeRangePeriodEntry
        MAX-ACCESS   not-accessible
        STATUS   current
        DESCRIPTION
            "The entry of period time range table."
            --"定义一条周期时间段."
       INDEX { aclTimeRangePeriodName, aclTimeRangePeriodStartWeekDay,
               aclTimeRangePeriodStartHour, aclTimeRangePeriodStartMin,
               aclTimeRangePeriodEndWeekDay, aclTimeRangePeriodEndHour,
               aclTimeRangePeriodEndMin }
       ::= { aclTimeRangePeriodTable 1 }

    AclTimeRangePeriodEntry ::=
        SEQUENCE {
            aclTimeRangePeriodName
                OCTET STRING,
            aclTimeRangePeriodStartWeekDay
                Unsigned32,
            aclTimeRangePeriodStartHour
                Unsigned32,
            aclTimeRangePeriodStartMin
                Unsigned32,
            aclTimeRangePeriodEndWeekDay
                Unsigned32,
            aclTimeRangePeriodEndHour
                Unsigned32,
            aclTimeRangePeriodEndMin
                Unsigned32,
            aclTimeRangePeriodRowStatus
                RowStatus
            }

    aclTimeRangePeriodName OBJECT-TYPE
        SYNTAX   OCTET STRING (SIZE (0..32))
        MAX-ACCESS   read-only
        STATUS   current
        DESCRIPTION
            "The name of period time range."
            --"时间段的名字"
        ::= { aclTimeRangePeriodEntry 1 }

    aclTimeRangePeriodStartWeekDay OBJECT-TYPE
        SYNTAX   Unsigned32
        MAX-ACCESS   read-only
        STATUS   current
        DESCRIPTION
            "The start week day of period time range."
            --"周期时间段起始时间的日期（星期几）"
        ::= { aclTimeRangePeriodEntry 2 }

    aclTimeRangePeriodStartHour OBJECT-TYPE
        SYNTAX   Unsigned32
        MAX-ACCESS   read-only
        STATUS   current
        DESCRIPTION
            "The start hour of period time range."
            --"周期时间段的起始时间（几点）"
       ::= { aclTimeRangePeriodEntry 3 }

    aclTimeRangePeriodStartMin OBJECT-TYPE
        SYNTAX   Unsigned32
        MAX-ACCESS   read-only
        STATUS   current
        DESCRIPTION
            "The start minute of period time range."
            --"周期时间段的起始时间（几分）"
       ::= { aclTimeRangePeriodEntry 4 }

    aclTimeRangePeriodEndWeekDay OBJECT-TYPE
        SYNTAX   Unsigned32
        MAX-ACCESS   read-only
        STATUS   current
        DESCRIPTION
            "The end week day of period time range."
            --"周期时间段终止时间的日期（星期几）"
        ::= { aclTimeRangePeriodEntry 5 }

    aclTimeRangePeriodEndHour OBJECT-TYPE
        SYNTAX   Unsigned32
        MAX-ACCESS   read-only
        STATUS   current
        DESCRIPTION
            "The end hour of period time range."
            --"周期时间段的终止时间（几点）"
       ::= { aclTimeRangePeriodEntry 6 }

    aclTimeRangePeriodEndMin OBJECT-TYPE
        SYNTAX   Unsigned32
        MAX-ACCESS   read-only
        STATUS   current
        DESCRIPTION
            "The end minute of period time range."
            --"周期时间段的终止时间（几分）"
       ::= { aclTimeRangePeriodEntry 7 }

    aclTimeRangePeriodRowStatus OBJECT-TYPE
        SYNTAX   RowStatus
        MAX-ACCESS   read-write
        STATUS   current
        DESCRIPTION
            "The row status of period time range entry."
            --"周期时间段的当前状态"
        ::= { aclTimeRangePeriodEntry 8 }

    -----------------------------------------------------
    -- the active ACL group
    -----------------------------------------------------

    aclActiveTable OBJECT-TYPE
        SYNTAX  SEQUENCE OF AclActiveEntry
        ACCESS  not-accessible
        STATUS  current
        DESCRIPTION
                "A list of active acl entries. "
        ::= { gbnL2QACL 15 }

    aclActiveEntry OBJECT-TYPE
        SYNTAX  AclActiveEntry
        ACCESS  not-accessible
        STATUS  current
        DESCRIPTION
                "A list of active acl entries. "
        INDEX   { aclActiveIndex }
        ::= { aclActiveTable 1 }

    AclActiveEntry ::=
        SEQUENCE {
            aclActiveIndex
                INTEGER,
            aclActiveUserGroupName
                OCTET STRING,
            aclActiveUserGroupSubitem
                INTEGER,
            aclActiveIpGroupName
                OCTET STRING,
            aclActiveIpGroupSubitem
                INTEGER,
            aclActiveLinkGroupName
                OCTET STRING,
            aclActiveLinkGroupSubitem
                INTEGER,
            aclActiveBlock0Priority
                INTEGER,
            aclActiveBlock1Priority
                INTEGER,
            aclActiveBlock2Priority
                INTEGER,
            aclActiveBlock3Priority
                INTEGER,
            aclActiveBlock4Priority
                INTEGER,
            aclActiveConfigSequence
                INTEGER,
            aclActiveRunning
                TruthValue,
            aclActiveRowStatus
                RowStatus,
            aclActiveBlock5Priority
                INTEGER,
            aclActiveBlock6Priority
                INTEGER,
            aclActiveBlock7Priority
                INTEGER,
            aclActiveBlock8Priority
                INTEGER,
            aclActiveBlock9Priority
                INTEGER,
            aclActiveBlock10Priority
                INTEGER,
            aclActiveBlock11Priority
                INTEGER,
            aclActiveDirection
               INTEGER,
            aclActiveInterface
               INTEGER
        }

    aclActiveIndex OBJECT-TYPE
        SYNTAX  INTEGER
        ACCESS  read-only
        STATUS  current
        DESCRIPTION
                "A unique value for each active acl.  "
        ::= { aclActiveEntry 1 }

    aclActiveUserGroupName OBJECT-TYPE
        SYNTAX  OCTET STRING (SIZE (0..31))
        ACCESS  read-write
        STATUS  current
        DESCRIPTION
                "the name of the active user group acl. "
        ::= { aclActiveEntry 2 }

    aclActiveUserGroupSubitem OBJECT-TYPE
        SYNTAX  INTEGER(0..127)
        ACCESS  read-write
        STATUS  current
        DESCRIPTION
                "the number of the active user group acl subitem. "
        ::= { aclActiveEntry 3 }

    aclActiveIpGroupName OBJECT-TYPE
        SYNTAX  OCTET STRING (SIZE (0..31))
        ACCESS  read-write
        STATUS  current
        DESCRIPTION
                "the name of the active ip group acl. "
        ::= { aclActiveEntry 4 }

    aclActiveIpGroupSubitem OBJECT-TYPE
        SYNTAX  INTEGER(0..127)
        ACCESS  read-write
        STATUS  current
        DESCRIPTION
                "the number of the active ip group acl subitem. "
        ::= { aclActiveEntry 5 }

    aclActiveLinkGroupName OBJECT-TYPE
        SYNTAX  OCTET STRING (SIZE (0..31))
        ACCESS  read-write
        STATUS  current
        DESCRIPTION
                "the name of the active link group acl. "
        ::= { aclActiveEntry 6 }

    aclActiveLinkGroupSubitem OBJECT-TYPE
        SYNTAX  INTEGER(0..127)
        ACCESS  read-write
        STATUS  current
        DESCRIPTION
                "the number of the active link group acl subitem. "
        ::= { aclActiveEntry 7 }

    aclActiveBlock0Priority OBJECT-TYPE
        SYNTAX  INTEGER(0..16)
        ACCESS  read-only
        STATUS  current
        DESCRIPTION
                "the block 0 priority of the active ACL. 16 means no filter rules in the Hardware."
        ::= { aclActiveEntry 8 }

    aclActiveBlock1Priority OBJECT-TYPE
        SYNTAX  INTEGER(0..16)
        ACCESS  read-only
        STATUS  current
        DESCRIPTION
                "the block 1 priority of the active ACL. 16 means no filter rules in the Hardware."
        ::= { aclActiveEntry 9 }

    aclActiveBlock2Priority OBJECT-TYPE
        SYNTAX  INTEGER(0..16)
        ACCESS  read-only
        STATUS  current
        DESCRIPTION
                "the block 2 priority of the active ACL. 16 means no filter rules in the Hardware."
        ::= { aclActiveEntry 10 }

    aclActiveBlock3Priority OBJECT-TYPE
        SYNTAX  INTEGER(0..16)
        ACCESS  read-only
        STATUS  current
        DESCRIPTION
                "the block 3 priority of the active ACL. 16 means no filter rules in the Hardware."
        ::= { aclActiveEntry 11 }

    aclActiveBlock4Priority OBJECT-TYPE
        SYNTAX  INTEGER(0..16)
        ACCESS  read-only
        STATUS  current
        DESCRIPTION
                "the block 4 priority of the active ACL. 16 means no filter rules in the Hardware."
        ::= { aclActiveEntry 12 }

    aclActiveConfigSequence OBJECT-TYPE
        SYNTAX  INTEGER(1..1024)
        ACCESS  read-only
        STATUS  current
        DESCRIPTION
                "the config sequence of the active ACL."
        ::= { aclActiveEntry 13 }

    aclActiveRunning OBJECT-TYPE
        SYNTAX   TruthValue
        MAX-ACCESS   read-only
        STATUS   current
        DESCRIPTION
           "the running status of the active ACL."
       ::= { aclActiveEntry 14 }

    aclActiveRowStatus OBJECT-TYPE
        SYNTAX      RowStatus
        MAX-ACCESS  read-create
        STATUS      current
        DESCRIPTION
            "This object indicates the status of this entry."
        ::= { aclActiveEntry 15 }

    aclActiveBlock5Priority OBJECT-TYPE
        SYNTAX  INTEGER(0..16)
        ACCESS  read-only
        STATUS  current
        DESCRIPTION
                "the block 5 priority of the active ACL. 16 means no filter rules in the Hardware."
                --激活ACL在block 5中的优先级，16表示没有过滤规则在硬件中
        ::= { aclActiveEntry 16 }

    aclActiveBlock6Priority OBJECT-TYPE
        SYNTAX  INTEGER(0..16)
        ACCESS  read-only
        STATUS  current
        DESCRIPTION
                "the block 6 priority of the active ACL. 16 means no filter rules in the Hardware."
                --激活ACL在block 6中的优先级，16表示没有过滤规则在硬件中
        ::= { aclActiveEntry 17 }

    aclActiveBlock7Priority OBJECT-TYPE
        SYNTAX  INTEGER(0..16)
        ACCESS  read-only
        STATUS  current
        DESCRIPTION
                "the block 7 priority of the active ACL. 16 means no filter rules in the Hardware."
                --激活ACL在block 7中的优先级，16表示没有过滤规则在硬件中
        ::= { aclActiveEntry 18 }

    aclActiveBlock8Priority OBJECT-TYPE
        SYNTAX  INTEGER(0..16)
        ACCESS  read-only
        STATUS  current
        DESCRIPTION
                "the block 8 priority of the active ACL. 16 means no filter rules in the Hardware."
                --激活ACL在block 8中的优先级，16表示没有过滤规则在硬件中
        ::= { aclActiveEntry 19 }

    aclActiveBlock9Priority OBJECT-TYPE
        SYNTAX  INTEGER(0..16)
        ACCESS  read-only
        STATUS  current
        DESCRIPTION
                "the block 9 priority of the active ACL. 16 means no filter rules in the Hardware."
                --激活ACL在block 9中的优先级，16表示没有过滤规则在硬件中
        ::= { aclActiveEntry 20 }

    aclActiveBlock10Priority OBJECT-TYPE
        SYNTAX  INTEGER(0..16)
        ACCESS  read-only
        STATUS  current
        DESCRIPTION
                "the block 10 priority of the active ACL. 16 means no filter rules in the Hardware."
                --激活ACL在block 10中的优先级，16表示没有过滤规则在硬件中
        ::= { aclActiveEntry 21 }

    aclActiveBlock11Priority OBJECT-TYPE
        SYNTAX  INTEGER(0..16)
        ACCESS  read-only
        STATUS  current
        DESCRIPTION
                "the block 11 priority of the active ACL. 16 means no filter rules in the Hardware."
                --激活ACL在block 11中的优先级，16表示没有过滤规则在硬件中
        ::= { aclActiveEntry 22 }

    aclActiveDirection OBJECT-TYPE
        SYNTAX  INTEGER {
                    inbound(0),
                    outbound(1)
                }
        ACCESS  read-write
        STATUS  current
        DESCRIPTION
                "ingress/egress of rule.default is inbound"
                --入口/出口acl，默认为入口。
        ::= { aclActiveEntry 23 }

    aclActiveInterface OBJECT-TYPE
        SYNTAX  INTEGER
        ACCESS  read-write
        STATUS  current
        DESCRIPTION
                "the interface of referenced acl, 0 indicates the global reference."
                --引用acl的端口，为0表示全局引用。
        ::= { aclActiveEntry 24 }

    -----------------------------------------------------
    -- the mirror-to QOS group
    -----------------------------------------------------

    qosMirrorToTable OBJECT-TYPE
        SYNTAX  SEQUENCE OF QosMirrorToEntry
        ACCESS  not-accessible
        STATUS  current
        DESCRIPTION
                "A list of mirror-to QOS entries. "
        ::= { gbnL2QACL 16 }

    qosMirrorToEntry OBJECT-TYPE
        SYNTAX  QosMirrorToEntry
        ACCESS  not-accessible
        STATUS  current
        DESCRIPTION
                "A list of mirror-to QOS entries. "
        INDEX   { qosMirrorToIndex }
        ::= { qosMirrorToTable 1 }

    QosMirrorToEntry ::=
        SEQUENCE {
            qosMirrorToIndex
                INTEGER,
            qosMirrorToUserGroupName
                OCTET STRING,
            qosMirrorToUserGroupSubitem
                INTEGER,
            qosMirrorToIpGroupName
                OCTET STRING,
            qosMirrorToIpGroupSubitem
                INTEGER,
            qosMirrorToLinkGroupName
                OCTET STRING,
            qosMirrorToLinkGroupSubitem
                INTEGER,
            qosMirrorToInterface
                INTEGER,
            qosMirrorToBlock0Priority
                INTEGER,
            qosMirrorToBlock1Priority
                INTEGER,
            qosMirrorToBlock2Priority
                INTEGER,
            qosMirrorToBlock3Priority
                INTEGER,
            qosMirrorToBlock4Priority
                INTEGER,
            qosMirrorToConfigSequence
                INTEGER,
            qosMirrorToRunning
                TruthValue,
            qosMirrorToRowStatus
                RowStatus,
            qosMirrorToBlock5Priority
                INTEGER,
            qosMirrorToBlock6Priority
                INTEGER,
            qosMirrorToBlock7Priority
                INTEGER,
            qosMirrorToBlock8Priority
                INTEGER,
            qosMirrorToBlock9Priority
                INTEGER,
            qosMirrorToBlock10Priority
                INTEGER,
            qosMirrorToBlock11Priority
                INTEGER
        }

    qosMirrorToIndex OBJECT-TYPE
        SYNTAX  INTEGER
        ACCESS  read-only
        STATUS  current
        DESCRIPTION
                "A unique value for each mirror-to QOS.  "
        ::= { qosMirrorToEntry 1 }

    qosMirrorToUserGroupName OBJECT-TYPE
        SYNTAX  OCTET STRING (SIZE (0..31))
        ACCESS  read-write
        STATUS  current
        DESCRIPTION
                "the name of the mirror-to QOS user group acl. "
        ::= { qosMirrorToEntry 2 }

    qosMirrorToUserGroupSubitem OBJECT-TYPE
        SYNTAX  INTEGER(0..127)
        ACCESS  read-write
        STATUS  current
        DESCRIPTION
                "the number of the mirror-to QOS user group acl subitem. "
        ::= { qosMirrorToEntry 3 }

    qosMirrorToIpGroupName OBJECT-TYPE
        SYNTAX  OCTET STRING (SIZE (0..31))
        ACCESS  read-write
        STATUS  current
        DESCRIPTION
                "the name of the mirror-to QOS ip group acl. "
        ::= { qosMirrorToEntry 4 }

    qosMirrorToIpGroupSubitem OBJECT-TYPE
        SYNTAX  INTEGER(0..127)
        ACCESS  read-write
        STATUS  current
        DESCRIPTION
                "the number of the mirror-to QOS ip group acl subitem. "
        ::= { qosMirrorToEntry 5 }

    qosMirrorToLinkGroupName OBJECT-TYPE
        SYNTAX  OCTET STRING (SIZE (0..31))
        ACCESS  read-write
        STATUS  current
        DESCRIPTION
                "the name of the mirror-to QOS link group acl. "
        ::= { qosMirrorToEntry 6 }

    qosMirrorToLinkGroupSubitem OBJECT-TYPE
        SYNTAX  INTEGER(0..127)
        ACCESS  read-write
        STATUS  current
        DESCRIPTION
                "the number of the mirror-to QOS link group acl subitem. "
        ::= { qosMirrorToEntry 7 }

    qosMirrorToInterface OBJECT-TYPE
        SYNTAX  INTEGER (1..26)
        ACCESS  read-write
        STATUS  current
        DESCRIPTION
                "the mirror-to interface of the mirror-to QOS. "
        ::= { qosMirrorToEntry 8 }

    qosMirrorToBlock0Priority OBJECT-TYPE
        SYNTAX  INTEGER(0..16)
        ACCESS  read-only
        STATUS  current
        DESCRIPTION
                "the block 0 priority of the mirror-to QOS. 16 means no filter rules in the Hardware."
        ::= { qosMirrorToEntry 9 }

    qosMirrorToBlock1Priority OBJECT-TYPE
        SYNTAX  INTEGER(0..16)
        ACCESS  read-only
        STATUS  current
        DESCRIPTION
                "the block 1 priority of the mirror-to QOS. 16 means no filter rules in the Hardware."
        ::= { qosMirrorToEntry 10 }

    qosMirrorToBlock2Priority OBJECT-TYPE
        SYNTAX  INTEGER(0..16)
        ACCESS  read-only
        STATUS  current
        DESCRIPTION
                "the block 2 priority of the mirror-to QOS. 16 means no filter rules in the Hardware."
        ::= { qosMirrorToEntry 11 }

    qosMirrorToBlock3Priority OBJECT-TYPE
        SYNTAX  INTEGER(0..16)
        ACCESS  read-only
        STATUS  current
        DESCRIPTION
                "the block 3 priority of the mirror-to QOS. 16 means no filter rules in the Hardware."
        ::= { qosMirrorToEntry 12 }

    qosMirrorToBlock4Priority OBJECT-TYPE
        SYNTAX  INTEGER(0..16)
        ACCESS  read-only
        STATUS  current
        DESCRIPTION
                "the block 4 priority of the mirror-to QOS. 16 means no filter rules in the Hardware."
        ::= { qosMirrorToEntry 13 }

    qosMirrorToConfigSequence OBJECT-TYPE
        SYNTAX  INTEGER(1..1024)
        ACCESS  read-only
        STATUS  current
        DESCRIPTION
                "the config sequence of the mirror-to QOS."
        ::= { qosMirrorToEntry 14 }

    qosMirrorToRunning OBJECT-TYPE
        SYNTAX   TruthValue
        MAX-ACCESS   read-only
        STATUS   current
        DESCRIPTION
           "the running status of the mirror-to QOS. "
       ::= { qosMirrorToEntry 15 }

    qosMirrorToRowStatus OBJECT-TYPE
        SYNTAX      RowStatus
        MAX-ACCESS  read-create
        STATUS      current
        DESCRIPTION
            "This object indicates the status of this entry."
        ::= { qosMirrorToEntry 16 }

    qosMirrorToBlock5Priority OBJECT-TYPE
        SYNTAX  INTEGER(0..16)
        ACCESS  read-only
        STATUS  current
        DESCRIPTION
                "the block 5 priority of the mirror-to QOS. 16 means no filter rules in the Hardware."
                --流镜像在block 5中的优先级，16表示没有过滤规则在硬件中
        ::= { qosMirrorToEntry 17 }

    qosMirrorToBlock6Priority OBJECT-TYPE
        SYNTAX  INTEGER(0..16)
        ACCESS  read-only
        STATUS  current
        DESCRIPTION
                "the block 6 priority of the mirror-to QOS. 16 means no filter rules in the Hardware."
                --流镜像在block 6 中的优先级，16表示没有过滤规则在硬件中
        ::= { qosMirrorToEntry 18 }

    qosMirrorToBlock7Priority OBJECT-TYPE
        SYNTAX  INTEGER(0..16)
        ACCESS  read-only
        STATUS  current
        DESCRIPTION
                "the block 7 priority of the mirror-to QOS. 16 means no filter rules in the Hardware."
                --流镜像在block 7 中的优先级，16表示没有过滤规则在硬件中
        ::= { qosMirrorToEntry 19 }

    qosMirrorToBlock8Priority OBJECT-TYPE
        SYNTAX  INTEGER(0..16)
        ACCESS  read-only
        STATUS  current
        DESCRIPTION
                "the block 8 priority of the mirror-to QOS. 16 means no filter rules in the Hardware."
                --流镜像在block 8 中的优先级，16表示没有过滤规则在硬件中
        ::= { qosMirrorToEntry 20 }

    qosMirrorToBlock9Priority OBJECT-TYPE
        SYNTAX  INTEGER(0..16)
        ACCESS  read-only
        STATUS  current
        DESCRIPTION
                "the block 9 priority of the mirror-to QOS. 16 means no filter rules in the Hardware."
                --流镜像在block 9 中的优先级，16表示没有过滤规则在硬件中
        ::= { qosMirrorToEntry 21 }

    qosMirrorToBlock10Priority OBJECT-TYPE
        SYNTAX  INTEGER(0..16)
        ACCESS  read-only
        STATUS  current
        DESCRIPTION
                "the block 10 priority of the mirror-to QOS. 16 means no filter rules in the Hardware."
                --流镜像在block 10 中的优先级，16表示没有过滤规则在硬件中
        ::= { qosMirrorToEntry 22 }

    qosMirrorToBlock11Priority OBJECT-TYPE
        SYNTAX  INTEGER(0..16)
        ACCESS  read-only
        STATUS  current
        DESCRIPTION
                "the block 11 priority of the mirror-to QOS. 16 means no filter rules in the Hardware."
                --流镜像在block 11 中的优先级，16表示没有过滤规则在硬件中
        ::= { qosMirrorToEntry 23 }

   -----------------------------------------------------
   -- the rate-limit QOS
   -----------------------------------------------------

   qosRateLimitTable OBJECT-TYPE
       SYNTAX  SEQUENCE OF QosRateLimitEntry
       ACCESS  not-accessible
       STATUS  current
       DESCRIPTION
               "A list of rate-limit QOS entries. "
       ::= { gbnL2QACL 17 }

   qosRateLimitEntry OBJECT-TYPE
       SYNTAX  QosRateLimitEntry
       ACCESS  not-accessible
       STATUS  current
       DESCRIPTION
               "A list of rate-limit QOS entries. "
       INDEX   { qosRateLimitIndex }
       ::= { qosRateLimitTable 1 }

   QosRateLimitEntry ::=
       SEQUENCE {
           qosRateLimitIndex
               INTEGER,
           qosRateLimitUserGroupName
               OCTET STRING,
           qosRateLimitUserGroupSubitem
               INTEGER,
           qosRateLimitIpGroupName
               OCTET STRING,
           qosRateLimitIpGroupSubitem
               INTEGER,
           qosRateLimitLinkGroupName
               OCTET STRING,
           qosRateLimitLinkGroupSubitem
               INTEGER,
           qosRateLimitIntf
               INTEGER,
           qosRateLimitTargetRate
               INTEGER,
           qosRateLimitExceedAction
               INTEGER,
           qosRateLimitDscpValue
               INTEGER,
           qosRateLimitBlock0Priority
                INTEGER,
           qosRateLimitBlock1Priority
                INTEGER,
           qosRateLimitBlock2Priority
                INTEGER,
           qosRateLimitBlock3Priority
                INTEGER,
           qosRateLimitBlock4Priority
                INTEGER,
           qosRateLimitConfigSequence
                INTEGER,
           qosRateLimitRunning
               TruthValue,
           qosRateLimitRowStatus
               RowStatus,
           qosRateLimitBlock5Priority
                INTEGER,
           qosRateLimitBlock6Priority
                INTEGER,
           qosRateLimitBlock7Priority
                INTEGER,
           qosRateLimitBlock8Priority
                INTEGER,
           qosRateLimitBlock9Priority
                INTEGER,
           qosRateLimitBlock10Priority
                INTEGER,
           qosRateLimitBlock11Priority
                INTEGER,
           qosRateLimitPolicerId
                INTEGER,
           qosRateLimitUsePolicer
               TruthValue,
           qosRateLimitCIR
               INTEGER,
           qosRateLimitCBS
               INTEGER,
           qosRateLimitPIR
               INTEGER,
           qosRateLimitPBS
               INTEGER,
           qosRateLimitRedAction
               INTEGER,
           qosRateLimitRedDscp
               INTEGER,
           qosRateLimitYellowAction
               INTEGER,
           qosRateLimitYellowDscp
               INTEGER,
           qosRateLimitGreenAction
               INTEGER,
           qosRateLimitGreenDscp
               INTEGER,
           qosRateLimitUsetrTCM
               TruthValue
       }

   qosRateLimitIndex OBJECT-TYPE
       SYNTAX  INTEGER
       ACCESS  read-only
       STATUS  current
       DESCRIPTION
               "A unique value for each rate-limit QOS.  "
       ::= { qosRateLimitEntry 1 }

   qosRateLimitUserGroupName OBJECT-TYPE
       SYNTAX  OCTET STRING (SIZE (0..31))
       ACCESS  read-write
       STATUS  current
       DESCRIPTION
               "the name of the rate-limit QOS user group acl. "
       ::= { qosRateLimitEntry 2 }

   qosRateLimitUserGroupSubitem OBJECT-TYPE
       SYNTAX  INTEGER(0..127)
       ACCESS  read-write
       STATUS  current
       DESCRIPTION
               "the number of the rate-limit QOS user group acl subitem. "
       ::= { qosRateLimitEntry 3 }

   qosRateLimitIpGroupName OBJECT-TYPE
       SYNTAX  OCTET STRING (SIZE (0..31))
       ACCESS  read-write
       STATUS  current
       DESCRIPTION
               "the name of the rate-limit QOS ip group acl. "
       ::= { qosRateLimitEntry 4 }

   qosRateLimitIpGroupSubitem OBJECT-TYPE
       SYNTAX  INTEGER(0..127)
       ACCESS  read-write
       STATUS  current
       DESCRIPTION
               "the number of the rate-limit QOS ip group acl subitem. "
       ::= { qosRateLimitEntry 5 }

   qosRateLimitLinkGroupName OBJECT-TYPE
       SYNTAX  OCTET STRING (SIZE (0..31))
       ACCESS  read-write
       STATUS  current
       DESCRIPTION
               "the name of the rate-limit QOS link group acl. "
       ::= { qosRateLimitEntry 6 }

   qosRateLimitLinkGroupSubitem OBJECT-TYPE
       SYNTAX  INTEGER(0..127)
       ACCESS  read-write
       STATUS  current
       DESCRIPTION
               "the number of the rate-limit QOS link group acl subitem. "
       ::= { qosRateLimitEntry 7 }

   qosRateLimitIntf OBJECT-TYPE
       SYNTAX  INTEGER
       ACCESS  read-write
       STATUS  current
       DESCRIPTION
               "the target rate on this interface. "
       ::= { qosRateLimitEntry 8 }

   qosRateLimitTargetRate OBJECT-TYPE
       SYNTAX  INTEGER (1..100)
       ACCESS  read-write
       STATUS  current
       DESCRIPTION
               "the target rate of the rate-limit QOS. "
       ::= { qosRateLimitEntry 9 }

   qosRateLimitExceedAction OBJECT-TYPE
       SYNTAX  INTEGER {
                   drop(1),
                   set-dscp-value(2)
               }
       ACCESS  read-write
       STATUS  current
       DESCRIPTION
               "the exceed action of the rate-limit QOS. "
       ::= { qosRateLimitEntry 10 }

   qosRateLimitDscpValue OBJECT-TYPE
       SYNTAX  INTEGER (0..63)
       ACCESS  read-write
       STATUS  current
       DESCRIPTION
               "the dscp value of the rate-limit QOS. "
       ::= { qosRateLimitEntry 11 }

   qosRateLimitBlock0Priority OBJECT-TYPE
       SYNTAX  INTEGER(0..16)
       ACCESS  read-only
       STATUS  current
       DESCRIPTION
               "the block 0 priority of the rate-limit QOS. 16 means no filter rules in the Hardware."
       ::= { qosRateLimitEntry 12 }

   qosRateLimitBlock1Priority OBJECT-TYPE
       SYNTAX  INTEGER(0..16)
       ACCESS  read-only
       STATUS  current
       DESCRIPTION
               "the block 1 priority of the rate-limit QOS. 16 means no filter rules in the Hardware."
       ::= { qosRateLimitEntry 13 }

   qosRateLimitBlock2Priority OBJECT-TYPE
       SYNTAX  INTEGER(0..16)
       ACCESS  read-only
       STATUS  current
       DESCRIPTION
               "the block 2 priority of the rate-limit QOS. 16 means no filter rules in the Hardware."
       ::= { qosRateLimitEntry 14 }

   qosRateLimitBlock3Priority OBJECT-TYPE
       SYNTAX  INTEGER(0..16)
       ACCESS  read-only
       STATUS  current
       DESCRIPTION
               "the block 3 priority of the rate-limit QOS. 16 means no filter rules in the Hardware."
       ::= { qosRateLimitEntry 15 }

   qosRateLimitBlock4Priority OBJECT-TYPE
       SYNTAX  INTEGER(0..16)
       ACCESS  read-only
       STATUS  current
       DESCRIPTION
               "the block 4 priority of the rate-limit QOS. 16 means no filter rules in the Hardware."
       ::= { qosRateLimitEntry 16 }

   qosRateLimitConfigSequence OBJECT-TYPE
       SYNTAX  INTEGER(1..1024)
       ACCESS  read-only
       STATUS  current
       DESCRIPTION
               "the config sequence of the rate-limit QOS."
       ::= { qosRateLimitEntry 17 }

   qosRateLimitRunning OBJECT-TYPE
       SYNTAX   TruthValue
       MAX-ACCESS   read-only
       STATUS   current
       DESCRIPTION
          "the running status of the rate-limit QOS."
      ::= { qosRateLimitEntry 18 }

   qosRateLimitRowStatus OBJECT-TYPE
       SYNTAX      RowStatus
       MAX-ACCESS  read-create
       STATUS      current
       DESCRIPTION
           "This object indicates the status of this entry."
       ::= { qosRateLimitEntry 19 }

   qosRateLimitBlock5Priority OBJECT-TYPE
       SYNTAX  INTEGER(0..16)
       ACCESS  read-only
       STATUS  current
       DESCRIPTION
               "the block 5 priority of the rate-limit QOS. 16 means no filter rules in the Hardware."
               --流量监管在block 5 中的优先级，16表示没有过滤规则在硬件中
       ::= { qosRateLimitEntry 20 }

   qosRateLimitBlock6Priority OBJECT-TYPE
       SYNTAX  INTEGER(0..16)
       ACCESS  read-only
       STATUS  current
       DESCRIPTION
               "the block 6 priority of the rate-limit QOS. 16 means no filter rules in the Hardware."
               --流量监管在block 6 中的优先级，16表示没有过滤规则在硬件中
       ::= { qosRateLimitEntry 21 }

   qosRateLimitBlock7Priority OBJECT-TYPE
       SYNTAX  INTEGER(0..16)
       ACCESS  read-only
       STATUS  current
       DESCRIPTION
               "the block 7 priority of the rate-limit QOS. 16 means no filter rules in the Hardware."
               --流量监管在block 7 中的优先级，16表示没有过滤规则在硬件中
       ::= { qosRateLimitEntry 22 }

   qosRateLimitBlock8Priority OBJECT-TYPE
       SYNTAX  INTEGER(0..16)
       ACCESS  read-only
       STATUS  current
       DESCRIPTION
               "the block 8 priority of the rate-limit QOS. 16 means no filter rules in the Hardware."
               --流量监管在block 8 中的优先级，16表示没有过滤规则在硬件中
       ::= { qosRateLimitEntry 23 }

   qosRateLimitBlock9Priority OBJECT-TYPE
       SYNTAX  INTEGER(0..16)
       ACCESS  read-only
       STATUS  current
       DESCRIPTION
               "the block 9 priority of the rate-limit QOS. 16 means no filter rules in the Hardware."
               --流量监管在block 9 中的优先级，16表示没有过滤规则在硬件中
       ::= { qosRateLimitEntry 24 }

   qosRateLimitBlock10Priority OBJECT-TYPE
       SYNTAX  INTEGER(0..16)
       ACCESS  read-only
       STATUS  current
       DESCRIPTION
               "the block 10 priority of the rate-limit QOS. 16 means no filter rules in the Hardware."
               --流量监管在block 10 中的优先级，16表示没有过滤规则在硬件中
       ::= { qosRateLimitEntry 25 }

   qosRateLimitBlock11Priority OBJECT-TYPE
       SYNTAX  INTEGER(0..16)
       ACCESS  read-only
       STATUS  current
       DESCRIPTION
               "the block 11 priority of the rate-limit QOS. 16 means no filter rules in the Hardware."
               --流量监管在block 11 中的优先级，16表示没有过滤规则在硬件中
       ::= { qosRateLimitEntry 26 }

   qosRateLimitPolicerId OBJECT-TYPE
       SYNTAX  INTEGER
       ACCESS  read-write
       STATUS  current
       DESCRIPTION
               "the two rate policer ID of the rate-limit QOS."
       ::= { qosRateLimitEntry 27 }

   qosRateLimitUsePolicer OBJECT-TYPE
       SYNTAX   TruthValue
       MAX-ACCESS   read-write
       STATUS   current
       DESCRIPTION
          "this value determines whether the rate-limit QOS use a two rate policer."
      ::= { qosRateLimitEntry 28 }
   qosRateLimitCIR    OBJECT-TYPE
       SYNTAX  INTEGER(64..1048512)
       ACCESS  read-write
       STATUS  current
       DESCRIPTION
               "the Committed information rate value ."
       ::= { qosRateLimitEntry 29 }

   qosRateLimitCBS    OBJECT-TYPE
       SYNTAX  INTEGER(4..16384)
       ACCESS  read-write
       STATUS  current
       DESCRIPTION
               "the Committed burst size value ."
       ::= { qosRateLimitEntry 30 }

   qosRateLimitPIR    OBJECT-TYPE
       SYNTAX  INTEGER(64..1048512)
       ACCESS  read-write
       STATUS  current
       DESCRIPTION
               "the peak information rate value ."
       ::= { qosRateLimitEntry 31 }

   qosRateLimitPBS    OBJECT-TYPE
       SYNTAX  INTEGER(4..16384)
       ACCESS  read-write
       STATUS  current
       DESCRIPTION
               "the peak burst size value ."
       ::= { qosRateLimitEntry 32 }

   qosRateLimitRedAction   OBJECT-TYPE
       SYNTAX  INTEGER{
               drop(1),
               set-dscp-value(2),
               copy-to-cpu(3),
               transmit(4)
               }
       ACCESS  read-write
       STATUS  current
       DESCRIPTION
               "the packets marked red action ."
       ::= { qosRateLimitEntry 33 }

   qosRateLimitRedDscp   OBJECT-TYPE
       SYNTAX  INTEGER(0..63)
       ACCESS  read-write
       STATUS  current
       DESCRIPTION
               "the packets marked red set dscp value."
       ::= { qosRateLimitEntry 34}

   qosRateLimitYellowAction     OBJECT-TYPE
       SYNTAX  INTEGER{
               drop(1),
               set-dscp-value(2),
               copy-to-cpu(3),
               transmit(4)
               }
       ACCESS  read-write
       STATUS  current
       DESCRIPTION
               "the packets marked yellow action."
       ::= { qosRateLimitEntry 35 }

   qosRateLimitYellowDscp OBJECT-TYPE
       SYNTAX  INTEGER(0..63)
       ACCESS  read-write
       STATUS  current
       DESCRIPTION
               "the packets marked yellow set dscp value."
       ::= { qosRateLimitEntry 36 }

  qosRateLimitGreenAction    OBJECT-TYPE
       SYNTAX  INTEGER{
              drop(1),
               set-dscp-value(2),
               copy-to-cpu(3),
               transmit(4)
               }
       ACCESS  read-write
       STATUS  current
       DESCRIPTION
               "the packets marked green action ."
       ::= { qosRateLimitEntry 37 }

   qosRateLimitGreenDscp   OBJECT-TYPE
       SYNTAX  INTEGER(0..63)
       ACCESS  read-write
       STATUS  current
       DESCRIPTION
               "the packets marked green set dscp value."
       ::= { qosRateLimitEntry 38}

  qosRateLimitUsetrTCM OBJECT-TYPE
       SYNTAX   TruthValue
       MAX-ACCESS   read-write
       STATUS   current
       DESCRIPTION
          "this value determines whether the rate-limit QOS use a two rate policer."
      ::= { qosRateLimitEntry 39 }

   -----------------------------------------------------
   -- the traffic-priority QOS
   -----------------------------------------------------

   qosTrafficPriorityTable OBJECT-TYPE
       SYNTAX  SEQUENCE OF QosTrafficPriorityEntry
       ACCESS  not-accessible
       STATUS  current
       DESCRIPTION
               "A list of traffic-priority QOS entries. "
       ::= { gbnL2QACL 18 }

   qosTrafficPriorityEntry OBJECT-TYPE
       SYNTAX  QosTrafficPriorityEntry
       ACCESS  not-accessible
       STATUS  current
       DESCRIPTION
               "A list of traffic-priority QOS entries. "
       INDEX   { qosTrafficPriorityIndex }
       ::= { qosTrafficPriorityTable 1 }

   QosTrafficPriorityEntry ::=
       SEQUENCE {
           qosTrafficPriorityIndex
               INTEGER,
           qosTrafficPriorityUserGroupName
               OCTET STRING,
           qosTrafficPriorityUserGroupSubitem
               INTEGER,
           qosTrafficPriorityIpGroupName
               OCTET STRING,
           qosTrafficPriorityIpGroupSubitem
               INTEGER,
           qosTrafficPriorityLinkGroupName
               OCTET STRING,
           qosTrafficPriorityLinkGroupSubitem
               INTEGER,
           qosTrafficPriorityDscp
               INTEGER,
           qosTrafficPriorityIpPrecedence
               INTEGER,
           qosTrafficPriorityCos
               INTEGER,
           qosTrafficPriorityLocalPrecedence
               INTEGER,
           qosTrafficPriorityBlock0Priority
               INTEGER,
           qosTrafficPriorityBlock1Priority
               INTEGER,
           qosTrafficPriorityBlock2Priority
               INTEGER,
           qosTrafficPriorityBlock3Priority
               INTEGER,
           qosTrafficPriorityBlock4Priority
               INTEGER,
           qosTrafficPriorityConfigSequence
               INTEGER,
           qosTrafficPriorityRunning
               TruthValue,
           qosTrafficPriorityRowStatus
               RowStatus,
           qosTrafficPriorityBlock5Priority
               INTEGER,
           qosTrafficPriorityBlock6Priority
               INTEGER,
           qosTrafficPriorityBlock7Priority
               INTEGER,
           qosTrafficPriorityBlock8Priority
               INTEGER,
           qosTrafficPriorityBlock9Priority
               INTEGER,
           qosTrafficPriorityBlock10Priority
               INTEGER,
           qosTrafficPriorityBlock11Priority
               INTEGER
       }

   qosTrafficPriorityIndex OBJECT-TYPE
       SYNTAX  INTEGER
       ACCESS  read-only
       STATUS  current
       DESCRIPTION
               "A unique value for each traffic-priority QOS.  "
       ::= { qosTrafficPriorityEntry 1 }

   qosTrafficPriorityUserGroupName OBJECT-TYPE
       SYNTAX  OCTET STRING (SIZE (0..31))
       ACCESS  read-write
       STATUS  current
       DESCRIPTION
               "the name of the traffic-priority QOS user group acl. "
       ::= { qosTrafficPriorityEntry 2 }

   qosTrafficPriorityUserGroupSubitem OBJECT-TYPE
       SYNTAX  INTEGER(0..127)
       ACCESS  read-write
       STATUS  current
       DESCRIPTION
               "the number of the traffic-priority QOS user group acl subitem. "
       ::= { qosTrafficPriorityEntry 3 }

   qosTrafficPriorityIpGroupName OBJECT-TYPE
       SYNTAX  OCTET STRING (SIZE (0..31))
       ACCESS  read-write
       STATUS  current
       DESCRIPTION
               "the name of the traffic-priority QOS ip group acl. "
       ::= { qosTrafficPriorityEntry 4 }

   qosTrafficPriorityIpGroupSubitem OBJECT-TYPE
       SYNTAX  INTEGER(0..127)
       ACCESS  read-write
       STATUS  current
       DESCRIPTION
               "the number of the traffic-priority QOS ip group acl subitem. "
       ::= { qosTrafficPriorityEntry 5 }

   qosTrafficPriorityLinkGroupName OBJECT-TYPE
       SYNTAX  OCTET STRING (SIZE (0..31))
       ACCESS  read-write
       STATUS  current
       DESCRIPTION
               "the name of the traffic-priority QOS link group acl. "
       ::= { qosTrafficPriorityEntry 6 }

   qosTrafficPriorityLinkGroupSubitem OBJECT-TYPE
       SYNTAX  INTEGER(0..127)
       ACCESS  read-write
       STATUS  current
       DESCRIPTION
               "the number of the traffic-priority QOS link group acl subitem. "
       ::= { qosTrafficPriorityEntry 7 }

   qosTrafficPriorityDscp OBJECT-TYPE
       SYNTAX  INTEGER (0..63)
       ACCESS  read-write
       STATUS  current
       DESCRIPTION
               "the DSCP of the traffic-priority QOS. "
       ::= { qosTrafficPriorityEntry 8 }

   qosTrafficPriorityIpPrecedence OBJECT-TYPE
       SYNTAX  INTEGER (0..7)
       ACCESS  read-write
       STATUS  current
       DESCRIPTION
               "the IP precedence of the traffic-priority QOS. "
       ::= { qosTrafficPriorityEntry 9 }

   qosTrafficPriorityCos OBJECT-TYPE
       SYNTAX  INTEGER (0..7)
       ACCESS  read-write
       STATUS  current
       DESCRIPTION
               "the COS of the traffic-priority QOS. "
       ::= { qosTrafficPriorityEntry 10 }

   qosTrafficPriorityLocalPrecedence OBJECT-TYPE
       SYNTAX  INTEGER (0..7)
       ACCESS  read-write
       STATUS  current
       DESCRIPTION
               "the local precedence of the traffic-priority QOS. "
       ::= { qosTrafficPriorityEntry 11 }

   qosTrafficPriorityBlock0Priority OBJECT-TYPE
       SYNTAX  INTEGER(0..16)
       ACCESS  read-only
       STATUS  current
       DESCRIPTION
               "the block 0 priority of the traffic-priority QOS. 16 means no filter rules in the Hardware."
       ::= { qosTrafficPriorityEntry 12 }

   qosTrafficPriorityBlock1Priority OBJECT-TYPE
       SYNTAX  INTEGER(0..16)
       ACCESS  read-only
       STATUS  current
       DESCRIPTION
               "the block 1 priority of the traffic-priority QOS. 16 means no filter rules in the Hardware."
       ::= { qosTrafficPriorityEntry 13 }

   qosTrafficPriorityBlock2Priority OBJECT-TYPE
       SYNTAX  INTEGER(0..16)
       ACCESS  read-only
       STATUS  current
       DESCRIPTION
               "the block 2 priority of the traffic-priority QOS. 16 means no filter rules in the Hardware."
       ::= { qosTrafficPriorityEntry 14 }

   qosTrafficPriorityBlock3Priority OBJECT-TYPE
       SYNTAX  INTEGER(0..16)
       ACCESS  read-only
       STATUS  current
       DESCRIPTION
               "the block 3 priority of the traffic-priority QOS. 16 means no filter rules in the Hardware."
       ::= { qosTrafficPriorityEntry 15 }

   qosTrafficPriorityBlock4Priority OBJECT-TYPE
       SYNTAX  INTEGER(0..16)
       ACCESS  read-only
       STATUS  current
       DESCRIPTION
               "the block 4 priority of the traffic-priority QOS. 16 means no filter rules in the Hardware."
       ::= { qosTrafficPriorityEntry 16 }

   qosTrafficPriorityConfigSequence OBJECT-TYPE
       SYNTAX  INTEGER(1..1024)
       ACCESS  read-only
       STATUS  current
       DESCRIPTION
               "the config sequence of the traffic-priority QOS."
       ::= { qosTrafficPriorityEntry 17 }

   qosTrafficPriorityRunning OBJECT-TYPE
       SYNTAX   TruthValue
       MAX-ACCESS   read-only
       STATUS   current
       DESCRIPTION
           "the running status of the traffic-priority QOS."
       ::= { qosTrafficPriorityEntry 18 }

   qosTrafficPriorityRowStatus OBJECT-TYPE
       SYNTAX      RowStatus
       MAX-ACCESS  read-create
       STATUS      current
       DESCRIPTION
           "This object indicates the status of this entry."
       ::= { qosTrafficPriorityEntry 19 }

   qosTrafficPriorityBlock5Priority OBJECT-TYPE
       SYNTAX  INTEGER(0..16)
       ACCESS  read-only
       STATUS  current
       DESCRIPTION
               "the block 5 priority of the traffic-priority QOS. 16 means no filter rules in the Hardware."
               --报文优先级在block 5 中的优先级，16表示没有过滤规则在硬件中
       ::= { qosTrafficPriorityEntry 20 }

   qosTrafficPriorityBlock6Priority OBJECT-TYPE
       SYNTAX  INTEGER(0..16)
       ACCESS  read-only
       STATUS  current
       DESCRIPTION
               "the block 6 priority of the traffic-priority QOS. 16 means no filter rules in the Hardware."
               --报文优先级在block 6 中的优先级，16表示没有过滤规则在硬件中
       ::= { qosTrafficPriorityEntry 21 }

   qosTrafficPriorityBlock7Priority OBJECT-TYPE
       SYNTAX  INTEGER(0..16)
       ACCESS  read-only
       STATUS  current
       DESCRIPTION
               "the block 7 priority of the traffic-priority QOS. 16 means no filter rules in the Hardware."
               --报文优先级在block 7 中的优先级，16表示没有过滤规则在硬件中
       ::= { qosTrafficPriorityEntry 22 }

   qosTrafficPriorityBlock8Priority OBJECT-TYPE
       SYNTAX  INTEGER(0..16)
       ACCESS  read-only
       STATUS  current
       DESCRIPTION
               "the block 8 priority of the traffic-priority QOS. 16 means no filter rules in the Hardware."
               --报文优先级在block 8 中的优先级，16表示没有过滤规则在硬件中
       ::= { qosTrafficPriorityEntry 23 }

   qosTrafficPriorityBlock9Priority OBJECT-TYPE
       SYNTAX  INTEGER(0..16)
       ACCESS  read-only
       STATUS  current
       DESCRIPTION
               "the block 9 priority of the traffic-priority QOS. 16 means no filter rules in the Hardware."
               --报文优先级在block 9 中的优先级，16表示没有过滤规则在硬件中
       ::= { qosTrafficPriorityEntry 24 }

   qosTrafficPriorityBlock10Priority OBJECT-TYPE
       SYNTAX  INTEGER(0..16)
       ACCESS  read-only
       STATUS  current
       DESCRIPTION
               "the block 10 priority of the traffic-priority QOS. 16 means no filter rules in the Hardware."
               --报文优先级在block 10 中的优先级，16表示没有过滤规则在硬件中
       ::= { qosTrafficPriorityEntry 25 }

   qosTrafficPriorityBlock11Priority OBJECT-TYPE
       SYNTAX  INTEGER(0..16)
       ACCESS  read-only
       STATUS  current
       DESCRIPTION
               "the block 11 priority of the traffic-priority QOS. 16 means no filter rules in the Hardware."
               --报文优先级在block 11 中的优先级，16表示没有过滤规则在硬件中
       ::= { qosTrafficPriorityEntry 26 }

    -----------------------------------------------------
   -- the traffic-policy based route
   -----------------------------------------------------

   qosTrafficPbrTable OBJECT-TYPE
       SYNTAX  SEQUENCE OF QosTrafficPbrEntry
       ACCESS  not-accessible
       STATUS  current
       DESCRIPTION
               "A list of traffic-policy-based-route QOS entries. "
       ::= { gbnL2QACL 19 }

   qosTrafficPbrEntry OBJECT-TYPE
       SYNTAX  QosTrafficPbrEntry
       ACCESS  not-accessible
       STATUS  current
       DESCRIPTION
               "A list of traffic-policy-based-route QOS entries. "
       INDEX   { qosTrafficPbrIndex }
       ::= { qosTrafficPbrTable 1 }

   QosTrafficPbrEntry ::=
       SEQUENCE {
           qosTrafficPbrIndex
               INTEGER,
           qosTrafficPbrUserGroupName
               OCTET STRING,
           qosTrafficPbrUserGroupSubitem
               INTEGER,
           qosTrafficPbrIpGroupName
               OCTET STRING,
           qosTrafficPbrIpGroupSubitem
               INTEGER,
           qosTrafficPbrLinkGroupName
               OCTET STRING,
           qosTrafficPbrLinkGroupSubitem
               INTEGER,
           qosTrafficPbrNextHopIp
               IpAddress,
           qosTrafficPbrConfigSequence
               INTEGER,
           qosTrafficPbrRunning
               TruthValue,
           qosTrafficPbrRowStatus
               RowStatus,
       }

   qosTrafficPbrIndex OBJECT-TYPE
       SYNTAX  INTEGER
       ACCESS  read-only
       STATUS  current
       DESCRIPTION
               "A unique value for each traffic-PBR QOS.  "
       ::= { qosTrafficPbrEntry 1 }

   qosTrafficPbrUserGroupName OBJECT-TYPE
       SYNTAX  OCTET STRING (SIZE (0..31))
       ACCESS  read-write
       STATUS  current
       DESCRIPTION
               "the name of the traffic-PBR QOS user group acl. "
       ::= { qosTrafficPbrEntry 2 }

   qosTrafficPbrUserGroupSubitem OBJECT-TYPE
       SYNTAX  INTEGER(0..127)
       ACCESS  read-write
       STATUS  current
       DESCRIPTION
               "the number of the traffic-PBR QOS user group acl subitem. "
       ::= { qosTrafficPbrEntry 3 }

   qosTrafficPbrIpGroupName OBJECT-TYPE
       SYNTAX  OCTET STRING (SIZE (0..31))
       ACCESS  read-write
       STATUS  current
       DESCRIPTION
               "the name of the traffic-PBR QOS ip group acl. "
       ::= { qosTrafficPbrEntry 4 }

   qosTrafficPbrIpGroupSubitem OBJECT-TYPE
       SYNTAX  INTEGER(0..127)
       ACCESS  read-write
       STATUS  current
       DESCRIPTION
               "the number of the traffic-PBR QOS ip group acl subitem. "
       ::= { qosTrafficPbrEntry 5 }

   qosTrafficPbrLinkGroupName OBJECT-TYPE
       SYNTAX  OCTET STRING (SIZE (0..31))
       ACCESS  read-write
       STATUS  current
       DESCRIPTION
               "the name of the traffic-PBR QOS link group acl. "
       ::= { qosTrafficPbrEntry 6 }

   qosTrafficPbrLinkGroupSubitem OBJECT-TYPE
       SYNTAX  INTEGER(0..127)
       ACCESS  read-write
       STATUS  current
       DESCRIPTION
               "the number of the traffic-PBR QOS link group acl subitem. "
       ::= { qosTrafficPbrEntry 7 }

   qosTrafficPbrNextHopIp OBJECT-TYPE
       SYNTAX  IpAddress
       ACCESS  read-write
       STATUS  current
       DESCRIPTION
               "the IP precedence of the traffic-PBR QOS. "
       ::= { qosTrafficPbrEntry 8 }

   qosTrafficPbrConfigSequence OBJECT-TYPE
       SYNTAX  INTEGER(1..1024)
       ACCESS  read-only
       STATUS  current
       DESCRIPTION
               "the config sequence of the traffic-PBR QOS."
       ::= { qosTrafficPbrEntry 9 }

   qosTrafficPbrRunning OBJECT-TYPE
       SYNTAX   TruthValue
       MAX-ACCESS   read-only
       STATUS   current
       DESCRIPTION
           "the running status of the traffic-PBR QOS."
       ::= { qosTrafficPbrEntry 10 }

   qosTrafficPbrRowStatus OBJECT-TYPE
       SYNTAX      RowStatus
       MAX-ACCESS  read-create
       STATUS      current
       DESCRIPTION
           "This object indicates the status of this entry."
       ::= { qosTrafficPbrEntry 11 }

   -----------------------------------------------------
   -- the traffic redirect QOS
   -----------------------------------------------------

   qosTrafficRedirectTable OBJECT-TYPE
       SYNTAX  SEQUENCE OF QosTrafficRedirectEntry
       ACCESS  not-accessible
       STATUS  current
       DESCRIPTION
               "A list of traffic-redirect QOS entries. "
       ::= { gbnL2QACL 20 }

   qosTrafficRedirectEntry OBJECT-TYPE
       SYNTAX  QosTrafficRedirectEntry
       ACCESS  not-accessible
       STATUS  current
       DESCRIPTION
               "A list of traffic-redirect QOS entries. "
       INDEX   { qosTrafficRedirectIndex }
       ::= { qosTrafficRedirectTable 1 }

   QosTrafficRedirectEntry ::=
       SEQUENCE {
           qosTrafficRedirectIndex
               INTEGER,
           qosTrafficRedirectUserGroupName
               OCTET STRING,
           qosTrafficRedirectUserGroupSubitem
               INTEGER,
           qosTrafficRedirectIpGroupName
               OCTET STRING,
           qosTrafficRedirectIpGroupSubitem
               INTEGER,
           qosTrafficRedirectLinkGroupName
               OCTET STRING,
           qosTrafficRedirectLinkGroupSubitem
               INTEGER,
           qosTrafficRedirectInterface
               INTEGER,
           qosTrafficRedirectBlock0Priority
               INTEGER,
           qosTrafficRedirectBlock1Priority
               INTEGER,
           qosTrafficRedirectBlock2Priority
               INTEGER,
           qosTrafficRedirectBlock3Priority
               INTEGER,
           qosTrafficRedirectBlock4Priority
               INTEGER,
           qosTrafficRedirectConfigSequence
               INTEGER,
           qosTrafficRedirectRunning
               TruthValue,
           qosTrafficRedirectRowStatus
               RowStatus,
           qosTrafficRedirectBlock5Priority
               INTEGER,
           qosTrafficRedirectBlock6Priority
               INTEGER,
           qosTrafficRedirectBlock7Priority
               INTEGER,
           qosTrafficRedirectBlock8Priority
               INTEGER,
           qosTrafficRedirectBlock9Priority
               INTEGER,
           qosTrafficRedirectBlock10Priority
               INTEGER,
           qosTrafficRedirectBlock11Priority
               INTEGER
       }

   qosTrafficRedirectIndex OBJECT-TYPE
       SYNTAX  INTEGER
       ACCESS  read-only
       STATUS  current
       DESCRIPTION
               "A unique value for each traffic-redirect QOS.  "
       ::= { qosTrafficRedirectEntry 1 }

   qosTrafficRedirectUserGroupName OBJECT-TYPE
       SYNTAX  OCTET STRING (SIZE (0..31))
       ACCESS  read-write
       STATUS  current
       DESCRIPTION
               "the name of the traffic-redirect QOS user group acl. "
       ::= { qosTrafficRedirectEntry 2 }

   qosTrafficRedirectUserGroupSubitem OBJECT-TYPE
       SYNTAX  INTEGER(0..127)
       ACCESS  read-write
       STATUS  current
       DESCRIPTION
               "the number of the traffic-redirect QOS user group acl subitem. "
       ::= { qosTrafficRedirectEntry 3 }

   qosTrafficRedirectIpGroupName OBJECT-TYPE
       SYNTAX  OCTET STRING (SIZE (0..31))
       ACCESS  read-write
       STATUS  current
       DESCRIPTION
               "the name of the traffic-redirect QOS ip group acl. "
       ::= { qosTrafficRedirectEntry 4 }

   qosTrafficRedirectIpGroupSubitem OBJECT-TYPE
       SYNTAX  INTEGER(0..127)
       ACCESS  read-write
       STATUS  current
       DESCRIPTION
               "the number of the traffic-redirect QOS ip group acl subitem. "
       ::= { qosTrafficRedirectEntry 5 }

   qosTrafficRedirectLinkGroupName OBJECT-TYPE
       SYNTAX  OCTET STRING (SIZE (0..31))
       ACCESS  read-write
       STATUS  current
       DESCRIPTION
               "the name of the traffic-redirect QOS link group acl. "
       ::= { qosTrafficRedirectEntry 6 }

   qosTrafficRedirectLinkGroupSubitem OBJECT-TYPE
       SYNTAX  INTEGER(0..127)
       ACCESS  read-write
       STATUS  current
       DESCRIPTION
               "the number of the traffic-redirect QOS link group acl subitem. "
       ::= { qosTrafficRedirectEntry 7 }

   qosTrafficRedirectInterface OBJECT-TYPE
       SYNTAX  INTEGER (1..28)
       ACCESS  read-write
       STATUS  current
       DESCRIPTION
               "the redirect interface of the traffic-redirect QOS.1－24 for fast-ethernet port 1－24，25－26 for giga-ethernet port 1－2，28 for CPU port，27 is invaild value. "
       ::= { qosTrafficRedirectEntry 8 }

   qosTrafficRedirectBlock0Priority OBJECT-TYPE
       SYNTAX  INTEGER(0..16)
       ACCESS  read-only
       STATUS  current
       DESCRIPTION
               "the block 0 priority of the traffic-redirect QOS. 16 means no filter rules in the Hardware."
       ::= { qosTrafficRedirectEntry 9 }

   qosTrafficRedirectBlock1Priority OBJECT-TYPE
       SYNTAX  INTEGER(0..16)
       ACCESS  read-only
       STATUS  current
       DESCRIPTION
               "the block 1 priority of the traffic-redirect QOS. 16 means no filter rules in the Hardware."
       ::= { qosTrafficRedirectEntry 10 }

   qosTrafficRedirectBlock2Priority OBJECT-TYPE
       SYNTAX  INTEGER(0..16)
       ACCESS  read-only
       STATUS  current
       DESCRIPTION
               "the block 2 priority of the traffic-redirect QOS. 16 means no filter rules in the Hardware."
       ::= { qosTrafficRedirectEntry 11 }

   qosTrafficRedirectBlock3Priority OBJECT-TYPE
       SYNTAX  INTEGER(0..16)
       ACCESS  read-only
       STATUS  current
       DESCRIPTION
               "the block 3 priority of the traffic-redirect QOS. 16 means no filter rules in the Hardware."
       ::= { qosTrafficRedirectEntry 12 }

   qosTrafficRedirectBlock4Priority OBJECT-TYPE
       SYNTAX  INTEGER(0..16)
       ACCESS  read-only
       STATUS  current
       DESCRIPTION
               "the block 4 priority of the traffic-redirect QOS. 16 means no filter rules in the Hardware."
       ::= { qosTrafficRedirectEntry 13 }

   qosTrafficRedirectConfigSequence OBJECT-TYPE
       SYNTAX  INTEGER(1..1024)
       ACCESS  read-only
       STATUS  current
       DESCRIPTION
               "the config sequence of the traffic-redirect QOS."
       ::= { qosTrafficRedirectEntry 14 }

   qosTrafficRedirectRunning OBJECT-TYPE
        SYNTAX   TruthValue
        MAX-ACCESS   read-only
        STATUS   current
        DESCRIPTION
           "the running status of the traffic-redirect QOS."
       ::= { qosTrafficRedirectEntry 15 }

   qosTrafficRedirectRowStatus OBJECT-TYPE
       SYNTAX      RowStatus
       MAX-ACCESS  read-create
       STATUS      current
       DESCRIPTION
           "This object indicates the status of this entry."
       ::= { qosTrafficRedirectEntry 16 }

   qosTrafficRedirectBlock5Priority OBJECT-TYPE
       SYNTAX  INTEGER(0..16)
       ACCESS  read-only
       STATUS  current
       DESCRIPTION
               "the block 5 priority of the traffic-redirect QOS. 16 means no filter rules in the Hardware."
               --报文重定向在block 5 中的优先级，16表示没有过滤规则在硬件中
       ::= { qosTrafficRedirectEntry 17 }

   qosTrafficRedirectBlock6Priority OBJECT-TYPE
       SYNTAX  INTEGER(0..16)
       ACCESS  read-only
       STATUS  current
       DESCRIPTION
               "the block 6 priority of the traffic-redirect QOS. 16 means no filter rules in the Hardware."
               --报文重定向在block 6 中的优先级，16表示没有过滤规则在硬件中
       ::= { qosTrafficRedirectEntry 18 }

   qosTrafficRedirectBlock7Priority OBJECT-TYPE
       SYNTAX  INTEGER(0..16)
       ACCESS  read-only
       STATUS  current
       DESCRIPTION
               "the block 7 priority of the traffic-redirect QOS. 16 means no filter rules in the Hardware."
               --报文重定向在block 7 中的优先级，16表示没有过滤规则在硬件中
       ::= { qosTrafficRedirectEntry 19 }

   qosTrafficRedirectBlock8Priority OBJECT-TYPE
       SYNTAX  INTEGER(0..16)
       ACCESS  read-only
       STATUS  current
       DESCRIPTION
               "the block 8 priority of the traffic-redirect QOS. 16 means no filter rules in the Hardware."
               --报文重定向在block 8 中的优先级，16表示没有过滤规则在硬件中
       ::= { qosTrafficRedirectEntry 20 }

   qosTrafficRedirectBlock9Priority OBJECT-TYPE
       SYNTAX  INTEGER(0..16)
       ACCESS  read-only
       STATUS  current
       DESCRIPTION
               "the block 9 priority of the traffic-redirect QOS. 16 means no filter rules in the Hardware."
               --报文重定向在block 9 中的优先级，16表示没有过滤规则在硬件中
       ::= { qosTrafficRedirectEntry 21 }

   qosTrafficRedirectBlock10Priority OBJECT-TYPE
       SYNTAX  INTEGER(0..16)
       ACCESS  read-only
       STATUS  current
       DESCRIPTION
               "the block 10 priority of the traffic-redirect QOS. 16 means no filter rules in the Hardware."
               --报文重定向在block 10 中的优先级，16表示没有过滤规则在硬件中
       ::= { qosTrafficRedirectEntry 22 }

   qosTrafficRedirectBlock11Priority OBJECT-TYPE
       SYNTAX  INTEGER(0..16)
       ACCESS  read-only
       STATUS  current
       DESCRIPTION
               "the block 11 priority of the traffic-redirect QOS. 16 means no filter rules in the Hardware."
               --报文重定向在block 11 中的优先级，16表示没有过滤规则在硬件中
       ::= { qosTrafficRedirectEntry 23 }

   -----------------------------------------------------
   -- the traffic statistics QOS
   -----------------------------------------------------

   qosTrafficStatisticsTable OBJECT-TYPE
       SYNTAX  SEQUENCE OF QosTrafficStatisticsEntry
       ACCESS  not-accessible
       STATUS  current
       DESCRIPTION
               "A list of traffic-statistics QOS entries. "
       ::= { gbnL2QACL 21}

   qosTrafficStatisticsEntry OBJECT-TYPE
       SYNTAX  QosTrafficStatisticsEntry
       ACCESS  not-accessible
       STATUS  current
       DESCRIPTION
               "A list of traffic-statistics QOS entries. "
       INDEX   { qosTrafficStatisticsIndex }
       ::= { qosTrafficStatisticsTable 1 }

   QosTrafficStatisticsEntry ::=
       SEQUENCE {
           qosTrafficStatisticsIndex
               INTEGER,
           qosTrafficStatisticsUserGroupName
               OCTET STRING,
           qosTrafficStatisticsUserGroupSubitem
               INTEGER,
           qosTrafficStatisticsIpGroupName
               OCTET STRING,
           qosTrafficStatisticsIpGroupSubitem
               INTEGER,
           qosTrafficStatisticsLinkGroupName
               OCTET STRING,
           qosTrafficStatisticsLinkGroupSubitem
               INTEGER,
           qosTrafficStatisticsBlock0Priority
               INTEGER,
           qosTrafficStatisticsBlock1Priority
               INTEGER,
           qosTrafficStatisticsBlock2Priority
               INTEGER,
           qosTrafficStatisticsBlock3Priority
               INTEGER,
           qosTrafficStatisticsBlock4Priority
               INTEGER,
           qosTrafficStatisticsConfigSequence
               INTEGER,
           qosTrafficStatisticsRunning
               TruthValue,
           qosTrafficStatisticsRowStatus
               RowStatus,
           qosTrafficStatisticsCounter
               Integer32,
           qosTrafficStatisticsBlock5Priority
               INTEGER,
           qosTrafficStatisticsBlock6Priority
               INTEGER,
           qosTrafficStatisticsBlock7Priority
               INTEGER,
           qosTrafficStatisticsBlock8Priority
               INTEGER,
           qosTrafficStatisticsBlock9Priority
               INTEGER,
           qosTrafficStatisticsBlock10Priority
               INTEGER,
           qosTrafficStatisticsBlock11Priority
               INTEGER,
           qosTrafficStatisticsDirection
               INTEGER
      }

   qosTrafficStatisticsIndex OBJECT-TYPE
       SYNTAX  INTEGER
       ACCESS  read-only
       STATUS  current
       DESCRIPTION
               "A unique value for each traffic-statistics QOS.  "
       ::= { qosTrafficStatisticsEntry 1 }

   qosTrafficStatisticsUserGroupName OBJECT-TYPE
       SYNTAX  OCTET STRING (SIZE (0..31))
       ACCESS  read-write
       STATUS  current
       DESCRIPTION
               "the name of the traffic-statistics QOS user group acl. "
       ::= { qosTrafficStatisticsEntry 2 }

   qosTrafficStatisticsUserGroupSubitem OBJECT-TYPE
       SYNTAX  INTEGER(0..127)
       ACCESS  read-write
       STATUS  current
       DESCRIPTION
               "the number of the traffic-statistics QOS user group acl subitem. "
       ::= { qosTrafficStatisticsEntry 3 }

   qosTrafficStatisticsIpGroupName OBJECT-TYPE
       SYNTAX  OCTET STRING (SIZE (0..31))
       ACCESS  read-write
       STATUS  current
       DESCRIPTION
               "the name of the traffic-statistics QOS ip group acl. "
       ::= { qosTrafficStatisticsEntry 4 }

   qosTrafficStatisticsIpGroupSubitem OBJECT-TYPE
       SYNTAX  INTEGER(0..127)
       ACCESS  read-write
       STATUS  current
       DESCRIPTION
               "the number of the traffic-statistics QOS ip group acl subitem. "
       ::= { qosTrafficStatisticsEntry 5 }

   qosTrafficStatisticsLinkGroupName OBJECT-TYPE
       SYNTAX  OCTET STRING (SIZE (0..31))
       ACCESS  read-write
       STATUS  current
       DESCRIPTION
               "the name of the traffic-statistics QOS link group acl. "
       ::= { qosTrafficStatisticsEntry 6 }

   qosTrafficStatisticsLinkGroupSubitem OBJECT-TYPE
       SYNTAX  INTEGER(0..127)
       ACCESS  read-write
       STATUS  current
       DESCRIPTION
               "the number of the traffic-statistics QOS link group acl subitem. "
       ::= { qosTrafficStatisticsEntry 7 }

   qosTrafficStatisticsBlock0Priority OBJECT-TYPE
       SYNTAX  INTEGER(0..16)
       ACCESS  read-only
       STATUS  current
       DESCRIPTION
               "the block 0 priority of the traffic-statistics QOS. 16 means no filter rules in the Hardware."
       ::= { qosTrafficStatisticsEntry 8 }

   qosTrafficStatisticsBlock1Priority OBJECT-TYPE
       SYNTAX  INTEGER(0..16)
       ACCESS  read-only
       STATUS  current
       DESCRIPTION
               "the block 1 priority of the traffic-statistics QOS. 16 means no filter rules in the Hardware."
       ::= { qosTrafficStatisticsEntry 9 }

   qosTrafficStatisticsBlock2Priority OBJECT-TYPE
       SYNTAX  INTEGER(0..16)
       ACCESS  read-only
       STATUS  current
       DESCRIPTION
               "the block 2 priority of the traffic-statistics QOS. 16 means no filter rules in the Hardware."
       ::= { qosTrafficStatisticsEntry 10 }

   qosTrafficStatisticsBlock3Priority OBJECT-TYPE
       SYNTAX  INTEGER(0..16)
       ACCESS  read-only
       STATUS  current
       DESCRIPTION
               "the block 3 priority of the traffic-statistics QOS. 16 means no filter rules in the Hardware."
       ::= { qosTrafficStatisticsEntry 11 }

   qosTrafficStatisticsBlock4Priority OBJECT-TYPE
       SYNTAX  INTEGER(0..16)
       ACCESS  read-only
       STATUS  current
       DESCRIPTION
               "the block 4 priority of the traffic-statistics QOS. 16 means no filter rules in the Hardware."
       ::= { qosTrafficStatisticsEntry 12 }

   qosTrafficStatisticsConfigSequence OBJECT-TYPE
       SYNTAX  INTEGER(1..1024)
       ACCESS  read-only
       STATUS  current
       DESCRIPTION
               "the config sequence of the traffic-statistics QOS."
       ::= { qosTrafficStatisticsEntry 13 }

   qosTrafficStatisticsRunning OBJECT-TYPE
        SYNTAX   TruthValue
        MAX-ACCESS   read-only
        STATUS   current
        DESCRIPTION
           "the running status of the traffic-statistics QOS."
       ::= { qosTrafficStatisticsEntry 14 }

   qosTrafficStatisticsRowStatus OBJECT-TYPE
       SYNTAX      RowStatus
       MAX-ACCESS  read-create
       STATUS      current
       DESCRIPTION
           "This object indicates the status of this entry."
       ::= { qosTrafficStatisticsEntry 15 }

   qosTrafficStatisticsCounter OBJECT-TYPE
       SYNTAX      Integer32
       MAX-ACCESS  read-create
       STATUS      current
       DESCRIPTION
           "This object indicates the value of the counter."
       ::= { qosTrafficStatisticsEntry 16 }

   qosTrafficStatisticsBlock5Priority OBJECT-TYPE
       SYNTAX  INTEGER(0..16)
       ACCESS  read-only
       STATUS  current
       DESCRIPTION
               "the block 5 priority of the traffic-statistics QOS. 16 means no filter rules in the Hardware."
               --流量统计在block 5 中的优先级，16表示没有过滤规则在硬件中
       ::= { qosTrafficStatisticsEntry 17 }

   qosTrafficStatisticsBlock6Priority OBJECT-TYPE
       SYNTAX  INTEGER(0..16)
       ACCESS  read-only
       STATUS  current
       DESCRIPTION
               "the block 6 priority of the traffic-statistics QOS. 16 means no filter rules in the Hardware."
               --流量统计在block 6 中的优先级，16表示没有过滤规则在硬件中
       ::= { qosTrafficStatisticsEntry 18 }

   qosTrafficStatisticsBlock7Priority OBJECT-TYPE
       SYNTAX  INTEGER(0..16)
       ACCESS  read-only
       STATUS  current
       DESCRIPTION
               "the block 7 priority of the traffic-statistics QOS. 16 means no filter rules in the Hardware."
               --流量统计在block 7 中的优先级，16表示没有过滤规则在硬件中
       ::= { qosTrafficStatisticsEntry 19 }

   qosTrafficStatisticsBlock8Priority OBJECT-TYPE
       SYNTAX  INTEGER(0..16)
       ACCESS  read-only
       STATUS  current
       DESCRIPTION
               "the block 8 priority of the traffic-statistics QOS. 16 means no filter rules in the Hardware."
               --流量统计在block 8 中的优先级，16表示没有过滤规则在硬件中
       ::= { qosTrafficStatisticsEntry 20 }

   qosTrafficStatisticsBlock9Priority OBJECT-TYPE
       SYNTAX  INTEGER(0..16)
       ACCESS  read-only
       STATUS  current
       DESCRIPTION
               "the block 9 priority of the traffic-statistics QOS. 16 means no filter rules in the Hardware."
               --流量统计在block 9 中的优先级，16表示没有过滤规则在硬件中
       ::= { qosTrafficStatisticsEntry 21 }

   qosTrafficStatisticsBlock10Priority OBJECT-TYPE
       SYNTAX  INTEGER(0..16)
       ACCESS  read-only
       STATUS  current
       DESCRIPTION
               "the block 10 priority of the traffic-statistics QOS. 16 means no filter rules in the Hardware."
               --流量统计在block 10 中的优先级，16表示没有过滤规则在硬件中
       ::= { qosTrafficStatisticsEntry 22 }

   qosTrafficStatisticsBlock11Priority OBJECT-TYPE
       SYNTAX  INTEGER(0..16)
       ACCESS  read-only
       STATUS  current
       DESCRIPTION
               "the block 11 priority of the traffic-statistics QOS. 16 means no filter rules in the Hardware."
               --流量统计在block 11 中的优先级，16表示没有过滤规则在硬件中
       ::= { qosTrafficStatisticsEntry 23 }

   qosTrafficStatisticsDirection OBJECT-TYPE
        SYNTAX  INTEGER {
                    inbound(0),
                    outbound(1)
                }
        ACCESS  read-write
        STATUS  current
        DESCRIPTION
                "ingress/egress of rule.default is inbound"
                --入口/出口acl，默认为入口。
        ::= { qosTrafficStatisticsEntry 24 }
   -----------------------------------------------------
   -- the line-rate QOS
   -----------------------------------------------------

   qosLineRateTable OBJECT-TYPE
       SYNTAX  SEQUENCE OF QosLineRateEntry
       ACCESS  not-accessible
       STATUS  current
       DESCRIPTION
               "A list of line-rate QOS entries. "
       ::= { gbnL2QACL 22 }

   qosLineRateEntry OBJECT-TYPE
       SYNTAX  QosLineRateEntry
       ACCESS  not-accessible
       STATUS  current
       DESCRIPTION
               "A list of line-rate QOS entries. "
       INDEX   { qosLineRateInterface }
       ::= { qosLineRateTable 1 }

   QosLineRateEntry ::=
       SEQUENCE {
           qosLineRateInterface
               INTEGER,
           qosLineRateTargetRate
               INTEGER
       }

   qosLineRateInterface OBJECT-TYPE
       SYNTAX  INTEGER (1..26)
       ACCESS  read-only
       STATUS  current
       DESCRIPTION
               "the line rate interface.  "
       ::= { qosLineRateEntry 1 }

   qosLineRateTargetRate OBJECT-TYPE
       SYNTAX  INTEGER (1..100)
       ACCESS  read-write
       STATUS  current
       DESCRIPTION
               "the target rate of the line-rate QOS. "
       ::= { qosLineRateEntry 2 }

   -----------------------------------------------------
   -- the traffic copy to cpu QOS
   -----------------------------------------------------

   qosTrafficCopyToCpuTable OBJECT-TYPE
       SYNTAX  SEQUENCE OF QosTrafficCopyToCpuEntry
       ACCESS  not-accessible
       STATUS  current
       DESCRIPTION
               "A list of traffic-copy-to-cpu QOS entries. "
       ::= { gbnL2QACL 23 }

   qosTrafficCopyToCpuEntry OBJECT-TYPE
       SYNTAX  QosTrafficCopyToCpuEntry
       ACCESS  not-accessible
       STATUS  current
       DESCRIPTION
               "A list of traffic-copy-to-cpu QOS entries. "
       INDEX   { qosTrafficCopyToCpuIndex }
       ::= { qosTrafficCopyToCpuTable 1 }

   QosTrafficCopyToCpuEntry ::=
       SEQUENCE {
           qosTrafficCopyToCpuIndex
               INTEGER,
           qosTrafficCopyToCpuUserGroupName
               OCTET STRING,
           qosTrafficCopyToCpuUserGroupSubitem
               INTEGER,
           qosTrafficCopyToCpuIpGroupName
               OCTET STRING,
           qosTrafficCopyToCpuIpGroupSubitem
               INTEGER,
           qosTrafficCopyToCpuLinkGroupName
               OCTET STRING,
           qosTrafficCopyToCpuLinkGroupSubitem
               INTEGER,
           qosTrafficCopyToCpuBlock0Priority
               INTEGER,
           qosTrafficCopyToCpuBlock1Priority
               INTEGER,
           qosTrafficCopyToCpuBlock2Priority
               INTEGER,
           qosTrafficCopyToCpuBlock3Priority
               INTEGER,
           qosTrafficCopyToCpuBlock4Priority
               INTEGER,
           qosTrafficCopyToCpuConfigSequence
               INTEGER,
           qosTrafficCopyToCpuRunning
               TruthValue,
           qosTrafficCopyToCpuRowStatus
               RowStatus,
           qosTrafficCopyToCpuBlock5Priority
               INTEGER,
           qosTrafficCopyToCpuBlock6Priority
               INTEGER,
           qosTrafficCopyToCpuBlock7Priority
               INTEGER,
           qosTrafficCopyToCpuBlock8Priority
               INTEGER,
           qosTrafficCopyToCpuBlock9Priority
               INTEGER,
           qosTrafficCopyToCpuBlock10Priority
               INTEGER,
           qosTrafficCopyToCpuBlock11Priority
               INTEGER
       }

   qosTrafficCopyToCpuIndex OBJECT-TYPE
       SYNTAX  INTEGER
       ACCESS  read-only
       STATUS  current
       DESCRIPTION
               "A unique value for each traffic-copy-to-cpu QOS.  "
       ::= { qosTrafficCopyToCpuEntry 1 }

   qosTrafficCopyToCpuUserGroupName OBJECT-TYPE
       SYNTAX  OCTET STRING (SIZE (0..31))
       ACCESS  read-write
       STATUS  current
       DESCRIPTION
               "the name of the traffic-copy-to-cpu QOS user group acl. "
       ::= { qosTrafficCopyToCpuEntry 2 }

   qosTrafficCopyToCpuUserGroupSubitem OBJECT-TYPE
       SYNTAX  INTEGER(0..127)
       ACCESS  read-write
       STATUS  current
       DESCRIPTION
               "the number of the traffic-copy-to-cpu QOS user group acl subitem. "
       ::= { qosTrafficCopyToCpuEntry 3 }

   qosTrafficCopyToCpuIpGroupName OBJECT-TYPE
       SYNTAX  OCTET STRING (SIZE (0..31))
       ACCESS  read-write
       STATUS  current
       DESCRIPTION
               "the name of the traffic-copy-to-cpu QOS ip group acl. "
       ::= { qosTrafficCopyToCpuEntry 4 }

   qosTrafficCopyToCpuIpGroupSubitem OBJECT-TYPE
       SYNTAX  INTEGER(0..127)
       ACCESS  read-write
       STATUS  current
       DESCRIPTION
               "the number of the traffic-copy-to-cpu QOS ip group acl subitem. "
       ::= { qosTrafficCopyToCpuEntry 5 }

   qosTrafficCopyToCpuLinkGroupName OBJECT-TYPE
       SYNTAX  OCTET STRING (SIZE (0..31))
       ACCESS  read-write
       STATUS  current
       DESCRIPTION
               "the name of the traffic-copy-to-cpu QOS link group acl. "
       ::= { qosTrafficCopyToCpuEntry 6 }

   qosTrafficCopyToCpuLinkGroupSubitem OBJECT-TYPE
       SYNTAX  INTEGER(0..127)
       ACCESS  read-write
       STATUS  current
       DESCRIPTION
               "the number of the traffic-copy-to-cpu QOS link group acl subitem. "
       ::= { qosTrafficCopyToCpuEntry 7 }

   qosTrafficCopyToCpuBlock0Priority OBJECT-TYPE
       SYNTAX  INTEGER(0..16)
       ACCESS  read-only
       STATUS  current
       DESCRIPTION
               "the block 0 priority of the traffic-copy-to-cpu QOS. 16 means no filter rules in the Hardware."
       ::= { qosTrafficCopyToCpuEntry 8 }

   qosTrafficCopyToCpuBlock1Priority OBJECT-TYPE
       SYNTAX  INTEGER(0..16)
       ACCESS  read-only
       STATUS  current
       DESCRIPTION
               "the block 1 priority of the traffic-copy-to-cpu QOS. 16 means no filter rules in the Hardware."
       ::= { qosTrafficCopyToCpuEntry 9 }

   qosTrafficCopyToCpuBlock2Priority OBJECT-TYPE
       SYNTAX  INTEGER(0..16)
       ACCESS  read-only
       STATUS  current
       DESCRIPTION
               "the block 2 priority of the traffic-copy-to-cpu QOS. 16 means no filter rules in the Hardware."
       ::= { qosTrafficCopyToCpuEntry 10 }

   qosTrafficCopyToCpuBlock3Priority OBJECT-TYPE
       SYNTAX  INTEGER(0..16)
       ACCESS  read-only
       STATUS  current
       DESCRIPTION
               "the block 3 priority of the traffic-copy-to-cpu QOS. 16 means no filter rules in the Hardware."
       ::= { qosTrafficCopyToCpuEntry 11 }

   qosTrafficCopyToCpuBlock4Priority OBJECT-TYPE
       SYNTAX  INTEGER(0..16)
       ACCESS  read-only
       STATUS  current
       DESCRIPTION
               "the block 4 priority of the traffic-copy-to-cpu QOS. 16 means no filter rules in the Hardware."
       ::= { qosTrafficCopyToCpuEntry 12 }

   qosTrafficCopyToCpuConfigSequence OBJECT-TYPE
       SYNTAX  INTEGER(1..1024)
       ACCESS  read-only
       STATUS  current
       DESCRIPTION
               "the config sequence of the traffic-copy-to-cpu QOS."
       ::= { qosTrafficCopyToCpuEntry 13 }

   qosTrafficCopyToCpuRunning OBJECT-TYPE
        SYNTAX   TruthValue
        MAX-ACCESS   read-only
        STATUS   current
        DESCRIPTION
           "the running status of the traffic-copy-to-cpu QOS."
       ::= { qosTrafficCopyToCpuEntry 14 }

   qosTrafficCopyToCpuRowStatus OBJECT-TYPE
       SYNTAX      RowStatus
       MAX-ACCESS  read-create
       STATUS      current
       DESCRIPTION
           "This object indicates the status of this entry."
       ::= { qosTrafficCopyToCpuEntry 15 }

   qosTrafficCopyToCpuBlock5Priority OBJECT-TYPE
       SYNTAX  INTEGER(0..16)
       ACCESS  read-only
       STATUS  current
       DESCRIPTION
               "the block 5 priority of the traffic-copy-to-cpu QOS. 16 means no filter rules in the Hardware."
               --报文拷贝到CPU在block 5 中的优先级，16表示没有过滤规则在硬件中
       ::= { qosTrafficCopyToCpuEntry 16 }

   qosTrafficCopyToCpuBlock6Priority OBJECT-TYPE
       SYNTAX  INTEGER(0..16)
       ACCESS  read-only
       STATUS  current
       DESCRIPTION
               "the block 6 priority of the traffic-copy-to-cpu QOS. 16 means no filter rules in the Hardware."
               --报文拷贝到CPU在block 6 中的优先级，16表示没有过滤规则在硬件中
       ::= { qosTrafficCopyToCpuEntry 17 }

   qosTrafficCopyToCpuBlock7Priority OBJECT-TYPE
       SYNTAX  INTEGER(0..16)
       ACCESS  read-only
       STATUS  current
       DESCRIPTION
               "the block 7 priority of the traffic-copy-to-cpu QOS. 16 means no filter rules in the Hardware."
               --报文拷贝到CPU在block 7 中的优先级，16表示没有过滤规则在硬件中
       ::= { qosTrafficCopyToCpuEntry 18 }

   qosTrafficCopyToCpuBlock8Priority OBJECT-TYPE
       SYNTAX  INTEGER(0..16)
       ACCESS  read-only
       STATUS  current
       DESCRIPTION
               "the block 8 priority of the traffic-copy-to-cpu QOS. 16 means no filter rules in the Hardware."
               --报文拷贝到CPU在block 8 中的优先级，16表示没有过滤规则在硬件中
       ::= { qosTrafficCopyToCpuEntry 19 }

   qosTrafficCopyToCpuBlock9Priority OBJECT-TYPE
       SYNTAX  INTEGER(0..16)
       ACCESS  read-only
       STATUS  current
       DESCRIPTION
               "the block 9 priority of the traffic-copy-to-cpu QOS. 16 means no filter rules in the Hardware."
               --报文拷贝到CPU在block 9 中的优先级，16表示没有过滤规则在硬件中
       ::= { qosTrafficCopyToCpuEntry 20 }

   qosTrafficCopyToCpuBlock10Priority OBJECT-TYPE
       SYNTAX  INTEGER(0..16)
       ACCESS  read-only
       STATUS  current
       DESCRIPTION
               "the block 10 priority of the traffic-copy-to-cpu QOS. 16 means no filter rules in the Hardware."
               --报文拷贝到CPU在block 10 中的优先级，16表示没有过滤规则在硬件中
       ::= { qosTrafficCopyToCpuEntry 21 }

   qosTrafficCopyToCpuBlock11Priority OBJECT-TYPE
       SYNTAX  INTEGER(0..16)
       ACCESS  read-only
       STATUS  current
       DESCRIPTION
               "the block 11 priority of the traffic-copy-to-cpu QOS. 16 means no filter rules in the Hardware."
               --报文拷贝到CPU在block 11 中的优先级，16表示没有过滤规则在硬件中
       ::= { qosTrafficCopyToCpuEntry 22 }

   -----------------------------------------------------
   -- the port-isolation configuration
   -----------------------------------------------------
   qaclAppPortIsolationGroup  OBJECT IDENTIFIER ::= { gbnL2QACL 24 }

   qaclAppPortIsolationDownLinkPorts OBJECT-TYPE
       SYNTAX  PortList
       ACCESS  read-write
       STATUS  current
       DESCRIPTION
               "qacl application port isolation down link portlist"
               -- QACL应用端口隔离的下行端口列表 --
       ::= { qaclAppPortIsolationGroup 1 }

   -----------------------------------------------------
   -- the storm control
   -----------------------------------------------------

   stormControlTable OBJECT-TYPE
       SYNTAX  SEQUENCE OF StormControlEntry
       ACCESS  not-accessible
       STATUS  current
       DESCRIPTION
               "A list of storm control entries. "
       ::= { gbnL2QACL 25 }

   stormControlEntry OBJECT-TYPE
       SYNTAX  StormControlEntry
       ACCESS  not-accessible
       STATUS  current
       DESCRIPTION
               "A list of storm control entries. "
       INDEX   { stormControlInterface, stormControlType }
       ::= { stormControlTable 1 }

   StormControlEntry ::=
       SEQUENCE {
           stormControlInterface
               INTEGER,
           stormControlType
               PacketFlowType,
           stormControlTargetRate
               INTEGER,
           stormControlRowStatus
               RowStatus
       }

   stormControlInterface OBJECT-TYPE
       SYNTAX  INTEGER (1..26)
       ACCESS  read-only
       STATUS  current
       DESCRIPTION
               "the storm control interface. "
               --风暴控制端口
       ::= { stormControlEntry 1 }

   stormControlType OBJECT-TYPE
       SYNTAX  PacketFlowType
       ACCESS  read-only
       STATUS  current
       DESCRIPTION
               "the pack flow type of the storm control. "
               --风暴控制报文流类型
       ::= { stormControlEntry 2 }

   stormControlTargetRate OBJECT-TYPE
       SYNTAX  INTEGER (1..1000)
       ACCESS  read-write
       STATUS  current
       DESCRIPTION
               "the target rate of the storm control. "
               --风暴控制目标速率
       ::= { stormControlEntry 3 }

   stormControlRowStatus OBJECT-TYPE
        SYNTAX   RowStatus
        MAX-ACCESS   read-write
        STATUS   current
        DESCRIPTION
                "row status of the storm control"
                --风暴控制行状态
        ::= { stormControlEntry 4 }

   -----------------------------------------------------
   -- the traffic rewrite vlan QOS
   -----------------------------------------------------

   qosTrafficRewriteVlanTable OBJECT-TYPE
       SYNTAX  SEQUENCE OF QosTrafficRewriteVlanEntry
       ACCESS  not-accessible
       STATUS  current
       DESCRIPTION
               "A list of traffic-rewrite-vlan QOS entries. "
       ::= { gbnL2QACL 26 }

   qosTrafficRewriteVlanEntry OBJECT-TYPE
       SYNTAX  QosTrafficRewriteVlanEntry
       ACCESS  not-accessible
       STATUS  current
       DESCRIPTION
               "A list of traffic-rewrite-vlan QOS entries. "
       INDEX   { qosTrafficRewriteVlanIndex }
       ::= { qosTrafficRewriteVlanTable 1 }

   QosTrafficRewriteVlanEntry ::=
       SEQUENCE {
           qosTrafficRewriteVlanIndex
               INTEGER,
           qosTrafficRewriteVlanUserGroupName
               OCTET STRING,
           qosTrafficRewriteVlanUserGroupSubitem
               INTEGER,
           qosTrafficRewriteVlanIpGroupName
               OCTET STRING,
           qosTrafficRewriteVlanIpGroupSubitem
               INTEGER,
           qosTrafficRewriteVlanLinkGroupName
               OCTET STRING,
           qosTrafficRewriteVlanLinkGroupSubitem
               INTEGER,
           qosTrafficRewriteVlanVid
               INTEGER,
           qosTrafficRewriteVlanBlock0Priority
               INTEGER,
           qosTrafficRewriteVlanBlock1Priority
               INTEGER,
           qosTrafficRewriteVlanBlock2Priority
               INTEGER,
           qosTrafficRewriteVlanBlock3Priority
               INTEGER,
           qosTrafficRewriteVlanBlock4Priority
               INTEGER,
           qosTrafficRewriteVlanConfigSequence
               INTEGER,
           qosTrafficRewriteVlanRunning
               TruthValue,
           qosTrafficRewriteVlanRowStatus
               RowStatus,
           qosTrafficRewriteVlanBlock5Priority
               INTEGER,
           qosTrafficRewriteVlanBlock6Priority
               INTEGER,
           qosTrafficRewriteVlanBlock7Priority
               INTEGER,
           qosTrafficRewriteVlanBlock8Priority
               INTEGER,
           qosTrafficRewriteVlanBlock9Priority
               INTEGER,
           qosTrafficRewriteVlanBlock10Priority
               INTEGER,
           qosTrafficRewriteVlanBlock11Priority
               INTEGER
       }

   qosTrafficRewriteVlanIndex OBJECT-TYPE
       SYNTAX  INTEGER
       ACCESS  read-only
       STATUS  current
       DESCRIPTION
               "A unique value for each traffic-rewrite-vlan QOS.  "
       ::= { qosTrafficRewriteVlanEntry 1 }

   qosTrafficRewriteVlanUserGroupName OBJECT-TYPE
       SYNTAX  OCTET STRING (SIZE (0..31))
       ACCESS  read-write
       STATUS  current
       DESCRIPTION
               "the name of the traffic-rewrite-vlan QOS user group acl. "
       ::= { qosTrafficRewriteVlanEntry 2 }

   qosTrafficRewriteVlanUserGroupSubitem OBJECT-TYPE
       SYNTAX  INTEGER(0..127)
       ACCESS  read-write
       STATUS  current
       DESCRIPTION
               "the number of the traffic-rewrite-vlan QOS user group acl subitem. "
       ::= { qosTrafficRewriteVlanEntry 3 }

   qosTrafficRewriteVlanIpGroupName OBJECT-TYPE
       SYNTAX  OCTET STRING (SIZE (0..31))
       ACCESS  read-write
       STATUS  current
       DESCRIPTION
               "the name of the traffic-rewrite-vlan QOS ip group acl. "
       ::= { qosTrafficRewriteVlanEntry 4 }

   qosTrafficRewriteVlanIpGroupSubitem OBJECT-TYPE
       SYNTAX  INTEGER(0..127)
       ACCESS  read-write
       STATUS  current
       DESCRIPTION
               "the number of the traffic-rewrite-vlan QOS ip group acl subitem. "
       ::= { qosTrafficRewriteVlanEntry 5 }

   qosTrafficRewriteVlanLinkGroupName OBJECT-TYPE
       SYNTAX  OCTET STRING (SIZE (0..31))
       ACCESS  read-write
       STATUS  current
       DESCRIPTION
               "the name of the traffic-rewrite-vlan QOS link group acl. "
       ::= { qosTrafficRewriteVlanEntry 6 }

   qosTrafficRewriteVlanLinkGroupSubitem OBJECT-TYPE
       SYNTAX  INTEGER(0..127)
       ACCESS  read-write
       STATUS  current
       DESCRIPTION
               "the number of the traffic-rewrite-vlan QOS link group acl subitem. "
       ::= { qosTrafficRewriteVlanEntry 7 }

   qosTrafficRewriteVlanVid OBJECT-TYPE
       SYNTAX  INTEGER (1..28)
       ACCESS  read-write
       STATUS  current
       DESCRIPTION
               "the vlan ID of the traffic-rewrite-vlan QOS.1－24 for fast-ethernet port 1－24，25－26 for giga-ethernet port 1－2，28 for CPU port，27 is invaild value. "
       ::= { qosTrafficRewriteVlanEntry 8 }

   qosTrafficRewriteVlanBlock0Priority OBJECT-TYPE
       SYNTAX  INTEGER(0..16)
       ACCESS  read-only
       STATUS  current
       DESCRIPTION
               "the block 0 priority of the traffic-rewrite-vlan QOS. 16 means no filter rules in the Hardware."
       ::= { qosTrafficRewriteVlanEntry 9 }

   qosTrafficRewriteVlanBlock1Priority OBJECT-TYPE
       SYNTAX  INTEGER(0..16)
       ACCESS  read-only
       STATUS  current
       DESCRIPTION
               "the block 1 priority of the traffic-rewrite-vlan QOS. 16 means no filter rules in the Hardware."
       ::= { qosTrafficRewriteVlanEntry 10 }

   qosTrafficRewriteVlanBlock2Priority OBJECT-TYPE
       SYNTAX  INTEGER(0..16)
       ACCESS  read-only
       STATUS  current
       DESCRIPTION
               "the block 2 priority of the traffic-rewrite-vlan QOS. 16 means no filter rules in the Hardware."
       ::= { qosTrafficRewriteVlanEntry 11 }

   qosTrafficRewriteVlanBlock3Priority OBJECT-TYPE
       SYNTAX  INTEGER(0..16)
       ACCESS  read-only
       STATUS  current
       DESCRIPTION
               "the block 3 priority of the traffic-rewrite-vlan QOS. 16 means no filter rules in the Hardware."
       ::= { qosTrafficRewriteVlanEntry 12 }

   qosTrafficRewriteVlanBlock4Priority OBJECT-TYPE
       SYNTAX  INTEGER(0..16)
       ACCESS  read-only
       STATUS  current
       DESCRIPTION
               "the block 4 priority of the traffic-rewrite-vlan QOS. 16 means no filter rules in the Hardware."
       ::= { qosTrafficRewriteVlanEntry 13 }

   qosTrafficRewriteVlanConfigSequence OBJECT-TYPE
       SYNTAX  INTEGER(1..1024)
       ACCESS  read-only
       STATUS  current
       DESCRIPTION
               "the config sequence of the traffic-rewrite-vlan QOS."
       ::= { qosTrafficRewriteVlanEntry 14 }

   qosTrafficRewriteVlanRunning OBJECT-TYPE
        SYNTAX   TruthValue
        MAX-ACCESS   read-only
        STATUS   current
        DESCRIPTION
           "the running status of the traffic-rewrite-vlan QOS."
       ::= { qosTrafficRewriteVlanEntry 15 }

   qosTrafficRewriteVlanRowStatus OBJECT-TYPE
       SYNTAX      RowStatus
       MAX-ACCESS  read-create
       STATUS      current
       DESCRIPTION
           "This object indicates the status of this entry."
       ::= { qosTrafficRewriteVlanEntry 16 }

   qosTrafficRewriteVlanBlock5Priority OBJECT-TYPE
       SYNTAX  INTEGER(0..16)
       ACCESS  read-only
       STATUS  current
       DESCRIPTION
               "the block 5 priority of the traffic-rewrite-vlan QOS. 16 means no filter rules in the Hardware."
       ::= { qosTrafficRewriteVlanEntry 17 }

   qosTrafficRewriteVlanBlock6Priority OBJECT-TYPE
       SYNTAX  INTEGER(0..16)
       ACCESS  read-only
       STATUS  current
       DESCRIPTION
               "the block 6 priority of the traffic-rewrite-vlan QOS. 16 means no filter rules in the Hardware."
       ::= { qosTrafficRewriteVlanEntry 18 }

   qosTrafficRewriteVlanBlock7Priority OBJECT-TYPE
       SYNTAX  INTEGER(0..16)
       ACCESS  read-only
       STATUS  current
       DESCRIPTION
               "the block 7 priority of the traffic-rewrite-vlan QOS. 16 means no filter rules in the Hardware."
       ::= { qosTrafficRewriteVlanEntry 19 }

   qosTrafficRewriteVlanBlock8Priority OBJECT-TYPE
       SYNTAX  INTEGER(0..16)
       ACCESS  read-only
       STATUS  current
       DESCRIPTION
               "the block 8 priority of the traffic-rewrite-vlan QOS. 16 means no filter rules in the Hardware."
       ::= { qosTrafficRewriteVlanEntry 20 }

   qosTrafficRewriteVlanBlock9Priority OBJECT-TYPE
       SYNTAX  INTEGER(0..16)
       ACCESS  read-only
       STATUS  current
       DESCRIPTION
               "the block 9 priority of the traffic-rewrite-vlan QOS. 16 means no filter rules in the Hardware."
       ::= { qosTrafficRewriteVlanEntry 21 }

   qosTrafficRewriteVlanBlock10Priority OBJECT-TYPE
       SYNTAX  INTEGER(0..16)
       ACCESS  read-only
       STATUS  current
       DESCRIPTION
               "the block 10 priority of the traffic-rewrite-vlan QOS. 16 means no filter rules in the Hardware."
       ::= { qosTrafficRewriteVlanEntry 22 }

   qosTrafficRewriteVlanBlock11Priority OBJECT-TYPE
       SYNTAX  INTEGER(0..16)
       ACCESS  read-only
       STATUS  current
       DESCRIPTION
               "the block 11 priority of the traffic-rewrite-vlan QOS. 16 means no filter rules in the Hardware."
       ::= { qosTrafficRewriteVlanEntry 23 }

   -----------------------------------------------------
   -- the traffic insert vlan QOS
   -----------------------------------------------------

   qosTrafficInsertVlanTable OBJECT-TYPE
       SYNTAX  SEQUENCE OF QosTrafficInsertVlanEntry
       ACCESS  not-accessible
       STATUS  current
       DESCRIPTION
               "A list of traffic-insert-vlan QOS entries. "
       ::= { gbnL2QACL 27 }

   qosTrafficInsertVlanEntry OBJECT-TYPE
       SYNTAX  QosTrafficInsertVlanEntry
       ACCESS  not-accessible
       STATUS  current
       DESCRIPTION
               "A list of traffic-insert-vlan QOS entries. "
       INDEX   { qosTrafficInsertVlanIndex }
       ::= { qosTrafficInsertVlanTable 1 }

   QosTrafficInsertVlanEntry ::=
       SEQUENCE {
           qosTrafficInsertVlanIndex
               INTEGER,
           qosTrafficInsertVlanUserGroupName
               OCTET STRING,
           qosTrafficInsertVlanUserGroupSubitem
               INTEGER,
           qosTrafficInsertVlanIpGroupName
               OCTET STRING,
           qosTrafficInsertVlanIpGroupSubitem
               INTEGER,
           qosTrafficInsertVlanLinkGroupName
               OCTET STRING,
           qosTrafficInsertVlanLinkGroupSubitem
               INTEGER,
           qosTrafficInsertVlanVid
               INTEGER,
           qosTrafficInsertVlanBlock0Priority
               INTEGER,
           qosTrafficInsertVlanBlock1Priority
               INTEGER,
           qosTrafficInsertVlanBlock2Priority
               INTEGER,
           qosTrafficInsertVlanBlock3Priority
               INTEGER,
           qosTrafficInsertVlanBlock4Priority
               INTEGER,
           qosTrafficInsertVlanConfigSequence
               INTEGER,
           qosTrafficInsertVlanRunning
               TruthValue,
           qosTrafficInsertVlanRowStatus
               RowStatus,
           qosTrafficInsertVlanBlock5Priority
               INTEGER,
           qosTrafficInsertVlanBlock6Priority
               INTEGER,
           qosTrafficInsertVlanBlock7Priority
               INTEGER,
           qosTrafficInsertVlanBlock8Priority
               INTEGER,
           qosTrafficInsertVlanBlock9Priority
               INTEGER,
           qosTrafficInsertVlanBlock10Priority
               INTEGER,
           qosTrafficInsertVlanBlock11Priority
               INTEGER
       }

   qosTrafficInsertVlanIndex OBJECT-TYPE
       SYNTAX  INTEGER
       ACCESS  read-only
       STATUS  current
       DESCRIPTION
               "A unique value for each traffic-insert-vlan QOS.  "
       ::= { qosTrafficInsertVlanEntry 1 }

   qosTrafficInsertVlanUserGroupName OBJECT-TYPE
       SYNTAX  OCTET STRING (SIZE (0..31))
       ACCESS  read-write
       STATUS  current
       DESCRIPTION
               "the name of the traffic-insert-vlan QOS user group acl. "
       ::= { qosTrafficInsertVlanEntry 2 }

   qosTrafficInsertVlanUserGroupSubitem OBJECT-TYPE
       SYNTAX  INTEGER(0..127)
       ACCESS  read-write
       STATUS  current
       DESCRIPTION
               "the number of the traffic-insert-vlan QOS user group acl subitem. "
       ::= { qosTrafficInsertVlanEntry 3 }

   qosTrafficInsertVlanIpGroupName OBJECT-TYPE
       SYNTAX  OCTET STRING (SIZE (0..31))
       ACCESS  read-write
       STATUS  current
       DESCRIPTION
               "the name of the traffic-insert-vlan QOS ip group acl. "
       ::= { qosTrafficInsertVlanEntry 4 }

   qosTrafficInsertVlanIpGroupSubitem OBJECT-TYPE
       SYNTAX  INTEGER(0..127)
       ACCESS  read-write
       STATUS  current
       DESCRIPTION
               "the number of the traffic-insert-vlan QOS ip group acl subitem. "
       ::= { qosTrafficInsertVlanEntry 5 }

   qosTrafficInsertVlanLinkGroupName OBJECT-TYPE
       SYNTAX  OCTET STRING (SIZE (0..31))
       ACCESS  read-write
       STATUS  current
       DESCRIPTION
               "the name of the traffic-insert-vlan QOS link group acl. "
       ::= { qosTrafficInsertVlanEntry 6 }

   qosTrafficInsertVlanLinkGroupSubitem OBJECT-TYPE
       SYNTAX  INTEGER(0..127)
       ACCESS  read-write
       STATUS  current
       DESCRIPTION
               "the number of the traffic-insert-vlan QOS link group acl subitem. "
       ::= { qosTrafficInsertVlanEntry 7 }

   qosTrafficInsertVlanVid OBJECT-TYPE
       SYNTAX  INTEGER (1..28)
       ACCESS  read-write
       STATUS  current
       DESCRIPTION
               "the vlan ID of the traffic-insert-vlan QOS.1－24 for fast-ethernet port 1－24，25－26 for giga-ethernet port 1－2，28 for CPU port，27 is invaild value. "
       ::= { qosTrafficInsertVlanEntry 8 }

   qosTrafficInsertVlanBlock0Priority OBJECT-TYPE
       SYNTAX  INTEGER(0..16)
       ACCESS  read-only
       STATUS  current
       DESCRIPTION
               "the block 0 priority of the traffic-insert-vlan QOS. 16 means no filter rules in the Hardware."
       ::= { qosTrafficInsertVlanEntry 9 }

   qosTrafficInsertVlanBlock1Priority OBJECT-TYPE
       SYNTAX  INTEGER(0..16)
       ACCESS  read-only
       STATUS  current
       DESCRIPTION
               "the block 1 priority of the traffic-insert-vlan QOS. 16 means no filter rules in the Hardware."
       ::= { qosTrafficInsertVlanEntry 10 }

   qosTrafficInsertVlanBlock2Priority OBJECT-TYPE
       SYNTAX  INTEGER(0..16)
       ACCESS  read-only
       STATUS  current
       DESCRIPTION
               "the block 2 priority of the traffic-insert-vlan QOS. 16 means no filter rules in the Hardware."
       ::= { qosTrafficInsertVlanEntry 11 }

   qosTrafficInsertVlanBlock3Priority OBJECT-TYPE
       SYNTAX  INTEGER(0..16)
       ACCESS  read-only
       STATUS  current
       DESCRIPTION
               "the block 3 priority of the traffic-insert-vlan QOS. 16 means no filter rules in the Hardware."
       ::= { qosTrafficInsertVlanEntry 12 }

   qosTrafficInsertVlanBlock4Priority OBJECT-TYPE
       SYNTAX  INTEGER(0..16)
       ACCESS  read-only
       STATUS  current
       DESCRIPTION
               "the block 4 priority of the traffic-insert-vlan QOS. 16 means no filter rules in the Hardware."
       ::= { qosTrafficInsertVlanEntry 13 }

   qosTrafficInsertVlanConfigSequence OBJECT-TYPE
       SYNTAX  INTEGER(1..1024)
       ACCESS  read-only
       STATUS  current
       DESCRIPTION
               "the config sequence of the traffic-insert-vlan QOS."
       ::= { qosTrafficInsertVlanEntry 14 }

   qosTrafficInsertVlanRunning OBJECT-TYPE
        SYNTAX   TruthValue
        MAX-ACCESS   read-only
        STATUS   current
        DESCRIPTION
           "the running status of the traffic-insert-vlan QOS."
       ::= { qosTrafficInsertVlanEntry 15 }

   qosTrafficInsertVlanRowStatus OBJECT-TYPE
       SYNTAX      RowStatus
       MAX-ACCESS  read-create
       STATUS      current
       DESCRIPTION
           "This object indicates the status of this entry."
       ::= { qosTrafficInsertVlanEntry 16 }

   qosTrafficInsertVlanBlock5Priority OBJECT-TYPE
       SYNTAX  INTEGER(0..16)
       ACCESS  read-only
       STATUS  current
       DESCRIPTION
               "the block 5 priority of the traffic-insert-vlan QOS. 16 means no filter rules in the Hardware."
       ::= { qosTrafficInsertVlanEntry 17 }

   qosTrafficInsertVlanBlock6Priority OBJECT-TYPE
       SYNTAX  INTEGER(0..16)
       ACCESS  read-only
       STATUS  current
       DESCRIPTION
               "the block 6 priority of the traffic-insert-vlan QOS. 16 means no filter rules in the Hardware."
       ::= { qosTrafficInsertVlanEntry 18 }

   qosTrafficInsertVlanBlock7Priority OBJECT-TYPE
       SYNTAX  INTEGER(0..16)
       ACCESS  read-only
       STATUS  current
       DESCRIPTION
               "the block 7 priority of the traffic-insert-vlan QOS. 16 means no filter rules in the Hardware."
       ::= { qosTrafficInsertVlanEntry 19 }

   qosTrafficInsertVlanBlock8Priority OBJECT-TYPE
       SYNTAX  INTEGER(0..16)
       ACCESS  read-only
       STATUS  current
       DESCRIPTION
               "the block 8 priority of the traffic-insert-vlan QOS. 16 means no filter rules in the Hardware."
       ::= { qosTrafficInsertVlanEntry 20 }

   qosTrafficInsertVlanBlock9Priority OBJECT-TYPE
       SYNTAX  INTEGER(0..16)
       ACCESS  read-only
       STATUS  current
       DESCRIPTION
               "the block 9 priority of the traffic-insert-vlan QOS. 16 means no filter rules in the Hardware."
       ::= { qosTrafficInsertVlanEntry 21 }

   qosTrafficInsertVlanBlock10Priority OBJECT-TYPE
       SYNTAX  INTEGER(0..16)
       ACCESS  read-only
       STATUS  current
       DESCRIPTION
               "the block 10 priority of the traffic-insert-vlan QOS. 16 means no filter rules in the Hardware."
       ::= { qosTrafficInsertVlanEntry 22 }

   qosTrafficInsertVlanBlock11Priority OBJECT-TYPE
       SYNTAX  INTEGER(0..16)
       ACCESS  read-only
       STATUS  current
       DESCRIPTION
               "the block 11 priority of the traffic-insert-vlan QOS. 16 means no filter rules in the Hardware."
       ::= { qosTrafficInsertVlanEntry 23 }

   -----------------------------------------------------
   -- the two rate policer
   -----------------------------------------------------

   qosTwoRatePolicerTable OBJECT-TYPE
       SYNTAX  SEQUENCE OF QosTwoRatePolicerEntry
       ACCESS  not-accessible
       STATUS  current
       DESCRIPTION
               "A list of two rate policer entries. "
       ::= { gbnL2QACL 28 }

   qosTwoRatePolicerEntry OBJECT-TYPE
       SYNTAX  QosTwoRatePolicerEntry
       ACCESS  not-accessible
       STATUS  current
       DESCRIPTION
               "A list of two rate policer entries. "
       INDEX   { qosTwoRatePolicerId }
       ::= { qosTwoRatePolicerTable 1 }

   QosTwoRatePolicerEntry ::=
       SEQUENCE {
           qosTwoRatePolicerId
               INTEGER,
           qosTwoRatePolicerCir
               INTEGER,
           qosTwoRatePolicerCbs
               INTEGER,
           qosTwoRatePolicerPir
               INTEGER,
           qosTwoRatePolicerPbs
               INTEGER,
           qosTwoRatePolicerColorAware
               TruthValue,
           qosTwoRatePolicerL2PriorityRemark
               TruthValue,
           qosTwoRatePolicerL3PriorityRemark
               TruthValue,
           qosTwoRatePolicerRemarkDscpCos
               TruthValue,
           qosTwoRatePolicerRemarkTrafficClass
               TruthValue,
           qosTwoRatePolicerDropRed
               TruthValue,
           qosTwoRatePolicerUseNum
               INTEGER,
           qosTwoRatePolicerRowStatus
               RowStatus
       }

   qosTwoRatePolicerId OBJECT-TYPE
       SYNTAX  INTEGER
       ACCESS  read-only
       STATUS  current
       DESCRIPTION
               "the two rate policer ID. "
       ::= { qosTwoRatePolicerEntry 1 }

   qosTwoRatePolicerCir OBJECT-TYPE
       SYNTAX  INTEGER
       ACCESS  read-write
       STATUS  current
       DESCRIPTION
               "the two rate policer Committed Information Rate(CIR). "
       ::= { qosTwoRatePolicerEntry 2 }

   qosTwoRatePolicerCbs OBJECT-TYPE
       SYNTAX  INTEGER
       ACCESS  read-write
       STATUS  current
       DESCRIPTION
               "the two rate policer Committed Burst Size(CBS). "
       ::= { qosTwoRatePolicerEntry 3 }

   qosTwoRatePolicerPir OBJECT-TYPE
       SYNTAX  INTEGER
       ACCESS  read-write
       STATUS  current
       DESCRIPTION
               "the two rate policer Peak Information Rate(PIR). "
       ::= { qosTwoRatePolicerEntry 4 }

   qosTwoRatePolicerPbs OBJECT-TYPE
       SYNTAX  INTEGER
       ACCESS  read-write
       STATUS  current
       DESCRIPTION
               "the two rate policer Peak Burst Size(PBS). "
       ::= { qosTwoRatePolicerEntry 5 }

   qosTwoRatePolicerColorAware OBJECT-TYPE
       SYNTAX  TruthValue
       ACCESS  read-write
       STATUS  current
       DESCRIPTION
               "the status of the two rate policer color aware mode. "
       ::= { qosTwoRatePolicerEntry 6 }

   qosTwoRatePolicerL2PriorityRemark OBJECT-TYPE
       SYNTAX  TruthValue
       ACCESS  read-write
       STATUS  current
       DESCRIPTION
               "This value determines whether re-marking of packets is done based on Traffic Class or CoS fields determined by previous marking mechanism(i.e. Bridge, Policy, InLIF). "
       ::= { qosTwoRatePolicerEntry 7 }

   qosTwoRatePolicerL3PriorityRemark OBJECT-TYPE
       SYNTAX  TruthValue
       ACCESS  read-write
       STATUS  current
       DESCRIPTION
               "This value determines whether re-marking for IP packets is done based on DSCP field."
       ::= { qosTwoRatePolicerEntry 8 }

   qosTwoRatePolicerRemarkDscpCos OBJECT-TYPE
       SYNTAX  TruthValue
       ACCESS  read-write
       STATUS  current
       DESCRIPTION
               "This value determines if the DSCP and CoS are re-marked. "
       ::= { qosTwoRatePolicerEntry 9 }

   qosTwoRatePolicerRemarkTrafficClass OBJECT-TYPE
       SYNTAX  TruthValue
       ACCESS  read-write
       STATUS  current
       DESCRIPTION
               "This value determines if the traffic class are re-marked. "
       ::= { qosTwoRatePolicerEntry 10 }

   qosTwoRatePolicerDropRed OBJECT-TYPE
       SYNTAX  TruthValue
       ACCESS  read-write
       STATUS  current
       DESCRIPTION
               "This value determines whether packets which are marked red by the traffic policing mechanism will be droped. "
       ::= { qosTwoRatePolicerEntry 11 }

   qosTwoRatePolicerUseNum OBJECT-TYPE
       SYNTAX  INTEGER
       ACCESS  read-only
       STATUS  current
       DESCRIPTION
               "the number of QoS which use this two rate policer . "
       ::= { qosTwoRatePolicerEntry 12 }

   qosTwoRatePolicerRowStatus OBJECT-TYPE
       SYNTAX  RowStatus
       MAX-ACCESS  read-create
       STATUS  current
       DESCRIPTION
           "This object indicates the status of this entry."
       ::= { qosTwoRatePolicerEntry 13 }

   -----------------------------------------------------
   -- the L2 priority remark table
   -----------------------------------------------------

   qosL2PriorityRemarkTable OBJECT-TYPE
       SYNTAX  SEQUENCE OF QosL2PriorityRemarkEntry
       ACCESS  not-accessible
       STATUS  current
       DESCRIPTION
               "A list of L2 priority remark entries. "
       ::= { gbnL2QACL 29 }

   qosL2PriorityRemarkEntry OBJECT-TYPE
       SYNTAX  QosL2PriorityRemarkEntry
       ACCESS  not-accessible
       STATUS  current
       DESCRIPTION
               "A list of L2 priority remark entries. "
       INDEX   { qosL2PriorityRemarkColor, qosL2PriorityRemarkOldCos }
       ::= { qosL2PriorityRemarkTable 1 }

   QosL2PriorityRemarkEntry ::=
       SEQUENCE {
           qosL2PriorityRemarkColor
               INTEGER,
           qosL2PriorityRemarkOldCos
               INTEGER,
           qosL2PriorityRemarkDscp
               INTEGER,
           qosL2PriorityRemarkDropPrecedence
               INTEGER,
           qosL2PriorityRemarkTrafficClass
               INTEGER,
           qosL2PriorityRemarkCos
               INTEGER
       }

   qosL2PriorityRemarkColor OBJECT-TYPE
       SYNTAX  INTEGER
       ACCESS  read-only
       STATUS  current
       DESCRIPTION
               "the color of the packet. "
       ::= { qosL2PriorityRemarkEntry 1 }

   qosL2PriorityRemarkOldCos OBJECT-TYPE
       SYNTAX  INTEGER
       ACCESS  read-only
       STATUS  current
       DESCRIPTION
               "the old CoS of the packet. "
       ::= { qosL2PriorityRemarkEntry 2 }

   qosL2PriorityRemarkDscp OBJECT-TYPE
       SYNTAX  INTEGER
       ACCESS  read-write
       STATUS  current
       DESCRIPTION
               "the DSCP applied to the packet. "
       ::= { qosL2PriorityRemarkEntry 3 }

   qosL2PriorityRemarkDropPrecedence OBJECT-TYPE
       SYNTAX  INTEGER
       ACCESS  read-write
       STATUS  current
       DESCRIPTION
               "the drop precedence applied to the packet. "
       ::= { qosL2PriorityRemarkEntry 4 }

   qosL2PriorityRemarkTrafficClass OBJECT-TYPE
       SYNTAX  INTEGER
       ACCESS  read-write
       STATUS  current
       DESCRIPTION
               "the traffic class applied to the packet. "
       ::= { qosL2PriorityRemarkEntry 5 }

   qosL2PriorityRemarkCos OBJECT-TYPE
       SYNTAX  INTEGER
       ACCESS  read-write
       STATUS  current
       DESCRIPTION
               "the CoS applied to the packet. "
       ::= { qosL2PriorityRemarkEntry 6 }

   -----------------------------------------------------
   -- the L3 priority remark table
   -----------------------------------------------------

   qosL3PriorityRemarkTable OBJECT-TYPE
       SYNTAX  SEQUENCE OF QosL3PriorityRemarkEntry
       ACCESS  not-accessible
       STATUS  current
       DESCRIPTION
               "A list of L3 priority remark entries. "
       ::= { gbnL2QACL 30 }

   qosL3PriorityRemarkEntry OBJECT-TYPE
       SYNTAX  QosL3PriorityRemarkEntry
       ACCESS  not-accessible
       STATUS  current
       DESCRIPTION
               "A list of L3 priority remark entries. "
       INDEX   { qosL3PriorityRemarkColor, qosL3PriorityRemarkOldDscp }
       ::= { qosL3PriorityRemarkTable 1 }

   QosL3PriorityRemarkEntry ::=
       SEQUENCE {
           qosL3PriorityRemarkColor
               INTEGER,
           qosL3PriorityRemarkOldDscp
               INTEGER,
           qosL3PriorityRemarkDscp
               INTEGER,
           qosL3PriorityRemarkDropPrecedence
               INTEGER,
           qosL3PriorityRemarkTrafficClass
               INTEGER,
           qosL3PriorityRemarkCos
               INTEGER
       }

   qosL3PriorityRemarkColor OBJECT-TYPE
       SYNTAX  INTEGER
       ACCESS  read-only
       STATUS  current
       DESCRIPTION
               "the color of the packet. "
       ::= { qosL3PriorityRemarkEntry 1 }

   qosL3PriorityRemarkOldDscp OBJECT-TYPE
       SYNTAX  INTEGER
       ACCESS  read-only
       STATUS  current
       DESCRIPTION
               "the old DSCP of the packet. "
       ::= { qosL3PriorityRemarkEntry 2 }

   qosL3PriorityRemarkDscp OBJECT-TYPE
       SYNTAX  INTEGER
       ACCESS  read-write
       STATUS  current
       DESCRIPTION
               "the DSCP applied to the packet. "
       ::= { qosL3PriorityRemarkEntry 3 }

   qosL3PriorityRemarkDropPrecedence OBJECT-TYPE
       SYNTAX  INTEGER
       ACCESS  read-write
       STATUS  current
       DESCRIPTION
               "the drop precedence applied to the packet. "
       ::= { qosL3PriorityRemarkEntry 4 }

   qosL3PriorityRemarkTrafficClass OBJECT-TYPE
       SYNTAX  INTEGER
       ACCESS  read-write
       STATUS  current
       DESCRIPTION
               "the traffic class applied to the packet. "
       ::= { qosL3PriorityRemarkEntry 5 }

   qosL3PriorityRemarkCos OBJECT-TYPE
       SYNTAX  INTEGER
       ACCESS  read-write
       STATUS  current
       DESCRIPTION
               "the CoS applied to the packet. "
       ::= { qosL3PriorityRemarkEntry 6 }
    -----------------------------------------------------
   -- the trTCM mode
   -----------------------------------------------------
   qosRateLimittrTCMMode OBJECT IDENTIFIER ::= { gbnL2QACL 31 }
   trTCMMode  OBJECT-TYPE
        SYNTAX INTEGER{
              colore-aware(1),
              color_blind(2)
              }
        MAX-ACCESS read-write
        STATUS current
        DESCRIPTION
           "two rate three color marking mode."
        ::= { qosRateLimittrTCMMode 1 }

    trTCMPreColorValue  OBJECT-TYPE
        SYNTAX INTEGER{
              green(0),
              red(1),
              yellow(3)
              }
        MAX-ACCESS read-write
        STATUS current
        DESCRIPTION
           "two rate three color marking pre-color value."
        ::= { qosRateLimittrTCMMode 2 }
-------------------------------------------------------------
----acl ipv6 mode
-------------------------------------------------------------
   aclIpv6KeyMode  OBJECT-TYPE
        SYNTAX INTEGER{
              mac(1),
              destination_ip(2)
              }
        MAX-ACCESS read-write
        STATUS current
        DESCRIPTION
           "mode of ipv6 key,mac(1) means acl-rules can inlcude mac-address,but only include 120~127 bits of destination ipaddressv6.
            destination_ip(2) means acl-rules can include all 128 bits of destination ipaddressv6,but can not include mac-address."
        ::= { gbnL2QACL 32 }
END
