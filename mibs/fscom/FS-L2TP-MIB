-- ====================================================================
-- Copyright (c) 2011 by FS.COM Inc.. All rights reserved.
--
-- Description: The MIB is designed to trap L2TP tunnel create or destroy information.
-- Reference: fs Enterprise MIB
-- =====================================================================
FS-L2TP-MIB DEFINITIONS ::= BEGIN

    IMPORTS
        DisplayString,TEXTUAL-CONVENTION, TimeStamp
            FROM SNMPv2-TC
        IpAddress, Integer32, Counter32, Counter64, OBJECT-TYPE,
        MODULE-IDENTITY, Gauge32, NOTIFICATION-TYPE, Unsigned32
            FROM SNMPv2-SMI
        MODULE-COMPLIANCE, OBJECT-GROUP, NOTIFICATION-GROUP
            FROM SNMPv2-CONF
        fsMgmt
            FROM FS-SMI;

    fsVPDNMIB MODULE-IDENTITY
        LAST-UPDATED "201102170000Z"
        ORGANIZATION
            "FS.COM Inc.."
        CONTACT-INFO
            "Tel: 400-865-2852
             E-mail: https://www.fs.com/live_chat_service_mail.html"
        DESCRIPTION
            "The MIB is designed to get statistic information of
             vpdn tunnels. With this MIB, we can get information of a certain
             tunnel or all tunnels."
        REVISION      "201102170000Z"
        DESCRIPTION
                "Initial version of this MIB module."
        ::= { fsMgmt 112 }

      fsL2TPSessionObjects OBJECT IDENTIFIER ::= {fsVPDNMIB 1}
      fsVPDNMonitor OBJECT IDENTIFIER ::= {fsVPDNMIB 2}
 -- ===============================================
-- definition of table.
-- ===============================================
		fsL2TPSessionTable OBJECT-TYPE
			SYNTAX SEQUENCE OF FSL2TPSessionEntry
			MAX-ACCESS not-accessible
			STATUS current
			DESCRIPTION
				"The l2tp session Table. There is one
				entry in this table for each active l2tp Session."
			::= { fsL2TPSessionObjects 1 }


		fsL2TPSessionEntry OBJECT-TYPE
			SYNTAX FSL2TPSessionEntry
			MAX-ACCESS not-accessible
			STATUS current
			DESCRIPTION
				"Information about fsL2TPSessionTable."
			INDEX { l2tpPrivateSessionIfIndex }
			::= { fsL2TPSessionTable 1 }

		FSL2TPSessionEntry ::=
			SEQUENCE {
			    l2tpPrivateSessionIfIndex
					Integer32,
				l2tpPrivateLocalTunnelID
					Integer32,
				l2tpPrivateSessionLocalIpAdd
					IpAddress,
				l2tpPrivateSessionRemoteIpAdd
					IpAddress,
				l2tpPrivateSessionVrfId
					Integer32,
				l2tpPrivateSessionExistTime
					Integer32,
				l2tpPrivateSessionStatus
					INTEGER
			 }
        l2tpPrivateSessionIfIndex OBJECT-TYPE
			SYNTAX Integer32 (1..2147483647)
			MAX-ACCESS read-only
			STATUS current
			DESCRIPTION
				"The session va index."
			::= { fsL2TPSessionEntry 1 }

		l2tpPrivateLocalTunnelID OBJECT-TYPE
			SYNTAX Integer32 (1..2147483647)
			MAX-ACCESS read-only
			STATUS current
			DESCRIPTION
				"The tunnel ID index."
			::= { fsL2TPSessionEntry 2 }

		l2tpPrivateSessionLocalIpAdd OBJECT-TYPE
			SYNTAX IpAddress
			MAX-ACCESS read-only
			STATUS current
			DESCRIPTION
				"The tunnel other side IP."
			::= { fsL2TPSessionEntry 3 }

	    l2tpPrivateSessionRemoteIpAdd OBJECT-TYPE
			SYNTAX IpAddress
			MAX-ACCESS read-only
			STATUS current
			DESCRIPTION
				"The tunnel other side IP."
			::= { fsL2TPSessionEntry 4 }

	    l2tpPrivateSessionVrfId OBJECT-TYPE
			SYNTAX Integer32 (1..2147483647)
			MAX-ACCESS read-only
			STATUS current
			DESCRIPTION
				"The tunnel Session index."
			::= { fsL2TPSessionEntry 5 }

	    l2tpPrivateSessionExistTime OBJECT-TYPE
			SYNTAX Integer32 (1..2147483647)
			MAX-ACCESS read-only
			STATUS current
			DESCRIPTION
				"The tunnel Session index."
			::= { fsL2TPSessionEntry 6 }

            -- 1.3.6.1.4.1.52642.1.1.10.2.112.1.1.1.7
            l2tpPrivateSessionStatus OBJECT-TYPE
                        SYNTAX	INTEGER {
                            sessionIdle(1),
                            sessionConnecting(2),
                            sessionEstablished(3),
                            sessionDisconnecting(4)
                        }
			MAX-ACCESS read-write
			STATUS current
			DESCRIPTION
				"Description."
			::= { fsL2TPSessionEntry 7 }


-- ===============================================
-- definition of traps.
-- ===============================================
    fsVPDNMonitorTRAP OBJECT IDENTIFIER ::= { fsVPDNMonitor 1 }
    fsVPDNNotifications OBJECT IDENTIFIER ::= { fsVPDNMonitorTRAP 1 }

    fsVPDNStart NOTIFICATION-TYPE
        OBJECTS {
                  l2tpPrivateSessionIfIndex,
                  l2tpPrivateLocalTunnelID,
                  l2tpPrivateSessionLocalIpAdd,
                  l2tpPrivateSessionRemoteIpAdd,
                  l2tpPrivateSessionVrfId,
                  l2tpPrivateSessionExistTime
               }
        STATUS     current
        DESCRIPTION
            "This notification is generated when an VPDN is created."
        ::= { fsVPDNNotifications 1 }

    fsVPDNStop NOTIFICATION-TYPE
        OBJECTS {
                  l2tpPrivateSessionIfIndex,
                  l2tpPrivateLocalTunnelID,
                  l2tpPrivateSessionLocalIpAdd,
                  l2tpPrivateSessionRemoteIpAdd,
                  l2tpPrivateSessionVrfId,
                  l2tpPrivateSessionExistTime
               }
        STATUS     current
        DESCRIPTION
            "This notification is generated when an VPDN is destroy."
        ::= { fsVPDNNotifications 2 }

END
