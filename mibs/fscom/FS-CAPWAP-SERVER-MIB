-- *****************************************************************
-- FS-CAPWAP-SERVER-MIB.mib:  FS Capwap Server MIB file
--
-- Aug 2010, xueweiwen
--
-- Copyright (c) 2010 by FS.COM Inc..
-- All rights reserved.
--
-- *****************************************************************
--

FS-CAPWAP-SERVER-MIB DEFINITIONS ::= BEGIN

IMPORTS
    MODULE-IDENTITY,
    OBJECT-TYPE,
    Counter32,
    Unsigned32,
    IpAddress
            FROM SNMPv2-SMI
    InetAddressType,
    InetAddress
            FROM INET-ADDRESS-MIB
    DisplayString,
    MacAddress,
    RowStatus
            FROM SNMPv2-TC
    MODULE-COMPLIANCE,
    OBJECT-GROUP
            FROM SNMPv2-CONF
    fsMgmt
            FROM FS-SMI;

fsCapwapSvrMIB MODULE-IDENTITY
    LAST-UPDATED "201008240000Z"
    ORGANIZATION "FS.COM Inc.."
    CONTACT-INFO
           "
           Tel: 400-865-2852

           E-mail: https://www.fs.com/live_chat_service_mail.html"
    DESCRIPTION
           "This module defines fs capwap server mibs."
    REVISION      "201008240000Z"
    DESCRIPTION
           "Initial version of this MIB module."
    ::= { fsMgmt 89 }


fsCapwapSvrMIBObjects OBJECT IDENTIFIER ::= { fsCapwapSvrMIB 1 }


-- capwap server white list url
fsCapwapSvrWhiteListURLTable OBJECT-TYPE
    SYNTAX  SEQUENCE OF FSCapwapSvrWhiteListURLEntry
    MAX-ACCESS  not-accessible
    STATUS  current
    DESCRIPTION
        "The table of Capwap server white list URL Info."
    ::= { fsCapwapSvrMIBObjects 1 }

fsCapwapSvrWhiteListURLEntry OBJECT-TYPE
    SYNTAX  FSCapwapSvrWhiteListURLEntry
    MAX-ACCESS  not-accessible
    STATUS  current
    DESCRIPTION
        "The entry of Capwap server white list URL info table."
    INDEX   { fsCapwapSvrWhiteListIndex }
    ::= { fsCapwapSvrWhiteListURLTable 1 }

FSCapwapSvrWhiteListURLEntry ::=
    SEQUENCE {
        fsCapwapSvrWhiteListIndex            Unsigned32,
        fsCapwapSvrWhiteListURL              DisplayString,
        fsCapwapSvrWhiteListURLParserStatus  DisplayString,
        fsCapwapSvrWhiteListURLRowStatus     RowStatus
    }

fsCapwapSvrWhiteListIndex OBJECT-TYPE
    SYNTAX       Unsigned32
    MAX-ACCESS   read-only
    STATUS       current
    DESCRIPTION
        "The index of the Capwap server white list url."
    ::= { fsCapwapSvrWhiteListURLEntry 1 }

fsCapwapSvrWhiteListURL OBJECT-TYPE
    SYNTAX       DisplayString (SIZE (0..255))
    MAX-ACCESS   read-create
    STATUS       current
    DESCRIPTION
        "The URL of the Capwap server white list."
    ::= { fsCapwapSvrWhiteListURLEntry 2 }

fsCapwapSvrWhiteListURLParserStatus OBJECT-TYPE
    SYNTAX       DisplayString (SIZE (0..255))
    MAX-ACCESS   read-only
    STATUS       current
    DESCRIPTION
        "The URL parser status of the Capwap server white list."
    ::= { fsCapwapSvrWhiteListURLEntry 3 }

fsCapwapSvrWhiteListURLRowStatus OBJECT-TYPE
    SYNTAX       RowStatus
    MAX-ACCESS   read-create
    STATUS       current
    DESCRIPTION
        "The RowStatus of the Capwap server white list URL table."
    ::= { fsCapwapSvrWhiteListURLEntry 4 }


-- capwap server white list ip
fsCapwapSvrWhiteListIPTable OBJECT-TYPE
    SYNTAX  SEQUENCE OF FSCapwapSvrWhiteListIPEntry
    MAX-ACCESS  not-accessible
    STATUS  current
    DESCRIPTION
        "The table of Capwap server white list IP Info."
    ::= { fsCapwapSvrMIBObjects 2 }

fsCapwapSvrWhiteListIPEntry OBJECT-TYPE
    SYNTAX  FSCapwapSvrWhiteListIPEntry
    MAX-ACCESS  not-accessible
    STATUS  current
    DESCRIPTION
        "The entry of Capwap server white list IP info table."
    INDEX   { fsCapwapSvrWhiteListIP }
    ::= { fsCapwapSvrWhiteListIPTable 1 }

FSCapwapSvrWhiteListIPEntry ::=
    SEQUENCE {
        fsCapwapSvrWhiteListIP            IpAddress,
        fsCapwapSvrWhiteListIPRowStatus   RowStatus
    }

fsCapwapSvrWhiteListIP OBJECT-TYPE
    SYNTAX       IpAddress
    MAX-ACCESS   read-only
    STATUS       current
    DESCRIPTION
        "The IP of the Capwap server white list."
    ::= { fsCapwapSvrWhiteListIPEntry 1 }

fsCapwapSvrWhiteListIPRowStatus OBJECT-TYPE
    SYNTAX       RowStatus
    MAX-ACCESS   read-create
    STATUS       current
    DESCRIPTION
        "The RowStatus of the Capwap server white list IP table."
    ::= { fsCapwapSvrWhiteListIPEntry 2 }


-- capwap server black list URL
fsCapwapSvrBlackListURLTable OBJECT-TYPE
    SYNTAX  SEQUENCE OF FSCapwapSvrBlackListURLEntry
    MAX-ACCESS  not-accessible
    STATUS  current
    DESCRIPTION
        "The table of Portal URL Info."
    ::= { fsCapwapSvrMIBObjects 3 }

fsCapwapSvrBlackListURLEntry OBJECT-TYPE
    SYNTAX  FSCapwapSvrBlackListURLEntry
    MAX-ACCESS  not-accessible
    STATUS  current
    DESCRIPTION
        "The entry of Portal URL info table."
    INDEX   { fsCapwapSvrBlackListIndex }
    ::= { fsCapwapSvrBlackListURLTable 1 }

FSCapwapSvrBlackListURLEntry ::=
    SEQUENCE {
        fsCapwapSvrBlackListIndex            Unsigned32,
        fsCapwapSvrBlackListURL              DisplayString,
        fsCapwapSvrBlackListURLParserStatus  DisplayString,
        fsCapwapSvrBlackListURLRowStatus     RowStatus
    }

fsCapwapSvrBlackListIndex OBJECT-TYPE
    SYNTAX       Unsigned32
    MAX-ACCESS   read-only
    STATUS       current
    DESCRIPTION
        "The URL of the Capwap server black list."
    ::= { fsCapwapSvrBlackListURLEntry 1 }

fsCapwapSvrBlackListURL OBJECT-TYPE
    SYNTAX       DisplayString (SIZE (0..255))
    MAX-ACCESS   read-create
    STATUS       current
    DESCRIPTION
        "The URL of the Capwap server black list."
    ::= { fsCapwapSvrBlackListURLEntry 2 }

fsCapwapSvrBlackListURLParserStatus OBJECT-TYPE
    SYNTAX       DisplayString (SIZE (0..255))
    MAX-ACCESS   read-only
    STATUS       current
    DESCRIPTION
        "The URL parser status of the Capwap server black list."
    ::= { fsCapwapSvrBlackListURLEntry 3 }

fsCapwapSvrBlackListURLRowStatus OBJECT-TYPE
    SYNTAX       RowStatus
    MAX-ACCESS   read-create
    STATUS       current
    DESCRIPTION
        "The RowStatus of the Capwap server black list IP table."
    ::= { fsCapwapSvrBlackListURLEntry 4 }


-- capwap server black list ip
fsCapwapSvrBlackListIPTable OBJECT-TYPE
    SYNTAX  SEQUENCE OF FSCapwapSvrBlackListIPEntry
    MAX-ACCESS  not-accessible
    STATUS  current
    DESCRIPTION
        "The table of Capwap server black list IP Info."
    ::= { fsCapwapSvrMIBObjects 4 }

fsCapwapSvrBlackListIPEntry OBJECT-TYPE
    SYNTAX  FSCapwapSvrBlackListIPEntry
    MAX-ACCESS  not-accessible
    STATUS  current
    DESCRIPTION
        "The entry of Capwap server black list IP info table."
    INDEX   { fsCapwapSvrBlackListIP }
    ::= { fsCapwapSvrBlackListIPTable 1 }

FSCapwapSvrBlackListIPEntry ::=
    SEQUENCE {
        fsCapwapSvrBlackListIP            IpAddress,
        fsCapwapSvrBlackListIPRowStatus   RowStatus
    }

fsCapwapSvrBlackListIP OBJECT-TYPE
    SYNTAX       IpAddress
    MAX-ACCESS   read-only
    STATUS       current
    DESCRIPTION
        "The IP of the Capwap server black list."
    ::= { fsCapwapSvrBlackListIPEntry 1 }

fsCapwapSvrBlackListIPRowStatus OBJECT-TYPE
    SYNTAX       RowStatus
    MAX-ACCESS   read-create
    STATUS       current
    DESCRIPTION
        "The RowStatus of the Capwap server black list IP table."
    ::= { fsCapwapSvrBlackListIPEntry 2 }


-- capwap server black list port
fsCapwapSvrBlackListPortTable OBJECT-TYPE
    SYNTAX  SEQUENCE OF FSCapwapSvrBlackListPortEntry
    MAX-ACCESS  not-accessible
    STATUS  current
    DESCRIPTION
        "The table of Capwap server black list port Info."
    ::= { fsCapwapSvrMIBObjects 5 }

fsCapwapSvrBlackListPortEntry OBJECT-TYPE
    SYNTAX  FSCapwapSvrBlackListPortEntry
    MAX-ACCESS  not-accessible
    STATUS  current
    DESCRIPTION
        "The entry of Capwap server black list port info table."
    INDEX   { fsCapwapSvrBlackListPort }
    ::= { fsCapwapSvrBlackListPortTable 1 }

FSCapwapSvrBlackListPortEntry ::=
    SEQUENCE {
        fsCapwapSvrBlackListPort            INTEGER,
        fsCapwapSvrBlackListPortRowStatus   RowStatus
    }

fsCapwapSvrBlackListPort OBJECT-TYPE
    SYNTAX       INTEGER
    MAX-ACCESS   read-only
    STATUS       current
    DESCRIPTION
        "The port of the Capwap server black list."
    ::= { fsCapwapSvrBlackListPortEntry 1 }

fsCapwapSvrBlackListPortRowStatus OBJECT-TYPE
    SYNTAX       RowStatus
    MAX-ACCESS   read-create
    STATUS       current
    DESCRIPTION
        "The RowStatus of the Capwap server black list port table."
    ::= { fsCapwapSvrBlackListPortEntry 2 }


-- capwap server white list mac
fsCapwapSvrWhiteListMacTable OBJECT-TYPE
    SYNTAX  SEQUENCE OF FSCapwapSvrWhiteListMacEntry
    MAX-ACCESS  not-accessible
    STATUS  current
    DESCRIPTION
        "The table of Capwap server white list Mac Info."
    ::= { fsCapwapSvrMIBObjects 6 }

fsCapwapSvrWhiteListMacEntry OBJECT-TYPE
    SYNTAX  FSCapwapSvrWhiteListMacEntry
    MAX-ACCESS  not-accessible
    STATUS  current
    DESCRIPTION
        "The entry of Capwap server white list Mac info table."
    INDEX   { fsCapwapSvrWhiteListMacIndex }
    ::= { fsCapwapSvrWhiteListMacTable 1 }

FSCapwapSvrWhiteListMacEntry ::=
    SEQUENCE {
        fsCapwapSvrWhiteListMacIndex            Unsigned32,
        fsCapwapSvrWhiteListMac              MacAddress,
        fsCapwapSvrWhiteListMacRowStatus     RowStatus
    }

fsCapwapSvrWhiteListMacIndex OBJECT-TYPE
    SYNTAX       Unsigned32
    MAX-ACCESS   read-only
    STATUS       current
    DESCRIPTION
        "The index of the Capwap server white list Mac."
    ::= { fsCapwapSvrWhiteListMacEntry 1 }

fsCapwapSvrWhiteListMac OBJECT-TYPE
    SYNTAX       MacAddress
    MAX-ACCESS   read-create
    STATUS       current
    DESCRIPTION
        "The Mac of the Capwap server white list."
    ::= { fsCapwapSvrWhiteListMacEntry 2 }

fsCapwapSvrWhiteListMacRowStatus OBJECT-TYPE
    SYNTAX       RowStatus
    MAX-ACCESS   read-create
    STATUS       current
    DESCRIPTION
        "The RowStatus of the Capwap server white list Mac table."
    ::= { fsCapwapSvrWhiteListMacEntry 3 }


---
---compliance statements
---
fsCapwapSvrMIBConformance OBJECT IDENTIFIER ::= { fsCapwapSvrMIB 2 }
fsCapwapSvrMIBCompliances OBJECT IDENTIFIER ::= { fsCapwapSvrMIBConformance 1 }
fsCapwapSvrMIBGroups      OBJECT IDENTIFIER ::= { fsCapwapSvrMIBConformance 2 }

fsCapwapSvrMIBCompliance MODULE-COMPLIANCE
   STATUS  current
   DESCRIPTION
   			"The compliance statement for entities which implement
       	 the capwapServer MIB"
   MODULE
   GROUP fsCapwapSvrMIBGroup
 	 DESCRIPTION
        "This group is mandatory only for those system which support
         capwapServer function."
   ::= { fsCapwapSvrMIBCompliances 1 }

fsCapwapSvrMIBGroup OBJECT-GROUP
   OBJECTS {
        fsCapwapSvrWhiteListURL,
        fsCapwapSvrWhiteListURLParserStatus,
        fsCapwapSvrWhiteListURLRowStatus,
        fsCapwapSvrWhiteListIP,
        fsCapwapSvrWhiteListIPRowStatus,
        fsCapwapSvrBlackListURL,
        fsCapwapSvrBlackListURLParserStatus,
        fsCapwapSvrBlackListURLRowStatus,
        fsCapwapSvrBlackListIP,
        fsCapwapSvrBlackListIPRowStatus,
        fsCapwapSvrBlackListPort,
        fsCapwapSvrBlackListPortRowStatus,
        fsCapwapSvrWhiteListMac,
        fsCapwapSvrWhiteListMacRowStatus
      }
   STATUS  deprecated
   DESCRIPTION
         "The basic collection of objects providing management of capwapServer management."
   ::= { fsCapwapSvrMIBGroups 1 }

END
