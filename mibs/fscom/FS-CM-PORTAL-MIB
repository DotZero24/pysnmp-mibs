-- *****************************************************************
-- FS-CM-PORTAL-MIB.mib:  FS China Mobile Portal MIB file
--
-- March 2010, panshiyong
--
-- Copyright (c) 2010 by FS.COM Inc..
-- All rights reserved.
--
-- *****************************************************************
--

FS-CM-PORTAL-MIB DEFINITIONS ::= BEGIN

IMPORTS
    MODULE-IDENTITY,
    OBJECT-TYPE,
    Counter32,
    Unsigned32,
    Integer32
            FROM SNMPv2-SMI
    InetAddressType,
    InetAddress
            FROM INET-ADDRESS-MIB
    DisplayString,
    MacAddress,
    RowStatus
            FROM SNMPv2-TC
    MODULE-COMPLIANCE,
    OBJECT-GROUP
            FROM SNMPv2-CONF
    fsMgmt
            FROM FS-SMI;

fsCMPortalMIB MODULE-IDENTITY
    LAST-UPDATED "201003220000Z"
    ORGANIZATION "FS.COM Inc.."
    CONTACT-INFO
           "
           Tel: 400-865-2852

           E-mail: https://www.fs.com/live_chat_service_mail.html"
    DESCRIPTION
           "This module defines fs portal mibs."
    REVISION      "201003220000Z"
    DESCRIPTION
           "Initial version of this MIB module."
    ::= { fsMgmt 74 }


fsCMPortalMIBObjects OBJECT IDENTIFIER ::= { fsCMPortalMIB 1 }


fsCMPortalMaxAuthNum OBJECT-TYPE
		SYNTAX   Integer32
    MAX-ACCESS  read-write
    STATUS  current
    DESCRIPTION
    		"The max number of all portal authenticated user online."
    ::= { fsCMPortalMIBObjects 1 }

fsCMPortalCurAuthNum OBJECT-TYPE
		SYNTAX  Integer32
    MAX-ACCESS  read-only
    STATUS  current
    DESCRIPTION
    		"The current number of all portal authenticated user online."
    ::= { fsCMPortalMIBObjects 2 }

fsCMPortalServerInetAddressType OBJECT-TYPE
		SYNTAX InetAddressType
    MAX-ACCESS read-write
    STATUS  current
    DESCRIPTION
    		"The inet address type of the portal server."
		::= { fsCMPortalMIBObjects 3 }

fsCMPortalServerInetAddress OBJECT-TYPE
		SYNTAX InetAddress
    MAX-ACCESS read-write
    STATUS  current
    DESCRIPTION
    		"The inet address of portal server."
		::= { fsCMPortalMIBObjects 4 }

fsCMPortalServerInetPortNumber OBJECT-TYPE
		SYNTAX  INTEGER
    MAX-ACCESS  read-write
    STATUS  current
    DESCRIPTION
    		"The inet port number of portal server."
		::= { fsCMPortalMIBObjects 5 }

fsCMPortalServerUnavailableCode OBJECT-TYPE
		SYNTAX  INTEGER {
		        	not-configured(0),
		        	ping-failed(1)
		        }
    MAX-ACCESS read-only
    STATUS  current
    DESCRIPTION
    		"The flag code of portal server unavailable:
    		 0 - not-configured,
    		 1 - ping-failed
    		 "
    ::= { fsCMPortalMIBObjects 6 }

fsCMPortalAuthReqCount OBJECT-TYPE
    SYNTAX Counter32
    MAX-ACCESS read-only
    STATUS  current
    DESCRIPTION
    		"The authenticator request count of portal server."
    ::= { fsCMPortalMIBObjects 7 }

fsCMPortalAuthRespCount OBJECT-TYPE
    SYNTAX Counter32
    MAX-ACCESS read-only
    STATUS  current
    DESCRIPTION
    		"The authenticator respone count of portal server."
    ::= { fsCMPortalMIBObjects 8 }

fsCMPortalChallengeReqCount OBJECT-TYPE
    SYNTAX Counter32
    MAX-ACCESS read-only
    STATUS  current
    DESCRIPTION
    		"The challenge request count of portal server."
    ::= { fsCMPortalMIBObjects 9 }

fsCMPortalChallengeRespCount OBJECT-TYPE
    SYNTAX Counter32
    MAX-ACCESS read-only
    STATUS  current
    DESCRIPTION
    		"The challenge request count of portal server."
    ::= { fsCMPortalMIBObjects 10 }

fsCMPortalGlobalServerURL OBJECT-TYPE
    SYNTAX DisplayString (SIZE (0..255))
    MAX-ACCESS read-write
    STATUS  current
    DESCRIPTION
    		"The URL of portal server."
    ::= { fsCMPortalMIBObjects 11 }

--
-- fs CMCC Portal URL Info
--
fsCMPortalServerURLTable OBJECT-TYPE
        SYNTAX  SEQUENCE OF FSCMPortalServerURLEntry
        MAX-ACCESS  not-accessible
        STATUS  current
        DESCRIPTION
            "The table of Portal URL Info."
        ::= { fsCMPortalMIBObjects 12 }

fsCMPortalServerURLEntry OBJECT-TYPE
        SYNTAX  FSCMPortalServerURLEntry
        MAX-ACCESS  not-accessible
        STATUS  current
        DESCRIPTION
            "The entry of Portal URL info table."
        INDEX   { fsCMPortalServerURLId }
        ::= { fsCMPortalServerURLTable 1 }

FSCMPortalServerURLEntry ::=
    SEQUENCE {
            fsCMPortalServerURLId          Unsigned32,
            fsCMPortalServerURL            DisplayString,
            fsCMPortalServerName           DisplayString,
            fsCMPortalServerInUsedCount    Unsigned32,
            fsCMPortalServerConfigStatus   RowStatus
            }

fsCMPortalServerURLId OBJECT-TYPE
        SYNTAX       Unsigned32
        MAX-ACCESS   read-only
        STATUS       current
        DESCRIPTION
            "The Id of the Portal Server in device."
        ::= { fsCMPortalServerURLEntry 1 }

fsCMPortalServerURL OBJECT-TYPE
        SYNTAX  DisplayString (SIZE (0..255))
        MAX-ACCESS  read-write
        STATUS  current
        DESCRIPTION
            " The Portal URL."
         ::= { fsCMPortalServerURLEntry 2 }

fsCMPortalServerName OBJECT-TYPE
        SYNTAX  DisplayString (SIZE (0..32))
        MAX-ACCESS  read-write
        STATUS  current
        DESCRIPTION
            " The Portal Server's Name."
         ::= { fsCMPortalServerURLEntry 3 }

fsCMPortalServerInUsedCount OBJECT-TYPE
        SYNTAX       Unsigned32
        MAX-ACCESS   read-only
        STATUS       current
        DESCRIPTION
            "The count that this Portal Server is used by Control Cells in the device."
        ::= { fsCMPortalServerURLEntry 4 }

fsCMPortalServerConfigStatus OBJECT-TYPE
        SYNTAX  RowStatus
        MAX-ACCESS  read-write
        STATUS  current
        DESCRIPTION
            "Setting this object to 'invalid' will try to remove specific Portal Server from device."
         ::= { fsCMPortalServerURLEntry 5 }

fsCMPortalHttpReqCount OBJECT-TYPE
    SYNTAX Counter32
    MAX-ACCESS read-only
    STATUS  current
    DESCRIPTION
    		"The http request count to portal server for redirection."
    ::= { fsCMPortalMIBObjects 13 }

fsCMPortalHttpRespCount OBJECT-TYPE
    SYNTAX Counter32
    MAX-ACCESS read-only
    STATUS  current
    DESCRIPTION
    		"The http response count by portal server for redirection."
    ::= { fsCMPortalMIBObjects 14 }

fsCMPortalExceptionFailCount OBJECT-TYPE
    SYNTAX Counter32
    MAX-ACCESS read-only
    STATUS  current
    DESCRIPTION
    		"The user offline count for exception reason."
    ::= { fsCMPortalMIBObjects 15 }

fsCMPortalAuthSuccessedCount OBJECT-TYPE
    SYNTAX Counter32
    MAX-ACCESS read-only
    STATUS  current
    DESCRIPTION
    		"The radius authenticator response count for success result."
    ::= { fsCMPortalMIBObjects 16 }

fsCMPortalNormalAuthReqCount OBJECT-TYPE
    SYNTAX Counter32
    MAX-ACCESS read-only
    STATUS  current
    DESCRIPTION
    		"The normal authenticator request count of portal server."
    ::= { fsCMPortalMIBObjects 17 }

fsCMPortalEDUAuthReqCount OBJECT-TYPE
    SYNTAX Counter32
    MAX-ACCESS read-only
    STATUS  current
    DESCRIPTION
    		"The education authenticator request count of portal server."
    ::= { fsCMPortalMIBObjects 18 }

fsCMPortalStarbucksAuthReqCount OBJECT-TYPE
    SYNTAX Counter32
    MAX-ACCESS read-only
    STATUS  current
    DESCRIPTION
    		"The starbuck authenticator request count of portal server."
    ::= { fsCMPortalMIBObjects 19 }

fsCMPortalNormalAuthRespCount OBJECT-TYPE
    SYNTAX Counter32
    MAX-ACCESS read-only
    STATUS  current
    DESCRIPTION
    		"The normal authenticator respone count of portal server."
    ::= { fsCMPortalMIBObjects 20 }

fsCMPortalEDUAuthRespCount OBJECT-TYPE
    SYNTAX Counter32
    MAX-ACCESS read-only
    STATUS  current
    DESCRIPTION
    		"The education authenticator respone count of portal server."
    ::= { fsCMPortalMIBObjects 21 }

fsCMPortalStarbucksAuthRespCount OBJECT-TYPE
    SYNTAX Counter32
    MAX-ACCESS read-only
    STATUS  current
    DESCRIPTION
    		"The starbucks authenticator respone count of portal server."
    ::= { fsCMPortalMIBObjects 22 }

fsACPortalMaxAuthNum OBJECT-TYPE
		SYNTAX   Integer32
    MAX-ACCESS  read-only
    STATUS  current
    DESCRIPTION
    		"The max number of AC systerm authenticated user online."
    ::= { fsCMPortalMIBObjects 23 }

fsACPortalCurrentMaxAuthNum OBJECT-TYPE
		SYNTAX   Integer32
    MAX-ACCESS  read-only
    STATUS  current
    DESCRIPTION
    		"The max number of AC current authenticated user online."
    ::= { fsCMPortalMIBObjects 24}

--
-- fs CMCC Portal Auth Fail Cause Info
--
fsCMPortalAuthFailCauseTable OBJECT-TYPE
        SYNTAX  SEQUENCE OF FSCMPortalAuthFailCauseEntry
        MAX-ACCESS  not-accessible
        STATUS  current
        DESCRIPTION
            "The table of Portal Auth fail cause Info."
        ::= { fsCMPortalMIBObjects 25 }

fsCMPortalAuthFailCauseEntry OBJECT-TYPE
        SYNTAX  FSCMPortalAuthFailCauseEntry
        MAX-ACCESS  not-accessible
        STATUS  current
        DESCRIPTION
            "The entry of Portal Auth fail cause info table."
        INDEX   { fsCMPortalAuthFailCauseErrId }
        ::= { fsCMPortalAuthFailCauseTable 1 }

FSCMPortalAuthFailCauseEntry ::=
    SEQUENCE {
            fsCMPortalAuthFailCauseErrId    DisplayString,
            fsCMPortalAuthFailCauseCount    Unsigned32
            }

fsCMPortalAuthFailCauseErrId OBJECT-TYPE
        SYNTAX  DisplayString (SIZE (0..32))
        MAX-ACCESS   read-only
        STATUS       current
        DESCRIPTION
            "The ErrID of the Portal Auth fail cause."
        ::= { fsCMPortalAuthFailCauseEntry 1 }

fsCMPortalAuthFailCauseCount OBJECT-TYPE
        SYNTAX  Unsigned32
        MAX-ACCESS  read-only
        STATUS  current
        DESCRIPTION
            " The count of the Portal Auth fail cause."
         ::= { fsCMPortalAuthFailCauseEntry 2 }

--
-- fs CMCC Portal Auth Fail Code Info
--
fsCMPortalAuthFailCodeTable OBJECT-TYPE
        SYNTAX  SEQUENCE OF FSCMPortalAuthFailCodeEntry
        MAX-ACCESS  not-accessible
        STATUS  current
        DESCRIPTION
            "The table of Portal Auth fail code Info."
        ::= { fsCMPortalMIBObjects 26 }

fsCMPortalAuthFailCodeEntry OBJECT-TYPE
        SYNTAX  FSCMPortalAuthFailCodeEntry
        MAX-ACCESS  not-accessible
        STATUS  current
        DESCRIPTION
            "The entry of Portal Auth fail code info table."
        INDEX   { fsCMPortalAuthFailCodeIndex }
        ::= { fsCMPortalAuthFailCodeTable 1 }

FSCMPortalAuthFailCodeEntry ::=
    SEQUENCE {
            fsCMPortalAuthFailCodeIndex     Unsigned32,
            fsCMPortalAuthFailCode          Unsigned32,
            fsCMPortalAuthFailCodeCount     Unsigned32
            }

fsCMPortalAuthFailCodeIndex OBJECT-TYPE
        SYNTAX       Unsigned32
        MAX-ACCESS   read-only
        STATUS       current
        DESCRIPTION
            "The index of the Portal Auth fail code."
        ::= { fsCMPortalAuthFailCodeEntry 1 }

fsCMPortalAuthFailCode OBJECT-TYPE
        SYNTAX       Unsigned32
        MAX-ACCESS   read-only
        STATUS       current
        DESCRIPTION
            "The value of the Portal Auth fail code."
        ::= { fsCMPortalAuthFailCodeEntry 2 }

fsCMPortalAuthFailCodeCount OBJECT-TYPE
        SYNTAX  Unsigned32
        MAX-ACCESS  read-only
        STATUS  current
        DESCRIPTION
            " The count of the Portal Auth fail code."
         ::= { fsCMPortalAuthFailCodeEntry 3 }

fsCMPortalLogoutReqCount OBJECT-TYPE
    SYNTAX Counter32
    MAX-ACCESS read-only
    STATUS  current
    DESCRIPTION
            "The logout request count of portal server."
    ::= { fsCMPortalMIBObjects 27 }

fsCMPortalLogoutRespCount OBJECT-TYPE
    SYNTAX Counter32
    MAX-ACCESS read-only
    STATUS  current
    DESCRIPTION
            "The logout respone count of portal server."
    ::= { fsCMPortalMIBObjects 28 }

fsCMPortalNtfLogoutReqCount OBJECT-TYPE
    SYNTAX Counter32
    MAX-ACCESS read-only
    STATUS  current
    DESCRIPTION
            "The ntf_logout request count of portal server."
    ::= { fsCMPortalMIBObjects 29 }

fsCMPortalNtfLogoutRespCount OBJECT-TYPE
    SYNTAX Counter32
    MAX-ACCESS read-only
    STATUS  current
    DESCRIPTION
            "The ntf_logout respone count of portal server."
    ::= { fsCMPortalMIBObjects 30 }

fsCMPortalAuthFailCount OBJECT-TYPE
    SYNTAX Counter32
    MAX-ACCESS read-only
    STATUS  current
    DESCRIPTION
            "The auth fail count."
    ::= { fsCMPortalMIBObjects 32 }

fsCMPortalMaxHttpConnectionNum OBJECT-TYPE
    SYNTAX Counter32
    MAX-ACCESS read-only
    STATUS  current
    DESCRIPTION
            "The max http connection num."
    ::= { fsCMPortalMIBObjects 33 }


--
-- fs AP nas port id Info
--
fsApNasPortIdTable OBJECT-TYPE
        SYNTAX  SEQUENCE OF FSApNasPortIdEntry
        MAX-ACCESS  not-accessible
        STATUS  current
        DESCRIPTION
            "The table of AP's nas port id Info."
        ::= { fsCMPortalMIBObjects 31 }

fsApNasPortIdEntry OBJECT-TYPE
        SYNTAX  FSApNasPortIdEntry
        MAX-ACCESS  not-accessible
        STATUS  current
        DESCRIPTION
            "The entry of AP's nas port id info table."
        INDEX   { fsApNasPortIdApMacAddress, fsApNasPortIdRadioId, fsApNasPortIdWlanId }
        ::= { fsApNasPortIdTable 1 }

FSApNasPortIdEntry ::=
    SEQUENCE {
            fsApNasPortIdApMacAddress     MacAddress,
            fsApNasPortIdRadioId          Unsigned32,
            fsApNasPortIdWlanId           Unsigned32,
            fsApNasPortIdNasPortId        DisplayString
            }

fsApNasPortIdApMacAddress OBJECT-TYPE
        SYNTAX       MacAddress
        MAX-ACCESS   read-only
        STATUS       current
        DESCRIPTION
            "The MacAddress of the AP."
        ::= { fsApNasPortIdEntry 1 }

fsApNasPortIdRadioId OBJECT-TYPE
        SYNTAX       Unsigned32
        MAX-ACCESS   read-only
        STATUS       current
        DESCRIPTION
            "The RadioId of the AP."
        ::= { fsApNasPortIdEntry 2 }

fsApNasPortIdWlanId OBJECT-TYPE
        SYNTAX  Unsigned32
        MAX-ACCESS  read-only
        STATUS  current
        DESCRIPTION
            "The WlanId of the AP."
         ::= { fsApNasPortIdEntry 3 }

fsApNasPortIdNasPortId OBJECT-TYPE
        SYNTAX  DisplayString
        MAX-ACCESS  read-only
        STATUS  current
        DESCRIPTION
            " The NasPortId of the AP."
         ::= { fsApNasPortIdEntry 4 }

---
---Portal trap nodes
---
fsCMPortalMIBTrap    OBJECT IDENTIFIER ::= { fsCMPortalMIB 0 }

fsCMPortalServerDownTrap NOTIFICATION-TYPE
   OBJECTS {
   			fsCMPortalServerInetAddressType,
        fsCMPortalServerInetAddress,
        fsCMPortalServerInetPortNumber,
        fsCMPortalServerUnavailableCode }
   STATUS current
   DESCRIPTION
   		"This trap is generated when the portal server doesn't
   		 respond client's requests for specified times."
   ::= { fsCMPortalMIBTrap 1 }

fsCMPortalServerRecoverTrap NOTIFICATION-TYPE
   OBJECTS {
   			fsCMPortalServerInetAddressType,
        fsCMPortalServerInetAddress,
        fsCMPortalServerInetPortNumber,
        fsCMPortalServerUnavailableCode }
   STATUS current
   DESCRIPTION
   		"This trap is generated when the portal server recover from
   		 the down status."
   ::= { fsCMPortalMIBTrap 2 }

---
---compliance statements
---
fsCMPortalMIBConformance OBJECT IDENTIFIER ::= { fsCMPortalMIB 2 }
fsCMPortalMIBCompliances OBJECT IDENTIFIER ::= { fsCMPortalMIBConformance 1 }
fsCMPortalMIBGroups      OBJECT IDENTIFIER ::= { fsCMPortalMIBConformance 2 }

fsCMPortalMIBCompliance MODULE-COMPLIANCE
   STATUS  current
   DESCRIPTION
   			"The compliance statement for entities which implement
       	 the Portal MIB"
   MODULE  -- this module
   GROUP fsCMPortalMIBGroup
 	 DESCRIPTION
        "This group is mandatory only for those system which support portal function."
   ::= { fsCMPortalMIBCompliances 1 }

fsCMPortalMIBGroup OBJECT-GROUP
   OBJECTS {
   			fsCMPortalMaxAuthNum,
   			fsCMPortalCurAuthNum,
   			fsCMPortalServerInetAddressType,
   			fsCMPortalServerInetAddress,
   			fsCMPortalServerInetPortNumber,
   			fsCMPortalServerUnavailableCode,
   			fsCMPortalAuthReqCount,
   			fsCMPortalAuthRespCount,
   			fsCMPortalChallengeReqCount,
   			fsCMPortalChallengeRespCount,
   			fsCMPortalGlobalServerURL,
   			fsCMPortalServerURL,
                        fsCMPortalServerName,
                        fsCMPortalServerInUsedCount,
                        fsCMPortalServerConfigStatus,
		    fsCMPortalHttpReqCount,
			fsCMPortalHttpRespCount,
			fsCMPortalExceptionFailCount,
		    fsCMPortalAuthSuccessedCount,
		    fsCMPortalNormalAuthReqCount,
		    fsCMPortalEDUAuthReqCount,
		    fsCMPortalStarbucksAuthReqCount,
		    fsCMPortalNormalAuthRespCount,
		    fsCMPortalEDUAuthRespCount,
		    fsCMPortalStarbucksAuthRespCount,
		    fsACPortalMaxAuthNum,
            fsACPortalCurrentMaxAuthNum,
            fsCMPortalAuthFailCauseCount,
            fsCMPortalAuthFailCode,
            fsCMPortalAuthFailCodeCount,
            fsCMPortalLogoutReqCount,
            fsCMPortalLogoutRespCount,
            fsCMPortalNtfLogoutReqCount,
            fsCMPortalNtfLogoutRespCount,
            fsApNasPortIdApMacAddress,
            fsApNasPortIdRadioId,
            fsApNasPortIdWlanId,
            fsApNasPortIdNasPortId
      }
   STATUS  deprecated
   DESCRIPTION
         "The basic collection of objects providing management of portal management."
   ::= { fsCMPortalMIBGroups 1 }

END
