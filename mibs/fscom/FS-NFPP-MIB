-- *****************************************************************
-- FS-NFPP-MIB.mib:  FS NFPP MIB file
--
-- July 2009, yuhuabing
--
-- Copyright (c) 2009 by FS.COM Inc..
-- All rights reserved.
--
-- *****************************************************************
--

FS-NFPP-MIB DEFINITIONS ::= BEGIN

IMPORTS
        MODULE-IDENTITY,
        OBJECT-TYPE,
        NOTIFICATION-TYPE
                FROM SNMPv2-SMI
        MODULE-COMPLIANCE,
        OBJECT-GROUP,
        NOTIFICATION-GROUP
                FROM SNMPv2-CONF
        fsMgmt
                FROM FS-SMI;

fsNFPPMIB MODULE-IDENTITY
        LAST-UPDATED "200907090000Z"
        ORGANIZATION "FS.COM Inc.."
        CONTACT-INFO
                "
                Tel: 400-865-2852

                E-mail: https://www.fs.com/live_chat_service_mail.html"
        DESCRIPTION
                "This module defines fs NFPP mibs."
        REVISION      "200907090000Z"
        DESCRIPTION
                "Initial version of this MIB module."
        ::= { fsMgmt 43}

fsNFPPMIBObjects OBJECT IDENTIFIER ::= { fsNFPPMIB 1 }

  fsNFPPMessageContent OBJECT-TYPE
          SYNTAX OCTET STRING(SIZE(0..512))
          MAX-ACCESS accessible-for-notify
          STATUS current
          DESCRIPTION
            "NFPP Message Content"
          ::= { fsNFPPMIBObjects 0}

-- notifications

fsNFPPMIBNotificationPrefix OBJECT IDENTIFIER ::= { fsNFPPMIB 2 }
fsNFPPMIBNotifications OBJECT IDENTIFIER ::= { fsNFPPMIBNotificationPrefix 0 }

fsNFPPMessageGenerated NOTIFICATION-TYPE
	OBJECTS   {fsNFPPMessageContent}
	STATUS	   current
	DESCRIPTION
	       "When NFPP Event Occur, this message is Generated."
	::= { fsNFPPMIBNotifications 1 }


fsNFPPMIBConformance OBJECT IDENTIFIER ::= { fsNFPPMIB 3}
fsNFPPMIBCompliances OBJECT IDENTIFIER ::= { fsNFPPMIBConformance 1 }
fsNFPPMIBGroups      OBJECT IDENTIFIER ::= { fsNFPPMIBConformance 2 }

-- compliance statements

fsNFPPMIBCompliance MODULE-COMPLIANCE
        STATUS  current
        DESCRIPTION
                "The compliance statement for entities which implement
                the FS NFPP MIB"
        MODULE  -- this module
                MANDATORY-GROUPS {
                        fsNFPPNotifObjectsGroup,
                        fsNFPPNotificationsGroup
                 }
         ::= { fsNFPPMIBCompliances 1 }

-- units of conformance

fsNFPPNotifObjectsGroup OBJECT-GROUP
       OBJECTS {
           fsNFPPMessageContent
       }
       STATUS  current
       DESCRIPTION
                "A collection of objects that specify information for
                 TRIP notifications."
       ::= { fsNFPPMIBGroups 1 }

fsNFPPNotificationsGroup NOTIFICATION-GROUP
        NOTIFICATIONS {
               fsNFPPMessageGenerated
        }
        STATUS        current
        DESCRIPTION
              "A collection of NFPP traps."
      ::= { fsNFPPMIBGroups 2 }

END
