-- *****************************************************************
-- FS-IP-MANAGE-MIB.mib:  FS IP MANAGE MIB file
--
-- March 2002, Wuzg
--
-- Copyright (c) 2002 by FS.COM Inc..
-- All rights reserved.
--
-- *****************************************************************
--

FS-IP-MANAGE-MIB DEFINITIONS ::= BEGIN

IMPORTS
        MODULE-IDENTITY,
        OBJECT-TYPE,
        IpAddress
                FROM SNMPv2-SMI
        MODULE-COMPLIANCE,
        OBJECT-GROUP
                FROM SNMPv2-CONF
        EnabledStatus
                FROM P-BRIDGE-MIB
        fsMgmt
                FROM FS-SMI;

fsIpManageMIB MODULE-IDENTITY
        LAST-UPDATED "200203200000Z"
        ORGANIZATION "FS.COM Inc.."
        CONTACT-INFO
                "
                Tel: 400-865-2852

                E-mail: https://www.fs.com/live_chat_service_mail.html"
        DESCRIPTION
                "This module defines fs IP managment mibs."
        REVISION      "200203200000Z"
        DESCRIPTION
                "Initial version of this MIB module."
        ::= { fsMgmt 12}

fsDhcpMIBObjects OBJECT IDENTIFIER ::= { fsIpManageMIB 1 }
fsIpMIBObjects OBJECT IDENTIFIER ::= { fsIpManageMIB 2 }
--
-- fs  Dhcp Group
--

fsDhcpRelayAgentGlobalStatus OBJECT-TYPE
    SYNTAX EnabledStatus
    MAX-ACCESS read-write
    STATUS current
    DESCRIPTION
            "Global Dhcp relay agent status"
    DEFVAL { disabled }
            ::={ fsDhcpMIBObjects 2 }

fsDhcpServerIp OBJECT-TYPE
    SYNTAX IpAddress
    MAX-ACCESS read-write
    STATUS current
    DESCRIPTION
             "Ip address of internet host which returns configuration
              parameters to DHCP clients."
        ::={ fsDhcpMIBObjects 3 }


fsIpDefaultGateWay OBJECT-TYPE
    SYNTAX IpAddress
    MAX-ACCESS read-write
    STATUS current
    DESCRIPTION
             "Ip default gateway of system. This value applay only in layer 2"
        ::={ fsIpMIBObjects 1 }

fsIpManageMIBConformance OBJECT IDENTIFIER ::= { fsIpManageMIB 3 }
fsIpManageMIBCompliances OBJECT IDENTIFIER ::= { fsIpManageMIBConformance 1 }
fsIpManageMIBGroups      OBJECT IDENTIFIER ::= { fsIpManageMIBConformance 2 }


-- compliance statements

fsIpManageMIBCompliance MODULE-COMPLIANCE
        STATUS  current
        DESCRIPTION
                "The compliance statement for entities which implement
                the FS Snooping Dhcp MIB"
        MODULE  -- this module
                MANDATORY-GROUPS { fsL2L3DhcpManageMIBGroup
                 }
        ::= { fsIpManageMIBCompliances 1 }

-- units of conformance

fsL2L3DhcpManageMIBGroup OBJECT-GROUP
        OBJECTS {
           fsDhcpRelayAgentGlobalStatus,
           fsDhcpServerIp
        }
        STATUS  current
        DESCRIPTION
                "A collection of objects providing IP managment in layer2 or layer3 mode."
        ::= { fsIpManageMIBGroups 1 }

END
