-- *****************************************************************
-- FS-CAPWAP-MULTICAST-MIB.mib:  FS CAPWAP MULTICAST MIB file
--
-- Oct 2009, xieweiwu
--
-- Copyright (c) 2009 by FS.COM Inc..
-- All rights reserved.
--
-- *****************************************************************
--

FS-CAPWAP-MULTICAST-MIB DEFINITIONS ::= BEGIN

IMPORTS
        MODULE-IDENTITY,
        OBJECT-TYPE,
        IpAddress
                FROM SNMPv2-SMI
        MODULE-COMPLIANCE,
        OBJECT-GROUP
                FROM SNMPv2-CONF
        fsMgmt
                FROM FS-SMI;

fsCapwapMulticastMIB MODULE-IDENTITY
        LAST-UPDATED "200910220000Z"
        ORGANIZATION "FS.COM Inc.."
        CONTACT-INFO
                "
                Tel: 400-865-2852

                E-mail: https://www.fs.com/live_chat_service_mail.html"
        DESCRIPTION
                "This module defines fs Capwap Multicast mibs."
        REVISION      "200910220000Z"
        DESCRIPTION
                "Initial version of this MIB module."
        ::= { fsMgmt 59}

fsCapwapMulticastMIBObjects OBJECT IDENTIFIER ::= { fsCapwapMulticastMIB 1 }


--capwap multicast mode
fsCapwapMulticastWorkingMode OBJECT-TYPE
        SYNTAX INTEGER {
            unicast(1),    -- Working in capwap unicast(1),
            multicast(2)    -- Working in capwap multicast(2)
        }
        MAX-ACCESS read-write
        STATUS current
        DESCRIPTION
            "System Multicast working mode:
             unicast(1):
                Working in capwap unicast.
             multicast(2):
                Working in capwap multicast."
        DEFVAL { unicast }
        ::= { fsCapwapMulticastMIBObjects 1 }

--show capwap multicast group address
fsCapwapMulticastGroup OBJECT-TYPE
        SYNTAX IpAddress
        MAX-ACCESS read-write
        STATUS current
        DESCRIPTION
            "the address of capwap multicast"
        ::= { fsCapwapMulticastMIBObjects 2 }

fsCapwapMulticastMIBConformance OBJECT IDENTIFIER ::= { fsCapwapMulticastMIB 2 }
fsCapwapMulticastMIBCompliances OBJECT IDENTIFIER ::= { fsCapwapMulticastMIBConformance 1 }
fsCapwapMulticastMIBGroups      OBJECT IDENTIFIER ::= { fsCapwapMulticastMIBConformance 2 }


-- compliance statements

fsCapwapMulticastMIBCompliance MODULE-COMPLIANCE
        STATUS  current
        DESCRIPTION
                "The compliance statement for entities which implement
                the FS Capwap Multicast MIB"
        MODULE  -- this module
                MANDATORY-GROUPS { fsCapwapMulticastMIBGroup
                 }
        ::= { fsCapwapMulticastMIBCompliances 1 }

-- units of conformance

fsCapwapMulticastMIBGroup OBJECT-GROUP
        OBJECTS {
           fsCapwapMulticastWorkingMode,
           fsCapwapMulticastGroup
        }
        STATUS  current
        DESCRIPTION
                "A collection of objects providing CapwapMulticast configure ."
        ::= { fsCapwapMulticastMIBGroups 1 }

END
