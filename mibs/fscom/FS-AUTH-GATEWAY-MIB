-- *****************************************************************
-- FS-AUTH-GATEWAY-MIB.mib:  FS Auth-Gateway MIB file
--
-- April 2009, Chenfg
--
-- Copyright (c) 2009 by FS.COM Inc..
-- All rights reserved.
--
-- *****************************************************************
--

FS-AUTH-GATEWAY-MIB DEFINITIONS ::= BEGIN

IMPORTS
    MODULE-IDENTITY,
    OBJECT-TYPE,
    NOTIFICATION-TYPE,
    IpAddress,
    Unsigned32,
    TimeTicks,
    Integer32,
    Gauge32
            FROM SNMPv2-SMI
    RowStatus,
    MacAddress,
    DisplayString
            FROM SNMPv2-TC
    IfIndex
            FROM FS-TC
    InetAddressType,
    InetAddress
            FROM INET-ADDRESS-MIB
    MODULE-COMPLIANCE,
    OBJECT-GROUP,
    NOTIFICATION-GROUP
            FROM SNMPv2-CONF
    fsMgmt
            FROM FS-SMI;

fsWebAuthMIB MODULE-IDENTITY
    LAST-UPDATED "201003080000Z"
    ORGANIZATION "FS.COM Inc.."
    CONTACT-INFO
            "
            Tel: 400-865-2852

            E-mail: https://www.fs.com/live_chat_service_mail.html"
    DESCRIPTION
            "This module defines fs authGateway mibs."
    REVISION      "201003080000Z"
    DESCRIPTION
            "Added fsWebAuthUserExtTable."
    REVISION      "201002220000Z"
    DESCRIPTION
            "Add some objects for Application Security Zone Solutions
             by Wujj."
    REVISION      "200904160000Z"
    DESCRIPTION
            "Initial version of this MIB module."
    ::= { fsMgmt 40}

fsWebAuthMIBObjects OBJECT IDENTIFIER ::= { fsWebAuthMIB 1 }


-- Web authentication gateway user table

fsWebAuthUserTable OBJECT-TYPE
    SYNTAX  SEQUENCE OF FSWebAuthUserEntry
    MAX-ACCESS  not-accessible
    STATUS      current
    DESCRIPTION
            "A table that contains generic information about every user
            that is authenticated by web authentication gateway."
    ::= { fsWebAuthMIBObjects 1 }

fsWebAuthUserEntry OBJECT-TYPE
    SYNTAX  FSWebAuthUserEntry
    MAX-ACCESS  not-accessible
    STATUS  current
    DESCRIPTION
         "The entry of web authentication gateway table."
    INDEX   { authUserIpAddr }
    ::= { fsWebAuthUserTable 1 }

FSWebAuthUserEntry ::=
    SEQUENCE {
        authUserIpAddr                   IpAddress,
        authUserOnlineFlag               Gauge32,
        authUserTimeLimit                Gauge32,
        authUserTimeUsed                 Gauge32,
        authUserStatus                   RowStatus,
        authUserRoleName                 OCTET STRING,
        authUserSecZoneName              OCTET STRING,
        authUserSecZonePermissionType    Gauge32,
        authUserSecZonePermissionList    OCTET STRING,
        authUserOtherPermissionType      Gauge32,
        authUserTerminateCause	         Gauge32
    }

authUserIpAddr OBJECT-TYPE
    SYNTAX  IpAddress
    MAX-ACCESS  read-only
    STATUS  current
    DESCRIPTION
            "The IP address of the user."
    ::= { fsWebAuthUserEntry 1 }

authUserOnlineFlag OBJECT-TYPE
    SYNTAX  Gauge32
    MAX-ACCESS  read-only
    STATUS  current
    DESCRIPTION
            "The online(1)/offline(2) flag of the user."
    ::= { fsWebAuthUserEntry 2 }


authUserTimeLimit OBJECT-TYPE
    SYNTAX  Gauge32
    MAX-ACCESS  read-create
    STATUS  current
    DESCRIPTION
            "The value, in seconds, is time limit of the online user.
            If the time is unlimited, then this object has the value 0."
    ::= { fsWebAuthUserEntry 3 }

authUserTimeUsed OBJECT-TYPE
    SYNTAX  Gauge32
    MAX-ACCESS  read-only
    STATUS  current
    DESCRIPTION
            "The value, in seconds, is time used by the online user."
    ::= { fsWebAuthUserEntry 4 }

-- up-link bandwidth Limit
-- ::= { fsWebAuthUserEntry 5 }     this OID is obsolete

-- down-link bandwidth Limit
-- ::= { fsWebAuthUserEntry 6 }     this OID is obsolete

-- intramural up-link flow limit
-- ::= { fsWebAuthUserEntry 7 }     this OID is obsolete

-- intramural down-link flow limit
-- ::= { fsWebAuthUserEntry 8 }     this OID is obsolete

-- inland up-link flow limit
-- ::= { fsWebAuthUserEntry 9 }     this OID is obsolete

-- inland down-link flow limit
-- ::= { fsWebAuthUserEntry 10 }    this OID is obsolete

-- overseas up-link flow limit
-- ::= { fsWebAuthUserEntry 11 }    this OID is obsolete

-- overseas down-link flow limit
-- ::= { fsWebAuthUserEntry 12 }    this OID is obsolete

-- intramural up-link flow counter
-- ::= { fsWebAuthUserEntry 13 }    this OID is obsolete

-- intramural down-link flow counter
-- ::= { fsWebAuthUserEntry 14 }    this OID is obsolete

-- inland up-link flow counter
-- ::= { fsWebAuthUserEntry 15 }    this OID is obsolete

-- inland down-link flow counter
-- ::= { fsWebAuthUserEntry 16 }    this OID is obsolete

-- overseas up-link flow counter
-- ::= { fsWebAuthUserEntry 17 }    this OID is obsolete

-- overseas down-link flow counter
-- ::= { fsWebAuthUserEntry 18 }    this OID is obsolete

authUserStatus OBJECT-TYPE
    SYNTAX RowStatus
    MAX-ACCESS read-create
    STATUS current
    DESCRIPTION
            "The status of this row, by which new entries may be
            created, or old entries deleted from this table."
   ::= { fsWebAuthUserEntry 19 }

authUserRoleName OBJECT-TYPE
    SYNTAX  OCTET STRING(SIZE (32))
    MAX-ACCESS read-create
    STATUS current
    DESCRIPTION
            "The roleName of the user, defined in Application Security Zone Solutions.
            Apply to all support the Application Security Zone Solutions RSR Series products."
    ::= { fsWebAuthUserEntry 20 }

authUserSecZoneName OBJECT-TYPE
    SYNTAX  OCTET STRING(SIZE (32))
    MAX-ACCESS read-create
    STATUS current
    DESCRIPTION
            "User login secZoneName, defined in Application Security Zone Solutions.
            Apply to all support the Application Security Zone Solutions Firewall Series products."
    ::= { fsWebAuthUserEntry 21}

authUserSecZonePermissionType OBJECT-TYPE
    SYNTAX  Gauge32
    MAX-ACCESS read-create
    STATUS current
    DESCRIPTION
            "Login user's permission type, defined in Application Security Zone Solutions.
            Apply to all support the Application Security Zone Solutions Firewall Series products.
            permit(1),deny(2)"
    ::= { fsWebAuthUserEntry 22}

authUserSecZonePermissionList OBJECT-TYPE
    SYNTAX  OCTET STRING(SIZE (512))
    MAX-ACCESS read-create
    STATUS current
    DESCRIPTION
            "Login user's permission list, defined in Application Security Zone Solutions.
            Apply to all support the Application Security Zone Solutions Firewall Series products.
            for example,the permission list 192.168.20.21-255.255.255.255、192.168.21.21-255.255.255.0、192.168.22.22-255.255.255.128
            values C0A81414FFFFFFFFFFC0A81515FFFFFF00C0A81616FFFFFF80"
    ::= { fsWebAuthUserEntry 23}

authUserOtherPermissionType  OBJECT-TYPE
    SYNTAX  Gauge32
    MAX-ACCESS read-create
    STATUS current
    DESCRIPTION
            "Login user's other permission type, defined in Application Security Zone Solutions.
            Apply to all support the Application Security Zone Solutions Firewall Series products.
            permit(1),deny(2)"
    ::= { fsWebAuthUserEntry 24}

authUserTerminateCause OBJECT-TYPE
    SYNTAX  Gauge32
    MAX-ACCESS  read-only
    STATUS  current
    DESCRIPTION
            "The value, used by the offline user."
    ::= { fsWebAuthUserEntry 25 }

-- Web authentication gateway user extension table

fsWebAuthUserExtTable OBJECT-TYPE
    SYNTAX  SEQUENCE OF FSWebAuthUserExtEntry
    MAX-ACCESS  not-accessible
    STATUS      current
    DESCRIPTION
            "A table that contains generic information about every user
            that is authenticated by web authentication gateway."
    ::= { fsWebAuthMIBObjects 2 }

fsWebAuthUserExtEntry OBJECT-TYPE
    SYNTAX  FSWebAuthUserExtEntry
    MAX-ACCESS  not-accessible
    STATUS  current
    DESCRIPTION
         "The entry of web authentication gateway table."
    INDEX   { authUserExtAddrType, authUserExtAddr }
    ::= { fsWebAuthUserExtTable 1 }

FSWebAuthUserExtEntry ::=
    SEQUENCE {
        authUserExtAddrType                 InetAddressType,
        authUserExtAddr                     InetAddress,
        authUserExtMac                      MacAddress,
        authUserExtIfIndex                  IfIndex,
        authUserExtVlanId                   Unsigned32,
        authUserExtOnlineFlag               Gauge32,
        authUserExtTimeLimit                Gauge32,
        authUserExtTimeUsed                 Gauge32,
        authUserExtErrCause                 DisplayString,
        authUserExtStatus                   RowStatus
    }

authUserExtAddrType OBJECT-TYPE
    SYNTAX  InetAddressType
    MAX-ACCESS  read-only
    STATUS  current
    DESCRIPTION
            "The type of Internet address of the the user."
    ::= { fsWebAuthUserExtEntry 1 }

authUserExtAddr OBJECT-TYPE
    SYNTAX  InetAddress (SIZE(0..64))
    MAX-ACCESS  read-only
    STATUS  current
    DESCRIPTION
            "The Internet address of the the user. The type of this address is
            determined by the value of the authUserExtAddrType object."
    ::= { fsWebAuthUserExtEntry 2 }

authUserExtMac OBJECT-TYPE
    SYNTAX  MacAddress
    MAX-ACCESS  read-only
    STATUS  current
    DESCRIPTION
            "The MAC address of the the user."
    ::= { fsWebAuthUserExtEntry 3 }

authUserExtIfIndex OBJECT-TYPE
    SYNTAX  IfIndex
    MAX-ACCESS  read-only
    STATUS  current
    DESCRIPTION
            "The interface index associated with the user."
    ::= { fsWebAuthUserExtEntry 4 }

authUserExtVlanId OBJECT-TYPE
    SYNTAX  Unsigned32
    MAX-ACCESS  read-only
    STATUS  current
    DESCRIPTION
            "The VLAN-ID associated with the user."
    ::= { fsWebAuthUserExtEntry 5 }

authUserExtOnlineFlag OBJECT-TYPE
    SYNTAX  Gauge32
    MAX-ACCESS  read-only
    STATUS  current
    DESCRIPTION
            "The online(1)/offline(2) flag of the user."
    ::= { fsWebAuthUserExtEntry 6 }

authUserExtTimeLimit OBJECT-TYPE
    SYNTAX  Gauge32
    MAX-ACCESS  read-create
    STATUS  current
    DESCRIPTION
            "The value, in seconds, is time limit of the online user.
            If the time is unlimited, then this object has the value 0."
    ::= { fsWebAuthUserExtEntry 7 }

authUserExtTimeUsed OBJECT-TYPE
    SYNTAX  Gauge32
    MAX-ACCESS  read-only
    STATUS  current
    DESCRIPTION
            "The value, in seconds, is time used by the online user."
    ::= { fsWebAuthUserExtEntry 8 }

authUserExtErrCause OBJECT-TYPE
    SYNTAX DisplayString (SIZE  (0..64))
    MAX-ACCESS read-only
    STATUS current
    DESCRIPTION
            "The error cause information of the offline user.
            The default value is the null string, which indicates no error."
    DEFVAL { "" }
    ::= { fsWebAuthUserExtEntry 9 }

authUserExtStatus OBJECT-TYPE
    SYNTAX RowStatus
    MAX-ACCESS read-create
    STATUS current
    DESCRIPTION
            "The status of this row, by which new entries may be
            created, or old entries deleted from this table."
    ::= { fsWebAuthUserExtEntry 10 }


-- webauth user white list
-- add 2010-06
fsWebAuthWhiteListTable OBJECT-TYPE
    SYNTAX   SEQUENCE OF FSWebAuthWhiteListEntry
    MAX-ACCESS  not-accessible
    STATUS      current
    DESCRIPTION
         "A table that contains Whitelist of user authenticated
          by web authenticaton gateway."
    ::= { fsWebAuthMIBObjects 3 }

fsWebAuthWhiteListEntry OBJECT-TYPE
    SYNTAX  FSWebAuthWhiteListEntry
    MAX-ACCESS  not-accessible
    STATUS  current
    DESCRIPTION
         "The entry of web authentication user Whitelist
          table."
    INDEX   {
            fsWebAuthWhiteListAddress,
            fsWebAuthWhiteListNetMask
        }
    ::= { fsWebAuthWhiteListTable 1 }

FSWebAuthWhiteListEntry ::=
    SEQUENCE {
        fsWebAuthWhiteListAddress     IpAddress,
        fsWebAuthWhiteListNetMask     IpAddress,
        fsWebAuthWhiteListPort1       Unsigned32,
        fsWebAuthWhiteListPort2       Unsigned32,
        fsWebAuthWhiteListPort3       Unsigned32,
        fsWebAuthWhiteListPort4       Unsigned32,
        fsWebAuthWhiteListPort5       Unsigned32,
        fsWebAuthWhiteListPort6       Unsigned32,
        fsWebAuthWhiteListPort7       Unsigned32,
        fsWebAuthWhiteListPort8       Unsigned32,
        fsWebAuthWhiteListBindArpFlag INTEGER,
        fsWebAuthWhiteListStatus      RowStatus
    }

fsWebAuthWhiteListAddress OBJECT-TYPE
    SYNTAX IpAddress
    MAX-ACCESS read-only
    STATUS current
    DESCRIPTION
            "The ip address of user white list."
    ::= { fsWebAuthWhiteListEntry 1 }

fsWebAuthWhiteListNetMask OBJECT-TYPE
    SYNTAX IpAddress
    MAX-ACCESS read-only
    STATUS current
    DESCRIPTION
            "The NetMask of user white list."
    ::= { fsWebAuthWhiteListEntry 2 }

fsWebAuthWhiteListPort1 OBJECT-TYPE
    SYNTAX Unsigned32
    MAX-ACCESS read-create
    STATUS current
    DESCRIPTION
            "The access port1 of user white list."
    ::= { fsWebAuthWhiteListEntry 3 }

fsWebAuthWhiteListPort2 OBJECT-TYPE
    SYNTAX Unsigned32
    MAX-ACCESS read-create
    STATUS current
    DESCRIPTION
            "The access port2 of user white list."
    ::= { fsWebAuthWhiteListEntry 4 }

fsWebAuthWhiteListPort3 OBJECT-TYPE
    SYNTAX Unsigned32
    MAX-ACCESS read-create
    STATUS current
    DESCRIPTION
            "The access port3 of user white list."
    ::= { fsWebAuthWhiteListEntry 5 }

fsWebAuthWhiteListPort4 OBJECT-TYPE
    SYNTAX Unsigned32
    MAX-ACCESS read-create
    STATUS current
    DESCRIPTION
            "The access port4 of user white list."
    ::= { fsWebAuthWhiteListEntry 6 }

fsWebAuthWhiteListPort5 OBJECT-TYPE
    SYNTAX Unsigned32
    MAX-ACCESS read-create
    STATUS current
    DESCRIPTION
            "The access port5 of user white list."
    ::= { fsWebAuthWhiteListEntry 7 }

fsWebAuthWhiteListPort6 OBJECT-TYPE
    SYNTAX Unsigned32
    MAX-ACCESS read-create
    STATUS current
    DESCRIPTION
            "The access port6 of user white list."
    ::= { fsWebAuthWhiteListEntry 8 }

fsWebAuthWhiteListPort7 OBJECT-TYPE
    SYNTAX Unsigned32
    MAX-ACCESS read-create
    STATUS current
    DESCRIPTION
            "The access port7 of user white list."
    ::= { fsWebAuthWhiteListEntry 9 }

fsWebAuthWhiteListPort8 OBJECT-TYPE
    SYNTAX Unsigned32
    MAX-ACCESS read-create
    STATUS current
    DESCRIPTION
            "The access port8 of user white list."
    ::= { fsWebAuthWhiteListEntry 10 }

fsWebAuthWhiteListBindArpFlag OBJECT-TYPE
    SYNTAX INTEGER {
              no(0),
              yes(1)
           }
    MAX-ACCESS read-create
    STATUS current
    DESCRIPTION
            "The flag represent whether bind the arp or not.
             0 - not binding arp,
             1 - need to binding arp"
    ::= { fsWebAuthWhiteListEntry 11 }

fsWebAuthWhiteListStatus OBJECT-TYPE
    SYNTAX RowStatus
    MAX-ACCESS read-create
    STATUS current
    DESCRIPTION
            "The status of this row, by which new entries may be
            created, or old entries deleted from this table."
    ::= { fsWebAuthWhiteListEntry 12 }


-- webauth SDG user list
-- add 2010-12
fsWebAuthSDGUserTable OBJECT-TYPE
    SYNTAX   SEQUENCE OF FSWebAuthSDGUserEntry
    MAX-ACCESS  not-accessible
    STATUS      current
    DESCRIPTION
         "A table that contains webauth SDG user."
    ::= { fsWebAuthMIBObjects 4 }

fsWebAuthSDGUserEntry OBJECT-TYPE
    SYNTAX  FSWebAuthSDGUserEntry
    MAX-ACCESS  not-accessible
    STATUS  current
    DESCRIPTION
         "The SDG user entry of web authentication gateway table."
    INDEX   { authSDGUserVrfg, authSDGUserIpAddr }
    ::= { fsWebAuthSDGUserTable 1 }

FSWebAuthSDGUserEntry ::=
    SEQUENCE {
        authSDGUserVrfg                   DisplayString,
        authSDGUserIpAddr                   IpAddress,
        authSDGUserOnlineFlag               Gauge32,
        authSDGUserTimeLimit                Gauge32,
        authSDGUserTimeUsed                 Gauge32,
        authSDGUserVrf                    DisplayString,
        authSDGUserRoleName                 OCTET STRING,
        authSDGUserSecZoneName              OCTET STRING,
        authSDGUserSecZonePermissionType    Gauge32,
        authSDGUserSecZonePermissionList    OCTET STRING,
        authSDGUserOtherPermissionType      Gauge32,
        authSDGUserTerminateCause	         Gauge32,
        authSDGUserStatus                   RowStatus
    }

authSDGUserVrfg OBJECT-TYPE
    SYNTAX  DisplayString (SIZE (0..32))
    MAX-ACCESS  read-only
    STATUS  current
    DESCRIPTION
            "The vrf group name of the SDG user."
    ::= { fsWebAuthSDGUserEntry 1 }

authSDGUserIpAddr OBJECT-TYPE
    SYNTAX  IpAddress
    MAX-ACCESS  read-only
    STATUS  current
    DESCRIPTION
            "The IP address of the SDG user."
    ::= { fsWebAuthSDGUserEntry 2 }

authSDGUserOnlineFlag OBJECT-TYPE
    SYNTAX  Gauge32
    MAX-ACCESS  read-only
    STATUS  current
    DESCRIPTION
            "The online(1)/offline(2) flag of the SDG user."
    ::= { fsWebAuthSDGUserEntry 3 }


authSDGUserTimeLimit OBJECT-TYPE
    SYNTAX  Gauge32
    MAX-ACCESS  read-create
    STATUS  current
    DESCRIPTION
            "The value, in seconds, is time limit of the online SDG user.
            If the time is unlimited, then this object has the value 0."
    ::= { fsWebAuthSDGUserEntry 4 }

authSDGUserTimeUsed OBJECT-TYPE
    SYNTAX  Gauge32
    MAX-ACCESS  read-only
    STATUS  current
    DESCRIPTION
            "The value, in seconds, is time used by the online SDG user."
    ::= { fsWebAuthSDGUserEntry 5 }

authSDGUserVrf OBJECT-TYPE
    SYNTAX  DisplayString
    MAX-ACCESS  read-only
    STATUS  current
    DESCRIPTION
            "The (dest) vrf name for the user."
    ::= { fsWebAuthSDGUserEntry 6 }

-- up-link bandwidth Limit
-- ::= { fsWebAuthSDGUserEntry 7 }     this OID is obsolete

-- down-link bandwidth Limit
-- ::= { fsWebAuthSDGUserEntry 8 }     this OID is obsolete

-- intramural up-link flow limit
-- ::= { fsWebAuthSDGUserEntry 9 }     this OID is obsolete

-- intramural down-link flow limit
-- ::= { fsWebAuthSDGUserEntry 10 }     this OID is obsolete

-- inland up-link flow limit
-- ::= { fsWebAuthSDGUserEntry 11 }     this OID is obsolete

-- inland down-link flow limit
-- ::= { fsWebAuthSDGUserEntry 12 }    this OID is obsolete

-- overseas up-link flow limit
-- ::= { fsWebAuthSDGUserEntry 13 }    this OID is obsolete

-- overseas down-link flow limit
-- ::= { fsWebAuthSDGUserEntry 14 }    this OID is obsolete

-- intramural up-link flow counter
-- ::= { fsWebAuthSDGUserEntry 15 }    this OID is obsolete

-- intramural down-link flow counter
-- ::= { fsWebAuthSDGUserEntry 16 }    this OID is obsolete

-- inland up-link flow counter
-- ::= { fsWebAuthSDGUserEntry 17 }    this OID is obsolete

-- inland down-link flow counter
-- ::= { fsWebAuthSDGUserEntry 18 }    this OID is obsolete

-- overseas up-link flow counter
-- ::= { fsWebAuthSDGUserEntry 19 }    this OID is obsolete

-- overseas down-link flow counter
-- ::= { fsWebAuthSDGUserEntry 20 }    this OID is obsolete

authSDGUserRoleName OBJECT-TYPE
    SYNTAX  OCTET STRING(SIZE (32))
    MAX-ACCESS read-create
    STATUS current
    DESCRIPTION
            "The roleName of the user, defined in Application Security Zone Solutions.
            Apply to all support the Application Security Zone Solutions RSR Series products."
    ::= { fsWebAuthSDGUserEntry 21 }

authSDGUserSecZoneName OBJECT-TYPE
    SYNTAX  OCTET STRING(SIZE (32))
    MAX-ACCESS read-create
    STATUS current
    DESCRIPTION
            "User login secZoneName, defined in Application Security Zone Solutions.
            Apply to all support the Application Security Zone Solutions Firewall Series products."
    ::= { fsWebAuthSDGUserEntry 22}

authSDGUserSecZonePermissionType OBJECT-TYPE
    SYNTAX  Gauge32
    MAX-ACCESS read-create
    STATUS current
    DESCRIPTION
            "Login user's permission type, defined in Application Security Zone Solutions.
            Apply to all support the Application Security Zone Solutions Firewall Series products.
            permit(1),deny(2)"
    ::= { fsWebAuthSDGUserEntry 23}

authSDGUserSecZonePermissionList OBJECT-TYPE
    SYNTAX  OCTET STRING(SIZE (512))
    MAX-ACCESS read-create
    STATUS current
    DESCRIPTION
            "Login user's permission list, defined in Application Security Zone Solutions.
            Apply to all support the Application Security Zone Solutions Firewall Series products.
            for example,the permission list 192.168.20.21-255.255.255.255、192.168.21.21-255.255.255.0、192.168.22.22-255.255.255.128
            values C0A81414FFFFFFFFFFC0A81515FFFFFF00C0A81616FFFFFF80"
    ::= { fsWebAuthSDGUserEntry 24}

authSDGUserOtherPermissionType  OBJECT-TYPE
    SYNTAX  Gauge32
    MAX-ACCESS read-create
    STATUS current
    DESCRIPTION
            "Login user's other permission type, defined in Application Security Zone Solutions.
            Apply to all support the Application Security Zone Solutions Firewall Series products.
            permit(1),deny(2)"
    ::= { fsWebAuthSDGUserEntry 25}

authSDGUserTerminateCause OBJECT-TYPE
    SYNTAX  Gauge32
    MAX-ACCESS  read-only
    STATUS  current
    DESCRIPTION
            "The value, used by the offline user."
    ::= { fsWebAuthSDGUserEntry 26 }

authSDGUserStatus OBJECT-TYPE
    SYNTAX RowStatus
    MAX-ACCESS read-create
    STATUS current
    DESCRIPTION
            "The status of this row, by which new entries may be
            created, or old entries deleted from this table."
   ::= { fsWebAuthSDGUserEntry 27 }


-- Web authentication user table indexed with mac address.
-- added 2013-03

fsWebAuthMacUserTable OBJECT-TYPE
    SYNTAX  SEQUENCE OF FSWebAuthMacUserEntry
    MAX-ACCESS  not-accessible
    STATUS      current
    DESCRIPTION
            "A table that contains information, indexed with mac address,
            for each user that is authenticated by web authentication gateway."
    ::= { fsWebAuthMIBObjects 5 }

fsWebAuthMacUserEntry OBJECT-TYPE
    SYNTAX  FSWebAuthMacUserEntry
    MAX-ACCESS  not-accessible
    STATUS  current
    DESCRIPTION
         "The entry of web authentication mac table."
    INDEX   { fsAuthMacUserMacAddr }
    ::= { fsWebAuthMacUserTable 1 }

FSWebAuthMacUserEntry ::=
    SEQUENCE {
        fsAuthMacUserMacAddr               MacAddress,
        fsAuthMacUserName                  OCTET STRING,
        fsAuthMacUserTerminalId            OCTET STRING
    }

fsAuthMacUserMacAddr OBJECT-TYPE
    SYNTAX  MacAddress
    MAX-ACCESS  read-only
    STATUS  current
    DESCRIPTION
            "The MAC address of the the user."
    ::= { fsWebAuthMacUserEntry 1 }

fsAuthMacUserName OBJECT-TYPE
    SYNTAX  OCTET STRING(SIZE (253))
    MAX-ACCESS read-only
    STATUS current
    DESCRIPTION
            "Name of the user, specified with fsAuthMacUserMacAddr. "
    ::= { fsWebAuthMacUserEntry 2 }

fsAuthMacUserTerminalId OBJECT-TYPE
    SYNTAX  OCTET STRING(SIZE (253))
    MAX-ACCESS read-only
    STATUS current
    DESCRIPTION
            "Terminal Identification of the user, specified with fsAuthMacUserMacAddr. "
    ::= { fsWebAuthMacUserEntry 3 }

fsWebAuthUserMIB OBJECT IDENTIFIER ::= { fsWebAuthMIBObjects 6 }

fsWebAuthUserMIBTable OBJECT-TYPE
    SYNTAX  SEQUENCE OF FSWebAuthUserMIBEntry
    MAX-ACCESS  not-accessible
    STATUS      current
    DESCRIPTION
            "A table that contains information, indexed with ip address,
			for each user that is authenticated by web authentication gateway."
	::= { fsWebAuthUserMIB 1 }

fsWebAuthUserMIBEntry OBJECT-TYPE
    SYNTAX  FSWebAuthUserMIBEntry
    MAX-ACCESS  not-accessible
    STATUS  current
    DESCRIPTION
         "The entry of web authentication ip table."
    INDEX   { fsAuthUserMIBIpAddress }
    ::= { fsWebAuthUserMIBTable 1 }

FSWebAuthUserMIBEntry ::=
    SEQUENCE {
        fsAuthUserMIBIpAddress                IpAddress,
        fsAuthUserMIBName                     OCTET STRING,
        fsAuthUserMIBAuthType                 Gauge32,
        fsAuthUserMIBMacAddress               MacAddress,
        fsAuthUserMIBVlanId                   Gauge32,
        fsAuthUserMIBPortIndex                Gauge32,
        fsAuthUserMIBTimeUsed                 Gauge32
    }

fsAuthUserMIBIpAddress OBJECT-TYPE
    SYNTAX    IpAddress
    MAX-ACCESS read-only
    STATUS current
    DESCRIPTION
            "Webauth user ip address. "
    ::= { fsWebAuthUserMIBEntry 1 }

fsAuthUserMIBName OBJECT-TYPE
    SYNTAX    OCTET STRING
    MAX-ACCESS read-only
    STATUS current
    DESCRIPTION
            "Webauth username. "
    ::= { fsWebAuthUserMIBEntry 2 }

fsAuthUserMIBAuthType OBJECT-TYPE
    SYNTAX    Gauge32
    MAX-ACCESS read-only
    STATUS current
    DESCRIPTION
            "Webauth user authentication type, 1-v2portal, 2-iportal. "
    ::= { fsWebAuthUserMIBEntry 3 }

fsAuthUserMIBMacAddress OBJECT-TYPE
    SYNTAX    MacAddress
    MAX-ACCESS read-only
    STATUS current
    DESCRIPTION
            "Webauth user mac address. "
    ::= { fsWebAuthUserMIBEntry 4 }

fsAuthUserMIBVlanId OBJECT-TYPE
    SYNTAX    Gauge32
    MAX-ACCESS read-only
    STATUS current
    DESCRIPTION
            "Webauth user vlanid. "
    ::= { fsWebAuthUserMIBEntry 5 }

fsAuthUserMIBPortIndex OBJECT-TYPE
    SYNTAX    Gauge32
    MAX-ACCESS read-only
    STATUS current
    DESCRIPTION
            "Webauth user authentication port index. "
    ::= { fsWebAuthUserMIBEntry 6 }

fsAuthUserMIBTimeUsed OBJECT-TYPE
    SYNTAX    Gauge32
    MAX-ACCESS read-only
    STATUS current
    DESCRIPTION
            "Webauth user time used. "
    ::= { fsWebAuthUserMIBEntry 7 }


-- Web authentication direct site user table

fsWebAuthDirectSiteTable OBJECT-TYPE
    SYNTAX   SEQUENCE OF FSWebAuthDirectSiteEntry
    MAX-ACCESS  not-accessible
    STATUS      current
    DESCRIPTION
         "A table that contains DirectSite user
          by web authenticaton gateway."
    ::= { fsWebAuthMIBObjects 7 }

fsWebAuthDirectSiteEntry OBJECT-TYPE
    SYNTAX  FSWebAuthDirectSiteEntry
    MAX-ACCESS  not-accessible
    STATUS  current
    DESCRIPTION
         "The entry of web authentication DirectSite user
          table."
    INDEX   {
            fsWebAuthDirectSiteAddress,
            fsWebAuthDirectSiteNetMask
        }
    ::= { fsWebAuthDirectSiteTable 1 }

FSWebAuthDirectSiteEntry ::=
    SEQUENCE {
        fsWebAuthDirectSiteAddress     IpAddress,
        fsWebAuthDirectSiteNetMask     IpAddress,
        fsWebAuthDirectSiteStatus      RowStatus,
        fsWebAuthDirectSiteBindArpFlag INTEGER
    }

fsWebAuthDirectSiteAddress OBJECT-TYPE
    SYNTAX IpAddress
    MAX-ACCESS read-only
    STATUS current
    DESCRIPTION
            "The ip address of direct site user."
    ::= { fsWebAuthDirectSiteEntry 1 }

fsWebAuthDirectSiteNetMask OBJECT-TYPE
    SYNTAX IpAddress
    MAX-ACCESS read-only
    STATUS current
    DESCRIPTION
            "The NetMask of direct site user."
    ::= { fsWebAuthDirectSiteEntry 2 }

fsWebAuthDirectSiteStatus OBJECT-TYPE
    SYNTAX RowStatus
    MAX-ACCESS read-create
    STATUS current
    DESCRIPTION
            "The status of this row, by which new entries may be
            created, or old entries deleted from this table."
    ::= { fsWebAuthDirectSiteEntry 3 }

fsWebAuthDirectSiteBindArpFlag OBJECT-TYPE
    SYNTAX INTEGER {
              no(0),
              yes(1)
           }
    MAX-ACCESS read-create
    STATUS current
    DESCRIPTION
            "The flag represent whether bind the arp or not.
             0 - not binding arp,
             1 - need to binding arp"
    ::= { fsWebAuthDirectSiteEntry 4 }

-- webauth direct host user table

fsWebAuthDirectHostTable OBJECT-TYPE
    SYNTAX   SEQUENCE OF FSWebAuthDirectHostEntry
    MAX-ACCESS  not-accessible
    STATUS      current
    DESCRIPTION
         "A table that contains DirectHost of user authenticated
          by web authenticaton gateway."
    ::= { fsWebAuthMIBObjects 8 }

fsWebAuthDirectHostEntry OBJECT-TYPE
    SYNTAX  FSWebAuthDirectHostEntry
    MAX-ACCESS  not-accessible
    STATUS  current
    DESCRIPTION
         "The entry of web authentication user DirectHost
          table."
    INDEX   {
            fsWebAuthDirectHostAddress,
            fsWebAuthDirectHostNetMask
        }
    ::= { fsWebAuthDirectHostTable 1 }

FSWebAuthDirectHostEntry ::=
    SEQUENCE {
        fsWebAuthDirectHostAddress     IpAddress,
        fsWebAuthDirectHostNetMask     IpAddress,
        fsWebAuthDirectHostPort1       Unsigned32,
        fsWebAuthDirectHostPort2       Unsigned32,
        fsWebAuthDirectHostPort3       Unsigned32,
        fsWebAuthDirectHostPort4       Unsigned32,
        fsWebAuthDirectHostPort5       Unsigned32,
        fsWebAuthDirectHostPort6       Unsigned32,
        fsWebAuthDirectHostPort7       Unsigned32,
        fsWebAuthDirectHostPort8       Unsigned32,
        fsWebAuthDirectHostBindArpFlag INTEGER,
        fsWebAuthDirectHostStatus      RowStatus,
        fsWebAuthDirectHostPortIfx     Gauge32
    }

fsWebAuthDirectHostAddress OBJECT-TYPE
    SYNTAX IpAddress
    MAX-ACCESS read-only
    STATUS current
    DESCRIPTION
            "The ip address of user DirectHost."
    ::= { fsWebAuthDirectHostEntry 1 }

fsWebAuthDirectHostNetMask OBJECT-TYPE
    SYNTAX IpAddress
    MAX-ACCESS read-only
    STATUS current
    DESCRIPTION
            "The NetMask of user DirectHost."
    ::= { fsWebAuthDirectHostEntry 2 }

fsWebAuthDirectHostPort1 OBJECT-TYPE
    SYNTAX Unsigned32
    MAX-ACCESS read-create
    STATUS current
    DESCRIPTION
            "The access port1 of user DirectHost."
    ::= { fsWebAuthDirectHostEntry 3 }

fsWebAuthDirectHostPort2 OBJECT-TYPE
    SYNTAX Unsigned32
    MAX-ACCESS read-create
    STATUS current
    DESCRIPTION
            "The access port2 of user DirectHost."
    ::= { fsWebAuthDirectHostEntry 4 }

fsWebAuthDirectHostPort3 OBJECT-TYPE
    SYNTAX Unsigned32
    MAX-ACCESS read-create
    STATUS current
    DESCRIPTION
            "The access port3 of user DirectHost."
    ::= { fsWebAuthDirectHostEntry 5 }

fsWebAuthDirectHostPort4 OBJECT-TYPE
    SYNTAX Unsigned32
    MAX-ACCESS read-create
    STATUS current
    DESCRIPTION
            "The access port4 of user DirectHost."
    ::= { fsWebAuthDirectHostEntry 6 }

fsWebAuthDirectHostPort5 OBJECT-TYPE
    SYNTAX Unsigned32
    MAX-ACCESS read-create
    STATUS current
    DESCRIPTION
            "The access port5 of user DirectHost."
    ::= { fsWebAuthDirectHostEntry 7 }

fsWebAuthDirectHostPort6 OBJECT-TYPE
    SYNTAX Unsigned32
    MAX-ACCESS read-create
    STATUS current
    DESCRIPTION
            "The access port6 of user DirectHost."
    ::= { fsWebAuthDirectHostEntry 8 }

fsWebAuthDirectHostPort7 OBJECT-TYPE
    SYNTAX Unsigned32
    MAX-ACCESS read-create
    STATUS current
    DESCRIPTION
            "The access port7 of user DirectHost."
    ::= { fsWebAuthDirectHostEntry 9 }

fsWebAuthDirectHostPort8 OBJECT-TYPE
    SYNTAX Unsigned32
    MAX-ACCESS read-create
    STATUS current
    DESCRIPTION
            "The access port8 of user DirectHost."
    ::= { fsWebAuthDirectHostEntry 10 }

fsWebAuthDirectHostBindArpFlag OBJECT-TYPE
    SYNTAX INTEGER {
              no(0),
              yes(1)
           }
    MAX-ACCESS read-create
    STATUS current
    DESCRIPTION
            "The flag represent whether bind the arp or not.
             0 - not binding arp,
             1 - need to binding arp"
    ::= { fsWebAuthDirectHostEntry 11 }

fsWebAuthDirectHostStatus OBJECT-TYPE
    SYNTAX RowStatus
    MAX-ACCESS read-create
    STATUS current
    DESCRIPTION
            "The status of this row, by which new entries may be
            created, or old entries deleted from this table."
    ::= { fsWebAuthDirectHostEntry 12 }

fsWebAuthDirectHostPortIfx OBJECT-TYPE
    SYNTAX Gauge32
    MAX-ACCESS read-create
    STATUS current
    DESCRIPTION
            "The access portifx of user DirectHost."
    ::= { fsWebAuthDirectHostEntry 13 }

--- web-auth free acct ip table

fsWebAuthFreeAcctIpTable OBJECT-TYPE
    SYNTAX   SEQUENCE OF FSWebAuthFreeAcctIpEntry
    MAX-ACCESS  not-accessible
    STATUS      current
    DESCRIPTION
         "A table that contains FreeAcctIp of user authenticated
          by web authenticaton gateway."
    ::= { fsWebAuthMIBObjects 9 }

fsWebAuthFreeAcctIpEntry OBJECT-TYPE
    SYNTAX  FSWebAuthFreeAcctIpEntry
    MAX-ACCESS  not-accessible
    STATUS  current
    DESCRIPTION
         "The entry of web authentication user FreeAcctIp
          table."
    INDEX   {
            fsWebAuthFreeAcctIpAddress,
            fsWebAuthFreeAcctIpNetMask
        }
    ::= { fsWebAuthFreeAcctIpTable 1 }

FSWebAuthFreeAcctIpEntry ::=
    SEQUENCE {
        fsWebAuthFreeAcctIpAddress     IpAddress,
        fsWebAuthFreeAcctIpNetMask     IpAddress,
        fsWebAuthFreeAcctIpStatus      RowStatus
    }

fsWebAuthFreeAcctIpAddress OBJECT-TYPE
    SYNTAX IpAddress
    MAX-ACCESS read-only
    STATUS current
    DESCRIPTION
            "The ip address of user FreeAcctIp."
    ::= { fsWebAuthFreeAcctIpEntry 1 }

fsWebAuthFreeAcctIpNetMask OBJECT-TYPE
    SYNTAX IpAddress
    MAX-ACCESS read-only
    STATUS current
    DESCRIPTION
            "The NetMask of user FreeAcctIp."
    ::= { fsWebAuthFreeAcctIpEntry 2 }

fsWebAuthFreeAcctIpStatus OBJECT-TYPE
    SYNTAX RowStatus
    MAX-ACCESS read-create
    STATUS current
    DESCRIPTION
            "The status of this row, by which new entries may be
            created, or old entries deleted from this table."
    ::= { fsWebAuthFreeAcctIpEntry 3 }

--- web-auth free acct url table

fsWebAuthFreeAcctUrlTable OBJECT-TYPE
    SYNTAX   SEQUENCE OF FSWebAuthFreeAcctUrlEntry
    MAX-ACCESS  not-accessible
    STATUS      current
    DESCRIPTION
         "A table that contains FreeAcctUrl
          by web authenticaton gateway."
    ::= { fsWebAuthMIBObjects 10 }

fsWebAuthFreeAcctUrlEntry OBJECT-TYPE
    SYNTAX  FSWebAuthFreeAcctUrlEntry
    MAX-ACCESS  not-accessible
    STATUS  current
    DESCRIPTION
         "The entry of web authentication user FreeAcctUrl
          table."
    INDEX   {
            fsWebAuthFreeAcctUrl
        }
    ::= { fsWebAuthFreeAcctUrlTable 1 }

FSWebAuthFreeAcctUrlEntry ::=
    SEQUENCE {
        fsWebAuthFreeAcctUrl     		OCTET STRING,
        fsWebAuthFreeAcctUrlStatus      RowStatus
    }

fsWebAuthFreeAcctUrl OBJECT-TYPE
    SYNTAX    OCTET STRING
    MAX-ACCESS read-only
    STATUS current
    DESCRIPTION
            "web-auth free acct url "
    ::= { fsWebAuthFreeAcctUrlEntry 1 }

fsWebAuthFreeAcctUrlStatus OBJECT-TYPE
    SYNTAX RowStatus
    MAX-ACCESS read-create
    STATUS current
    DESCRIPTION
            "The status of this row, by which new entries may be
            created, or old entries deleted from this table."
    ::= { fsWebAuthFreeAcctUrlEntry 2 }

--- web-auth no offline Detect table

fsWebAuthOfflineDetectTable OBJECT-TYPE
    SYNTAX   SEQUENCE OF FSWebAuthOfflineDetectEntry
    MAX-ACCESS  not-accessible
    STATUS      current
    DESCRIPTION
         "A table that contains OfflineDetect
          by web authenticaton gateway."
    ::= { fsWebAuthMIBObjects 11 }

fsWebAuthOfflineDetectEntry OBJECT-TYPE
    SYNTAX  FSWebAuthOfflineDetectEntry
    MAX-ACCESS  not-accessible
    STATUS  current
    DESCRIPTION
         "The entry of web authentication user OfflineDetect
          table."
    INDEX   {
            fsWebAuthOfflineDetectime
        }
    ::= { fsWebAuthOfflineDetectTable 1 }

FSWebAuthOfflineDetectEntry ::=
    SEQUENCE {
        fsWebAuthOfflineDetectime    	  Unsigned32,
        fsWebAuthOfflineDetectStatus      RowStatus
    }

fsWebAuthOfflineDetectime  OBJECT-TYPE
    SYNTAX Unsigned32
    MAX-ACCESS read-only
    STATUS current
    DESCRIPTION
            "The webauth no flow offline interval time."
    ::= { fsWebAuthOfflineDetectEntry 1 }

fsWebAuthOfflineDetectStatus OBJECT-TYPE
    SYNTAX RowStatus
    MAX-ACCESS read-create
    STATUS current
    DESCRIPTION
            "The status of this row, by which new entries may be
            created, or old entries deleted from this table."
    ::= { fsWebAuthOfflineDetectEntry 2 }

--- web-auth current online user

fsWebAuthCurrentOnlineUser OBJECT-TYPE
        SYNTAX   Integer32
    MAX-ACCESS  read-only
    STATUS  current
    DESCRIPTION
            "The maximum number of current online user."
    ::= { fsWebAuthMIBObjects 12 }

--- web-auth current user

fsWebAuthCurrentUser OBJECT-TYPE
        SYNTAX   Integer32
    MAX-ACCESS  read-only
    STATUS  current
    DESCRIPTION
            "The maximum number of current user."
    ::= { fsWebAuthMIBObjects 13 }

--- web-auth maximum online user

fsWebAuthMaximumOnlineUser OBJECT-TYPE
        SYNTAX   Integer32
    MAX-ACCESS  read-only
    STATUS  current
    DESCRIPTION
            "The maximum number of maximum online user."
    ::= { fsWebAuthMIBObjects 14 }

-- web-auth trap

fsWebAuthMIBTraps        OBJECT IDENTIFIER ::= { fsWebAuthMIB 2 }
fsWebAuthMIBTrapsObjects OBJECT IDENTIFIER ::= { fsWebAuthMIB 4 }

-- Trap Objects
fsWebAuthApMac OBJECT-TYPE
    SYNTAX      MacAddress
    MAX-ACCESS  accessible-for-notify
    STATUS      current
    DESCRIPTION
        "Represents the unique identifier of a AP."
    ::= { fsWebAuthMIBTrapsObjects 1 }

fsWebAuthApIp OBJECT-TYPE
    SYNTAX      IpAddress
    MAX-ACCESS  accessible-for-notify
    STATUS      current
    DESCRIPTION
        "Represents the Ip address of a AP."
    ::= { fsWebAuthMIBTrapsObjects 2 }

fsWebAuthStaMac OBJECT-TYPE
    SYNTAX      MacAddress
    MAX-ACCESS  accessible-for-notify
    STATUS      current
    DESCRIPTION
        "Represents the unique identifier of a STA."
    ::= { fsWebAuthMIBTrapsObjects 3 }

fsWebAuthStaIp OBJECT-TYPE
    SYNTAX      IpAddress
    MAX-ACCESS  accessible-for-notify
    STATUS      current
    DESCRIPTION
        "Represents the Ip of a STA."
    ::= { fsWebAuthMIBTrapsObjects 4 }

fsWebAuthStaIpv6 OBJECT-TYPE
    SYNTAX      InetAddress
    MAX-ACCESS  accessible-for-notify
    STATUS      current
    DESCRIPTION
              "Sta ipv6 address."
    ::= { fsWebAuthMIBTrapsObjects 5 }

fsWebAuthStaOperType OBJECT-TYPE
    SYNTAX      INTEGER (1..3)
    MAX-ACCESS  accessible-for-notify
    STATUS      current
    DESCRIPTION
        "Represents the sta's web-auth operation, 1-webon,2-weboff, 3-webauthfail"
    ::= { fsWebAuthMIBTrapsObjects 6 }

fsWebAuthStaApRadioId OBJECT-TYPE
    SYNTAX      INTEGER(1..2)
    MAX-ACCESS  accessible-for-notify
    STATUS      current
    DESCRIPTION
        "Represents the radio id which STA attach."
    ::= { fsWebAuthMIBTrapsObjects 7 }

fsWebAuthStaApRadioType OBJECT-TYPE
    SYNTAX      INTEGER (1..2)
    MAX-ACCESS  accessible-for-notify
    STATUS      current
    DESCRIPTION
              "1--802.11b
               2--802.11a"
    ::= { fsWebAuthMIBTrapsObjects 8 }

fsWebAuthStaVlanId OBJECT-TYPE
    SYNTAX      INTEGER (1..4094)
    MAX-ACCESS  accessible-for-notify
    STATUS      current
    DESCRIPTION
              "Vlan Id the sta belongs to"
    ::= { fsWebAuthMIBTrapsObjects 9 }

fsWebAuthStaWlanId OBJECT-TYPE
    SYNTAX      INTEGER (1..4095)
    MAX-ACCESS  accessible-for-notify
    STATUS      current
    DESCRIPTION
              "Wlan Id the sta belongs to"
    ::= { fsWebAuthMIBTrapsObjects 10 }

fsWebAuthOperTime OBJECT-TYPE
    SYNTAX	TimeTicks
    MAX-ACCESS  accessible-for-notify
    STATUS      current
    DESCRIPTION
              "Sta auth oper time"
    ::= { fsWebAuthMIBTrapsObjects 11 }

fsWebAuthStaAssoAuthMode OBJECT-TYPE
    SYNTAX  INTEGER {
        open(0),
        wep(1),
        dot1x-wep(2),
        dot1x-wpa(3),
        dot1x-wpa2(4),
        mab(5),
        psk-wpa(6),
        psk-wpa2(7),
        wapi(8)
    }
    MAX-ACCESS  accessible-for-notify
    STATUS  current
    DESCRIPTION
            "The Sta associate authentication mode."
    ::= { fsWebAuthMIBTrapsObjects 12 }

fsWebAuthStaNetAuthMode OBJECT-TYPE
    SYNTAX  INTEGER {
        open(0),
        web(1)
    }
    MAX-ACCESS  accessible-for-notify
    STATUS  current
    DESCRIPTION
            "The Sta's authentication mode after associated."
    ::= { fsWebAuthMIBTrapsObjects 13 }

fsWebAuthStaRssi OBJECT-TYPE
    SYNTAX      INTEGER
    MAX-ACCESS  accessible-for-notify
    STATUS      current
    DESCRIPTION
            "The Sta's Received Signal Strength Indicator."
    ::= { fsWebAuthMIBTrapsObjects 14 }

fsWebAuthStaSsid OBJECT-TYPE
    SYNTAX  DisplayString
    MAX-ACCESS  accessible-for-notify
    STATUS  current
    DESCRIPTION
            "Sta associate ssid."
    ::= { fsWebAuthMIBTrapsObjects 15 }

fsWebAuthStaLinkRate OBJECT-TYPE
    SYNTAX  INTEGER
    MAX-ACCESS  accessible-for-notify
    STATUS  current
    DESCRIPTION
            "Sta link rate."
    ::= { fsWebAuthMIBTrapsObjects 16 }

fsWebAuthStaCurChannel OBJECT-TYPE
    SYNTAX  INTEGER
    MAX-ACCESS  accessible-for-notify
    STATUS  current
    DESCRIPTION
            "Sta current channel."
    ::= { fsWebAuthMIBTrapsObjects 17 }

fsWebAuthStaUsername OBJECT-TYPE
    SYNTAX	DisplayString (SIZE(1..255))
    MAX-ACCESS  accessible-for-notify
    STATUS      current
    DESCRIPTION
              "Sta auth username"
    ::= { fsWebAuthMIBTrapsObjects 18 }

fsWebAuthStaTerminalType OBJECT-TYPE
    SYNTAX      DisplayString
    MAX-ACCESS  accessible-for-notify
    STATUS      current
    DESCRIPTION
              "Sta terminal type"
    ::= { fsWebAuthMIBTrapsObjects 19 }

fsWebAuthStaTerminateCause OBJECT-TYPE
    SYNTAX  INTEGER
    MAX-ACCESS  accessible-for-notify
    STATUS  current
    DESCRIPTION
            "Sta terminate cause."
    ::= { fsWebAuthMIBTrapsObjects 20 }

fsWebAuthStaReplyMessage OBJECT-TYPE
    SYNTAX  DisplayString
    MAX-ACCESS  accessible-for-notify
    STATUS  current
    DESCRIPTION
            "Sta auth fail reason ."
    ::= { fsWebAuthMIBTrapsObjects 21 }

fsWebAuthStaTerminalId OBJECT-TYPE
    SYNTAX      DisplayString
    MAX-ACCESS  accessible-for-notify
    STATUS      current
    DESCRIPTION
              "Sta terminal Identification"
    ::= { fsWebAuthMIBTrapsObjects 22 }

fsWebAuthType OBJECT-TYPE
    SYNTAX    INTEGER (1..2)
    MAX-ACCESS  accessible-for-notify
    STATUS      current
    DESCRIPTION
              "Webauth user type(1-v2portal, 2-iportal)"
    ::= { fsWebAuthMIBTrapsObjects 23 }

fsWebAuthPortIndex OBJECT-TYPE
    SYNTAX    INTEGER
    MAX-ACCESS  accessible-for-notify
    STATUS      current
    DESCRIPTION
              "Webauth user authentication port index"
    ::= { fsWebAuthMIBTrapsObjects 24 }

fsWebAuthTlvNum OBJECT-TYPE
    SYNTAX    INTEGER
    MAX-ACCESS  accessible-for-notify
    STATUS      current
    DESCRIPTION
              "Webauth redirect info TLV number"
    ::= { fsWebAuthMIBTrapsObjects 25 }

fsWebAuthTlv OBJECT-TYPE
    SYNTAX    DisplayString
    MAX-ACCESS  accessible-for-notify
    STATUS      current
    DESCRIPTION
              "Webauth redirect info TLV strings"
    ::= { fsWebAuthMIBTrapsObjects 26 }

-- Trap Node
fsWebAuthUserLeave NOTIFICATION-TYPE
    OBJECTS   { authUserIpAddr, authUserTimeUsed, authUserTerminateCause }
    STATUS     current
    DESCRIPTION
            "The user offline trap."
    ::= { fsWebAuthMIBTraps 1 }

fsWebAuthUserExtLeave NOTIFICATION-TYPE
    OBJECTS  {
                authUserExtAddrType,
                authUserExtAddr,
                authUserExtMac,
                authUserExtIfIndex,
                authUserExtVlanId,
                authUserExtTimeUsed,
                authUserExtErrCause
    }
    STATUS     current
    DESCRIPTION
            "The user extension offline trap."
    ::= { fsWebAuthMIBTraps 2 }

fsWebAuthSDGUserLeave NOTIFICATION-TYPE
    OBJECTS   {
		    authSDGUserVrfg,
		    authSDGUserIpAddr,
		    authSDGUserTimeUsed,
		    authSDGUserTerminateCause
    }
    STATUS     current
    DESCRIPTION
            "The user offline trap."
    ::= { fsWebAuthMIBTraps 3 }

fsWebAuthWlanMgmt NOTIFICATION-TYPE
    OBJECTS   {
          fsWebAuthApMac,
          fsWebAuthApIp,
          fsWebAuthStaMac,
          fsWebAuthStaIp,
          fsWebAuthStaIpv6,
          fsWebAuthStaOperType,
          fsWebAuthStaApRadioId,
          fsWebAuthStaApRadioType,
          fsWebAuthStaVlanId,
          fsWebAuthStaWlanId,
          fsWebAuthOperTime,
          fsWebAuthStaAssoAuthMode,
          fsWebAuthStaNetAuthMode,
          fsWebAuthStaRssi,
          fsWebAuthStaSsid,
          fsWebAuthStaLinkRate,
          fsWebAuthStaCurChannel,
          fsWebAuthStaUsername,
          fsWebAuthStaTerminalType,
          fsWebAuthStaTerminateCause,
          fsWebAuthStaReplyMessage,
          fsWebAuthStaTerminalId
    }
    STATUS     current
    DESCRIPTION
            "Wlan Web-auth user mgmt trap sent when sta login or logout."
    ::= { fsWebAuthMIBTraps 4 }

fsWebAuthUserOper NOTIFICATION-TYPE
    OBJECTS    {
                fsWebAuthStaOperType,
                fsWebAuthType,
                fsWebAuthStaUsername,
                fsWebAuthStaIp,
                fsWebAuthStaMac,
                fsWebAuthStaVlanId,
                fsWebAuthPortIndex,
                fsWebAuthStaTerminateCause
	}
    STATUS     current
    DESCRIPTION
            "Web-auth user mgmt trap sent when user login, logout or authentication failed."
    ::= { fsWebAuthMIBTraps 5 }

fsWebAuthRedirectInfo NOTIFICATION-TYPE
    OBJECTS    {
                fsWebAuthTlvNum,
                fsWebAuthTlv
    }
    STATUS     current
    DESCRIPTION
              "Web-auth user first redirect info."
    ::= { fsWebAuthMIBTraps 6 }

-- compliance statements

fsWebAuthMIBConformance OBJECT IDENTIFIER ::= { fsWebAuthMIB 3 }
fsWebAuthMIBCompliances OBJECT IDENTIFIER ::= { fsWebAuthMIBConformance 1 }
fsWebAuthMIBGroups      OBJECT IDENTIFIER ::= { fsWebAuthMIBConformance 2 }

fsWebAuthMIBCompliance MODULE-COMPLIANCE
    STATUS  current
    DESCRIPTION
            "The compliance statement for entities which implement
            the My WebAuth MIB"
    MODULE  -- this module
            MANDATORY-GROUPS { fsWebAuthMIBGroup, fsWebAuthTrapGroup
             }

    ::= { fsWebAuthMIBCompliances 1 }

-- units of conformance

fsWebAuthMIBGroup OBJECT-GROUP
    OBJECTS {
         authUserIpAddr,
         authUserOnlineFlag,
         authUserTimeLimit,
         authUserTimeUsed,
         authUserStatus,
         authUserRoleName,
         authUserSecZoneName,
         authUserSecZonePermissionType,
         authUserSecZonePermissionList,
         authUserOtherPermissionType,
         authUserTerminateCause,
         authUserExtAddrType,
         authUserExtAddr,
         authUserExtMac,
         authUserExtIfIndex,
         authUserExtVlanId,
         authUserExtOnlineFlag,
         authUserExtTimeLimit,
         authUserExtTimeUsed,
         authUserExtErrCause,
         authUserExtStatus,
         fsWebAuthWhiteListAddress,
         fsWebAuthWhiteListNetMask,
         fsWebAuthWhiteListPort1,
         fsWebAuthWhiteListPort2,
         fsWebAuthWhiteListPort3,
         fsWebAuthWhiteListPort4,
         fsWebAuthWhiteListPort5,
         fsWebAuthWhiteListPort6,
         fsWebAuthWhiteListPort7,
         fsWebAuthWhiteListPort8,
         fsWebAuthWhiteListBindArpFlag,
         fsWebAuthWhiteListStatus,
         authSDGUserVrfg,
         authSDGUserIpAddr,
         authSDGUserOnlineFlag,
         authSDGUserTimeLimit,
         authSDGUserTimeUsed,
         authSDGUserVrf,
         authSDGUserRoleName,
         authSDGUserSecZoneName,
         authSDGUserSecZonePermissionType,
         authSDGUserSecZonePermissionList,
         authSDGUserOtherPermissionType,
         authSDGUserTerminateCause,
         authSDGUserStatus,
         fsWebAuthDirectSiteAddress,
         fsWebAuthDirectSiteNetMask,
         fsWebAuthDirectSiteStatus,
         fsWebAuthDirectSiteBindArpFlag,
         fsWebAuthDirectHostAddress,
         fsWebAuthDirectHostNetMask,
         fsWebAuthDirectHostPort1,
         fsWebAuthDirectHostPort2,
         fsWebAuthDirectHostPort3,
         fsWebAuthDirectHostPort4,
         fsWebAuthDirectHostPort5,
         fsWebAuthDirectHostPort6,
         fsWebAuthDirectHostPort7,
         fsWebAuthDirectHostPort8,
         fsWebAuthDirectHostBindArpFlag,
         fsWebAuthDirectHostStatus,
         fsWebAuthDirectHostPortIfx,
		 fsWebAuthFreeAcctIpAddress,
         fsWebAuthFreeAcctIpNetMask,
         fsWebAuthFreeAcctIpStatus,
		 fsWebAuthFreeAcctUrl,
         fsWebAuthFreeAcctUrlStatus,
		 fsWebAuthOfflineDetectime,
         fsWebAuthOfflineDetectStatus,
         fsWebAuthCurrentOnlineUser,
         fsWebAuthCurrentUser,
         fsWebAuthMaximumOnlineUser
         }
    STATUS  current
    DESCRIPTION
            "A collection of objects providing authGateway management and
            opertion to a FS agent."
    ::= { fsWebAuthMIBGroups 1 }

fsWebAuthTrapGroup NOTIFICATION-GROUP
    NOTIFICATIONS {
        fsWebAuthUserLeave,
        fsWebAuthUserExtLeave,
        fsWebAuthSDGUserLeave
    }
    STATUS  current
    DESCRIPTION
            "A collection of traps providing authGateway management and
            opertion to a FS agent."
    ::= { fsWebAuthMIBGroups 2 }

END
