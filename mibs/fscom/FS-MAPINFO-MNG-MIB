-- *****************************************************************
-- FS-MAPINFO-MNG-MIB.mib:  FS MAPINFO MNG MIB file
--
-- March 2002, Wuzg
--
-- Copyright (c) 2002 by FS.COM Inc..
-- All rights reserved.
--
-- *****************************************************************
--

FS-MAPINFO-MNG-MIB DEFINITIONS ::= BEGIN

IMPORTS
        MODULE-IDENTITY,
        OBJECT-TYPE,
        Counter32,
        Counter64,
        Unsigned32,
        Integer32,
        IpAddress
                FROM SNMPv2-SMI
        InetAddressType,
        InetAddress
                FROM INET-ADDRESS-MIB
        Counter
                FROM RFC1155-SMI
        TruthValue,
        DisplayString,
        RowStatus,
        MacAddress
                FROM SNMPv2-TC
        MODULE-COMPLIANCE,
        OBJECT-GROUP
                FROM SNMPv2-CONF
        ConfigStatus,
        IfIndex
                FROM FS-TC
        EnabledStatus
                FROM P-BRIDGE-MIB
        radiusAuthServerAddress,
        radiusAuthClientServerPortNumber
            FROM RADIUS-AUTH-CLIENT-MIB
        radiusAccServerAddress,
        radiusAccClientServerPortNumber
            FROM RADIUS-ACC-CLIENT-MIB
        fsMgmt
                FROM FS-SMI;

fsMapinfoMngMIB MODULE-IDENTITY
        LAST-UPDATED "200203200000Z"
        ORGANIZATION "FS.COM Inc.."
        CONTACT-INFO
                "
                Tel: 400-865-2852

                E-mail: https://www.fs.com/live_chat_service_mail.html"
        DESCRIPTION
                "This module defines fs Mapinf Mng mibs."
        REVISION      "201607032000Z"
        DESCRIPTION
                "Initial version of this MIB module."
        ::= { fsMgmt 150}

fsMapinfoMngMIBObjects OBJECT IDENTIFIER ::= { fsMapinfoMngMIB 1 }

fsUserObjects OBJECT IDENTIFIER ::= { fsMapinfoMngMIBObjects 1 }
fsFluxObjects OBJECT IDENTIFIER ::= { fsMapinfoMngMIBObjects 2 }

--
-- fs Micro-Ap User information
--
fsUserTable OBJECT-TYPE
  SYNTAX  SEQUENCE OF FSUserEntry
  MAX-ACCESS  not-accessible
        STATUS  current
        DESCRIPTION
            "The table of User which from Micro-Ap."
        ::= { fsUserObjects 1 }


fsUserEntry OBJECT-TYPE
        SYNTAX  FSUserEntry
        MAX-ACCESS  not-accessible
        STATUS  current
        DESCRIPTION
            "The entry of User who come from Micro-Ap."
        INDEX   { fsUserMacAddress,fsUserVid}
        ::= { fsUserTable 1 }


FSUserEntry ::=
    SEQUENCE {
            fsUserMacAddress MacAddress,
            fsUserVid Unsigned32,
            fsUserDevMacAddress MacAddress,
            fsUserDevSlot Unsigned32,
            fsUserMapPort Unsigned32,
            fsUserRowStatus ConfigStatus
            }

fsUserMacAddress OBJECT-TYPE
        SYNTAX       MacAddress
        MAX-ACCESS   read-only
        STATUS       current
        DESCRIPTION
            "The MacAddress of user who come from Micro-AP."
        ::= { fsUserEntry 1 }

fsUserVid OBJECT-TYPE
        SYNTAX       Unsigned32
        MAX-ACCESS   read-only
        STATUS       current
        DESCRIPTION
            "The VID of user who come from Micro-AP."
        ::= { fsUserEntry 2 }

fsUserDevMacAddress OBJECT-TYPE
        SYNTAX       MacAddress
        MAX-ACCESS   read-only
        STATUS       current
        DESCRIPTION
            "The Mac Address of Ap-dev which Micro-AP link to."
        ::= { fsUserEntry 3 }

fsUserDevSlot OBJECT-TYPE
        SYNTAX       Unsigned32
        MAX-ACCESS   read-only
        STATUS       current
        DESCRIPTION
            "The Slot of Ap-dev which Micro-AP link to."
        ::= { fsUserEntry 4 }

fsUserMapPort OBJECT-TYPE
        SYNTAX       Unsigned32
        MAX-ACCESS   read-only
        STATUS       current
        DESCRIPTION
            "The Port of Micro-AP which the User link to."
        ::= { fsUserEntry 5 }

fsUserRowStatus OBJECT-TYPE
        SYNTAX  ConfigStatus
        MAX-ACCESS  read-write
        STATUS  current
        DESCRIPTION
            "The object indicate creat or delete of fsUserTable."
         ::= { fsUserEntry 6 }

--
-- fs Micro-Ap flux information
--
fsFluxTable OBJECT-TYPE
  SYNTAX  SEQUENCE OF FSFluxEntry
  MAX-ACCESS  not-accessible
        STATUS  current
        DESCRIPTION
            "The table of Flux of Micri-AP."
        ::= { fsFluxObjects 1 }


fsFluxEntry OBJECT-TYPE
        SYNTAX  FSFluxEntry
        MAX-ACCESS  not-accessible
        STATUS  current
        DESCRIPTION
            "The entry of Flux of Micri-AP."
        INDEX   { fsFluxDevMacAddress, fsFluxDevSlot, fsFluxMapPort}
        ::= { fsFluxTable 1 }


FSFluxEntry ::=
    SEQUENCE {
            fsFluxDevMacAddress MacAddress,
            fsFluxDevSlot Unsigned32,
            fsFluxMapPort Unsigned32,
            fsFluxMapPortState INTEGER(0..1),
            fsFluxInputBps Counter64,
            fsFluxOutputBps Counter64,
            fsFluxInputPackets Counter64,
            fsFluxOutputPackets Counter64,
            fsFluxInputBytes Counter64,
            fsFluxOutputBytes Counter64,
            fsFluxRowStatus ConfigStatus
            }

fsFluxDevMacAddress OBJECT-TYPE
        SYNTAX       MacAddress
        MAX-ACCESS   read-only
        STATUS       current
        DESCRIPTION
            "The Mac Address of Ap-dev which Micro-AP link to."
        ::= { fsFluxEntry 1 }

fsFluxDevSlot OBJECT-TYPE
        SYNTAX       Unsigned32
        MAX-ACCESS   read-only
        STATUS       current
        DESCRIPTION
            "The Slot of Ap-dev which Micro-AP link to."
        ::= { fsFluxEntry 2 }

fsFluxMapPort OBJECT-TYPE
        SYNTAX       Unsigned32
        MAX-ACCESS   read-only
        STATUS       current
        DESCRIPTION
            "The Port of Micro-AP."
        ::= { fsFluxEntry 3 }

fsFluxMapPortState OBJECT-TYPE
        SYNTAX       INTEGER(0..1)
        MAX-ACCESS   read-only
        STATUS       current
        DESCRIPTION
            "The state of port which belong to Micro-AP."
        ::= { fsFluxEntry 4 }

fsFluxInputBps OBJECT-TYPE
        SYNTAX       Counter64
        MAX-ACCESS   read-only
        STATUS       current
        DESCRIPTION
            "The value of input, unit: bps."
        ::= { fsFluxEntry 5 }

fsFluxOutputBps OBJECT-TYPE
        SYNTAX       Counter64
        MAX-ACCESS   read-only
        STATUS       current
        DESCRIPTION
            "The value of output, unit: bps."
        ::= { fsFluxEntry 6 }

fsFluxInputPackets OBJECT-TYPE
        SYNTAX       Counter64
        MAX-ACCESS   read-only
        STATUS       current
        DESCRIPTION
            "The value of input, unit: packet."
        ::= { fsFluxEntry 7 }

fsFluxOutputPackets OBJECT-TYPE
        SYNTAX       Counter64
        MAX-ACCESS   read-only
        STATUS       current
        DESCRIPTION
            "The value of output, unit: packet."
        ::= { fsFluxEntry 8 }

fsFluxInputBytes OBJECT-TYPE
        SYNTAX       Counter64
        MAX-ACCESS   read-only
        STATUS       current
        DESCRIPTION
            "The value of input, unit: bytes."
        ::= { fsFluxEntry 9 }

fsFluxOutputBytes OBJECT-TYPE
        SYNTAX       Counter64
        MAX-ACCESS   read-only
        STATUS       current
        DESCRIPTION
            "The value of output, unit: bytes."
        ::= { fsFluxEntry 10 }

fsFluxRowStatus OBJECT-TYPE
        SYNTAX       ConfigStatus
        MAX-ACCESS   read-write
        STATUS       current
        DESCRIPTION
            "The object indicate creat or delete of fsUserTable."
        ::= { fsFluxEntry 11 }


fsMapinfoMngMIBConformance OBJECT IDENTIFIER ::= { fsMapinfoMngMIB 2 }
fsMapinfoMngMIBCompliances OBJECT IDENTIFIER ::= { fsMapinfoMngMIBConformance 1 }
fsMapinfoMngMIBGroups      OBJECT IDENTIFIER ::= { fsMapinfoMngMIBConformance 2 }

-- compliance statements

fsMapinfoMngMIBCompliance MODULE-COMPLIANCE
        STATUS  current
        DESCRIPTION
                "The compliance statement for entities which implement
                 the FS MAPINFO MNG MIB"
        MODULE  -- this module
                MANDATORY-GROUPS {
                        fsUserMIBGroup,
                        fsFluxMIBGroup
                 }
         ::= { fsMapinfoMngMIBCompliances 1 }

-- units of conformance

fsUserMIBGroup OBJECT-GROUP
        OBJECTS {
            fsUserMacAddress,
            fsUserVid,
            fsUserDevMacAddress,
            fsUserDevSlot,
            fsUserMapPort,
            fsUserRowStatus
        }
        STATUS  current
        DESCRIPTION
                "A collection of objects providing dot1x  authentication managment."
        ::= { fsMapinfoMngMIBGroups 1 }

fsFluxMIBGroup OBJECT-GROUP
        OBJECTS {
            fsFluxDevMacAddress,
            fsFluxDevSlot,
            fsFluxMapPort,
            fsFluxMapPortState,
            fsFluxInputBps,
            fsFluxOutputBps,
            fsFluxInputPackets,
            fsFluxOutputPackets,
            fsFluxInputBytes,
            fsFluxOutputBytes,
            fsFluxRowStatus
        }
        STATUS  current
        DESCRIPTION
                "A collection of objects providing dot1x  authentication managment."
        ::= { fsMapinfoMngMIBGroups 2 }

END
