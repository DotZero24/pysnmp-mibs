-- *****************************************************************
-- FS-AP-MGMT-MIB.mib:  FS AP MGMT MIB file
--
-- July 2013, linwei4
--
-- Copyright (c) 2012 by FS.COM Inc..
-- All rights reserved.
-- *****************************************************************
--
FS-AP-MGMT-MIB DEFINITIONS ::= BEGIN

IMPORTS
        OBJECT-TYPE,
        Integer32,
        MODULE-IDENTITY
                FROM SNMPv2-SMI
        fsMgmt
                FROM FS-SMI;

fsApMgmtMIB MODULE-IDENTITY
    LAST-UPDATED "201307230000Z"
    ORGANIZATION "FS.COM Inc.."
    CONTACT-INFO
        "
    Tel: 400-865-2852

    E-mail: https://www.fs.com/live_chat_service_mail.html"
    DESCRIPTION
        "This module defines ac management mibs."
    REVISION      "201307230000Z"
    DESCRIPTION
        "Initial version of this MIB module."
    ::= { fsMgmt 124}

--***************** define the AP root nodes *****************
fsApMgmtMIBObjects OBJECT IDENTIFIER      ::= { fsApMgmtMIB 1 }
fsApMgmt     OBJECT IDENTIFIER ::= { fsApMgmtMIBObjects 1 }

--********************************************************************
--                                                                  **
--                  AP nodes                                        **
--                                                                  **
--********************************************************************

-- 1.ap_mode, the ap's mode
fsApMode OBJECT-TYPE
    SYNTAX  INTEGER (0..1)
    MAX-ACCESS  read-only
    STATUS  current
    DESCRIPTION
            "The ap mode:
            0--fit
            1--fat"
    ::= { fsApMgmt 1 }

END
