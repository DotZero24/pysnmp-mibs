--
-- *******************************************************************
-- FS-IPSEC2-MIB.mib
-- May 2010, humin
--
-- Copyright (c) 2009 by FS.COM Inc..
-- All rights reserved.
-- *******************************************************************
--

	FS-IPSEC2-MIB DEFINITIONS ::= BEGIN

		IMPORTS
			OBJECT-GROUP, MODULE-COMPLIANCE, NOTIFICATION-GROUP
				FROM SNMPv2-CONF
			IpAddress, Integer32, Unsigned32, Gauge32, Counter32,
			Counter64, OBJECT-TYPE, NOTIFICATION-TYPE
				FROM SNMPv2-SMI
			DisplayString, TimeStamp, TEXTUAL-CONVENTION
				FROM SNMPv2-TC
			fsMgmt
                                 FROM FS-SMI;

        fsIPSec2MibModule MODULE-IDENTITY
			LAST-UPDATED "201112191637Z"		-- December 19, 2011 at 16:37 GMT
			ORGANIZATION
				"Organization."
			CONTACT-INFO
				"Contact-info."
			DESCRIPTION
				"Description."
			::= { fsMgmt 108 }


--
-- Textual conventions
--

		FSIPSecNegoType ::= TEXTUAL-CONVENTION
			STATUS current
			DESCRIPTION
				"The type of key used by an IPSec Phase-2 Tunnel. invalidType(2147483647)
				is defined as invalid value."
			SYNTAX INTEGER
				{
				ike(1),
				manual(2),
				invalidType(2147483647)
				}

		FSEncapMode ::= TEXTUAL-CONVENTION
			STATUS current
			DESCRIPTION
				"The encapsulation mode used by an IPSec Phase-2 Tunnel."
			SYNTAX INTEGER
				{
				tunnel(1),
				transport(2),
				invalidMode(2147483647)
				}

		FSEncryptAlgo ::= TEXTUAL-CONVENTION
			STATUS current
			DESCRIPTION
				"The encryption algorithm used in the IKE and IPSec negotiations.
				invalidAlg(2147483647) is defined as invalid value."
			SYNTAX INTEGER
				{
				none(0),
				desCbc(2),
				threedesCbc(3),
				aesCbc(12),
				sm1Cbc(128),
				invalidAlg(2147483647)
				}

		FSAuthAlgo ::= TEXTUAL-CONVENTION
			STATUS current
			DESCRIPTION
				"The authentication algorithm used in the IKE negotiations.
				invalidAlg(2147483647) is defined as invalid value."
			SYNTAX INTEGER
				{
				none(0),
				md5(2),
				sha(3),
				invalidAlg(2147483647)
				}

		FSDiffHellmanGrp ::= TEXTUAL-CONVENTION
			STATUS current
			DESCRIPTION
				"The Diffie Hellman Group used in the IKE and IPSec negotiations.
				invalidAlg(2147483647) is defined as invalid value."
			SYNTAX INTEGER
				{
				modp768(1),
				modp1024(2),
				invalidMode(2147483647)
				}

		FSIPSecTunnelState ::= TEXTUAL-CONVENTION
			STATUS current
			DESCRIPTION
				"The state of IPSec tunnel."
			SYNTAX INTEGER
				{
				establishing(1),
				active(2),
				expiring(3)
				}

		FSSaProtocol ::= TEXTUAL-CONVENTION
			STATUS current
			DESCRIPTION
				"The protocol of security association."
			SYNTAX INTEGER
				{
				reserved(0),
				isakmp(1),
				ah(2),
				esp(3)
				}

		FSTrafficType ::= TEXTUAL-CONVENTION
			STATUS current
			DESCRIPTION
				"The type of the data flow."
			SYNTAX INTEGER
				{
				ipv4Addr(1),
				ipv4AddrSubnet(2),
				ipv6Addr(3),
				ipv6AddrSubnet(4),
				ipv4AddrRange(5),
				ipv6AddrRange(6)
				}

--  1.3.6.1.4.1.52642.1.1.10.2.108.1
-- December 19, 2011 at 16:37 GMT
--
-- Textual conventions
--
		FSIPSec2NegoType ::= TEXTUAL-CONVENTION
			STATUS current
			DESCRIPTION
				"The type of key used by an IPSec Phase-2 Tunnel. invalidType(2147483647)
				is defined as invalid value."
			SYNTAX INTEGER
				{
				ike(1),
				manual(2),
				invalidType(2147483647)
				}

		FSIPSec2TunnelState ::= TEXTUAL-CONVENTION
			STATUS current
			DESCRIPTION
				"The state of IPSec tunnel."
			SYNTAX INTEGER
				{
				establishing(1),
				active(2),
				expiring(3)
				}


--
-- Node definitions
--

		-- 1.3.6.1.4.1.52642.1.1.10.2.108.1
		fsIPSec2Objects OBJECT IDENTIFIER ::= { fsIPSec2MibModule 1 }


		-- 1.3.6.1.4.1.52642.1.1.10.2.108.1.1
		fsIPSec2TunnelTable OBJECT-TYPE
			SYNTAX SEQUENCE OF FSIPSec2TunnelEntry
			MAX-ACCESS not-accessible
			STATUS current
			DESCRIPTION
				"The IPSec Phase-2 Tunnel Table. There is one
				entry in this table for each active IPSec Phase-2 Tunnel."
			::= { fsIPSec2Objects 1 }


		-- 1.3.6.1.4.1.52642.1.1.10.2.108.1.1.1
		fsIPSec2TunnelEntry OBJECT-TYPE
			SYNTAX FSIPSec2TunnelEntry
			MAX-ACCESS not-accessible
			STATUS current
			DESCRIPTION
				"Information about FSIPSec2TunnelTable."
			INDEX { fsIPSec2TunIfIndex, fsIPSec2TunRemoteAddr, fsIPSec2TrafficLocalType, fsIPSec2TrafficLocalProtocol, fsIPSec2TrafficLocalAddr1,
				fsIPSec2TrafficLocalAddr2, fsIPSec2TrafficLocalPort, fsIPSec2TrafficRemoteAddr1, fsIPSec2TrafficRemoteAddr2, fsIPSec2TrafficRemotePort
				 }
			::= { fsIPSec2TunnelTable 1 }


		FSIPSec2TunnelEntry ::=
			SEQUENCE {
				fsIPSec2TunIfIndex
					Integer32,
				fsIPSec2TunnelTrafficIndex
					Integer32,
				fsIPSec2TunIndex
					Integer32,
				fsIPSec2TunIKETunnelIndex
					Integer32,
				fsIPSec2TunnelAhOutSaIndex
					Integer32,
				fsIPSec2TunnelAhInSaIndex
					Integer32,
				fsIPSec2TunnelEspOutSaIndex
					Integer32,
				fsIPSec2TunnelEspInSaIndex
					Integer32,
				fsIPSec2TunLocalAddr
					IpAddress,
				fsIPSec2TunRemoteAddr
					IpAddress,
				fsIPSec2TunLocalHostname
					DisplayString,
				fsIPSec2TunRemoteHostname
					DisplayString,
				fsIPSec2TunKeyType
					FSIPSec2NegoType,
				fsIPSec2TunEncapMode
					FSEncapMode,
				fsIPSec2TunInitiator
					INTEGER,
				fsIPSec2TunLifeSize
					Integer32,
				fsIPSec2TunLifeTime
					Integer32,
				fsIPSec2TunRemainTime
					Integer32,
				fsIPSec2TunActiveTime
					Integer32,
				fsIPSec2TunCreateTime
					TimeStamp,
				fsIPSec2TunRemainSize
					Integer32,
				fsIPSec2TunTotalRefreshes
					Counter32,
				fsIPSec2TunCurrentSaInstances
					Gauge32,
				fsIPSec2TunInSaEncryptAlgo
					FSEncryptAlgo,
				fsIPSec2TunInSaAhAuthAlgo
					FSAuthAlgo,
				fsIPSec2TunInSaEspAuthAlgo
					FSAuthAlgo,
				fsIPSec2TunDiffHellmanGrp
					FSDiffHellmanGrp,
				fsIPSec2TunOutSaEncryptAlgo
					FSEncryptAlgo,
				fsIPSec2TunOutSaAhAuthAlgo
					FSAuthAlgo,
				fsIPSec2TunOutSaEspAuthAlgo
					FSAuthAlgo,
				fsIPSec2TunMapName
					DisplayString,
				fsIPSec2TunSeqNum
					Integer32,
				fsIPSec2TunStatus
					FSIPSec2TunnelState
			 }

		-- 1.3.6.1.4.1.52642.1.1.10.2.108.1.1.1.1
		fsIPSec2TunIfIndex OBJECT-TYPE
			SYNTAX Integer32 (1..2147483647)
			MAX-ACCESS read-only
			STATUS current
			DESCRIPTION
				"The interface index( the ifIndex of ifTable )."
			::= { fsIPSec2TunnelEntry 1 }


		-- 1.3.6.1.4.1.52642.1.1.10.2.108.1.1.1.2
		fsIPSec2TunnelTrafficIndex OBJECT-TYPE
			SYNTAX Integer32
			MAX-ACCESS read-only
			STATUS current
			DESCRIPTION
				"Description."
			::= { fsIPSec2TunnelEntry 2 }


		-- 1.3.6.1.4.1.52642.1.1.10.2.108.1.1.1.3
		fsIPSec2TunIndex OBJECT-TYPE
			SYNTAX Integer32 (1..2147483647)
			MAX-ACCESS read-only
			STATUS current
			DESCRIPTION
				"The index of IPSec Phase-2 Tunnel Table. The value of
				the index is a number which begins at one and is
				incremented with each tunnel that is created. The
				value of this object will wrap at 2,147,483,647."
			::= { fsIPSec2TunnelEntry 3 }


		-- 1.3.6.1.4.1.52642.1.1.10.2.108.1.1.1.5
		fsIPSec2TunIKETunnelIndex OBJECT-TYPE
			SYNTAX Integer32 (1..2147483647)
			MAX-ACCESS read-only
			STATUS current
			DESCRIPTION
				"The index of the associated IPSec Phase-1 IKE Tunnel
				(IKETunIndex in the IKETunnelTable). 2147483647 is defined as
				invalid value. "
			::= { fsIPSec2TunnelEntry 5 }


		-- 1.3.6.1.4.1.52642.1.1.10.2.108.1.1.1.6
		fsIPSec2TunnelAhOutSaIndex OBJECT-TYPE
			SYNTAX Integer32
			MAX-ACCESS read-only
			STATUS current
			DESCRIPTION
				"Description."
			::= { fsIPSec2TunnelEntry 6 }


		-- 1.3.6.1.4.1.52642.1.1.10.2.108.1.1.1.7
		fsIPSec2TunnelAhInSaIndex OBJECT-TYPE
			SYNTAX Integer32 (1..2147483647)
			MAX-ACCESS read-only
			STATUS current
			DESCRIPTION
				"The index of the associated IPSec Phase-1 IKE Tunnel
				(IKETunIndex in the IKETunnelTable). 2147483647 is defined as
				invalid value. "
			::= { fsIPSec2TunnelEntry 7 }


		-- 1.3.6.1.4.1.52642.1.1.10.2.108.1.1.1.8
		fsIPSec2TunnelEspOutSaIndex OBJECT-TYPE
			SYNTAX Integer32 (1..2147483647)
			MAX-ACCESS read-only
			STATUS current
			DESCRIPTION
				"The index of the associated IPSec Phase-1 IKE Tunnel
				(IKETunIndex in the IKETunnelTable). 2147483647 is defined as
				invalid value. "
			::= { fsIPSec2TunnelEntry 8 }


		-- 1.3.6.1.4.1.52642.1.1.10.2.108.1.1.1.9
		fsIPSec2TunnelEspInSaIndex OBJECT-TYPE
			SYNTAX Integer32
			MAX-ACCESS read-only
			STATUS current
			DESCRIPTION
				"Description."
			::= { fsIPSec2TunnelEntry 9 }


		-- 1.3.6.1.4.1.52642.1.1.10.2.108.1.1.1.10
		fsIPSec2TunLocalAddr OBJECT-TYPE
			SYNTAX IpAddress
			MAX-ACCESS read-only
			STATUS current
			DESCRIPTION
				"The IP address of the local peer for the IPSec Phase-2
				Tunnel. 0.0.0.0 is defined as invalid value."
			::= { fsIPSec2TunnelEntry 10 }


		-- 1.3.6.1.4.1.52642.1.1.10.2.108.1.1.1.11
		fsIPSec2TunRemoteAddr OBJECT-TYPE
			SYNTAX IpAddress
			MAX-ACCESS read-only
			STATUS current
			DESCRIPTION
				"The IP address of the remote peer for the IPSec Phase-2
				Tunnel. 0.0.0.0 is defined as invalid value."
			::= { fsIPSec2TunnelEntry 11 }


		-- 1.3.6.1.4.1.52642.1.1.10.2.108.1.1.1.12
		fsIPSec2TunLocalHostname OBJECT-TYPE
			SYNTAX DisplayString
			MAX-ACCESS read-only
			STATUS current
			DESCRIPTION
				"The Hostname of the local peer for the IPSec Phase-2
				Tunnel."
			::= { fsIPSec2TunnelEntry 12 }


		-- 1.3.6.1.4.1.52642.1.1.10.2.108.1.1.1.13
		fsIPSec2TunRemoteHostname OBJECT-TYPE
			SYNTAX DisplayString
			MAX-ACCESS read-only
			STATUS current
			DESCRIPTION
				"The Hostname of the remote peer for the IPSec Phase-2
				Tunnel. "
			::= { fsIPSec2TunnelEntry 13 }


		-- 1.3.6.1.4.1.52642.1.1.10.2.108.1.1.1.14
		fsIPSec2TunKeyType OBJECT-TYPE
			SYNTAX FSIPSec2NegoType
			MAX-ACCESS read-only
			STATUS current
			DESCRIPTION
				"The key negotiate mode used by the IPSec Phase-2 Tunnel."
			::= { fsIPSec2TunnelEntry 14 }


		-- 1.3.6.1.4.1.52642.1.1.10.2.108.1.1.1.15
		fsIPSec2TunEncapMode OBJECT-TYPE
			SYNTAX FSEncapMode
			MAX-ACCESS read-only
			STATUS current
			DESCRIPTION
				"The encapsulation mode used by the IPSec Phase-2 Tunnel."
			::= { fsIPSec2TunnelEntry 15 }


		-- 1.3.6.1.4.1.52642.1.1.10.2.108.1.1.1.16
		fsIPSec2TunInitiator OBJECT-TYPE
			SYNTAX INTEGER
				{
				local(1),
				remote(2),
				none(2147483647)
				}
			MAX-ACCESS read-only
			STATUS current
			DESCRIPTION
				"The initiator of this IPSec tunnel. Value none is used for manual
				IPsec tunnel, for there is no initiator or responder in this method."
			::= { fsIPSec2TunnelEntry 16 }


		-- 1.3.6.1.4.1.52642.1.1.10.2.108.1.1.1.17
		fsIPSec2TunLifeSize OBJECT-TYPE
			SYNTAX Integer32 (1..2147483647)
			MAX-ACCESS read-only
			STATUS current
			DESCRIPTION
				"The negotiated LifeSize of the IPSec Phase-2 Tunnel in kilobytes.
				2147483647 is defined as invalid value."
			::= { fsIPSec2TunnelEntry 17 }


		-- 1.3.6.1.4.1.52642.1.1.10.2.108.1.1.1.18
		fsIPSec2TunLifeTime OBJECT-TYPE
			SYNTAX Integer32 (1..2147483647)
			MAX-ACCESS read-only
			STATUS current
			DESCRIPTION
				"The negotiated LifeTime of the IPSec Phase-2 Tunnel in seconds.
				2147483647 is defined as invalid value."
			::= { fsIPSec2TunnelEntry 18 }


		-- 1.3.6.1.4.1.52642.1.1.10.2.108.1.1.1.19
		fsIPSec2TunRemainTime OBJECT-TYPE
			SYNTAX Integer32 (0..2147483647)
			MAX-ACCESS read-only
			STATUS current
			DESCRIPTION
				"The remain time of SA in seconds. 2147483647 is defined as invalid
				value."
			::= { fsIPSec2TunnelEntry 19 }


		-- 1.3.6.1.4.1.52642.1.1.10.2.108.1.1.1.20
		fsIPSec2TunActiveTime OBJECT-TYPE
			SYNTAX Integer32 (0..2147483647)
			MAX-ACCESS read-only
			STATUS current
			DESCRIPTION
				"The duration the IPSec Phase-2 Tunnel has been active in
				hundredths of seconds. 2147483647 is defined as invalid value."
			::= { fsIPSec2TunnelEntry 20 }


		-- 1.3.6.1.4.1.52642.1.1.10.2.108.1.1.1.21
		fsIPSec2TunCreateTime OBJECT-TYPE
			SYNTAX TimeStamp
			MAX-ACCESS read-only
			STATUS current
			DESCRIPTION
				"The Time Stamp when the IPSec Phase-2 Tunnel created."
			::= { fsIPSec2TunnelEntry 21 }


		-- 1.3.6.1.4.1.52642.1.1.10.2.108.1.1.1.23
		fsIPSec2TunRemainSize OBJECT-TYPE
			SYNTAX Integer32 (0..2147483647)
			MAX-ACCESS read-only
			STATUS current
			DESCRIPTION
				"The remain LifeSize of SA in kilobytes. 2147483647 is defined as
				invalid value."
			::= { fsIPSec2TunnelEntry 23 }


		-- 1.3.6.1.4.1.52642.1.1.10.2.108.1.1.1.24
		fsIPSec2TunTotalRefreshes OBJECT-TYPE
			SYNTAX Counter32
			MAX-ACCESS read-only
			STATUS current
			DESCRIPTION
				"The total number of security association refreshing performed."
			::= { fsIPSec2TunnelEntry 24 }


		-- 1.3.6.1.4.1.52642.1.1.10.2.108.1.1.1.25
		fsIPSec2TunCurrentSaInstances OBJECT-TYPE
			SYNTAX Gauge32
			MAX-ACCESS read-only
			STATUS current
			DESCRIPTION
				"The number of security associations which are currently active
				or expiring."
			::= { fsIPSec2TunnelEntry 25 }


		-- 1.3.6.1.4.1.52642.1.1.10.2.108.1.1.1.26
		fsIPSec2TunInSaEncryptAlgo OBJECT-TYPE
			SYNTAX FSEncryptAlgo
			MAX-ACCESS read-only
			STATUS current
			DESCRIPTION
				"The encryption algorithm used by the inbound security association
				of the IPSec Phase-2 Tunnel."
			::= { fsIPSec2TunnelEntry 26 }


		-- 1.3.6.1.4.1.52642.1.1.10.2.108.1.1.1.27
		fsIPSec2TunInSaAhAuthAlgo OBJECT-TYPE
			SYNTAX FSAuthAlgo
			MAX-ACCESS read-only
			STATUS current
			DESCRIPTION
				"The authentication algorithm used by the inbound authentication
				header (AH) security association of the IPSec Phase-2 Tunnel."
			::= { fsIPSec2TunnelEntry 27 }


		-- 1.3.6.1.4.1.52642.1.1.10.2.108.1.1.1.28
		fsIPSec2TunInSaEspAuthAlgo OBJECT-TYPE
			SYNTAX FSAuthAlgo
			MAX-ACCESS read-only
			STATUS current
			DESCRIPTION
				"The authentication algorithm used by the inbound encapsulation
				security protocol(ESP) security association of the IPSec
				Phase-2 Tunnel."
			::= { fsIPSec2TunnelEntry 28 }


		-- 1.3.6.1.4.1.52642.1.1.10.2.108.1.1.1.29
		fsIPSec2TunDiffHellmanGrp OBJECT-TYPE
			SYNTAX FSDiffHellmanGrp
			MAX-ACCESS read-only
			STATUS current
			DESCRIPTION
				"The Diffie Hellman Group used by the security association of the
				IPSec Phase-2 Tunnel."
			::= { fsIPSec2TunnelEntry 29 }


		-- 1.3.6.1.4.1.52642.1.1.10.2.108.1.1.1.30
		fsIPSec2TunOutSaEncryptAlgo OBJECT-TYPE
			SYNTAX FSEncryptAlgo
			MAX-ACCESS read-only
			STATUS current
			DESCRIPTION
				"The encryption algorithm used by the outbound security
				association of the IPSec Phase-2 Tunnel."
			::= { fsIPSec2TunnelEntry 30 }


		-- 1.3.6.1.4.1.52642.1.1.10.2.108.1.1.1.31
		fsIPSec2TunOutSaAhAuthAlgo OBJECT-TYPE
			SYNTAX FSAuthAlgo
			MAX-ACCESS read-only
			STATUS current
			DESCRIPTION
				"The authentication algorithm used by the outbound
				authentication header (AH) security association of
				the IPSec Phase-2 Tunnel."
			::= { fsIPSec2TunnelEntry 31 }


		-- 1.3.6.1.4.1.52642.1.1.10.2.108.1.1.1.32
		fsIPSec2TunOutSaEspAuthAlgo OBJECT-TYPE
			SYNTAX FSAuthAlgo
			MAX-ACCESS read-only
			STATUS current
			DESCRIPTION
				"The authentication algorithm used by the outbound encapsulation
				security protocol(ESP) security association of the IPSec
				Phase-2 Tunnel."
			::= { fsIPSec2TunnelEntry 32 }


		-- 1.3.6.1.4.1.52642.1.1.10.2.108.1.1.1.33
		fsIPSec2TunMapName OBJECT-TYPE
			SYNTAX DisplayString
			MAX-ACCESS read-only
			STATUS current
			DESCRIPTION
				"The Map name used by this IPSec tunnel."
			::= { fsIPSec2TunnelEntry 33 }


		-- 1.3.6.1.4.1.52642.1.1.10.2.108.1.1.1.34
		fsIPSec2TunSeqNum OBJECT-TYPE
			SYNTAX Integer32 (1..2147483647)
			MAX-ACCESS read-only
			STATUS current
			DESCRIPTION
				"The sequence number of policy used by this IPSec tunnel."
			::= { fsIPSec2TunnelEntry 34 }


		-- 1.3.6.1.4.1.52642.1.1.10.2.108.1.1.1.35
		fsIPSec2TunStatus OBJECT-TYPE
			SYNTAX FSIPSec2TunnelState
			MAX-ACCESS read-write
			STATUS current
			DESCRIPTION
				"The status of the IPSec Tunnel."
			::= { fsIPSec2TunnelEntry 35 }


		-- 1.3.6.1.4.1.52642.1.1.10.2.108.1.2
		fsIPSec2TunnelStatTable OBJECT-TYPE
			SYNTAX SEQUENCE OF FSIPSec2TunnelStatEntry
			MAX-ACCESS not-accessible
			STATUS current
			DESCRIPTION
				"The IPSec Phase-2 Tunnel Statistics Table. "
			::= { fsIPSec2Objects 2 }


		-- 1.3.6.1.4.1.52642.1.1.10.2.108.1.2.1
		fsIPSec2TunnelStatEntry OBJECT-TYPE
			SYNTAX FSIPSec2TunnelStatEntry
			MAX-ACCESS not-accessible
			STATUS current
			DESCRIPTION
				"Information about FSIPSec2TunnelStatTable."
			INDEX { fsIPSec2TunIndex }
			::= { fsIPSec2TunnelStatTable 1 }


		FSIPSec2TunnelStatEntry ::=
			SEQUENCE {
				fsIPSec2TunInOctets
					Counter64,
				fsIPSec2TunInDecompOctets
					Counter64,
				fsIPSec2TunInPkts
					Counter64,
				fsIPSec2TunInSpeed
					Counter64,
				fsIPSec2TunInDropPkts
					Counter64,
				fsIPSec2TunOutOctets
					Counter64,
				fsIPSec2TunOutUncompOctets
					Counter64,
				fsIPSec2TunOutPkts
					Counter64,
				fsIPSec2TunOutSpeed
					Counter64,
				fsIPSec2TunOutDropPkts
					Counter64
			 }

		-- 1.3.6.1.4.1.52642.1.1.10.2.108.1.2.1.1
		fsIPSec2TunInOctets OBJECT-TYPE
			SYNTAX Counter64
			MAX-ACCESS read-only
			STATUS current
			DESCRIPTION
				"The total number of octets received by this IPSec Phase-2 Tunnel.
				This value is accumulated BEFORE determining whether or not the
				packet should be decompressed."
			::= { fsIPSec2TunnelStatEntry 1 }


		-- 1.3.6.1.4.1.52642.1.1.10.2.108.1.2.1.2
		fsIPSec2TunInDecompOctets OBJECT-TYPE
			SYNTAX Counter64
			MAX-ACCESS read-only
			STATUS current
			DESCRIPTION
				"The total number of decompressed octets received by this IPSec
				Phase-2 Tunnel. This value is accumulated AFTER the packet
				is decompressed."
			::= { fsIPSec2TunnelStatEntry 2 }


		-- 1.3.6.1.4.1.52642.1.1.10.2.108.1.2.1.3
		fsIPSec2TunInPkts OBJECT-TYPE
			SYNTAX Counter64
			MAX-ACCESS read-only
			STATUS current
			DESCRIPTION
				"The total number of packets received by this IPSec Phase-2 Tunnel."
			::= { fsIPSec2TunnelStatEntry 3 }


		-- 1.3.6.1.4.1.52642.1.1.10.2.108.1.2.1.4
		fsIPSec2TunInSpeed OBJECT-TYPE
			SYNTAX Counter64
			MAX-ACCESS read-only
			STATUS current
			DESCRIPTION
				"The Speed(bps) of packets received by this IPSec Phase-2 Tunnel."
			::= { fsIPSec2TunnelStatEntry 4 }


		-- 1.3.6.1.4.1.52642.1.1.10.2.108.1.2.1.5
		fsIPSec2TunInDropPkts OBJECT-TYPE
			SYNTAX Counter64
			MAX-ACCESS read-only
			STATUS current
			DESCRIPTION
				"The total number of packets dropped during receiving process
				by this IPSec Phase-2 Tunnel."
			::= { fsIPSec2TunnelStatEntry 5 }


		-- 1.3.6.1.4.1.52642.1.1.10.2.108.1.2.1.6
		fsIPSec2TunOutOctets OBJECT-TYPE
			SYNTAX Counter64
			MAX-ACCESS read-only
			STATUS current
			DESCRIPTION
				"The total number of octets sent by this IPSec Phase-2 Tunnel.
				This value is accumulated AFTER determining whether or not
				the packet should be compressed."
			::= { fsIPSec2TunnelStatEntry 6 }


		-- 1.3.6.1.4.1.52642.1.1.10.2.108.1.2.1.7
		fsIPSec2TunOutUncompOctets OBJECT-TYPE
			SYNTAX Counter64
			MAX-ACCESS read-only
			STATUS current
			DESCRIPTION
				"The total number of uncompressed octets sent by this IPSec Phase-2
				Tunnel.This value is accumulated BEFORE the packet is compressed."
			::= { fsIPSec2TunnelStatEntry 7 }


		-- 1.3.6.1.4.1.52642.1.1.10.2.108.1.2.1.8
		fsIPSec2TunOutPkts OBJECT-TYPE
			SYNTAX Counter64
			MAX-ACCESS read-only
			STATUS current
			DESCRIPTION
				"The total number of packets sent by this IPSec Phase-2 Tunnel."
			::= { fsIPSec2TunnelStatEntry 8 }


		-- 1.3.6.1.4.1.52642.1.1.10.2.108.1.2.1.9
		fsIPSec2TunOutSpeed OBJECT-TYPE
			SYNTAX Counter64
			MAX-ACCESS read-only
			STATUS current
			DESCRIPTION
				"The Speed(bps) of packets sent by this IPSec Phase-2 Tunnel. "
			::= { fsIPSec2TunnelStatEntry 9 }


		-- 1.3.6.1.4.1.52642.1.1.10.2.108.1.2.1.10
		fsIPSec2TunOutDropPkts OBJECT-TYPE
			SYNTAX Counter64
			MAX-ACCESS read-only
			STATUS current
			DESCRIPTION
				"The total number of packets dropped during sending process
				by this IPSec Phase-2 Tunnel."
			::= { fsIPSec2TunnelStatEntry 10 }


		-- 1.3.6.1.4.1.52642.1.1.10.2.108.1.3
		fsIPSec2SaTable OBJECT-TYPE
			SYNTAX SEQUENCE OF FSIPSec2SaEntry
			MAX-ACCESS not-accessible
			STATUS current
			DESCRIPTION
				"The IPSec Phase-2 Security Protection Index Table.  This table
				contains an entry for each active and expiring security association."
			::= { fsIPSec2Objects 3 }


		-- 1.3.6.1.4.1.52642.1.1.10.2.108.1.3.1
		fsIPSec2SaEntry OBJECT-TYPE
			SYNTAX FSIPSec2SaEntry
			MAX-ACCESS not-accessible
			STATUS current
			DESCRIPTION
				"Information about FSIPSec2SaTable."
			INDEX { fsIPSec2SaIndex }
			::= { fsIPSec2SaTable 1 }


		FSIPSec2SaEntry ::=
			SEQUENCE {
				fsIPSec2SaIndex
					Integer32,
				fsIPSec2SaDirection
					INTEGER,
				fsIPSec2SaValue
					Unsigned32,
				fsIPSec2SaProtocol
					FSSaProtocol,
				fsIPSec2SaEncryptAlgo
					FSEncryptAlgo,
				fsIPSec2SaAuthAlgo
					FSAuthAlgo,
				fsIPSec2SaStatus
					FSIPSec2TunnelState
			 }

		-- 1.3.6.1.4.1.52642.1.1.10.2.108.1.3.1.1
		fsIPSec2SaIndex OBJECT-TYPE
			SYNTAX Integer32 (1..2147483647)
			MAX-ACCESS read-only
			STATUS current
			DESCRIPTION
				"The number of the Sa associated with the Phase-2 Tunnel
				Table.  The value of this index is a number which begins
				at one and is incremented with each Sa associated with
				an IPSec Phase-2 Tunnel.  The value of this object will
				wrap at 2,147,483,647."
			::= { fsIPSec2SaEntry 1 }


		-- 1.3.6.1.4.1.52642.1.1.10.2.108.1.3.1.2
		fsIPSec2SaDirection OBJECT-TYPE
			SYNTAX INTEGER
				{
				in(1),
				out(2)
				}
			MAX-ACCESS read-only
			STATUS current
			DESCRIPTION
				"The direction of the SA."
			::= { fsIPSec2SaEntry 2 }


		-- 1.3.6.1.4.1.52642.1.1.10.2.108.1.3.1.3
		fsIPSec2SaValue OBJECT-TYPE
			SYNTAX Unsigned32 (1..4294967295)
			MAX-ACCESS read-only
			STATUS current
			DESCRIPTION
				"The value of the SPI."
			::= { fsIPSec2SaEntry 3 }


		-- 1.3.6.1.4.1.52642.1.1.10.2.108.1.3.1.4
		fsIPSec2SaProtocol OBJECT-TYPE
			SYNTAX FSSaProtocol
			MAX-ACCESS read-only
			STATUS current
			DESCRIPTION
				"The security protocol of the SA."
			::= { fsIPSec2SaEntry 4 }


		-- 1.3.6.1.4.1.52642.1.1.10.2.108.1.3.1.5
		fsIPSec2SaEncryptAlgo OBJECT-TYPE
			SYNTAX FSEncryptAlgo
			MAX-ACCESS read-only
			STATUS current
			DESCRIPTION
				"The encryption algorithm used by the security association
				of the IPSec Phase-2 Tunnel."
			::= { fsIPSec2SaEntry 5 }


		-- 1.3.6.1.4.1.52642.1.1.10.2.108.1.3.1.6
		fsIPSec2SaAuthAlgo OBJECT-TYPE
			SYNTAX FSAuthAlgo
			MAX-ACCESS read-only
			STATUS current
			DESCRIPTION
				"The authentication algorithm used by the SA."
			::= { fsIPSec2SaEntry 6 }


		-- 1.3.6.1.4.1.52642.1.1.10.2.108.1.3.1.7
		fsIPSec2SaStatus OBJECT-TYPE
			SYNTAX FSIPSec2TunnelState
			MAX-ACCESS read-only
			STATUS current
			DESCRIPTION
				"The status of the SA."
			::= { fsIPSec2SaEntry 7 }


		-- 1.3.6.1.4.1.52642.1.1.10.2.108.1.4
		fsIPSec2TrafficTable OBJECT-TYPE
			SYNTAX SEQUENCE OF FSIPSec2TrafficEntry
			MAX-ACCESS not-accessible
			STATUS current
			DESCRIPTION
				"The IPSec Phase-2 Tunnel Traffic Table. "
			::= { fsIPSec2Objects 4 }


		-- 1.3.6.1.4.1.52642.1.1.10.2.108.1.4.1
		fsIPSec2TrafficEntry OBJECT-TYPE
			SYNTAX FSIPSec2TrafficEntry
			MAX-ACCESS not-accessible
			STATUS current
			DESCRIPTION
				"Information about FSIPSec2TrafficTable."
			INDEX { fsIPSec2TunnelTrafficIndex }
			::= { fsIPSec2TrafficTable 1 }


		FSIPSec2TrafficEntry ::=
			SEQUENCE {
				fsIPSec2TrafficIndex
					Integer32,
				fsIPSec2TrafficLocalType
					FSTrafficType,
				fsIPSec2TrafficLocalAddr1
					IpAddress,
				fsIPSec2TrafficLocalAddr2
					IpAddress,
				fsIPSec2TrafficLocalProtocol
					Integer32,
				fsIPSec2TrafficLocalPort
					Integer32,
				fsIPSec2TrafficLocalHostname
					DisplayString,
				fsIPSec2TrafficRemoteType
					FSTrafficType,
				fsIPSec2TrafficRemoteAddr1
					IpAddress,
				fsIPSec2TrafficRemoteAddr2
					IpAddress,
				fsIPSec2TrafficRemoteProtocol
					Integer32,
				fsIPSec2TrafficRemotePort
					Integer32,
				fsIPSec2TrafficRemoteHostname
					DisplayString
			 }

		-- 1.3.6.1.4.1.52642.1.1.10.2.108.1.4.1.1
		fsIPSec2TrafficIndex OBJECT-TYPE
			SYNTAX Integer32
			MAX-ACCESS read-only
			STATUS current
			DESCRIPTION
				"Description."
			::= { fsIPSec2TrafficEntry 1 }


		-- 1.3.6.1.4.1.52642.1.1.10.2.108.1.4.1.2
		fsIPSec2TrafficLocalType OBJECT-TYPE
			SYNTAX FSTrafficType
			MAX-ACCESS read-only
			STATUS current
			DESCRIPTION
				"The type of local peer. Possible values are: a single
				IP address, or an IP address range, or an IP subnet."
			::= { fsIPSec2TrafficEntry 2 }


		-- 1.3.6.1.4.1.52642.1.1.10.2.108.1.4.1.3
		fsIPSec2TrafficLocalAddr1 OBJECT-TYPE
			SYNTAX IpAddress
			MAX-ACCESS read-only
			STATUS current
			DESCRIPTION
				"The first specification of local peer's IP address. If
				the local peer type is single IP address, then this is the
				value of the IP address. If the local peer type is IP subnet,
				then this is the value of the subnet. If the local peer type
				is IP address range, then this is the value of beginning IP
				address of the range."
			::= { fsIPSec2TrafficEntry 3 }


		-- 1.3.6.1.4.1.52642.1.1.10.2.108.1.4.1.4
		fsIPSec2TrafficLocalAddr2 OBJECT-TYPE
			SYNTAX IpAddress
			MAX-ACCESS read-only
			STATUS current
			DESCRIPTION
				"The second specification of local peer's IP address. If the local
				peer type is single IP address, then this is the value of the
				IP address. If the local peer type is IP subnet, then this is
				the value of the subnet mask. If the local peer type is IP
				address range, then this is the value of ending IP address of
				the range."
			::= { fsIPSec2TrafficEntry 4 }


		-- 1.3.6.1.4.1.52642.1.1.10.2.108.1.4.1.5
		fsIPSec2TrafficLocalProtocol OBJECT-TYPE
			SYNTAX Integer32 (0..255)
			MAX-ACCESS read-only
			STATUS current
			DESCRIPTION
				"The protocol number of the local peer's traffic."
			::= { fsIPSec2TrafficEntry 5 }


		-- 1.3.6.1.4.1.52642.1.1.10.2.108.1.4.1.6
		fsIPSec2TrafficLocalPort OBJECT-TYPE
			SYNTAX Integer32 (0..65535)
			MAX-ACCESS read-only
			STATUS current
			DESCRIPTION
				"The port number of the local peer's traffic."
			::= { fsIPSec2TrafficEntry 6 }


		-- 1.3.6.1.4.1.52642.1.1.10.2.108.1.4.1.7
		fsIPSec2TrafficLocalHostname OBJECT-TYPE
			SYNTAX DisplayString
			MAX-ACCESS read-only
			STATUS current
			DESCRIPTION
				"The Hostname of local peer's IP address."
			::= { fsIPSec2TrafficEntry 7 }


		-- 1.3.6.1.4.1.52642.1.1.10.2.108.1.4.1.8
		fsIPSec2TrafficRemoteType OBJECT-TYPE
			SYNTAX FSTrafficType
			MAX-ACCESS read-only
			STATUS current
			DESCRIPTION
				"The type of remote peer. Possible values are: a single
				IP address, or an IP address range, or an IP subnet."
			::= { fsIPSec2TrafficEntry 8 }


		-- 1.3.6.1.4.1.52642.1.1.10.2.108.1.4.1.9
		fsIPSec2TrafficRemoteAddr1 OBJECT-TYPE
			SYNTAX IpAddress
			MAX-ACCESS read-only
			STATUS current
			DESCRIPTION
				"The first specification of remote peer's IP address.
				If the remote peer type is single IP address, then
				this is the value of the IP address. If the remote
				peer type is IP subnet, then this is the value
				of the subnet. If the remote peer type is IP
				address range, then this is the value of beginning
				IP address of the range."
			::= { fsIPSec2TrafficEntry 9 }


		-- 1.3.6.1.4.1.52642.1.1.10.2.108.1.4.1.10
		fsIPSec2TrafficRemoteAddr2 OBJECT-TYPE
			SYNTAX IpAddress
			MAX-ACCESS read-only
			STATUS current
			DESCRIPTION
				"Single IP address, then this is the value of the IP
				address. If the remote peer type is IP subnet,
				then this is the value of the subnet mask. If the
				remote peer type is IP address range, then this
				is the value of ending IP address of the range."
			::= { fsIPSec2TrafficEntry 10 }


		-- 1.3.6.1.4.1.52642.1.1.10.2.108.1.4.1.11
		fsIPSec2TrafficRemoteProtocol OBJECT-TYPE
			SYNTAX Integer32 (0..255)
			MAX-ACCESS read-only
			STATUS current
			DESCRIPTION
				"The protocol number of the remote peer's traffic."
			::= { fsIPSec2TrafficEntry 11 }


		-- 1.3.6.1.4.1.52642.1.1.10.2.108.1.4.1.12
		fsIPSec2TrafficRemotePort OBJECT-TYPE
			SYNTAX Integer32 (0..65535)
			MAX-ACCESS read-only
			STATUS current
			DESCRIPTION
				"The port number of the remote peer's traffic."
			::= { fsIPSec2TrafficEntry 12 }


		-- 1.3.6.1.4.1.52642.1.1.10.2.108.1.4.1.13
		fsIPSec2TrafficRemoteHostname OBJECT-TYPE
			SYNTAX DisplayString
			MAX-ACCESS read-only
			STATUS current
			DESCRIPTION
				"The Hostname of remote peer's IP address."
			::= { fsIPSec2TrafficEntry 13 }


		-- 1.3.6.1.4.1.52642.1.1.10.2.108.1.5
		fsIPSec2GlobalStats OBJECT IDENTIFIER ::= { fsIPSec2Objects 5 }


		-- 1.3.6.1.4.1.52642.1.1.10.2.108.1.5.1
		fsIPSec2GlobalActiveTunnels OBJECT-TYPE
			SYNTAX Gauge32
			MAX-ACCESS read-only
			STATUS current
			DESCRIPTION
				"The total number of currently active  IPSec Phase-2 Tunnels."
			::= { fsIPSec2GlobalStats 1 }


		-- 1.3.6.1.4.1.52642.1.1.10.2.108.1.5.2
		fsIPSec2GlobalActiveSas OBJECT-TYPE
			SYNTAX Gauge32
			MAX-ACCESS read-only
			STATUS current
			DESCRIPTION
				"The total number of currently active or expiring IPSec Phase-2 SA."
			::= { fsIPSec2GlobalStats 2 }


		-- 1.3.6.1.4.1.52642.1.1.10.2.108.1.5.3
		fsIPSec2GlobalInOctets OBJECT-TYPE
			SYNTAX Counter64
			MAX-ACCESS read-only
			STATUS current
			DESCRIPTION
				"The total number of octets received by all current and previous
				IPSec Phase-2 Tunnels. This value is accumulated BEFORE determining
				whether or not the packet should be decompressed."
			::= { fsIPSec2GlobalStats 3 }


		-- 1.3.6.1.4.1.52642.1.1.10.2.108.1.5.4
		fsIPSec2GlobalInPkts OBJECT-TYPE
			SYNTAX Counter64
			MAX-ACCESS read-only
			STATUS current
			DESCRIPTION
				"The total number of packets received by all current and
				previous IPSec Phase-2 Tunnels."
			::= { fsIPSec2GlobalStats 4 }


		-- 1.3.6.1.4.1.52642.1.1.10.2.108.1.5.5
		fsIPSec2GlobalInSpeed OBJECT-TYPE
			SYNTAX Counter64
			MAX-ACCESS read-only
			STATUS current
			DESCRIPTION
				"The total speed(bps) of packets received by all current and
				previous IPSec Phase-2 Tunnels."
			::= { fsIPSec2GlobalStats 5 }


		-- 1.3.6.1.4.1.52642.1.1.10.2.108.1.5.6
		fsIPSec2GlobalInDrops OBJECT-TYPE
			SYNTAX Counter64
			MAX-ACCESS read-only
			STATUS current
			DESCRIPTION
				"The total number of packets dropped during receiving
				process by all current and previous IPSec Phase-2
				Tunnels. "
			::= { fsIPSec2GlobalStats 6 }


		-- 1.3.6.1.4.1.52642.1.1.10.2.108.1.5.7
		fsIPSec2GlobalOutOctets OBJECT-TYPE
			SYNTAX Counter64
			MAX-ACCESS read-only
			STATUS current
			DESCRIPTION
				"The total number of octets sent by all current and previous
				IPSec Phase-2 Tunnels. This value is accumulated AFTER
				determining whether or not the packet should be compressed."
			::= { fsIPSec2GlobalStats 7 }


		-- 1.3.6.1.4.1.52642.1.1.10.2.108.1.5.8
		fsIPSec2GlobalOutPkts OBJECT-TYPE
			SYNTAX Counter64
			MAX-ACCESS read-only
			STATUS current
			DESCRIPTION
				"The total number of packets sent by all current and previous
				IPSec Phase-2 Tunnels."
			::= { fsIPSec2GlobalStats 8 }


		-- 1.3.6.1.4.1.52642.1.1.10.2.108.1.5.9
		fsIPSec2GlobalOutSpeed OBJECT-TYPE
			SYNTAX Counter64
			MAX-ACCESS read-only
			STATUS current
			DESCRIPTION
				"The total speed(bps) of packets sent by all current and previous
				IPSec Phase-2 Tunnels."
			::= { fsIPSec2GlobalStats 9 }


		-- 1.3.6.1.4.1.52642.1.1.10.2.108.1.5.10
		fsIPSec2GlobalOutDrops OBJECT-TYPE
			SYNTAX Counter64
			MAX-ACCESS read-only
			STATUS current
			DESCRIPTION
				"The total number of packets dropped during sending process
				by all current and previous IPSec Phase-2 Tunnels."
			::= { fsIPSec2GlobalStats 10 }


		-- 1.3.6.1.4.1.52642.1.1.10.2.108.1.6
		fsIPSec2TrapObject OBJECT IDENTIFIER ::= { fsIPSec2Objects 6 }


		-- 1.3.6.1.4.1.52642.1.1.10.2.108.1.6.1
		fsIPSec2MapName OBJECT-TYPE
			SYNTAX DisplayString
			MAX-ACCESS accessible-for-notify
			STATUS current
			DESCRIPTION
				"The IPSec map name with a trap."
			::= { fsIPSec2TrapObject 1 }


		-- 1.3.6.1.4.1.52642.1.1.10.2.108.1.6.2
		fsIPSec2SeqNum OBJECT-TYPE
			SYNTAX Integer32
			MAX-ACCESS accessible-for-notify
			STATUS current
			DESCRIPTION
				"The IPSec map sequence number with a trap."
			::= { fsIPSec2TrapObject 2 }


		-- 1.3.6.1.4.1.52642.1.1.10.2.108.1.6.3
		fsIPSec2SpiValue OBJECT-TYPE
			SYNTAX Integer32
			MAX-ACCESS accessible-for-notify
			STATUS current
			DESCRIPTION
				"The SPI value associated with a trap."
			::= { fsIPSec2TrapObject 3 }


		-- 1.3.6.1.4.1.52642.1.1.10.2.108.1.7
		fsIPSec2Trap OBJECT IDENTIFIER ::= { fsIPSec2Objects 7 }


		-- 1.3.6.1.4.1.52642.1.1.10.2.108.1.7.1
		fsIPSec2Notifications OBJECT IDENTIFIER ::= { fsIPSec2Trap 1 }


		-- 1.3.6.1.4.1.52642.1.1.10.2.108.1.7.1.1
		fsIPSec2TunnelStart NOTIFICATION-TYPE
			OBJECTS { fsIPSec2TunIfIndex, fsIPSec2TunRemoteAddr, fsIPSec2TrafficLocalType, fsIPSec2TrafficLocalAddr1, fsIPSec2TrafficLocalAddr2,
				fsIPSec2TrafficLocalProtocol, fsIPSec2TrafficLocalPort, fsIPSec2TrafficRemoteAddr1, fsIPSec2TrafficRemoteAddr2, fsIPSec2TrafficRemotePort
				 }
			STATUS current
			DESCRIPTION
				"This notification is generated when an IPSec Phase-2
				Tunnel is created."
			::= { fsIPSec2Notifications 1 }


		-- 1.3.6.1.4.1.52642.1.1.10.2.108.1.7.1.2
		fsIPSec2TunnelStop NOTIFICATION-TYPE
			OBJECTS { fsIPSec2TunIfIndex, fsIPSec2TunRemoteAddr, fsIPSec2TrafficLocalType, fsIPSec2TrafficLocalAddr1, fsIPSec2TrafficLocalAddr2,
				fsIPSec2TrafficLocalProtocol, fsIPSec2TrafficLocalPort, fsIPSec2TrafficRemoteAddr1, fsIPSec2TrafficRemoteAddr2, fsIPSec2TrafficRemotePort
				 }
			STATUS current
			DESCRIPTION
				"This notification is generated when an IPSec Phase-2
				Tunnel is deleted."
			::= { fsIPSec2Notifications 2 }


		-- 1.3.6.1.4.1.52642.1.1.10.2.108.2
		fsIPSec2Conformance OBJECT IDENTIFIER ::= { fsIPSec2MibModule 2 }


		-- 1.3.6.1.4.1.52642.1.1.10.2.108.2.1
		fsIPSec2Compliances OBJECT IDENTIFIER ::= { fsIPSec2Conformance 1 }


		-- 1.3.6.1.4.1.52642.1.1.10.2.108.2.1.1
		fsIPSec2Compliance MODULE-COMPLIANCE
			STATUS current
			DESCRIPTION
				" "
			MODULE -- this module
				MANDATORY-GROUPS { fsIPSec2TunnelTableGroup, fsIPSec2TunnelStatGroup, fsIPSec2SaGroup, fsIPSec2TrafficTableGroup, fsIPSec2GlobalStatsGroup,
					fsIPSec2TrapObjectGroup, fsIPSec2TrapGroup }
			::= { fsIPSec2Compliances 1 }


		-- 1.3.6.1.4.1.52642.1.1.10.2.108.2.2
		fsIPSec2Groups OBJECT IDENTIFIER ::= { fsIPSec2Conformance 2 }


		-- 1.3.6.1.4.1.52642.1.1.10.2.108.2.2.1
		fsIPSec2TunnelTableGroup OBJECT-GROUP
			OBJECTS { fsIPSec2TunIfIndex, fsIPSec2TunLocalAddr, fsIPSec2TunRemoteAddr, fsIPSec2TunLocalHostname, fsIPSec2TunRemoteHostname,
				fsIPSec2TunKeyType, fsIPSec2TunEncapMode, fsIPSec2TunInitiator, fsIPSec2TunLifeSize, fsIPSec2TunLifeTime,
				fsIPSec2TunRemainTime, fsIPSec2TunActiveTime, fsIPSec2TunCreateTime, fsIPSec2TunRemainSize, fsIPSec2TunTotalRefreshes,
				fsIPSec2TunCurrentSaInstances, fsIPSec2TunInSaEncryptAlgo, fsIPSec2TunInSaAhAuthAlgo, fsIPSec2TunInSaEspAuthAlgo, fsIPSec2TunDiffHellmanGrp,
				fsIPSec2TunOutSaEncryptAlgo, fsIPSec2TunOutSaAhAuthAlgo, fsIPSec2TunOutSaEspAuthAlgo, fsIPSec2TunMapName, fsIPSec2TunSeqNum,
				fsIPSec2TunStatus, fsIPSec2TunInOctets, fsIPSec2TunInDecompOctets, fsIPSec2TunInPkts, fsIPSec2TunInSpeed,
				fsIPSec2TunInDropPkts, fsIPSec2TunOutOctets, fsIPSec2TunOutUncompOctets, fsIPSec2TunOutPkts, fsIPSec2TunOutSpeed,
				fsIPSec2TunOutDropPkts }
			STATUS current
			DESCRIPTION
				"The group contains the IPSec tunnel's property information."
			::= { fsIPSec2Groups 1 }


		-- 1.3.6.1.4.1.52642.1.1.10.2.108.2.2.2
		fsIPSec2TunnelStatGroup OBJECT-GROUP
			OBJECTS { fsIPSec2TunInOctets, fsIPSec2TunInDecompOctets, fsIPSec2TunInPkts, fsIPSec2TunInSpeed, fsIPSec2TunInDropPkts,
				fsIPSec2TunOutOctets, fsIPSec2TunOutUncompOctets, fsIPSec2TunOutPkts, fsIPSec2TunOutSpeed, fsIPSec2TunOutDropPkts
				 }
			STATUS current
			DESCRIPTION
				"The group contains the IPSec tunnel's statistic information."
			::= { fsIPSec2Groups 2 }


		-- 1.3.6.1.4.1.52642.1.1.10.2.108.2.2.3
		fsIPSec2SaGroup OBJECT-GROUP
			OBJECTS { fsIPSec2SaIndex, fsIPSec2SaDirection, fsIPSec2SaValue, fsIPSec2SaProtocol, fsIPSec2SaEncryptAlgo,
				fsIPSec2SaAuthAlgo, fsIPSec2SaStatus }
			STATUS current
			DESCRIPTION
				"The group contains the SA's property information."
			::= { fsIPSec2Groups 3 }


		-- 1.3.6.1.4.1.52642.1.1.10.2.108.2.2.4
		fsIPSec2TrafficTableGroup OBJECT-GROUP
			OBJECTS { fsIPSec2TrafficLocalType, fsIPSec2TrafficLocalAddr1, fsIPSec2TrafficLocalAddr2, fsIPSec2TrafficLocalProtocol, fsIPSec2TrafficLocalPort,
				fsIPSec2TrafficRemoteAddr1, fsIPSec2TrafficRemoteAddr2, fsIPSec2TrafficRemotePort, fsIPSec2TrafficLocalHostname, fsIPSec2TrafficRemoteType,
				fsIPSec2TrafficRemoteProtocol, fsIPSec2TrafficRemoteHostname }
			STATUS current
			DESCRIPTION
				"The group contains the property information of the
				data flow protected by IPSec tunnel."
			::= { fsIPSec2Groups 4 }


		-- 1.3.6.1.4.1.52642.1.1.10.2.108.2.2.5
		fsIPSec2GlobalStatsGroup OBJECT-GROUP
			OBJECTS { fsIPSec2GlobalActiveTunnels, fsIPSec2GlobalActiveSas, fsIPSec2GlobalInOctets, fsIPSec2GlobalInPkts, fsIPSec2GlobalInSpeed,
				fsIPSec2GlobalInDrops, fsIPSec2GlobalOutOctets, fsIPSec2GlobalOutPkts, fsIPSec2GlobalOutSpeed, fsIPSec2GlobalOutDrops
				 }
			STATUS current
			DESCRIPTION
				"The group contains all of the IPSec tunnel's statistic
				information."
			::= { fsIPSec2Groups 5 }


		-- 1.3.6.1.4.1.52642.1.1.10.2.108.2.2.6
		fsIPSec2TrapObjectGroup OBJECT-GROUP
			OBJECTS { fsIPSec2MapName, fsIPSec2SeqNum, fsIPSec2SpiValue }
			STATUS current
			DESCRIPTION
				"The group contains all of trap objects of IPSec tunnels."
			::= { fsIPSec2Groups 6 }


		-- 1.3.6.1.4.1.52642.1.1.10.2.108.2.2.7
		fsIPSec2TrapGroup NOTIFICATION-GROUP
			NOTIFICATIONS { fsIPSec2TunnelStart, fsIPSec2TunnelStop }
			STATUS current
			DESCRIPTION
				"The group contains all of trap of IPSec tunnels."
			::= { fsIPSec2Groups 7 }



	END

--
-- FS-IPSEC2-MIB.mib
--
