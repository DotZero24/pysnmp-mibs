-- *****************************************************************
-- FS-MMU-MIB.mib: FS MMU MIB File for 3PJ1
--
-- June 2015, chenlong
--
-- Copyright (c) 2015 by FS.COM Inc..
-- All rights reserved.
--
-- *****************************************************************
--

FS-MMU-MIB DEFINITIONS ::= BEGIN

IMPORTS
        MODULE-IDENTITY,
        OBJECT-TYPE,
        Integer32,
        Counter64,
        NOTIFICATION-TYPE
                FROM SNMPv2-SMI
        MODULE-COMPLIANCE,
        OBJECT-GROUP,
        NOTIFICATION-GROUP
                FROM SNMPv2-CONF
        IfIndex
                FROM FS-TC
        fsMgmt
                FROM FS-SMI;

fsMMUMIB MODULE-IDENTITY
        LAST-UPDATED "201506240000Z"
        ORGANIZATION "FS.COM Inc.."
        CONTACT-INFO
                "
                Tel: 400-865-2852

                E-mail: https://www.fs.com/live_chat_service_mail.html"
        DESCRIPTION
                "This module defines fs NFPP mibs."
        REVISION      "201506240000Z"
        DESCRIPTION
                "Initial version of this MIB module."
        ::= { fsMgmt 141 }

-- 第一个消息，统计端口入口方向的报文

fsMmuIfVoqInTable OBJECT-TYPE
        SYNTAX SEQUENCE OF FSMmuIfVoqInEntry
        MAX-ACCESS not-accessible
        STATUS current
        DESCRIPTION
            "Packet statistics of IN direction."
        ::= { fsMMUMIB 1 }

fsMmuIfVoqInEntry OBJECT-TYPE
        SYNTAX FSMmuIfVoqInEntry
        MAX-ACCESS not-accessible
        STATUS current
        DESCRIPTION
            "Parameters of fsMmuIfVoqInTable."
            INDEX { fsInIfxId, fsInQueueId, fsInDevId, fsInSlotId, fsInPgId }
        ::= { fsMmuIfVoqInTable 1 }

FSMmuIfVoqInEntry ::=
        SEQUENCE {
            fsInIfxId IfIndex,
            fsInQueueId Integer32,
            fsInDevId Integer32,
            fsInSlotId Integer32,
            fsInPgId Integer32,
            fsInTransmitPackets Counter64,
            fsInTransmitBytes Counter64,
            fsInDropPackets Counter64,
            fsInDropBytes Counter64
        }

fsInIfxId OBJECT-TYPE
        SYNTAX IfIndex
        MAX-ACCESS read-only
        STATUS current
        DESCRIPTION
            "Interface index."
        ::= { fsMmuIfVoqInEntry 1 }

fsInQueueId OBJECT-TYPE
        SYNTAX Integer32
        MAX-ACCESS read-only
        STATUS current
        DESCRIPTION
            "Queue index."
        ::= { fsMmuIfVoqInEntry 2 }

fsInDevId OBJECT-TYPE
        SYNTAX Integer32
        MAX-ACCESS read-only
        STATUS current
        DESCRIPTION
            "Device index."
        ::= { fsMmuIfVoqInEntry 3 }

fsInSlotId OBJECT-TYPE
        SYNTAX Integer32
        MAX-ACCESS read-only
        STATUS current
        DESCRIPTION
            "Slot index."
        ::= { fsMmuIfVoqInEntry 4 }

fsInPgId OBJECT-TYPE
        SYNTAX Integer32
        MAX-ACCESS read-only
        STATUS current
        DESCRIPTION
            "Port group index."
        ::= { fsMmuIfVoqInEntry 5 }

fsInTransmitPackets OBJECT-TYPE
        SYNTAX Counter64
        MAX-ACCESS read-only
        STATUS current
        DESCRIPTION
            "Transmitted packets."
        ::= { fsMmuIfVoqInEntry 6 }

fsInTransmitBytes OBJECT-TYPE
        SYNTAX Counter64
        MAX-ACCESS read-only
        STATUS current
        DESCRIPTION
            "Transmitted bytes."
        ::= { fsMmuIfVoqInEntry 7 }

fsInDropPackets OBJECT-TYPE
        SYNTAX Counter64
        MAX-ACCESS read-only
        STATUS current
        DESCRIPTION
            "Dropped packets."
        ::= { fsMmuIfVoqInEntry 8 }

fsInDropBytes OBJECT-TYPE
        SYNTAX Counter64
        MAX-ACCESS read-only
        STATUS current
        DESCRIPTION
            "Dropped bytes."
        ::= { fsMmuIfVoqInEntry 9 }

-- 第二个消息，统计端口出口方向的报文

fsMmuIfVoqOutTable OBJECT-TYPE
        SYNTAX SEQUENCE OF FSMmuIfVoqOutEntry
        MAX-ACCESS not-accessible
        STATUS current
        DESCRIPTION
            "Packet statistics of OUT direction."
        ::= { fsMMUMIB 2 }

fsMmuIfVoqOutEntry OBJECT-TYPE
        SYNTAX FSMmuIfVoqOutEntry
        MAX-ACCESS not-accessible
        STATUS current
        DESCRIPTION
            "Parameters of fsMmuIfVoqOutTable."
            INDEX { fsOutIfxId, fsOutQueueId, fsOutDevId, fsOutSlotId, fsOutPgId }
        ::= { fsMmuIfVoqOutTable 1 }

FSMmuIfVoqOutEntry ::=
        SEQUENCE {
            fsOutIfxId IfIndex,
            fsOutQueueId Integer32,
            fsOutDevId Integer32,
            fsOutSlotId Integer32,
            fsOutPgId Integer32,
            fsOutTransmitPackets Counter64,
            fsOutTransmitBytes Counter64,
            fsOutDropPackets Counter64,
            fsOutDropBytes Counter64
        }

fsOutIfxId OBJECT-TYPE
        SYNTAX IfIndex
        MAX-ACCESS read-only
        STATUS current
        DESCRIPTION
            "Interface index."
        ::= { fsMmuIfVoqOutEntry 1 }

fsOutQueueId OBJECT-TYPE
        SYNTAX Integer32
        MAX-ACCESS read-only
        STATUS current
        DESCRIPTION
            "Queue index."
        ::= { fsMmuIfVoqOutEntry 2 }

fsOutDevId OBJECT-TYPE
        SYNTAX Integer32
        MAX-ACCESS read-only
        STATUS current
        DESCRIPTION
            "Device index."
        ::= { fsMmuIfVoqOutEntry 3 }

fsOutSlotId OBJECT-TYPE
        SYNTAX Integer32
        MAX-ACCESS read-only
        STATUS current
        DESCRIPTION
            "Slot index."
        ::= { fsMmuIfVoqOutEntry 4 }

fsOutPgId OBJECT-TYPE
        SYNTAX Integer32
        MAX-ACCESS read-only
        STATUS current
        DESCRIPTION
            "Port group index."
        ::= { fsMmuIfVoqOutEntry 5 }

fsOutTransmitPackets OBJECT-TYPE
        SYNTAX Counter64
        MAX-ACCESS read-only
        STATUS current
        DESCRIPTION
            "Transmitted packets."
        ::= { fsMmuIfVoqOutEntry 6 }

fsOutTransmitBytes OBJECT-TYPE
        SYNTAX Counter64
        MAX-ACCESS read-only
        STATUS current
        DESCRIPTION
            "Transmitted bytes."
        ::= { fsMmuIfVoqOutEntry 7 }

fsOutDropPackets OBJECT-TYPE
        SYNTAX Counter64
        MAX-ACCESS read-only
        STATUS current
        DESCRIPTION
            "Dropped packets."
        ::= { fsMmuIfVoqOutEntry 8 }

fsOutDropBytes OBJECT-TYPE
        SYNTAX Counter64
        MAX-ACCESS read-only
        STATUS current
        DESCRIPTION
            "Dropped bytes."
        ::= { fsMmuIfVoqOutEntry 9 }

-- 第三个消息，统计buffer超过门限的次数

fsMmuIfWarnTable OBJECT-TYPE
        SYNTAX SEQUENCE OF FSMmuIfWarnEntry
        MAX-ACCESS not-accessible
        STATUS current
        DESCRIPTION
            "Times buffer over usage-warn-limit."
        ::= { fsMMUMIB 3 }

fsMmuIfWarnEntry OBJECT-TYPE
        SYNTAX FSMmuIfWarnEntry
        MAX-ACCESS not-accessible
        STATUS current
        DESCRIPTION
            "Parameters of fsMmuIfWarnTable."
            INDEX { fsWarnIfxId, fsWarnDevId, fsWarnSlotId, fsWarnPgId }
        ::= { fsMmuIfWarnTable 1 }

FSMmuIfWarnEntry ::=
        SEQUENCE {
            fsWarnIfxId IfIndex,
            fsWarnDevId Integer32,
            fsWarnSlotId Integer32,
            fsWarnPgId Integer32,
            fsWarnUsedCell Integer32,
            fsWarnTotalCell Integer32,
            fsWarnLimit Integer32,
            fsWarnCount Integer32
        }

fsWarnIfxId OBJECT-TYPE
        SYNTAX IfIndex
        MAX-ACCESS read-only
        STATUS current
        DESCRIPTION
            "Interface index."
        ::= { fsMmuIfWarnEntry 1 }


fsWarnDevId OBJECT-TYPE
        SYNTAX Integer32
        MAX-ACCESS read-only
        STATUS current
        DESCRIPTION
            "Device index."
        ::= { fsMmuIfWarnEntry 2 }

fsWarnSlotId OBJECT-TYPE
        SYNTAX Integer32
        MAX-ACCESS read-only
        STATUS current
        DESCRIPTION
            "Slot index."
        ::= { fsMmuIfWarnEntry 3 }

fsWarnPgId OBJECT-TYPE
        SYNTAX Integer32
        MAX-ACCESS read-only
        STATUS current
        DESCRIPTION
            "Port group index."
        ::= { fsMmuIfWarnEntry 4 }

fsWarnUsedCell OBJECT-TYPE
        SYNTAX Integer32
        MAX-ACCESS read-only
        STATUS current
        DESCRIPTION
            "Used cell num."
        ::= { fsMmuIfWarnEntry 5 }

fsWarnTotalCell OBJECT-TYPE
        SYNTAX Integer32
        MAX-ACCESS read-only
        STATUS current
        DESCRIPTION
            "Total cell num."
        ::= { fsMmuIfWarnEntry 6 }

fsWarnLimit OBJECT-TYPE
        SYNTAX Integer32
        MAX-ACCESS read-only
        STATUS current
        DESCRIPTION
            "The usage-warn-limit value."
        ::= { fsMmuIfWarnEntry 7 }

fsWarnCount OBJECT-TYPE
        SYNTAX Integer32
        MAX-ACCESS read-only
        STATUS current
        DESCRIPTION
            "The count buffer over usage-warn-limit."
        ::= { fsMmuIfWarnEntry 8 }



-- 第四个消息，统计端口的buffer

fsMmuIfVoqWarnTable OBJECT-TYPE
        SYNTAX SEQUENCE OF FSMmuIfVoqWarnEntry
        MAX-ACCESS not-accessible
        STATUS current
        DESCRIPTION
            "buffer statistics ."
        ::= { fsMMUMIB 4 }

fsMmuIfVoqWarnEntry OBJECT-TYPE
        SYNTAX FSMmuIfVoqWarnEntry
        MAX-ACCESS not-accessible
        STATUS current
        DESCRIPTION
            "Parameters of fsMmuIfVoqWarnTable."
            INDEX { fsVoqWarnIfxId, fsVoqWarnQueueId, fsVoqWarnDevId, fsVoqWarnSlotId, fsVoqWarnPgId }
        ::= { fsMmuIfVoqWarnTable 1 }

FSMmuIfVoqWarnEntry ::=
        SEQUENCE {
            fsVoqWarnIfxId IfIndex,
            fsVoqWarnQueueId Integer32,
			fsVoqWarnDevId Integer32,
            fsVoqWarnSlotId Integer32,
            fsVoqWarnPgId Integer32,
            fsVoqWarnUsedcells Counter64,
            fsVoqWarnAvailablecells Counter64,
            fsVoqWarnTotalcells Counter64,
            fsVoqWarnUsage Counter64,
            fsVoqWarnUsagewarnlimit Counter64,
            fsVoqWarnUsagewarncount Counter64,
			fsVoqWarnPeakedcells Counter64
        }

fsVoqWarnIfxId OBJECT-TYPE
        SYNTAX IfIndex
        MAX-ACCESS read-only
        STATUS current
        DESCRIPTION
            "Interface index."
        ::= { fsMmuIfVoqWarnEntry 1 }

fsVoqWarnQueueId OBJECT-TYPE
        SYNTAX Integer32
        MAX-ACCESS read-only
        STATUS current
        DESCRIPTION
            "Queue index."
        ::= { fsMmuIfVoqWarnEntry 2 }

fsVoqWarnDevId OBJECT-TYPE
        SYNTAX Integer32
        MAX-ACCESS read-only
        STATUS current
        DESCRIPTION
            "Device index."
        ::= { fsMmuIfVoqWarnEntry 3 }

fsVoqWarnSlotId OBJECT-TYPE
        SYNTAX Integer32
        MAX-ACCESS read-only
        STATUS current
        DESCRIPTION
            "Slot index."
        ::= { fsMmuIfVoqWarnEntry 4 }

fsVoqWarnPgId OBJECT-TYPE
        SYNTAX Integer32
        MAX-ACCESS read-only
        STATUS current
        DESCRIPTION
            "Port group index."
        ::= { fsMmuIfVoqWarnEntry 5 }

fsVoqWarnUsedcells OBJECT-TYPE
        SYNTAX Counter64
        MAX-ACCESS read-only
        STATUS current
        DESCRIPTION
            "Used cells."
        ::= { fsMmuIfVoqWarnEntry 6 }

fsVoqWarnAvailablecells OBJECT-TYPE
        SYNTAX Counter64
        MAX-ACCESS read-only
        STATUS current
        DESCRIPTION
            "Available cells."
        ::= { fsMmuIfVoqWarnEntry 7 }

fsVoqWarnTotalcells OBJECT-TYPE
        SYNTAX Counter64
        MAX-ACCESS read-only
        STATUS current
        DESCRIPTION
            "Total cells."
        ::= { fsMmuIfVoqWarnEntry 8 }

fsVoqWarnUsage OBJECT-TYPE
        SYNTAX Counter64
        MAX-ACCESS read-only
        STATUS current
        DESCRIPTION
            "Usage."
        ::= { fsMmuIfVoqWarnEntry 9 }

fsVoqWarnUsagewarnlimit OBJECT-TYPE
        SYNTAX Counter64
        MAX-ACCESS read-only
        STATUS current
        DESCRIPTION
            "Usage warn limit."
        ::= { fsMmuIfVoqWarnEntry 10 }

fsVoqWarnUsagewarncount OBJECT-TYPE
        SYNTAX Counter64
        MAX-ACCESS read-only
        STATUS current
        DESCRIPTION
            "Usage warn count."
        ::= { fsMmuIfVoqWarnEntry 11 }

fsVoqWarnPeakedcells OBJECT-TYPE
        SYNTAX Counter64
        MAX-ACCESS read-only
        STATUS current
        DESCRIPTION
            "Peaked cells."
        ::= { fsMmuIfVoqWarnEntry 12 }

--mmu queue  support
fsMmuIfQueueSupportTable OBJECT-TYPE
        SYNTAX SEQUENCE OF FSMmuIfQueueSupportEntry
        MAX-ACCESS not-accessible
        STATUS current
        DESCRIPTION
            "List  queues  of interfaces."
        ::= { fsMMUMIB 5 }

fsMmuIfQueueSupportEntry OBJECT-TYPE
        SYNTAX FSMmuIfQueueSupportEntry
        MAX-ACCESS not-accessible
        STATUS current
        DESCRIPTION
            "Queue Entry."
        INDEX { fsMmuIfIndex, fsMmuIfQueueIndex,fsMmuIfSliceIndex}
        ::= { fsMmuIfQueueSupportTable 1 }

FSMmuIfQueueSupportEntry ::=
        SEQUENCE {
            fsMmuIfIndex IfIndex,
            fsMmuIfQueueIndex Integer32,
            fsMmuIfSliceIndex Integer32,
            fsMmuIfQueueSupportUsedCells Counter64,
            fsMmuIfQueueSupportAvailableCells Counter64,
            fsMmuIfQueueSupportTotalCells Counter64,
            fsMmuIfQueueSupportUsage Counter64,
            fsMmuIfQueueSupportUsageWarnLimit Counter64,
            fsMmuIfQueueSupportUsageWarnCount Counter64,
            fsMmuIfQueueSupportPeakedCells Counter64
        }

fsMmuIfIndex OBJECT-TYPE
        SYNTAX IfIndex
        MAX-ACCESS read-only
        STATUS current
        DESCRIPTION
            "Interface index."
        ::= { fsMmuIfQueueSupportEntry 1 }

fsMmuIfQueueIndex OBJECT-TYPE
        SYNTAX Integer32
        MAX-ACCESS read-only
        STATUS current
        DESCRIPTION
            "Queue index."
        ::= { fsMmuIfQueueSupportEntry 2 }

fsMmuIfSliceIndex OBJECT-TYPE
        SYNTAX Integer32
        MAX-ACCESS read-only
        STATUS current
        DESCRIPTION
            "Slice index."
        ::= { fsMmuIfQueueSupportEntry 3 }

fsMmuIfQueueSupportUsedCells OBJECT-TYPE
        SYNTAX Counter64
        MAX-ACCESS read-only
        STATUS current
        DESCRIPTION
            "Used Cells of queues."
        ::= { fsMmuIfQueueSupportEntry 4 }

fsMmuIfQueueSupportAvailableCells OBJECT-TYPE
        SYNTAX Counter64
        MAX-ACCESS read-only
        STATUS current
        DESCRIPTION
            "Available Cells of queues."
        ::= { fsMmuIfQueueSupportEntry 5 }

fsMmuIfQueueSupportTotalCells OBJECT-TYPE
        SYNTAX Counter64
        MAX-ACCESS read-only
        STATUS current
        DESCRIPTION
            "size of queues."
        ::= { fsMmuIfQueueSupportEntry 6 }

fsMmuIfQueueSupportUsage OBJECT-TYPE
        SYNTAX Counter64
        MAX-ACCESS read-only
        STATUS current
        DESCRIPTION
            "usage of queues."
        ::= { fsMmuIfQueueSupportEntry 7 }

fsMmuIfQueueSupportUsageWarnLimit OBJECT-TYPE
        SYNTAX Counter64
        MAX-ACCESS read-only
        STATUS current
        DESCRIPTION
            "Usage Warn Limit of queues."
        ::= { fsMmuIfQueueSupportEntry 8 }

fsMmuIfQueueSupportUsageWarnCount OBJECT-TYPE
        SYNTAX Counter64
        MAX-ACCESS read-only
        STATUS current
        DESCRIPTION
            "Usage Warn Count of queues."
        ::= { fsMmuIfQueueSupportEntry 9 }

fsMmuIfQueueSupportPeakedCells OBJECT-TYPE
        SYNTAX Counter64
        MAX-ACCESS read-only
        STATUS current
        DESCRIPTION
            "Peaked Cells of queues."
        ::= { fsMmuIfQueueSupportEntry 10 }

-- mmu multicast queue support
fsMmuIfMulticastQueueSupportTable OBJECT-TYPE
        SYNTAX SEQUENCE OF FSMmuIfMulticastQueueSupportEntry
        MAX-ACCESS not-accessible
        STATUS current
        DESCRIPTION
            "List multicast queues of interfaces."
        ::= { fsMMUMIB 6 }

fsMmuIfMulticastQueueSupportEntry OBJECT-TYPE
        SYNTAX FSMmuIfMulticastQueueSupportEntry
        MAX-ACCESS not-accessible
        STATUS current
        DESCRIPTION
            "Multicast Queue Entry."
        INDEX { fsMmuIfIndexMulticast, fsMmuIfMulticastQueueIndex, fsMmuIfSliceIndexMulticast}
        ::= { fsMmuIfMulticastQueueSupportTable 1 }

FSMmuIfMulticastQueueSupportEntry ::=
        SEQUENCE {
            fsMmuIfIndexMulticast IfIndex,
            fsMmuIfMulticastQueueIndex Integer32,
            fsMmuIfSliceIndexMulticast Integer32,
      	    fsMmuIfMulticastQueueSupportUsedCells Counter64,
            fsMmuIfMulticastQueueSupportAvailableCells Counter64,
            fsMmuIfMulticastQueueSupportTotalCells Counter64,
            fsMmuIfMulticastQueueSupportUsage Counter64,
            fsMmuIfMulticastQueueSupportUsageWarnLimit Counter64,
            fsMmuIfMulticastQueueSupportUsageWarnCount Counter64,
            fsMmuIfMulticastQueueSupportPeakedCells Counter64
        }

fsMmuIfIndexMulticast OBJECT-TYPE
        SYNTAX IfIndex
        MAX-ACCESS read-only
        STATUS current
        DESCRIPTION
            "Interface index."
        ::= { fsMmuIfMulticastQueueSupportEntry 1 }

fsMmuIfMulticastQueueIndex OBJECT-TYPE
        SYNTAX Integer32
        MAX-ACCESS read-only
        STATUS current
        DESCRIPTION
            "Multicast Queue index."
        ::= { fsMmuIfMulticastQueueSupportEntry 2 }

fsMmuIfSliceIndexMulticast OBJECT-TYPE
        SYNTAX Integer32
        MAX-ACCESS read-only
        STATUS current
        DESCRIPTION
            "Slice of index."
        ::= { fsMmuIfMulticastQueueSupportEntry 3 }


fsMmuIfMulticastQueueSupportUsedCells OBJECT-TYPE
        SYNTAX Counter64
        MAX-ACCESS read-only
        STATUS current
        DESCRIPTION
            "Used Cells of multicast queues."
        ::= { fsMmuIfMulticastQueueSupportEntry 4 }

fsMmuIfMulticastQueueSupportAvailableCells OBJECT-TYPE
        SYNTAX Counter64
        MAX-ACCESS read-only
        STATUS current
        DESCRIPTION
            "Available Cells of multicast queues."
        ::= { fsMmuIfMulticastQueueSupportEntry 5 }

fsMmuIfMulticastQueueSupportTotalCells OBJECT-TYPE
        SYNTAX Counter64
        MAX-ACCESS read-only
        STATUS current
        DESCRIPTION
            "size of multicast queues."
        ::= { fsMmuIfMulticastQueueSupportEntry 6 }

fsMmuIfMulticastQueueSupportUsage OBJECT-TYPE
        SYNTAX Counter64
        MAX-ACCESS read-only
        STATUS current
        DESCRIPTION
            "Usage of multicast queues."
        ::= { fsMmuIfMulticastQueueSupportEntry 7 }


fsMmuIfMulticastQueueSupportUsageWarnLimit OBJECT-TYPE
        SYNTAX Counter64
        MAX-ACCESS read-only
        STATUS current
        DESCRIPTION
            "Usage Warn Limit of multicast queues."
        ::= { fsMmuIfMulticastQueueSupportEntry 8 }

fsMmuIfMulticastQueueSupportUsageWarnCount OBJECT-TYPE
        SYNTAX Counter64
        MAX-ACCESS read-only
        STATUS current
        DESCRIPTION
            "Usage Warn Count of multicast queues."
        ::= { fsMmuIfMulticastQueueSupportEntry 9 }


fsMmuIfMulticastQueueSupportPeakedCells OBJECT-TYPE
        SYNTAX Counter64
        MAX-ACCESS read-only
        STATUS current
        DESCRIPTION
            "Usage Warn Limit of multicast queues."
        ::= { fsMmuIfMulticastQueueSupportEntry 10 }

-- Mmu if  Priority Group Support
fsMmuIfPriorityGroupSupportTable OBJECT-TYPE
        SYNTAX SEQUENCE OF FSMmuIfPriorityGroupSupportEntry
        MAX-ACCESS not-accessible
        STATUS current
        DESCRIPTION
            "Priority Group of interfaces."
        ::= { fsMMUMIB 7 }

fsMmuIfPriorityGroupSupportEntry OBJECT-TYPE
        SYNTAX FSMmuIfPriorityGroupSupportEntry
        MAX-ACCESS not-accessible
        STATUS current
        DESCRIPTION
            "Priority Group Entry."
        INDEX { fsMmuIfIndexPriorityGroup, fsMmuIfPriorityGroupIdIndex, fsMmuIfSliceIndexPriorityGroup}
        ::= { fsMmuIfPriorityGroupSupportTable 1 }

FSMmuIfPriorityGroupSupportEntry ::=
        SEQUENCE {
            fsMmuIfIndexPriorityGroup IfIndex,
            fsMmuIfPriorityGroupIdIndex Integer32,
            fsMmuIfSliceIndexPriorityGroup Integer32,
      	    fsMmuIfPriorityGroupSupportUsedCells Counter64,
            fsMmuIfPriorityGroupSupportAvailableCells Counter64,
            fsMmuIfPriorityGroupSupportTotalCells Counter64,
            fsMmuIfPriorityGroupSupportUsage Counter64,
            fsMmuIfPriorityGroupSupportPeakedCells Counter64,
            fsMmuIfPriorityGroupSupportUsedHeadroom Counter64,
            fsMmuIfPriorityGroupSupportAvailableHeadroom Counter64,
            fsMmuIfPriorityGroupSupportPeakedHeadroom Counter64
        }

fsMmuIfIndexPriorityGroup OBJECT-TYPE
        SYNTAX IfIndex
        MAX-ACCESS read-only
        STATUS current
        DESCRIPTION
            "Interface of index."
        ::= { fsMmuIfPriorityGroupSupportEntry 1 }

fsMmuIfPriorityGroupIdIndex OBJECT-TYPE
        SYNTAX Integer32
        MAX-ACCESS read-only
        STATUS current
        DESCRIPTION
            "Priority Group Id of Index."
        ::= { fsMmuIfPriorityGroupSupportEntry 2 }

fsMmuIfSliceIndexPriorityGroup OBJECT-TYPE
        SYNTAX Integer32
        MAX-ACCESS read-only
        STATUS current
        DESCRIPTION
            "Slice of index."
        ::= { fsMmuIfPriorityGroupSupportEntry 3 }


fsMmuIfPriorityGroupSupportUsedCells OBJECT-TYPE
        SYNTAX Counter64
        MAX-ACCESS read-only
        STATUS current
        DESCRIPTION
            "Used Cells of Priority Group."
        ::= { fsMmuIfPriorityGroupSupportEntry 4 }

fsMmuIfPriorityGroupSupportAvailableCells OBJECT-TYPE
        SYNTAX Counter64
        MAX-ACCESS read-only
        STATUS current
        DESCRIPTION
            "Available Cells of Priority Group."
        ::= { fsMmuIfPriorityGroupSupportEntry 5 }

fsMmuIfPriorityGroupSupportTotalCells OBJECT-TYPE
        SYNTAX Counter64
        MAX-ACCESS read-only
        STATUS current
        DESCRIPTION
            "size of Priority Group."
        ::= { fsMmuIfPriorityGroupSupportEntry 6 }

fsMmuIfPriorityGroupSupportUsage OBJECT-TYPE
        SYNTAX Counter64
        MAX-ACCESS read-only
        STATUS current
        DESCRIPTION
            "Usage of Priority Group."
        ::= { fsMmuIfPriorityGroupSupportEntry 7 }

fsMmuIfPriorityGroupSupportPeakedCells OBJECT-TYPE
        SYNTAX Counter64
        MAX-ACCESS read-only
        STATUS current
        DESCRIPTION
            "Peaked Cells of Priority Group."
        ::= { fsMmuIfPriorityGroupSupportEntry 8 }

fsMmuIfPriorityGroupSupportUsedHeadroom OBJECT-TYPE
        SYNTAX Counter64
        MAX-ACCESS read-only
        STATUS current
        DESCRIPTION
            "Used Headroom of Priority Group."
        ::= { fsMmuIfPriorityGroupSupportEntry 9 }

fsMmuIfPriorityGroupSupportAvailableHeadroom OBJECT-TYPE
        SYNTAX Counter64
        MAX-ACCESS read-only
        STATUS current
        DESCRIPTION
            "Available Headroom of Priority Group."
        ::= { fsMmuIfPriorityGroupSupportEntry 10 }

fsMmuIfPriorityGroupSupportPeakedHeadroom OBJECT-TYPE
        SYNTAX Counter64
        MAX-ACCESS read-only
        STATUS current
        DESCRIPTION
            "Peaked Headroom of Priority Group."
        ::= { fsMmuIfPriorityGroupSupportEntry 11 }

END
