-- *****************************************************************
-- FS-SPAN-MIB.mib:  FS SPAN MIB file
--
-- March 2002, Wuzg
--
-- Copyright (c) 2002 by FS.COM Inc..
-- All rights reserved.
--
-- *****************************************************************
--

FS-SPAN-MIB DEFINITIONS ::= BEGIN

IMPORTS
        MODULE-IDENTITY,
        OBJECT-TYPE,
        Integer32
                FROM SNMPv2-SMI
        MODULE-COMPLIANCE,
        OBJECT-GROUP
                FROM SNMPv2-CONF
        ConfigStatus,
        IfIndex
                FROM FS-TC
        fsMgmt
                FROM FS-SMI;

fsSPANMIB MODULE-IDENTITY
        LAST-UPDATED "200203200000Z"
        ORGANIZATION "FS.COM Inc.."
        CONTACT-INFO
                "
                Tel: 400-865-2852

                E-mail: https://www.fs.com/live_chat_service_mail.html"
        DESCRIPTION
                "This module defines fs SPAN(Statistical Processing and Analysis)mibs."
        REVISION      "200203200000Z"
        DESCRIPTION
                "Initial version of this MIB module."
        ::= { fsMgmt 23}

fsSPANMIBObjects OBJECT IDENTIFIER ::= { fsSPANMIB 1 }


fsSPANSessionNum OBJECT-TYPE
        SYNTAX Integer32
        MAX-ACCESS read-only
        STATUS current
        DESCRIPTION
            "Max num of SPAN session which the system support."
        ::= { fsSPANMIBObjects 1 }

fsSPANTable OBJECT-TYPE
        SYNTAX SEQUENCE OF FSSPANEntry
        MAX-ACCESS not-accessible
        STATUS current
        DESCRIPTION
            "list of  SPAN configuration objects."
        ::= { fsSPANMIBObjects 2 }

fsSPANEntry OBJECT-TYPE
        SYNTAX FSSPANEntry
        MAX-ACCESS not-accessible
        STATUS current
        DESCRIPTION
            "Entry contains SPAN configuration objects."
        INDEX { fsSPANSession,fsSPANIfIndex}
        ::= { fsSPANTable 1 }

FSSPANEntry ::=
        SEQUENCE {
            fsSPANSession Integer32,
            fsSPANIfIndex IfIndex,
            fsSPANIfRole INTEGER,
            fsSPANEntryStatus ConfigStatus
        }
fsSPANSession OBJECT-TYPE
        SYNTAX Integer32
        MAX-ACCESS read-only
        STATUS current
        DESCRIPTION
            "Index of an association of a destination port with source ports or source."
        ::= { fsSPANEntry 1 }

fsSPANIfIndex OBJECT-TYPE
        SYNTAX IfIndex
        MAX-ACCESS read-only
        STATUS current
        DESCRIPTION
            " "
        ::= { fsSPANEntry 2 }

fsSPANIfRole OBJECT-TYPE
        SYNTAX INTEGER{
            span-desc(1),    -- a destination port (also called a monitoring port) that
                             -- receives a copy of traffic from the source port.
            span-src-rx(2),  -- A source port (also called a monitored port) which
                             -- the received packets is monitored.
            span-src-tx(3),  -- A source port (also called a monitored port) which
                             -- the transmitted packets  is monitored.
            span-src-all(4)  -- A source port (also called a monitored port) which
                             -- the received and transmitted packets  is all monitored.
        }
        MAX-ACCESS read-create
        STATUS current
        DESCRIPTION
            " Role of the interface in the SPAN session"
        ::= { fsSPANEntry 3 }

fsSPANEntryStatus OBJECT-TYPE
        SYNTAX ConfigStatus
        MAX-ACCESS read-create
        STATUS current
        DESCRIPTION
            "Status of this entry, set its value to invalid will delete the interface of
             this entry and set this object to valid will have no any effect"
        ::= { fsSPANEntry 4 }

fsSPANMIBConformance OBJECT IDENTIFIER ::= { fsSPANMIB 3 }
fsSPANMIBCompliances OBJECT IDENTIFIER ::= { fsSPANMIBConformance 1 }
fsSPANMIBGroups      OBJECT IDENTIFIER ::= { fsSPANMIBConformance 2 }


-- compliance statements

fsSPANMIBCompliance MODULE-COMPLIANCE
        STATUS  current
        DESCRIPTION
                "The compliance statement for entities which implement
                the FS IfConfig MIB"
        MODULE  -- this module
                MANDATORY-GROUPS { fsSPANMIBGroup
                 }
        ::= { fsSPANMIBCompliances 1 }

-- units of conformance

fsSPANMIBGroup OBJECT-GROUP
        OBJECTS {
            fsSPANSession,
            fsSPANIfIndex,
            fsSPANIfRole,
            fsSPANEntryStatus
        }
        STATUS  current
        DESCRIPTION
                "A collection of objects providing port SPAN configure."
        ::= { fsSPANMIBGroups 1 }

END
