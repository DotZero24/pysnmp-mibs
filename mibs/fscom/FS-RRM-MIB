-- *******************************************************************
-- FS-RRM-MIB.mib : FS RRM MIB file
-- November 2009, chenmingjin
--
-- Copyright (c) 2009 by FS.COM Inc..
-- All rights reserved.
-- *******************************************************************

FS-RRM-MIB DEFINITIONS ::= BEGIN

IMPORTS
        IpAddress,
        OBJECT-TYPE,
        MODULE-IDENTITY,
        NOTIFICATION-TYPE,
        Integer32,
        Unsigned32
                FROM SNMPv2-SMI
        MacAddress,
        DisplayString,
        TruthValue
                FROM SNMPv2-TC
        NOTIFICATION-GROUP,
        MODULE-COMPLIANCE,
        OBJECT-GROUP
                FROM SNMPv2-CONF
        fsMgmt
                FROM FS-SMI;

--********************************************************************
--  MODULE IDENTITY
--********************************************************************

fsRrmMIB MODULE-IDENTITY
    LAST-UPDATED "200912150000Z"
    ORGANIZATION "FS.COM Inc.."
    CONTACT-INFO
        "
    Tel: 400-865-2852

    E-mail: https://www.fs.com/live_chat_service_mail.html"
    DESCRIPTION
        "This module defines wlan rrm mibs."
    REVISION      "200912150000Z"
    DESCRIPTION
        "Initial version of this MIB module."
    ::= { fsMgmt 63 }


--********************** define the Rrm root nodes ***************************
fsRrmMIBObjects     OBJECT IDENTIFIER     ::= { fsRrmMIB 1 }
fsRrmMIBTraps       OBJECT IDENTIFIER     ::= { fsRrmMIB 2 }
fsRrmMIBConformance OBJECT IDENTIFIER     ::= { fsRrmMIB 3 }


--***************** define the fsRrmMIBObjects nodes *********************
fsRrmObjectsGroup   OBJECT IDENTIFIER      ::= { fsRrmMIBObjects 1 }
fsRrmObjectsDot11a  OBJECT IDENTIFIER      ::= { fsRrmMIBObjects 2 }
fsRrmObjectsDot11b  OBJECT IDENTIFIER      ::= { fsRrmMIBObjects 3 }
fsRrmObjectsAP     	OBJECT IDENTIFIER      ::= { fsRrmMIBObjects 4 }

--***************** define the fsRrmObjectsDot11a nodes *****************
fsRrmDCADot11a      OBJECT IDENTIFIER      ::= { fsRrmObjectsDot11a 1 }
fsRrmTPCDot11a      OBJECT IDENTIFIER      ::= { fsRrmObjectsDot11a 2 }
fsRrmCHDDot11a      OBJECT IDENTIFIER      ::= { fsRrmObjectsDot11a 3 }
fsRrmGroupDot11a    OBJECT IDENTIFIER      ::= { fsRrmObjectsDot11a 4 }
fsRrmProfileDot11a  OBJECT IDENTIFIER      ::= { fsRrmObjectsDot11a 5 }
fsRrmMonitorDot11a  OBJECT IDENTIFIER      ::= { fsRrmObjectsDot11a 6 }
fsRrmFactoryDot11a  OBJECT IDENTIFIER      ::= { fsRrmObjectsDot11a 7 }

--***************** define the fsRrmObjectsDot11a nodes *****************
fsRrmDCADot11b      OBJECT IDENTIFIER      ::= { fsRrmObjectsDot11b 1 }
fsRrmTPCDot11b      OBJECT IDENTIFIER      ::= { fsRrmObjectsDot11b 2 }
fsRrmCHDDot11b      OBJECT IDENTIFIER      ::= { fsRrmObjectsDot11b 3 }
fsRrmGroupDot11b    OBJECT IDENTIFIER      ::= { fsRrmObjectsDot11b 4 }
fsRrmProfileDot11b  OBJECT IDENTIFIER      ::= { fsRrmObjectsDot11b 5 }
fsRrmMonitorDot11b  OBJECT IDENTIFIER      ::= { fsRrmObjectsDot11b 6 }
fsRrmFactoryDot11b  OBJECT IDENTIFIER      ::= { fsRrmObjectsDot11b 7 }


--********************************************************************
--                                                                  **
--                           Rf group name                          **
--                                                                  **
--********************************************************************

fsRrmRFNetworkName OBJECT-TYPE
    SYNTAX      DisplayString (SIZE(1..19))
    MAX-ACCESS  read-write
    STATUS      current
    DESCRIPTION
        "RF Network Group Name to which this FS Switch belongs.
         Airespace Switches on a network form a RF Network Group as
         well as a Mobility Group. RF Network Groups does the channel
         and power management of AP while Mobility Group does load
         balancing and hand off for clients."
    ::= { fsRrmObjectsGroup 1 }


--********************************************************************
--                                                                  **
--                       AP Profile Display                         **
--                                                                  **
--********************************************************************
ProfileState ::= INTEGER { pass (1), fail (0) }

fsRrmAPIfSlotId OBJECT-TYPE
    SYNTAX 			INTEGER(1..32)
    MAX-ACCESS 	read-only
    STATUS 			current
    DESCRIPTION
        		"Number of Radio Interfaces on the Airespace AP.
         		Currently maximum two interfaces are supported.
         		One would be of type 802.11a and other of type
         		802.11b/g."
    ::= {  fsRrmObjectsAP 1 }

fsRrmAPName OBJECT-TYPE
    SYNTAX 			DisplayString (SIZE(1..32))
    MAX-ACCESS 	read-only
    STATUS 			current
    DESCRIPTION
        		"Name assigned to this AP. If an AP is not configured its
         		factory default name will be ap:<last three byte of
         		MACAddress> eg. ap:af:12:be"
    ::= { fsRrmObjectsAP 2 }


--********************************************************************
-- * Begin of fsRrmAPIfProfileThresholdConfigTable
--********************************************************************

fsRrmAPIfProfileThresholdConfigTable OBJECT-TYPE
		SYNTAX 			SEQUENCE OF FSRrmAPIfProfileThresholdConfigEntry
		MAX-ACCESS 	not-accessible
		STATUS 			current
		DESCRIPTION
        		"Table of attributes for various thresholds to be
         		set on each Airespace AP Interface for Load
        		performance profile , interference performance
        		profile and Noise performance profile."
		::= { fsRrmObjectsAP 3 }

fsRrmAPIfProfileThresholdConfigEntry OBJECT-TYPE
		SYNTAX 			FSRrmAPIfProfileThresholdConfigEntry
 		MAX-ACCESS 	not-accessible
  	STATUS 			current
  	DESCRIPTION
         		"An entry (conceptual row) in the Phy Thresholds
          	Table. Entries in this MIB are indexed by
        		fsRrmAPDot3MacAddress and fsRrmAPIfSlotId"
   	INDEX { fsRrmAPIfThresholdMacAddr, fsRrmAPIfThresholdRadioType }
    ::= { fsRrmAPIfProfileThresholdConfigTable 1 }

FSRrmAPIfProfileThresholdConfigEntry ::=
     	SEQUENCE {
     				fsRrmAPIfThresholdMacAddr    MacAddress,
            fsRrmAPIfThresholdRadioType  INTEGER,
            fsRrmAPIfThresholdName DisplayString,
            fsRrmAPIfForeignInterferenceThreshold INTEGER,
            fsRrmAPIfForeignNoiseThreshold        INTEGER,
            fsRrmAPIfRFUtilizationThreshold       INTEGER,
            fsRrmAPIfThroughputThreshold          Unsigned32,
            fsRrmAPIfMobilesThreshold             INTEGER,
            fsRrmAPIfForeignGlobalConfig          INTEGER,
            fsRrmAPIfNoiseGlobalConfig            INTEGER,
            fsRrmAPIfRFUtilizationGlobalConfig    INTEGER,
            fsRrmAPIfThroughputGlobalConfig       INTEGER,
            fsRrmAPIfMobilesGlobalConfig          INTEGER
		}

fsRrmAPIfThresholdRadioType OBJECT-TYPE
    SYNTAX 			INTEGER {type80211a(0),type80211b(1)}
    MAX-ACCESS 	read-only
    STATUS 			current
    DESCRIPTION
      			"radio type, type 802.11b means 2.4GHz, type 802.11a means 5GHz,"
		::= {fsRrmAPIfProfileThresholdConfigEntry 1 }

fsRrmAPIfForeignInterferenceThreshold OBJECT-TYPE
    SYNTAX 			INTEGER(1..100)
    MAX-ACCESS 	read-write
    STATUS 			current
    DESCRIPTION
      			"foreign interference threshold between 1 and 100 percent."
		::= {fsRrmAPIfProfileThresholdConfigEntry 2 }

fsRrmAPIfForeignNoiseThreshold OBJECT-TYPE
    SYNTAX 			INTEGER(-127..0)
    MAX-ACCESS 	read-write
    STATUS 			current
    DESCRIPTION
     				"foreign noise threshold between -127 and 0 dBm."
   	::= {fsRrmAPIfProfileThresholdConfigEntry 3 }

fsRrmAPIfRFUtilizationThreshold OBJECT-TYPE
    SYNTAX 			INTEGER(1..100)
    MAX-ACCESS 	read-write
    STATUS 			current
    DESCRIPTION
    				"RF utlization threshold between 1 and 100 percent."
		::= {fsRrmAPIfProfileThresholdConfigEntry 4 }

fsRrmAPIfThroughputThreshold OBJECT-TYPE
    SYNTAX 			Unsigned32(1000..10000000)
    MAX-ACCESS 	read-write
    STATUS 			current
    DESCRIPTION
    				" Airespace AP data-rate threshold between 1000 and 1000000000."
		::= {fsRrmAPIfProfileThresholdConfigEntry 5 }

fsRrmAPIfMobilesThreshold OBJECT-TYPE
    SYNTAX 			INTEGER(1..128)
    MAX-ACCESS 	read-write
    STATUS 			current
    DESCRIPTION
    				" Airespace AP mobiles threshold between 1 and 128."
		::= {fsRrmAPIfProfileThresholdConfigEntry 6 }

fsRrmAPIfThresholdName OBJECT-TYPE
    SYNTAX 			DisplayString (SIZE(1..32))
    MAX-ACCESS 	read-only
    STATUS 			current
    DESCRIPTION
        		"The name of the AP"
    ::= { fsRrmAPIfProfileThresholdConfigEntry 7 }

fsRrmAPIfThresholdMacAddr OBJECT-TYPE
    SYNTAX      MacAddress
    MAX-ACCESS  read-only
    STATUS      current
    DESCRIPTION
            "The MAC address of radio on the AP"
    ::= { fsRrmAPIfProfileThresholdConfigEntry 8 }

fsRrmAPIfForeignGlobalConfig OBJECT-TYPE
    SYNTAX 			INTEGER(0..1)
    MAX-ACCESS  read-write
    STATUS      current
    DESCRIPTION
            "Interference threshold inherited from global or not, 1: global config, 0: ap config"
    ::= { fsRrmAPIfProfileThresholdConfigEntry 9 }

fsRrmAPIfNoiseGlobalConfig OBJECT-TYPE
    SYNTAX 			INTEGER(0..1)
    MAX-ACCESS  read-write
    STATUS      current
    DESCRIPTION
            "Noise threshold inherited from global or not, 1: global config, 0: ap config"
    ::= { fsRrmAPIfProfileThresholdConfigEntry 10 }

fsRrmAPIfRFUtilizationGlobalConfig OBJECT-TYPE
    SYNTAX 			INTEGER(0..1)
    MAX-ACCESS  read-write
    STATUS      current
    DESCRIPTION
            "RFUtilization threshold inherited from global or not, 1: global config, 0: ap config"
    ::= { fsRrmAPIfProfileThresholdConfigEntry 11 }

fsRrmAPIfThroughputGlobalConfig OBJECT-TYPE
    SYNTAX 			INTEGER(0..1)
    MAX-ACCESS  read-write
    STATUS      current
    DESCRIPTION
            "Throughput threshold inherited from global or not, 1: global config, 0: ap config"
    ::= { fsRrmAPIfProfileThresholdConfigEntry 12 }

fsRrmAPIfMobilesGlobalConfig OBJECT-TYPE
    SYNTAX 			INTEGER(0..1)
    MAX-ACCESS  read-write
    STATUS      current
    DESCRIPTION
            "Mobiles threshold inherited from global or not, 1: global config, 0: ap config"
    ::= { fsRrmAPIfProfileThresholdConfigEntry 13 }

--********************************************************************
-- * Begin of fsRrmAPIfLoadParametersTable
--********************************************************************
fsRrmAPIfLoadParametersTable OBJECT-TYPE
		SYNTAX 			SEQUENCE OF FSRrmAPIfLoadParametersEntry
		MAX-ACCESS 	not-accessible
		STATUS 			current
		DESCRIPTION
        		"These are RRM performance related read only parameters
        		per Airespace AP"
		::= { fsRrmObjectsAP 4 }

fsRrmAPIfLoadParametersEntry OBJECT-TYPE
		SYNTAX 			FSRrmAPIfLoadParametersEntry
		MAX-ACCESS 	not-accessible
		STATUS 			current
		DESCRIPTION
          	"An entry (conceptual row) in the Table.
          	Entries in this MIB are indexed by
         	fsRrmAPDot3MacAddress and fsRrmAPIfSlotId"
 		INDEX { fsRrmAPIfLoadMacAddr, fsRrmAPIfLoadSlotId }
 		::= { fsRrmAPIfLoadParametersTable 1 }

FSRrmAPIfLoadParametersEntry ::=
  	SEQUENCE {
  	    fsRrmAPIfLoadName DisplayString,
        fsRrmAPIfLoadMacAddr MacAddress,
        fsRrmAPIfLoadSlotId INTEGER,
     		fsRrmAPIfLoadRxUtilization        INTEGER,
   			fsRrmAPIfLoadTxUtilization        INTEGER,
  			fsRrmAPIfLoadChannelUtilization   INTEGER,
   			fsRrmAPIfLoadNumOfClients         Integer32,
   			fsRrmAPIfPoorSNRClients           Integer32,
   			fsRrmAPIfThroughput		      INTEGER
		}

fsRrmAPIfLoadRxUtilization OBJECT-TYPE
		SYNTAX 			INTEGER(0..100)
		MAX-ACCESS 	read-only
		STATUS 			current
		DESCRIPTION
      			"This is the percentage of time the Airespace AP
        		receiver is busy operating on packets. It is a number
       			from 0-100 representing a load from 0 to 1."
		::= { fsRrmAPIfLoadParametersEntry 1 }

fsRrmAPIfLoadTxUtilization OBJECT-TYPE
 		SYNTAX 			INTEGER(0..100)
		MAX-ACCESS 	read-only
		STATUS 			current
		DESCRIPTION
      			"This is the percentage of time the Airespace AP
         		transmitter is busy operating on packets. It is a
       			number from 0-100 representing a load from 0 to 1."
		::= { fsRrmAPIfLoadParametersEntry 2 }

fsRrmAPIfLoadChannelUtilization OBJECT-TYPE
    SYNTAX 			INTEGER(0..100)
    MAX-ACCESS 	read-only
    STATUS 			current
    DESCRIPTION
            "Channel Utilization"
    ::= { fsRrmAPIfLoadParametersEntry 3 }

fsRrmAPIfLoadNumOfClients OBJECT-TYPE
		SYNTAX 			Integer32
   	MAX-ACCESS 	read-only
   	STATUS 			current
   	DESCRIPTION
         		"This is the number of clients attached to this Airespace
        		AP at the last measurement interval(This comes from
        		APF)"
    ::= { fsRrmAPIfLoadParametersEntry 4 }

fsRrmAPIfPoorSNRClients OBJECT-TYPE
		SYNTAX 			Integer32
		MAX-ACCESS 	read-only
		STATUS 			current
		DESCRIPTION
           	"This is the number of clients with poor SNR attached to
          	this Airespace AP at the last measurement interval
          	( This comes from APF )."
		::= { fsRrmAPIfLoadParametersEntry 5 }

fsRrmAPIfLoadName OBJECT-TYPE
    SYNTAX 			DisplayString (SIZE(1..32))
    MAX-ACCESS 	read-only
    STATUS 			current
    DESCRIPTION
        		"The name of the AP"
    ::= { fsRrmAPIfLoadParametersEntry 6 }

fsRrmAPIfLoadMacAddr OBJECT-TYPE
    SYNTAX      MacAddress
    MAX-ACCESS  read-only
    STATUS      current
    DESCRIPTION
            "The MAC address of radio on the AP"
    ::= { fsRrmAPIfLoadParametersEntry 7 }

fsRrmAPIfLoadSlotId OBJECT-TYPE
    SYNTAX 			INTEGER(1..32)
    MAX-ACCESS 	read-only
    STATUS 			current
    DESCRIPTION
        		"Number of Radio Interfaces on the Airespace AP.
         		Currently maximum two interfaces are supported.
         		One would be of type 802.11a and other of type
         		802.11b/g."
    ::= {  fsRrmAPIfLoadParametersEntry 8 }

fsRrmAPIfThroughput OBJECT-TYPE
    SYNTAX 			INTEGER
    MAX-ACCESS 	read-only
    STATUS 			current
    DESCRIPTION
        		"Throughput in ap's radio, it represent the performance of
        		ap"
    ::= {  fsRrmAPIfLoadParametersEntry 9 }


--********************************************************************
-- * Begin of fsRrmAPIfChannelInterferenceInfoTable
--********************************************************************

fsRrmAPIfChannelInterferenceInfoTable OBJECT-TYPE
		SYNTAX 			SEQUENCE OF FSRrmAPIfChannelInterferenceInfoEntry
		MAX-ACCESS 	not-accessible
		STATUS 			current
		DESCRIPTION
         		"This is a table of channel information like interference
         		and noise from other 802.11 networks on each channel."
		::= { fsRrmObjectsAP 5 }

fsRrmAPIfChannelInterferenceInfoEntry OBJECT-TYPE
 		SYNTAX 			FSRrmAPIfChannelInterferenceInfoEntry
 		MAX-ACCESS 	not-accessible
  	STATUS 			current
		DESCRIPTION
        		"An entry (conceptual row) in the Table.
          	Entries in this MIB are indexed by
        		fsRrmAPDot3MacAddress, fsRrmAPIfSlotId"
		INDEX { fsRrmAPIfInterferenceMacAddr, fsRrmAPIfInterferenceSlotId,
                fsRrmAPIfInterferenceChannelNo}
		::= { fsRrmAPIfChannelInterferenceInfoTable 1 }

FSRrmAPIfChannelInterferenceInfoEntry ::=
    SEQUENCE {
        fsRrmAPIfInterferenceName DisplayString,
        fsRrmAPIfInterferenceMacAddr MacAddress,
        fsRrmAPIfInterferenceSlotId INTEGER,
    		fsRrmAPIfInterferenceChannelNo     		Integer32,
    		fsRrmAPIfInterferencePower         		Integer32,
    		fsRrmAPIfInterferenceUtilization   		INTEGER
    }

fsRrmAPIfInterferenceChannelNo OBJECT-TYPE
  	SYNTAX 			Integer32
   	MAX-ACCESS 	read-only
   	STATUS 			current
   	DESCRIPTION
           	"Channel Number on AP"
    ::= { fsRrmAPIfChannelInterferenceInfoEntry 1}

fsRrmAPIfInterferencePower OBJECT-TYPE
		SYNTAX 			Integer32
		MAX-ACCESS 	read-only
		STATUS 			current
		DESCRIPTION
		       "Power of Interference from other 802.11 networks on
		        this channel"
		::= { fsRrmAPIfChannelInterferenceInfoEntry 2}

fsRrmAPIfInterferenceUtilization OBJECT-TYPE
		SYNTAX 			INTEGER(0..100)
		MAX-ACCESS 	read-only
		STATUS 			current
		DESCRIPTION
						"Interference from other 802.11 networks on this
		        channel"
		::= { fsRrmAPIfChannelInterferenceInfoEntry 3}

fsRrmAPIfInterferenceName OBJECT-TYPE
    SYNTAX 			DisplayString (SIZE(1..32))
    MAX-ACCESS 	read-only
    STATUS 			current
    DESCRIPTION
        		"The name of the AP"
    ::= { fsRrmAPIfChannelInterferenceInfoEntry 4 }

fsRrmAPIfInterferenceMacAddr OBJECT-TYPE
    SYNTAX      MacAddress
    MAX-ACCESS  read-only
    STATUS      current
    DESCRIPTION
            "The MAC address of radio on the AP"
    ::= { fsRrmAPIfChannelInterferenceInfoEntry 5 }

fsRrmAPIfInterferenceSlotId OBJECT-TYPE
    SYNTAX 			INTEGER(1..32)
    MAX-ACCESS 	read-only
    STATUS 			current
    DESCRIPTION
        		"Number of Radio Interfaces on the Airespace AP.
         		Currently maximum two interfaces are supported.
         		One would be of type 802.11a and other of type
         		802.11b/g."
    ::= {  fsRrmAPIfChannelInterferenceInfoEntry 6 }

--********************************************************************
-- * Begin of fsRrmAPIfChannelNoiseInfoTable
--********************************************************************
fsRrmAPIfChannelNoiseInfoTable OBJECT-TYPE
		SYNTAX 			SEQUENCE OF FSRrmAPIfChannelNoiseInfoEntry
		MAX-ACCESS 	not-accessible
		STATUS 			current
		DESCRIPTION
          	"This is a table of channel information like
         		interference and noise from other 802.11 networks on
          	each channel."
		::= { fsRrmObjectsAP 6 }

fsRrmAPIfChannelNoiseInfoEntry OBJECT-TYPE
  	SYNTAX FSRrmAPIfChannelNoiseInfoEntry
  	MAX-ACCESS not-accessible
 		STATUS current
 		DESCRIPTION
          	"An entry (conceptual row) in the Table.
           	Entries in this MIB are indexed by fsRrmAPDot3MacAddress,
           	fsRrmAPIfSlotId"
  	INDEX { fsRrmAPIfNoiseMacAddr, fsRrmAPIfNoiseSlotId,
               fsRrmAPIfNoiseChannelNo }
 		::= { fsRrmAPIfChannelNoiseInfoTable 1 }

FSRrmAPIfChannelNoiseInfoEntry ::=
		SEQUENCE {
		    fsRrmAPIfNoiseName DisplayString,
        fsRrmAPIfNoiseMacAddr MacAddress,
        fsRrmAPIfNoiseSlotId INTEGER,
     		fsRrmAPIfNoiseChannelNo         	Integer32,
 				fsRrmAPIfDBNoisePower          		Integer32
		}

fsRrmAPIfNoiseChannelNo OBJECT-TYPE
		SYNTAX 			Integer32
 		MAX-ACCESS 	read-only
   	STATUS 			current
  	DESCRIPTION
           	"Channel Number on AP"
    ::= { fsRrmAPIfChannelNoiseInfoEntry 1 }

fsRrmAPIfDBNoisePower OBJECT-TYPE
 		SYNTAX 			Integer32
		MAX-ACCESS 	read-only
		STATUS 			current
		DESCRIPTION
        		"This is the average noise power in dBm on
          	each channel that is available to Airespace AP"
    ::= { fsRrmAPIfChannelNoiseInfoEntry 2 }

fsRrmAPIfNoiseName OBJECT-TYPE
    SYNTAX 			DisplayString (SIZE(1..32))
    MAX-ACCESS 	read-only
    STATUS 			current
    DESCRIPTION
        		"The name of the AP"
    ::= { fsRrmAPIfChannelNoiseInfoEntry 3 }

fsRrmAPIfNoiseMacAddr OBJECT-TYPE
    SYNTAX      MacAddress
    MAX-ACCESS  read-only
    STATUS      current
    DESCRIPTION
            "The MAC address of radio on the AP"
    ::= { fsRrmAPIfChannelNoiseInfoEntry 4 }

fsRrmAPIfNoiseSlotId OBJECT-TYPE
    SYNTAX 			INTEGER(1..32)
    MAX-ACCESS 	read-only
    STATUS 			current
    DESCRIPTION
        		"Number of Radio Interfaces on the Airespace AP.
         		Currently maximum two interfaces are supported.
         		One would be of type 802.11a and other of type
         		802.11b/g."
    ::= {  fsRrmAPIfChannelNoiseInfoEntry 5 }

--********************************************************************
-- * Begin of fsRrmAPIfProfileStateTable
--********************************************************************

fsRrmAPIfProfileStateTable OBJECT-TYPE
		SYNTAX 			SEQUENCE OF FSRrmAPIfProfileStateEntry
		MAX-ACCESS 	not-accessible
		STATUS 			current
		DESCRIPTION
		        "This is a table of state of interference monitor
		         on each Airespace AP"
		::= { fsRrmObjectsAP 7 }

fsRrmAPIfProfileStateEntry OBJECT-TYPE
		SYNTAX 			FSRrmAPIfProfileStateEntry
		MAX-ACCESS 	not-accessible
		STATUS 			current
		DESCRIPTION
		       "An entry (conceptual row) in the Table.
		        Entries in this MIB are indexed by fsRrmAPDot3MacAddress,
		        fsRrmAPIfSlotId"
		INDEX { fsRrmAPIfProfileMacAddr, fsRrmAPIfProfileSlotId }
		::= { fsRrmAPIfProfileStateTable 1 }

FSRrmAPIfProfileStateEntry ::=
		SEQUENCE {
		    fsRrmAPIfProfileName DisplayString,
        fsRrmAPIfProfileMacAddr MacAddress,
        fsRrmAPIfProfileSlotId INTEGER,
        fsRrmAPIfLoadProfileState          	ProfileState,
        fsRrmAPIfInterferenceProfileState 	ProfileState,
        fsRrmAPIfNoiseProfileState         	ProfileState,
        fsRrmAPIfCoverageProfileState      	ProfileState,
        fsRrmAPIfPerformanceProfileState 		ProfileState
		}

fsRrmAPIfLoadProfileState OBJECT-TYPE
		SYNTAX 			ProfileState
		MAX-ACCESS 	read-only
		STATUS 			current
		DESCRIPTION
		        "This field represents the current state of the LOAD
		         monitor. This is a total measurement of the business of
		         this Airespace AP. PASS indicates that this Airespace
		         AP is performing adequately compared to the Airespace
		         AP profile. FAIL indicates the Airespace AP is not
		         performing adequately against the LOAD profile."
		::= { fsRrmAPIfProfileStateEntry 1 }


fsRrmAPIfInterferenceProfileState OBJECT-TYPE
		SYNTAX 			ProfileState
		MAX-ACCESS 	read-only
		STATUS 			current
		DESCRIPTION
		       "This field represents the current state of Interference
		        monitor. This is a total measurement of the interference
		        present at this Airespace AP. PASS indicates that this
		        Airespace AP is performing adequately compared to the
		        Interference profile.  FAIL indicates the Airespace AP
		        is not performing adequately against the Interference
		        profile."
		::= { fsRrmAPIfProfileStateEntry 2 }

fsRrmAPIfNoiseProfileState OBJECT-TYPE
		SYNTAX 			ProfileState
		MAX-ACCESS 	read-only
		STATUS 			current
		DESCRIPTION
						"This field represents the current state of Noise
						monitor. This is a total measurement of the noise
						present at this Airespace AP. PASS indicates that this
						Airespace AP is performing adequately compared to the
						noise profile.
						FAIL indicates the Airespace AP is not performing
						adequately against the noise profile."
		::= { fsRrmAPIfProfileStateEntry 3 }

fsRrmAPIfCoverageProfileState OBJECT-TYPE
		SYNTAX 			ProfileState
		MAX-ACCESS 	read-only
		STATUS 			current
		DESCRIPTION
		       "This field represents the current state of coverage
		        monitor. This is a total measurement of the client
		        coverage at this Airespace AP. PASS indicates that
		        this  Airespace AP is performing adequately compared
		        to the  coverage profile. FAIL indicates the Airespace
		        AP is not performing adequately against the coverage
		        profile."
		::= { fsRrmAPIfProfileStateEntry 4}

fsRrmAPIfPerformanceProfileState OBJECT-TYPE
		SYNTAX 			ProfileState
		MAX-ACCESS 	read-only
		STATUS 			current
		DESCRIPTION
		       ""
		::= { fsRrmAPIfProfileStateEntry 5}

fsRrmAPIfProfileName OBJECT-TYPE
    SYNTAX 			DisplayString (SIZE(1..32))
    MAX-ACCESS 	read-only
    STATUS 			current
    DESCRIPTION
        		"The name of the AP"
    ::= { fsRrmAPIfProfileStateEntry 6 }

fsRrmAPIfProfileMacAddr OBJECT-TYPE
    SYNTAX      MacAddress
    MAX-ACCESS  read-only
    STATUS      current
    DESCRIPTION
            "The MAC address of radio on the AP"
    ::= { fsRrmAPIfProfileStateEntry 7 }

fsRrmAPIfProfileSlotId OBJECT-TYPE
    SYNTAX 			INTEGER(1..32)
    MAX-ACCESS 	read-only
    STATUS 			current
    DESCRIPTION
        		"Number of Radio Interfaces on the Airespace AP.
         		Currently maximum two interfaces are supported.
         		One would be of type 802.11a and other of type
         		802.11b/g."
    ::= {  fsRrmAPIfProfileStateEntry 8 }

--********************************************************************
-- * Begin of fsRrmAPIfRxNeighborsTable
--********************************************************************
fsRrmAPIfRxNeighborsTable OBJECT-TYPE
		SYNTAX 			SEQUENCE OF FSRrmAPIfRxNeighborsEntry
		MAX-ACCESS 	not-accessible
		STATUS 			current
		DESCRIPTION
		        "This is a table of Rx Neighbors for each Airespace AP
		         with their RSSI value."
		::= { fsRrmObjectsAP 8 }

fsRrmAPIfRxNeighborsEntry OBJECT-TYPE
		SYNTAX 			FSRrmAPIfRxNeighborsEntry
		MAX-ACCESS 	not-accessible
		STATUS 			current
		DESCRIPTION
		        "An entry (conceptual row) in the Table.
		         Entries in this MIB are indexed by fsRrmAPDot3MacAddress
		         fsRrmAPIfSlotId, fsRrmAPIfRxNeighborMacAddress"
		INDEX { fsRrmAPIfRxNeighborMacAddr, fsRrmAPIfRxNeighborSlotId,
		        fsRrmAPIfRxNeighborMacAddress, fsRrmAPIfRxNeighborSlot}
		::= { fsRrmAPIfRxNeighborsTable 1 }

FSRrmAPIfRxNeighborsEntry ::=
		SEQUENCE {
		    fsRrmAPIfRxNeighborName DisplayString,
        fsRrmAPIfRxNeighborMacAddr MacAddress,
        fsRrmAPIfRxNeighborSlotId INTEGER,
				fsRrmAPIfRxNeighborMacAddress          	MacAddress,
				fsRrmAPIfRxNeighborSlot                	Integer32,
				fsRrmAPIfRxNeighborIpAddress           	IpAddress,
				fsRrmAPIfRxNeighborRSSI                	Integer32,
				fsRrmAPIfRxNeighborSNR                	Integer32,
				fsRrmAPIfRxNeighborChannel             	Integer32,
				fsRrmAPIfRxNeighborChannelWidth        	INTEGER
		}

fsRrmAPIfRxNeighborMacAddress OBJECT-TYPE
		SYNTAX 			MacAddress
		MAX-ACCESS 	read-only
		STATUS 			current
		DESCRIPTION
		   			"MAC Address of Rx Neighbor of the Airespace AP"
		::= { fsRrmAPIfRxNeighborsEntry 1 }

fsRrmAPIfRxNeighborSlot OBJECT-TYPE
		SYNTAX 			Integer32
		MAX-ACCESS 	read-only
		STATUS 			current
		DESCRIPTION
		       "Slot value of the Rx Neighbor"
		::= { fsRrmAPIfRxNeighborsEntry 2 }

fsRrmAPIfRxNeighborIpAddress OBJECT-TYPE
		SYNTAX 			IpAddress
		MAX-ACCESS 	read-only
		STATUS 			current
		DESCRIPTION
		       "IP Address of Rx Neighbor of the Airespace AP"
		::= { fsRrmAPIfRxNeighborsEntry 3 }

fsRrmAPIfRxNeighborRSSI OBJECT-TYPE
		SYNTAX 			Integer32
		MAX-ACCESS 	read-only
		STATUS 			current
		DESCRIPTION
		       "RSSI value of the Rx Neighbor"
		::= { fsRrmAPIfRxNeighborsEntry 4 }

fsRrmAPIfRxNeighborSNR OBJECT-TYPE
		SYNTAX 			Integer32
		MAX-ACCESS 	read-only
		STATUS 			current
		DESCRIPTION
		       "SNR value of the Rx Neighbor"
		::= { fsRrmAPIfRxNeighborsEntry 5 }

fsRrmAPIfRxNeighborChannel OBJECT-TYPE
		SYNTAX  		Integer32
		MAX-ACCESS 	read-only
		STATUS 			current
		DESCRIPTION
		    		"This object represents Channel information which
		     		neighboring Access point is using."
		::= { fsRrmAPIfRxNeighborsEntry 6 }

fsRrmAPIfRxNeighborChannelWidth OBJECT-TYPE
		SYNTAX  		INTEGER {
		           five(1),
		           ten(2),
		           twenty(3),
		           aboveforty(4),
		           belowforty(5)
		}
		MAX-ACCESS 	read-only
		STATUS 			current
		DESCRIPTION
		    		"This object represents Channel bandwidth information
		     		which neighboring Access point is using."
		::= { fsRrmAPIfRxNeighborsEntry 7 }

fsRrmAPIfRxNeighborName OBJECT-TYPE
    SYNTAX 			DisplayString (SIZE(1..32))
    MAX-ACCESS 	read-only
    STATUS 			current
    DESCRIPTION
        		"The name of the AP"
    ::= { fsRrmAPIfRxNeighborsEntry 8 }

fsRrmAPIfRxNeighborMacAddr OBJECT-TYPE
    SYNTAX      MacAddress
    MAX-ACCESS  read-only
    STATUS      current
    DESCRIPTION
            "The MAC address of radio on the AP"
    ::= { fsRrmAPIfRxNeighborsEntry 9 }

fsRrmAPIfRxNeighborSlotId OBJECT-TYPE
    SYNTAX 			INTEGER(1..32)
    MAX-ACCESS 	read-only
    STATUS 			current
    DESCRIPTION
        		"Number of Radio Interfaces on the Airespace AP.
         		Currently maximum two interfaces are supported.
         		One would be of type 802.11a and other of type
         		802.11b/g."
    ::= {  fsRrmAPIfRxNeighborsEntry 10 }

-- *****************************************************************


--********************************************************************
-- * Begin of fsRrmAPIfStationRSSICoverageInfoTable
--********************************************************************
fsRrmAPIfStationRSSICoverageInfoTable OBJECT-TYPE
    SYNTAX 			SEQUENCE OF FSRrmAPIfStationRSSICoverageInfoEntry
    MAX-ACCESS 	not-accessible
    STATUS 			current
    DESCRIPTION
            "This is a table of channel information like interference
             and noise from other 802.11 networks on each channel."
    ::= { fsRrmObjectsAP 9 }

fsRrmAPIfStationRSSICoverageInfoEntry OBJECT-TYPE
		SYNTAX 			FSRrmAPIfStationRSSICoverageInfoEntry
		MAX-ACCESS 	not-accessible
		STATUS 			current
		DESCRIPTION
		       "An entry (conceptual row) in the Table.
		        Entries in this MIB are indexed by fsRrmAPDot3MacAddress,
		        fsRrmAPIfSlotId"
		INDEX { fsRrmAPIfStationRSSIMacAddr, fsRrmAPIfStationRSSISlotId,
		        fsRrmAPIfStationRSSICoverageIndex}
		::= { fsRrmAPIfStationRSSICoverageInfoTable 1 }

FSRrmAPIfStationRSSICoverageInfoEntry ::=
		SEQUENCE {
		    fsRrmAPIfStationRSSIName DisplayString,
        fsRrmAPIfStationRSSIMacAddr MacAddress,
        fsRrmAPIfStationRSSISlotId INTEGER,
				fsRrmAPIfStationRSSICoverageIndex     Integer32,
				fsRrmAPIfRSSILevel                    Integer32,
				fsRrmAPIfStationCountOnRSSI           Integer32
		}

fsRrmAPIfStationRSSICoverageIndex OBJECT-TYPE
		SYNTAX 			Integer32
		MAX-ACCESS 	read-only
		STATUS 			current
		DESCRIPTION
		       "RSSI Coverage Index on AP"
		::= { fsRrmAPIfStationRSSICoverageInfoEntry 1 }

fsRrmAPIfRSSILevel OBJECT-TYPE
		SYNTAX 			Integer32
		MAX-ACCESS 	read-only
		STATUS 			current
		DESCRIPTION
		       "RSSI Level"
		::= { fsRrmAPIfStationRSSICoverageInfoEntry 2 }

fsRrmAPIfStationCountOnRSSI OBJECT-TYPE
		SYNTAX 			Integer32
		MAX-ACCESS 	read-only
		STATUS 			current
		DESCRIPTION
		        "Number of stations on this RSSI Level"
		::= { fsRrmAPIfStationRSSICoverageInfoEntry 3 }

fsRrmAPIfStationRSSIName OBJECT-TYPE
    SYNTAX 			DisplayString (SIZE(1..32))
    MAX-ACCESS 	read-only
    STATUS 			current
    DESCRIPTION
        		"The name of the AP"
    ::= { fsRrmAPIfStationRSSICoverageInfoEntry 4 }

fsRrmAPIfStationRSSIMacAddr OBJECT-TYPE
    SYNTAX      MacAddress
    MAX-ACCESS  read-only
    STATUS      current
    DESCRIPTION
            "The MAC address of radio on the AP"
    ::= { fsRrmAPIfStationRSSICoverageInfoEntry 5 }

fsRrmAPIfStationRSSISlotId OBJECT-TYPE
    SYNTAX 			INTEGER(1..32)
    MAX-ACCESS 	read-only
    STATUS 			current
    DESCRIPTION
        		"Number of Radio Interfaces on the Airespace AP.
         		Currently maximum two interfaces are supported.
         		One would be of type 802.11a and other of type
         		802.11b/g."
    ::= {  fsRrmAPIfStationRSSICoverageInfoEntry 6 }

-- ********************************************************************
-- * Begin of fsRrmAPIfStationSNRCoverageInfoTable
-- ********************************************************************
fsRrmAPIfStationSNRCoverageInfoTable OBJECT-TYPE
		SYNTAX 			SEQUENCE OF FSRrmAPIfStationSNRCoverageInfoEntry
		MAX-ACCESS 	not-accessible
		STATUS 			current
		DESCRIPTION
		        "This is a table of Signal to Noise ratio Coverage
		         information on an AP Interface."
		::= { fsRrmObjectsAP 10 }

fsRrmAPIfStationSNRCoverageInfoEntry OBJECT-TYPE
		SYNTAX 			FSRrmAPIfStationSNRCoverageInfoEntry
		MAX-ACCESS 	not-accessible
		STATUS 			current
		DESCRIPTION
		       "An entry (conceptual row) in the Table.
		        Entries in this MIB are indexed by fsRrmAPDot3MacAddress,
		        fsRrmAPIfSlotId"
		INDEX { fsRrmAPIfStationSNRMacAddr, fsRrmAPIfStationSNRSlotId,
		        fsRrmAPIfStationSNRCoverageIndex}
		::= { fsRrmAPIfStationSNRCoverageInfoTable 1 }

FSRrmAPIfStationSNRCoverageInfoEntry ::=
		SEQUENCE {
		    fsRrmAPIfStationSNRName DisplayString,
        fsRrmAPIfStationSNRMacAddr MacAddress,
        fsRrmAPIfStationSNRSlotId INTEGER,
				fsRrmAPIfStationSNRCoverageIndex     	Integer32,
				fsRrmAPIfSNRLevel                 		Integer32,
				fsRrmAPIfStationCountOnSNR        		Integer32
		}

fsRrmAPIfStationSNRCoverageIndex OBJECT-TYPE
		SYNTAX 			Integer32
		MAX-ACCESS 	read-only
		STATUS 			current
		DESCRIPTION
		       "SNR Coverage Index on AP"
    ::= { fsRrmAPIfStationSNRCoverageInfoEntry 1}

fsRrmAPIfSNRLevel OBJECT-TYPE
		SYNTAX 			Integer32
		MAX-ACCESS 	read-only
		STATUS 			current
		DESCRIPTION
		       "SNR Level"
		::= { fsRrmAPIfStationSNRCoverageInfoEntry 2}

fsRrmAPIfStationCountOnSNR OBJECT-TYPE
    SYNTAX 			Integer32
    MAX-ACCESS 	read-only
    STATUS 			current
    DESCRIPTION
          "Number of stations on this SNR Level"
    ::= { fsRrmAPIfStationSNRCoverageInfoEntry 3}

fsRrmAPIfStationSNRName OBJECT-TYPE
    SYNTAX 			DisplayString (SIZE(1..32))
    MAX-ACCESS 	read-only
    STATUS 			current
    DESCRIPTION
        		"The name of the AP"
    ::= { fsRrmAPIfStationSNRCoverageInfoEntry 4 }

fsRrmAPIfStationSNRMacAddr OBJECT-TYPE
    SYNTAX      MacAddress
    MAX-ACCESS  read-only
    STATUS      current
    DESCRIPTION
            "The MAC address of radio on the AP"
    ::= { fsRrmAPIfStationSNRCoverageInfoEntry 5 }

fsRrmAPIfStationSNRSlotId OBJECT-TYPE
    SYNTAX 			INTEGER(1..32)
    MAX-ACCESS 	read-only
    STATUS 			current
    DESCRIPTION
        		"Number of Radio Interfaces on the Airespace AP.
         		Currently maximum two interfaces are supported.
         		One would be of type 802.11a and other of type
         		802.11b/g."
    ::= {  fsRrmAPIfStationSNRCoverageInfoEntry 6 }

-- ********************************************************************
-- * Begin of fsRrmAPIfRecommendedRFParametersTable
-- ********************************************************************
fsRrmAPIfRecommendedRFParametersTable OBJECT-TYPE
		SYNTAX 			SEQUENCE OF FSRrmAPIfRecommendedRFParametersEntry
		MAX-ACCESS 	not-accessible
		STATUS 			current
		DESCRIPTION
		  			" This table list Best Channel,Best TxPowerLevel,
		    		Best RTSThreshold,Best FragmentationThreshold etc
		    		for this AP Interface as determined by RRM."
		::= { fsRrmObjectsAP 11 }

fsRrmAPIfRecommendedRFParametersEntry OBJECT-TYPE
		SYNTAX 			FSRrmAPIfRecommendedRFParametersEntry
		MAX-ACCESS 	not-accessible
		STATUS 			current
		DESCRIPTION
		       "An entry (conceptual row) in the Table.
		        Entries in this MIB are indexed by fsRrmAPDot3MacAddress,
		        fsRrmAPIfSlotId"
		INDEX { fsRrmAPIfRecommendedMacAddr, fsRrmAPIfRecommendedSlotId}
    ::= { fsRrmAPIfRecommendedRFParametersTable 1 }

FSRrmAPIfRecommendedRFParametersEntry ::=
		SEQUENCE {
		    fsRrmAPIfRecommendedName DisplayString,
        fsRrmAPIfRecommendedMacAddr MacAddress,
        fsRrmAPIfRecommendedSlotId INTEGER,
				fsRrmAPIfRecommendedChannelNumber             Integer32,
				fsRrmAPIfRecommendedTxPowerLevel              Integer32,
				fsRrmAPIfRecommendedRTSThreshold              Integer32,
				fsRrmAPIfRecommendedFragmentationThreshold    Integer32
		}

fsRrmAPIfRecommendedChannelNumber OBJECT-TYPE
		SYNTAX 			Integer32
		MAX-ACCESS 	read-only
		STATUS 			current
		DESCRIPTION
		       "Recommended ChannelNumber by RRM for this APIf"
		::= { fsRrmAPIfRecommendedRFParametersEntry 1}

fsRrmAPIfRecommendedTxPowerLevel OBJECT-TYPE
		SYNTAX 			Integer32
		MAX-ACCESS 	read-only
		STATUS 			current
		DESCRIPTION
		       "Recommended TxPowerLevel by RRM for this APIf"
		::= { fsRrmAPIfRecommendedRFParametersEntry 2}

fsRrmAPIfRecommendedRTSThreshold OBJECT-TYPE
		SYNTAX 			Integer32
		MAX-ACCESS 	read-only
		STATUS 			current
		DESCRIPTION
		       "Recommended RTSThreshold by RRM for this APIf"
		::= { fsRrmAPIfRecommendedRFParametersEntry 3}

fsRrmAPIfRecommendedFragmentationThreshold OBJECT-TYPE
		SYNTAX 			Integer32
		MAX-ACCESS 	read-only
		STATUS 			current
		DESCRIPTION
		       "Recommended Fragmentation Threshold by RRM for this
		        APIf"
		::= { fsRrmAPIfRecommendedRFParametersEntry 4}

fsRrmAPIfRecommendedName OBJECT-TYPE
    SYNTAX 			DisplayString (SIZE(1..32))
    MAX-ACCESS 	read-only
    STATUS 			current
    DESCRIPTION
        		"The name of the AP"
    ::= { fsRrmAPIfRecommendedRFParametersEntry 5 }

fsRrmAPIfRecommendedMacAddr OBJECT-TYPE
    SYNTAX      MacAddress
    MAX-ACCESS  read-only
    STATUS      current
    DESCRIPTION
            "The MAC address of radio on the AP"
    ::= { fsRrmAPIfRecommendedRFParametersEntry 6 }

fsRrmAPIfRecommendedSlotId OBJECT-TYPE
    SYNTAX 			INTEGER(1..32)
    MAX-ACCESS 	read-only
    STATUS 			current
    DESCRIPTION
        		"Number of Radio Interfaces on the Airespace AP.
         		Currently maximum two interfaces are supported.
         		One would be of type 802.11a and other of type
         		802.11b/g."
    ::= {  fsRrmAPIfRecommendedRFParametersEntry 7 }

--********************************************************************
-- * Begin of fsRrmAPRadioTable
--********************************************************************

fsRrmAPRadioTable OBJECT-TYPE
		SYNTAX 			SEQUENCE OF FSRrmAPRadioEntry
		MAX-ACCESS 	not-accessible
		STATUS 			current
		DESCRIPTION
        		"ap radio table"
		::= { fsRrmObjectsAP 12 }

fsRrmAPRadioEntry OBJECT-TYPE
		SYNTAX 			FSRrmAPRadioEntry
 		MAX-ACCESS 	not-accessible
  	STATUS 			current
  	DESCRIPTION
         		"all radio in aps"
   	INDEX { fsRrmAPMacAddr, fsRrmAPRadioID}
    ::= { fsRrmAPRadioTable 1 }

FSRrmAPRadioEntry ::=
 		SEQUENCE {
 						fsRrmAPRealName  DisplayString,
            fsRrmAPMacAddr MacAddress,
     				fsRrmAPRadioID    INTEGER,
     				fsRrmAPRadioType  INTEGER
		}

fsRrmAPRadioID OBJECT-TYPE
    SYNTAX 			INTEGER(1..32)
    MAX-ACCESS 	read-only
    STATUS 			current
    DESCRIPTION
        		"Number of Radio Interfaces on the FS AP.
         		Currently maximum 32 interfaces are supported."
    ::= { fsRrmAPRadioEntry 1 }

fsRrmAPRadioType OBJECT-TYPE
    SYNTAX 			INTEGER {type80211a(0),type80211b(1)}
    MAX-ACCESS 	read-only
    STATUS 			current
    DESCRIPTION
      			"radio type, type 802.11b means 2.4GHz, type 802.11a means 5GHz,"
		::= { fsRrmAPRadioEntry 2 }

fsRrmAPRealName OBJECT-TYPE
    SYNTAX 			DisplayString (SIZE(1..32))
    MAX-ACCESS 	read-only
    STATUS 			current
    DESCRIPTION
        		"The name of the AP"
    ::= { fsRrmAPRadioEntry 3 }

fsRrmAPMacAddr OBJECT-TYPE
    SYNTAX      MacAddress
    MAX-ACCESS  read-only
    STATUS      current
    DESCRIPTION
            "The MAC address of radio on the AP"
    ::= { fsRrmAPRadioEntry 4 }

--********************************************************************
-- * Begin of fsRrmAPIfThroughputParametersTable
--********************************************************************
fsRrmAPIfThroughputParametersTable OBJECT-TYPE
		SYNTAX 			SEQUENCE OF FSRrmAPIfThroughputParametersEntry
		MAX-ACCESS 	not-accessible
		STATUS 			current
		DESCRIPTION
        		"These are RRM performance related read only parameters
        		per Airespace AP"
		::= { fsRrmObjectsAP 13 }

fsRrmAPIfThroughputParametersEntry OBJECT-TYPE
		SYNTAX 			FSRrmAPIfThroughputParametersEntry
		MAX-ACCESS 	not-accessible
		STATUS 			current
		DESCRIPTION
          	"An entry (conceptual row) in the Table.
          	Entries in this MIB are indexed by
         	fsRrmAPDot3MacAddress and fsRrmAPIfSlotId"
 		INDEX { fsRrmAPIfThroughputMacAddr, fsRrmAPIfThroughputSlotId }
 		::= { fsRrmAPIfThroughputParametersTable 1 }

FSRrmAPIfThroughputParametersEntry ::=
  	SEQUENCE {
        fsRrmAPIfThroughputMacAddr MacAddress,
        fsRrmAPIfThroughputSlotId  INTEGER,
        fsRrmAPIfThroughputAPName  DisplayString,
     		fsRrmAPIfThroughputRx      INTEGER,
   			fsRrmAPIfThroughputTx      INTEGER,
   			fsRrmAPIfThroughputTotal	 INTEGER
		}

fsRrmAPIfThroughputMacAddr OBJECT-TYPE
    SYNTAX      MacAddress
    MAX-ACCESS  read-only
    STATUS      current
    DESCRIPTION
            "The MAC address of radio on the AP"
    ::= { fsRrmAPIfThroughputParametersEntry 1 }

fsRrmAPIfThroughputSlotId OBJECT-TYPE
    SYNTAX 			INTEGER(1..32)
    MAX-ACCESS 	read-only
    STATUS 			current
    DESCRIPTION
        		"Number of Radio Interfaces on the Airespace AP.
         		Currently maximum two interfaces are supported.
         		One would be of type 802.11a and other of type
         		802.11b/g."
    ::= { fsRrmAPIfThroughputParametersEntry 2 }

fsRrmAPIfThroughputAPName OBJECT-TYPE
    SYNTAX 			DisplayString (SIZE(1..64))
    MAX-ACCESS 	read-only
    STATUS 			current
    DESCRIPTION
        		"The name of the AP"
    ::= { fsRrmAPIfThroughputParametersEntry 3 }

fsRrmAPIfThroughputRx OBJECT-TYPE
		SYNTAX 			INTEGER
		MAX-ACCESS 	read-only
		STATUS 			current
		DESCRIPTION
      			"This is the RX throughput"
		::= { fsRrmAPIfThroughputParametersEntry 4 }

fsRrmAPIfThroughputTx OBJECT-TYPE
 		SYNTAX 			INTEGER
		MAX-ACCESS 	read-only
		STATUS 			current
		DESCRIPTION
      			"This is the TX throughput"
		::= { fsRrmAPIfThroughputParametersEntry 5 }

fsRrmAPIfThroughputTotal OBJECT-TYPE
    SYNTAX 			INTEGER
    MAX-ACCESS 	read-only
    STATUS 			current
    DESCRIPTION
            "This is the total throughput"
    ::= { fsRrmAPIfThroughputParametersEntry 6 }

--********************************************************************
-- * Begin of fsRrmAPSnrBSSIDTable
--********************************************************************
fsRrmAPSnrBSSIDTable OBJECT-TYPE
		SYNTAX 			SEQUENCE OF FSRrmAPSnrBSSIDEntry
		MAX-ACCESS 	not-accessible
		STATUS 			current
		DESCRIPTION
        		"These are stat on ap snr BSSID"
		::= { fsRrmObjectsAP 14 }

fsRrmAPSnrBSSIDEntry OBJECT-TYPE
		SYNTAX 			FSRrmAPSnrBSSIDEntry
		MAX-ACCESS 	not-accessible
		STATUS 			current
		DESCRIPTION
          	"An entry (conceptual row) in the Table.
          	Entries in this MIB are indexed by
         	fsRrmAPDot3MacAddress and fsRrmAPIfSlotId"
 		INDEX { fsRrmAPSnrBSSIDMacAddr, fsRrmAPSnrBSSIDSlotId }
 		::= { fsRrmAPSnrBSSIDTable 1 }

FSRrmAPSnrBSSIDEntry ::=
  	SEQUENCE {
        fsRrmAPSnrBSSIDMacAddr                  MacAddress,
        fsRrmAPSnrBSSIDSlotId                   INTEGER,
        fsRrmAPSnrBSSIDAPName                   DisplayString,
     		fsRrmAPSnrBSSIDAverageSignalStrength    INTEGER,
   			fsRrmAPSnrBSSIDSignalPkts               INTEGER,
   			fsRrmAPSnrBSSIDHighestRxSignalStrength  INTEGER,
   			fsRrmAPSnrBSSIDLowestRxSignalStrength   INTEGER,
   			fsRrmAPSnrBSSIDSampleTime               INTEGER
		}

fsRrmAPSnrBSSIDMacAddr OBJECT-TYPE
    SYNTAX      MacAddress
    MAX-ACCESS  read-only
    STATUS      current
    DESCRIPTION
            "The MAC address of radio on the AP"
    ::= { fsRrmAPSnrBSSIDEntry 1 }

fsRrmAPSnrBSSIDSlotId OBJECT-TYPE
    SYNTAX 			INTEGER(1..32)
    MAX-ACCESS 	read-only
    STATUS 			current
    DESCRIPTION
        		"Number of Radio Interfaces on the Airespace AP.
         		Currently maximum two interfaces are supported.
         		One would be of type 802.11a and other of type
         		802.11b/g."
    ::= { fsRrmAPSnrBSSIDEntry 2 }

fsRrmAPSnrBSSIDAPName OBJECT-TYPE
    SYNTAX 			DisplayString (SIZE(1..64))
    MAX-ACCESS 	read-only
    STATUS 			current
    DESCRIPTION
        		"The name of the AP"
    ::= { fsRrmAPSnrBSSIDEntry 3 }

fsRrmAPSnrBSSIDAverageSignalStrength OBJECT-TYPE
		SYNTAX 			INTEGER
		MAX-ACCESS 	read-only
		STATUS 			current
		DESCRIPTION
      			"The average signal strength during monitor"
		::= { fsRrmAPSnrBSSIDEntry 4 }

fsRrmAPSnrBSSIDSignalPkts OBJECT-TYPE
 		SYNTAX 			INTEGER
		MAX-ACCESS 	read-only
		STATUS 			current
		DESCRIPTION
      			"The number of signal packets"
		::= { fsRrmAPSnrBSSIDEntry 5 }

fsRrmAPSnrBSSIDHighestRxSignalStrength OBJECT-TYPE
    SYNTAX 			INTEGER
    MAX-ACCESS 	read-only
    STATUS 			current
    DESCRIPTION
            "The highest rx signal strength during monitor"
    ::= { fsRrmAPSnrBSSIDEntry 6 }

fsRrmAPSnrBSSIDLowestRxSignalStrength OBJECT-TYPE
		SYNTAX 			INTEGER
		MAX-ACCESS 	read-only
		STATUS 			current
		DESCRIPTION
      			"The lowest rx signal strength during monitor"
		::= { fsRrmAPSnrBSSIDEntry 7 }

fsRrmAPSnrBSSIDSampleTime OBJECT-TYPE
 		SYNTAX 			INTEGER
		MAX-ACCESS 	read-only
		STATUS 			current
		DESCRIPTION
      			"The sample time"
		::= { fsRrmAPSnrBSSIDEntry 8 }

--********************************************************************
--                                                                  **
--                           DCA Algorithm                          **
--                                                                  **
--********************************************************************
fsRrmDot11bDynamicChannelAssignment OBJECT-TYPE
    SYNTAX      INTEGER {
        automatic (1),
        runOnce (2),
        static (3)
    }
    MAX-ACCESS  read-write
    STATUS      current
    DESCRIPTION
            "Dynamic channel assignment(DCA) has three modes. When the
            mode is auto, the channel assignment will be periodically
            updated for all APs that permit this operation. When the
            DCA is runOnce, channel assignments are updated based on
            the UPDATE_CMD received from the management. When the DCA
            is static, no dynamic channel assignments occurs and value
            are set to their global default.  Default is auto."
    DEFVAL { automatic }
    ::= { fsRrmDCADot11b 1 }

fsRrmDot11bAnchorTime OBJECT-TYPE
    SYNTAX      Unsigned32
    MAX-ACCESS  read-write
    STATUS      current
    DESCRIPTION
            "the time of DCA algorithm to start"
    DEFVAL { 0 }
    ::= { fsRrmDCADot11b 2 }

fsRrmDot11bChannalWidth11n OBJECT-TYPE
    SYNTAX      Unsigned32
    MAX-ACCESS  read-write
    STATUS      current
    DESCRIPTION
            "channel width in DCA for 802.11n"
    DEFVAL { 20 }
    ::= { fsRrmDCADot11b 3 }

fsRrmDot11bDynamicChannelUpdateInterval OBJECT-TYPE
    SYNTAX      Unsigned32
    MAX-ACCESS  read-write
    STATUS      current
    DESCRIPTION
            "When Channel dynamic alogirthm is running, this interval
            (in secs) specifies how often Channel assignement updates
            are attempted on an AP. NOTE: hysteresis is built into
            the algorithms so we will not have uproductive changes
            occuring. Default value is 600 secs"
    DEFVAL { 600 }
    ::= { fsRrmDCADot11b 4 }

fsRrmDot11bDCASensitivity OBJECT-TYPE
    SYNTAX      INTEGER {
        low (1),
        medium (2),
        high (3)
    }
    MAX-ACCESS  read-write
    STATUS      current
    DESCRIPTION
            "Consider foreign factor in DCA algorithm"
    DEFVAL  { medium }
    ::= { fsRrmDCADot11b 5 }

fsRrmDot11bForeignInterfereFactorEnable OBJECT-TYPE
    SYNTAX      INTEGER {disable(0),enable(1)}
    MAX-ACCESS  read-write
    STATUS      current
    DESCRIPTION
            "Consider foreign factor in DCA algorithm"
    DEFVAL  { enable }
    ::= { fsRrmDCADot11b 6 }

fsRrmDot11bLoadFactorEnable OBJECT-TYPE
    SYNTAX      INTEGER {disable(0),enable(1)}
    MAX-ACCESS  read-write
    STATUS      current
    DESCRIPTION
            "Consider foreign factor in DCA algorithm"
    DEFVAL  { disable }
    ::= { fsRrmDCADot11b 7 }

fsRrmDot11bNoiseFactorEnable OBJECT-TYPE
    SYNTAX      INTEGER {disable(0),enable(1)}
    MAX-ACCESS  read-write
    STATUS      current
    DESCRIPTION
            "Consider foreign factor in DCA algorithm"
    DEFVAL  { disable }
    ::= { fsRrmDCADot11b 8 }

fsRrmDot11bChannelUpdateCmdInvoke OBJECT-TYPE
    SYNTAX      INTEGER { default (0), activate (1) }
    MAX-ACCESS  read-write
    STATUS      current
    DESCRIPTION
        "When set to activate this starts a DCA calculation regardless
         of the dynamic update interval. This command should be invoke
         on Group Leader FS Switch.Invoking on a FS
         Switch which is not a Group leader has no effect."
    ::= {  fsRrmDCADot11b 9 }

fsRrmDot11bDCAChannelTable OBJECT-TYPE
    SYNTAX      SEQUENCE OF FSRrmDot11bDCAChannelEntry
    MAX-ACCESS  not-accessible
    STATUS      current
    DESCRIPTION
       "This is a table of FS Switch addresses that identifies
        the members of the Dot11a RF group containing this FS
        Switch. Max size is 20 entries."
    ::= { fsRrmDCADot11b 10 }

fsRrmDot11bDCAChannelEntry OBJECT-TYPE
    SYNTAX      FSRrmDot11bDCAChannelEntry
    MAX-ACCESS  not-accessible
    STATUS      current
    DESCRIPTION
        " ... "
    INDEX { fsRrmDot11bDCAChannelIndex }
    ::= { fsRrmDot11bDCAChannelTable 1 }

FSRrmDot11bDCAChannelEntry ::=
    SEQUENCE {
        fsRrmDot11bDCAChannelIndex        INTEGER,
        fsRrmDot11bDCAChannelOperation    INTEGER
    }

fsRrmDot11bDCAChannelIndex OBJECT-TYPE
    SYNTAX      INTEGER
    MAX-ACCESS  read-only
    STATUS      current
    DESCRIPTION
            "the index of dca channel."
    ::= { fsRrmDot11bDCAChannelEntry 1 }

fsRrmDot11bDCAChannelOperation OBJECT-TYPE
    SYNTAX      INTEGER {delete(0),add(1)}
    MAX-ACCESS  read-write
    STATUS      current
    DESCRIPTION
            "add or delete the channel using in DCA algorithm."
    ::= { fsRrmDot11bDCAChannelEntry 2 }


fsRrmDot11aDynamicChannelAssignment OBJECT-TYPE
    SYNTAX      INTEGER {
        automatic (1),
        runOnce (2),
        static (3)
    }
    MAX-ACCESS  read-write
    STATUS      current
    DESCRIPTION
            "Dynamic channel assignment(DCA) has three modes. When the
            mode is auto, the channel assignment will be periodically
            updated for all APs that permit this operation. When the
            DCA is runOnce, channel assignments are updated based on
            the UPDATE_CMD received from the management. When the DCA
            is static, no dynamic channel assignments occurs and value
            are set to their global default.  Default is auto."
    DEFVAL { automatic }
    ::= { fsRrmDCADot11a 1 }

fsRrmDot11aAnchorTime OBJECT-TYPE
    SYNTAX      Unsigned32
    MAX-ACCESS  read-write
    STATUS      current
    DESCRIPTION
            "the time of DCA algorithm to start"
    DEFVAL { 0 }
    ::= { fsRrmDCADot11a 2 }

fsRrmDot11aChannalWidth11n OBJECT-TYPE
    SYNTAX      Unsigned32
    MAX-ACCESS  read-write
    STATUS      current
    DESCRIPTION
            "channel width in DCA for 802.11n"
    DEFVAL { 20 }
    ::= { fsRrmDCADot11a 3 }

fsRrmDot11aDynamicChannelUpdateInterval OBJECT-TYPE
    SYNTAX      Unsigned32
    MAX-ACCESS  read-write
    STATUS      current
    DESCRIPTION
            "When Channel dynamic alogirthm is running, this interval
            (in secs) specifies how often Channel assignement updates
            are attempted on an AP. NOTE: hysteresis is built into
            the algorithms so we will not have uproductive changes
            occuring. Default value is 600 secs"
    DEFVAL { 600 }
    ::= { fsRrmDCADot11a 4 }

fsRrmDot11aDCASensitivity OBJECT-TYPE
    SYNTAX      INTEGER {
        low (1),
        medium (2),
        high (3)
    }
    MAX-ACCESS  read-write
    STATUS      current
    DESCRIPTION
            "Consider foreign factor in DCA algorithm"
    DEFVAL  { medium }
    ::= { fsRrmDCADot11a 5 }

fsRrmDot11aForeignInterfereFactorEnable OBJECT-TYPE
    SYNTAX      INTEGER {disable(0),enable(1)}
    MAX-ACCESS  read-write
    STATUS      current
    DESCRIPTION
            "Consider foreign factor in DCA algorithm"
    DEFVAL  { enable }
    ::= { fsRrmDCADot11a 6 }

fsRrmDot11aLoadFactorEnable OBJECT-TYPE
    SYNTAX      INTEGER {disable(0),enable(1)}
    MAX-ACCESS  read-write
    STATUS      current
    DESCRIPTION
            "Consider foreign factor in DCA algorithm"
    DEFVAL  { disable }
    ::= { fsRrmDCADot11a 7 }

fsRrmDot11aNoiseFactorEnable OBJECT-TYPE
    SYNTAX      INTEGER {disable(0),enable(1)}
    MAX-ACCESS  read-write
    STATUS      current
    DESCRIPTION
            "Consider foreign factor in DCA algorithm"
    DEFVAL  { disable }
    ::= { fsRrmDCADot11a 8 }

fsRrmDot11aChannelUpdateCmdInvoke OBJECT-TYPE
    SYNTAX      INTEGER { default (0), activate (1) }
    MAX-ACCESS  read-write
    STATUS      current
    DESCRIPTION
        "When set to activate this starts a DCA calculation regardless
         of the dynamic update interval. This command should be invoke
         on Group Leader FS Switch.Invoking on a FS
         Switch which is not a Group leader has no effect."
    ::= {  fsRrmDCADot11a 9 }

fsRrmDot11aDCAChannelTable OBJECT-TYPE
    SYNTAX      SEQUENCE OF FSRrmDot11aDCAChannelEntry
    MAX-ACCESS  not-accessible
    STATUS      current
    DESCRIPTION
       "This is a table of FS Switch addresses that identifies
        the members of the Dot11a RF group containing this FS
        Switch. Max size is 20 entries."
    ::= { fsRrmDCADot11a 10 }

fsRrmDot11aDCAChannelEntry OBJECT-TYPE
    SYNTAX      FSRrmDot11aDCAChannelEntry
    MAX-ACCESS  not-accessible
    STATUS      current
    DESCRIPTION
        " ... "
    INDEX { fsRrmDot11aDCAChannelIndex }
    ::= { fsRrmDot11aDCAChannelTable 1 }

FSRrmDot11aDCAChannelEntry ::=
    SEQUENCE {
        fsRrmDot11aDCAChannelIndex        INTEGER,
        fsRrmDot11aDCAChannelOperation    INTEGER
    }

fsRrmDot11aDCAChannelIndex OBJECT-TYPE
    SYNTAX      INTEGER
    MAX-ACCESS  read-only
    STATUS      current
    DESCRIPTION
            "the index of dca channel."
    ::= { fsRrmDot11aDCAChannelEntry 1 }

fsRrmDot11aDCAChannelOperation OBJECT-TYPE
    SYNTAX      INTEGER {delete(0),add(1)}
    MAX-ACCESS  read-write
    STATUS      current
    DESCRIPTION
            "add or delete the channel using in DCA algorithm."
    ::= { fsRrmDot11aDCAChannelEntry 2 }

--********************************************************************
--                                                                  **
--                           TPC Algorithm                          **
--                                                                  **
--********************************************************************
fsRrmDot11bDTPCSupport OBJECT-TYPE
    SYNTAX      INTEGER {disable(0),enable(1)}
    MAX-ACCESS  read-write
    STATUS current
    DESCRIPTION
        "This attribute may be used to enable the DTPC support on all
        802.11b/g radios. DTPC or Dynamic Transmit Power Control support
        means that the radio's transmit power will be advertised in the
        beacons and probe responses."
    DEFVAL { enable }
    ::= { fsRrmTPCDot11b 1 }

fsRrmDot11bDynamicTransmitPowerControl OBJECT-TYPE
    SYNTAX      INTEGER {
        automatic (1),
        runOnce (2),
        static (3)
    }
    MAX-ACCESS  read-write
    STATUS      current
    DESCRIPTION
        "Dynamic transmit power (DTP) has three modes. When the mode
         is auto, the transmit power of each FS AP will be
         periodically updated for all FS APs that permit this
         operation. When the DTP is runOnce,transmit power update will
         occur based on the UPDATE_CMD received from the management.
         When the DTP is static, no dynamic transmit power updates
         occur and their global defaults are used.  Default is auto."
    DEFVAL { automatic }
    ::= { fsRrmTPCDot11b 2 }

fsRrmDot11bDynamicTxPowerControlInterval OBJECT-TYPE
    SYNTAX      Unsigned32
    MAX-ACCESS  read-only
    STATUS      current
    DESCRIPTION
        "When Tx PowerControl dynamic alogirthm is running, this
         interval(in secs) specifies how often TxPower control updates
         are attempted on an FS AP. NOTE: hysteresis is
         build into the algorithms so we will not have uproductive
         changes occuring. Default value is 600 secs"
   DEFVAL { 600 }
   ::= { fsRrmTPCDot11b 3 }

fsRrmDot11bCurrentTxPowerLevel OBJECT-TYPE
    SYNTAX      INTEGER (1..8)
    MAX-ACCESS  read-write
    STATUS      current
    DESCRIPTION
            "The TxPowerLevel N currently being used to transmit data.
            Some PHYs also use this value to determine the receiver
            sensitivity requirements for CCA."
    ::= { fsRrmTPCDot11b 4 }

fsRrmDot11bPowerUpdateCmdInvoke OBJECT-TYPE
    SYNTAX      INTEGER { default (0), activate (1) }
    MAX-ACCESS  read-write
    STATUS      current
    DESCRIPTION
        "When set to activate this starts a DTP calculation regardless
         of the dynamic update interval. This command should be
         invoke on Group Leader FS Switch.Invoking on a
         FS Switch which is not a Group leader has no effect."
    ::= {  fsRrmTPCDot11b 5 }

fsRrmDot11bTXPowerThreshold OBJECT-TYPE
    SYNTAX      INTEGER (-90..-60)
    MAX-ACCESS  read-write
    STATUS      current
    DESCRIPTION
            "threshold value in TPC algorithm"
    DEFVAL { -70 }
    ::= { fsRrmTPCDot11b 6 }

fsRrmDot11bTPCNeighborNumber OBJECT-TYPE
    SYNTAX      INTEGER
    MAX-ACCESS  read-only
    STATUS      current
    DESCRIPTION
            "threshold value in TPC algorithm"
    DEFVAL { 3 }
    ::= { fsRrmTPCDot11b 7 }

fsRrmDot11aDTPCSupport OBJECT-TYPE
    SYNTAX      INTEGER {disable(0),enable(1)}
    MAX-ACCESS  read-write
    STATUS current
    DESCRIPTION
        "This attribute may be used to enable the DTPC support on all
        802.11b/g radios. DTPC or Dynamic Transmit Power Control support
        means that the radio's transmit power will be advertised in the
        beacons and probe responses."
    DEFVAL { enable }
    ::= { fsRrmTPCDot11a 1 }

fsRrmDot11aDynamicTransmitPowerControl OBJECT-TYPE
    SYNTAX      INTEGER {
        automatic (1),
        runOnce (2),
        static (3)
    }
    MAX-ACCESS  read-write
    STATUS      current
    DESCRIPTION
        "Dynamic transmit power (DTP) has three modes. When the mode
         is auto, the transmit power of each FS AP will be
         periodically updated for all FS APs that permit this
         operation. When the DTP is runOnce,transmit power update will
         occur based on the UPDATE_CMD received from the management.
         When the DTP is static, no dynamic transmit power updates
         occur and their global defaults are used.  Default is auto."
    DEFVAL { automatic }
    ::= { fsRrmTPCDot11a 2 }

fsRrmDot11aDynamicTxPowerControlInterval OBJECT-TYPE
    SYNTAX      Unsigned32
    MAX-ACCESS  read-only
    STATUS      current
    DESCRIPTION
        "When Tx PowerControl dynamic alogirthm is running, this
         interval(in secs) specifies how often TxPower control updates
         are attempted on an FS AP. NOTE: hysteresis is
         build into the algorithms so we will not have uproductive
         changes occuring. Default value is 600 secs"
   DEFVAL { 600 }
   ::= { fsRrmTPCDot11a 3 }

fsRrmDot11aCurrentTxPowerLevel OBJECT-TYPE
    SYNTAX      INTEGER (1..8)
    MAX-ACCESS  read-write
    STATUS      current
    DESCRIPTION
            "The TxPowerLevel N currently being used to transmit data.
            Some PHYs also use this value to determine the receiver
            sensitivity requirements for CCA."
    ::= { fsRrmTPCDot11a 4 }

fsRrmDot11aPowerUpdateCmdInvoke OBJECT-TYPE
    SYNTAX      INTEGER { default (0), activate (1) }
    MAX-ACCESS  read-write
    STATUS      current
    DESCRIPTION
        "When set to activate this starts a DTP calculation regardless
         of the dynamic update interval. This command should be
         invoke on Group Leader FS Switch.Invoking on a
         FS Switch which is not a Group leader has no effect."
    ::= {  fsRrmTPCDot11a 5 }

fsRrmDot11aTXPowerThreshold OBJECT-TYPE
    SYNTAX      INTEGER (-90..-60)
    MAX-ACCESS  read-write
    STATUS      current
    DESCRIPTION
            "threshold value in TPC algorithm"
    DEFVAL { -70 }
    ::= { fsRrmTPCDot11a 6 }

fsRrmDot11aTPCNeighborNumber OBJECT-TYPE
    SYNTAX      INTEGER
    MAX-ACCESS  read-only
    STATUS      current
    DESCRIPTION
            "threshold value in TPC algorithm"
    DEFVAL { 3 }
    ::= { fsRrmTPCDot11a 7 }

--********************************************************************
--                                                                  **
--                           CHD Algorithm                          **
--                                                                  **
--********************************************************************
fsRrmDot11bCoverageEnable OBJECT-TYPE
    SYNTAX      INTEGER {disable(0),enable(1)}
    MAX-ACCESS  read-write
    STATUS      current
    DESCRIPTION
        "CHD algorighm. Default is enable."
    DEFVAL { enable }
    ::= { fsRrmCHDDot11b 1 }

fsRrmDot11bCoverageExceptionGlobal OBJECT-TYPE
    SYNTAX      INTEGER (1..100)
    MAX-ACCESS  read-write
    STATUS      current
    DESCRIPTION
        "CHD algorighm."
    DEFVAL { 25 }
    ::= { fsRrmCHDDot11b 2 }

fsRrmDot11bCoverageLevelGlobal OBJECT-TYPE
    SYNTAX      INTEGER (1..75)
    MAX-ACCESS  read-write
    STATUS      current
    DESCRIPTION
        "CHD algorighm."
    DEFVAL { 3 }
    ::= { fsRrmCHDDot11b 3 }

fsRrmDot11bCoverageDataRSSIThreshold OBJECT-TYPE
    SYNTAX      INTEGER (-90..-60)
    MAX-ACCESS  read-write
    STATUS      current
    DESCRIPTION
        "CHD algorighm."
    DEFVAL { -80 }
    ::= { fsRrmCHDDot11b 4 }

fsRrmDot11bCoverageVoiceRSSIThreshold OBJECT-TYPE
    SYNTAX      INTEGER (-90..-60)
    MAX-ACCESS  read-write
    STATUS      current
    DESCRIPTION
        "CHD algorighm."
    DEFVAL { -75 }
    ::= { fsRrmCHDDot11b 5 }

fsRrmDot11bCoverageDataPacketCount OBJECT-TYPE
    SYNTAX      INTEGER (1..255)
    MAX-ACCESS  read-write
    STATUS      current
    DESCRIPTION
        "CHD algorighm."
    DEFVAL { 10 }
    ::= { fsRrmCHDDot11b 6 }

fsRrmDot11bCoverageVoicePacketCount OBJECT-TYPE
    SYNTAX      INTEGER (1..255)
    MAX-ACCESS  read-write
    STATUS      current
    DESCRIPTION
        "CHD algorighm."
    DEFVAL { 10 }
    ::= { fsRrmCHDDot11b 7 }

fsRrmDot11bCoverageDataFailRate OBJECT-TYPE
    SYNTAX      INTEGER (1..100)
    MAX-ACCESS  read-write
    STATUS      current
    DESCRIPTION
        "CHD algorighm."
    DEFVAL { 20 }
    ::= { fsRrmCHDDot11b 8 }

fsRrmDot11bCoverageVoiceFailRate OBJECT-TYPE
    SYNTAX      INTEGER (1..100)
    MAX-ACCESS  read-write
    STATUS      current
    DESCRIPTION
        "CHD algorighm."
    DEFVAL { 20 }
    ::= { fsRrmCHDDot11b 9 }

fsRrmDot11aCoverageEnable OBJECT-TYPE
    SYNTAX      INTEGER {disable(0),enable(1)}
    MAX-ACCESS  read-write
    STATUS      current
    DESCRIPTION
        "CHD algorighm. Default is enable."
    DEFVAL { enable }
    ::= { fsRrmCHDDot11a 1 }

fsRrmDot11aCoverageExceptionGlobal OBJECT-TYPE
    SYNTAX      INTEGER (1..100)
    MAX-ACCESS  read-write
    STATUS      current
    DESCRIPTION
        "CHD algorighm."
    DEFVAL { 25 }
    ::= { fsRrmCHDDot11a 2 }

fsRrmDot11aCoverageLevelGlobal OBJECT-TYPE
    SYNTAX      INTEGER (1..75)
    MAX-ACCESS  read-write
    STATUS      current
    DESCRIPTION
        "CHD algorighm."
    DEFVAL { 3 }
    ::= { fsRrmCHDDot11a 3 }

fsRrmDot11aCoverageDataRSSIThreshold OBJECT-TYPE
    SYNTAX      INTEGER (-90..-60)
    MAX-ACCESS  read-write
    STATUS      current
    DESCRIPTION
        "CHD algorighm."
    DEFVAL { -80 }
    ::= { fsRrmCHDDot11a 4 }

fsRrmDot11aCoverageVoiceRSSIThreshold OBJECT-TYPE
    SYNTAX      INTEGER (-90..-60)
    MAX-ACCESS  read-write
    STATUS      current
    DESCRIPTION
        "CHD algorighm."
    DEFVAL { -75 }
    ::= { fsRrmCHDDot11a 5 }

fsRrmDot11aCoverageDataPacketCount OBJECT-TYPE
    SYNTAX      INTEGER (1..255)
    MAX-ACCESS  read-write
    STATUS      current
    DESCRIPTION
        "CHD algorighm."
    DEFVAL { 10 }
    ::= { fsRrmCHDDot11a 6 }

fsRrmDot11aCoverageVoicePacketCount OBJECT-TYPE
    SYNTAX      INTEGER (1..255)
    MAX-ACCESS  read-write
    STATUS      current
    DESCRIPTION
        "CHD algorighm."
    DEFVAL { 10 }
    ::= { fsRrmCHDDot11a 7 }

fsRrmDot11aCoverageDataFailRate OBJECT-TYPE
    SYNTAX      INTEGER (1..100)
    MAX-ACCESS  read-write
    STATUS      current
    DESCRIPTION
        "CHD algorighm."
    DEFVAL { 20 }
    ::= { fsRrmCHDDot11a 8 }

fsRrmDot11aCoverageVoiceFailRate OBJECT-TYPE
    SYNTAX      INTEGER (1..100)
    MAX-ACCESS  read-write
    STATUS      current
    DESCRIPTION
        "CHD algorighm."
    DEFVAL { 20 }
    ::= { fsRrmCHDDot11a 9 }

--********************************************************************
--                                                                  **
--                      RRM Group Infomation                        **
--                                                                  **
--********************************************************************
fsRrmDot11bGlobalAutomaticGrouping OBJECT-TYPE
    SYNTAX      INTEGER { automatic (1), off (0) }
    MAX-ACCESS  read-write
    STATUS      current
    DESCRIPTION
        "Dynamic grouping has two modes: on and off. When the grouping
         is off, no dynamic grouping occurs. Each FS Switch
         optimizes only its own FS APs' parameters. When
         grouping is on, the FS Switches form groups and
         elect leaders to perform better dynamic parameter
         optimization."
    DEFVAL { automatic }
    ::= { fsRrmGroupDot11b 1 }

fsRrmDot11bGroupLeaderMacAddr OBJECT-TYPE
    SYNTAX      MacAddress
    MAX-ACCESS  read-only
    STATUS      current
    DESCRIPTION
        "This is the MAC address of the group leader for the Dot11b
         group containing this FS Switch."
    ::= { fsRrmGroupDot11b 2 }

fsRrmDot11bGroupLeader OBJECT-TYPE
    SYNTAX      INTEGER {no(0),yes(1)}
    MAX-ACCESS  read-only
    STATUS      current
    DESCRIPTION
        "If this FS Switch is a Dot11b Group Leader then this
         attribute will be true else it will be false."
    ::= { fsRrmGroupDot11b 3 }

fsRrmDot11bGroupLastUpdateTime OBJECT-TYPE
    SYNTAX      Unsigned32
    MAX-ACCESS  read-only
    STATUS      current
    DESCRIPTION
        "Last time the Dot11b grouping was updated on this FS
         Switch. This is valid only if the FS Switch is a
         group leader."
    ::= { fsRrmGroupDot11b 4 }

fsRrmDot11bGroupInterval OBJECT-TYPE
    SYNTAX      Unsigned32
    MAX-ACCESS  read-only
    STATUS      current
    DESCRIPTION
        "When grouping is on, this interval(in secs) represents the
         period with which the grouping algorithm is run. Grouping
         algorithm will also run when the group contents changes and
         the automatic grouping is enabled. A dynamic grouping can be
         started upon request from the system administrator. Default
         value is 3600 secs."
    DEFVAL { 3600 }
    ::= {fsRrmGroupDot11b 5}

fsRrmDot11bGroupTable OBJECT-TYPE
    SYNTAX      SEQUENCE OF FSRrmDot11bGroupEntry
    MAX-ACCESS  not-accessible
    STATUS      current
    DESCRIPTION
       "This is a table of FS Switch addresses that identifies
        the members of the Dot11b RF group containing this FS
        Switch. Max size is 20 entries."
    ::= { fsRrmGroupDot11b 6 }

fsRrmDot11bGroupEntry OBJECT-TYPE
    SYNTAX      FSRrmDot11bGroupEntry
    MAX-ACCESS  not-accessible
    STATUS      current
    DESCRIPTION
        " ... "
    INDEX { fsRrmDot11bPeerMacAddress }
    ::= { fsRrmDot11bGroupTable 1 }

FSRrmDot11bGroupEntry ::=
    SEQUENCE {
        fsRrmDot11bPeerMacAddress       MacAddress,
        fsRrmDot11bPeerIpAddress        IpAddress
    }

fsRrmDot11bPeerMacAddress OBJECT-TYPE
    SYNTAX      MacAddress
    MAX-ACCESS  read-only
    STATUS      current
    DESCRIPTION
            "The MAC address of the member Switch."
    ::= { fsRrmDot11bGroupEntry 1 }

fsRrmDot11bPeerIpAddress OBJECT-TYPE
    SYNTAX      IpAddress
    MAX-ACCESS  read-only
    STATUS      current
    DESCRIPTION
            "The IP address of the FS Switch."
    ::= { fsRrmDot11bGroupEntry 2 }

fsRrmDot11bSummaryTable OBJECT-TYPE
    SYNTAX      SEQUENCE OF FSRrmDot11bSummaryEntry
    MAX-ACCESS  not-accessible
    STATUS      current
    DESCRIPTION
       ""
    ::= { fsRrmGroupDot11b 7 }

fsRrmDot11bSummaryEntry OBJECT-TYPE
    SYNTAX      FSRrmDot11bSummaryEntry
    MAX-ACCESS  not-accessible
    STATUS      current
    DESCRIPTION
        " ... "
    INDEX { fsRrmDot11bSummaryMacAddress, fsRrmDot11bAPRadioID}
    ::= { fsRrmDot11bSummaryTable 1 }

FSRrmDot11bSummaryEntry ::=
    SEQUENCE {
        fsRrmDot11bSummaryMacAddress   MacAddress,
        fsRrmDot11bAPname           					DisplayString,
        fsRrmDot11bAPRadioID									Unsigned32,
        fsRrmDot11bAPChannel        					Unsigned32,
        fsRrmDot11bAPTxPower        					Unsigned32,
        fsRrmDot11bAPChannelRrmChangeFlag    	INTEGER,
        fsRrmDot11bAPTxPowerRrmChangeFlag    	INTEGER
    }

fsRrmDot11bAPname OBJECT-TYPE
    SYNTAX      DisplayString
    MAX-ACCESS  read-only
    STATUS      current
    DESCRIPTION
            ""
    ::= { fsRrmDot11bSummaryEntry 1 }

fsRrmDot11bAPRadioID OBJECT-TYPE
    SYNTAX      Unsigned32
    MAX-ACCESS  read-only
    STATUS      current
    DESCRIPTION
            ""
    ::= { fsRrmDot11bSummaryEntry 2 }

fsRrmDot11bAPChannel OBJECT-TYPE
    SYNTAX      Unsigned32
    MAX-ACCESS  read-only
    STATUS      current
    DESCRIPTION
            ""
    ::= { fsRrmDot11bSummaryEntry 3 }

fsRrmDot11bAPTxPower OBJECT-TYPE
    SYNTAX      Unsigned32
    MAX-ACCESS  read-only
    STATUS      current
    DESCRIPTION
            ""
    ::= { fsRrmDot11bSummaryEntry 4 }

fsRrmDot11bAPChannelRrmChangeFlag OBJECT-TYPE
    SYNTAX      INTEGER {no(0),yes(1)}
    MAX-ACCESS  read-only
    STATUS      current
    DESCRIPTION
            ""
    ::= { fsRrmDot11bSummaryEntry 5 }

fsRrmDot11bAPTxPowerRrmChangeFlag OBJECT-TYPE
    SYNTAX      INTEGER {no(0),yes(1)}
    MAX-ACCESS  read-only
    STATUS      current
    DESCRIPTION
            ""
    ::= { fsRrmDot11bSummaryEntry 6 }

fsRrmDot11bSummaryMacAddress OBJECT-TYPE
    SYNTAX      MacAddress
    MAX-ACCESS  read-only
    STATUS      current
    DESCRIPTION
            "The MAC address of the member Switch."
    ::= { fsRrmDot11bSummaryEntry 7 }


fsRrmDot11aGlobalAutomaticGrouping OBJECT-TYPE
    SYNTAX      INTEGER { automatic (1), off (0) }
    MAX-ACCESS  read-write
    STATUS      current
    DESCRIPTION
        "Dynamic grouping has two modes: on and off. When the grouping
         is off, no dynamic grouping occurs. Each FS Switch
         optimizes only its own FS APs' parameters. When
         grouping is on, the FS Switches form groups and
         elect leaders to perform better dynamic parameter
         optimization."
    DEFVAL { automatic }
    ::= { fsRrmGroupDot11a 1 }

fsRrmDot11aGroupLeaderMacAddr OBJECT-TYPE
    SYNTAX      MacAddress
    MAX-ACCESS  read-only
    STATUS      current
    DESCRIPTION
        "This is the MAC address of the group leader for the dot11a
         group containing this FS Switch."
    ::= { fsRrmGroupDot11a 2 }

fsRrmDot11aGroupLeader OBJECT-TYPE
    SYNTAX      INTEGER {no(0),yes(1)}
    MAX-ACCESS  read-only
    STATUS      current
    DESCRIPTION
        "If this FS Switch is a Dot11a Group Leader then this
         attribute will be true else it will be false."
    ::= { fsRrmGroupDot11a 3 }

fsRrmDot11aGroupLastUpdateTime OBJECT-TYPE
    SYNTAX      Unsigned32
    MAX-ACCESS  read-only
    STATUS      current
    DESCRIPTION
        "Last time the dot11a grouping was updated on this FS
         Switch. This is valid only if the FS Switch is a
         group leader."
    ::= { fsRrmGroupDot11a 4 }

fsRrmDot11aGroupInterval OBJECT-TYPE
    SYNTAX      Unsigned32
    MAX-ACCESS  read-only
    STATUS      current
    DESCRIPTION
        "When grouping is on, this interval(in secs) represents the
         period with which the grouping algorithm is run. Grouping
         algorithm will also run when the group contents changes and
         the automatic grouping is enabled. A dynamic grouping can be
         started upon request from the system administrator. Default
         value is 3600 secs."
    DEFVAL { 3600 }
    ::= {fsRrmGroupDot11a 5}

fsRrmDot11aGroupTable OBJECT-TYPE
    SYNTAX      SEQUENCE OF FSRrmDot11aGroupEntry
    MAX-ACCESS  not-accessible
    STATUS      current
    DESCRIPTION
       "This is a table of FS Switch addresses that identifies
        the members of the Dot11a RF group containing this FS
        Switch. Max size is 20 entries."
    ::= { fsRrmGroupDot11a 6 }

fsRrmDot11aGroupEntry OBJECT-TYPE
    SYNTAX      FSRrmDot11aGroupEntry
    MAX-ACCESS  not-accessible
    STATUS      current
    DESCRIPTION
        " ... "
    INDEX { fsRrmDot11aPeerMacAddress }
    ::= { fsRrmDot11aGroupTable 1 }

FSRrmDot11aGroupEntry ::=
    SEQUENCE {
        fsRrmDot11aPeerMacAddress       MacAddress,
        fsRrmDot11aPeerIpAddress        IpAddress
    }

fsRrmDot11aPeerMacAddress OBJECT-TYPE
    SYNTAX      MacAddress
    MAX-ACCESS  read-only
    STATUS      current
    DESCRIPTION
            "The MAC address of the member Switch."
    ::= { fsRrmDot11aGroupEntry 1 }

fsRrmDot11aPeerIpAddress OBJECT-TYPE
    SYNTAX      IpAddress
    MAX-ACCESS  read-only
    STATUS      current
    DESCRIPTION
            "The IP address of the FS Switch."
    ::= { fsRrmDot11aGroupEntry 2 }

fsRrmDot11aSummaryTable OBJECT-TYPE
    SYNTAX      SEQUENCE OF FSRrmDot11aSummaryEntry
    MAX-ACCESS  not-accessible
    STATUS      current
    DESCRIPTION
       ""
    ::= { fsRrmGroupDot11a 7 }

fsRrmDot11aSummaryEntry OBJECT-TYPE
    SYNTAX      FSRrmDot11aSummaryEntry
    MAX-ACCESS  not-accessible
    STATUS      current
    DESCRIPTION
        " ... "
    INDEX { fsRrmDot11aSummaryMacAddress,  fsRrmDot11aAPRadioID}
    ::= { fsRrmDot11aSummaryTable 1 }

FSRrmDot11aSummaryEntry ::=
    SEQUENCE {
        fsRrmDot11aSummaryMacAddress MacAddress,
        fsRrmDot11aAPname           					DisplayString,
        fsRrmDot11aAPRadioID									Unsigned32,
        fsRrmDot11aAPChannel        					Unsigned32,
        fsRrmDot11aAPTxPower        					Unsigned32,
        fsRrmDot11aAPChannelRrmChangeFlag    	INTEGER,
        fsRrmDot11aAPTxPowerRrmChangeFlag    	INTEGER
    }

fsRrmDot11aAPname OBJECT-TYPE
    SYNTAX      DisplayString
    MAX-ACCESS  read-only
    STATUS      current
    DESCRIPTION
            ""
    ::= { fsRrmDot11aSummaryEntry 1 }

fsRrmDot11aAPRadioID OBJECT-TYPE
    SYNTAX      Unsigned32
    MAX-ACCESS  read-only
    STATUS      current
    DESCRIPTION
            ""
    ::= { fsRrmDot11aSummaryEntry 2 }

fsRrmDot11aAPChannel OBJECT-TYPE
    SYNTAX      Unsigned32
    MAX-ACCESS  read-only
    STATUS      current
    DESCRIPTION
            ""
    ::= { fsRrmDot11aSummaryEntry 3 }

fsRrmDot11aAPTxPower OBJECT-TYPE
    SYNTAX      Unsigned32
    MAX-ACCESS  read-only
    STATUS      current
    DESCRIPTION
            ""
    ::= { fsRrmDot11aSummaryEntry 4 }

fsRrmDot11aAPChannelRrmChangeFlag OBJECT-TYPE
    SYNTAX      INTEGER {no(0),yes(1)}
    MAX-ACCESS  read-only
    STATUS      current
    DESCRIPTION
            ""
    ::= { fsRrmDot11aSummaryEntry 5 }

fsRrmDot11aAPTxPowerRrmChangeFlag OBJECT-TYPE
    SYNTAX      INTEGER {no(0),yes(1)}
    MAX-ACCESS  read-only
    STATUS      current
    DESCRIPTION
            ""
    ::= { fsRrmDot11aSummaryEntry 6 }

fsRrmDot11aSummaryMacAddress OBJECT-TYPE
    SYNTAX      MacAddress
    MAX-ACCESS  read-only
    STATUS      current
    DESCRIPTION
            "The MAC address of the member Switch."
    ::= { fsRrmDot11aSummaryEntry 7 }

--********************************************************************
--                                                                  **
--                       RRM Profile Value                          **
--                                                                  **
--********************************************************************
fsRrmDot11bForeignInterferenceThreshold OBJECT-TYPE
    SYNTAX      INTEGER(1..100)
    MAX-ACCESS  read-write
    STATUS      current
    DESCRIPTION
            "foreign 802.11B interference threshold between 0 and 100
            percent."
    DEFVAL { 10 }
    ::= {fsRrmProfileDot11b 1 }

fsRrmDot11bForeignNoiseThreshold OBJECT-TYPE
    SYNTAX      INTEGER(-127..0)
    MAX-ACCESS  read-write
    STATUS      current
    DESCRIPTION
            " 802.11B foreign noise threshold between -127 and 0 dBm."
    DEFVAL { -70 }
    ::= {fsRrmProfileDot11b 2 }

fsRrmDot11bRFUtilizationThreshold OBJECT-TYPE
    SYNTAX      INTEGER(1..100)
    MAX-ACCESS  read-write
    STATUS      current
    DESCRIPTION
            "802.11B RF utlization threshold between 0 and 100
            percent."
    DEFVAL { 80 }
    ::= {fsRrmProfileDot11b 3 }

fsRrmDot11bThroughputThreshold OBJECT-TYPE
    SYNTAX      Unsigned32(1000..10000000)
    MAX-ACCESS  read-write
    STATUS      current
    DESCRIPTION
            " 802.11B throughput threshold between 1000 and 10000000"
    DEFVAL { 1000000 }
    ::= {fsRrmProfileDot11b 4 }

fsRrmDot11bMobilesThreshold OBJECT-TYPE
    SYNTAX      INTEGER(1..75)
    MAX-ACCESS  read-write
    STATUS      current
    DESCRIPTION
            "802.11B mobiles threshold between 1 and 75"
    DEFVAL { 12 }
    ::= {fsRrmProfileDot11b 5 }


fsRrmDot11aForeignInterferenceThreshold OBJECT-TYPE
    SYNTAX      INTEGER(1..100)
    MAX-ACCESS  read-write
    STATUS      current
    DESCRIPTION
            "foreign 802.11A interference threshold between 0 and 100
            percent."
    DEFVAL { 10 }
    ::= {fsRrmProfileDot11a 1 }

fsRrmDot11aForeignNoiseThreshold OBJECT-TYPE
    SYNTAX      INTEGER(-127..0)
    MAX-ACCESS  read-write
    STATUS      current
    DESCRIPTION
            " 802.11A foreign noise threshold between -127 and 0 dBm."
    DEFVAL { -70 }
    ::= {fsRrmProfileDot11a 2 }

fsRrmDot11aRFUtilizationThreshold OBJECT-TYPE
    SYNTAX      INTEGER(1..100)
    MAX-ACCESS  read-write
    STATUS      current
    DESCRIPTION
            "802.11A RF utlization threshold between 0 and 100
            percent."
    DEFVAL { 80 }
    ::= {fsRrmProfileDot11a 3 }

fsRrmDot11aThroughputThreshold OBJECT-TYPE
    SYNTAX      Unsigned32(1000..10000000)
    MAX-ACCESS  read-write
    STATUS      current
    DESCRIPTION
            " 802.11A throughput threshold between 1000 and 10000000"
    DEFVAL { 1000000 }
    ::= {fsRrmProfileDot11a 4 }

fsRrmDot11aMobilesThreshold OBJECT-TYPE
    SYNTAX      INTEGER(1..75)
    MAX-ACCESS  read-write
    STATUS      current
    DESCRIPTION
            "802.11A mobiles threshold between 1 and 75"
    DEFVAL { 12 }
    ::= {fsRrmProfileDot11a 5 }


--********************************************************************
--                                                                  **
--                         RRM Monitor                              **
--                                                                  **
--********************************************************************
fsRrmDot11bMonitorEnable OBJECT-TYPE
    SYNTAX      INTEGER { enable (1), disable (0) }
    MAX-ACCESS  read-write
    STATUS      current
    DESCRIPTION
        "Enable or disable monitor function."
    DEFVAL { enable }
    ::= { fsRrmMonitorDot11b 1 }

fsRrmDot11bChannelMonitorList OBJECT-TYPE
    SYNTAX      INTEGER {
        all(1),
        country(2),
        dca(3)
    }
    MAX-ACCESS  read-write
    STATUS      current
    DESCRIPTION
    "This attribute specifies the channels on which the switch monitors
     noise, interference and rogues.  The first option allows
     monitoring on all channels while the second one on only those
     that are supported by the country of operation. the option dca
     implies that the monitor channel list will include those channels
     that are used by automatic channel assignment."
    DEFVAL { country }
    ::= { fsRrmMonitorDot11b 2 }

fsRrmDot11bMonitorInterval OBJECT-TYPE
    SYNTAX      Unsigned32(60..3600)
    MAX-ACCESS  read-write
    STATUS      current
    DESCRIPTION
       "This interval( in secs) specifies how often the AP goto off
       channel state to monitor. Default is 300 secs"
    DEFVAL { 180 }
    ::= {fsRrmMonitorDot11b 3}

fsRrmDot11bCoverageMeasurementInterval OBJECT-TYPE
    SYNTAX      Unsigned32(60..3600)
    MAX-ACCESS  read-write
    STATUS      current
    DESCRIPTION
       "This interval( in secs) specifies how often do we get new
       coverage measurements at each FS AP. Default is 300 secs"
    DEFVAL { 180 }
    ::= {fsRrmMonitorDot11b 4}

fsRrmDot11bLoadMeasurementInterval OBJECT-TYPE
    SYNTAX      Unsigned32(60..3600)
    MAX-ACCESS  read-write
    STATUS      current
    DESCRIPTION
       "This interval( in secs) specifies how often do we get new
       load measurements at each FS AP. Default is 300 secs"
    DEFVAL { 60 }
    ::= {fsRrmMonitorDot11b 5}

fsRrmDot11bNoiseMeasurementInterval OBJECT-TYPE
    SYNTAX      Unsigned32(60..3600)
    MAX-ACCESS  read-write
    STATUS      current
    DESCRIPTION
       "This interval( in secs) specifies how often do we get new
        noise and interference measurements at each FS AP.
        Default is 300 secs"
    DEFVAL { 180 }
    ::= { fsRrmMonitorDot11b 6 }

fsRrmDot11bSignalMeasurementInterval OBJECT-TYPE
    SYNTAX      Unsigned32(60..3600)
    MAX-ACCESS  read-write
    STATUS      current
    DESCRIPTION
       "This interval (in secs) specifies how often do we get new
        signal strength measurements at each FS AP. Default is
        300 secs"
    DEFVAL { 60 }
    ::= { fsRrmMonitorDot11b 7 }

fsRrmDot11bNeighborMessageInterval OBJECT-TYPE
    SYNTAX      Unsigned32(60..3600)
    MAX-ACCESS  read-write
    STATUS      current
    DESCRIPTION
       "This interval (in secs) specifies how often the AP send
       neighbor message"
    DEFVAL { 60 }
    ::= { fsRrmMonitorDot11b 8 }


fsRrmDot11aMonitorEnable OBJECT-TYPE
    SYNTAX      INTEGER { enable (1), disable (0) }
    MAX-ACCESS  read-write
    STATUS      current
    DESCRIPTION
        "Enable or disable monitor function."
    DEFVAL { enable }
    ::= { fsRrmMonitorDot11a 1 }

fsRrmDot11aChannelMonitorList OBJECT-TYPE
    SYNTAX      INTEGER {
        all(1),
        country(2),
        dca(3)
    }
    MAX-ACCESS  read-write
    STATUS      current
    DESCRIPTION
    "This attribute specifies the channels on which the switch monitors
     noise, interference and rogues.  The first option allows
     monitoring on all channels while the second one on only those
     that are supported by the country of operation. the option dca
     implies that the monitor channel list will include those channels
     that are used by automatic channel assignment."
    DEFVAL { country }
    ::= { fsRrmMonitorDot11a 2 }

fsRrmDot11aMonitorInterval OBJECT-TYPE
    SYNTAX      Unsigned32(60..3600)
    MAX-ACCESS  read-write
    STATUS      current
    DESCRIPTION
       "This interval( in secs) specifies how often the AP goto off
       channel state to monitor. Default is 300 secs"
    DEFVAL { 180 }
    ::= {fsRrmMonitorDot11a 3}

fsRrmDot11aCoverageMeasurementInterval OBJECT-TYPE
    SYNTAX      Unsigned32(60..3600)
    MAX-ACCESS  read-write
    STATUS      current
    DESCRIPTION
       "This interval( in secs) specifies how often do we get new
       coverage measurements at each FS AP. Default is 300 secs"
    DEFVAL { 180 }
    ::= {fsRrmMonitorDot11a 4}

fsRrmDot11aLoadMeasurementInterval OBJECT-TYPE
    SYNTAX      Unsigned32(60..3600)
    MAX-ACCESS  read-write
    STATUS      current
    DESCRIPTION
       "This interval( in secs) specifies how often do we get new
       load measurements at each FS AP. Default is 300 secs"
    DEFVAL { 60 }
    ::= {fsRrmMonitorDot11a 5}

fsRrmDot11aNoiseMeasurementInterval OBJECT-TYPE
    SYNTAX      Unsigned32(60..3600)
    MAX-ACCESS  read-write
    STATUS      current
    DESCRIPTION
       "This interval( in secs) specifies how often do we get new
        noise and interference measurements at each FS AP.
        Default is 300 secs"
    DEFVAL { 180 }
    ::= { fsRrmMonitorDot11a 6 }

fsRrmDot11aSignalMeasurementInterval OBJECT-TYPE
    SYNTAX      Unsigned32(60..3600)
    MAX-ACCESS  read-write
    STATUS      current
    DESCRIPTION
       "This interval (in secs) specifies how often do we get new
        signal strength measurements at each FS AP. Default is
        300 secs"
    DEFVAL { 60 }
    ::= { fsRrmMonitorDot11a 7 }

fsRrmDot11aNeighborMessageInterval OBJECT-TYPE
    SYNTAX      Unsigned32(60..3600)
    MAX-ACCESS  read-write
    STATUS      current
    DESCRIPTION
       "This interval (in secs) specifies how often the AP send
       neighbor message"
    DEFVAL { 60 }
    ::= { fsRrmMonitorDot11a 8 }


--********************************************************************
--                                                                  **
--                    Set Factory Defaults                          **
--                                                                  **
--********************************************************************
fsRrmDot11bSetFactoryDefault OBJECT-TYPE
    SYNTAX      INTEGER {default(0),activate (1)}
    MAX-ACCESS  read-write
    STATUS      current
    DESCRIPTION
            "When set to activate all Rrm parameters are reset to
            factory defaults"
   ::= { fsRrmFactoryDot11b 1 }

fsRrmDot11aSetFactoryDefault OBJECT-TYPE
    SYNTAX      INTEGER {default(0),activate (1)}
    MAX-ACCESS  read-write
    STATUS      current
    DESCRIPTION
            "When set to activate all Rrm parameters are reset to
            factory defaults"
   ::= { fsRrmFactoryDot11a 1 }


-- *************************************************************
-- fsRrmTrapControl would specify all the objects that enable/disable the
-- the generation of traps by FS Switch
-- fsRrmTraps would specify all the possible traps that FS Switch
-- would need to generate
-- *************************************************************

--***************** define the fsRrmMIBObjects nodes *****************
fsRrmTrapControl    OBJECT IDENTIFIER ::= { fsRrmMIBTraps 1 }
fsRrmTrapVariable   OBJECT IDENTIFIER ::= { fsRrmMIBTraps 2 }
fsRrmTraps          OBJECT IDENTIFIER ::= { fsRrmMIBTraps 3 }


-- *************************************************************
-- extra trap variables definining here
-- *************************************************************
-- for AP infomation
fsRrmAPMacAddrTrapVariable OBJECT-TYPE
    SYNTAX      MacAddress
    MAX-ACCESS  accessible-for-notify
    STATUS      current
    DESCRIPTION
            "the variable of ap radio MAC address in trap"
    ::= { fsRrmTrapVariable 1 }

fsRrmAPRadioIDTrapVariable OBJECT-TYPE
    SYNTAX      Integer32
    MAX-ACCESS  accessible-for-notify
    STATUS      current
    DESCRIPTION
            "the variable of radio id in trap"
    ::= { fsRrmTrapVariable 2 }

fsRrmAPRadioTypeTrapVariable OBJECT-TYPE
    SYNTAX      INTEGER  {type80211a(0), type80211b(1)}
    MAX-ACCESS  accessible-for-notify
    STATUS      current
    DESCRIPTION
            "the variable of radio type in trap"
    ::= { fsRrmTrapVariable 3 }

-- Get Trap Value
fsRrmClientNumberTrapVariable OBJECT-TYPE
    SYNTAX      Integer32
    MAX-ACCESS  accessible-for-notify
    STATUS      current
    DESCRIPTION
            "the variable of client number in trap"
    ::= { fsRrmTrapVariable 4 }

fsRrmForeignInterfereTrapVariable OBJECT-TYPE
    SYNTAX      Integer32
    MAX-ACCESS  accessible-for-notify
    STATUS      current
    DESCRIPTION
            "the variable of interference in trap"
    ::= { fsRrmTrapVariable 5 }

fsRrmNoiseTrapVariable OBJECT-TYPE
    SYNTAX      Integer32
    MAX-ACCESS  accessible-for-notify
    STATUS      current
    DESCRIPTION
            "the variable of noise in trap"
    ::= { fsRrmTrapVariable 6 }

fsRrmThroughputTrapVariable OBJECT-TYPE
    SYNTAX      Unsigned32
    MAX-ACCESS  accessible-for-notify
    STATUS      current
    DESCRIPTION
            "the variable of throughput in trap"
    ::= { fsRrmTrapVariable 7 }

fsRrmUtilizationTrapVariable OBJECT-TYPE
    SYNTAX      Integer32
    MAX-ACCESS  accessible-for-notify
    STATUS      current
    DESCRIPTION
            "the variable of utilization in trap"
    ::= { fsRrmTrapVariable 8 }

-- for TPC
fsRrmAPTxPowerBeforeChange OBJECT-TYPE
    SYNTAX      Integer32
    MAX-ACCESS  accessible-for-notify
    STATUS      current
    DESCRIPTION
    "The txpower level before change"
    ::= {  fsRrmTrapVariable 9 }

fsRrmAPTxPowerAfterChange OBJECT-TYPE
    SYNTAX      Integer32
    MAX-ACCESS  accessible-for-notify
    STATUS      current
    DESCRIPTION
    "The txpower level after change"
    ::= {  fsRrmTrapVariable 10 }

-- for DCA
fsRrmAPChannelNumberBeforeChannge OBJECT-TYPE
    SYNTAX      Integer32
    MAX-ACCESS  accessible-for-notify
    STATUS      current
    DESCRIPTION
    "The channel before change"
    ::= {  fsRrmTrapVariable 11 }

fsRrmAPChannelNumberAfterChannge OBJECT-TYPE
    SYNTAX      Integer32
    MAX-ACCESS  accessible-for-notify
    STATUS      current
    DESCRIPTION
    "The channel after channge"
    ::= {  fsRrmTrapVariable 12 }


fsRrmDot11bGroupLeaderMacAddrTrapVariable OBJECT-TYPE
    SYNTAX      MacAddress
    MAX-ACCESS  accessible-for-notify
    STATUS      current
    DESCRIPTION
            "The MAC address of the group leader."
    ::= { fsRrmTrapVariable 13 }

fsRrmDot11aGroupLeaderMacAddrTrapVariable OBJECT-TYPE
    SYNTAX      MacAddress
    MAX-ACCESS  accessible-for-notify
    STATUS      current
    DESCRIPTION
            "The MAC address of the group leader."
    ::= { fsRrmTrapVariable 14 }

fsRrmAPChannelChangeReason OBJECT-TYPE
    SYNTAX  	INTEGER {
            signal(1),
            interference(2),
            noise(3),
	          load(4),
	          radar(5),
	          other(6)
     }
    MAX-ACCESS 	accessible-for-notify
    STATUS 	current
    DESCRIPTION
	     "The reason cause the channel changed"
    ::= { fsRrmTrapVariable 15 }

fsRrmAPChannelChangeReasonValue OBJECT-TYPE
    SYNTAX      Integer32
    MAX-ACCESS  accessible-for-notify
    STATUS      current
    DESCRIPTION
    	     "The special value along with the reason of channel change"
    ::= {  fsRrmTrapVariable 16 }

fsRrmAPTxPowerChangeCoverageFlag OBJECT-TYPE
    SYNTAX      INTEGER {no(0),yes(1)}
    MAX-ACCESS  accessible-for-notify
    STATUS      current
    DESCRIPTION
    	    "Indication the power change cause by which algorithm, TPC
    	    Algorithm or CHD Algorithm"
    ::= {  fsRrmTrapVariable 17 }

fsRrmDFSFreeCount OBJECT-TYPE
    SYNTAX      INTEGER
    MAX-ACCESS  accessible-for-notify
    STATUS      current
    DESCRIPTION
    	    "Indication the number of channel usable"
    ::= {  fsRrmTrapVariable 18 }

fsRrmAPChannelChangeCount OBJECT-TYPE
    SYNTAX      INTEGER
    MAX-ACCESS  accessible-for-notify
    STATUS      current
    DESCRIPTION
    	    "the number of channel change"
    ::= {  fsRrmTrapVariable 19 }

-- *************************************************************
-- Whenever LOAD, NOISE, INTERFERENCE, COVERAGE Profile state changes
-- from PASS to FAIL for FS AP IF, notification will be sent, if
-- configured to do so.
-- *************************************************************

fsRrmAPDot11bProfileTrapControlMask OBJECT-TYPE
    SYNTAX      Unsigned32
    MAX-ACCESS  read-write
    STATUS      current
    DESCRIPTION
           "This mask describes what events merit traps to network
            management. If the bit for a particular event is turned
            on then notification will be generated on event occurance.
                Event                    corresponding bit
                -----                    -----------------
                ClientNumProfileFail             1
                LoadProfileFail                  2
                NoiseProfileFail                 4
                InterferenceProfileFail          8
                PerformanceProfileFailed         16
           "
    DEFVAL { 0 }
    ::= { fsRrmTrapControl 1 }

fsRrmAPDot11aProfileTrapControlMask OBJECT-TYPE
    SYNTAX      Unsigned32
    MAX-ACCESS  read-write
    STATUS      current
    DESCRIPTION
           "This mask describes what events merit traps to network
            management. If the bit for a particular event is turned
            on then notification will be generated on event occurance.
                Event                    corresponding bit
                -----                    -----------------
                ClientNumProfileFail             1
                LoadProfileFail                  2
                NoiseProfileFail                 4
                InterferenceProfileFail          8
                PerformanceProfileFailed         16
           "
    DEFVAL { 0 }
    ::= { fsRrmTrapControl 2 }

fsRrmAPClientNumProfileFailed NOTIFICATION-TYPE
    OBJECTS {
        fsRrmAPMacAddrTrapVariable,
        fsRrmAPRadioIDTrapVariable,
        fsRrmAPRadioTypeTrapVariable,
        fsRrmClientNumberTrapVariable
    }
    STATUS current
    DESCRIPTION
        "too many clients "
    ::= { fsRrmTraps 1 }

fsRrmAPLoadProfileFailed NOTIFICATION-TYPE
    OBJECTS {
        fsRrmAPMacAddrTrapVariable,
        fsRrmAPRadioIDTrapVariable,
        fsRrmAPRadioTypeTrapVariable,
        fsRrmUtilizationTrapVariable
    }
    STATUS current
    DESCRIPTION
        "When LOAD Profile state changes from PASS to FAIL,
         notification will be sent with Dot3 MAC address of FS
         AP and slot ID of FS AP IF. This trap sending can be
         enable/disable using fsRrmRrmProfileTrapControlFlag "
    ::= { fsRrmTraps 2 }

fsRrmAPNoiseProfileFailed NOTIFICATION-TYPE
    OBJECTS {
        fsRrmAPMacAddrTrapVariable,
        fsRrmAPRadioIDTrapVariable,
        fsRrmAPRadioTypeTrapVariable,
        fsRrmNoiseTrapVariable
    }
    STATUS current
    DESCRIPTION
        "When Noise Profile state changes from PASS to FAIL,
         notification will be sent with Dot3 MAC address of FS
         AP and slot ID of FS AP IF. This trap sending can be
         enable/disable using fsRrmRrmProfileTrapControlFlag "
    ::= { fsRrmTraps 3 }

fsRrmAPInterferenceProfileFailed NOTIFICATION-TYPE
    OBJECTS {
        fsRrmAPMacAddrTrapVariable,
        fsRrmAPRadioIDTrapVariable,
        fsRrmAPRadioTypeTrapVariable,
        fsRrmForeignInterfereTrapVariable
    }
    STATUS current
    DESCRIPTION
        "When Interference Profile state changes from PASS to FAIL,
         notification will be sent with Dot3 MAC address of FS
         AP and slot ID of FS AP IF. This trap sending can be
         enable/disable using fsRrmRrmProfileTrapControlFlag "
    ::= { fsRrmTraps 4 }

fsRrmAPPerformanceProfileFailed NOTIFICATION-TYPE
    OBJECTS {
        fsRrmAPMacAddrTrapVariable,
        fsRrmAPRadioIDTrapVariable,
        fsRrmAPRadioTypeTrapVariable,
        fsRrmThroughputTrapVariable
    }
    STATUS current
    DESCRIPTION
        " "
    ::= { fsRrmTraps 5 }

fsRrmAPClientNumProfileUpdatedToPass NOTIFICATION-TYPE
    OBJECTS {
        fsRrmAPMacAddrTrapVariable,
        fsRrmAPRadioIDTrapVariable,
        fsRrmAPRadioTypeTrapVariable,
        fsRrmClientNumberTrapVariable
    }
    STATUS current
    DESCRIPTION
        ""
    ::= { fsRrmTraps 6 }

fsRrmAPLoadProfileUpdatedToPass NOTIFICATION-TYPE
    OBJECTS {
        fsRrmAPMacAddrTrapVariable,
        fsRrmAPRadioIDTrapVariable,
        fsRrmAPRadioTypeTrapVariable,
        fsRrmUtilizationTrapVariable
    }
    STATUS current
    DESCRIPTION
        "When LOAD Profile state changes from FAIL to PASSt this
         notification will be sent with Dot3 MAC address of FS
         AP and slot ID of FS AP IF. This trap sending can be
         enable/disable using fsRrmRrmProfileTrapControlFlag "
    ::= { fsRrmTraps 7 }

fsRrmAPNoiseProfileUpdatedToPass NOTIFICATION-TYPE
    OBJECTS {
        fsRrmAPMacAddrTrapVariable,
        fsRrmAPRadioIDTrapVariable,
        fsRrmAPRadioTypeTrapVariable,
        fsRrmNoiseTrapVariable
    }
    STATUS current
    DESCRIPTION
        "When Noise Profile state changes from FAIL tp PASS,
         notification will be sent with Dot3 MAC address of FS
         AP and slot ID of FS AP IF. This trap sending can be
         enable/disable using fsRrmRrmProfileTrapControlFlag "
    ::= { fsRrmTraps 8 }

fsRrmAPInterferenceProfileUpdatedToPass NOTIFICATION-TYPE
    OBJECTS {
        fsRrmAPMacAddrTrapVariable,
        fsRrmAPRadioIDTrapVariable,
        fsRrmAPRadioTypeTrapVariable,
        fsRrmForeignInterfereTrapVariable
    }
    STATUS current
    DESCRIPTION
        "When Interference Profile state changes from FAIL tp PASS,
         notification will be sent with Dot3 MAC address of FS
         AP and slot ID of FS AP IF. This trap sending can be
         enable /disable using fsRrmRrmProfileTrapControlFlag "
    ::= { fsRrmTraps 9 }

fsRrmAPPerformanceProfileUpdatedToPass NOTIFICATION-TYPE
    OBJECTS {
        fsRrmAPMacAddrTrapVariable,
        fsRrmAPRadioIDTrapVariable,
        fsRrmAPRadioTypeTrapVariable,
        fsRrmThroughputTrapVariable
    }
    STATUS current
    DESCRIPTION
        " "
    ::= { fsRrmTraps 10 }


fsRrmAPDot11bParamUpdateTrapControlMask OBJECT-TYPE
    SYNTAX      Unsigned32
    MAX-ACCESS  read-write
    STATUS      current
    DESCRIPTION
           "Mac Parameters are updated for a FS AP interface
            whenever Dynamic Algorithm are run. This mask describes
            what update events merit traps to network management. If
            the bit for a particular event is turned on then
            notification will be generated on event occurance.
                Event                    corresponding bit
                -----                    -----------------
                TxPowerChange                  1
                ChannelChange                  2
           "
    DEFVAL { 0 }
    ::= { fsRrmTrapControl 3 }

fsRrmAPDot11aParamUpdateTrapControlMask OBJECT-TYPE
    SYNTAX      Unsigned32
    MAX-ACCESS  read-write
    STATUS      current
    DESCRIPTION
           "Mac Parameters are updated for a FS AP interface
            whenever Dynamic Algorithm are run. This mask describes
            what update events merit traps to network management. If
            the bit for a particular event is turned on then
            notification will be generated on event occurance.
                Event                    corresponding bit
                -----                    -----------------
                TxPowerChange                  1
                ChannelChange                  2
           "
    DEFVAL { 0 }
    ::= { fsRrmTrapControl 4 }

fsRrmAPCurrentTxPowerChanged NOTIFICATION-TYPE
    OBJECTS {
        fsRrmAPMacAddrTrapVariable,
        fsRrmAPRadioIDTrapVariable,
        fsRrmAPRadioTypeTrapVariable,
        fsRrmAPTxPowerBeforeChange,
        fsRrmAPTxPowerAfterChange,
        fsRrmAPTxPowerChangeCoverageFlag
    }
    STATUS current
    DESCRIPTION
        "Whenever dynamic algorithms are running and
         fsRrmAPIfPhyPowerAutomaticOn is true, FS AP Interface's
         CurrentTxPower might get updated by algorithm. When
         this occurs notification will be sent with Dot3 MAC address of
         FS AP and slot ID of FS AP IF along with the
         currentTxPower for this FS AP IF"
    ::= { fsRrmTraps 11 }

fsRrmAPCurrentChannelChanged NOTIFICATION-TYPE
    OBJECTS {
        fsRrmAPMacAddrTrapVariable,
        fsRrmAPRadioIDTrapVariable,
        fsRrmAPRadioTypeTrapVariable,
        fsRrmAPChannelNumberBeforeChannge,
        fsRrmAPChannelNumberAfterChannge,
        fsRrmAPChannelChangeReason,
        fsRrmAPChannelChangeReasonValue,
        fsRrmAPChannelChangeCount
    }
    STATUS current
    DESCRIPTION
        "Whenever dynamic algorithms are running and
         fsRrmAPIfPhyChannelAutomaticOn is true, FS AP
         Interface's CurrentChannel might get updated by algorithm.
         When this occurs notification will be sent with Dot3 MAC
         address of FS AP and slot ID of FS AP IF along
         with the currentChannel for this FS AP IF"
    ::= { fsRrmTraps 12 }


-- *************************************************************
-- Also, when dynamic grouping is done and new Group leader is choosen
-- NMS needs to be informed so that necessary updates can be done in
-- NMS.
-- *************************************************************

fsRrmDot11bGroupingDone NOTIFICATION-TYPE
    OBJECTS { fsRrmDot11bGroupLeaderMacAddrTrapVariable }
    STATUS current
    DESCRIPTION
        "When Grouping is done, this notification will be sent from the
         previous Group Leader where grouping algorithm was run. It has
         MAC address of the new Group Leader."
    ::= { fsRrmTraps 13 }

fsRrmDot11aGroupingDone NOTIFICATION-TYPE
    OBJECTS { fsRrmDot11aGroupLeaderMacAddrTrapVariable }
    STATUS current
    DESCRIPTION
        "When Grouping is done, this notification will be sent from the
         previous Group Leader where grouping algorithm was run. It has
         MAC address of the new Group Leader."
    ::= { fsRrmTraps 14 }


fsRrmDot11bDFSFreeCountBelowThreshold NOTIFICATION-TYPE
    OBJECTS { fsRrmDFSFreeCount }
    STATUS current
    DESCRIPTION
        "When the free channel in 802.11b DCA too few, this notification
         will be sent"
    ::= { fsRrmTraps 15 }

fsRrmDot11aDFSFreeCountBelowThreshold NOTIFICATION-TYPE
    OBJECTS { fsRrmDFSFreeCount }
    STATUS current
    DESCRIPTION
        "When the free channel in 802.11b DCA too few, this notification
         will be sent"
    ::= { fsRrmTraps 16 }

fsRrmNeighborAPInterference NOTIFICATION-TYPE
    OBJECTS { fsRrmAPMacAddrTrapVariable }
    STATUS current
    DESCRIPTION
        "notice when find interference form neighbor AP"
    ::= { fsRrmTraps 17 }

fsRrmStationInterference NOTIFICATION-TYPE
    OBJECTS { fsRrmAPMacAddrTrapVariable }
    STATUS current
    DESCRIPTION
        "notice when find interference form station"
    ::= { fsRrmTraps 18 }

fsRrmOtherDiveceInterference NOTIFICATION-TYPE
    OBJECTS { fsRrmAPMacAddrTrapVariable }
    STATUS current
    DESCRIPTION
        "notice when find interference form other divece"
    ::= { fsRrmTraps 19 }

--***************** define the fsRrmMIBConformance nodes ************
fsRrmMIBCompliances OBJECT IDENTIFIER ::= { fsRrmMIBConformance 1 }
fsRrmMIBGroups      OBJECT IDENTIFIER ::= { fsRrmMIBConformance 2 }

--********************************************************************
--                                                                  **
--           compliance statements                                  **
--                                                                  **
--********************************************************************
fsRrmMIBCompliance MODULE-COMPLIANCE
    STATUS  current
    DESCRIPTION
            "The compliance statement for entities which implement
            the FS RRM module"
    MODULE  -- this module
        MANDATORY-GROUPS {
            fsRrmMIBGroup,
            fsRrmTrapsGroup
        }
    ::= { fsRrmMIBCompliances 1 }

--********************************************************************
--                                                                  **
--           units of conformance                                   **
--                                                                  **
--********************************************************************
fsRrmMIBGroup OBJECT-GROUP
    OBJECTS {

--Begin rf group
        fsRrmRFNetworkName,

--Begin AP auto-rf
				fsRrmAPName,
				fsRrmAPIfThresholdRadioType,
				fsRrmAPIfForeignInterferenceThreshold,
				fsRrmAPIfForeignNoiseThreshold,
				fsRrmAPIfRFUtilizationThreshold,
				fsRrmAPIfThroughputThreshold,
				fsRrmAPIfMobilesThreshold,
				fsRrmAPIfThresholdMacAddr,
        fsRrmAPIfThresholdRadioType,
        fsRrmAPIfThresholdName,

				fsRrmAPIfLoadRxUtilization,
				fsRrmAPIfLoadTxUtilization,
				fsRrmAPIfLoadChannelUtilization,
				fsRrmAPIfLoadNumOfClients,
				fsRrmAPIfPoorSNRClients,
				fsRrmAPIfLoadName,
        fsRrmAPIfLoadMacAddr,
        fsRrmAPIfLoadSlotId,
        fsRrmAPIfThroughput,

				fsRrmAPIfInterferenceChannelNo,
				fsRrmAPIfInterferencePower,
				fsRrmAPIfInterferenceUtilization,
				fsRrmAPIfInterferenceName,
        fsRrmAPIfInterferenceMacAddr,
        fsRrmAPIfInterferenceSlotId,

				fsRrmAPIfNoiseChannelNo,
				fsRrmAPIfDBNoisePower,
				fsRrmAPIfNoiseName,
        fsRrmAPIfNoiseMacAddr,
        fsRrmAPIfNoiseSlotId,

				fsRrmAPIfLoadProfileState,
				fsRrmAPIfInterferenceProfileState,
				fsRrmAPIfNoiseProfileState,
				fsRrmAPIfCoverageProfileState,
				fsRrmAPIfPerformanceProfileState,
				fsRrmAPIfProfileName,
        fsRrmAPIfProfileMacAddr,
        fsRrmAPIfProfileSlotId,

				fsRrmAPIfRxNeighborMacAddress,
				fsRrmAPIfRxNeighborSlot,
				fsRrmAPIfRxNeighborIpAddress,
				fsRrmAPIfRxNeighborRSSI,
				fsRrmAPIfRxNeighborSNR,
				fsRrmAPIfRxNeighborChannel,
				fsRrmAPIfRxNeighborChannelWidth,
				fsRrmAPIfRxNeighborName,
        fsRrmAPIfRxNeighborMacAddr,
        fsRrmAPIfRxNeighborSlotId,

				fsRrmAPIfStationRSSICoverageIndex,
				fsRrmAPIfRSSILevel,
				fsRrmAPIfStationCountOnRSSI,
				fsRrmAPIfStationRSSIName,
        fsRrmAPIfStationRSSIMacAddr,
        fsRrmAPIfStationRSSISlotId,

				fsRrmAPIfStationSNRCoverageIndex,
				fsRrmAPIfSNRLevel,
				fsRrmAPIfStationCountOnSNR,
				fsRrmAPIfStationSNRName,
        fsRrmAPIfStationSNRMacAddr,
        fsRrmAPIfStationSNRSlotId,

				fsRrmAPIfRecommendedChannelNumber,
				fsRrmAPIfRecommendedTxPowerLevel,
				fsRrmAPIfRecommendedRTSThreshold,
				fsRrmAPIfRecommendedFragmentationThreshold,
				fsRrmAPIfRecommendedName,
        fsRrmAPIfRecommendedMacAddr,
        fsRrmAPIfRecommendedSlotId,

     		fsRrmAPRadioID,
     		fsRrmAPRadioType,
     		fsRrmAPRealName,
        fsRrmAPMacAddr,

        fsRrmAPIfThroughputMacAddr,
        fsRrmAPIfThroughputSlotId,
        fsRrmAPIfThroughputAPName,
     	fsRrmAPIfThroughputRx,
   	fsRrmAPIfThroughputTx,
   	fsRrmAPIfThroughputTotal,

        fsRrmAPSnrBSSIDMacAddr,
        fsRrmAPSnrBSSIDSlotId,
        fsRrmAPSnrBSSIDAPName,
     	fsRrmAPSnrBSSIDAverageSignalStrength,
   	fsRrmAPSnrBSSIDSignalPkts,
   	fsRrmAPSnrBSSIDHighestRxSignalStrength,
   	fsRrmAPSnrBSSIDLowestRxSignalStrength,
   	fsRrmAPSnrBSSIDSampleTime,

--Begin fsRrmDCA
        fsRrmDot11bDynamicChannelAssignment,
        fsRrmDot11bAnchorTime,
        fsRrmDot11bChannalWidth11n,
        fsRrmDot11bDynamicChannelUpdateInterval,
        fsRrmDot11bDCASensitivity,
        fsRrmDot11bForeignInterfereFactorEnable,
        fsRrmDot11bLoadFactorEnable,
        fsRrmDot11bNoiseFactorEnable,
        fsRrmDot11bChannelUpdateCmdInvoke,
        fsRrmDot11bDCAChannelIndex,
        fsRrmDot11bDCAChannelOperation,
        fsRrmDot11aDynamicChannelAssignment,
        fsRrmDot11aAnchorTime,
        fsRrmDot11aChannalWidth11n,
        fsRrmDot11aDynamicChannelUpdateInterval,
        fsRrmDot11aDCASensitivity,
        fsRrmDot11aForeignInterfereFactorEnable,
        fsRrmDot11aLoadFactorEnable,
        fsRrmDot11aNoiseFactorEnable,
        fsRrmDot11aChannelUpdateCmdInvoke,
        fsRrmDot11aDCAChannelIndex,
        fsRrmDot11aDCAChannelOperation,

--Begin fsRrmTPC
        fsRrmDot11bDTPCSupport,
        fsRrmDot11bDynamicTransmitPowerControl,
        fsRrmDot11bDynamicTxPowerControlInterval,
        fsRrmDot11bCurrentTxPowerLevel,
        fsRrmDot11bPowerUpdateCmdInvoke,
        fsRrmDot11bTXPowerThreshold,
        fsRrmDot11bTPCNeighborNumber,
        fsRrmDot11aDTPCSupport,
        fsRrmDot11aDynamicTransmitPowerControl,
        fsRrmDot11aDynamicTxPowerControlInterval,
        fsRrmDot11aCurrentTxPowerLevel,
        fsRrmDot11aPowerUpdateCmdInvoke,
        fsRrmDot11aTXPowerThreshold,
        fsRrmDot11aTPCNeighborNumber,

--Begin fsRrmCHD
        fsRrmDot11bCoverageEnable,
        fsRrmDot11bCoverageExceptionGlobal,
        fsRrmDot11bCoverageLevelGlobal,
        fsRrmDot11bCoverageDataRSSIThreshold,
        fsRrmDot11bCoverageVoiceRSSIThreshold,
        fsRrmDot11bCoverageDataPacketCount,
        fsRrmDot11bCoverageVoicePacketCount,
        fsRrmDot11bCoverageDataFailRate,
        fsRrmDot11bCoverageVoiceFailRate,
        fsRrmDot11aCoverageEnable,
        fsRrmDot11aCoverageExceptionGlobal,
        fsRrmDot11aCoverageLevelGlobal,
        fsRrmDot11aCoverageDataRSSIThreshold,
        fsRrmDot11aCoverageVoiceRSSIThreshold,
        fsRrmDot11aCoverageDataPacketCount,
        fsRrmDot11aCoverageVoicePacketCount,
        fsRrmDot11aCoverageDataFailRate,
        fsRrmDot11aCoverageVoiceFailRate,

--Begin fsRrmGroup
        fsRrmDot11bGlobalAutomaticGrouping,
        fsRrmDot11bGroupLeaderMacAddr,
        fsRrmDot11bGroupLeader,
        fsRrmDot11bGroupLastUpdateTime,
        fsRrmDot11bGroupInterval,
        fsRrmDot11bPeerMacAddress,
        fsRrmDot11bPeerIpAddress,
        fsRrmDot11bAPname,
        fsRrmDot11bAPRadioID,
        fsRrmDot11bAPChannel,
        fsRrmDot11bAPTxPower,
        fsRrmDot11bAPChannelRrmChangeFlag,
        fsRrmDot11bAPTxPowerRrmChangeFlag,
        fsRrmDot11bSummaryMacAddress,

        fsRrmDot11aGlobalAutomaticGrouping,
        fsRrmDot11aGroupLeader,
        fsRrmDot11aGroupLastUpdateTime,
        fsRrmDot11aGroupInterval,
        fsRrmDot11aPeerMacAddress,
        fsRrmDot11aPeerIpAddress,
        fsRrmDot11aAPname,
        fsRrmDot11aAPRadioID,
        fsRrmDot11aAPChannel,
        fsRrmDot11aAPTxPower,
        fsRrmDot11aAPChannelRrmChangeFlag,
        fsRrmDot11aAPTxPowerRrmChangeFlag,
        fsRrmDot11aSummaryMacAddress,

--Begin fsRrmProfile
        fsRrmDot11bForeignInterferenceThreshold,
        fsRrmDot11bForeignNoiseThreshold,
        fsRrmDot11bRFUtilizationThreshold,
        fsRrmDot11bThroughputThreshold,
        fsRrmDot11bMobilesThreshold,
        fsRrmDot11aForeignInterferenceThreshold,
        fsRrmDot11aForeignNoiseThreshold,
        fsRrmDot11aRFUtilizationThreshold,
        fsRrmDot11aThroughputThreshold,
        fsRrmDot11aMobilesThreshold,

--Begin fsRrmMonitor
        fsRrmDot11bMonitorEnable,
        fsRrmDot11bChannelMonitorList,
        fsRrmDot11bMonitorInterval,
        fsRrmDot11bCoverageMeasurementInterval,
        fsRrmDot11bLoadMeasurementInterval,
        fsRrmDot11bNoiseMeasurementInterval,
        fsRrmDot11bSignalMeasurementInterval,
        fsRrmDot11bNeighborMessageInterval,
        fsRrmDot11aMonitorEnable,
        fsRrmDot11aChannelMonitorList,
        fsRrmDot11aMonitorInterval,
        fsRrmDot11aCoverageMeasurementInterval,
        fsRrmDot11aLoadMeasurementInterval,
        fsRrmDot11aNoiseMeasurementInterval,
        fsRrmDot11aSignalMeasurementInterval,
        fsRrmDot11aNeighborMessageInterval,

--Begin fsRrmFactory
        fsRrmDot11bSetFactoryDefault,
        fsRrmDot11aSetFactoryDefault
    }
    STATUS      current
    DESCRIPTION
        "This collection of objects provide the information
         about FS Radio Resource Management Configuration
         Parameters. These objects are defined under fsRrmRrm object."
    ::= { fsRrmMIBGroups 1 }

fsRrmTrapsGroup OBJECT-GROUP
    OBJECTS {
--Begin fsRrmTrapControl
        fsRrmAPDot11bProfileTrapControlMask,
        fsRrmAPDot11aProfileTrapControlMask,
        fsRrmAPDot11bParamUpdateTrapControlMask,
        fsRrmAPDot11aParamUpdateTrapControlMask,

--Begin fsRrmTrapVariable
-- for Ap info
        fsRrmAPMacAddrTrapVariable,
        fsRrmAPRadioIDTrapVariable,
        fsRrmAPRadioTypeTrapVariable,
-- for Trap value
        fsRrmClientNumberTrapVariable,
        fsRrmForeignInterfereTrapVariable,
        fsRrmNoiseTrapVariable,
        fsRrmThroughputTrapVariable,
        fsRrmUtilizationTrapVariable,
-- for TPC
        fsRrmAPTxPowerBeforeChange,
        fsRrmAPTxPowerAfterChange,
        fsRrmAPTxPowerChangeCoverageFlag,

-- for DCA
        fsRrmAPChannelNumberBeforeChannge,
        fsRrmAPChannelNumberAfterChannge,
        fsRrmAPChannelChangeReason,
        fsRrmAPChannelChangeReasonValue,
        fsRrmAPChannelChangeCount,
        fsRrmDFSFreeCount,

-- for leader
        fsRrmDot11bGroupLeaderMacAddrTrapVariable,
        fsRrmDot11aGroupLeaderMacAddrTrapVariable
    }
    STATUS      current
    DESCRIPTION
        "This collection of objects provide the information
         about FS Trap Configuration and Trap definition.
         These objects are defined under fsRrmTrap."
    ::= { fsRrmMIBGroups 2 }

fsRrmTrap NOTIFICATION-GROUP
    NOTIFICATIONS {
        fsRrmAPClientNumProfileFailed,
        fsRrmAPLoadProfileFailed,
        fsRrmAPNoiseProfileFailed,
        fsRrmAPInterferenceProfileFailed,
        fsRrmAPPerformanceProfileFailed,
        fsRrmAPClientNumProfileUpdatedToPass,
        fsRrmAPLoadProfileUpdatedToPass,
        fsRrmAPNoiseProfileUpdatedToPass,
        fsRrmAPInterferenceProfileUpdatedToPass,
        fsRrmAPPerformanceProfileUpdatedToPass,
        fsRrmAPCurrentTxPowerChanged,
        fsRrmAPCurrentChannelChanged,
        fsRrmDot11bGroupingDone,
        fsRrmDot11aGroupingDone,
        fsRrmDot11bDFSFreeCountBelowThreshold,
        fsRrmDot11aDFSFreeCountBelowThreshold,
        fsRrmNeighborAPInterference,
        fsRrmStationInterference,
        fsRrmOtherDiveceInterference
    }
    STATUS      current
    DESCRIPTION
        "This  collection of objects provides all notification
         that Switch need to generate to the Management System."
    ::= { fsRrmMIBGroups 3 }

END
