-- *******************************************************************
-- FS-WLAN-FAT-AP-IN-MIB.mib : FS MIB
-- February 2010, ruanyucheng
--
-- Copyright (c) 2010 by FS.COM Inc..
-- All rights reserved.
-- *******************************************************************
FS-WLAN-FAT-AP-IN-MIB DEFINITIONS ::= BEGIN
    IMPORTS
        MODULE-IDENTITY,
        OBJECT-TYPE,
        Integer32,
        IpAddress,
        Unsigned32,
        TimeTicks
            FROM SNMPv2-SMI
        TruthValue,
        DisplayString,
        MacAddress,
        RowStatus
            FROM SNMPv2-TC
        Gauge
            FROM RFC1155-SMI
        MODULE-COMPLIANCE,
        NOTIFICATION-GROUP,
        OBJECT-GROUP
            FROM SNMPv2-CONF
        fsApgWlanId
            FROM FS-AC-MGMT-MIB
        ifIndex
            FROM RFC1213-MIB
        fsMgmt
            FROM FS-SMI;
--*******************************************
--* module definition
--*******************************************
fsStandardmibmodule MODULE-IDENTITY
    LAST-UPDATED    "201002260000Z"
    ORGANIZATION
        "FS.COM Inc.."
    CONTACT-INFO
        "Tel: 400-865-2852
           E-mail: https://www.fs.com/live_chat_service_mail.html "

    DESCRIPTION
       "
       Wlan software private MIB for FS SNC according to the China
       Mobile standard. This is device manage MIB.
       "
    REVISION      "201002280000Z"
    DESCRIPTION
       "Initial version of this MIB module."

    ::= { fsMgmt  82 }



fsStandardTraps               OBJECT IDENTIFIER  ::= { fsStandardmibmodule 0 }
fsConfigInfoObjects           OBJECT IDENTIFIER  ::= { fsStandardmibmodule 1 }
fsPerformanceStatObjects      OBJECT IDENTIFIER  ::= { fsStandardmibmodule 2 }

fsSysInfoConfig               OBJECT IDENTIFIER  ::= { fsConfigInfoObjects 1 }
fsRadioInfoConfig             OBJECT IDENTIFIER  ::= { fsConfigInfoObjects 2 }
fsWapiConfig                  OBJECT IDENTIFIER  ::= { fsConfigInfoObjects 3 }
fsAdminInfoConfig             OBJECT IDENTIFIER  ::= { fsConfigInfoObjects 4 }
fsPollTimeConfig              OBJECT IDENTIFIER  ::= { fsConfigInfoObjects 5 }

fsAirIfServiceStat            OBJECT IDENTIFIER  ::= { fsPerformanceStatObjects 1 }
fsTermServiceStat             OBJECT IDENTIFIER  ::= { fsPerformanceStatObjects 2 }


--**************************************************
--* Traps begin here
--**************************************************

fsRadioPortTrap NOTIFICATION-TYPE
    STATUS  current
    DESCRIPTION
            " Radio port trap."
    ::= { fsStandardTraps 1 }

--**************************************************
--* Traps end here
--**************************************************

--**************************************************
--* fsSysInfoConfig begins here
--**************************************************

fsDomain OBJECT-TYPE
    SYNTAX DisplayString
    MAX-ACCESS read-only
    STATUS current
    DESCRIPTION
        "The domain of the AP."
    ::= { fsSysInfoConfig 1}

fsLayer2Isolate OBJECT-TYPE
    SYNTAX INTEGER
    MAX-ACCESS read-write
    STATUS current
    DESCRIPTION
        "Is layer 2 isolation opened."
    ::= { fsSysInfoConfig 2}

fsDosAttackProtect OBJECT-TYPE
    SYNTAX INTEGER
    MAX-ACCESS read-write
    STATUS current
    DESCRIPTION
        "Is DOS attack protected."
    ::= { fsSysInfoConfig 3}

--**************************************************
--* fsVlanConfigTable begins
--**************************************************
fsVlanConfigTable OBJECT-TYPE
    SYNTAX SEQUENCE OF FSVlanConfigEntry
    MAX-ACCESS not-accessible
    STATUS current
    DESCRIPTION
        "Configuration of vlan"
    ::= { fsSysInfoConfig 4 }

fsVlanConfigEntry OBJECT-TYPE
    SYNTAX FSVlanConfigEntry
    MAX-ACCESS not-accessible
    STATUS current
    DESCRIPTION
        "The entry of apVlanConfigTable."
    INDEX
    { fsWlanId}
    ::= { fsVlanConfigTable 1 }

FSVlanConfigEntry ::=
    SEQUENCE {
        fsVlanId                        INTEGER,
        fsSSID													DisplayString
        }

fsVlanId OBJECT-TYPE
    SYNTAX INTEGER
    MAX-ACCESS read-create
    STATUS current
    DESCRIPTION
        "Vlan ID."
    ::= { fsVlanConfigEntry 1 }

fsSSID OBJECT-TYPE
    SYNTAX DisplayString
    MAX-ACCESS read-create
    STATUS current
    DESCRIPTION
        "SSID."
    ::= { fsVlanConfigEntry 2 }


--**************************************************
--* fsVlanConfigTable ends
--**************************************************


--**************************************************
--* fsSysInfoConfig ends here
--**************************************************

--**************************************************
--* fsRadioInfoConfig begins here
--**************************************************


--**************************************************
--* fsRadioConfigTable begins
--**************************************************
fsRadioConfigTable OBJECT-TYPE
    SYNTAX SEQUENCE OF FSRadioConfigEntry
    MAX-ACCESS not-accessible
    STATUS current
    DESCRIPTION
        "Configuration of Radio"
    ::= { fsRadioInfoConfig 1 }

fsRadioConfigEntry OBJECT-TYPE
    SYNTAX FSRadioConfigEntry
    MAX-ACCESS not-accessible
    STATUS current
    DESCRIPTION
        "The entry of apRadioConfigTable."
    INDEX
    { ifIndex }
    ::= { fsRadioConfigTable 1 }

FSRadioConfigEntry ::=
    SEQUENCE {
	fsSSIDNum  		 INTEGER,
	fsRadioSecurityMch   INTEGER ,
	fsRadioSecurityParam DisplayString,
	fsRadioQos           INTEGER,
	fsRtsCtsThreshold    INTEGER,
        fsMaxUserPermit 	 INTEGER,
	fsUserNumOnLine      INTEGER,
	fsAirInterfaceType 	 INTEGER,
        fsChannelMode        INTEGER,
    	fsCurrentChannel	 INTEGER,
    	fsSNR	 	 INTEGER,
    	fsHoppingTimes	 INTEGER,
        fsHopDetectItvTime 	 INTEGER,
        fsPowerMgr     	 INTEGER,
    	fsTxPower		 INTEGER
        }
fsSSIDNum OBJECT-TYPE
    SYNTAX INTEGER
    MAX-ACCESS read-only
    STATUS current
    DESCRIPTION
        "SSID number."
    ::= { fsRadioConfigEntry 1 }

fsRadioSecurityMch OBJECT-TYPE
    SYNTAX INTEGER
    MAX-ACCESS read-write
    STATUS current
    DESCRIPTION
        "Radio security mechanism of the AP."
    ::= { fsRadioConfigEntry 2 }

fsRadioSecurityParam OBJECT-TYPE
    SYNTAX DisplayString
    MAX-ACCESS read-write
    STATUS current
    DESCRIPTION
        "Radio security parameter of the AP."
    ::= { fsRadioConfigEntry 3 }

fsRadioQos OBJECT-TYPE
    SYNTAX INTEGER
    MAX-ACCESS read-write
    STATUS current
    DESCRIPTION
        "Whether to activate VMM."
    ::= { fsRadioConfigEntry 4 }

fsRtsCtsThreshold OBJECT-TYPE
    SYNTAX INTEGER
    MAX-ACCESS read-write
    STATUS current
    DESCRIPTION
        "RTS/CTS threshold"
    ::= { fsRadioConfigEntry 5 }

fsMaxUserPermit OBJECT-TYPE
    SYNTAX INTEGER
    MAX-ACCESS read-write
    STATUS current
    DESCRIPTION
        "Max user number permited"
    ::= { fsRadioConfigEntry 6 }

fsUserNumOnLine OBJECT-TYPE
    SYNTAX INTEGER
    MAX-ACCESS read-only
    STATUS current
    DESCRIPTION
        "User number on line"
    ::= { fsRadioConfigEntry 7 }

fsAirInterfaceType OBJECT-TYPE
    SYNTAX INTEGER
    MAX-ACCESS read-write
    STATUS current
    DESCRIPTION
        "Air interface type"
    ::= { fsRadioConfigEntry 8 }

fsChannelMode OBJECT-TYPE
    SYNTAX INTEGER
    MAX-ACCESS read-write
    STATUS current
    DESCRIPTION
        "Channel mode of the AP."
    ::= { fsRadioConfigEntry 9 }

fsCurrentChannel OBJECT-TYPE
    SYNTAX INTEGER
    MAX-ACCESS read-write
    STATUS current
    DESCRIPTION
        "Current channel."
    ::= { fsRadioConfigEntry 10 }

fsSNR OBJECT-TYPE
    SYNTAX INTEGER
    MAX-ACCESS read-only
    STATUS current
    DESCRIPTION
        "Signal noise ratio."
    ::= { fsRadioConfigEntry 11 }

fsHoppingTimes OBJECT-TYPE
    SYNTAX INTEGER
    MAX-ACCESS read-only
    STATUS current
    DESCRIPTION
        "Frequency hopping times"
    ::= { fsRadioConfigEntry 12 }

fsHopDetectItvTime OBJECT-TYPE
    SYNTAX INTEGER
    MAX-ACCESS read-write
    STATUS current
    DESCRIPTION
        "Inteval time of hopping detection"
    ::= { fsRadioConfigEntry 13 }

fsPowerMgr OBJECT-TYPE
    SYNTAX INTEGER
    MAX-ACCESS read-write
    STATUS current
    DESCRIPTION
        "Power management of the AP"
    ::= { fsRadioConfigEntry 14 }

fsTxPower OBJECT-TYPE
    SYNTAX INTEGER
    MAX-ACCESS read-only
    STATUS current
    DESCRIPTION
        "Current transmit power of the AP"
    ::= { fsRadioConfigEntry 15 }


--**************************************************
--* fsRadioConfigTable ends
--**************************************************


--**************************************************
--* fsRadioInfoConfig ends here
--**************************************************


--**************************************************
--* fsWapiConfig begins here
--**************************************************


--**************************************************
--* fsWapiConfigTable begins
--**************************************************

fsWapiConfigTable OBJECT-TYPE
    SYNTAX SEQUENCE OF FSWapiConfigEntry
    MAX-ACCESS not-accessible
    STATUS current
    DESCRIPTION
        "The table describe the wapi cofiguration the AP."
    ::= { fsWapiConfig 1	 }

fsWapiConfigEntry OBJECT-TYPE
    SYNTAX FSWapiConfigEntry
    MAX-ACCESS not-accessible
    STATUS current
    DESCRIPTION
        "The entry of fsWapiConfigTable."
    INDEX
    { fsWlanId }
    ::= { fsWapiConfigTable 1 }


FSWapiConfigEntry ::=
    SEQUENCE {
        fsWlanId								INTEGER,
        fsTrustASCfg            INTEGER,
        fsCertType              INTEGER,
        fsCertState							INTEGER,
        fsCertSetup             INTEGER
    }

fsWlanId OBJECT-TYPE
    SYNTAX INTEGER
    MAX-ACCESS read-only
    STATUS current
    DESCRIPTION
        "Index of the table."
    ::= { fsWapiConfigEntry 1 }

fsTrustASCfg OBJECT-TYPE
    SYNTAX INTEGER
    MAX-ACCESS read-write
    STATUS current
    DESCRIPTION
        "AS config trust by AP."
    ::= { fsWapiConfigEntry 2 }

fsCertType OBJECT-TYPE
    SYNTAX INTEGER
    MAX-ACCESS read-only
    STATUS current
    DESCRIPTION
        "Certificate type."
    ::= { fsWapiConfigEntry 3 }

fsCertState OBJECT-TYPE
    SYNTAX INTEGER
    MAX-ACCESS read-only
    STATUS current
    DESCRIPTION
        "Certificate state."
    ::= { fsWapiConfigEntry 4 }

fsCertSetup OBJECT-TYPE
    SYNTAX INTEGER
    MAX-ACCESS read-write
    STATUS current
    DESCRIPTION
        "Certificate setup."
    ::= { fsWapiConfigEntry 5 }

--**************************************************
--* fsWapiConfigTable ends
--**************************************************

--**************************************************
--* fsWapiConfig ends here
--**************************************************


--**************************************************
--*fsAdminInfoConfig
--**************************************************
fsAdminName OBJECT-TYPE
    SYNTAX DisplayString  (SIZE(1..32))
    MAX-ACCESS read-write
    STATUS current
				DESCRIPTION
           "The name of the administrator."
		::= { fsAdminInfoConfig 1 }

fsAdminPwd OBJECT-TYPE
    SYNTAX DisplayString  (SIZE(1..32))
    MAX-ACCESS read-write
    STATUS current
				DESCRIPTION
           "The password of the administrator."
		::= { fsAdminInfoConfig 2 }


--**************************************************
--*fsPollTimeConfig
--**************************************************
fsPollTimeOfLast OBJECT-TYPE
    SYNTAX TimeTicks
    MAX-ACCESS read-only
    STATUS current
				DESCRIPTION
           "The last time of administrator
            poll the devices."
		::= { fsPollTimeConfig 1 }


--**************************************************
--* fsAirIfServiceStat begins here
--**************************************************
fsUplinkTotalDataFrameNum OBJECT-TYPE
    SYNTAX INTEGER
    MAX-ACCESS read-only
    STATUS current
    DESCRIPTION
        "Total uplink data frame number of channel during AP running time."
    ::= { fsAirIfServiceStat 1}

fsDownlinkTotalDataFrameNum OBJECT-TYPE
    SYNTAX INTEGER
    MAX-ACCESS read-only
    STATUS current
    DESCRIPTION
        "Total downlink data frame number of channel during AP running time."
    ::= { fsAirIfServiceStat 2}

fsDownlinkTotalLostDataFrameNum OBJECT-TYPE
    SYNTAX INTEGER
    MAX-ACCESS read-only
    STATUS current
    DESCRIPTION
        "Total downlink lost data frame number of channel during AP running time."
    ::= { fsAirIfServiceStat 3}



fsTotalSignalFrameNum OBJECT-TYPE
    SYNTAX INTEGER
    MAX-ACCESS read-only
    STATUS current
    DESCRIPTION
        "Total signal frame number of the AP."
    ::= { fsAirIfServiceStat 4}

fsCorrectPkgByteRxByMAC OBJECT-TYPE
    SYNTAX INTEGER
    MAX-ACCESS read-only
    STATUS current
    DESCRIPTION
        "Total correct package byte number receive by MAC layer."
    ::= { fsAirIfServiceStat 5}

fsPkgByteTxByMAC OBJECT-TYPE
    SYNTAX INTEGER
    MAX-ACCESS read-only
    STATUS current
    DESCRIPTION
        "Total package byte number  transmit by MAC layer."
    ::= { fsAirIfServiceStat 6}

fsUplinkPortFlow OBJECT-TYPE
    SYNTAX INTEGER
    MAX-ACCESS read-only
    STATUS current
    DESCRIPTION
        "Radio uplink port flow of the AP."
    ::= { fsAirIfServiceStat 7}


fsDownlinkPortFlow OBJECT-TYPE
    SYNTAX INTEGER
    MAX-ACCESS read-only
    STATUS current
    DESCRIPTION
        "Radio downlink port flow of the AP."
    ::= { fsAirIfServiceStat 8}


--**************************************************
--* fsAirIfServiceStat ends here
--**************************************************


--**************************************************
--* fsTermServiceStat begins here
--**************************************************

fsTotalUserNum OBJECT-TYPE
    SYNTAX INTEGER
    MAX-ACCESS read-only
    STATUS current
    DESCRIPTION
        "Total user number that have connected to the AP."
    ::= { fsTermServiceStat 1}


fsUserAccumulateTime OBJECT-TYPE
    SYNTAX INTEGER
    MAX-ACCESS read-only
    STATUS current
    DESCRIPTION
        "Total accumulation time of all users that have connected to the AP."
    ::= { fsTermServiceStat 2}



--**************************************************
--* fsTermServiceStatSSIDTable begins
--**************************************************

fsTermServiceStatSSIDTable OBJECT-TYPE
    SYNTAX SEQUENCE OF FSTermServiceStatSSIDEntry
    MAX-ACCESS not-accessible
    STATUS current
    DESCRIPTION
        "Statistic of air terminal service by SSID."
    ::= { fsTermServiceStat 34	 }

fsTermServiceStatSSIDEntry OBJECT-TYPE
    SYNTAX FSTermServiceStatSSIDEntry
    MAX-ACCESS not-accessible
    STATUS current
    DESCRIPTION
        "The entry of apTermServiceStatSSIDTable."
    INDEX
    { fsWlanId }
    ::= { fsTermServiceStatSSIDTable 1 }

FSTermServiceStatSSIDEntry ::=
    SEQUENCE {
        fsCorrectPkgByteRxByMACBySSID                       INTEGER,
        fsPkgByteTxByMACBySSID    						              INTEGER,
        fsAirIfResUsageRatio									              INTEGER,
        fsTotalAssociationUserNum                           INTEGER,
        fsOnlineUserNum												              INTEGER,
        fsUserReqAccessTimes									              INTEGER,
        fsResponseReqAccessTimes							              INTEGER,
        fsSuccessAccessTimes									              INTEGER,
				fsIneffiLinkVerifyFailTime													INTEGER,
				fsTimeoutLinkVerifyFailTime	                        INTEGER,
				fsInefficiencyLinkVerifyFailTime                    INTEGER,
				fsOtherReasonLinkVerifyFailTime                     INTEGER,
				fsIneffiAssociationFailTime                         INTEGER,
				fsTimeoutAssociationFailTime                        INTEGER,
				fsInefficiencyAssociationFailTime                   INTEGER,
				fsOtherReasonAssociationFailTime                    INTEGER,
				fsTotalReassociationAtmptTimes                      INTEGER,
				fsTotalReassociationSuccessTimes                    INTEGER,
				fsIneffiReassociationFailTime                       INTEGER,
				fsTimeoutReassociationFailTime                      INTEGER,
				fsInefficiencyReassociationFailTime                 INTEGER,
				fsOtherReasonReassociationFailTime                  INTEGER,
				fsTotalIdentificationAtmptTimes                     INTEGER,
				fsTotalIdentificationSuccessTimes                   INTEGER,
				fsPwdErrorIdentifyFailTime                          INTEGER,
				fsIneffiIdentificationFailTime                      INTEGER,
				fsTimeoutIdentificationFailTime                     INTEGER,
				fsInefficiencyIdentificationFailTime                INTEGER,
				fsOtherReasonIdentificationFailTime                 INTEGER,
				fsTotalRemoveLinkVerifyFailTimes                    INTEGER,
				fsLeaveAPCoverageRemoveLinkVerifyFailTimes          INTEGER,
				fsInefficiencyRemoveLinkVerifyFailTime              INTEGER,
				fsLinkVerifyFailRemoveLinkVerifyFailTime            INTEGER,
				fsOtherReasonRemoveLinkVerifyFailTime               INTEGER,
				fsTotalRemoveLinkAssociationTimes                   INTEGER,
				fsLeaveAPCoverageRemoveAssociationFailTimes         INTEGER,
				fsInefficiencyRemoveAssociationFailTime             INTEGER,
				fsAssociationFailRemoveAssociationFailTime          INTEGER,
				fsOtherReasonRemoveAssociationFailTime              INTEGER
    }

fsCorrectPkgByteRxByMACBySSID OBJECT-TYPE
    SYNTAX INTEGER
    MAX-ACCESS read-only
    STATUS current
    DESCRIPTION
        "Total correct package byte number receive by MAC layer."
    ::= { fsTermServiceStatSSIDEntry 1}

fsPkgByteTxByMACBySSID OBJECT-TYPE
    SYNTAX INTEGER
    MAX-ACCESS read-only
    STATUS current
    DESCRIPTION
        "Total package byte number  transmit by MAC layer."
    ::= { fsTermServiceStatSSIDEntry 2}

fsAirIfResUsageRatio OBJECT-TYPE
    SYNTAX INTEGER
    MAX-ACCESS read-only
    STATUS current
    DESCRIPTION
        "Resource usage ratio of AP air interface."
    ::= { fsTermServiceStatSSIDEntry 3}

fsTotalAssociationUserNum OBJECT-TYPE
    SYNTAX INTEGER
    MAX-ACCESS read-only
    STATUS current
    DESCRIPTION
        "Total number of users associated to the AP."
    ::= { fsTermServiceStatSSIDEntry 4}

fsOnlineUserNum OBJECT-TYPE
    SYNTAX INTEGER
    MAX-ACCESS read-only
    STATUS current
    DESCRIPTION
        "Number of users online."
    ::= { fsTermServiceStatSSIDEntry 5}

fsUserReqAccessTimes OBJECT-TYPE
    SYNTAX INTEGER
    MAX-ACCESS read-only
    STATUS current
    DESCRIPTION
        "Times of request initiate by the user."
    ::= { fsTermServiceStatSSIDEntry 6}

fsResponseReqAccessTimes OBJECT-TYPE
    SYNTAX INTEGER
    MAX-ACCESS read-only
    STATUS current
    DESCRIPTION
        "Times of correct response to user access request."
    ::= { fsTermServiceStatSSIDEntry 7}

fsSuccessAccessTimes OBJECT-TYPE
    SYNTAX INTEGER
    MAX-ACCESS read-only
    STATUS current
    DESCRIPTION
        "Times of succeed access to the AP."
    ::= { fsTermServiceStatSSIDEntry 8}

fsIneffiLinkVerifyFailTime OBJECT-TYPE
    SYNTAX INTEGER
    MAX-ACCESS read-only
    STATUS current
    DESCRIPTION
        "Total link verify failure times due to algorithm or transform SN discrepancy."
    ::= { fsTermServiceStatSSIDEntry 9}

fsTimeoutLinkVerifyFailTime OBJECT-TYPE
    SYNTAX INTEGER
    MAX-ACCESS read-only
    STATUS current
    DESCRIPTION
        "Total link verify failure times due to timeout."
    ::= { fsTermServiceStatSSIDEntry 10}

fsInefficiencyLinkVerifyFailTime OBJECT-TYPE
    SYNTAX INTEGER
    MAX-ACCESS read-only
    STATUS current
    DESCRIPTION
        "Total link verify failure times due to inefficiency."
    ::= { fsTermServiceStatSSIDEntry 11}

fsOtherReasonLinkVerifyFailTime OBJECT-TYPE
    SYNTAX INTEGER
    MAX-ACCESS read-only
    STATUS current
    DESCRIPTION
        "Total link verify failure times due to other reason."
    ::= { fsTermServiceStatSSIDEntry 12}

fsIneffiAssociationFailTime OBJECT-TYPE
    SYNTAX INTEGER
    MAX-ACCESS read-only
    STATUS current
    DESCRIPTION
        "Total Association failure times due to algorithm or transform SN discrepancy."
    ::= { fsTermServiceStatSSIDEntry 13}

fsTimeoutAssociationFailTime OBJECT-TYPE
    SYNTAX INTEGER
    MAX-ACCESS read-only
    STATUS current
    DESCRIPTION
        "Total Association failure times due to timeout."
    ::= { fsTermServiceStatSSIDEntry 14}

fsInefficiencyAssociationFailTime OBJECT-TYPE
    SYNTAX INTEGER
    MAX-ACCESS read-only
    STATUS current
    DESCRIPTION
        "Total Association failure times due to inefficiency."
    ::= { fsTermServiceStatSSIDEntry 15}

fsOtherReasonAssociationFailTime OBJECT-TYPE
    SYNTAX INTEGER
    MAX-ACCESS read-only
    STATUS current
    DESCRIPTION
        "Total Association failure times due to other reason."
    ::= { fsTermServiceStatSSIDEntry 16}

fsTotalReassociationAtmptTimes OBJECT-TYPE
    SYNTAX INTEGER
    MAX-ACCESS read-only
    STATUS current
    DESCRIPTION
        "Total re-association attempt times."
    ::= { fsTermServiceStatSSIDEntry 17}

fsTotalReassociationSuccessTimes OBJECT-TYPE
    SYNTAX INTEGER
    MAX-ACCESS read-only
    STATUS current
    DESCRIPTION
        "Total re-association success times."
    ::= { fsTermServiceStatSSIDEntry 18}

fsIneffiReassociationFailTime OBJECT-TYPE
    SYNTAX INTEGER
    MAX-ACCESS read-only
    STATUS current
    DESCRIPTION
        "Total Reassociation failure times due to algorithm or transform SN discrepancy."
    ::= { fsTermServiceStatSSIDEntry 19}

fsTimeoutReassociationFailTime OBJECT-TYPE
    SYNTAX INTEGER
    MAX-ACCESS read-only
    STATUS current
    DESCRIPTION
        "Total Reassociation failure times due to timeout."
    ::= { fsTermServiceStatSSIDEntry 20}

fsInefficiencyReassociationFailTime OBJECT-TYPE
    SYNTAX INTEGER
    MAX-ACCESS read-only
    STATUS current
    DESCRIPTION
        "Total Reassociation failure times due to inefficiency."
    ::= { fsTermServiceStatSSIDEntry 21}

fsOtherReasonReassociationFailTime OBJECT-TYPE
    SYNTAX INTEGER
    MAX-ACCESS read-only
    STATUS current
    DESCRIPTION
        "Total Reassociation failure times due to other reason."
    ::= { fsTermServiceStatSSIDEntry 22}

fsTotalIdentificationAtmptTimes OBJECT-TYPE
    SYNTAX INTEGER
    MAX-ACCESS read-only
    STATUS current
    DESCRIPTION
        "Total Identification attempt times."
    ::= { fsTermServiceStatSSIDEntry 23}

fsTotalIdentificationSuccessTimes OBJECT-TYPE
    SYNTAX INTEGER
    MAX-ACCESS read-only
    STATUS current
    DESCRIPTION
        "Total Identification success times."
    ::= { fsTermServiceStatSSIDEntry 24}

fsPwdErrorIdentifyFailTime OBJECT-TYPE
    SYNTAX INTEGER
    MAX-ACCESS read-only
    STATUS current
    DESCRIPTION
        "Total identification failure times due to password error."
    ::= { fsTermServiceStatSSIDEntry 25}

fsIneffiIdentificationFailTime OBJECT-TYPE
    SYNTAX INTEGER
    MAX-ACCESS read-only
    STATUS current
    DESCRIPTION
        "Total Identification failure times due to algorithm or transform SN discrepancy."
    ::= { fsTermServiceStatSSIDEntry 26}

fsTimeoutIdentificationFailTime OBJECT-TYPE
    SYNTAX INTEGER
    MAX-ACCESS read-only
    STATUS current
    DESCRIPTION
        "Total Identification failure times due to timeout."
    ::= { fsTermServiceStatSSIDEntry 27}

fsInefficiencyIdentificationFailTime OBJECT-TYPE
    SYNTAX INTEGER
    MAX-ACCESS read-only
    STATUS current
    DESCRIPTION
        "Total Identification failure times due to inefficiency."
    ::= { fsTermServiceStatSSIDEntry 28}

fsOtherReasonIdentificationFailTime OBJECT-TYPE
    SYNTAX INTEGER
    MAX-ACCESS read-only
    STATUS current
    DESCRIPTION
        "Total Identification failure times due to other reason."
    ::= { fsTermServiceStatSSIDEntry 29}

fsTotalRemoveLinkVerifyFailTimes OBJECT-TYPE
    SYNTAX INTEGER
    MAX-ACCESS read-only
    STATUS current
    DESCRIPTION
        "Total failure times of removing link verification."
    ::= { fsTermServiceStatSSIDEntry 30}

fsLeaveAPCoverageRemoveLinkVerifyFailTimes OBJECT-TYPE
    SYNTAX INTEGER
    MAX-ACCESS read-only
    STATUS current
    DESCRIPTION
        "Total failure times due to leaving AP coverage area."
    ::= { fsTermServiceStatSSIDEntry 31}

fsInefficiencyRemoveLinkVerifyFailTime OBJECT-TYPE
    SYNTAX INTEGER
    MAX-ACCESS read-only
    STATUS current
    DESCRIPTION
        "Total remove link failure times due to inefficiency."
    ::= { fsTermServiceStatSSIDEntry 32}

fsLinkVerifyFailRemoveLinkVerifyFailTime OBJECT-TYPE
    SYNTAX INTEGER
    MAX-ACCESS read-only
    STATUS current
    DESCRIPTION
        "Total remove link failure times due to link verify failure."
    ::= { fsTermServiceStatSSIDEntry 33}

fsOtherReasonRemoveLinkVerifyFailTime OBJECT-TYPE
    SYNTAX INTEGER
    MAX-ACCESS read-only
    STATUS current
    DESCRIPTION
        "Total remove link failure times due to other reason."
    ::= { fsTermServiceStatSSIDEntry 34}

fsTotalRemoveLinkAssociationTimes OBJECT-TYPE
    SYNTAX INTEGER
    MAX-ACCESS read-only
    STATUS current
    DESCRIPTION
        "Total failure times of removing association."
    ::= { fsTermServiceStatSSIDEntry 35}

fsLeaveAPCoverageRemoveAssociationFailTimes OBJECT-TYPE
    SYNTAX INTEGER
    MAX-ACCESS read-only
    STATUS current
    DESCRIPTION
        "Total remove association failure times due to leaving AP coverage area."
    ::= { fsTermServiceStatSSIDEntry 36}

fsInefficiencyRemoveAssociationFailTime OBJECT-TYPE
    SYNTAX INTEGER
    MAX-ACCESS read-only
    STATUS current
    DESCRIPTION
        "Total remove association failure times due to inefficiency."
    ::= { fsTermServiceStatSSIDEntry 37}

fsAssociationFailRemoveAssociationFailTime OBJECT-TYPE
    SYNTAX INTEGER
    MAX-ACCESS read-only
    STATUS current
    DESCRIPTION
        "Total remove association failure times due to link verify failure."
    ::= { fsTermServiceStatSSIDEntry 38}

fsOtherReasonRemoveAssociationFailTime OBJECT-TYPE
    SYNTAX INTEGER
    MAX-ACCESS read-only
    STATUS current
    DESCRIPTION
        "Total remove association failure times due to other reason."
    ::= { fsTermServiceStatSSIDEntry 39}


--**************************************************
--* fsTermServiceStatSSIDTable ends
--**************************************************


--**************************************************
--* fsUserMacAddrTable begins
--**************************************************

fsUserMacAddrTable OBJECT-TYPE
    SYNTAX SEQUENCE OF FSUserMacAddrEntry
    MAX-ACCESS not-accessible
    STATUS current
    DESCRIPTION
        "Statistic of user MAC address by SSID."
    ::= { fsTermServiceStat 35	 }

fsUserMacAddrEntry OBJECT-TYPE
    SYNTAX FSUserMacAddrEntry
    MAX-ACCESS not-accessible
    STATUS current
    DESCRIPTION
        "The entry of fsUserMacAddrTable."
    INDEX
    { fsWlanId,fsTerminalIndex}
    ::= { fsUserMacAddrTable 1 }

FSUserMacAddrEntry ::=
    SEQUENCE {
        fsTerminalIndex            INTEGER,
        fsUserMacAdddr             MacAddress
    }
fsTerminalIndex OBJECT-TYPE
    SYNTAX INTEGER
    MAX-ACCESS read-only
    STATUS current
    DESCRIPTION
        "The index of the terminal."
    ::= { fsUserMacAddrEntry 1}

fsUserMacAdddr OBJECT-TYPE
    SYNTAX MacAddress
    MAX-ACCESS read-only
    STATUS current
    DESCRIPTION
        "User MAC address."
    ::= { fsUserMacAddrEntry 2}



--**************************************************
--* fsUserMacAddrTable ends
--**************************************************

--**************************************************
--* fsTermServiceStatTable begins
--**************************************************

fsTermServiceStatTable OBJECT-TYPE
    SYNTAX SEQUENCE OF FSTermServiceStatEntry
    MAX-ACCESS not-accessible
    STATUS current
    DESCRIPTION
        "Statistic of terminal service by terminal."
    ::= { fsTermServiceStat 36	 }

fsTermServiceStatEntry OBJECT-TYPE
    SYNTAX FSTermServiceStatEntry
    MAX-ACCESS not-accessible
    STATUS current
    DESCRIPTION
        "The entry of fsTermServiceStatTable."
    INDEX
    { fsTerminalIndex}
    ::= { fsTermServiceStatTable 1 }

FSTermServiceStatEntry ::=
    SEQUENCE {
        fsTotalReTxFramNum				 INTEGER,
        fsUserOnLineTime					 INTEGER,
        fsRevDataFrameNum					 INTEGER,
        fsRevErrorDataFrameNum		 INTEGER,
        fsSendDataFrameNum				 INTEGER,
        fsSendSuccessDataFrameNum	 INTEGER,
        fsSendReTxDataFrameNum	 	 INTEGER,
        fsAvgSendRate							 INTEGER,
        fsAvgReceiveRate					 INTEGER,
        fsTotalDataThroughput			 INTEGER,
        fsSignalStrength					 INTEGER,
        fsNoise										 INTEGER
    }
fsTotalReTxFramNum OBJECT-TYPE
    SYNTAX INTEGER
    MAX-ACCESS read-only
    STATUS current
    DESCRIPTION
        "The total re-transmit data frame number of each user."
    ::= { fsTermServiceStatEntry 1}


fsUserOnLineTime OBJECT-TYPE
    SYNTAX INTEGER
    MAX-ACCESS read-only
    STATUS current
    DESCRIPTION
        "User on-line time."
    ::= { fsTermServiceStatEntry 2}

fsRevDataFrameNum OBJECT-TYPE
    SYNTAX INTEGER
    MAX-ACCESS read-only
    STATUS current
    DESCRIPTION
        "Number of data frame receive by AP from user."
    ::= { fsTermServiceStatEntry 3}

fsRevErrorDataFrameNum OBJECT-TYPE
    SYNTAX INTEGER
    MAX-ACCESS read-only
    STATUS current
    DESCRIPTION
        "Number of error data frame receive by AP from user."
    ::= { fsTermServiceStatEntry 4}

fsSendDataFrameNum OBJECT-TYPE
    SYNTAX INTEGER
    MAX-ACCESS read-only
    STATUS current
    DESCRIPTION
        "Number of data frame sent by AP to user."
    ::= { fsTermServiceStatEntry 5}

fsSendSuccessDataFrameNum OBJECT-TYPE
    SYNTAX INTEGER
    MAX-ACCESS read-only
    STATUS current
    DESCRIPTION
        "Number of data frame sent by AP to user successfully."
    ::= { fsTermServiceStatEntry 6}

fsSendReTxDataFrameNum OBJECT-TYPE
    SYNTAX INTEGER
    MAX-ACCESS read-only
    STATUS current
    DESCRIPTION
        "Number of retransmit data frame sent by AP to user successfully."
    ::= { fsTermServiceStatEntry 7}


fsAvgSendRate OBJECT-TYPE
    SYNTAX INTEGER
    MAX-ACCESS read-only
    STATUS current
    DESCRIPTION
        "Avearage rate of data that is sent from the AP to users"
    ::= { fsTermServiceStatEntry 8}

fsAvgReceiveRate OBJECT-TYPE
    SYNTAX INTEGER
    MAX-ACCESS read-only
    STATUS current
    DESCRIPTION
        "Avearage rate of data that is received by users from the AP"
    ::= { fsTermServiceStatEntry 9}

fsTotalDataThroughput OBJECT-TYPE
    SYNTAX INTEGER
    MAX-ACCESS read-only
    STATUS current
    DESCRIPTION
        "Total data throughout of the user."
    ::= { fsTermServiceStatEntry 10}

fsSignalStrength OBJECT-TYPE
    SYNTAX INTEGER
    MAX-ACCESS read-only
    STATUS current
    DESCRIPTION
        "Signal strength receive by the AP."
    ::= { fsTermServiceStatEntry 11}

fsNoise OBJECT-TYPE
    SYNTAX INTEGER
    MAX-ACCESS read-only
    STATUS current
    DESCRIPTION
        "Noise when AP receive information from user."
    ::= { fsTermServiceStatEntry 12}

--**************************************************
--* fsTermServiceStatTable ends
--**************************************************


--**************************************************
--* fsTermServiceStat ends here
--**************************************************


END
