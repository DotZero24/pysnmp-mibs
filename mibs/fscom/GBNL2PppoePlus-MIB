GBNL2PppoePlus-MIB  DEFINITIONS ::= BEGIN

    IMPORTS
        MODULE-IDENTITY, OBJECT-TYPE,
        Integer32, Counter32,
        TimeTicks, IpAddress                    FROM SNMPv2-SMI
        DisplayString, TruthValue,RowStatus     FROM SNMPv2-TC

        MODULE-COMPLIANCE, OBJECT-GROUP         FROM SNMPv2-CONF

        gbnL2                                   FROM ADMIN-MASTER-MIB;


    gbnL2PppoePlus MODULE-IDENTITY
        LAST-UPDATED    "200711220000Z"  -- November 22,2007
        ORGANIZATION    "admin Systems, Inc."
        CONTACT-INFO    "admin Systems, Inc.
                         E-mail: support@admin.com.cn"

        DESCRIPTION     "ADMIN Enterprise MIB definition."

        REVISION        "200711220000Z"  -- November 22,2007
        DESCRIPTION     "Initial MIB creation."

        ::= { gbnL2 6 }

------------------------------------------------------------------------------
-- Textual Conventions (i.e., these do not affect object encoding):
------------------------------------------------------------------------------
    pppoeplusOnOff OBJECT-TYPE
        SYNTAX       TruthValue
        MAX-ACCESS read-write
        STATUS current
        DESCRIPTION
            "start/stop pppoe plus.Default is off。"
        --开启关闭 pppoe plus 功能。
        ::= { gbnL2PppoePlus 1 }

    pppoeplusType OBJECT-TYPE
        SYNTAX      INTEGER{
                        standard(0),
                        huawei(1),
			self-defined(2)
        }
        MAX-ACCESS read-write
        STATUS current
        DESCRIPTION
            "pppoeplus type. standard:0;huawei:1;self-defined:2. Default is 0."
        --pppoeplus 类型，默认为standard.
        ::= { gbnL2PppoePlus 2 }

    pppoeplusFormat OBJECT-TYPE
        SYNTAX      INTEGER(0..1)
        MAX-ACCESS read-write
        STATUS current
        DESCRIPTION
            "pppoeplus format. binary:0;ascii:1. Default is 0."
        ::= { gbnL2PppoePlus 3 }

    pppoeplusDelimiter OBJECT-TYPE
        SYNTAX      INTEGER(0..3)
        MAX-ACCESS read-write
        STATUS current
        DESCRIPTION
            "pppoeplus delimiter. space:0;dot:1;slash:2;colon:3. Default is 0."
        ::= { gbnL2PppoePlus 4 }

    pppoeplusCircuitidOrder OBJECT-TYPE
        SYNTAX      OCTET STRING (SIZE(0..255))
        MAX-ACCESS read-write
        STATUS current
        DESCRIPTION
            "pppoeplus circuit id in global. When pppoe+ type set to self-defined, use it to set circuit id in order.
            The string is take a few numbers from 1-9, then join them in any order, separated by commas.
            0-9 means: null,vlan,port,switch mac,client mac,switch hostname,string,ont mac,ont id,ont sn.
            it is order sensitive. For example, '1,2' means first vlan then port, while '2,1' means first port then vlan."
        ::= { gbnL2PppoePlus 5 }

    pppoeplusCircuitidString OBJECT-TYPE
        SYNTAX      OCTET STRING (SIZE(0..255))
        MAX-ACCESS read-write
        STATUS current
        DESCRIPTION
            "pppoeplus circuit id user defined string in global. When pppoe+ type set to self-defined, use it to set circuit id.
            The range of the string length is 1-128. "
        ::= { gbnL2PppoePlus 6 }

    pppoeplusRemoteidOrder OBJECT-TYPE
        SYNTAX      OCTET STRING (SIZE(0..255))
        MAX-ACCESS read-write
        STATUS current
        DESCRIPTION
            "pppoeplus remote id in global. When pppoe+ type set to self-defined, use it to set remote id in order.
            The string is take a few numbers from 3-6, then join them in any order, separated by commas.
            0,3-6 means: null,switch mac,client mac,switch hostname,string. It is order sensitive. "
        ::= { gbnL2PppoePlus 7 }

    pppoeplusRemoteidString OBJECT-TYPE
        SYNTAX      OCTET STRING (SIZE(0..255))
        MAX-ACCESS read-write
        STATUS current
        DESCRIPTION
            "pppoeplus remote id user defined string in global. When pppoe+ type set to self-defined, use it to set remote id.
            The range of the string length is 1-128. "
        ::= { gbnL2PppoePlus 8 }

    pppoeplusPortsTable OBJECT-TYPE
        SYNTAX SEQUENCE OF pppoeplusPortsEntry
        MAX-ACCESS not-accessible
        STATUS current
        DESCRIPTION
            "pppoeplus ports configuration table. "
        ::= { gbnL2PppoePlus 9 }

    pppoeplusPortsEntry OBJECT-TYPE
        SYNTAX pppoeplusPortsEntry
        MAX-ACCESS not-accessible
        STATUS current
        DESCRIPTION
            "entry of pppoeplus ports configuration table. "
       	INDEX	{ pppoeplusPortsIndex }
        ::= { pppoeplusPortsTable 1 }

    pppoeplusPortsEntry	::=
				SEQUENCE
				{
				pppoeplusPortsIndex   INTEGER(1..255),
				pppoeplusPortsOnOff   INTEGER(0..1),
				pppoeplusPortsTrust   INTEGER(0..1),
				pppoeplusPortsDropPadi   INTEGER(0..1),
				pppoeplusPortsDropPado   INTEGER(0..1),
				pppoeplusPortsStrategy   INTEGER(0..2),
				pppoeplusPortsCircuit  OCTET STRING (SIZE(0..255))
				}

    pppoeplusPortsIndex OBJECT-TYPE
        SYNTAX      INTEGER(1..255)
        MAX-ACCESS read-only
        STATUS current
        DESCRIPTION
            "pppoeplus ports index."
        ::= { pppoeplusPortsEntry 1 }

    pppoeplusPortsOnOff OBJECT-TYPE
        SYNTAX      INTEGER(0..1)
        MAX-ACCESS read-write
        STATUS current
        DESCRIPTION
            "pppoeplus ports on off."
        ::= { pppoeplusPortsEntry 2 }

    pppoeplusPortsTrust OBJECT-TYPE
        SYNTAX      INTEGER(0..1)
        MAX-ACCESS read-write
        STATUS current
        DESCRIPTION
            "pppoeplus ports trust."
        ::= { pppoeplusPortsEntry 3 }

    pppoeplusPortsDropPadi OBJECT-TYPE
        SYNTAX      INTEGER(0..1)
        MAX-ACCESS read-write
        STATUS current
        DESCRIPTION
            "pppoeplus ports drop padi and padr packet."
        ::= { pppoeplusPortsEntry 4 }

    pppoeplusPortsDropPado OBJECT-TYPE
        SYNTAX      INTEGER(0..1)
        MAX-ACCESS read-write
        STATUS current
        DESCRIPTION
            "pppoeplus ports drop pado and pads packet."
        ::= { pppoeplusPortsEntry 5 }

    pppoeplusPortsStrategy OBJECT-TYPE
        SYNTAX      INTEGER(0..2)
        MAX-ACCESS read-write
        STATUS current
        DESCRIPTION
            "strategy of pppoeplus ports. Replace:0;keep:1;drop:2. Default:0."
        ::= { pppoeplusPortsEntry 6 }


    pppoeplusPortsCircuit OBJECT-TYPE
        SYNTAX      OCTET STRING (SIZE(0..255))
        MAX-ACCESS read-write
        STATUS current
        DESCRIPTION
            "pppoeplus circuit id user defined string in ports. The range of the string length is 1-63."
        ::= { pppoeplusPortsEntry 7 }

END
