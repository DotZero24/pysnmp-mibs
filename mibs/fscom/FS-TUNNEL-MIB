-- *****************************************************************
-- FS-TUNNEL-MIB.mib:  FS Time MIB file
--
-- June 2012, zhangtao
--
-- Copyright (c) 2012 by FS.COM Inc..
-- All rights reserved.
--
-- *****************************************************************
--

FS-TUNNEL-MIB DEFINITIONS ::= BEGIN

    IMPORTS
        fsMgmt
            FROM FS-SMI
        IpAddress, Integer32, OBJECT-TYPE, MODULE-IDENTITY
            FROM SNMPv2-SMI;

		-- 1.3.6.1.4.1.52642.1.1.10.2.1
    fsTunnelMib MODULE-IDENTITY
        LAST-UPDATED "201206201634Z"		-- June 20, 2012 at 16:34 GMT
        ORGANIZATION
            "FS.COM Inc.."
        CONTACT-INFO
            "
             Tel: 400-865-2852

             E-mail: https://www.fs.com/live_chat_service_mail.html"
        DESCRIPTION
             "This module defines fs tunnel mibs."
        REVISION
             "201206200000Z"
        DESCRIPTION
            "Initial version of this MIB module."
			::= { fsMgmt 114 }

--
-- Node definitions
--

		-- 1.3.6.1.4.1.52642.1.1.10.2.1.1
		fsTunnelObjects OBJECT IDENTIFIER ::= { fsTunnelMib 1 }

		-- 1.3.6.1.4.1.52642.1.1.10.2.1.1.1
		fsTunnelTable OBJECT-TYPE
			SYNTAX SEQUENCE OF FSTunnelEntry
			MAX-ACCESS not-accessible
			STATUS current
			DESCRIPTION
				"Description."
			::= { fsTunnelObjects 1 }

		-- 1.3.6.1.4.1.52642.1.1.10.2.1.1.1.1
		fsTunnelEntry OBJECT-TYPE
			SYNTAX FSTunnelEntry
			MAX-ACCESS not-accessible
			STATUS current
			DESCRIPTION
				"Description."
			INDEX { fsTunnelIp }
			::= { fsTunnelTable 1 }

		FSTunnelEntry ::=
			SEQUENCE {
				fsTunnelIp
					IpAddress,
				fsTunnelOutIfindex
					Integer32
			 }

		-- 1.3.6.1.4.1.52642.1.1.10.2.1.1.1.1.1
		fsTunnelIp OBJECT-TYPE
			SYNTAX IpAddress
			MAX-ACCESS read-only
			STATUS current
			DESCRIPTION
				"Description."
			::= { fsTunnelEntry 1 }

		-- 1.3.6.1.4.1.52642.1.1.10.2.1.1.1.1.2
		fsTunnelOutIfindex OBJECT-TYPE
			SYNTAX Integer32
			MAX-ACCESS read-only
			STATUS current
			DESCRIPTION
				"Description."
			::= { fsTunnelEntry 2 }

	END

--
-- FS-TUNNEL-MIB.my
--
