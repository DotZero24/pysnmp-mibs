-- *****************************************************************
-- FS-CPP-MIB.mib:  FS CPP MIB file
--
-- Dec 2014, Linxiaojie
--
-- Copyright (c) 2012 by FS.COM Inc..
-- All rights reserved.
--
-- *****************************************************************
--

FS-CPP-MIB DEFINITIONS ::= BEGIN

IMPORTS
        MODULE-IDENTITY,
        OBJECT-TYPE,
        NOTIFICATION-TYPE,
        Integer32,
        OBJECT-TYPE
                FROM SNMPv2-SMI
        TruthValue,
        DisplayString
                FROM SNMPv2-TC
        MODULE-COMPLIANCE,
        OBJECT-GROUP
                FROM SNMPv2-CONF
        fsMgmt
                FROM FS-SMI;

fsCPPMIB MODULE-IDENTITY
        LAST-UPDATED "201412192100Z"
        ORGANIZATION "FS.COM Inc.."
        CONTACT-INFO
                "
                Tel: 400-865-2852

                E-mail: https://www.fs.com/live_chat_service_mail.html"
        DESCRIPTION
                "This module defines fs cpp mibs."
        REVISION      "201412192100Z"
        DESCRIPTION
                "Add a table about cpp."
        REVISION      "201412192100Z"
        DESCRIPTION
                "Initial version of this MIB module."
        ::= { fsMgmt 132 }

fsCPPMIBObjects OBJECT IDENTIFIER ::= { fsCPPMIB 1 }

fsCPPTable OBJECT-TYPE
        SYNTAX 			SEQUENCE OF FSCPPEntry
        MAX-ACCESS 	not-accessible
        STATUS 			current
        DESCRIPTION
            " "
        ::= { fsCPPMIBObjects 1 }

fsCPPEntry OBJECT-TYPE
        SYNTAX 			FSCPPEntry
        MAX-ACCESS 	not-accessible
        STATUS 			current
        DESCRIPTION
            " "
        INDEX { cppIndex }
        ::= { fsCPPTable 1 }

FSCPPEntry ::=
        SEQUENCE {
            cppIndex			Integer32,
            cppDeviceId			Integer32,
            cppSlotId			Integer32,
            cppCardIndex		DisplayString,
            cppPacketType		DisplayString,
            cppTrafficClass		Integer32,
            cppBandwidth		Integer32,
            cppRate			Integer32,
            cppDrop			Integer32,
            cppTotal			Integer32,
            cppTotalDrop		Integer32
        }
cppIndex OBJECT-TYPE
        SYNTAX 			Integer32 (1..2147483647)
        MAX-ACCESS 	read-only
        STATUS 			current
        DESCRIPTION
            " "
        ::= { fsCPPEntry 1 }

cppDeviceId OBJECT-TYPE
        SYNTAX 			Integer32 (1..2147483647)
        MAX-ACCESS 	read-only
        STATUS 			current
        DESCRIPTION
            " "
        ::= { fsCPPEntry 2 }

cppSlotId OBJECT-TYPE
        SYNTAX 			Integer32 (1..2147483647)
        MAX-ACCESS 	read-only
        STATUS 			current
        DESCRIPTION
            " "
        ::= { fsCPPEntry 3 }

cppCardIndex OBJECT-TYPE
        SYNTAX DisplayString(SIZE (1..32))
        MAX-ACCESS read-only
        STATUS current
        DESCRIPTION
            " "
        ::= { fsCPPEntry 4 }

cppPacketType OBJECT-TYPE
        SYNTAX DisplayString(SIZE (1..32))
        MAX-ACCESS read-only
        STATUS current
        DESCRIPTION
            " "
        ::= { fsCPPEntry 5 }

cppTrafficClass OBJECT-TYPE
        SYNTAX 			Integer32 (1..2147483647)
        MAX-ACCESS 	read-only
        STATUS 			current
        DESCRIPTION
            " "
        ::= { fsCPPEntry 6 }

cppBandwidth OBJECT-TYPE
        SYNTAX 			Integer32 (1..2147483647)
        MAX-ACCESS 	read-only
        STATUS 			current
        DESCRIPTION
            " "
        ::= { fsCPPEntry 7 }

cppRate OBJECT-TYPE
        SYNTAX 			Integer32 (1..2147483647)
        MAX-ACCESS 	read-only
        STATUS 			current
        DESCRIPTION
            " "
        ::= { fsCPPEntry 8 }

cppDrop OBJECT-TYPE
        SYNTAX 			Integer32 (1..2147483647)
        MAX-ACCESS 	read-only
        STATUS 			current
        DESCRIPTION
            " "
        ::= { fsCPPEntry 9 }

cppTotal OBJECT-TYPE
        SYNTAX 			Integer32 (1..2147483647)
        MAX-ACCESS 	read-only
        STATUS 			current
        DESCRIPTION
            " "
        ::= { fsCPPEntry 10 }

cppTotalDrop OBJECT-TYPE
        SYNTAX 			Integer32 (1..2147483647)
        MAX-ACCESS 	read-only
        STATUS 			current
        DESCRIPTION
            " "
        ::= { fsCPPEntry 11 }


fsCPPTcTable OBJECT-TYPE
        SYNTAX 			SEQUENCE OF FSCPPTcEntry
        MAX-ACCESS 	not-accessible
        STATUS 			current
        DESCRIPTION
            " "
        ::= { fsCPPMIBObjects 2 }

fsCPPTcEntry OBJECT-TYPE
        SYNTAX 			FSCPPTcEntry
        MAX-ACCESS 	not-accessible
        STATUS 			current
        DESCRIPTION
            " "
        INDEX { cppTcIndex }
        ::= { fsCPPTcTable 1 }

FSCPPTcEntry ::=
        SEQUENCE {
            cppTcIndex			Integer32,
            cppTcDeviceId	        Integer32,
            cppTcSlotId			Integer32,
            cppTcTrafficClass		Integer32,
            cppTcCardIndex		DisplayString,
            cppTcBandwidth		Integer32,
            cppTcRate			Integer32,
            cppTcDrop			Integer32
        }

cppTcIndex OBJECT-TYPE
        SYNTAX 			Integer32 (1..2147483647)
        MAX-ACCESS 	read-only
        STATUS 			current
        DESCRIPTION
            " "
        ::= { fsCPPTcEntry 1 }

cppTcDeviceId OBJECT-TYPE
        SYNTAX 			Integer32 (1..2147483647)
        MAX-ACCESS 	read-only
        STATUS 			current
        DESCRIPTION
            " "
        ::= { fsCPPTcEntry 2 }

cppTcSlotId OBJECT-TYPE
        SYNTAX 			Integer32 (1..2147483647)
        MAX-ACCESS 	read-only
        STATUS 			current
        DESCRIPTION
            " "
        ::= { fsCPPTcEntry 3 }

cppTcTrafficClass OBJECT-TYPE
        SYNTAX 			Integer32 (1..2147483647)
        MAX-ACCESS 	read-only
        STATUS 			current
        DESCRIPTION
            " "
        ::= { fsCPPTcEntry 4 }

cppTcCardIndex OBJECT-TYPE
        SYNTAX DisplayString(SIZE (1..32))
        MAX-ACCESS read-only
        STATUS current
        DESCRIPTION
            " "
        ::= { fsCPPTcEntry 5 }

cppTcBandwidth OBJECT-TYPE
        SYNTAX 			Integer32 (1..2147483647)
        MAX-ACCESS 	read-only
        STATUS 			current
        DESCRIPTION
            " "
        ::= { fsCPPTcEntry 6 }

cppTcRate OBJECT-TYPE
        SYNTAX 			Integer32 (1..2147483647)
        MAX-ACCESS 	read-only
        STATUS 			current
        DESCRIPTION
            " "
        ::= { fsCPPTcEntry 7 }

cppTcDrop OBJECT-TYPE
        SYNTAX 			Integer32 (1..2147483647)
        MAX-ACCESS 	read-only
        STATUS 			current
        DESCRIPTION
            " "
        ::= { fsCPPTcEntry 8 }


END
