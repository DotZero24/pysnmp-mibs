-- *****************************************************************
-- FS-DHCP-CLIENT-MIB.mib:  FS DHCP client MIB file
--
-- Oct 2015, lushunqin
--
-- Copyright (c) 2015 by FS.COM Inc..
-- All rights reserved.
-- *****************************************************************
--

FS-DHCP-CLIENT-MIB DEFINITIONS ::= BEGIN

IMPORTS
    MODULE-IDENTITY,
    OBJECT-TYPE,
    IpAddress,
    Integer32,
    Unsigned32
        FROM SNMPv2-SMI

    MODULE-COMPLIANCE,
    OBJECT-GROUP
        FROM SNMPv2-CONF

    TruthValue,
    MacAddress,
    DisplayString,
    RowStatus
        FROM SNMPv2-TC

    InterfaceIndex
        FROM IF-MIB

    VlanIndex
        FROM Q-BRIDGE-MIB

    fsMgmt
        FROM FS-SMI;

--********************************************************************
--*  MODULE IDENTITY
--********************************************************************

fsDhcpClientMIB    MODULE-IDENTITY
       LAST-UPDATED    "201502090000Z"
       ORGANIZATION    "FS.COM Inc.."
       CONTACT-INFO
                "
                Tel: 400-865-2852

                E-mail: https://www.fs.com/live_chat_service_mail.html"

        DESCRIPTION
            "This module defines fs DHCP Client mibs."

        REVISION      "201502090000Z"
        DESCRIPTION
                "Initial version of this MIB module. "
        ::= { fsMgmt 135 }

fsDhcpClientMIBObjects OBJECT IDENTIFIER
    ::= { fsDhcpClientMIB 0 }

fsDhcpClientConfig OBJECT IDENTIFIER
	::= { fsDhcpClientMIBObjects 1 }



--*******************************************************************
--DHCP Client Config :  ip address dhcp on interface
--*******************************************************************

    fsDhcpClientIntfTable OBJECT-TYPE
         SYNTAX      SEQUENCE OF FSDhcpClientIntfEntry
         MAX-ACCESS  not-accessible
         STATUS      current
         DESCRIPTION
                     "A table listing the  ip address dhcp
                     on interface configed for DHCP client."
         ::= { fsDhcpClientConfig 2 }

    fsDhcpClientIntfEntry OBJECT-TYPE
         SYNTAX      FSDhcpClientIntfEntry
         MAX-ACCESS  not-accessible
         STATUS      current
         DESCRIPTION
                     "Ip address dhcp entry configed on interface
                 for DHCP client."
         INDEX       { fsDhcpIntfClientIndex }
         ::= { fsDhcpClientIntfTable 1 }

    FSDhcpClientIntfEntry ::= SEQUENCE {
             fsDhcpIntfClientIndex         InterfaceIndex,
             fsDhcpClientIpAddrDhcpStatus  INTEGER
             }

    fsDhcpIntfClientIndex OBJECT-TYPE
         SYNTAX      InterfaceIndex
         MAX-ACCESS  read-only
         STATUS      current
         DESCRIPTION
                     "Interface DHCP client index."
         ::= { fsDhcpClientIntfEntry 1 }

    fsDhcpClientIpAddrDhcpStatus OBJECT-TYPE
         SYNTAX      INTEGER {
                     enable(1),
                     disable(0)
                     }
         MAX-ACCESS  read-create
         STATUS      current
         DESCRIPTION
                     "Ip address dhcp entry configed on interface
                 for DHCP client. "
         ::= { fsDhcpClientIntfEntry 2 }


fsDhcpClientMIBConformance OBJECT IDENTIFIER ::= { fsDhcpClientMIB 2 }
fsDhcpClientMIBCompliances OBJECT IDENTIFIER ::= { fsDhcpClientMIBConformance 1 }
fsDhcpClientMIBGroups      OBJECT IDENTIFIER ::= { fsDhcpClientMIBConformance 2 }


-- compliance statements

fsDhcpClientMIBCompliance MODULE-COMPLIANCE
        STATUS  current
        DESCRIPTION
                "The compliance statement for entities which implement
                the FS Dhcp Client MIB"
        MODULE  -- this module
                MANDATORY-GROUPS { fsDhcpClientIntfConfigGroup
                }
        ::= { fsDhcpClientMIBCompliances 1 }

-- units of conformance

fsDhcpClientIntfConfigGroup OBJECT-GROUP
        OBJECTS {
             fsDhcpClientIpAddrDhcpStatus
        }
        STATUS  current
        DESCRIPTION
                "A collection of objects providing dhcp client config information."
        ::= { fsDhcpClientMIBGroups 1 }

END
