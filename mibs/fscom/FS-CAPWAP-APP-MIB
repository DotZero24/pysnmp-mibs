-- *****************************************************************
-- FS-CAPWAP-APP-MIB.mib:  FS CAPWAP APP MIB file
--
-- Jul 2010, Panshiyong
--
-- Copyright(c) 2010 by FS.COM Inc..
-- All rights reserved.
--
-- *****************************************************************
--

FS-CAPWAP-APP-MIB DEFINITIONS ::= BEGIN

IMPORTS
        MODULE-IDENTITY,
        OBJECT-TYPE,
        TimeTicks,
        Unsigned32,
        Integer32,
        IpAddress
                FROM SNMPv2-SMI
        DisplayString,
        TruthValue,
        TAddress,
        RowStatus
                FROM SNMPv2-TC
        MODULE-COMPLIANCE,
        OBJECT-GROUP
                FROM SNMPv2-CONF
        InetAddressType,
        InetAddress
                FROM INET-ADDRESS-MIB
        sysObjectID
                FROM RFC1213-MIB
        fsSystemSerialno
                FROM FS-SYSTEM-MIB
        fsDeviceMacAddress
                FROM FS-ENTITY-MIB
        fsMgmt
                FROM FS-SMI;

fsCapwapAppMIB MODULE-IDENTITY
        LAST-UPDATED "201006040000Z"
        ORGANIZATION "FS.COM Inc.."
        CONTACT-INFO
                "
                Tel: 400-865-2852

                E-mail: https://www.fs.com/live_chat_service_mail.html"
        DESCRIPTION
                "This module defines fs Capwap App mibs."
        REVISION      "201006040000Z"
        DESCRIPTION
                "Initial version of this MIB module."
        ::= { fsMgmt 87 }

fsCapwapAppMIBObjects   OBJECT IDENTIFIER ::= { fsCapwapAppMIB 1 }


--**********************************************************************
-- about heartbeat info
--**********************************************************************
fsAppHeartbeatMIBObjects
    OBJECT IDENTIFIER ::= { fsCapwapAppMIBObjects 1 }

fsAppHeartbeatOnOff OBJECT-TYPE
    SYNTAX INTEGER {
             off(0),
             on(1)
           }
    MAX-ACCESS read-write
    STATUS current
    DESCRIPTION
        "Heartbeat detect switch."
    ::= { fsAppHeartbeatMIBObjects 1 }

fsAppHeartbeatPeriod OBJECT-TYPE
    SYNTAX INTEGER (60..3600)
    MAX-ACCESS read-write
    STATUS current
    DESCRIPTION
        "Heartbeat detect periode."
    ::= { fsAppHeartbeatMIBObjects 2 }

fsAppHeartbeatIpAddr OBJECT-TYPE
    SYNTAX IpAddress
    MAX-ACCESS read-only
    STATUS current
    DESCRIPTION
        "IP address of the AP"
    ::= { fsAppHeartbeatMIBObjects 3 }

fsAppHeartbeatTimeStamp OBJECT-TYPE
    SYNTAX TimeTicks
    MAX-ACCESS read-only
    STATUS current
    DESCRIPTION
        "Time stamp of the AP"
    ::= { fsAppHeartbeatMIBObjects 4 }


-- heartbeat traps
fsAppHeartbeatMIBTraps OBJECT IDENTIFIER ::= { fsAppHeartbeatMIBObjects 0 }

fsAppHeartbeatTrap NOTIFICATION-TYPE
    OBJECTS {
        fsAppHeartbeatIpAddr,
        fsAppHeartbeatTimeStamp
    }
    STATUS  current
    DESCRIPTION
            " This trap will be sent when a heartbeat periode pass."
    ::= { fsAppHeartbeatMIBTraps 1 }


--**********************************************************************
-- about admin info
--**********************************************************************
fsAppAdminInfoMIBObjects
    OBJECT IDENTIFIER ::= { fsCapwapAppMIBObjects 2 }

fsAppAdminInfoTable OBJECT-TYPE
    SYNTAX SEQUENCE OF FSAppAdminInfoEntry
    MAX-ACCESS not-accessible
    STATUS current
    DESCRIPTION
        "The table about admin info."
    ::= { fsAppAdminInfoMIBObjects 1 }

fsAppAdminInfoEntry OBJECT-TYPE
    SYNTAX FSAppAdminInfoEntry
    MAX-ACCESS not-accessible
    STATUS current
    DESCRIPTION
        "The entry of fsAdminInfoTable."
    INDEX { fsAppAdminName }
    ::= { fsAppAdminInfoTable 1 }

FSAppAdminInfoEntry ::=
    SEQUENCE {
       fsAppAdminName      DisplayString,
       fsAppAdminPwd       DisplayString,
       fsAppAdminPriLevel  INTEGER,
       fsAppAdminStatus    RowStatus
    }

fsAppAdminName OBJECT-TYPE
    SYNTAX DisplayString(SIZE(1..64))
    MAX-ACCESS read-only
    STATUS current
    DESCRIPTION
           "The name of the administrator."
    ::= { fsAppAdminInfoEntry 1 }

fsAppAdminPwd OBJECT-TYPE
    SYNTAX DisplayString(SIZE(1..255))
    MAX-ACCESS read-create
    STATUS current
    DESCRIPTION
           "The password of the administrator."
    ::= { fsAppAdminInfoEntry 2 }

fsAppAdminPriLevel OBJECT-TYPE
    SYNTAX INTEGER
    MAX-ACCESS read-create
    STATUS current
    DESCRIPTION
           "The privilege level of the administrator."
    ::= { fsAppAdminInfoEntry 3 }

fsAppAdminStatus OBJECT-TYPE
    SYNTAX RowStatus
    MAX-ACCESS read-create
    STATUS current
    DESCRIPTION
           "The rowstatus of the adminInfoEntry."
    ::= { fsAppAdminInfoEntry 4 }


fsAppAdminInfoName OBJECT-TYPE
    SYNTAX DisplayString(SIZE(1..64))
    MAX-ACCESS not-accessible
    STATUS current
    DESCRIPTION
        "The administrator name info."
    ::= { fsAppAdminInfoMIBObjects 2 }

fsAppAdminInfoIpAddr OBJECT-TYPE
    SYNTAX IpAddress
    MAX-ACCESS not-accessible
    STATUS current
    DESCRIPTION
        "The administrator ip address info."
    ::= { fsAppAdminInfoMIBObjects 3 }

fsAppAdminInfoConfigContext OBJECT-TYPE
    SYNTAX OCTET STRING(SIZE(1..512))
    MAX-ACCESS not-accessible
    STATUS current
    DESCRIPTION
        "The context of configuration."
    ::= { fsAppAdminInfoMIBObjects 4 }

fsAppAdminInfoLoginType OBJECT-TYPE
    SYNTAX DisplayString(SIZE(1..64))
    MAX-ACCESS not-accessible
    STATUS current
    DESCRIPTION
        "The administrator login type."
    ::= { fsAppAdminInfoMIBObjects 5 }

fsAppAdminTerminalInfo OBJECT-TYPE
    SYNTAX DisplayString(SIZE(1..64))
    MAX-ACCESS not-accessible
    STATUS current
    DESCRIPTION
        "The administrator terminal information:
         console  -  login from console
         aux id   -  login from auxiliary
         vty id   -  login from telnet or ssh
         web      -  login from http/web "
    ::= { fsAppAdminInfoMIBObjects 6 }

fsAppAdminLoginFailReason OBJECT-TYPE
    SYNTAX INTEGER
    MAX-ACCESS not-accessible
    STATUS current
    DESCRIPTION
        "The administrator login fail reason:
         1  -  username or password is error "
    ::= { fsAppAdminInfoMIBObjects 7 }

fsAppAdminTargetLevel OBJECT-TYPE
    SYNTAX INTEGER (0..15)
    MAX-ACCESS not-accessible
    STATUS current
    DESCRIPTION
        "The administrator target level"
    ::= { fsAppAdminInfoMIBObjects 8 }

-- admin traps
fsAppAdminMIBTraps
    OBJECT IDENTIFIER ::= { fsAppAdminInfoMIBObjects 0 }

fsAppAdminLoginTrap NOTIFICATION-TYPE
    OBJECTS {
        fsAppAdminInfoName,
        fsAppAdminInfoIpAddr,
        fsAppAdminInfoLoginType
    }
    STATUS  current
    DESCRIPTION
            " This trap will be sent when the administrator rlogin the device."
    ::= { fsAppAdminMIBTraps 1 }

fsAppAdminModifyConfigTrap NOTIFICATION-TYPE
    OBJECTS {
        fsAppAdminInfoName,
        fsAppAdminInfoIpAddr,
        fsAppAdminInfoConfigContext
    }
    STATUS  current
    DESCRIPTION
            " This trap will be sent when the administrator modify the configuration."
    ::= { fsAppAdminMIBTraps 2 }

fsAppAdminLoginFailTrap NOTIFICATION-TYPE
    OBJECTS {
        fsAppAdminInfoName,
        fsAppAdminInfoIpAddr,
        fsAppAdminTerminalInfo,
        fsAppAdminLoginFailReason
    }
    STATUS  current
    DESCRIPTION
            " This trap will be sent when the administrator login the device failed."
    ::= { fsAppAdminMIBTraps 3 }

fsAppAdminEnableFailTrap NOTIFICATION-TYPE
    OBJECTS {
        fsAppAdminInfoName,
        fsAppAdminInfoIpAddr,
        fsAppAdminTerminalInfo,
        fsAppAdminTargetLevel
    }
    STATUS  current
    DESCRIPTION
            " This trap will be sent when the administrator enter target cli level failed."
    ::= { fsAppAdminMIBTraps 4 }

--**********************************************************************
-- about polltime info
--**********************************************************************
fsAppPollTimeMIBObjects
    OBJECT IDENTIFIER ::= { fsCapwapAppMIBObjects 3 }

fsAppPollTimeOfLast OBJECT-TYPE
    SYNTAX TimeTicks
    MAX-ACCESS read-only
    STATUS current
    DESCRIPTION
           "The last time of administrator
            poll the devices."
		::= { fsAppPollTimeMIBObjects 1 }


--**********************************************************************
-- about config info
--**********************************************************************
fsAppConfigMIBObjects
    OBJECT IDENTIFIER ::= { fsCapwapAppMIBObjects 4 }

fsAppRcvToDefConfig OBJECT-TYPE
    SYNTAX INTEGER{
         normal(0),
         reset(1)
    }
    MAX-ACCESS read-write
    STATUS current
    DESCRIPTION
        "0 - normal,
         1 - recove the device to default config. then reload the device"
    ::= { fsAppConfigMIBObjects 1 }

fsAppConfigFileName OBJECT-TYPE
    SYNTAX DisplayString(SIZE (1..32))
    MAX-ACCESS read-only
    STATUS current
    DESCRIPTION
        "Name of configuration file."
    ::= { fsAppConfigMIBObjects 2 }

fsAppConfigParseErrReason OBJECT-TYPE
    SYNTAX DisplayString(SIZE (1..255))
    MAX-ACCESS read-only
    STATUS current
    DESCRIPTION
        "The reason of configuration file parse error."
    ::= { fsAppConfigMIBObjects 3 }

-- modify config trap
fsAppConfigMIBTraps
    OBJECT IDENTIFIER ::= { fsAppConfigMIBObjects 0 }

fsAppConfigModifyFileTrap NOTIFICATION-TYPE
    STATUS  current
    DESCRIPTION
            "The notification of discovering someone
             modify the configuration file."
    ::= { fsAppConfigMIBTraps 1 }

fsAppConfigParseErrTrap NOTIFICATION-TYPE
    OBJECTS {
        fsAppConfigFileName,
        fsAppConfigParseErrReason
    }
    STATUS  current
    DESCRIPTION
        "The notification of discovering parser
         configuration file error."
    ::= { fsAppConfigMIBTraps 2 }


--**********************************************************************
-- about syslog info
--**********************************************************************
fsAppSyslogMIBObjects
    OBJECT IDENTIFIER ::= { fsCapwapAppMIBObjects 5 }

fsAppSyslogSvcEnable OBJECT-TYPE
    SYNTAX TruthValue
    MAX-ACCESS read-write
    STATUS current
    DESCRIPTION
        "Whether to open syslog service or not:
         2 - no
         1 - yes.
        "
    ::= { fsAppSyslogMIBObjects 1 }

fsAppSyslogReportEventLevel OBJECT-TYPE
    SYNTAX INTEGER
    MAX-ACCESS read-write
    STATUS current
    DESCRIPTION
        "Report event level"
    ::= { fsAppSyslogMIBObjects 2 }


fsAppSyslogSvrCfgTable OBJECT-TYPE
    SYNTAX SEQUENCE OF FSAppSyslogSvrCfgEntry
    MAX-ACCESS not-accessible
    STATUS current
    DESCRIPTION
        "The table discribe the system log configuration of the AP."
    ::= { fsAppSyslogMIBObjects 3 }

fsAppSyslogSvrCfgEntry OBJECT-TYPE
    SYNTAX FSAppSyslogSvrCfgEntry
    MAX-ACCESS not-accessible
    STATUS current
    DESCRIPTION
        "The entry of apSyslogSvrCfgTable."
    INDEX {
          fsAppSyslogSvrNetType,
          fsAppSyslogSvrNetAddr
      }
    ::= { fsAppSyslogSvrCfgTable 1 }

FSAppSyslogSvrCfgEntry ::=
    SEQUENCE {
        fsAppSyslogSvrNetType    InetAddressType,
        fsAppSyslogSvrNetAddr    InetAddress,
        fsAppSyslogSvrNetPort    Unsigned32,
        fsAppSyslogVrfName       DisplayString,
        fsAppSyslogStatus        RowStatus
	  }

fsAppSyslogSvrNetType  OBJECT-TYPE
    SYNTAX InetAddressType
    MAX-ACCESS read-only
    STATUS current
    DESCRIPTION
        "Address type of syslog server."
    ::= { fsAppSyslogSvrCfgEntry 1 }

fsAppSyslogSvrNetAddr OBJECT-TYPE
    SYNTAX InetAddress
    MAX-ACCESS read-only
    STATUS current
    DESCRIPTION
        "Address of syslog server."
    ::= { fsAppSyslogSvrCfgEntry 2 }

fsAppSyslogSvrNetPort OBJECT-TYPE
    SYNTAX Unsigned32
    MAX-ACCESS read-create
    STATUS current
    DESCRIPTION
        "NetPort of syslog server."
    ::= { fsAppSyslogSvrCfgEntry 3 }

fsAppSyslogVrfName OBJECT-TYPE
    SYNTAX DisplayString
    MAX-ACCESS read-create
    STATUS current
    DESCRIPTION
        "Vrf name of syslog server."
    ::= { fsAppSyslogSvrCfgEntry 4 }

fsAppSyslogStatus OBJECT-TYPE
    SYNTAX RowStatus
    MAX-ACCESS read-create
    STATUS current
    DESCRIPTION
        "RowStatus of syslog server."
    ::= { fsAppSyslogSvrCfgEntry 5 }

--
-- about syslog Taddress info
--
fsSyslogServerAddrInfoTable OBJECT-TYPE
    SYNTAX SEQUENCE OF FSSyslogServerAddrInfoEntry
    MAX-ACCESS not-accessible
    STATUS current
    DESCRIPTION
        "The table discribe the syslog server informations."
    ::= { fsAppSyslogMIBObjects 4 }

fsSyslogServerAddrInfoEntry OBJECT-TYPE
    SYNTAX FSSyslogServerAddrInfoEntry
    MAX-ACCESS not-accessible
    STATUS current
    DESCRIPTION
        "The entry of fsSyslogServerAddrInfoTable."
    INDEX {
        fsSyslogServerIndex
    }
    ::= { fsSyslogServerAddrInfoTable 1 }

FSSyslogServerAddrInfoEntry ::=
    SEQUENCE {
        fsSyslogServerIndex      Integer32,
        fsSyslogServerAddr       TAddress,
        fsSyslogServerVrfName    DisplayString,
        fsSyslogServerStatus     RowStatus
	  }

fsSyslogServerIndex OBJECT-TYPE
    SYNTAX Integer32
    MAX-ACCESS read-only
    STATUS current
    DESCRIPTION
        "Index of syslog server information table."
    ::= { fsSyslogServerAddrInfoEntry 1 }

fsSyslogServerAddr OBJECT-TYPE
    SYNTAX TAddress
    MAX-ACCESS read-create
    STATUS current
    DESCRIPTION
        "Taddess of syslog server."
    ::= { fsSyslogServerAddrInfoEntry 2 }

fsSyslogServerVrfName OBJECT-TYPE
    SYNTAX DisplayString
    MAX-ACCESS read-create
    STATUS current
    DESCRIPTION
        "Vrf name of syslog server."
    ::= { fsSyslogServerAddrInfoEntry 3 }

fsSyslogServerStatus OBJECT-TYPE
    SYNTAX RowStatus
    MAX-ACCESS read-create
    STATUS current
    DESCRIPTION
        "RowStatus of syslog server."
    ::= { fsSyslogServerAddrInfoEntry 4 }


--**********************************************************************
-- about Trap Action info
--**********************************************************************
fsAppTrapActionMIBObjects
    OBJECT IDENTIFIER ::= { fsCapwapAppMIBObjects 6 }

fsAppTrapActionEnable OBJECT-TYPE
    SYNTAX INTEGER {
        disableSendTrap(0),  -- disable send trap
        enableSendTrap(1)    -- enable  send trap
    }
    MAX-ACCESS read-write
    STATUS current
    DESCRIPTION
        "This value decide enable or not to send trap
         while some notification happen."
    ::= { fsAppTrapActionMIBObjects 1 }

fsAppTrapActionTable OBJECT-TYPE
    SYNTAX SEQUENCE OF FSAppTrapActionEntry
    MAX-ACCESS not-accessible
    STATUS current
    DESCRIPTION
        "This table of the trap's action."
    ::= { fsAppTrapActionMIBObjects 2 }

fsAppTrapActionEntry OBJECT-TYPE
    SYNTAX FSAppTrapActionEntry
    MAX-ACCESS not-accessible
    STATUS current
    DESCRIPTION
        "List of of the trap's action."
    INDEX { fsAppTrapType }
    ::= { fsAppTrapActionTable 1 }

FSAppTrapActionEntry ::=
    SEQUENCE {
        fsAppTrapType   INTEGER,
        fsAppTrapAction INTEGER,
        fsAppTrapDescr  DisplayString
    }

fsAppTrapType OBJECT-TYPE
    SYNTAX INTEGER {
        gencoldstart(1),
        genwarmstart(2),
        genlinkdown(3),
        genlinkup(4),
        genauthenfail(5),
        genegpnbloss(6),
        spenewroot(7),
        spetopchange(8),
        spehardchange(9),
        speportsecuviolation(10),
        spestormviolation(11),
        spemacnotification(12),
        spevrrpnewmaster(13),
        spevrrpauthfailure(14),
        spepowerstatetrans(15),
        spefanstatetrans(16),
        speospf(17),
        speospfvifstatechange(18),
        speospfnbrstatechange(19),
        speospfvifnbrstatechange(20),
        speospfifconfigerror(21),
        speospfvifconfigerror(22),
        speospfifauthfailure(23),
        speospfvifauthfailure(24),
        speospfifrxbadpacket(25),
        speospfvifrxbadpacket(26),
        speospftxretransmit(27),
        speospfviftxretransmit(28),
        speospforiginatelsa(29),
        speospfmaxagelsa(30),
        speospflsdboverflow(31),
        speospflsdbapproachingoverflow(32),
        speospfifstatechange(33),
        spebgpestablished(34),
        spebgpbackwardtransition(35),
        speisisdatabaseoverload(36),
        speisismanualaddressdrop(37),
        speisiscorruptedlspdetected(38),
        speisisattempttoexceedmaxseq(39),
        speisisidlenmismatch(40),
        speisismaxareaaddrmismatch(41),
        speisisownlsppurge(42),
        speisisseqnumberskip(43),
        speisisauthtypefailure(44),
        speisisauthfailure(45),
        speisisversionskew(46),
        speisisareamismatch(47),
        speisisrejectedadj(48),
        speisislsptoolargetopropagate(49),
        speisisoriglspbufsizemismatch(50),
        speisisprotocolsupportedmismatch(51),
        speisisadjchange(52),
        spepim(53),
        speigmp(54),
        spedvmrp(55),
        speentitychange(56),
        specluster(57),
        spedetectipviolation(58),
        spelinestate(59),
        spesysguard(60),
        spernfpmsgtrap(61),
        sperrmclientsfailedtrap(62),
        sperrmloadfailedtrap(63),
        sperrmnoisefailedtrap(64),
        sperrminterferencefailedtrap(65),
        sperrmperformancefailedtrap(66),
        sperrmclientspasstrap(67),
        sperrmloadpasstrap(68),
        sperrmnoisepasstrap(69),
        sperrminterferencepasstrap(70),
        sperrmperformancepasstrap(71),
        sperrmchannelchangetrap(72),
        sperrmtxpowerchangetrap(73),
        sperrmleaderachangetrap(74),
        sperrmleaderbchangetrap(75),
        sperrmdfsfreecountatrap(76),
        sperrmdfsfreecountbtrap(77),
        sperrmneighborapintertrap(78),
        sperrmstationintertrap(79),
        sperrmotherdiveceintertrap(80),
        rmonalarmfallingtrap(81),
        rmonalarmrisingtrap(82),
        smpframerelaytrap(83),
        priventitytrans(84),
        privtemperaturetrans(85),
        speipv6ifstatechange(86),
        psmachashconflicttrap(87),
        privwebauthuserleave(88),
        radiusauthserverdowntrap(89),
        radiusacctserverdowntrap(90),
        configurationerrortrap(91),
        cpuusagetoohightrap(92),
        cpuusagetoohighrecovtrap(93),
        memusagetoohightrap(94),
        memusagetoohighrecovtrap(95),
        systmcoldstarttrap(96),
        ipaddrchangetrap(97),
        apmtworkmodechgtrap(98),
        apswupdatefailtrap(99),
        ssidkeyconflicttrap(100),
        fatapheartbeattrap(101),
        acconfigurationerrortrap(102),
        accpuusagetoohightrap(103),
        accpuusagetoohighrecovtrap(104),
        acmemusagetoohightrap(105),
        acmemusagetoohighrecovtrap(106),
        acofflinetrap(107),
        aconlinetrap(108),
        acapmtworkmodechgtrap(109),
        acapswupdatefailtrap(110),
        acssidkeyconflicttrap(111),
        acfatapheartbeattrap(112),
        staauthfailtrap(113),
        staassofailtrap(114),
        acstaauthfailtrap(115),
        acstaassofailtrap(116),
        invalidcertinvadetrap(117),
        repaccacktrap(118),
        tamperattacktrap(119),
        lowersafeattacktrap(120),
        addrredirectiontrap(121),
        acinvalidcertinvadetrap(122),
        acrepaccacktrap(123),
        actamperattacktrap(124),
        aclowersafeattacktrap(125),
        acaddrredirectiontrap(126),
        widsieee80211connect(127),
        widsieee80211disconnect(128),
        widsieee80211reauthentication(129),
        widsieee80211authenticationfailure(130),
        widsieee80211connectfailure(131),
        apcointerfdetectedtrap(132),
        apcointerfcleartrap(133),
        apnerborinterfdetectedtrap(134),
        apneiborinterfcleartrap(135),
        stainterfdetectedtrap(136),
        stainterfcleartrap(137),
        otherdeviceinterfdetectedtrap(138),
        otherdevinterfcleartrap(139),
        radiodowntrap(140),
        radiodownrecovtrap(141),
        apstafulltrap(142),
        apstafullrecovertrap(143),
        apmtrdochanlchgtrap(144),
        acapcointerfdetectedtrap(145),
        acapcointerfcleartrap(146),
        acapnerborinterfdetectedtrap(147),
        acapneiborinterfcleartrap(148),
        acstainterfdetectedtrap(149),
        acstainterfcleartrap(150),
        acotherdeviceinterfdetectedtrap(151),
        acotherdevinterfcleartrap(152),
        acradiodowntrap(153),
        acradiodownrecovtrap(154),
        acapstafulltrap(155),
        acapstafullrecovertrap(156),
        acapmtrdochanlchgtrap(157),
        acspeciousdevicedetecttrap(158),
        acrxpackage(159),
        accpuusage(160),
        capwapbasechanup(161),
        capwapbasechandown(162),
        capwapbasedecrypterrorreport(163),
        capwapbasejoinfail(164),
        capwapbaseimageupgradefail(165),
        capwapbaseconifgmsgerror(166),
        capwapbaseradiooperstatu(167),
        capwapbaseauthenfail(168),
        apmgmtaptimestamp(169),
        apmgmtstaoper(170),
        apmgmtmbchange(171),
        apmgmtapswupdtfail(172),
        widswarninginfo(173),
        privcmccportalunavailable(174),
        privipaddrchange(175),
        dhcppoolexhaust(176),
        dhcppoolnoexhaust(177),
        speheartbeatperiodtrap(178),
        tftpupgradefailed(179),
        syscpuhigh(180),
        syscpuhighrecov(181),
        systemperaturehigh(182),
        systemperaturehighrecov(183),
        sysmemoryhigh(184),
        sysmemoryhighrecov(185),
        speconfigmodifytrap(186),
        speconfigparseerrtrap(187),
        apmgmtstaactoverthrehold(188),
        apmgmtstadisactoverthredhold(189),
        apmgmtstaroamtotaloverthredhlod(190),
        apmgmtstaroamoerminoverthredhold(191),
        apmgmtapwritebuffero(192),
        apmgmtacheartbeat(193),
        apmgmtacpowerstatus(194),
        radiusauthserverrecovertrap(195),
        radiusacctserverrecovertrap(196),
        privcmccportalavailable(197),
        sysapcpuhigh(198),
        sysapcpuhighrecov(199),
        sysapmemoryhigh(200),
        sysapmemoryhighrecov(201),
        syssystemreset(202)
    }
    MAX-ACCESS read-only
    STATUS current
    DESCRIPTION
        "Trap type identifier, every kind of trap which the system support
         will has one entry in this table."
    ::= { fsAppTrapActionEntry 1 }

fsAppTrapAction OBJECT-TYPE
    SYNTAX INTEGER {
        off(0),     -- do nothing
        on(1)       -- send trap
    }
    MAX-ACCESS read-write
    STATUS current
    DESCRIPTION
        "This value decide how to deal with when this type trap has happened."
    ::= { fsAppTrapActionEntry 2 }

fsAppTrapDescr OBJECT-TYPE
    SYNTAX DisplayString
    MAX-ACCESS read-write
    STATUS current
    DESCRIPTION
        "The description of the trap."
    ::= { fsAppTrapActionEntry 3 }

--**********************************************************************
-- about ZCM Zero-Config Management info
--**********************************************************************
fsZCMMIBObjects
    OBJECT IDENTIFIER ::= { fsCapwapAppMIBObjects 7 }

-- zcm mib
fsAssignedIPAddress OBJECT-TYPE
    SYNTAX IpAddress
    MAX-ACCESS not-accessible
    STATUS current
    DESCRIPTION
        "The device ip address information."
    ::= { fsZCMMIBObjects 1 }

fsNeedConfiguration OBJECT-TYPE
    SYNTAX INTEGER {
             no(0),  -- system does not need configuration
             yes(1)  -- system need configuration
           }
    MAX-ACCESS not-accessible
    STATUS current
    DESCRIPTION
        "The device does need configuration."
    ::= { fsZCMMIBObjects 2 }

-- zcm trap
fsZCMMIBTraps
    OBJECT IDENTIFIER ::= { fsZCMMIBObjects 0 }

fsZCMNotifyTrap NOTIFICATION-TYPE
    OBJECTS {
        fsSystemSerialno,
        fsDeviceMacAddress,
        fsAssignedIPAddress,
        fsNeedConfiguration,
        sysObjectID
    }
    STATUS  current
    DESCRIPTION
            "The notification sent when the device startup."
    ::= { fsZCMMIBTraps 1 }

--**********************************************************************
-- about conformance info
--**********************************************************************
fsCapwapAppMIBConformance OBJECT IDENTIFIER ::= { fsCapwapAppMIB 2 }
fsCapwapAppMIBCompliances OBJECT IDENTIFIER ::= { fsCapwapAppMIBConformance 1 }
fsCapwapAppMIBGroups      OBJECT IDENTIFIER ::= { fsCapwapAppMIBConformance 2 }

-- compliance statements
fsCapwapAppMIBCompliance MODULE-COMPLIANCE
    STATUS  current
    DESCRIPTION
        "The compliance statement for entities which implement
         the FS Capwap App MIB"
    MODULE
    MANDATORY-GROUPS {
        fsCapwapAppMIBGroup
    }
    ::= { fsCapwapAppMIBCompliances 1 }

-- units of conformance

fsCapwapAppMIBGroup OBJECT-GROUP
        OBJECTS {
           fsAppHeartbeatOnOff,
           fsAppHeartbeatPeriod,
           fsAppHeartbeatIpAddr,
           fsAppHeartbeatTimeStamp,
           fsAppAdminName,
           fsAppAdminPwd,
           fsAppAdminPriLevel,
           fsAppAdminStatus,
           fsAppPollTimeOfLast,
           fsAppRcvToDefConfig,
           fsAppConfigFileName,
           fsAppConfigParseErrReason,
           fsAppSyslogSvcEnable,
           fsAppSyslogReportEventLevel,
           fsAppSyslogSvrNetType,
           fsAppSyslogSvrNetAddr,
           fsAppSyslogSvrNetPort,
           fsAppSyslogVrfName,
           fsAppSyslogStatus,
           fsSyslogServerAddr,
           fsSyslogServerVrfName,
           fsSyslogServerStatus
        }
        STATUS  current
        DESCRIPTION
                "A collection of objects providing Capwap App configure."
        ::= { fsCapwapAppMIBGroups 1 }

END
