--
-- ISKRATEL-IPMI-MIB.mib
-- MIB generated by MG-SOFT Visual MIB Builder Version 7.0  Build 240
-- Wednesday, March 28, 2012 at 12:22:19
--

	ISKRATEL-IPMI-MIB DEFINITIONS ::= BEGIN

		IMPORTS
			msanAdditionalConf
				FROM ISKRATEL-MSAN-MIB
			DisplayString
				FROM RFC1213-MIB
			Integer32, OBJECT-TYPE, MODULE-IDENTITY
				FROM SNMPv2-SMI;


		-- 1.3.6.1.4.1.1332.1.1.5.3.33
		msanShMC MODULE-IDENTITY
			LAST-UPDATED "201203280944Z"		-- March 28, 2012 at 09:44 GMT
			ORGANIZATION
				"Iskratel"
			CONTACT-INFO
				"Contact-info."
			DESCRIPTION
				"Description."
			::= { msanAdditionalConf 33 }





--
-- Node definitions
--

		-- 1.3.6.1.4.1.1332.1.1.5.3.33.1
		msanShMCImpControllerVariablesTable OBJECT-TYPE
			SYNTAX SEQUENCE OF MsanShMCImpControllerVariablesEntry
			MAX-ACCESS not-accessible
			STATUS current
			DESCRIPTION
				"A Imp Controller report"
			::= { msanShMC 1 }


		-- 1.3.6.1.4.1.1332.1.1.5.3.33.1.1
		msanShMCImpControllerVariablesEntry OBJECT-TYPE
			SYNTAX MsanShMCImpControllerVariablesEntry
			MAX-ACCESS not-accessible
			STATUS current
			DESCRIPTION
				"An IPM Controller entry"
			INDEX { msanShMCImpControllerIndex }
			::= { msanShMCImpControllerVariablesTable 1 }


		MsanShMCImpControllerVariablesEntry ::=
			SEQUENCE {
				msanShMCImpControllerIndex
					INTEGER,
				msanShMCImpControllerSdrVersion
					INTEGER,
				msanShMCImpControllerPicmgVersion
					INTEGER,
				msanShMCImpControllerSlaveAddress
					INTEGER,
				msanShMCImpControllerChannelNumber
					INTEGER,
				msanShMCImpControllerPowerStateNotification
					INTEGER,
				msanShMCImpControllerGlobalInitialisation
					INTEGER,
				msanShMCImpControllerCapabilities
					INTEGER,
				msanShMCImpControllerIdString
					DisplayString,
				msanShMCImpControllerMaximumFru
					INTEGER,
				msanShMCImpControllerOwnFruId
					INTEGER
			 }

		-- 1.3.6.1.4.1.1332.1.1.5.3.33.1.1.1
		msanShMCImpControllerIndex OBJECT-TYPE
			SYNTAX INTEGER (0..255)
			MAX-ACCESS read-only
			STATUS current
			DESCRIPTION
				"Table entry index, equal to <addr>"
			::= { msanShMCImpControllerVariablesEntry 1 }


		-- 1.3.6.1.4.1.1332.1.1.5.3.33.1.1.2
		msanShMCImpControllerSdrVersion OBJECT-TYPE
			SYNTAX INTEGER (0..255)
			MAX-ACCESS read-only
			STATUS current
			DESCRIPTION
				"SDR Version of the Management Controller Device Locator
				Record for this controller"
			::= { msanShMCImpControllerVariablesEntry 2 }


		-- 1.3.6.1.4.1.1332.1.1.5.3.33.1.1.3
		msanShMCImpControllerPicmgVersion OBJECT-TYPE
			SYNTAX INTEGER (0..255)
			MAX-ACCESS read-only
			STATUS current
			DESCRIPTION
				"PICMG Extension Version as reported by controller in a
				Get PICMG Properties replay"
			::= { msanShMCImpControllerVariablesEntry 3 }


		-- 1.3.6.1.4.1.1332.1.1.5.3.33.1.1.4
		msanShMCImpControllerSlaveAddress OBJECT-TYPE
			SYNTAX INTEGER (0..255)
			MAX-ACCESS read-only
			STATUS current
			DESCRIPTION
				"Device Slave Address as defined in the Management Controller
				Device Locator Record for this controller"
			::= { msanShMCImpControllerVariablesEntry 4 }


		-- 1.3.6.1.4.1.1332.1.1.5.3.33.1.1.5
		msanShMCImpControllerChannelNumber OBJECT-TYPE
			SYNTAX INTEGER (0..255)
			MAX-ACCESS read-only
			STATUS current
			DESCRIPTION
				"Channel Number as defined in the Management Controller
				Device Locator Record for this controller"
			::= { msanShMCImpControllerVariablesEntry 5 }


		-- 1.3.6.1.4.1.1332.1.1.5.3.33.1.1.6
		msanShMCImpControllerPowerStateNotification OBJECT-TYPE
			SYNTAX INTEGER (0..255)
			MAX-ACCESS read-only
			STATUS current
			DESCRIPTION
				"Power State Notification as defined in the Management Controller
				Device Locator Record for this controller"
			::= { msanShMCImpControllerVariablesEntry 6 }


		-- 1.3.6.1.4.1.1332.1.1.5.3.33.1.1.7
		msanShMCImpControllerGlobalInitialisation OBJECT-TYPE
			SYNTAX INTEGER (0..255)
			MAX-ACCESS read-only
			STATUS current
			DESCRIPTION
				"Global Initialisation as defined in the Management Controller
				Device Locator Record for this controller"
			::= { msanShMCImpControllerVariablesEntry 7 }


		-- 1.3.6.1.4.1.1332.1.1.5.3.33.1.1.8
		msanShMCImpControllerCapabilities OBJECT-TYPE
			SYNTAX INTEGER (0..255)
			MAX-ACCESS read-only
			STATUS current
			DESCRIPTION
				"Device Capabilities as defined in the Management Controller
				Device Locator Record for this controller"
			::= { msanShMCImpControllerVariablesEntry 8 }


		-- 1.3.6.1.4.1.1332.1.1.5.3.33.1.1.9
		msanShMCImpControllerIdString OBJECT-TYPE
			SYNTAX DisplayString (SIZE (0..255))
			MAX-ACCESS read-only
			STATUS current
			DESCRIPTION
				"Device ID String as defined in the Management Controller
				Device Locator Record for this controller"
			::= { msanShMCImpControllerVariablesEntry 9 }


		-- 1.3.6.1.4.1.1332.1.1.5.3.33.1.1.10
		msanShMCImpControllerMaximumFru OBJECT-TYPE
			SYNTAX INTEGER (0..255)
			MAX-ACCESS read-only
			STATUS current
			DESCRIPTION
				"Max FRU Device ID as reported by controller in a
				Get PICMG Properties replay"
			::= { msanShMCImpControllerVariablesEntry 10 }


		-- 1.3.6.1.4.1.1332.1.1.5.3.33.1.1.11
		msanShMCImpControllerOwnFruId OBJECT-TYPE
			SYNTAX INTEGER (0..255)
			MAX-ACCESS read-only
			STATUS current
			DESCRIPTION
				"FRU Device ID from IPM Controller as reported by controller
				in a Get PICMG Properties replay"
			::= { msanShMCImpControllerVariablesEntry 11 }


		-- 1.3.6.1.4.1.1332.1.1.5.3.33.2
		msanShMCFruDeviceVariablesTable OBJECT-TYPE
			SYNTAX SEQUENCE OF MsanShMCFruDeviceVariablesEntry
			MAX-ACCESS not-accessible
			STATUS current
			DESCRIPTION
				"A FRU Device report"
			::= { msanShMC 2 }


		-- 1.3.6.1.4.1.1332.1.1.5.3.33.2.1
		msanShMCFruDeviceVariablesEntry OBJECT-TYPE
			SYNTAX MsanShMCFruDeviceVariablesEntry
			MAX-ACCESS not-accessible
			STATUS current
			DESCRIPTION
				"An IPM Controller entry"
			INDEX { msanShMCFruDeviceIndex }
			::= { msanShMCFruDeviceVariablesTable 1 }


		MsanShMCFruDeviceVariablesEntry ::=
			SEQUENCE {
				msanShMCFruDeviceIndex
					INTEGER,
				msanShMCFruDeviceSdrVersion
					INTEGER,
				msanShMCFruDeviceSlaveAddress
					INTEGER,
				msanShMCFruDeviceSFruDeviceId
					INTEGER,
				msanShMCFruDeviceChannelNumber
					INTEGER,
				msanShMCFruDeviceDeviceType
					INTEGER,
				msanShMCFruDeviceDeviceTypeModifier
					INTEGER,
				msanShMCFruDeviceFruEntityId
					INTEGER,
				msanShMCFruDeviceFruEntityInstance
					INTEGER,
				msanShMCFruDeviceIdString
					DisplayString,
				msanShMCFruDeviceHotSwapState
					INTEGER,
				msanShMCFruDeviceActivated
					INTEGER
			 }

		-- 1.3.6.1.4.1.1332.1.1.5.3.33.2.1.1
		msanShMCFruDeviceIndex OBJECT-TYPE
			SYNTAX INTEGER (0..-1)
			MAX-ACCESS read-only
			STATUS current
			DESCRIPTION
				"Table entry index, equal to <ipmb_addr> << 16 | <fru_id>"
			::= { msanShMCFruDeviceVariablesEntry 1 }


		-- 1.3.6.1.4.1.1332.1.1.5.3.33.2.1.2
		msanShMCFruDeviceSdrVersion OBJECT-TYPE
			SYNTAX INTEGER (0..255)
			MAX-ACCESS read-only
			STATUS current
			DESCRIPTION
				"SDR Version of the Management Controller Device Locator
				Record for this FRU"
			::= { msanShMCFruDeviceVariablesEntry 2 }


		-- 1.3.6.1.4.1.1332.1.1.5.3.33.2.1.3
		msanShMCFruDeviceSlaveAddress OBJECT-TYPE
			SYNTAX INTEGER (0..255)
			MAX-ACCESS read-only
			STATUS current
			DESCRIPTION
				"Device Slave Address as defined in the Management Controller
				Device Locator Record for this FRU"
			::= { msanShMCFruDeviceVariablesEntry 3 }


		-- 1.3.6.1.4.1.1332.1.1.5.3.33.2.1.4
		msanShMCFruDeviceSFruDeviceId OBJECT-TYPE
			SYNTAX INTEGER (0..255)
			MAX-ACCESS read-only
			STATUS current
			DESCRIPTION
				"FRU Device as defined in the Management Controller Device
				Locator Record for this FRU"
			::= { msanShMCFruDeviceVariablesEntry 4 }


		-- 1.3.6.1.4.1.1332.1.1.5.3.33.2.1.5
		msanShMCFruDeviceChannelNumber OBJECT-TYPE
			SYNTAX INTEGER (0..255)
			MAX-ACCESS read-only
			STATUS current
			DESCRIPTION
				"Channel Number as defined in the Management Controller
				Device Locator Record for this FRU"
			::= { msanShMCFruDeviceVariablesEntry 5 }


		-- 1.3.6.1.4.1.1332.1.1.5.3.33.2.1.6
		msanShMCFruDeviceDeviceType OBJECT-TYPE
			SYNTAX INTEGER (0..255)
			MAX-ACCESS read-only
			STATUS current
			DESCRIPTION
				"For FRUs with FRU Device ID different from zero:
				Device Type as defined in the FRU Device Locator Record for this FRU.
				Since the Management Controller Device Locator Record doesn't provide the
				Device Type information, for Management Controller devices (FRU #0),
				this field is set to FRU Inventory Device (10h)."
			::= { msanShMCFruDeviceVariablesEntry 6 }


		-- 1.3.6.1.4.1.1332.1.1.5.3.33.2.1.7
		msanShMCFruDeviceDeviceTypeModifier OBJECT-TYPE
			SYNTAX INTEGER (0..255)
			MAX-ACCESS read-only
			STATUS current
			DESCRIPTION
				"For FRUs with FRU Device ID different from zero:
				Device Type as defined in the FRU Device Locator Record for this FRU.
				Since the Management Controller Device Locator Record doesn't provide the
				Device Type information, for Management Controller devices (FRU #0),
				this field is set to Unspecified (FFh)."
			::= { msanShMCFruDeviceVariablesEntry 7 }


		-- 1.3.6.1.4.1.1332.1.1.5.3.33.2.1.8
		msanShMCFruDeviceFruEntityId OBJECT-TYPE
			SYNTAX INTEGER (0..255)
			MAX-ACCESS read-only
			STATUS current
			DESCRIPTION
				"(FRU) entity ID as defined in the Management Controller
				Device Locator Record for this FRU"
			::= { msanShMCFruDeviceVariablesEntry 8 }


		-- 1.3.6.1.4.1.1332.1.1.5.3.33.2.1.9
		msanShMCFruDeviceFruEntityInstance OBJECT-TYPE
			SYNTAX INTEGER (0..255)
			MAX-ACCESS read-only
			STATUS current
			DESCRIPTION
				"Channel Number as defined in the Management Controller
				Device Locator Record for this controller"
			::= { msanShMCFruDeviceVariablesEntry 9 }


		-- 1.3.6.1.4.1.1332.1.1.5.3.33.2.1.10
		msanShMCFruDeviceIdString OBJECT-TYPE
			SYNTAX DisplayString (SIZE (0..255))
			MAX-ACCESS read-only
			STATUS current
			DESCRIPTION
				"Device ID String as defined in the Management Controller
				Device Locator Record for this FRU"
			::= { msanShMCFruDeviceVariablesEntry 10 }


		-- 1.3.6.1.4.1.1332.1.1.5.3.33.2.1.11
		msanShMCFruDeviceHotSwapState OBJECT-TYPE
			SYNTAX INTEGER (0..255)
			MAX-ACCESS read-only
			STATUS current
			DESCRIPTION
				"Current PICMG 3.0 FRU state (M0..M7) for this FRU. If this
				variable is equal to n, that means that the FRU is in stat Mn"
			::= { msanShMCFruDeviceVariablesEntry 11 }


		-- 1.3.6.1.4.1.1332.1.1.5.3.33.2.1.12
		msanShMCFruDeviceActivated OBJECT-TYPE
			SYNTAX INTEGER (0..255)
			MAX-ACCESS read-write
			STATUS current
			DESCRIPTION
				"When reading:
				1 means that the FRU device is active (that is, in state M4),
				0 is return otherwise.
				When writing:
					writing 1 to this variable triggers sending the Set FRU Activation
					(Activate FRU) command to this FRU, if the FRU is in state M2 or M5,
					and sending Set FRU Activation policy (Clear Locked) command if
					the FRU is in state M1.

					writin 0 to this variable triggers sending the Set FRU Activation
					(Deactivate FRU) command to this FRU, if the FRU is in state M2, M3,
					M4 or M5, and sending Set FRU Activation policy (Set Locked)
					command if the FRU is in state M1 or M6"
			::= { msanShMCFruDeviceVariablesEntry 12 }


		-- 1.3.6.1.4.1.1332.1.1.5.3.33.3
		msanShMCSensorVariablesTable OBJECT-TYPE
			SYNTAX SEQUENCE OF MsanShMCSensorVariablesEntry
			MAX-ACCESS not-accessible
			STATUS current
			DESCRIPTION
				"A Sensor report"
			::= { msanShMC 3 }


		-- 1.3.6.1.4.1.1332.1.1.5.3.33.3.1
		msanShMCSensorVariablesEntry OBJECT-TYPE
			SYNTAX MsanShMCSensorVariablesEntry
			MAX-ACCESS not-accessible
			STATUS current
			DESCRIPTION
				"An IPM Controller entry"
			INDEX { msanShMCSensorIndex }
			::= { msanShMCSensorVariablesTable 1 }


		MsanShMCSensorVariablesEntry ::=
			SEQUENCE {
				msanShMCSensorIndex
					INTEGER,
				msanShMCSensorSdrVersion
					INTEGER,
				msanShMCSensorRecordType
					INTEGER,
				msanShMCSensorOwnerId
					INTEGER,
				msanShMCSensorOwnerLun
					INTEGER,
				msanShMCSensorNumber
					INTEGER,
				msanShMCSensorEntityInstance
					INTEGER,
				msanShMCSensorEntityId
					INTEGER,
				msanShMCSensorInitialisation
					INTEGER,
				msanShMCSensorCapabilities
					INTEGER,
				msanShMCSensorType
					INTEGER,
				msanShMCSensorEvent
					INTEGER,
				msanShMCSensorAssertionEventMask
					INTEGER,
				msanShMCSensorDeassertionEventMask
					INTEGER,
				msanShMCSensorMask
					INTEGER,
				msanShMCSensorUnit1
					INTEGER,
				msanShMCSensorUnit2
					INTEGER,
				msanShMCSensorUnit3
					INTEGER,
				msanShMCSensorLinearization
					INTEGER,
				msanShMCSensorM
					INTEGER,
				msanShMCSensorTolerance
					INTEGER,
				msanShMCSensorB
					INTEGER,
				msanShMCSensorAccuracy
					INTEGER,
				msanShMCSensorAccuracyExp
					INTEGER,
				msanShMCSensorRexp
					INTEGER,
				msanShMCSensorBexp
					INTEGER,
				msanShMCSensorCharacteristicFlags
					INTEGER,
				msanShMCSensorReading
					INTEGER,
				msanShMCSensorProcessedReading
					DisplayString,
				msanShMCSensorNominalReading
					INTEGER,
				msanShMCSensorNormalMaximum
					INTEGER,
				msanShMCSensorNormalMinimum
					INTEGER,
				msanShMCSensorMaximumReading
					INTEGER,
				msanShMCSensorMinimumReading
					INTEGER,
				msanShMCSensorUpperNonRecoverableThr
					INTEGER,
				msanShMCSensorUpperCriticalThr
					INTEGER,
				msanShMCSensorUpperNonCriticalThr
					INTEGER,
				msanShMCSensorLowerNonRecoverableThr
					INTEGER,
				msanShMCSensorLowerCriticalThr
					INTEGER,
				msanShMCSensorLowerNonCriticalThr
					INTEGER,
				msanShMCSensorPositiveGoingThrHysteresis
					INTEGER,
				msanShMCSensorNegativeGoingThrHysteresis
					INTEGER,
				msanShMCSensorIdString
					DisplayString,
				msanShMCSensorEntireSensorData
					OCTET STRING
			 }

		-- 1.3.6.1.4.1.1332.1.1.5.3.33.3.1.1
		msanShMCSensorIndex OBJECT-TYPE
			SYNTAX INTEGER (0..-1)
			MAX-ACCESS read-only
			STATUS current
			DESCRIPTION
				"Table entry index, equal to <ipmb_addr> << 16 | <seqnum>"
			::= { msanShMCSensorVariablesEntry 1 }


		-- 1.3.6.1.4.1.1332.1.1.5.3.33.3.1.2
		msanShMCSensorSdrVersion OBJECT-TYPE
			SYNTAX INTEGER (0..255)
			MAX-ACCESS read-only
			STATUS current
			DESCRIPTION
				"SDR Version of the Sensor Record"
			::= { msanShMCSensorVariablesEntry 2 }


		-- 1.3.6.1.4.1.1332.1.1.5.3.33.3.1.3
		msanShMCSensorRecordType OBJECT-TYPE
			SYNTAX INTEGER (0..255)
			MAX-ACCESS read-only
			STATUS current
			DESCRIPTION
				"Record Type of Sensor Record:
				01h - for Full Sensor Records"
			::= { msanShMCSensorVariablesEntry 3 }


		-- 1.3.6.1.4.1.1332.1.1.5.3.33.3.1.4
		msanShMCSensorOwnerId OBJECT-TYPE
			SYNTAX INTEGER (0..255)
			MAX-ACCESS read-only
			STATUS current
			DESCRIPTION
				"Sensor Owner ID as defined in the Sensor Record"
			::= { msanShMCSensorVariablesEntry 4 }


		-- 1.3.6.1.4.1.1332.1.1.5.3.33.3.1.5
		msanShMCSensorOwnerLun OBJECT-TYPE
			SYNTAX INTEGER (0..255)
			MAX-ACCESS read-only
			STATUS current
			DESCRIPTION
				"Sensor Owner LUN as defined in the Sensor Record"
			::= { msanShMCSensorVariablesEntry 5 }


		-- 1.3.6.1.4.1.1332.1.1.5.3.33.3.1.6
		msanShMCSensorNumber OBJECT-TYPE
			SYNTAX INTEGER (0..255)
			MAX-ACCESS read-only
			STATUS current
			DESCRIPTION
				"Sensor Number as defined in the Sensor Record"
			::= { msanShMCSensorVariablesEntry 6 }


		-- 1.3.6.1.4.1.1332.1.1.5.3.33.3.1.7
		msanShMCSensorEntityInstance OBJECT-TYPE
			SYNTAX INTEGER (0..255)
			MAX-ACCESS read-only
			STATUS current
			DESCRIPTION
				"Entity Instance as defined in the Sensor Record"
			::= { msanShMCSensorVariablesEntry 7 }


		-- 1.3.6.1.4.1.1332.1.1.5.3.33.3.1.8
		msanShMCSensorEntityId OBJECT-TYPE
			SYNTAX INTEGER (0..255)
			MAX-ACCESS read-only
			STATUS current
			DESCRIPTION
				"Entity ID as defined in the Sensor Record"
			::= { msanShMCSensorVariablesEntry 8 }


		-- 1.3.6.1.4.1.1332.1.1.5.3.33.3.1.9
		msanShMCSensorInitialisation OBJECT-TYPE
			SYNTAX INTEGER (0..255)
			MAX-ACCESS read-only
			STATUS current
			DESCRIPTION
				"Sensor Initialisation as defined in the Sensor Record"
			::= { msanShMCSensorVariablesEntry 9 }


		-- 1.3.6.1.4.1.1332.1.1.5.3.33.3.1.10
		msanShMCSensorCapabilities OBJECT-TYPE
			SYNTAX INTEGER (0..255)
			MAX-ACCESS read-only
			STATUS current
			DESCRIPTION
				"Sensor Capabilities as defined in the Sensor Record"
			::= { msanShMCSensorVariablesEntry 10 }


		-- 1.3.6.1.4.1.1332.1.1.5.3.33.3.1.11
		msanShMCSensorType OBJECT-TYPE
			SYNTAX INTEGER (0..255)
			MAX-ACCESS read-only
			STATUS current
			DESCRIPTION
				"Sensor Type as defined in the Sensor Record"
			::= { msanShMCSensorVariablesEntry 11 }


		-- 1.3.6.1.4.1.1332.1.1.5.3.33.3.1.12
		msanShMCSensorEvent OBJECT-TYPE
			SYNTAX INTEGER (0..255)
			MAX-ACCESS read-only
			STATUS current
			DESCRIPTION
				"Event/reading Type Code as defined in the Sensor Record"
			::= { msanShMCSensorVariablesEntry 12 }


		-- 1.3.6.1.4.1.1332.1.1.5.3.33.3.1.13
		msanShMCSensorAssertionEventMask OBJECT-TYPE
			SYNTAX INTEGER (0..65535)
			MAX-ACCESS read-only
			STATUS current
			DESCRIPTION
				"Assertion Event Mask / Lower Treshold Reading
				Mask as defined in the Sensor Record"
			::= { msanShMCSensorVariablesEntry 13 }


		-- 1.3.6.1.4.1.1332.1.1.5.3.33.3.1.14
		msanShMCSensorDeassertionEventMask OBJECT-TYPE
			SYNTAX INTEGER (0..65535)
			MAX-ACCESS read-only
			STATUS current
			DESCRIPTION
				"Deassertion Event Mask / Upper Treshold Reading
				Mask as defined in the Sensor Record"
			::= { msanShMCSensorVariablesEntry 14 }


		-- 1.3.6.1.4.1.1332.1.1.5.3.33.3.1.15
		msanShMCSensorMask OBJECT-TYPE
			SYNTAX INTEGER (0..255)
			MAX-ACCESS read-only
			STATUS current
			DESCRIPTION
				"Discrete Reading Mask / Settable Treshold Mask as defined in the Sensor Record"
			::= { msanShMCSensorVariablesEntry 15 }


		-- 1.3.6.1.4.1.1332.1.1.5.3.33.3.1.16
		msanShMCSensorUnit1 OBJECT-TYPE
			SYNTAX INTEGER (0..255)
			MAX-ACCESS read-only
			STATUS current
			DESCRIPTION
				"Sensor Units 1 as defined in the Sensor Record"
			::= { msanShMCSensorVariablesEntry 16 }


		-- 1.3.6.1.4.1.1332.1.1.5.3.33.3.1.17
		msanShMCSensorUnit2 OBJECT-TYPE
			SYNTAX INTEGER (0..255)
			MAX-ACCESS read-only
			STATUS current
			DESCRIPTION
				"Sensor Units 2 as defined in the Sensor Record"
			::= { msanShMCSensorVariablesEntry 17 }


		-- 1.3.6.1.4.1.1332.1.1.5.3.33.3.1.18
		msanShMCSensorUnit3 OBJECT-TYPE
			SYNTAX INTEGER (0..255)
			MAX-ACCESS read-only
			STATUS current
			DESCRIPTION
				"Sensor Units 3 as defined in the Sensor Record"
			::= { msanShMCSensorVariablesEntry 18 }


		-- 1.3.6.1.4.1.1332.1.1.5.3.33.3.1.19
		msanShMCSensorLinearization OBJECT-TYPE
			SYNTAX INTEGER (0..255)
			MAX-ACCESS read-only
			STATUS current
			DESCRIPTION
				"Linearization as defined in the Sensor Record.
				Valid only for full Sensor Records."
			::= { msanShMCSensorVariablesEntry 19 }


		-- 1.3.6.1.4.1.1332.1.1.5.3.33.3.1.20
		msanShMCSensorM OBJECT-TYPE
			SYNTAX INTEGER (0..255)
			MAX-ACCESS read-only
			STATUS current
			DESCRIPTION
				"M sensor reading conversion parameter as defined in the Sensor Record.
				Valid only for full Sensor Records."
			::= { msanShMCSensorVariablesEntry 20 }


		-- 1.3.6.1.4.1.1332.1.1.5.3.33.3.1.21
		msanShMCSensorTolerance OBJECT-TYPE
			SYNTAX INTEGER (0..255)
			MAX-ACCESS read-only
			STATUS current
			DESCRIPTION
				"Tolerance sensor reading conversion parameter as defined in the Sensor Record.
				Valid only for full Sensor Records."
			::= { msanShMCSensorVariablesEntry 21 }


		-- 1.3.6.1.4.1.1332.1.1.5.3.33.3.1.22
		msanShMCSensorB OBJECT-TYPE
			SYNTAX INTEGER (0..255)
			MAX-ACCESS read-only
			STATUS current
			DESCRIPTION
				"B sensor reading conversion parameter as defined in the Sensor Record.
				Valid only for full Sensor Records."
			::= { msanShMCSensorVariablesEntry 22 }


		-- 1.3.6.1.4.1.1332.1.1.5.3.33.3.1.23
		msanShMCSensorAccuracy OBJECT-TYPE
			SYNTAX INTEGER (0..255)
			MAX-ACCESS read-only
			STATUS current
			DESCRIPTION
				"Accuracy sensor reading conversion parameter as defined in the Sensor Record.
				Valid only for full Sensor Records."
			::= { msanShMCSensorVariablesEntry 23 }


		-- 1.3.6.1.4.1.1332.1.1.5.3.33.3.1.24
		msanShMCSensorAccuracyExp OBJECT-TYPE
			SYNTAX INTEGER (0..255)
			MAX-ACCESS read-only
			STATUS current
			DESCRIPTION
				"Accuracy exp sensor reading conversion parameter as defined in the Sensor Record.
				Valid only for full Sensor Records."
			::= { msanShMCSensorVariablesEntry 24 }


		-- 1.3.6.1.4.1.1332.1.1.5.3.33.3.1.25
		msanShMCSensorRexp OBJECT-TYPE
			SYNTAX INTEGER (0..255)
			MAX-ACCESS read-only
			STATUS current
			DESCRIPTION
				"R exp sensor reading conversion parameter as defined in the Sensor Record.
				Valid only for full Sensor Records."
			::= { msanShMCSensorVariablesEntry 25 }


		-- 1.3.6.1.4.1.1332.1.1.5.3.33.3.1.26
		msanShMCSensorBexp OBJECT-TYPE
			SYNTAX INTEGER (0..255)
			MAX-ACCESS read-only
			STATUS current
			DESCRIPTION
				"B exp sensor reading conversion parameter as defined in the Sensor Record.
				Valid only for full Sensor Records."
			::= { msanShMCSensorVariablesEntry 26 }


		-- 1.3.6.1.4.1.1332.1.1.5.3.33.3.1.27
		msanShMCSensorCharacteristicFlags OBJECT-TYPE
			SYNTAX INTEGER (0..255)
			MAX-ACCESS read-only
			STATUS current
			DESCRIPTION
				"Analog characteristic flags as defined in the Sensor Record.
				Valid only for full Sensor Records."
			::= { msanShMCSensorVariablesEntry 27 }


		-- 1.3.6.1.4.1.1332.1.1.5.3.33.3.1.28
		msanShMCSensorReading OBJECT-TYPE
			SYNTAX INTEGER (0..255)
			MAX-ACCESS read-only
			STATUS current
			DESCRIPTION
				"Current sensor reading in raw form."
			::= { msanShMCSensorVariablesEntry 28 }


		-- 1.3.6.1.4.1.1332.1.1.5.3.33.3.1.29
		msanShMCSensorProcessedReading OBJECT-TYPE
			SYNTAX DisplayString (SIZE (0..255))
			MAX-ACCESS read-only
			STATUS current
			DESCRIPTION
				"Current sensor reading processed according to reading
				conversion formula for this sensor"
			::= { msanShMCSensorVariablesEntry 29 }


		-- 1.3.6.1.4.1.1332.1.1.5.3.33.3.1.30
		msanShMCSensorNominalReading OBJECT-TYPE
			SYNTAX INTEGER (0..255)
			MAX-ACCESS read-only
			STATUS current
			DESCRIPTION
				"Nominal Reading as defined in the Sensor Record.
				Valid only for full Sensor Records."
			::= { msanShMCSensorVariablesEntry 30 }


		-- 1.3.6.1.4.1.1332.1.1.5.3.33.3.1.31
		msanShMCSensorNormalMaximum OBJECT-TYPE
			SYNTAX INTEGER (0..255)
			MAX-ACCESS read-only
			STATUS current
			DESCRIPTION
				"Normal Maximum as defined in the Sensor Record.
				Valid only for full Sensor Records."
			::= { msanShMCSensorVariablesEntry 31 }


		-- 1.3.6.1.4.1.1332.1.1.5.3.33.3.1.32
		msanShMCSensorNormalMinimum OBJECT-TYPE
			SYNTAX INTEGER (0..255)
			MAX-ACCESS read-only
			STATUS current
			DESCRIPTION
				"Normal Minimum as defined in the Sensor Record.
				Valid only for full Sensor Records."
			::= { msanShMCSensorVariablesEntry 32 }


		-- 1.3.6.1.4.1.1332.1.1.5.3.33.3.1.33
		msanShMCSensorMaximumReading OBJECT-TYPE
			SYNTAX INTEGER (0..255)
			MAX-ACCESS read-only
			STATUS current
			DESCRIPTION
				"Sensor Maximum Reading as defined in the Sensor Record.
				Valid only for full Sensor Records."
			::= { msanShMCSensorVariablesEntry 33 }


		-- 1.3.6.1.4.1.1332.1.1.5.3.33.3.1.34
		msanShMCSensorMinimumReading OBJECT-TYPE
			SYNTAX INTEGER (0..255)
			MAX-ACCESS read-only
			STATUS current
			DESCRIPTION
				"Sensor Minimum Reading as defined in the Sensor Record.
				Valid only for full Sensor Records."
			::= { msanShMCSensorVariablesEntry 34 }


		-- 1.3.6.1.4.1.1332.1.1.5.3.33.3.1.35
		msanShMCSensorUpperNonRecoverableThr OBJECT-TYPE
			SYNTAX INTEGER (0..255)
			MAX-ACCESS read-only
			STATUS current
			DESCRIPTION
				"Upper non-recoverable Threshold as defined in the Sensor Record.
				Valid only for full Sensor Records."
			::= { msanShMCSensorVariablesEntry 35 }


		-- 1.3.6.1.4.1.1332.1.1.5.3.33.3.1.36
		msanShMCSensorUpperCriticalThr OBJECT-TYPE
			SYNTAX INTEGER (0..255)
			MAX-ACCESS read-only
			STATUS current
			DESCRIPTION
				"Upper critical Threshold as defined in the Sensor Record.
				Valid only for full Sensor Records."
			::= { msanShMCSensorVariablesEntry 36 }


		-- 1.3.6.1.4.1.1332.1.1.5.3.33.3.1.37
		msanShMCSensorUpperNonCriticalThr OBJECT-TYPE
			SYNTAX INTEGER (0..255)
			MAX-ACCESS read-only
			STATUS current
			DESCRIPTION
				"Upper non-critical Threshold as defined in the Sensor Record.
				Valid only for full Sensor Records."
			::= { msanShMCSensorVariablesEntry 37 }


		-- 1.3.6.1.4.1.1332.1.1.5.3.33.3.1.38
		msanShMCSensorLowerNonRecoverableThr OBJECT-TYPE
			SYNTAX INTEGER (0..255)
			MAX-ACCESS read-only
			STATUS current
			DESCRIPTION
				"Lower non-recoverable Threshold as defined in the Sensor Record.
				Valid only for full Sensor Records."
			::= { msanShMCSensorVariablesEntry 38 }


		-- 1.3.6.1.4.1.1332.1.1.5.3.33.3.1.39
		msanShMCSensorLowerCriticalThr OBJECT-TYPE
			SYNTAX INTEGER (0..255)
			MAX-ACCESS read-only
			STATUS current
			DESCRIPTION
				"Lower critical Threshold as defined in the Sensor Record.
				Valid only for full Sensor Records."
			::= { msanShMCSensorVariablesEntry 39 }


		-- 1.3.6.1.4.1.1332.1.1.5.3.33.3.1.40
		msanShMCSensorLowerNonCriticalThr OBJECT-TYPE
			SYNTAX INTEGER (0..255)
			MAX-ACCESS read-only
			STATUS current
			DESCRIPTION
				"Lower non-critical Threshold as defined in the Sensor Record.
				Valid only for full Sensor Records."
			::= { msanShMCSensorVariablesEntry 40 }


		-- 1.3.6.1.4.1.1332.1.1.5.3.33.3.1.41
		msanShMCSensorPositiveGoingThrHysteresis OBJECT-TYPE
			SYNTAX INTEGER (0..255)
			MAX-ACCESS read-only
			STATUS current
			DESCRIPTION
				"Positive-going Threshold Hysteresis as defined in the Sensor Record.
				Valid only for full Sensor Records."
			::= { msanShMCSensorVariablesEntry 41 }


		-- 1.3.6.1.4.1.1332.1.1.5.3.33.3.1.42
		msanShMCSensorNegativeGoingThrHysteresis OBJECT-TYPE
			SYNTAX INTEGER (0..255)
			MAX-ACCESS read-only
			STATUS current
			DESCRIPTION
				"Negative-going Threshold Hysteresis as defined in the Sensor Record.
				Valid only for full Sensor Records."
			::= { msanShMCSensorVariablesEntry 42 }


		-- 1.3.6.1.4.1.1332.1.1.5.3.33.3.1.43
		msanShMCSensorIdString OBJECT-TYPE
			SYNTAX DisplayString (SIZE (0..255))
			MAX-ACCESS read-only
			STATUS current
			DESCRIPTION
				"Device ID String as defined in the Sensor Record."
			::= { msanShMCSensorVariablesEntry 43 }


		-- 1.3.6.1.4.1.1332.1.1.5.3.33.3.1.44
		msanShMCSensorEntireSensorData OBJECT-TYPE
			SYNTAX OCTET STRING (SIZE (0..255))
			MAX-ACCESS read-only
			STATUS current
			DESCRIPTION
				"Device ID String as defined in the Sensor Record."
			::= { msanShMCSensorVariablesEntry 44 }


		-- 1.3.6.1.4.1.1332.1.1.5.3.33.4
		msanShMCBoardsTable OBJECT-TYPE
			SYNTAX SEQUENCE OF MsanShMCBoardsEntry
			MAX-ACCESS not-accessible
			STATUS current
			DESCRIPTION
				"A list of boards"
			::= { msanShMC 4 }


		-- 1.3.6.1.4.1.1332.1.1.5.3.33.4.1
		msanShMCBoardsEntry OBJECT-TYPE
			SYNTAX MsanShMCBoardsEntry
			MAX-ACCESS not-accessible
			STATUS current
			DESCRIPTION
				"An IPM Controller entry"
			INDEX { msanShMCBoardsIndex }
			::= { msanShMCBoardsTable 1 }


		MsanShMCBoardsEntry ::=
			SEQUENCE {
				msanShMCBoardsIndex
					INTEGER,
				msanShMCBoardsBoardBasicPresent
					INTEGER,
				msanShMCBoardsBoardBasicHealthy
					INTEGER,
				msanShMCBoardsBoardBasicReset
					INTEGER,
				msanShMCBoardsBoardBasicSlaveAddress
					INTEGER,
				msanShMCBoardsBoardBasicFruDeviceId
					INTEGER
			 }

		-- 1.3.6.1.4.1.1332.1.1.5.3.33.4.1.1
		msanShMCBoardsIndex OBJECT-TYPE
			SYNTAX INTEGER (0..255)
			MAX-ACCESS read-only
			STATUS current
			DESCRIPTION
				"Table index equal to <boardnum>"
			::= { msanShMCBoardsEntry 1 }


		-- 1.3.6.1.4.1.1332.1.1.5.3.33.4.1.2
		msanShMCBoardsBoardBasicPresent OBJECT-TYPE
			SYNTAX INTEGER
				{
				absent(0),
				present(1)
				}
			MAX-ACCESS read-only
			STATUS current
			DESCRIPTION
				"0 - Board is absent
				1 - Board is present"
			::= { msanShMCBoardsEntry 2 }


		-- 1.3.6.1.4.1.1332.1.1.5.3.33.4.1.3
		msanShMCBoardsBoardBasicHealthy OBJECT-TYPE
			SYNTAX INTEGER
				{
				off(0),
				on(1)
				}
			MAX-ACCESS read-only
			STATUS current
			DESCRIPTION
				"Causes the BMC to return a high level version of the system health status in integer.
				The BMC returns an integer with the following values:
				     0 - off
				     1 - on"
			::= { msanShMCBoardsEntry 3 }


		-- 1.3.6.1.4.1.1332.1.1.5.3.33.4.1.4
		msanShMCBoardsBoardBasicReset OBJECT-TYPE
			SYNTAX INTEGER
				{
				none(0),
				cold(1)
				}
			MAX-ACCESS read-write
			STATUS current
			DESCRIPTION
				"on read:     1   - board is in reset state
				0   - otherwise
				on write:    0   - do nothing
				1   - perform COLD reset"
			::= { msanShMCBoardsEntry 4 }


		-- 1.3.6.1.4.1.1332.1.1.5.3.33.4.1.5
		msanShMCBoardsBoardBasicSlaveAddress OBJECT-TYPE
			SYNTAX INTEGER (0..255)
			MAX-ACCESS read-only
			STATUS current
			DESCRIPTION
				"The on board IPMI controller 7-bit I2C addresses for IPMB messages"
			::= { msanShMCBoardsEntry 5 }


		-- 1.3.6.1.4.1.1332.1.1.5.3.33.4.1.7
		msanShMCBoardsBoardBasicFruDeviceId OBJECT-TYPE
			SYNTAX INTEGER (0..255)
			MAX-ACCESS read-only
			STATUS current
			DESCRIPTION
				"FRU Device ID field is used to identify individual FRU devices
				on the given LUN in the management controller. Up to 255 FRU
				devices can be located on a given LUN. FRU Device ID #00 at
				LUN 00b is predefined as being the FRU Device for the FRU that
				the management controller is located on. Since there are four
				possible LUNs for a management controller, this means up to
				255*4 FRU devices can be supported behind a single management
				controller using this mechanism. The Read/Write FRU Device
				commands provide an abstracted interface that hides the
				technology used to implement the FRU device from system software."
			::= { msanShMCBoardsEntry 7 }


		-- 1.3.6.1.4.1.1332.1.1.5.3.33.5
		msanShMCSelTable OBJECT-TYPE
			SYNTAX SEQUENCE OF MsanShMCSelEntry
			MAX-ACCESS not-accessible
			STATUS current
			DESCRIPTION
				"A list of Sel"
			::= { msanShMC 5 }


		-- 1.3.6.1.4.1.1332.1.1.5.3.33.5.1
		msanShMCSelEntry OBJECT-TYPE
			SYNTAX MsanShMCSelEntry
			MAX-ACCESS not-accessible
			STATUS current
			DESCRIPTION
				"An System Event Log Variables entry"
			INDEX { msanShMCSelIndex }
			::= { msanShMCSelTable 1 }


		MsanShMCSelEntry ::=
			SEQUENCE {
				msanShMCSelIndex
					INTEGER,
				msanShMCSelcontents
					OCTET STRING
			 }

		-- 1.3.6.1.4.1.1332.1.1.5.3.33.5.1.1
		msanShMCSelIndex OBJECT-TYPE
			SYNTAX INTEGER (0..255)
			MAX-ACCESS read-only
			STATUS current
			DESCRIPTION
				"Table entry index, equal to <recid>"
			::= { msanShMCSelEntry 1 }


		-- 1.3.6.1.4.1.1332.1.1.5.3.33.5.1.2
		msanShMCSelcontents OBJECT-TYPE
			SYNTAX OCTET STRING (SIZE (0..255))
			MAX-ACCESS read-only
			STATUS current
			DESCRIPTION
				"Contents of the SEL entry"
			::= { msanShMCSelEntry 2 }


		-- 1.3.6.1.4.1.1332.1.1.5.3.33.6
		msanShMCShelfTable OBJECT-TYPE
			SYNTAX SEQUENCE OF MsanShMCShelfEntry
			MAX-ACCESS not-accessible
			STATUS current
			DESCRIPTION
				"A list of Shelf"
			::= { msanShMC 6 }


		-- 1.3.6.1.4.1.1332.1.1.5.3.33.6.1
		msanShMCShelfEntry OBJECT-TYPE
			SYNTAX MsanShMCShelfEntry
			MAX-ACCESS not-accessible
			STATUS current
			DESCRIPTION
				"An System Event Log Variables entry"
			INDEX { msanShMCShelfIndex }
			::= { msanShMCShelfTable 1 }


		MsanShMCShelfEntry ::=
			SEQUENCE {
				msanShMCShelfIndex
					INTEGER,
				msanShMCShelfHealthy
					INTEGER
			 }

		-- 1.3.6.1.4.1.1332.1.1.5.3.33.6.1.1
		msanShMCShelfIndex OBJECT-TYPE
			SYNTAX INTEGER (0..255)
			MAX-ACCESS read-only
			STATUS current
			DESCRIPTION
				"Table entry index, equal to <shelfid>"
			::= { msanShMCShelfEntry 1 }


		-- 1.3.6.1.4.1.1332.1.1.5.3.33.6.1.2
		msanShMCShelfHealthy OBJECT-TYPE
			SYNTAX INTEGER (0..255)
			MAX-ACCESS read-only
			STATUS current
			DESCRIPTION
				"1 - if the shelf doesn't have unhealthy components,
				0 - if there exist unhelthy components in the shelf"
			::= { msanShMCShelfEntry 2 }


		-- 1.3.6.1.4.1.1332.1.1.5.3.33.8
		msanShMCPefConfiguration OBJECT IDENTIFIER ::= { msanShMC 8 }


		-- 1.3.6.1.4.1.1332.1.1.5.3.33.8.1
		msanShMCPefConfigurationSetInProgress OBJECT-TYPE
			SYNTAX INTEGER
				{
				off(0),
				on(1)
				}
			MAX-ACCESS read-only
			STATUS current
			DESCRIPTION
				"Set in progrese parameter"
			::= { msanShMCPefConfiguration 1 }


		-- 1.3.6.1.4.1.1332.1.1.5.3.33.8.2
		msanShMCPefConfigurationControl OBJECT-TYPE
			SYNTAX INTEGER
				{
				off(0),
				on(1)
				}
			MAX-ACCESS read-write
			STATUS current
			DESCRIPTION
				"PEF Control parameter"
			::= { msanShMCPefConfiguration 2 }


		-- 1.3.6.1.4.1.1332.1.1.5.3.33.8.3
		msanShMCPefConfigurationActionGlobalControl OBJECT-TYPE
			SYNTAX INTEGER
				{
				off(0),
				on(1)
				}
			MAX-ACCESS read-write
			STATUS current
			DESCRIPTION
				"PEF Action global control  parameter"
			::= { msanShMCPefConfiguration 3 }


		-- 1.3.6.1.4.1.1332.1.1.5.3.33.8.4
		msanShMCPefConfigurationStartupDelay OBJECT-TYPE
			SYNTAX INTEGER
				{
				off(0),
				on(1)
				}
			MAX-ACCESS read-write
			STATUS current
			DESCRIPTION
				"PEF Startup Delay parameter"
			::= { msanShMCPefConfiguration 4 }


		-- 1.3.6.1.4.1.1332.1.1.5.3.33.8.5
		msanShMCPefConfigurationAlertStartupDelay OBJECT-TYPE
			SYNTAX INTEGER
				{
				off(0),
				on(1)
				}
			MAX-ACCESS read-only
			STATUS current
			DESCRIPTION
				"PEF Alert Startup Delay parameter"
			::= { msanShMCPefConfiguration 5 }


		-- 1.3.6.1.4.1.1332.1.1.5.3.33.8.6
		msanShMCPefConfigurationNumberOfEventFilters OBJECT-TYPE
			SYNTAX INTEGER
				{
				off(0),
				on(1)
				}
			MAX-ACCESS read-only
			STATUS current
			DESCRIPTION
				"Number of Event Filters parameter"
			::= { msanShMCPefConfiguration 6 }


		-- 1.3.6.1.4.1.1332.1.1.5.3.33.8.7
		msanShMCPefConfigurationNumberOfAlertPoliciEntries OBJECT-TYPE
			SYNTAX INTEGER
				{
				off(0),
				on(1)
				}
			MAX-ACCESS read-only
			STATUS current
			DESCRIPTION
				"Number of Alert Polici Entries parameter"
			::= { msanShMCPefConfiguration 7 }


		-- 1.3.6.1.4.1.1332.1.1.5.3.33.8.8
		msanShMCPefConfigurationSystemGuid OBJECT-TYPE
			SYNTAX INTEGER
				{
				off(0),
				on(1)
				}
			MAX-ACCESS read-write
			STATUS current
			DESCRIPTION
				"System GUID parameter, excluding the 'Used to fill in the GUID field
				in a PET Trap' byte"
			::= { msanShMCPefConfiguration 8 }


		-- 1.3.6.1.4.1.1332.1.1.5.3.33.8.9
		msanShMCPefConfigurationNumberOfAlertStrings OBJECT-TYPE
			SYNTAX INTEGER
				{
				off(0),
				on(1)
				}
			MAX-ACCESS read-only
			STATUS current
			DESCRIPTION
				"Number of Alert Strings parameter"
			::= { msanShMCPefConfiguration 9 }


		-- 1.3.6.1.4.1.1332.1.1.5.3.33.14
		msanShMCPefConfigurationEventFilterTable OBJECT-TYPE
			SYNTAX SEQUENCE OF MsanShMCPefConfigurationEventFilterEntry
			MAX-ACCESS not-accessible
			STATUS current
			DESCRIPTION
				"A list of PefConfigurationEventFilter"
			::= { msanShMC 14 }


		-- 1.3.6.1.4.1.1332.1.1.5.3.33.14.1
		msanShMCPefConfigurationEventFilterEntry OBJECT-TYPE
			SYNTAX MsanShMCPefConfigurationEventFilterEntry
			MAX-ACCESS not-accessible
			STATUS current
			DESCRIPTION
				"An System Event Log Variables entry"
			INDEX { msanShMCPefConfigurationEventFilterIndex }
			::= { msanShMCPefConfigurationEventFilterTable 1 }


		MsanShMCPefConfigurationEventFilterEntry ::=
			SEQUENCE {
				msanShMCPefConfigurationEventFilterIndex
					INTEGER,
				msanShMCPefConfigurationEventFilterData
					OCTET STRING
			 }

		-- 1.3.6.1.4.1.1332.1.1.5.3.33.14.1.1
		msanShMCPefConfigurationEventFilterIndex OBJECT-TYPE
			SYNTAX INTEGER (0..255)
			MAX-ACCESS read-only
			STATUS current
			DESCRIPTION
				"Table entry index, equal to <filter>"
			::= { msanShMCPefConfigurationEventFilterEntry 1 }


		-- 1.3.6.1.4.1.1332.1.1.5.3.33.14.1.2
		msanShMCPefConfigurationEventFilterData OBJECT-TYPE
			SYNTAX OCTET STRING (SIZE (20))
			MAX-ACCESS read-write
			STATUS current
			DESCRIPTION
				"Event Filter Table entry data, excluding the Set Selector byte"
			::= { msanShMCPefConfigurationEventFilterEntry 2 }


		-- 1.3.6.1.4.1.1332.1.1.5.3.33.19
		msanShMCPefConfigurationAlertStringTable OBJECT-TYPE
			SYNTAX SEQUENCE OF MsanShMCPefConfigurationAlertStringEntry
			MAX-ACCESS not-accessible
			STATUS current
			DESCRIPTION
				"A list of PEF Configuration Alert String"
			::= { msanShMC 19 }


		-- 1.3.6.1.4.1.1332.1.1.5.3.33.19.1
		msanShMCPefConfigurationAlertStringEntry OBJECT-TYPE
			SYNTAX MsanShMCPefConfigurationAlertStringEntry
			MAX-ACCESS not-accessible
			STATUS current
			DESCRIPTION
				"An System Event Log Variables entry"
			INDEX { msanShMCPefConfigurationAlertStringIndex }
			::= { msanShMCPefConfigurationAlertStringTable 1 }


		MsanShMCPefConfigurationAlertStringEntry ::=
			SEQUENCE {
				msanShMCPefConfigurationAlertStringIndex
					INTEGER,
				msanShMCPefConfigurationAlertStringKey
					OCTET STRING,
				msanShMCPefConfigurationAlertString
					DisplayString
			 }

		-- 1.3.6.1.4.1.1332.1.1.5.3.33.19.1.1
		msanShMCPefConfigurationAlertStringIndex OBJECT-TYPE
			SYNTAX INTEGER (0..255)
			MAX-ACCESS read-only
			STATUS current
			DESCRIPTION
				"Table entry index, equal to <strnum>"
			::= { msanShMCPefConfigurationAlertStringEntry 1 }


		-- 1.3.6.1.4.1.1332.1.1.5.3.33.19.1.2
		msanShMCPefConfigurationAlertStringKey OBJECT-TYPE
			SYNTAX OCTET STRING (SIZE (2))
			MAX-ACCESS read-only
			STATUS current
			DESCRIPTION
				"Alert String Keys entry data, excluding the Set Selector byte"
			::= { msanShMCPefConfigurationAlertStringEntry 2 }


		-- 1.3.6.1.4.1.1332.1.1.5.3.33.19.1.3
		msanShMCPefConfigurationAlertString OBJECT-TYPE
			SYNTAX DisplayString (SIZE (255))
			MAX-ACCESS read-only
			STATUS current
			DESCRIPTION
				"Alert Strings entry data, excluding the Set Selector byte"
			::= { msanShMCPefConfigurationAlertStringEntry 3 }


		-- 1.3.6.1.4.1.1332.1.1.5.3.33.20
		msanShMCFruInfoTable OBJECT-TYPE
			SYNTAX SEQUENCE OF MsanShMCFruInfoEntry
			MAX-ACCESS not-accessible
			STATUS current
			DESCRIPTION
				"A list of Fru Infornations"
			::= { msanShMC 20 }


		-- 1.3.6.1.4.1.1332.1.1.5.3.33.20.1
		msanShMCFruInfoEntry OBJECT-TYPE
			SYNTAX MsanShMCFruInfoEntry
			MAX-ACCESS not-accessible
			STATUS current
			DESCRIPTION
				"An FRU information"
			INDEX { msanShMCFruInfoIndex }
			::= { msanShMCFruInfoTable 1 }


		MsanShMCFruInfoEntry ::=
			SEQUENCE {
				msanShMCFruInfoIndex
					INTEGER,
				msanShMCFruInfoData
					OCTET STRING,
				msanShMCFruInfoDataWo
					OCTET STRING
			 }

		-- 1.3.6.1.4.1.1332.1.1.5.3.33.20.1.1
		msanShMCFruInfoIndex OBJECT-TYPE
			SYNTAX INTEGER (0..255)
			MAX-ACCESS read-only
			STATUS current
			DESCRIPTION
				"Index = (<ipmb addr> << 24) | (<fru id> << 16) | <block number>"
			::= { msanShMCFruInfoEntry 1 }


		-- 1.3.6.1.4.1.1332.1.1.5.3.33.20.1.2
		msanShMCFruInfoData OBJECT-TYPE
			SYNTAX OCTET STRING (SIZE (1..32))
			MAX-ACCESS read-only
			STATUS current
			DESCRIPTION
				"A block of data"
			::= { msanShMCFruInfoEntry 2 }


		-- 1.3.6.1.4.1.1332.1.1.5.3.33.20.1.3
		msanShMCFruInfoDataWo OBJECT-TYPE
			SYNTAX OCTET STRING (SIZE (1..32))
			MAX-ACCESS read-write
			STATUS current
			DESCRIPTION
				"Write any number of bytes up to 32. Due to limitations in the
				current version of the SNMP agent, <block number> is interpreted as a byte offest"
			::= { msanShMCFruInfoEntry 3 }


		-- 1.3.6.1.4.1.1332.1.1.5.3.33.32
		msanShMCBoardVariablesTable OBJECT-TYPE
			SYNTAX SEQUENCE OF MsanShMCBoardVariablesEntry
			MAX-ACCESS not-accessible
			STATUS current
			DESCRIPTION
				"A list of boards"
			::= { msanShMC 32 }


		-- 1.3.6.1.4.1.1332.1.1.5.3.33.32.1
		msanShMCBoardVariablesEntry OBJECT-TYPE
			SYNTAX MsanShMCBoardVariablesEntry
			MAX-ACCESS not-accessible
			STATUS current
			DESCRIPTION
				"An IPM Controller entry"
			INDEX { msanShMCBoardVariablesBoardBasicSlotNumber }
			::= { msanShMCBoardVariablesTable 1 }


		MsanShMCBoardVariablesEntry ::=
			SEQUENCE {
				msanShMCBoardVariablesBoardBasicSlotNumber
					INTEGER,
				msanShMCBoardVariablesBoardBasicPresent
					INTEGER,
				msanShMCBoardVariablesBoardBasicHealthy
					INTEGER,
				msanShMCBoardVariablesBoardBasicReset
					INTEGER,
				msanShMCBoardVariablesBoardBasicPowered
					INTEGER,
				msanShMCBoardVariablesBoardBasicSlaveAddress
					INTEGER,
				msanShMCBoardVariablesBoardBasicFruDeviceId
					INTEGER,
				msanShMCBoardVariablesBoardBasicFruinfoProductAreaPresent
					INTEGER,
				msanShMCBoardVariablesBoardBasicProductManufacturer
					DisplayString,
				msanShMCBoardVariablesBoardBasicProductName
					DisplayString,
				msanShMCBoardVariablesBoardBasicProductPartModelNumber
					DisplayString,
				msanShMCBoardVariablesBoardBasicProductVersionNumber
					DisplayString,
				msanShMCBoardVariablesBoardBasicProductSerialNumber
					DisplayString,
				msanShMCBoardVariablesBoardBasicBoardAreaPresent
					INTEGER,
				msanShMCBoardVariablesBoardBasicBoardManufacturer
					DisplayString,
				msanShMCBoardVariablesBoardBasicBoardProductName
					DisplayString,
				msanShMCBoardVariablesBoardBasicBoardSerialNumber
					DisplayString,
				msanShMCBoardVariablesBoardBasicBoardPartNumber
					DisplayString,
				msanShMCBoardVariablesBoardBasicBoardManufactureTime
					Integer32,
				msanShMCBoardVariablesSelectivePowerOffSwitchOffType
					INTEGER
			 }

		-- 1.3.6.1.4.1.1332.1.1.5.3.33.32.1.1
		msanShMCBoardVariablesBoardBasicSlotNumber OBJECT-TYPE
			SYNTAX INTEGER (0..255)
			MAX-ACCESS read-only
			STATUS current
			DESCRIPTION
				"Table index equal to <boardnum>"
			::= { msanShMCBoardVariablesEntry 1 }


		-- 1.3.6.1.4.1.1332.1.1.5.3.33.32.1.2
		msanShMCBoardVariablesBoardBasicPresent OBJECT-TYPE
			SYNTAX INTEGER
				{
				absent(0),
				present(1)
				}
			MAX-ACCESS read-only
			STATUS current
			DESCRIPTION
				"0 - Board is absent
				1 - Board is present"
			::= { msanShMCBoardVariablesEntry 2 }


		-- 1.3.6.1.4.1.1332.1.1.5.3.33.32.1.3
		msanShMCBoardVariablesBoardBasicHealthy OBJECT-TYPE
			SYNTAX INTEGER
				{
				off(0),
				on(1)
				}
			MAX-ACCESS read-only
			STATUS current
			DESCRIPTION
				"Causes the BMC to return a high level version of the system health status in integer.
				The BMC returns an integer with the following values:
				     0 - off
				     1 - on"
			::= { msanShMCBoardVariablesEntry 3 }


		-- 1.3.6.1.4.1.1332.1.1.5.3.33.32.1.4
		msanShMCBoardVariablesBoardBasicReset OBJECT-TYPE
			SYNTAX INTEGER
				{
				none(0),
				cold(1)
				}
			MAX-ACCESS read-write
			STATUS current
			DESCRIPTION
				"on read:     1   - board is in reset state
				0   - otherwise
				on write:    0   - do nothing
				1   - perform COLD reset"
			::= { msanShMCBoardVariablesEntry 4 }


		-- 1.3.6.1.4.1.1332.1.1.5.3.33.32.1.5
		msanShMCBoardVariablesBoardBasicPowered OBJECT-TYPE
			SYNTAX INTEGER
				{
				none(0),
				powered(1)
				}
			MAX-ACCESS read-only
			STATUS current
			DESCRIPTION
				"on read:     1   - board is powered
				0   - otherwise"
			::= { msanShMCBoardVariablesEntry 5 }


		-- 1.3.6.1.4.1.1332.1.1.5.3.33.32.1.6
		msanShMCBoardVariablesBoardBasicSlaveAddress OBJECT-TYPE
			SYNTAX INTEGER (0..255)
			MAX-ACCESS read-only
			STATUS current
			DESCRIPTION
				"The on board IPMI controller 7-bit I2C addresses for IPMB messages"
			::= { msanShMCBoardVariablesEntry 6 }


		-- 1.3.6.1.4.1.1332.1.1.5.3.33.32.1.7
		msanShMCBoardVariablesBoardBasicFruDeviceId OBJECT-TYPE
			SYNTAX INTEGER (0..255)
			MAX-ACCESS read-only
			STATUS current
			DESCRIPTION
				"FRU Device ID field is used to identify individual FRU devices
				on the given LUN in the management controller. Up to 255 FRU
				devices can be located on a given LUN. FRU Device ID #00 at
				LUN 00b is predefined as being the FRU Device for the FRU that
				the management controller is located on. Since there are four
				possible LUNs for a management controller, this means up to
				255*4 FRU devices can be supported behind a single management
				controller using this mechanism. The Read/Write FRU Device
				commands provide an abstracted interface that hides the
				technology used to implement the FRU device from system software."
			::= { msanShMCBoardVariablesEntry 7 }


		-- 1.3.6.1.4.1.1332.1.1.5.3.33.32.1.8
		msanShMCBoardVariablesBoardBasicFruinfoProductAreaPresent OBJECT-TYPE
			SYNTAX INTEGER
				{
				no(0),
				yes(1)
				}
			MAX-ACCESS read-only
			STATUS current
			DESCRIPTION
				"1 - if product area is present
				0 - otherwise"
			::= { msanShMCBoardVariablesEntry 8 }


		-- 1.3.6.1.4.1.1332.1.1.5.3.33.32.1.9
		msanShMCBoardVariablesBoardBasicProductManufacturer OBJECT-TYPE
			SYNTAX DisplayString (SIZE (0..255))
			MAX-ACCESS read-only
			STATUS current
			DESCRIPTION
				"Returns the product manufacturer from the board FRU information or N/A"
			::= { msanShMCBoardVariablesEntry 9 }


		-- 1.3.6.1.4.1.1332.1.1.5.3.33.32.1.10
		msanShMCBoardVariablesBoardBasicProductName OBJECT-TYPE
			SYNTAX DisplayString (SIZE (0..255))
			MAX-ACCESS read-only
			STATUS current
			DESCRIPTION
				"Returns the product name from the board FRU information or N/A"
			::= { msanShMCBoardVariablesEntry 10 }


		-- 1.3.6.1.4.1.1332.1.1.5.3.33.32.1.11
		msanShMCBoardVariablesBoardBasicProductPartModelNumber OBJECT-TYPE
			SYNTAX DisplayString (SIZE (0..255))
			MAX-ACCESS read-only
			STATUS current
			DESCRIPTION
				"Returns the product part model from the board FRU information or N/A"
			::= { msanShMCBoardVariablesEntry 11 }


		-- 1.3.6.1.4.1.1332.1.1.5.3.33.32.1.12
		msanShMCBoardVariablesBoardBasicProductVersionNumber OBJECT-TYPE
			SYNTAX DisplayString (SIZE (0..255))
			MAX-ACCESS read-only
			STATUS current
			DESCRIPTION
				"Returns the product version number from the board FRU information or N/A"
			::= { msanShMCBoardVariablesEntry 12 }


		-- 1.3.6.1.4.1.1332.1.1.5.3.33.32.1.13
		msanShMCBoardVariablesBoardBasicProductSerialNumber OBJECT-TYPE
			SYNTAX DisplayString (SIZE (0..255))
			MAX-ACCESS read-only
			STATUS current
			DESCRIPTION
				"Returns the product serial number from the board FRU information or N/A"
			::= { msanShMCBoardVariablesEntry 13 }


		-- 1.3.6.1.4.1.1332.1.1.5.3.33.32.1.14
		msanShMCBoardVariablesBoardBasicBoardAreaPresent OBJECT-TYPE
			SYNTAX INTEGER
				{
				no(0),
				yes(1)
				}
			MAX-ACCESS read-only
			STATUS current
			DESCRIPTION
				"1 - if board area is present
				0 - otherwise"
			::= { msanShMCBoardVariablesEntry 14 }


		-- 1.3.6.1.4.1.1332.1.1.5.3.33.32.1.15
		msanShMCBoardVariablesBoardBasicBoardManufacturer OBJECT-TYPE
			SYNTAX DisplayString (SIZE (0..255))
			MAX-ACCESS read-only
			STATUS current
			DESCRIPTION
				"Returns the board manufacturer from the board FRU information or N/A"
			::= { msanShMCBoardVariablesEntry 15 }


		-- 1.3.6.1.4.1.1332.1.1.5.3.33.32.1.16
		msanShMCBoardVariablesBoardBasicBoardProductName OBJECT-TYPE
			SYNTAX DisplayString (SIZE (0..255))
			MAX-ACCESS read-only
			STATUS current
			DESCRIPTION
				"Returns the board product name from the board FRU information or N/A"
			::= { msanShMCBoardVariablesEntry 16 }


		-- 1.3.6.1.4.1.1332.1.1.5.3.33.32.1.17
		msanShMCBoardVariablesBoardBasicBoardSerialNumber OBJECT-TYPE
			SYNTAX DisplayString (SIZE (0..255))
			MAX-ACCESS read-only
			STATUS current
			DESCRIPTION
				"Returns the board serial number from the board FRU information or N/A"
			::= { msanShMCBoardVariablesEntry 17 }


		-- 1.3.6.1.4.1.1332.1.1.5.3.33.32.1.18
		msanShMCBoardVariablesBoardBasicBoardPartNumber OBJECT-TYPE
			SYNTAX DisplayString (SIZE (0..255))
			MAX-ACCESS read-only
			STATUS current
			DESCRIPTION
				"Returns the board part number from the board FRU information or N/A"
			::= { msanShMCBoardVariablesEntry 18 }


		-- 1.3.6.1.4.1.1332.1.1.5.3.33.32.1.19
		msanShMCBoardVariablesBoardBasicBoardManufactureTime OBJECT-TYPE
			SYNTAX Integer32 (0..2147483647)
			MAX-ACCESS read-only
			STATUS current
			DESCRIPTION
				"Returns the board manufacturing time: the number of seconds since
				00:00:00, January 1, 1970, CoordinatedUnivarsal Time (UTC):
				-1 if the corresponding field is not present in the board FRu information."
			::= { msanShMCBoardVariablesEntry 19 }


		-- 1.3.6.1.4.1.1332.1.1.5.3.33.32.1.20
		msanShMCBoardVariablesSelectivePowerOffSwitchOffType OBJECT-TYPE
			SYNTAX INTEGER
				{
				automatic(1),
				switchOff(2),
				switchOn(3)
				}
			MAX-ACCESS read-write
			STATUS current
			DESCRIPTION
				"Selective_Power_Off switch off type per board."
			DEFVAL { automatic }
			::= { msanShMCBoardVariablesEntry 20 }


		-- 1.3.6.1.4.1.1332.1.1.5.3.33.33
		msanShMCFanTrayVariablesTable OBJECT-TYPE
			SYNTAX SEQUENCE OF MsanShMCFanTrayVariablesEntry
			MAX-ACCESS not-accessible
			STATUS current
			DESCRIPTION
				"A list of Fan Trays"
			::= { msanShMC 33 }


		-- 1.3.6.1.4.1.1332.1.1.5.3.33.33.1
		msanShMCFanTrayVariablesEntry OBJECT-TYPE
			SYNTAX MsanShMCFanTrayVariablesEntry
			MAX-ACCESS not-accessible
			STATUS current
			DESCRIPTION
				"An IPM Controller entry"
			INDEX { msanShMCFanTraySlotNumber }
			::= { msanShMCFanTrayVariablesTable 1 }


		MsanShMCFanTrayVariablesEntry ::=
			SEQUENCE {
				msanShMCFanTraySlotNumber
					INTEGER,
				msanShMCFanTrayPresent
					INTEGER,
				msanShMCFanTrayHealthy
					INTEGER,
				msanShMCFanTrayHealthLed
					INTEGER,
				msanShMCFanTraySlaveAddress
					INTEGER,
				msanShMCFanTrayFruDeviceId
					INTEGER,
				msanShMCFanTrayFruinfoProductAreaPresent
					INTEGER,
				msanShMCFanTrayFruinfoProductManufacturer
					DisplayString,
				msanShMCFanTrayFruinfoProductName
					DisplayString,
				msanShMCFanTrayFruinfoProductPartModelNumber
					DisplayString,
				msanShMCFanTrayFruinfoProductVersionNumber
					DisplayString,
				msanShMCFanTrayFruinfoProductSerialNumber
					DisplayString,
				msanShMCFanTrayFruinfoBoardAreaPresent
					INTEGER,
				msanShMCFanTrayFruinfoBoardManufacturer
					DisplayString,
				msanShMCFanTrayFruinfoBoardProductName
					DisplayString,
				msanShMCFanTrayFruinfoBoardSerialNumber
					DisplayString,
				msanShMCFanTrayFruinfoBoardPartNumber
					DisplayString,
				msanShMCFanTrayFruinfoBoardManufactureTime
					Integer32
			 }

		-- 1.3.6.1.4.1.1332.1.1.5.3.33.33.1.1
		msanShMCFanTraySlotNumber OBJECT-TYPE
			SYNTAX INTEGER (0..65535)
			MAX-ACCESS read-only
			STATUS current
			DESCRIPTION
				"Table index equal to <boardnum>,<Lun>,<Fru id><Sensor number>"
			::= { msanShMCFanTrayVariablesEntry 1 }


		-- 1.3.6.1.4.1.1332.1.1.5.3.33.33.1.2
		msanShMCFanTrayPresent OBJECT-TYPE
			SYNTAX INTEGER
				{
				absent(0),
				present(1)
				}
			MAX-ACCESS read-only
			STATUS current
			DESCRIPTION
				"0 - Board is absent
				1 - Board is present"
			::= { msanShMCFanTrayVariablesEntry 2 }


		-- 1.3.6.1.4.1.1332.1.1.5.3.33.33.1.3
		msanShMCFanTrayHealthy OBJECT-TYPE
			SYNTAX INTEGER
				{
				off(0),
				on(1)
				}
			MAX-ACCESS read-only
			STATUS current
			DESCRIPTION
				"Causes the BMC to return a high level version of the system health status in integer.
				The BMC returns an integer with the following values:
				     0 - off
				     1 - on"
			::= { msanShMCFanTrayVariablesEntry 3 }


		-- 1.3.6.1.4.1.1332.1.1.5.3.33.33.1.4
		msanShMCFanTrayHealthLed OBJECT-TYPE
			SYNTAX INTEGER
				{
				off(0),
				on(1)
				}
			MAX-ACCESS read-write
			STATUS current
			DESCRIPTION
				"on read:     1   - led is on
				0   - led is off
				on write:    0   - turn led off
				1   - turn led on"
			::= { msanShMCFanTrayVariablesEntry 4 }


		-- 1.3.6.1.4.1.1332.1.1.5.3.33.33.1.5
		msanShMCFanTraySlaveAddress OBJECT-TYPE
			SYNTAX INTEGER (0..255)
			MAX-ACCESS read-only
			STATUS current
			DESCRIPTION
				"The on board IPMI controller 7-bit I2C addresses for IPMB messages"
			::= { msanShMCFanTrayVariablesEntry 5 }


		-- 1.3.6.1.4.1.1332.1.1.5.3.33.33.1.6
		msanShMCFanTrayFruDeviceId OBJECT-TYPE
			SYNTAX INTEGER (0..255)
			MAX-ACCESS read-only
			STATUS current
			DESCRIPTION
				"FRU Device ID field is used to identify individual FRU devices
				on the given LUN in the management controller. Up to 255 FRU
				devices can be located on a given LUN. FRU Device ID #00 at
				LUN 00b is predefined as being the FRU Device for the FRU that
				the management controller is located on. Since there are four
				possible LUNs for a management controller, this means up to
				255*4 FRU devices can be supported behind a single management
				controller using this mechanism. The Read/Write FRU Device
				commands provide an abstracted interface that hides the
				technology used to implement the FRU device from system software."
			::= { msanShMCFanTrayVariablesEntry 6 }


		-- 1.3.6.1.4.1.1332.1.1.5.3.33.33.1.7
		msanShMCFanTrayFruinfoProductAreaPresent OBJECT-TYPE
			SYNTAX INTEGER
				{
				no(0),
				yes(1)
				}
			MAX-ACCESS read-only
			STATUS current
			DESCRIPTION
				"1 - if product area is present
				0 - otherwise"
			::= { msanShMCFanTrayVariablesEntry 7 }


		-- 1.3.6.1.4.1.1332.1.1.5.3.33.33.1.8
		msanShMCFanTrayFruinfoProductManufacturer OBJECT-TYPE
			SYNTAX DisplayString (SIZE (0..255))
			MAX-ACCESS read-only
			STATUS current
			DESCRIPTION
				"Returns the product manufacturer from the board FRU information or N/A"
			::= { msanShMCFanTrayVariablesEntry 8 }


		-- 1.3.6.1.4.1.1332.1.1.5.3.33.33.1.9
		msanShMCFanTrayFruinfoProductName OBJECT-TYPE
			SYNTAX DisplayString (SIZE (0..255))
			MAX-ACCESS read-only
			STATUS current
			DESCRIPTION
				"Returns the product name from the board FRU information or N/A"
			::= { msanShMCFanTrayVariablesEntry 9 }


		-- 1.3.6.1.4.1.1332.1.1.5.3.33.33.1.10
		msanShMCFanTrayFruinfoProductPartModelNumber OBJECT-TYPE
			SYNTAX DisplayString (SIZE (0..255))
			MAX-ACCESS read-only
			STATUS current
			DESCRIPTION
				"Returns the product part model from the board FRU information or N/A"
			::= { msanShMCFanTrayVariablesEntry 10 }


		-- 1.3.6.1.4.1.1332.1.1.5.3.33.33.1.11
		msanShMCFanTrayFruinfoProductVersionNumber OBJECT-TYPE
			SYNTAX DisplayString (SIZE (0..255))
			MAX-ACCESS read-only
			STATUS current
			DESCRIPTION
				"Returns the product version number from the board FRU information or N/A"
			::= { msanShMCFanTrayVariablesEntry 11 }


		-- 1.3.6.1.4.1.1332.1.1.5.3.33.33.1.12
		msanShMCFanTrayFruinfoProductSerialNumber OBJECT-TYPE
			SYNTAX DisplayString (SIZE (0..255))
			MAX-ACCESS read-only
			STATUS current
			DESCRIPTION
				"Returns the product serial number from the board FRU information or N/A"
			::= { msanShMCFanTrayVariablesEntry 12 }


		-- 1.3.6.1.4.1.1332.1.1.5.3.33.33.1.13
		msanShMCFanTrayFruinfoBoardAreaPresent OBJECT-TYPE
			SYNTAX INTEGER
				{
				no(0),
				yes(1)
				}
			MAX-ACCESS read-only
			STATUS current
			DESCRIPTION
				"1 - if board area is present
				0 - otherwise"
			::= { msanShMCFanTrayVariablesEntry 13 }


		-- 1.3.6.1.4.1.1332.1.1.5.3.33.33.1.14
		msanShMCFanTrayFruinfoBoardManufacturer OBJECT-TYPE
			SYNTAX DisplayString (SIZE (0..255))
			MAX-ACCESS read-only
			STATUS current
			DESCRIPTION
				"Returns the board manufacturer from the board FRU information or N/A"
			::= { msanShMCFanTrayVariablesEntry 14 }


		-- 1.3.6.1.4.1.1332.1.1.5.3.33.33.1.15
		msanShMCFanTrayFruinfoBoardProductName OBJECT-TYPE
			SYNTAX DisplayString (SIZE (0..255))
			MAX-ACCESS read-only
			STATUS current
			DESCRIPTION
				"Returns the board product name from the board FRU information or N/A"
			::= { msanShMCFanTrayVariablesEntry 15 }


		-- 1.3.6.1.4.1.1332.1.1.5.3.33.33.1.16
		msanShMCFanTrayFruinfoBoardSerialNumber OBJECT-TYPE
			SYNTAX DisplayString (SIZE (0..255))
			MAX-ACCESS read-only
			STATUS current
			DESCRIPTION
				"Returns the board serial number from the board FRU information or N/A"
			::= { msanShMCFanTrayVariablesEntry 16 }


		-- 1.3.6.1.4.1.1332.1.1.5.3.33.33.1.17
		msanShMCFanTrayFruinfoBoardPartNumber OBJECT-TYPE
			SYNTAX DisplayString (SIZE (0..255))
			MAX-ACCESS read-only
			STATUS current
			DESCRIPTION
				"Returns the board part number from the board FRU information or N/A"
			::= { msanShMCFanTrayVariablesEntry 17 }


		-- 1.3.6.1.4.1.1332.1.1.5.3.33.33.1.18
		msanShMCFanTrayFruinfoBoardManufactureTime OBJECT-TYPE
			SYNTAX Integer32 (0..2147483647)
			MAX-ACCESS read-only
			STATUS current
			DESCRIPTION
				"Returns the board manufacturing time: the number of seconds since
				00:00:00, January 1, 1970, CoordinatedUnivarsal Time (UTC):
				-1 if the corresponding field is not present in the board FRu information."
			::= { msanShMCFanTrayVariablesEntry 18 }


		-- 1.3.6.1.4.1.1332.1.1.5.3.33.34
		msanShMCPowerSupplyVariablesTable OBJECT-TYPE
			SYNTAX SEQUENCE OF MsanShMCPowerSupplyVariablesEntry
			MAX-ACCESS not-accessible
			STATUS current
			DESCRIPTION
				"A list of Power Supplys"
			::= { msanShMC 34 }


		-- 1.3.6.1.4.1.1332.1.1.5.3.33.34.1
		msanShMCPowerSupplyVariablesEntry OBJECT-TYPE
			SYNTAX MsanShMCPowerSupplyVariablesEntry
			MAX-ACCESS not-accessible
			STATUS current
			DESCRIPTION
				"An IPM Controller entry"
			INDEX { msanShMCPowerSupplySlotNumber }
			::= { msanShMCPowerSupplyVariablesTable 1 }


		MsanShMCPowerSupplyVariablesEntry ::=
			SEQUENCE {
				msanShMCPowerSupplySlotNumber
					INTEGER,
				msanShMCPowerSupplyDegrade
					INTEGER,
				msanShMCPowerSupplyFail
					INTEGER,
				msanShMCPowerSupplyInhibit
					INTEGER,
				msanShMCPowerSupplyHealthy
					INTEGER,
				msanShMCPowerSupplySlaveAddress
					INTEGER,
				msanShMCPowerSupplyFruDeviceId
					INTEGER,
				msanShMCPowerSupplyFruinfoProductAreaPresent
					INTEGER,
				msanShMCPowerSupplyFruinfoProductManufacturer
					DisplayString,
				msanShMCPowerSupplyFruinfoProductName
					DisplayString,
				msanShMCPowerSupplyFruinfoProductPartModelNumber
					DisplayString,
				msanShMCPowerSupplyFruinfoProductVersionNumber
					DisplayString,
				msanShMCPowerSupplyFruinfoProductSerialNumber
					DisplayString,
				msanShMCPowerSupplyFruinfoBoardAreaPresent
					INTEGER,
				msanShMCPowerSupplyFruinfoBoardManufacturer
					DisplayString,
				msanShMCPowerSupplyFruinfoBoardProductName
					DisplayString,
				msanShMCPowerSupplyFruinfoBoardSerialNumber
					DisplayString,
				msanShMCPowerSupplyFruinfoBoardPartNumber
					DisplayString,
				msanShMCPowerSupplyFruinfoBoardmanufactureTime
					Integer32
			 }

		-- 1.3.6.1.4.1.1332.1.1.5.3.33.34.1.1
		msanShMCPowerSupplySlotNumber OBJECT-TYPE
			SYNTAX INTEGER (0..65535)
			MAX-ACCESS read-only
			STATUS current
			DESCRIPTION
				"Table index equal to <boardnum>,<Lun>,<Fru id><Sensor number>"
			::= { msanShMCPowerSupplyVariablesEntry 1 }


		-- 1.3.6.1.4.1.1332.1.1.5.3.33.34.1.2
		msanShMCPowerSupplyDegrade OBJECT-TYPE
			SYNTAX INTEGER
				{
				absent(0),
				present(1)
				}
			MAX-ACCESS read-only
			STATUS current
			DESCRIPTION
				"0 - Board is absent
				1 - Board is present"
			::= { msanShMCPowerSupplyVariablesEntry 2 }


		-- 1.3.6.1.4.1.1332.1.1.5.3.33.34.1.3
		msanShMCPowerSupplyFail OBJECT-TYPE
			SYNTAX INTEGER
				{
				off(0),
				on(1)
				}
			MAX-ACCESS read-only
			STATUS current
			DESCRIPTION
				"Causes the BMC to return a high level version of the system health status in integer.
				The BMC returns an integer with the following values:
				     0 - off
				     1 - on"
			::= { msanShMCPowerSupplyVariablesEntry 3 }


		-- 1.3.6.1.4.1.1332.1.1.5.3.33.34.1.4
		msanShMCPowerSupplyInhibit OBJECT-TYPE
			SYNTAX INTEGER
				{
				on(0),
				inhibit(1)
				}
			MAX-ACCESS read-write
			STATUS current
			DESCRIPTION
				"on read:     1   - if power supply is in the Inhibited state
				0   - otherwise
				on write:    1   - Inhibit power supply
				0   - Reenable power supply"
			::= { msanShMCPowerSupplyVariablesEntry 4 }


		-- 1.3.6.1.4.1.1332.1.1.5.3.33.34.1.5
		msanShMCPowerSupplyHealthy OBJECT-TYPE
			SYNTAX INTEGER
				{
				off(0),
				on(1)
				}
			MAX-ACCESS read-write
			STATUS current
			DESCRIPTION
				"Causes the BMC to return a high level version of the system health status in integer.
				The BMC returns an integer with the following values:
				     0 - off
				     1 - on"
			::= { msanShMCPowerSupplyVariablesEntry 5 }


		-- 1.3.6.1.4.1.1332.1.1.5.3.33.34.1.6
		msanShMCPowerSupplySlaveAddress OBJECT-TYPE
			SYNTAX INTEGER (0..255)
			MAX-ACCESS read-only
			STATUS current
			DESCRIPTION
				"The on board IPMI controller 7-bit I2C addresses for IPMB messages"
			::= { msanShMCPowerSupplyVariablesEntry 6 }


		-- 1.3.6.1.4.1.1332.1.1.5.3.33.34.1.7
		msanShMCPowerSupplyFruDeviceId OBJECT-TYPE
			SYNTAX INTEGER (0..255)
			MAX-ACCESS read-only
			STATUS current
			DESCRIPTION
				"FRU Device ID field is used to identify individual FRU devices
				on the given LUN in the management controller. Up to 255 FRU
				devices can be located on a given LUN. FRU Device ID #00 at
				LUN 00b is predefined as being the FRU Device for the FRU that
				the management controller is located on. Since there are four
				possible LUNs for a management controller, this means up to
				255*4 FRU devices can be supported behind a single management
				controller using this mechanism. The Read/Write FRU Device
				commands provide an abstracted interface that hides the
				technology used to implement the FRU device from system software."
			::= { msanShMCPowerSupplyVariablesEntry 7 }


		-- 1.3.6.1.4.1.1332.1.1.5.3.33.34.1.8
		msanShMCPowerSupplyFruinfoProductAreaPresent OBJECT-TYPE
			SYNTAX INTEGER
				{
				no(0),
				yes(1)
				}
			MAX-ACCESS read-only
			STATUS current
			DESCRIPTION
				"1 - if product area is present
				0 - otherwise"
			::= { msanShMCPowerSupplyVariablesEntry 8 }


		-- 1.3.6.1.4.1.1332.1.1.5.3.33.34.1.9
		msanShMCPowerSupplyFruinfoProductManufacturer OBJECT-TYPE
			SYNTAX DisplayString (SIZE (0..255))
			MAX-ACCESS read-only
			STATUS current
			DESCRIPTION
				"Returns the product manufacturer from the board FRU information or N/A"
			::= { msanShMCPowerSupplyVariablesEntry 9 }


		-- 1.3.6.1.4.1.1332.1.1.5.3.33.34.1.10
		msanShMCPowerSupplyFruinfoProductName OBJECT-TYPE
			SYNTAX DisplayString (SIZE (0..255))
			MAX-ACCESS read-only
			STATUS current
			DESCRIPTION
				"Returns the product name from the board FRU information or N/A"
			::= { msanShMCPowerSupplyVariablesEntry 10 }


		-- 1.3.6.1.4.1.1332.1.1.5.3.33.34.1.11
		msanShMCPowerSupplyFruinfoProductPartModelNumber OBJECT-TYPE
			SYNTAX DisplayString (SIZE (0..255))
			MAX-ACCESS read-only
			STATUS current
			DESCRIPTION
				"Returns the product part model from the board FRU information or N/A"
			::= { msanShMCPowerSupplyVariablesEntry 11 }


		-- 1.3.6.1.4.1.1332.1.1.5.3.33.34.1.12
		msanShMCPowerSupplyFruinfoProductVersionNumber OBJECT-TYPE
			SYNTAX DisplayString (SIZE (0..255))
			MAX-ACCESS read-only
			STATUS current
			DESCRIPTION
				"Returns the product version number from the board FRU information or N/A"
			::= { msanShMCPowerSupplyVariablesEntry 12 }


		-- 1.3.6.1.4.1.1332.1.1.5.3.33.34.1.13
		msanShMCPowerSupplyFruinfoProductSerialNumber OBJECT-TYPE
			SYNTAX DisplayString (SIZE (0..255))
			MAX-ACCESS read-only
			STATUS current
			DESCRIPTION
				"Returns the product serial number from the board FRU information or N/A"
			::= { msanShMCPowerSupplyVariablesEntry 13 }


		-- 1.3.6.1.4.1.1332.1.1.5.3.33.34.1.14
		msanShMCPowerSupplyFruinfoBoardAreaPresent OBJECT-TYPE
			SYNTAX INTEGER
				{
				no(0),
				yes(1)
				}
			MAX-ACCESS read-only
			STATUS current
			DESCRIPTION
				"1 - if board area is present
				0 - otherwise"
			::= { msanShMCPowerSupplyVariablesEntry 14 }


		-- 1.3.6.1.4.1.1332.1.1.5.3.33.34.1.15
		msanShMCPowerSupplyFruinfoBoardManufacturer OBJECT-TYPE
			SYNTAX DisplayString (SIZE (0..255))
			MAX-ACCESS read-only
			STATUS current
			DESCRIPTION
				"Returns the board manufacturer from the board FRU information or N/A"
			::= { msanShMCPowerSupplyVariablesEntry 15 }


		-- 1.3.6.1.4.1.1332.1.1.5.3.33.34.1.16
		msanShMCPowerSupplyFruinfoBoardProductName OBJECT-TYPE
			SYNTAX DisplayString (SIZE (0..255))
			MAX-ACCESS read-only
			STATUS current
			DESCRIPTION
				"Returns the board product name from the board FRU information or N/A"
			::= { msanShMCPowerSupplyVariablesEntry 16 }


		-- 1.3.6.1.4.1.1332.1.1.5.3.33.34.1.17
		msanShMCPowerSupplyFruinfoBoardSerialNumber OBJECT-TYPE
			SYNTAX DisplayString (SIZE (0..255))
			MAX-ACCESS read-only
			STATUS current
			DESCRIPTION
				"Returns the board serial number from the board FRU information or N/A"
			::= { msanShMCPowerSupplyVariablesEntry 17 }


		-- 1.3.6.1.4.1.1332.1.1.5.3.33.34.1.18
		msanShMCPowerSupplyFruinfoBoardPartNumber OBJECT-TYPE
			SYNTAX DisplayString (SIZE (0..255))
			MAX-ACCESS read-only
			STATUS current
			DESCRIPTION
				"Returns the board part number from the board FRU information or N/A"
			::= { msanShMCPowerSupplyVariablesEntry 18 }


		-- 1.3.6.1.4.1.1332.1.1.5.3.33.34.1.19
		msanShMCPowerSupplyFruinfoBoardmanufactureTime OBJECT-TYPE
			SYNTAX Integer32 (0..2147483647)
			MAX-ACCESS read-only
			STATUS current
			DESCRIPTION
				"Returns the board manufacturing time: the number of seconds since
				00:00:00, January 1, 1970, CoordinatedUnivarsal Time (UTC):
				-1 if the corresponding field is not present in the board FRu information."
			::= { msanShMCPowerSupplyVariablesEntry 19 }


		-- 1.3.6.1.4.1.1332.1.1.5.3.33.35
		msanShMCShelfManagerVariablesTable OBJECT-TYPE
			SYNTAX SEQUENCE OF MsanShMCShelfManagerVariablesEntry
			MAX-ACCESS not-accessible
			STATUS current
			DESCRIPTION
				"A list of Shelf Managers"
			::= { msanShMC 35 }


		-- 1.3.6.1.4.1.1332.1.1.5.3.33.35.1
		msanShMCShelfManagerVariablesEntry OBJECT-TYPE
			SYNTAX MsanShMCShelfManagerVariablesEntry
			MAX-ACCESS not-accessible
			STATUS current
			DESCRIPTION
				"An IPM Controller entry"
			INDEX { msanShMCShelfManagerSlotNumber }
			::= { msanShMCShelfManagerVariablesTable 1 }


		MsanShMCShelfManagerVariablesEntry ::=
			SEQUENCE {
				msanShMCShelfManagerSlotNumber
					INTEGER,
				msanShMCShelfManagerSlaveAddress
					INTEGER,
				msanShMCShelfManagerPresent
					INTEGER,
				msanShMCShelfManagerHealthy
					INTEGER,
				msanShMCShelfManagerActive
					INTEGER,
				msanShMCShelfManagerReset
					INTEGER,
				msanShMCShelfManagerFruinfoProductAreaPresent
					INTEGER,
				msanShMCShelfManagerFruinfoProductManufacturer
					DisplayString,
				msanShMCShelfManagerFruinfoProductName
					DisplayString,
				msanShMCShelfManagerFruinfoProductPartModelNumber
					DisplayString,
				msanShMCShelfManagerFruinfoProductVersionNumber
					DisplayString,
				msanShMCShelfManagerFruinfoProductSerialNumber
					DisplayString,
				msanShMCShelfManagerFruinfoBoardAreaPresent
					INTEGER,
				msanShMCShelfManagerFruinfoBoardManufacturer
					DisplayString,
				msanShMCShelfManagerFruinfoBoardProductName
					DisplayString,
				msanShMCShelfManagerFruinfoBoardSerialNumber
					DisplayString,
				msanShMCShelfManagerFruinfoBoardPartNumber
					DisplayString,
				msanShMCShelfManagerFruinfoBoardmanufactureTime
					Integer32
			 }

		-- 1.3.6.1.4.1.1332.1.1.5.3.33.35.1.1
		msanShMCShelfManagerSlotNumber OBJECT-TYPE
			SYNTAX INTEGER (0..65535)
			MAX-ACCESS read-only
			STATUS current
			DESCRIPTION
				"Table index equal to <boardnum>,<Lun>,<Fru id><Sensor number>"
			::= { msanShMCShelfManagerVariablesEntry 1 }


		-- 1.3.6.1.4.1.1332.1.1.5.3.33.35.1.2
		msanShMCShelfManagerSlaveAddress OBJECT-TYPE
			SYNTAX INTEGER (0..255)
			MAX-ACCESS read-only
			STATUS current
			DESCRIPTION
				"The on board IPMI controller 7-bit I2C addresses for IPMB messages"
			::= { msanShMCShelfManagerVariablesEntry 2 }


		-- 1.3.6.1.4.1.1332.1.1.5.3.33.35.1.3
		msanShMCShelfManagerPresent OBJECT-TYPE
			SYNTAX INTEGER
				{
				absent(0),
				present(1)
				}
			MAX-ACCESS read-only
			STATUS current
			DESCRIPTION
				"0 - Shelf manager is absent
				1 - Shelf manager is present"
			::= { msanShMCShelfManagerVariablesEntry 3 }


		-- 1.3.6.1.4.1.1332.1.1.5.3.33.35.1.4
		msanShMCShelfManagerHealthy OBJECT-TYPE
			SYNTAX INTEGER
				{
				off(0),
				on(1)
				}
			MAX-ACCESS read-only
			STATUS current
			DESCRIPTION
				"Causes the BMC to return a high level version of the system health status in integer.
				The BMC returns an integer with the following values:
				     0 - off
				     1 - on"
			::= { msanShMCShelfManagerVariablesEntry 4 }


		-- 1.3.6.1.4.1.1332.1.1.5.3.33.35.1.5
		msanShMCShelfManagerActive OBJECT-TYPE
			SYNTAX INTEGER
				{
				standby(0),
				active(1)
				}
			MAX-ACCESS read-write
			STATUS current
			DESCRIPTION
				"on read:     1     - Shelf manager is active
				0     - Shelf manager is in standby
				on write:    0     - initiate switchover
				other - no change"
			::= { msanShMCShelfManagerVariablesEntry 5 }


		-- 1.3.6.1.4.1.1332.1.1.5.3.33.35.1.6
		msanShMCShelfManagerReset OBJECT-TYPE
			SYNTAX INTEGER
				{
				none(0),
				cold(1)
				}
			MAX-ACCESS read-write
			STATUS current
			DESCRIPTION
				"on read:     1   - board is in reset state
				0   - otherwise
				on write:    0   - do nothing
				1   - perform COLD reset"
			::= { msanShMCShelfManagerVariablesEntry 6 }


		-- 1.3.6.1.4.1.1332.1.1.5.3.33.35.1.7
		msanShMCShelfManagerFruinfoProductAreaPresent OBJECT-TYPE
			SYNTAX INTEGER
				{
				no(0),
				yes(1)
				}
			MAX-ACCESS read-only
			STATUS current
			DESCRIPTION
				"1 - if product area is present
				0 - otherwise"
			::= { msanShMCShelfManagerVariablesEntry 7 }


		-- 1.3.6.1.4.1.1332.1.1.5.3.33.35.1.8
		msanShMCShelfManagerFruinfoProductManufacturer OBJECT-TYPE
			SYNTAX DisplayString (SIZE (0..255))
			MAX-ACCESS read-only
			STATUS current
			DESCRIPTION
				"Returns the product manufacturer from the board FRU information or N/A"
			::= { msanShMCShelfManagerVariablesEntry 8 }


		-- 1.3.6.1.4.1.1332.1.1.5.3.33.35.1.9
		msanShMCShelfManagerFruinfoProductName OBJECT-TYPE
			SYNTAX DisplayString (SIZE (0..255))
			MAX-ACCESS read-only
			STATUS current
			DESCRIPTION
				"Returns the product name from the board FRU information or N/A"
			::= { msanShMCShelfManagerVariablesEntry 9 }


		-- 1.3.6.1.4.1.1332.1.1.5.3.33.35.1.10
		msanShMCShelfManagerFruinfoProductPartModelNumber OBJECT-TYPE
			SYNTAX DisplayString (SIZE (0..255))
			MAX-ACCESS read-only
			STATUS current
			DESCRIPTION
				"Returns the product part model from the board FRU information or N/A"
			::= { msanShMCShelfManagerVariablesEntry 10 }


		-- 1.3.6.1.4.1.1332.1.1.5.3.33.35.1.11
		msanShMCShelfManagerFruinfoProductVersionNumber OBJECT-TYPE
			SYNTAX DisplayString (SIZE (0..255))
			MAX-ACCESS read-only
			STATUS current
			DESCRIPTION
				"Returns the product version number from the board FRU information or N/A"
			::= { msanShMCShelfManagerVariablesEntry 11 }


		-- 1.3.6.1.4.1.1332.1.1.5.3.33.35.1.12
		msanShMCShelfManagerFruinfoProductSerialNumber OBJECT-TYPE
			SYNTAX DisplayString (SIZE (0..255))
			MAX-ACCESS read-only
			STATUS current
			DESCRIPTION
				"Returns the product serial number from the board FRU information or N/A"
			::= { msanShMCShelfManagerVariablesEntry 12 }


		-- 1.3.6.1.4.1.1332.1.1.5.3.33.35.1.13
		msanShMCShelfManagerFruinfoBoardAreaPresent OBJECT-TYPE
			SYNTAX INTEGER
				{
				no(0),
				yes(1)
				}
			MAX-ACCESS read-only
			STATUS current
			DESCRIPTION
				"1 - if board area is present
				0 - otherwise"
			::= { msanShMCShelfManagerVariablesEntry 13 }


		-- 1.3.6.1.4.1.1332.1.1.5.3.33.35.1.14
		msanShMCShelfManagerFruinfoBoardManufacturer OBJECT-TYPE
			SYNTAX DisplayString (SIZE (0..255))
			MAX-ACCESS read-only
			STATUS current
			DESCRIPTION
				"Returns the board manufacturer from the board FRU information or N/A"
			::= { msanShMCShelfManagerVariablesEntry 14 }


		-- 1.3.6.1.4.1.1332.1.1.5.3.33.35.1.15
		msanShMCShelfManagerFruinfoBoardProductName OBJECT-TYPE
			SYNTAX DisplayString (SIZE (0..255))
			MAX-ACCESS read-only
			STATUS current
			DESCRIPTION
				"Returns the board product name from the board FRU information or N/A"
			::= { msanShMCShelfManagerVariablesEntry 15 }


		-- 1.3.6.1.4.1.1332.1.1.5.3.33.35.1.16
		msanShMCShelfManagerFruinfoBoardSerialNumber OBJECT-TYPE
			SYNTAX DisplayString (SIZE (0..255))
			MAX-ACCESS read-only
			STATUS current
			DESCRIPTION
				"Returns the board serial number from the board FRU information or N/A"
			::= { msanShMCShelfManagerVariablesEntry 16 }


		-- 1.3.6.1.4.1.1332.1.1.5.3.33.35.1.17
		msanShMCShelfManagerFruinfoBoardPartNumber OBJECT-TYPE
			SYNTAX DisplayString (SIZE (0..255))
			MAX-ACCESS read-only
			STATUS current
			DESCRIPTION
				"Returns the board part number from the board FRU information or N/A"
			::= { msanShMCShelfManagerVariablesEntry 17 }


		-- 1.3.6.1.4.1.1332.1.1.5.3.33.35.1.18
		msanShMCShelfManagerFruinfoBoardmanufactureTime OBJECT-TYPE
			SYNTAX Integer32 (0..2147483647)
			MAX-ACCESS read-only
			STATUS current
			DESCRIPTION
				"Returns the board manufacturing time: the number of seconds since
				00:00:00, January 1, 1970, CoordinatedUnivarsal Time (UTC):
				-1 if the corresponding field is not present in the board FRu information."
			::= { msanShMCShelfManagerVariablesEntry 18 }


		-- 1.3.6.1.4.1.1332.1.1.5.3.33.36
		msanShMCChassisVariablesTable OBJECT-TYPE
			SYNTAX SEQUENCE OF MsanShMCChassisVariablesEntry
			MAX-ACCESS not-accessible
			STATUS current
			DESCRIPTION
				"A Chassis report"
			::= { msanShMC 36 }


		-- 1.3.6.1.4.1.1332.1.1.5.3.33.36.1
		msanShMCChassisVariablesEntry OBJECT-TYPE
			SYNTAX MsanShMCChassisVariablesEntry
			MAX-ACCESS not-accessible
			STATUS current
			DESCRIPTION
				"An IPM Controller entry"
			INDEX { msanShMCChassisId }
			::= { msanShMCChassisVariablesTable 1 }


		MsanShMCChassisVariablesEntry ::=
			SEQUENCE {
				msanShMCChassisId
					INTEGER,
				msanShMCChassisType
					INTEGER,
				msanShMCChassisPartNumber
					DisplayString,
				msanShMCChassisSerialNumber
					DisplayString,
				msanShMCChassisProductAreaPresent
					INTEGER,
				msanShMCChassisProductManufacturer
					DisplayString,
				msanShMCChassisProductName
					DisplayString,
				msanShMCChassisProductPartModelNumber
					DisplayString,
				msanShMCChassisProductVersionNumber
					DisplayString,
				msanShMCChassisProductSerialNumber
					DisplayString,
				msanShMCChassisBoardAreaPresent
					INTEGER,
				msanShMCChassisBoardManufacturer
					DisplayString,
				msanShMCChassisBoardProductName
					DisplayString,
				msanShMCChassisBoardSerialNumber
					DisplayString,
				msanShMCChassisBoardPartNumber
					DisplayString,
				msanShMCChassisBoardmanufactureTime
					Integer32
			 }

		-- 1.3.6.1.4.1.1332.1.1.5.3.33.36.1.1
		msanShMCChassisId OBJECT-TYPE
			SYNTAX INTEGER (0..255)
			MAX-ACCESS read-only
			STATUS current
			DESCRIPTION
				"Shelf Address"
			::= { msanShMCChassisVariablesEntry 1 }


		-- 1.3.6.1.4.1.1332.1.1.5.3.33.36.1.2
		msanShMCChassisType OBJECT-TYPE
			SYNTAX INTEGER (0..255)
			MAX-ACCESS read-only
			STATUS current
			DESCRIPTION
				"The 8 bit Chassis type from the Shelf FRU Information"
			::= { msanShMCChassisVariablesEntry 2 }


		-- 1.3.6.1.4.1.1332.1.1.5.3.33.36.1.3
		msanShMCChassisPartNumber OBJECT-TYPE
			SYNTAX DisplayString (SIZE (0..255))
			MAX-ACCESS read-only
			STATUS current
			DESCRIPTION
				"Chassis Part Number from the Shelf FRU Information"
			::= { msanShMCChassisVariablesEntry 3 }


		-- 1.3.6.1.4.1.1332.1.1.5.3.33.36.1.4
		msanShMCChassisSerialNumber OBJECT-TYPE
			SYNTAX DisplayString (SIZE (0..255))
			MAX-ACCESS read-only
			STATUS current
			DESCRIPTION
				"Chassis Serial Number from the Shelf FRU Information"
			::= { msanShMCChassisVariablesEntry 4 }


		-- 1.3.6.1.4.1.1332.1.1.5.3.33.36.1.5
		msanShMCChassisProductAreaPresent OBJECT-TYPE
			SYNTAX INTEGER
				{
				no(0),
				yes(1)
				}
			MAX-ACCESS read-only
			STATUS current
			DESCRIPTION
				"1 - if product area is present
				0 - otherwise"
			::= { msanShMCChassisVariablesEntry 5 }


		-- 1.3.6.1.4.1.1332.1.1.5.3.33.36.1.6
		msanShMCChassisProductManufacturer OBJECT-TYPE
			SYNTAX DisplayString (SIZE (0..255))
			MAX-ACCESS read-only
			STATUS current
			DESCRIPTION
				"Returns the product manufacturer from the board FRU information or N/A"
			::= { msanShMCChassisVariablesEntry 6 }


		-- 1.3.6.1.4.1.1332.1.1.5.3.33.36.1.7
		msanShMCChassisProductName OBJECT-TYPE
			SYNTAX DisplayString (SIZE (0..255))
			MAX-ACCESS read-only
			STATUS current
			DESCRIPTION
				"Returns the product name from the board FRU information or N/A"
			::= { msanShMCChassisVariablesEntry 7 }


		-- 1.3.6.1.4.1.1332.1.1.5.3.33.36.1.8
		msanShMCChassisProductPartModelNumber OBJECT-TYPE
			SYNTAX DisplayString (SIZE (0..255))
			MAX-ACCESS read-only
			STATUS current
			DESCRIPTION
				"Returns the product part model from the board FRU information or N/A"
			::= { msanShMCChassisVariablesEntry 8 }


		-- 1.3.6.1.4.1.1332.1.1.5.3.33.36.1.9
		msanShMCChassisProductVersionNumber OBJECT-TYPE
			SYNTAX DisplayString (SIZE (0..255))
			MAX-ACCESS read-only
			STATUS current
			DESCRIPTION
				"Returns the product version number from the board FRU information or N/A"
			::= { msanShMCChassisVariablesEntry 9 }


		-- 1.3.6.1.4.1.1332.1.1.5.3.33.36.1.10
		msanShMCChassisProductSerialNumber OBJECT-TYPE
			SYNTAX DisplayString (SIZE (0..255))
			MAX-ACCESS read-only
			STATUS current
			DESCRIPTION
				"Returns the product serial number from the board FRU information or N/A"
			::= { msanShMCChassisVariablesEntry 10 }


		-- 1.3.6.1.4.1.1332.1.1.5.3.33.36.1.11
		msanShMCChassisBoardAreaPresent OBJECT-TYPE
			SYNTAX INTEGER
				{
				no(0),
				yes(1)
				}
			MAX-ACCESS read-only
			STATUS current
			DESCRIPTION
				"1 - if board area is present
				0 - otherwise"
			::= { msanShMCChassisVariablesEntry 11 }


		-- 1.3.6.1.4.1.1332.1.1.5.3.33.36.1.12
		msanShMCChassisBoardManufacturer OBJECT-TYPE
			SYNTAX DisplayString (SIZE (0..255))
			MAX-ACCESS read-only
			STATUS current
			DESCRIPTION
				"Returns the board manufacturer from the board FRU information or N/A"
			::= { msanShMCChassisVariablesEntry 12 }


		-- 1.3.6.1.4.1.1332.1.1.5.3.33.36.1.13
		msanShMCChassisBoardProductName OBJECT-TYPE
			SYNTAX DisplayString (SIZE (0..255))
			MAX-ACCESS read-only
			STATUS current
			DESCRIPTION
				"Returns the board product name from the board FRU information or N/A"
			::= { msanShMCChassisVariablesEntry 13 }


		-- 1.3.6.1.4.1.1332.1.1.5.3.33.36.1.14
		msanShMCChassisBoardSerialNumber OBJECT-TYPE
			SYNTAX DisplayString (SIZE (0..255))
			MAX-ACCESS read-only
			STATUS current
			DESCRIPTION
				"Returns the board serial number from the board FRU information or N/A"
			::= { msanShMCChassisVariablesEntry 14 }


		-- 1.3.6.1.4.1.1332.1.1.5.3.33.36.1.15
		msanShMCChassisBoardPartNumber OBJECT-TYPE
			SYNTAX DisplayString (SIZE (0..255))
			MAX-ACCESS read-only
			STATUS current
			DESCRIPTION
				"Returns the board part number from the board FRU information or N/A"
			::= { msanShMCChassisVariablesEntry 15 }


		-- 1.3.6.1.4.1.1332.1.1.5.3.33.36.1.16
		msanShMCChassisBoardmanufactureTime OBJECT-TYPE
			SYNTAX Integer32 (0..2147483647)
			MAX-ACCESS read-only
			STATUS current
			DESCRIPTION
				"Returns the board manufacturing time: the number of seconds since
				00:00:00, January 1, 1970, CoordinatedUnivarsal Time (UTC):
				-1 if the corresponding field is not present in the board FRu information."
			::= { msanShMCChassisVariablesEntry 16 }


		-- 1.3.6.1.4.1.1332.1.1.5.3.33.37
		msanShMCEventVariablesTable OBJECT-TYPE
			SYNTAX SEQUENCE OF MsanShMCEventVariablesEntry
			MAX-ACCESS not-accessible
			STATUS current
			DESCRIPTION
				"A Event report"
			::= { msanShMC 37 }


		-- 1.3.6.1.4.1.1332.1.1.5.3.33.37.1
		msanShMCEventVariablesEntry OBJECT-TYPE
			SYNTAX MsanShMCEventVariablesEntry
			MAX-ACCESS not-accessible
			STATUS current
			DESCRIPTION
				"An IPM Controller entry"
			INDEX { msanShMCEventIndex }
			::= { msanShMCEventVariablesTable 1 }


		MsanShMCEventVariablesEntry ::=
			SEQUENCE {
				msanShMCEventIndex
					INTEGER,
				msanShMCEventDelete
					INTEGER,
				msanShMCEventTimeStamp
					Integer32,
				msanShMCEventClass
					INTEGER,
				msanShMCEventType
					INTEGER,
				msanShMCEventAsserted
					INTEGER,
				msanShMCEventOriginSiteType
					INTEGER,
				msanShMCEventOriginSiteNumber
					INTEGER,
				msanShMCEventOriginSlaveAddress
					INTEGER,
				msanShMCEventOriginFruId
					INTEGER,
				msanShMCEventOriginSensorNumber
					INTEGER
			 }

		-- 1.3.6.1.4.1.1332.1.1.5.3.33.37.1.1
		msanShMCEventIndex OBJECT-TYPE
			SYNTAX INTEGER (0..255)
			MAX-ACCESS read-only
			STATUS current
			DESCRIPTION
				"Table entry index, equal to <selentrynum>"
			::= { msanShMCEventVariablesEntry 1 }


		-- 1.3.6.1.4.1.1332.1.1.5.3.33.37.1.2
		msanShMCEventDelete OBJECT-TYPE
			SYNTAX INTEGER (0..255)
			MAX-ACCESS read-write
			STATUS current
			DESCRIPTION
				"returns 0 on reading, Writing 1 causes the current SEL entry to be deleted"
			::= { msanShMCEventVariablesEntry 2 }


		-- 1.3.6.1.4.1.1332.1.1.5.3.33.37.1.3
		msanShMCEventTimeStamp OBJECT-TYPE
			SYNTAX Integer32 (0..2147483647)
			MAX-ACCESS read-only
			STATUS current
			DESCRIPTION
				"Returns the board manufacturing time: the number of seconds since
				00:00:00, January 1, 1970, CoordinatedUnivarsal Time (UTC):
				-1 if the corresponding field is not present in the board FRu information."
			::= { msanShMCEventVariablesEntry 3 }


		-- 1.3.6.1.4.1.1332.1.1.5.3.33.37.1.4
		msanShMCEventClass OBJECT-TYPE
			SYNTAX INTEGER
				{
				other(0),
				temperature(1),
				voltage(2),
				current(3),
				fan(4),
				powerstate(225),
				hotswap(240)
				}
			MAX-ACCESS read-only
			STATUS current
			DESCRIPTION
				"Event class"
			::= { msanShMCEventVariablesEntry 4 }


		-- 1.3.6.1.4.1.1332.1.1.5.3.33.37.1.5
		msanShMCEventType OBJECT-TYPE
			SYNTAX INTEGER
				{
				other(0),
				aboveUpperNonRecoverable(1),
				aboveUpperCritical(2),
				aboveUpperNonCritical(3),
				belowLowerNonrecoverable(4),
				belowLowerCritical(5),
				belowLowerNonCritical(6),
				inserted(7),
				activated(8),
				communicationLost(9),
				communicationRestored(10),
				deactivated(11),
				extracted(12),
				powerDegrade(13),
				powerFail(14),
				powerInhibit(15)
				}
			MAX-ACCESS read-only
			STATUS current
			DESCRIPTION
				"Event type"
			::= { msanShMCEventVariablesEntry 5 }


		-- 1.3.6.1.4.1.1332.1.1.5.3.33.37.1.6
		msanShMCEventAsserted OBJECT-TYPE
			SYNTAX INTEGER
				{
				deasserted(0),
				asserted(1)
				}
			MAX-ACCESS read-only
			STATUS current
			DESCRIPTION
				"Event type"
			::= { msanShMCEventVariablesEntry 6 }


		-- 1.3.6.1.4.1.1332.1.1.5.3.33.37.1.7
		msanShMCEventOriginSiteType OBJECT-TYPE
			SYNTAX INTEGER (0..255)
			MAX-ACCESS read-only
			STATUS current
			DESCRIPTION
				"Origin Site Type"
			::= { msanShMCEventVariablesEntry 7 }


		-- 1.3.6.1.4.1.1332.1.1.5.3.33.37.1.8
		msanShMCEventOriginSiteNumber OBJECT-TYPE
			SYNTAX INTEGER (0..255)
			MAX-ACCESS read-only
			STATUS current
			DESCRIPTION
				"Origin Site Number"
			::= { msanShMCEventVariablesEntry 8 }


		-- 1.3.6.1.4.1.1332.1.1.5.3.33.37.1.9
		msanShMCEventOriginSlaveAddress OBJECT-TYPE
			SYNTAX INTEGER (0..255)
			MAX-ACCESS read-only
			STATUS current
			DESCRIPTION
				"Origin Slave Address"
			::= { msanShMCEventVariablesEntry 9 }


		-- 1.3.6.1.4.1.1332.1.1.5.3.33.37.1.10
		msanShMCEventOriginFruId OBJECT-TYPE
			SYNTAX INTEGER (0..255)
			MAX-ACCESS read-only
			STATUS current
			DESCRIPTION
				"Origin FRU ID"
			::= { msanShMCEventVariablesEntry 10 }


		-- 1.3.6.1.4.1.1332.1.1.5.3.33.37.1.11
		msanShMCEventOriginSensorNumber OBJECT-TYPE
			SYNTAX INTEGER (0..255)
			MAX-ACCESS read-only
			STATUS current
			DESCRIPTION
				"Origin Sensor Number"
			::= { msanShMCEventVariablesEntry 11 }


		-- 1.3.6.1.4.1.1332.1.1.5.3.33.38
		msanShMCGlobal OBJECT IDENTIFIER ::= { msanShMC 38 }


		-- 1.3.6.1.4.1.1332.1.1.5.3.33.38.1
		msanShMCSelectivePowerOffAdminMode OBJECT-TYPE
			SYNTAX INTEGER
				{
				enable(1),
				disable(2)
				}
			MAX-ACCESS read-write
			STATUS current
			DESCRIPTION
				"Selective_Power_Off power off delay."
			DEFVAL { disable }
			::= { msanShMCGlobal 1 }


		-- 1.3.6.1.4.1.1332.1.1.5.3.33.38.2
		msanSHMCSelectivePowerOffOffDelay OBJECT-TYPE
			SYNTAX INTEGER (1..10)
			UNITS "minutes"
			MAX-ACCESS read-write
			STATUS current
			DESCRIPTION
				"Selective_Power_Off power off delay."
			DEFVAL { 5 }
			::= { msanShMCGlobal 2 }


		-- 1.3.6.1.4.1.1332.1.1.5.3.33.38.3
		msanSHMCSelectivePowerOffOnDelay OBJECT-TYPE
			SYNTAX INTEGER (1..10)
			UNITS "minutes"
			MAX-ACCESS read-write
			STATUS current
			DESCRIPTION
				"Selective_Power_Off power on delay."
			DEFVAL { 1 }
			::= { msanShMCGlobal 3 }



	END

--
-- ISKRATEL-IPMI-MIB.mib
--
