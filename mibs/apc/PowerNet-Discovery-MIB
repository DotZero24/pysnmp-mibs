-- *************************************************************************
-- AMERICAN POWER CONVERSION PowerNet-MIB
-- *************************************************************************
-- Copyright (c) 2018 American Power Conversion, Inc.
-- PowerNet is a Trademark of American Power Conversion Corp.
--
-- Title: APC TOP LEVEL PowerNet MIB
--
-- Version : 4.2.6.X
--
-- Generated by script: tomib.awk
--
-- Input File: powernetPS.mib
--
-- Created: thursday April 11, 2018
--
-- Revision History: This is a section of the apcDiscovery section
--                    used for generating the Java code in Netbotz 5.1
-- *************************************************************************
PowerNet-Discovery-MIB DEFINITIONS ::= BEGIN

IMPORTS
   enterprises, IpAddress, Gauge, TimeTicks             FROM RFC1155-SMI
-- Exp Begin
   Integer32, Counter32, Gauge32                        FROM SNMPv2-SMI
-- Exp End

   OBJECT-TYPE                                          FROM RFC-1212
   TRAP-TYPE                                            FROM RFC-1215
   DisplayString                                        FROM SNMPv2-TC;

-- IMPORTS End
apc                            OBJECT IDENTIFIER ::=  { enterprises 318 }

products                       OBJECT IDENTIFIER ::=  { apc 1 }
apcmgmt                        OBJECT IDENTIFIER ::=  { apc 2 }

hardware                       OBJECT IDENTIFIER ::=  { products 1 }
software                       OBJECT IDENTIFIER ::=  { products 2 }
system                         OBJECT IDENTIFIER ::=  { products 3 }
experimental                   OBJECT IDENTIFIER ::=  { products 4 }
apcDiscovery                   OBJECT IDENTIFIER ::=  { experimental 2 }
apcTrapReceiver                OBJECT IDENTIFIER ::=  { experimental 4 }
-- Exp Begin


-- Exp Begin
-- the apcDiscovery group

apcDiscoveryInfoTableSize OBJECT-TYPE
   SYNTAX INTEGER
   ACCESS read-only
   STATUS mandatory
   DESCRIPTION
      "The number of APC devices discovered at this IP address."
   ::= { apcDiscovery 1 }

apcDiscoveryInfoTable OBJECT-TYPE
   SYNTAX SEQUENCE OF ApcDiscoveryInfoEntry
   ACCESS not-accessible
   STATUS mandatory
   DESCRIPTION
      "Allows for access to discovered device(s) at this IP.
       The number of entries is contained in the
       apcDiscoveryInfoTableSize OID."
   ::= { apcDiscovery 2 }

   apcDiscoveryInfoEntry OBJECT-TYPE
       SYNTAX ApcDiscoveryInfoEntry
       ACCESS not-accessible
       STATUS mandatory
       DESCRIPTION
          "The discovered device to query."
       INDEX  { apcDiscoveryInfoTableIndex}
       ::= { apcDiscoveryInfoTable 1 }

   ApcDiscoveryInfoEntry ::= SEQUENCE {
      apcDiscoveryInfoTableIndex            INTEGER,
      apcDiscoveryModel                     DisplayString,
      apcDiscoverySerialNumber              DisplayString,
      apcDiscoveryStatus                    INTEGER,
      apcDiscoveryLabelString               DisplayString,
      apcDiscoveryDeviceHierarchy           DisplayString,
      apcDiscoveryDeviceLocation            DisplayString,
      apcDiscoveryDeviceLocationMaxLength   INTEGER,
      apcDiscoveryDeviceName                DisplayString,
      apcDiscoveryDeviceNameMaxLength       INTEGER,
      apcDiscoveryDeviceInstance            INTEGER,
      apcDiscoveryDeviceParamsIndex         DisplayString,
      apcDiscoveryDdfXReference             INTEGER,
      apcDiscoveryDeviceStatusBlockId       DisplayString
   }

   apcDiscoveryInfoTableIndex OBJECT-TYPE
      SYNTAX INTEGER
      ACCESS read-only
      STATUS mandatory
      DESCRIPTION
         "The index to the discovered device table entry."
      ::= { apcDiscoveryInfoEntry 1 }

   apcDiscoveryModel OBJECT-TYPE
      SYNTAX DisplayString
      ACCESS read-only
      STATUS mandatory
      DESCRIPTION
      "The APC device generic model identifier."
      ::= { apcDiscoveryInfoEntry 2 }

   apcDiscoverySerialNumber OBJECT-TYPE
      SYNTAX DisplayString
      ACCESS read-only
      STATUS mandatory
      DESCRIPTION
         "Serial Number of the discovered device or sub-device. "
      ::= { apcDiscoveryInfoEntry 3 }

   apcDiscoveryStatus OBJECT-TYPE
      SYNTAX INTEGER  {
      unknown(1),
      deviceNormal(2),
      deviceWarning(3),
      deviceSevere(4),
      deviceLostCom(5)
   }
       ACCESS read-only
       STATUS mandatory
       DESCRIPTION
      "The status of the APC device.
       unknown(1) indicates the state is unknown.
       deviceNormal(2) indicates the device is functioning normally.
       deviceWarning(3) indicates the device has detected an abnormal condition.
       deviceSevere(4) indicates a condition requiring immediate attention.
       deviceLostCom(5) indicates that a sub-device is not mandatoryly communicating with the device."
   ::= { apcDiscoveryInfoEntry 4 }

   apcDiscoveryLabelString OBJECT-TYPE
      SYNTAX DisplayString
      ACCESS read-only
      STATUS mandatory
      DESCRIPTION
      "The label of the device to be presented in the ISX Manager discovery interface."
      ::= { apcDiscoveryInfoEntry 5 }

   apcDiscoveryDeviceHierarchy OBJECT-TYPE
      SYNTAX DisplayString
      ACCESS read-only
      STATUS mandatory
      DESCRIPTION
         "The relative position of the device:
              Primary (1) the main device (e.g. a UPS)
              Secondary (2) an additional device (e.g. Integrated Environmental Monitor)
              Subordinate (2.1) a dependent device (e.g. Temperature Sensor)"
      ::= { apcDiscoveryInfoEntry 6 }

   apcDiscoveryDeviceLocation OBJECT-TYPE
      SYNTAX DisplayString
      ACCESS read-write
      STATUS mandatory
      DESCRIPTION
         "The user-defined location of the device."
      ::= { apcDiscoveryInfoEntry 7 }

   apcDiscoveryDeviceLocationMaxLength OBJECT-TYPE
      SYNTAX INTEGER
      ACCESS read-only
      STATUS mandatory
      DESCRIPTION
         "The maximum length of the user-defined location of the device."
      ::= { apcDiscoveryInfoEntry 8 }

   apcDiscoveryDeviceName OBJECT-TYPE
      SYNTAX DisplayString
      ACCESS read-write
      STATUS mandatory
      DESCRIPTION
         "The user-defined name of the device."
      ::= { apcDiscoveryInfoEntry 9 }

   apcDiscoveryDeviceNameMaxLength OBJECT-TYPE
      SYNTAX INTEGER
      ACCESS read-only
      STATUS mandatory
      DESCRIPTION
         "The maximum length of the user-defined name of the device."
      ::= { apcDiscoveryInfoEntry 10 }

   apcDiscoveryDeviceInstance OBJECT-TYPE
      SYNTAX INTEGER
      ACCESS read-only
      STATUS mandatory
      DESCRIPTION
         "Unique instance identifier used to distinguish between devices of the same apcDiscoveryModel."
      ::= { apcDiscoveryInfoEntry 11 }

   apcDiscoveryDeviceParamsIndex OBJECT-TYPE
      SYNTAX DisplayString
      ACCESS read-only
      STATUS mandatory
      DESCRIPTION
         "Table reference/index used to access device parameter values."
      ::= { apcDiscoveryInfoEntry 12 }

   apcDiscoveryDdfXReference OBJECT-TYPE
      SYNTAX INTEGER
      ACCESS read-only
      STATUS mandatory
      DESCRIPTION
         "Cross reference identifier used to locate the DDF file specified in
           the apcDiscoveryDeviceDefTable table that is appropriate for this device."
      ::= { apcDiscoveryInfoEntry 13 }

   apcDiscoveryDeviceStatusBlockId OBJECT-TYPE
      SYNTAX DisplayString
      ACCESS read-only
      STATUS mandatory
      DESCRIPTION
         "The ID of the status block to display for this device."
      ::= { apcDiscoveryInfoEntry 14 }


apcDiscoveryDeviceFirmwareTableSize OBJECT-TYPE
   SYNTAX INTEGER
   ACCESS read-only
   STATUS mandatory
   DESCRIPTION
      "The number of firmware elements hosted at this APC device."
   ::= { apcDiscovery 3 }

apcDiscoveryDeviceFirmwareTable OBJECT-TYPE
   SYNTAX SEQUENCE OF ApcDiscoveryDeviceFirmwareEntry
   ACCESS not-accessible
   STATUS mandatory
   DESCRIPTION
      "Allows for access to firmware elements on this device.
       The number of entries is contained in the
       apcDiscoveryDeviceFirmwareTableSize OID."
   ::= { apcDiscovery 4 }

   apcDiscoveryDeviceFirmwareEntry OBJECT-TYPE
       SYNTAX ApcDiscoveryDeviceFirmwareEntry
       ACCESS not-accessible
       STATUS mandatory
       DESCRIPTION
          "The firmware element to query."
       INDEX  { apcDiscoveryDeviceFirmwareTableIndex}
       ::= { apcDiscoveryDeviceFirmwareTable 1 }

   ApcDiscoveryDeviceFirmwareEntry ::= SEQUENCE {
      apcDiscoveryDeviceFirmwareTableIndex INTEGER,
      apcDiscoveryDeviceSerialNumber       DisplayString,
      apcDiscoveryFirmwareName             DisplayString,
      apcDiscoveryFirmwareRevision         DisplayString
   }

   apcDiscoveryDeviceFirmwareTableIndex OBJECT-TYPE
      SYNTAX INTEGER
      ACCESS read-only
      STATUS mandatory
      DESCRIPTION
         "The index to the discovered device table entry."
      ::= { apcDiscoveryDeviceFirmwareEntry 1 }

   apcDiscoveryDeviceSerialNumber OBJECT-TYPE
      SYNTAX DisplayString
      ACCESS read-only
      STATUS mandatory
      DESCRIPTION
         "Serial Number of the device that has this firmware. "
      ::= { apcDiscoveryDeviceFirmwareEntry 2 }

   apcDiscoveryFirmwareName OBJECT-TYPE
      SYNTAX DisplayString
      ACCESS read-only
      STATUS mandatory
      DESCRIPTION
         "Firmware name for this firmware. "
      ::= { apcDiscoveryDeviceFirmwareEntry 3 }

   apcDiscoveryFirmwareRevision OBJECT-TYPE
      SYNTAX DisplayString
      ACCESS read-only
      STATUS mandatory
      DESCRIPTION
      "Revision of the firmware."
      ::= { apcDiscoveryDeviceFirmwareEntry 4 }

apcDiscoveryDeviceProtocolTableSize OBJECT-TYPE
   SYNTAX INTEGER
   ACCESS read-only
   STATUS mandatory
   DESCRIPTION
      "The number of protocols supported by this device."
   ::= { apcDiscovery 5 }

apcDiscoveryDeviceProtocolTable OBJECT-TYPE
   SYNTAX SEQUENCE OF ApcDiscoveryDeviceProtocolEntry
   ACCESS not-accessible
   STATUS mandatory
   DESCRIPTION
      "Allows for access to protocol entries on this device.
       Each entry represents a protocol that the device supports.
       The number of entries is contained in the
       apcDiscoveryDeviceProtocolTableSize OID."
   ::= { apcDiscovery 6 }

   apcDiscoveryDeviceProtocolEntry OBJECT-TYPE
       SYNTAX ApcDiscoveryDeviceProtocolEntry
       ACCESS not-accessible
       STATUS mandatory
       DESCRIPTION
          "The protocol element to query."
       INDEX  { apcDiscoveryDeviceProtocolTableIndex}
       ::= { apcDiscoveryDeviceProtocolTable 1 }

   ApcDiscoveryDeviceProtocolEntry ::= SEQUENCE {
      apcDiscoveryDeviceProtocolTableIndex INTEGER,
      apcDiscoveryProtocolNumber           INTEGER,
      apcDiscoveryProtocolVersion          DisplayString,
      apcDiscoveryProtocolPort             DisplayString,
      apcDiscoveryProtocolEnabledDisabled  INTEGER
   }

   apcDiscoveryDeviceProtocolTableIndex OBJECT-TYPE
      SYNTAX INTEGER
      ACCESS read-only
      STATUS mandatory
      DESCRIPTION
         "The index to the protocol table entry."
      ::= { apcDiscoveryDeviceProtocolEntry 1 }

   apcDiscoveryProtocolNumber OBJECT-TYPE
      SYNTAX INTEGER
      ACCESS read-only
      STATUS mandatory
      DESCRIPTION
         "Protocol Number.
          1-SNMP
          2-Telnet
          3-HTTP
          4-DCAL
          5-SDCAL (Secure DCAL)
          6-SSL
          7-SSH
          8-SCP
          9-NTP
          10-SMTP
          11-FTP Server
          12-TFTP Client
          13-BOOTP
          14-DHCP
          15-RADIUS
          16-ModBus"
      ::= { apcDiscoveryDeviceProtocolEntry 2 }

   apcDiscoveryProtocolVersion OBJECT-TYPE
      SYNTAX DisplayString
      ACCESS read-only
      STATUS mandatory
      DESCRIPTION
      "The version of the protocol."
      ::= { apcDiscoveryDeviceProtocolEntry 3 }

   apcDiscoveryProtocolPort OBJECT-TYPE
      SYNTAX DisplayString
      ACCESS read-only
      STATUS mandatory
      DESCRIPTION
       "Encoded port on which this protocol is being used."
      ::= { apcDiscoveryDeviceProtocolEntry 4 }

   apcDiscoveryProtocolEnabledDisabled OBJECT-TYPE
   SYNTAX INTEGER  {
      disabled(1),
      enabled(2)
   }
   ACCESS read-only
   STATUS mandatory
   DESCRIPTION
      "The enabled/disabled state of the protocol within this device .
       disabled(1) indicates the protocol is supported, but mandatoryly disabled.
       enabled(2) indicates the protocol is supported and enabled."
   ::= { apcDiscoveryDeviceProtocolEntry 5 }

-- the apc Essential Support additions

apcDiscoveryDeviceDefTableSize OBJECT-TYPE
   SYNTAX INTEGER
   ACCESS read-only
   STATUS mandatory
   DESCRIPTION
      "The number of DDF files available at this IP address."
   ::= { apcDiscovery 7 }

apcDiscoveryDeviceDefTable OBJECT-TYPE
   SYNTAX SEQUENCE OF ApcDiscoveryDeviceDefEntry
   ACCESS not-accessible
   STATUS mandatory
   DESCRIPTION
      "Allows for access to the device definition information for the
       discovered device(s) at this IP.
       The number of entries is contained in the
       apcDiscoveryDeviceDefTableSize OID."
   ::= { apcDiscovery 8 }

   apcDiscoveryDeviceDefEntry OBJECT-TYPE
       SYNTAX ApcDiscoveryDeviceDefEntry
       ACCESS not-accessible
       STATUS mandatory
       DESCRIPTION
          "The device description element for the device."
       INDEX  { apcDiscoveryDeviceDefTableIndex}
       ::= { apcDiscoveryDeviceDefTable 1 }

   ApcDiscoveryDeviceDefEntry ::= SEQUENCE {
      apcDiscoveryDeviceDefTableIndex        INTEGER,
      apcDiscoveryDeviceDefDeviceClass       DisplayString,
      apcDiscoveryDeviceDefDeviceType        DisplayString,
      apcDiscoveryDeviceDefDeviceFamily      DisplayString,
      apcDiscoveryDeviceDefDeviceVersion     DisplayString,
      apcDiscoveryDeviceDefDdfXReference     INTEGER
   }

   apcDiscoveryDeviceDefTableIndex OBJECT-TYPE
      SYNTAX INTEGER
      ACCESS read-only
      STATUS mandatory
      DESCRIPTION
         "The index to the device definition table entry."
      ::= { apcDiscoveryDeviceDefEntry 1 }

   apcDiscoveryDeviceDefDeviceClass OBJECT-TYPE
      SYNTAX DisplayString
      ACCESS read-only
      STATUS mandatory
      DESCRIPTION
         "String specifying the device class.  Class, Type, Family is used to identify the device
           described by this DDF file."
      ::= { apcDiscoveryDeviceDefEntry 2 }

   apcDiscoveryDeviceDefDeviceType OBJECT-TYPE
      SYNTAX DisplayString
      ACCESS read-only
      STATUS mandatory
      DESCRIPTION
         "String specifying the device type.  Class, Type, Family is used to
          identify the device described by this DDF file."
      ::= { apcDiscoveryDeviceDefEntry 3 }

   apcDiscoveryDeviceDefDeviceFamily OBJECT-TYPE
      SYNTAX DisplayString
      ACCESS read-only
      STATUS mandatory
      DESCRIPTION
         "String specifying the device family.  Class, Type, and Family are used
          to identify the device described by this DDF file."
      ::= { apcDiscoveryDeviceDefEntry 4 }

   apcDiscoveryDeviceDefDeviceVersion  OBJECT-TYPE
      SYNTAX DisplayString
      ACCESS read-only
      STATUS mandatory
      DESCRIPTION
         "A string value specifying the version of the DDF element
          to be used for this device."
      ::= { apcDiscoveryDeviceDefEntry 5 }

   apcDiscoveryDeviceDefDdfXReference OBJECT-TYPE
      SYNTAX INTEGER
      ACCESS read-only
      STATUS mandatory
      DESCRIPTION
         "Cross reference identifier used to locate the DDF file from the apcDiscoveryInfoTable table."
      ::= { apcDiscoveryDeviceDefEntry 6 }


apcDiscoveryDeviceAlarmStateChangeCount  OBJECT-TYPE
   SYNTAX INTEGER
   ACCESS read-only
   STATUS mandatory
   DESCRIPTION
      "The number of changes to the alarm state table.  This number starts at zero
       and increases by one for each change to the table."
   ::= { apcDiscovery 9 }

apcDiscoveryDeviceAlarmStateTableSize OBJECT-TYPE
   SYNTAX INTEGER
   ACCESS read-only
   STATUS mandatory
   DESCRIPTION
      "The number of elements in the alarm state table."
   ::= { apcDiscovery 10 }

apcDiscoveryDeviceAlarmStateTable OBJECT-TYPE
   SYNTAX SEQUENCE OF ApcDiscoveryDeviceAlarmStateEntry
   ACCESS not-accessible
   STATUS mandatory
   DESCRIPTION
      "Allows for access to alarm states reported by the devices at this IP address."
   ::= { apcDiscovery 11 }

   apcDiscoveryDeviceAlarmStateEntry OBJECT-TYPE
       SYNTAX ApcDiscoveryDeviceAlarmStateEntry
       ACCESS not-accessible
       STATUS mandatory
       DESCRIPTION
          "The condition entry."
       INDEX  { apcDiscoveryDeviceAlarmStateTableIndex}
       ::= { apcDiscoveryDeviceAlarmStateTable 1 }


   ApcDiscoveryDeviceAlarmStateEntry ::= SEQUENCE {
      apcDiscoveryDeviceAlarmStateTableIndex   INTEGER,
      apcDiscoveryDeviceAlarmStateSerialNumber DisplayString,
      apcDiscoveryDeviceAlarmStateCode         OCTET STRING,
      apcDiscoveryDeviceAlarmStateParam        OCTET STRING
   }

   apcDiscoveryDeviceAlarmStateTableIndex OBJECT-TYPE
      SYNTAX INTEGER
      ACCESS read-only
      STATUS mandatory
      DESCRIPTION
         "The index to the alarm state table entry."
      ::= { apcDiscoveryDeviceAlarmStateEntry 1 }

   apcDiscoveryDeviceAlarmStateSerialNumber OBJECT-TYPE
      SYNTAX DisplayString
      ACCESS read-only
      STATUS mandatory
      DESCRIPTION
         "Serial Number of the device that has the alarm state. "
      ::= { apcDiscoveryDeviceAlarmStateEntry 2 }

   apcDiscoveryDeviceAlarmStateCode OBJECT-TYPE
      SYNTAX OCTET STRING
      ACCESS read-only
      STATUS mandatory
      DESCRIPTION
         "Encoded data string representing mandatory device alarm state.
           The format of the 12-byte (012345678901) string is as follows:
           bytes 0-1  : 16-bit alarm code (byte 0 is actually deviceType, byte 1 is alarmType)
           bytes 2-3  : 16-bit device instance
           bytes 4-5  : 16-bit alarm instance
           byte    6  : 8-bits indicating
                         active        (bit  0),
                         severity      (bits 1-2),
                         signature     (bits 3-7)
           byte    7  : 8-bit transaction ID
           bytes 8-11 : 32-bits time alarm has been active"

      ::= { apcDiscoveryDeviceAlarmStateEntry 3 }

   apcDiscoveryDeviceAlarmStateParam OBJECT-TYPE
      SYNTAX OCTET STRING
      ACCESS read-only
      STATUS mandatory
      DESCRIPTION
         "Optional parameter or parameters associated with this
          alarm state. Parameters are encoded as a sequence of varbinds
          corresponding to values in the MIB."
      ::= { apcDiscoveryDeviceAlarmStateEntry 4 }

apcDiscoveryDeviceInfoChangeCount  OBJECT-TYPE

   SYNTAX INTEGER
   ACCESS read-only
   STATUS mandatory
   DESCRIPTION
      "The number of changes to the device info table.
       When a device is added or removed this count is
       incremented."
   ::= { apcDiscovery 12 }


-- the TrapReceiver group

apcTrapRecvTableSize OBJECT-TYPE
   SYNTAX INTEGER
   ACCESS read-only
   STATUS mandatory
   DESCRIPTION
      "The number of trap receivers in apcTrapRecvTable."
   ::= { apcTrapReceiver 1 }

apcTrapRecvTable OBJECT-TYPE
   SYNTAX SEQUENCE  OF  ApcTrapRecvEntry
   ACCESS not-accessible
   STATUS mandatory
   DESCRIPTION "Table of trap receivers."
   ::= { apcTrapReceiver 2 }

apcTrapRecvEntry OBJECT-TYPE
   SYNTAX ApcTrapRecvEntry
   ACCESS not-accessible
   STATUS mandatory
   DESCRIPTION "Trap receiver table."
   INDEX { apcTrapRecvIndex  }
   ::=  { apcTrapRecvTable 1 }

ApcTrapRecvEntry ::=  SEQUENCE {
   apcTrapRecvIndex    INTEGER,
   apcTrapRecvHost     DisplayString,
   apcTrapRecvType     INTEGER,
   apcTrapRecvUniqueId INTEGER
   }

apcTrapRecvIndex OBJECT-TYPE
   SYNTAX INTEGER
   ACCESS read-only
   STATUS mandatory
   DESCRIPTION "Trap receiver index."
   ::=  {  apcTrapRecvEntry 1  }

apcTrapRecvHost OBJECT-TYPE
   SYNTAX DisplayString (SIZE (0..64))
   ACCESS read-only
   STATUS mandatory
   DESCRIPTION "The host name of the manager."
   ::=  {  apcTrapRecvEntry 2  }

apcTrapRecvType OBJECT-TYPE
   SYNTAX INTEGER   {
        unknown (1),
        remove  (2),
        pcs     (3),
        isxm    (4)
   }
   ACCESS read-only
   STATUS mandatory
   DESCRIPTION "The type of manager."
   ::=  {  apcTrapRecvEntry 3  }

apcTrapRecvUniqueId OBJECT-TYPE
   SYNTAX INTEGER
   ACCESS read-only
   STATUS mandatory
   DESCRIPTION "Unique ID obtained from getting the apcTrapReceiverUniqueID OID."
   ::=  {  apcTrapRecvEntry 4  }

apcTrapRecvTableModify OBJECT-TYPE
   SYNTAX DisplayString (SIZE (0..100))
   ACCESS read-write
   STATUS mandatory
   DESCRIPTION "Allows the manager to modify the list of trap receivers... 'hostname, Value[, UniqueID]'"
   ::= { apcTrapReceiver 3 }

apcTrapReceiverUniqueID OBJECT-TYPE
   SYNTAX INTEGER
   ACCESS read-only
   STATUS mandatory
   DESCRIPTION "This OID returns a unique ID to be used to register for Traps."
   ::= { apcTrapReceiver 4 }

apcDiscoveryAlarmStateTableUpdate TRAP-TYPE
   ENTERPRISE apc
   VARIABLES { apcDiscoveryDeviceAlarmStateChangeCount }
   DESCRIPTION
      "INTERNAL: A Discovery Alarm State Table Update trap is sent
       when any data alarm state is added, removed, or its parameters
       are changed in the condition table.  This trap is
       only for machine-to-machine communication. "
   --#TYPE "APC X:"
   --#SUMMARY "."
   --#ARGUMENTS { }
   --#SEVERITY INFORMATIONAL
   --#TIMEINDEX 1
   --#HELP ""
   --#HELPTAG 0
   --#STATE OPERATIONAL
   ::= 1000

END
