--
-- NETBOTZ-FIVE-MIB       module definition
--
NetBotz50-MIB DEFINITIONS ::= BEGIN
   IMPORTS
       MODULE-IDENTITY, OBJECT-TYPE,NOTIFICATION-TYPE, enterprises, Counter32,Integer32         FROM SNMPv2-SMI
       TEXTUAL-CONVENTION, DisplayString, DateAndTime                                           FROM SNMPv2-TC
       NOTIFICATION-GROUP, OBJECT-GROUP                                                         FROM SNMPv2-CONF;

netBotz5-APC MODULE-IDENTITY
    LAST-UPDATED "202001310000Z"
    ORGANIZATION "Schneider Electric / APC"
    CONTACT-INFO
            "Postal: Schneider Electric / APC
                     800 Federal St
                     Andover MA 01810
                     US
             Contact: https://www.apc.com/us/en/support/"
   DESCRIPTION
            "NetBotz5-APC BotzWare MIB"
   REVISION     "201810170000Z" --  17 October 2018"
   DESCRIPTION  "for NetBotz 5"
   REVISION     "201901240000Z" --  24 January 2019"
   DESCRIPTION  "for NetBotz 5.1"
   REVISION     "201907170000Z" --  17 July 2019"
   DESCRIPTION  "for NetBotz 5.2"
   REVISION     "202001310000Z" --  31 January 2020"
   DESCRIPTION  "for NetBotz 5.3"
   ::= { enterprises 52674 500 1 }

netBotzAPC                          OBJECT IDENTIFIER ::= { enterprises 52674 }
netBotz5                            OBJECT IDENTIFIER ::= { netBotzAPC 500 }
netBotzTraps                        OBJECT IDENTIFIER ::= { netBotz5 10 }
netBotzTrapParms                    OBJECT IDENTIFIER ::= { netBotz5 11 }
netBotzProducts                     OBJECT IDENTIFIER ::= { netBotz5 20 }
netBotzSensorTraps                  OBJECT IDENTIFIER ::= { netBotzTraps 1 }
netBotzPodTraps                     OBJECT IDENTIFIER ::= { netBotzTraps 2 }
netBotzRpduTraps                    OBJECT IDENTIFIER ::= { netBotzTraps 3 }
netBotzUpsTraps                     OBJECT IDENTIFIER ::= { netBotzTraps 4 }
netBotzGenericTraps                 OBJECT IDENTIFIER ::= { netBotzTraps 5 }

netBotzTempSensorTraps              OBJECT IDENTIFIER ::= { netBotzSensorTraps 1 }
netBotzHumiditySensorTraps          OBJECT IDENTIFIER ::= { netBotzSensorTraps 2 }
netBotzDewPointSensorTraps          OBJECT IDENTIFIER ::= { netBotzSensorTraps 3 }
netBotzAirFlowSensorTraps           OBJECT IDENTIFIER ::= { netBotzSensorTraps 4 }
netBotzAmpDetectSensorTraps         OBJECT IDENTIFIER ::= { netBotzSensorTraps 5 }
netBotzDryContactSensorTraps        OBJECT IDENTIFIER ::= { netBotzSensorTraps 6 }
netBotzCameraMotionSensorTraps      OBJECT IDENTIFIER ::= { netBotzSensorTraps 7 }
netBotzDoorSensorTraps              OBJECT IDENTIFIER ::= { netBotzSensorTraps 8 }
netBotzWirelessStatusSensorTraps    OBJECT IDENTIFIER ::= { netBotzSensorTraps 9 }
netBotzOutputControlSensorTraps     OBJECT IDENTIFIER ::= { netBotzSensorTraps 10 }
netBotzLoopVoltageSensorTraps       OBJECT IDENTIFIER ::= { netBotzSensorTraps 11 }
netBotzSpotLeakSensorTraps          OBJECT IDENTIFIER ::= { netBotzSensorTraps 12 }
netBotzRopeLeakSensorTraps          OBJECT IDENTIFIER ::= { netBotzSensorTraps 13 }
netBotzRSSISensorTraps              OBJECT IDENTIFIER ::= { netBotzSensorTraps 14 }
netBotzBatterySensorTraps           OBJECT IDENTIFIER ::= { netBotzSensorTraps 15 }
netBotzOutletSensorTraps            OBJECT IDENTIFIER ::= { netBotzSensorTraps 16 }
netBotzBeaconTraps                  OBJECT IDENTIFIER ::= { netBotzSensorTraps 17 }
netBotzSmokeSensorTraps             OBJECT IDENTIFIER ::= { netBotzSensorTraps 18 }
netBotzVibrationSensorTraps         OBJECT IDENTIFIER ::= { netBotzSensorTraps 19 }
netBotzRackAccessTraps              OBJECT IDENTIFIER ::= { netBotzSensorTraps 20 }
netBotzTestTraps                    OBJECT IDENTIFIER ::= { netBotzSensorTraps 99 }
netBotzSensorPodTraps               OBJECT IDENTIFIER ::= { netBotzPodTraps 1 }
netBotzCameraTraps                  OBJECT IDENTIFIER ::= { netBotzPodTraps 2 }
netBotz4to20mAPodTraps              OBJECT IDENTIFIER ::= { netBotzPodTraps 3 }

netBotzPodPrefix                    OBJECT IDENTIFIER ::= { netBotzPodTraps 0 }
netBotzTempSensorPrefix             OBJECT IDENTIFIER ::= { netBotzTempSensorTraps 0 }
netBotzHumiditySensorPrefix         OBJECT IDENTIFIER ::= { netBotzHumiditySensorTraps 0 }
netBotzDewPointSensorPrefix         OBJECT IDENTIFIER ::= { netBotzDewPointSensorTraps 0 }
netBotzAirFlowSensorPrefix          OBJECT IDENTIFIER ::= { netBotzAirFlowSensorTraps 0 }
netBotzAmpDetectSensorPrefix        OBJECT IDENTIFIER ::= { netBotzAmpDetectSensorTraps 0 }
netBotzDryContactSensorPrefix       OBJECT IDENTIFIER ::= { netBotzDryContactSensorTraps 0 }
netBotzCameraMotionSensorPrefix     OBJECT IDENTIFIER ::= { netBotzCameraMotionSensorTraps 0 }
netBotzDoorSensorPrefix             OBJECT IDENTIFIER ::= { netBotzDoorSensorTraps 0 }
netBotzWirelessStatusSensorPrefix   OBJECT IDENTIFIER ::= { netBotzWirelessStatusSensorTraps 0 }
netBotzOutputControlSensorPrefix    OBJECT IDENTIFIER ::= { netBotzOutputControlSensorTraps 0 }
netBotzLoopVoltageSensorPrefix      OBJECT IDENTIFIER ::= { netBotzLoopVoltageSensorTraps 0 }
netBotzSpotLeakSensorPrefix         OBJECT IDENTIFIER ::= { netBotzSpotLeakSensorTraps 0 }
netBotzRopeLeakSensorPrefix         OBJECT IDENTIFIER ::= { netBotzRopeLeakSensorTraps 0 }
netBotzRSSISensorPrefix             OBJECT IDENTIFIER ::= { netBotzRSSISensorTraps 0 }
netBotzBatterySensorPrefix          OBJECT IDENTIFIER ::= { netBotzBatterySensorTraps 0 }
netBotzOutletSensorPrefix           OBJECT IDENTIFIER ::= { netBotzOutletSensorTraps 0 }
netBotzBeaconPrefix                 OBJECT IDENTIFIER ::= { netBotzBeaconTraps 0 }
netBotzSmokeSensorPrefix            OBJECT IDENTIFIER ::= { netBotzSmokeSensorTraps 0 }
netBotzVibrationSensorPrefix        OBJECT IDENTIFIER ::= { netBotzVibrationSensorTraps 0 }
netBotzTestPrefix                   OBJECT IDENTIFIER ::= { netBotzTestTraps 0 }
netBotzSensorPodPrefix              OBJECT IDENTIFIER ::= { netBotzSensorPodTraps 0 }
netBotzCameraPrefix                 OBJECT IDENTIFIER ::= { netBotzCameraTraps 0 }
netBotz4to20mAPodPrefix             OBJECT IDENTIFIER ::= { netBotz4to20mAPodTraps 0 }
netBotzRackAccessPrefix             OBJECT IDENTIFIER ::= { netBotzRackAccessTraps 0 }
netBotzRpduPrefix                   OBJECT IDENTIFIER ::= { netBotzRpduTraps 0 }
netBotzUpsPrefix                    OBJECT IDENTIFIER ::= { netBotzUpsTraps 0 }
netBotzGenericPrefix                OBJECT IDENTIFIER ::= { netBotzGenericTraps 0 }

netBotzBotz                         OBJECT IDENTIFIER ::= { netBotzProducts 10 }
netBotz750Rack                      OBJECT IDENTIFIER ::= { netBotzBotz 3000 }
netBotz755Wall                      OBJECT IDENTIFIER ::= { netBotzBotz 3001 }

--        MODULE-COMPLIANCE, OBJECT-GROUP,
--        NOTIFICATION-GROUP                     FROM SNMPv2-CONF;
netbotzBotzGroups OBJECT IDENTIFIER ::= { netBotz5 30 }

netbotzNotificationGroup NOTIFICATION-GROUP
    NOTIFICATIONS {
            netBotzAirFlowTooHigh,
            netBotzAirFlowTooHighRTN,
            netBotzAirFlowTooLow,
            netBotzAirFlowTooLowRTN,
            netBotzAirFlowUnplugged,
            netBotzAirFlowReplugged,
            netBotzAirFlowError,
            netBotzAirFlowErrorRTN,
            netBotzAmpDetectTooHigh,
            netBotzAmpDetectTooHighRTN,
            netBotzAmpDetectTooLow,
            netBotzAmpDetectTooLowRTN,
            netBotzAmpDetectUnplugged,
            netBotzAmpDetectReplugged,
            netBotzAmpDetectError,
            netBotzAmpDetectErrorRTN,
            netBotzFourToTwentymAPodUnplugged,
            netBotzFourToTwentymAPodReplugged,
            netBotzFourToTwentymAPodError,
            netBotzFourToTwentymAPodErrorRTN,
            netBotzFourToTwentymAPodTooLow,
            netBotzFourToTwentymAPodTooLowRTN,
            netBotzFourToTwentymAPodTooHigh,
            netBotzFourToTwentymAPodTooHighRTN,
            netBotzDewPointTooHigh,
            netBotzDewPointTooHighRTN,
            netBotzDewPointTooLow,
            netBotzDewPointTooLowRTN,
            netBotzDewPointUnplugged,
            netBotzDewPointReplugged,
            netBotzDewPointError,
            netBotzDewPointErrorRTN,
            netBotzDryContactUnplugged,
            netBotzDryContactReplugged,
            netBotzDryContactError,
            netBotzDryContactErrorRTN,
            netBotzDryContactValueError,
            netBotzDryContactValueErrorRTN,
            netBotzCameraMotionSensorUnplugged,
            netBotzCameraMotionSensorReplugged,
            netBotzCameraMotionSensorError,
            netBotzCameraMotionSensorErrorRTN,
            netBotzCameraMotionSensorValueError,
            netBotzCameraMotionSensorValueErrorRTN,
            netBotzDoorSensorUnplugged,
            netBotzDoorSensorReplugged,
            netBotzDoorSensorError,
            netBotzDoorSensorErrorRTN,
            netBotzDoorSensorValueError,
            netBotzDoorSensorValueErrorRTN,
            netBotzCameraUnplugged,
            netBotzCameraReplugged,
            netBotzHumidityTooHigh,
            netBotzHumidityTooHighRTN,
            netBotzHumidityTooLow,
            netBotzHumidityTooLowRTN,
            netBotzHumidityUnplugged,
            netBotzHumidityReplugged,
            netBotzHumidityError,
            netBotzHumidityErrorRTN,
            netBotzLogonError,
            netBotzLogonErrorResolved,
            netBotzLoopVoltageTooHigh,
            netBotzLoopVoltageTooHighRTN,
            netBotzLoopVoltageTooLow,
            netBotzLoopVoltageTooLowRTN,
            netBotzLoopVoltageUnplugged,
            netBotzLoopVoltageReplugged,
            netBotzLoopVoltageError,
            netBotzLoopVoltageErrorRTN,
            netBotzPodUnplugged,
            netBotzPodReplugged,
            netBotzRmtLinkError,
            netBotzRmtLinkErrorResolved,
            netBotzOutputControlSensorUnplugged,
            netBotzOutputControlSensorReplugged,
            netBotzOutputControlSensorError,
            netBotzOutputControlSensorErrorRTN,
            netBotzOutputControlSensorValueError,
            netBotzOutputControlSensorValueErrorRTN,
            netBotzTempTooHigh,
            netBotzTempTooHighRTN,
            netBotzTempTooLow,
            netBotzTempTooLowRTN,
            netBotzTempUnplugged,
            netBotzTempReplugged,
            netBotzTempError,
            netBotzTempErrorRTN,
            netBotzSensorPodUnplugged,
            netBotzSensorPodReplugged,
            netBotzWirelessStatusSensorUnplugged,
            netBotzWirelessStatusSensorReplugged,
            netBotzWirelessStatusSensorError,
            netBotzWirelessStatusSensorErrorRTN,
            netBotzWirelessStatusSensorValueError,
            netBotzWirelessStatusSensorValueErrorRTN,
            netBotzRopeLeakSensorUnplugged,
            netBotzRopeLeakSensorReplugged,
            netBotzRopeLeakSensorError,
            netBotzRopeLeakSensorErrorRTN,
            netBotzRopeLeakSensorValueError,
            netBotzRopeLeakSensorValueErrorRTN,
            netBotzSpotLeakSensorUnplugged,
            netBotzSpotLeakSensorReplugged,
            netBotzSpotLeakSensorError,
            netBotzSpotLeakSensorErrorRTN,
            netBotzSpotLeakSensorValueError,
            netBotzSpotLeakSensorValueErrorRTN,
            netBotzSmokeSensorUnplugged,
            netBotzSmokeSensorReplugged,
            netBotzSmokeSensorError,
            netBotzSmokeSensorErrorRTN,
            netBotzSmokeSensorValueError,
            netBotzSmokeSensorValueErrorRTN,
            netBotzRSSITooLow,
            netBotzRSSITooLowRTN,
            netBotzRSSISensorValueError,
            netBotzRSSISensorValueErrorRTN,
            netBotzBatterySensorError,
            netBotzBatterySensorErrorRTN,
            netBotzBatterySensorValueError,
            netBotzBatterySensorValueErrorRTN,
            netBotzBatteryTooLow,
            netBotzBatteryTooLowRTN,
            netBotzBeaconUnplugged,
            netBotzBeaconReplugged,
            netBotzBeaconError,
            netBotzBeaconErrorRTN,
            netBotzBeaconValueError,
            netBotzBeaconValueErrorRTN,
            netBotzOutletSensorError,
            netBotzOutletSensorErrorRTN,
            netBotzOutletSensorValueError,
            netBotzOutletSensorValueErrorRTN,
            netBotzVibrationSensorUnplugged,
            netBotzVibrationSensorReplugged,
            netBotzVibrationSensorError,
            netBotzVibrationSensorErrorRTN,
            netBotzVibrationSensorValueError,
            netBotzVibrationSensorValueErrorRTN,
            netBotzDoorSensorForcedEntryError,
            netBotzDoorSensorForcedEntryErrorRTN,
            netBotzRackHandleSensorOpenError,
            netBotzRackHandleSensorOpenErrorRTN,
            netBotzCardReaderLocalAuthorizationError,
            netBotzCardReaderLocalAuthorizationErrorRTN,
            netBotzCardReaderLdapAuthorizationError,
            netBotzCardReaderLdapAuthorizationErrorRTN,
            netBotzCardReaderUnplugged,
            netBotzCardReaderReplugged,
            netBotzCardReaderError,
            netBotzCardReaderErrorRTN,
            netBotzCardReaderValueError,
            netBotzCardReaderValueErrorRTN,
            netBotzRackHandleSensorUnplugged,
            netBotzRackHandleSensorReplugged,
            netBotzRackHandleSensorError,
            netBotzRackHandleSensorErrorRTN,
            netBotzRackHandleSensorValueError,
            netBotzRackHandleSensorValueErrorRTN,
            netBotzLockSensorUnplugged,
            netBotzLockSensorReplugged,
            netBotzLockSensorError,
            netBotzLockSensorErrorRTN,
            netBotzLockSensorValueError,
            netBotzLockSensorValueErrorRTN,
            netBotzRpduUnplugged,
            netBotzRpduReplugged,
            netBotzUpsUnplugged,
            netBotzUpsReplugged,

            netBotzGenericNotification,
            netBotzTestNotification

            }
    STATUS current
    DESCRIPTION " A collection of netbotz stuff"
    ::= { netbotzBotzGroups 2 }


--
-- Object Group
--
netbotzObjectGroup OBJECT-GROUP
    OBJECTS {
        netBotzErrorStatus,
        otherPortId,
        otherPortStatus,
        otherPortLabel,
        otherPortEncId,
        otherPortIndex,
        --other numeric
        otherNumericSensorValue,
        otherNumericSensorErrorStatus,
        otherNumericSensorLabel,
        otherNumericSensorEncId,
        otherNumericSensorPortId,
        otherNumericSensorValueStr,
        otherNumericSensorValueInt,
        otherNumericSensorUnits,
        otherNumericSensorValueIntX1000,
        otherNumericSensorValueIntX1000000,
        otherNumericSensorIndex,
        --other state
        otherStateSensorId,
        otherStateSensorValue,
        otherStateSensorErrorStatus,
        otherStateSensorLabel,
        otherStateSensorEncId,
        otherStateSensorPortId,
        otherStateSensorValueStr,
        otherStateSensorIndex,
        otherNumericSensorId,

        netBotzTrapSensorLabel,
        netBotzTrapStartTime,
        netBotzTrapSeverity,
        netBotzTrapSensorValue,
        netBotzTrapSensorValueInt,
        netBotzTrapSensorValueFraction,
        netBotzTrapData,

        tempSensorValue,
        tempSensorValueStr,
        tempSensorValueInt,
        tempSensorValueIntF,
        tempSensorId,
        tempSensorErrorStatus,
        tempSensorLabel,
        tempSensorEncId,
        tempSensorPortId,
        tempSensorIndex,

        -- ALlink
        alinkSensorCountId,
        alinkSensorCountValue,
        alinkSensorCountLabel,
        alinkSensorCountEncId,
        alinkSensorCountValueStr,
        alinkSensorCountValueInt,
        alinkSensorCountIndex,
        -- dew point
        dewPointSensorId,
        dewPointSensorValue,
        dewPointSensorErrorStatus,
        dewPointSensorLabel,
        dewPointSensorEncId,
        dewPointSensorPortId,
        dewPointSensorValueStr,
        dewPointSensorValueInt,
        dewPointSensorValueIntF,
        dewPointSensorIndex,
        -- airflow
        airFlowSensorId,
        airFlowSensorValue,
        airFlowSensorErrorStatus,
        airFlowSensorLabel,
        airFlowSensorEncId,
        airFlowSensorPortId,
        airFlowSensorValueStr,
        airFlowSensorValueInt,
        airFlowSensorIndex,
        -- AMP Detect
        ampDetectSensorId,
        ampDetectSensorValue,
        ampDetectSensorErrorStatus,
        ampDetectSensorLabel,
        ampDetectSensorEncId,
        ampDetectSensorPortId,
        ampDetectSensorValueStr,
        ampDetectSensorValueInt,
        ampDetectSensorIndex,
        -- Camera
        cameraId,
        cameraModel,
        cameraVendor,
        cameraConnectionStatus,
        cameraErrorStatus,
        cameraLabel,
        cameraAddress,
        cameraIndex,
        -- CMOT
        cameraMotionSensorId,
        cameraMotionSensorValue,
        cameraMotionSensorErrorStatus,
        cameraMotionSensorLabel,
        cameraMotionSensorEncId,
        cameraMotionSensorPortId,
        cameraMotionSensorValueStr,
        cameraMotionSensorIndex,
        -- enclosure
        enclosureId,
        enclosureStatus,
        enclosureErrorStatus,
        enclosureLabel,
        enclosureParentEncId,
        enclosureSerialNumber,
        enclosureIndex,
        -- humidity  sensor
        humiSensorId,
        humiSensorValue,
        humiSensorErrorStatus,
        humiSensorLabel,
        humiSensorEncId,
        humiSensorPortId,
        humiSensorValueStr,
        humiSensorValueInt,
        humiSensorIndex,
        -- dry contact
        dryContactSensorId,
        dryContactSensorErrorStatus,
        dryContactSensorLabel,
        dryContactSensorEncId,
        dryContactSensorPortId,
        dryContactSensorValueStr,
        dryContactSensorIndex,
        dryContactSensorValue,
        -- door switch
        doorSwitchSensorId,
        doorSwitchSensorValue,
        doorSwitchSensorErrorStatus,
        doorSwitchSensorLabel,
        doorSwitchSensorEncId,
        doorSwitchSensorPortId,
        doorSwitchSensorValueStr,
        doorSwitchSensorIndex,
        -- vibration
        vibrationSensorId,
        vibrationSensorValue,
        vibrationSensorErrorStatus,
        vibrationSensorLabel,
        vibrationSensorEncId,
        vibrationSensorPortId,
        vibrationSensorValueStr,
        vibrationSensorIndex,
        -- smoke
        smokeSensorId,
        smokeSensorValue,
        smokeSensorErrorStatus,
        smokeSensorLabel,
        smokeSensorEncId,
        smokeSensorPortId,
        smokeSensorValueStr,
        smokeSensorIndex,
        -- leak
        leakSensorId,
        leakSensorValue,
        leakSensorErrorStatus,
        leakSensorLabel,
        leakSensorEncId,
        leakSensorPortId,
        leakSensorValueStr,
        leakSensorIndex,
        -- beacon
        beaconId,
        beaconValue,
        beaconErrorStatus,
        beaconLabel,
        beaconEncId,
        beaconPortId,
        beaconValueStr,
        beaconIndex,
        -- switched outlet
        switchedOutletId,
        switchedOutletValue,
        switchedOutletErrorStatus,
        switchedOutletLabel,
        switchedOutletEncId,
        switchedOutletPortId,
        switchedOutletValueStr,
        switchedOutletIndex,
        -- door Lock
        doorLockSensorId,
        doorLockSensorValue,
        doorLockSensorErrorStatus,
        doorLockSensorLabel,
        doorLockSensorEncId,
        doorLockSensorPortId,
        doorLockSensorValueStr,
        doorLockSensorIndex,
        -- rack handle
        rackHandleSensorId,
        rackHandleSensorValue,
        rackHandleSensorErrorStatus,
        rackHandleSensorLabel,
        rackHandleSensorEncId,
        rackHandleSensorPortId,
        rackHandleSensorValueStr,
        rackHandleSensorIndex,
        -- output relay
        outputRelaySensorId ,
        outputRelaySensorValue,
        outputRelaySensorErrorStatus,
        outputRelaySensorLabel,
        outputRelaySensorEncId,
        outputRelaySensorPortId,
        outputRelaySensorValueStr,
        outputRelaySensorIndex,

        -- rssi
        rssiSensorId,
        rssiSensorValue,
        rssiSensorErrorStatus,
        rssiSensorLabel,
        rssiSensorEncId,
        rssiSensorPortId,
        rssiSensorValueStr,
        rssiSensorValueInt,
        rssiSensorUnits,
        rssiSensorIndex,
        --current input
        currentInputSensorId,
        currentInputSensorValue,
        currentInputSensorErrorStatus,
        currentInputSensorLabel,
        currentInputSensorEncId,
        currentInputSensorPortId,
        currentInputSensorValueStr,
        currentInputSensorValueInt,
        currentInputSensorUnits,
        currentInputSensorValueIntX1000,
        currentInputSensorValueIntX1000000,
        currentInputSensorIndex,
        -- voltage
        voltageSensorId,
        voltageSensorValue,
        voltageSensorErrorStatus,
        voltageSensorLabel,
        voltageSensorEncId,
        voltageSensorPortId,
        voltageSensorValueStr,
        voltageSensorValueInt,
        voltageSensorUnits,
        voltageSensorValueIntX1000,
        voltageSensorValueIntX1000000,
        voltageSensorIndex,
        -- batteryBattery
        batterySensorId,
        batterySensorValue,
        batterySensorErrorStatus,
        batterySensorLabel,
        batterySensorEncId,
        batterySensorPortId,
        batterySensorValueStr,
        batterySensorValueInt,
        batterySensorUnits,
        batterySensorValueIntX1000,
        batterySensorValueIntX1000000,
        batterySensorIndex,
        -- error condition
        errorCondId,
        errorCondSeverity,
        errorCondTypeId,
        errorCondStartTime,
        errorCondStartTimeStr,
        errorCondResolved,
        errorCondResolvedTime,
        errorCondResolvedTimeStr,
        errorCondEncId,
        errorCondPortId,
        errorCondSensorId,
        errorCondIndex,

        netBotzTrapErrorID,
        netBotzTrapErrorType,
        netBotzTrapErrorTypeLabel,
        netBotzTrapSensorID,
        netBotzTrapContainerID,
        netBotzTrapContainerLabel,
        netBotzTrapPortID,
        netBotzTrapPortLabel,
        netBotzTrapNotifyTime,
        netBotzTrapResolveTime,

        firmwareDescription,
        firmwareVersion,
        firmwareIndex
        }
    STATUS current
    DESCRIPTION " A collection of netbotz stuff"
    ::= { netbotzBotzGroups 1 }

OperStatus ::= TEXTUAL-CONVENTION
    STATUS current
    DESCRIPTION
        "The operational status of the device entity."
    SYNTAX INTEGER { disconnected(0), error(1), normal(2) }

ErrorStatus ::= TEXTUAL-CONVENTION
    STATUS current
    DESCRIPTION
        "The error status of the device entity.  If there are no error conditions
         reported for the entity, the status is normal.  Otherwise, the status is
         reported as the severity value of the highest severity error condition
         that is not resolved for the entity."
    SYNTAX INTEGER { normal(0), info(1), warning(2), error(3), critical(4), failure(5) }

BoolValue ::= TEXTUAL-CONVENTION
    STATUS current
    DESCRIPTION
        "A boolean value."
    SYNTAX INTEGER { no(0), yes(1), null(2) }

-- BoolValue ::= TEXTUAL-CONVENTION
--    STATUS current
--    DESCRIPTION
--        "A boolean value."
--    SYNTAX INTEGER { no(0), yes(1), null(2) }
netBotzEnclosures        OBJECT IDENTIFIER ::= { netBotz5 2 }
netBotzPorts             OBJECT IDENTIFIER ::= { netBotz5 3 }
netBotzSensors           OBJECT IDENTIFIER ::= { netBotz5 4 }
netBotzErrors            OBJECT IDENTIFIER ::= { netBotz5 5 }
netBotzCameras           OBJECT IDENTIFIER ::= { netBotz5 6 }
netBotzFirmware          OBJECT IDENTIFIER ::= { netBotz5 7 }

netBotzSensorCounts      OBJECT IDENTIFIER ::= { netBotzEnclosures 2}
netBotzNumericSensors    OBJECT IDENTIFIER ::= { netBotzSensors 1 }
netBotzStateSensors      OBJECT IDENTIFIER ::= { netBotzSensors 2 }


--
-- Top-level error status - worst active alert severity
--
netBotzErrorStatus OBJECT-TYPE
    SYNTAX     ErrorStatus
    MAX-ACCESS read-only
    STATUS     current
    DESCRIPTION
        "The error status of the appliance.  If there are no error conditions
         reported for the appliance, the status is normal.  Otherwise, the status is
         reported as the severity value of the highest severity error condition
         that is not resolved for the appliance."
    ::= { netBotz5 100 }

--
-- Enclosures
--
enclosureTable OBJECT-TYPE
    SYNTAX     SEQUENCE OF EnclosureEntry
    MAX-ACCESS not-accessible
    STATUS     current
    DESCRIPTION
        "A list of enclosures (base enclosure and pods)."
    ::= { netBotzEnclosures 1 }

enclosureEntry OBJECT-TYPE
    SYNTAX     EnclosureEntry
    MAX-ACCESS not-accessible
    STATUS     current
    DESCRIPTION
        "Enclosure entry."
    INDEX { enclosureIndex }
    ::= { enclosureTable 1 }

EnclosureEntry ::= SEQUENCE {
    enclosureId                          DisplayString,
    enclosureStatus                      OperStatus,
    enclosureErrorStatus                 ErrorStatus,
    enclosureLabel                       DisplayString,
    enclosureParentEncId                 DisplayString,
    enclosureSerialNumber                DisplayString,
    enclosureIndex                       Counter32
}

enclosureId OBJECT-TYPE
    SYNTAX     DisplayString (SIZE (0..127))
    MAX-ACCESS read-only
    STATUS     current
    DESCRIPTION
        "The id of the physical enclosure."
    ::= { enclosureEntry 1 }

enclosureStatus OBJECT-TYPE
    SYNTAX     OperStatus
    MAX-ACCESS read-only
    STATUS     current
    DESCRIPTION
        "The operational status of the enclosure."
    ::= { enclosureEntry 2 }

enclosureErrorStatus OBJECT-TYPE
    SYNTAX     ErrorStatus
    MAX-ACCESS read-only
    STATUS     current
    DESCRIPTION
        "The error status of the enclosure.  If there are no error conditions
         reported for the enclosure, the status is normal.  Otherwise, the status is
         reported as the severity value of the highest severity error condition
         that is not resolved for the enclosure."
    ::= { enclosureEntry 3 }

enclosureLabel OBJECT-TYPE
    SYNTAX     DisplayString
    MAX-ACCESS read-only
    STATUS     current
    DESCRIPTION
        "The unique label assigned to the enclosure (or pod)."
    ::= { enclosureEntry 4 }

enclosureParentEncId OBJECT-TYPE
    SYNTAX     DisplayString (SIZE (0..127))
    MAX-ACCESS read-only
    STATUS     current
    DESCRIPTION
        "The id of the parent enclosure this enclosure is attached to."
    ::= { enclosureEntry 5 }

enclosureSerialNumber OBJECT-TYPE
    SYNTAX     DisplayString (SIZE (0..127))
    MAX-ACCESS read-only
    STATUS     current
    DESCRIPTION
        "The serial number of this enclosure."
    ::= { enclosureEntry 6 }

enclosureIndex OBJECT-TYPE
    SYNTAX     Counter32
    MAX-ACCESS read-only
    STATUS     current
    DESCRIPTION
        "The index of the physical enclosure."
    ::= { enclosureEntry 7 }

-- +++++++++++++++++++++++++++++++++++++++++++++++++++++++++++++
-- Sensor-Counts Group
-- This group defines counters of sensors in an integer
-- value which is defined by the contained subgroups
alinkSensorCountTable OBJECT-TYPE
    SYNTAX     SEQUENCE OF AlinkSensorCountEntry
    MAX-ACCESS not-accessible
    STATUS     current
    DESCRIPTION
        "A count of alink-related sensors."
    ::= { netBotzSensorCounts 1 }

alinkSensorCountEntry OBJECT-TYPE
    SYNTAX     AlinkSensorCountEntry
    MAX-ACCESS not-accessible
    STATUS     current
    DESCRIPTION
        "A count-of-sensors entry."
    INDEX { alinkSensorCountIndex }
    ::= { alinkSensorCountTable 1 }

AlinkSensorCountEntry ::= SEQUENCE {
    alinkSensorCountId                      DisplayString,
    alinkSensorCountValue                   Integer32,
    alinkSensorCountLabel                   DisplayString,
    alinkSensorCountEncId                   DisplayString,
    alinkSensorCountValueStr                DisplayString,
    alinkSensorCountValueInt                Integer32,
    alinkSensorCountIndex                   Counter32
}

alinkSensorCountId OBJECT-TYPE
    SYNTAX     DisplayString (SIZE (0..127))
    MAX-ACCESS read-only
    STATUS     current
    DESCRIPTION
        "The unique id of the sensor."
    ::= { alinkSensorCountEntry 1 }

alinkSensorCountValue OBJECT-TYPE
    SYNTAX     Integer32 (0..65535)
    MAX-ACCESS read-only
    STATUS     current
    DESCRIPTION
        "The number of known connected sensors."
    ::= { alinkSensorCountEntry 2 }

alinkSensorCountLabel OBJECT-TYPE
    SYNTAX     DisplayString
    MAX-ACCESS read-only
    STATUS     current
    DESCRIPTION
        "The unique label assigned to the sensor count."
    ::= { alinkSensorCountEntry 3 }

alinkSensorCountEncId OBJECT-TYPE
    SYNTAX     DisplayString (SIZE (0..127))
    MAX-ACCESS read-only
    STATUS     current
    DESCRIPTION
        "The id of the physical enclosure represented by the sensor count."
    ::= { alinkSensorCountEntry 4 }

alinkSensorCountValueStr OBJECT-TYPE
    SYNTAX     DisplayString
    MAX-ACCESS read-only
    STATUS     current
    DESCRIPTION
        "The sensor count value shown as a string."
    ::= { alinkSensorCountEntry 5 }

alinkSensorCountValueInt OBJECT-TYPE
    SYNTAX     Integer32 (0..6554)
    MAX-ACCESS read-only
    STATUS     current
    DESCRIPTION
        "The sensor count as integer value."
    ::= { alinkSensorCountEntry 6 }

alinkSensorCountIndex OBJECT-TYPE
    SYNTAX     Counter32
    MAX-ACCESS read-only
    STATUS     current
    DESCRIPTION
        "The index of the sensor counter."
    ::= { alinkSensorCountEntry 7 }

-- +++++++++++++++++++++++++++++++++++++++++++++++++++++++++++++
--
-- Ports
--

otherPortTable OBJECT-TYPE
    SYNTAX     SEQUENCE OF OtherPortEntry
    MAX-ACCESS not-accessible
    STATUS     current
    DESCRIPTION
        "A list of other port entries."
    ::= { netBotzPorts 10 }

otherPortEntry OBJECT-TYPE
    SYNTAX     OtherPortEntry
    MAX-ACCESS not-accessible
    STATUS     current
    DESCRIPTION
        "Other port entry."
    INDEX { otherPortIndex }
    ::= { otherPortTable 1 }

OtherPortEntry ::= SEQUENCE {
    otherPortId                            DisplayString,
    otherPortStatus                        OperStatus,
    otherPortLabel                         DisplayString,
    otherPortEncId                         DisplayString,
    otherPortIndex                         Counter32
}

otherPortId OBJECT-TYPE
    SYNTAX     DisplayString (SIZE (0..127))
    MAX-ACCESS read-only
    STATUS     current
    DESCRIPTION
        "The unique id of the port."
    ::= { otherPortEntry 1 }

otherPortStatus OBJECT-TYPE
    SYNTAX     OperStatus
    MAX-ACCESS read-only
    STATUS     current
    DESCRIPTION
        "The operational status of the port."
    ::= { otherPortEntry 2 }

otherPortLabel OBJECT-TYPE
    SYNTAX     DisplayString
    MAX-ACCESS read-only
    STATUS     current
    DESCRIPTION
        "The unique label assigned to the port."
    ::= { otherPortEntry 3 }

otherPortEncId OBJECT-TYPE
    SYNTAX     DisplayString (SIZE (0..127))
    MAX-ACCESS read-only
    STATUS     current
    DESCRIPTION
        "The id of the physical enclosure containing the port."
    ::= { otherPortEntry 4 }

otherPortIndex OBJECT-TYPE
    SYNTAX     Counter32
    MAX-ACCESS read-only
    STATUS     current
    DESCRIPTION
        "The index of the port."
    ::= { otherPortEntry 5 }

-- Numeric Sensors Group
-- This group defines sensors for which the concepts of "less than"
-- and "greater than" are meaningful.
tempSensorTable OBJECT-TYPE
    SYNTAX     SEQUENCE OF TempSensorEntry
    MAX-ACCESS not-accessible
    STATUS     current
    DESCRIPTION
        "A list of temperature sensor entries."
    ::= { netBotzNumericSensors 1 }

tempSensorEntry OBJECT-TYPE
    SYNTAX     TempSensorEntry
    MAX-ACCESS not-accessible
    STATUS     current
    DESCRIPTION
        "A temperature sensor entry."
    INDEX { tempSensorIndex }
    ::= { tempSensorTable 1 }

TempSensorEntry ::= SEQUENCE {
    tempSensorId                       DisplayString,
    tempSensorValue                    Integer32,
    tempSensorErrorStatus              ErrorStatus,
    tempSensorLabel                    DisplayString,
    tempSensorEncId                    DisplayString,
    tempSensorPortId                   DisplayString,
    tempSensorValueStr                 DisplayString,
    tempSensorValueInt                 Integer32,
    tempSensorValueIntF                Integer32,
    tempSensorIndex                    Counter32
}

tempSensorId   OBJECT-TYPE
    SYNTAX     DisplayString (SIZE (0..127))
    MAX-ACCESS read-only
    STATUS     current
    DESCRIPTION
        "The unique id of the sensor."
    ::= { tempSensorEntry 1 }

tempSensorValue OBJECT-TYPE
    SYNTAX     Integer32 (-500..1000)
    MAX-ACCESS read-only
    STATUS     current
    DESCRIPTION
        "The temperature measured by the sensor in tenths of a degree Celsius."
    ::= { tempSensorEntry 2 }

tempSensorErrorStatus OBJECT-TYPE
    SYNTAX     ErrorStatus
    MAX-ACCESS read-only
    STATUS     current
    DESCRIPTION
        "The error status of the sensor.  If there are no error conditions
         reported for the sensor, the status is normal.  Otherwise, the status is
         reported as the severity value of the highest severity error condition
         that is not resolved for the sensor."
    ::= { tempSensorEntry 3 }

tempSensorLabel OBJECT-TYPE
    SYNTAX     DisplayString
    MAX-ACCESS read-only
    STATUS     current
    DESCRIPTION
        "The unique label assigned to the sensor."
    ::= { tempSensorEntry 4 }

tempSensorEncId OBJECT-TYPE
    SYNTAX     DisplayString (SIZE (0..127))
    MAX-ACCESS read-only
    STATUS     current
    DESCRIPTION
        "The id of the physical enclosure containing the sensor."
    ::= { tempSensorEntry 5 }

tempSensorPortId OBJECT-TYPE
    SYNTAX     DisplayString (SIZE (0..127))
    MAX-ACCESS read-only
    STATUS     current
    DESCRIPTION
        "The id of the port the sensor is plugged into (or empty string
         if it is not plugged into a port)."
    ::= { tempSensorEntry 6 }

tempSensorValueStr OBJECT-TYPE
    SYNTAX     DisplayString
    MAX-ACCESS read-only
    STATUS     current
    DESCRIPTION
        "The temperature reading, in degrees celsius, shown as a string (or empty string
         if it is not plugged into a port)."
    ::= { tempSensorEntry 7 }

tempSensorValueInt OBJECT-TYPE
    SYNTAX     Integer32 (-50..100)
    MAX-ACCESS read-only
    STATUS     current
    DESCRIPTION
        "The temperature measured by the sensor in degree Celsius."
    ::= { tempSensorEntry 8 }

tempSensorValueIntF OBJECT-TYPE
    SYNTAX     Integer32 (-50..212)
    MAX-ACCESS read-only
    STATUS     current
    DESCRIPTION
        "The temperature measured by the sensor in degree Farenheit."
    ::= { tempSensorEntry 9 }

tempSensorIndex   OBJECT-TYPE
    SYNTAX     Counter32
    MAX-ACCESS read-only
    STATUS     current
    DESCRIPTION
        "The index of the sensor."
    ::= { tempSensorEntry 10 }

humiSensorTable OBJECT-TYPE
    SYNTAX     SEQUENCE OF HumiSensorEntry
    MAX-ACCESS not-accessible
    STATUS     current
    DESCRIPTION
        "A list of humidity sensor entries."
    ::= { netBotzNumericSensors 2 }

humiSensorEntry OBJECT-TYPE
    SYNTAX     HumiSensorEntry
    MAX-ACCESS not-accessible
    STATUS     current
    DESCRIPTION
        "A humidity sensor entry."
    INDEX { humiSensorIndex }
    ::= { humiSensorTable 1 }

HumiSensorEntry ::= SEQUENCE {
    humiSensorId                       DisplayString,
    humiSensorValue                    Integer32,
    humiSensorErrorStatus              ErrorStatus,
    humiSensorLabel                    DisplayString,
    humiSensorEncId                    DisplayString,
    humiSensorPortId                   DisplayString,
    humiSensorValueStr                 DisplayString,
    humiSensorValueInt                 Integer32,
    humiSensorIndex                    Counter32
}

humiSensorId   OBJECT-TYPE
    SYNTAX     DisplayString (SIZE (0..127))
    MAX-ACCESS read-only
    STATUS     current
    DESCRIPTION
        "The unique id of the sensor."
    ::= { humiSensorEntry 1 }

humiSensorValue OBJECT-TYPE
    SYNTAX     Integer32 (0..1000)
    MAX-ACCESS read-only
    STATUS     current
    DESCRIPTION
        "The relative humidity measured by the sensor in tenths of a percent."
    ::= { humiSensorEntry 2 }

humiSensorErrorStatus OBJECT-TYPE
    SYNTAX     ErrorStatus
    MAX-ACCESS read-only
    STATUS     current
    DESCRIPTION
        "The error status of the sensor.  If there are no error conditions
         reported for the sensor, the status is normal.  Otherwise, the status is
         reported as the severity value of the highest severity error condition
         that is not resolved for the sensor."
    ::= { humiSensorEntry 3 }

humiSensorLabel OBJECT-TYPE
    SYNTAX     DisplayString
    MAX-ACCESS read-only
    STATUS     current
    DESCRIPTION
        "The unique label assigned to the sensor."
    ::= { humiSensorEntry 4 }

humiSensorEncId OBJECT-TYPE
    SYNTAX     DisplayString (SIZE (0..127))
    MAX-ACCESS read-only
    STATUS     current
    DESCRIPTION
        "The id of the physical enclosure containing the sensor."
    ::= { humiSensorEntry 5 }

humiSensorPortId OBJECT-TYPE
    SYNTAX     DisplayString (SIZE (0..127))
    MAX-ACCESS read-only
    STATUS     current
    DESCRIPTION
        "The id of the port the sensor is plugged into (or empty string
         if it is not plugged into a port)."
    ::= { humiSensorEntry 6 }

humiSensorValueStr OBJECT-TYPE
    SYNTAX     DisplayString
    MAX-ACCESS read-only
    STATUS     current
    DESCRIPTION
        "The humidity reading, in percent, shown as a string (or empty string
         if it is not plugged into a port)."
    ::= { humiSensorEntry 7 }

humiSensorValueInt OBJECT-TYPE
    SYNTAX     Integer32 (0..100)
    MAX-ACCESS read-only
    STATUS     current
    DESCRIPTION
        "The relative humidity measured by the sensor in percent."
    ::= { humiSensorEntry 8 }

humiSensorIndex   OBJECT-TYPE
    SYNTAX     Counter32
    MAX-ACCESS read-only
    STATUS     current
    DESCRIPTION
        "The index of the sensor."
    ::= { humiSensorEntry 9 }

dewPointSensorTable OBJECT-TYPE
    SYNTAX     SEQUENCE OF DewPointSensorEntry
    MAX-ACCESS not-accessible
    STATUS     current
    DESCRIPTION
        "A list of dew point sensor entries."
    ::= { netBotzNumericSensors 3 }

dewPointSensorEntry OBJECT-TYPE
    SYNTAX     DewPointSensorEntry
    MAX-ACCESS not-accessible
    STATUS     current
    DESCRIPTION
        "A dew point sensor entry."
    INDEX { dewPointSensorIndex }
    ::= { dewPointSensorTable 1 }

DewPointSensorEntry ::= SEQUENCE {
    dewPointSensorId                      DisplayString,
    dewPointSensorValue                   Integer32,
    dewPointSensorErrorStatus             ErrorStatus,
    dewPointSensorLabel                   DisplayString,
    dewPointSensorEncId                   DisplayString,
    dewPointSensorPortId                  DisplayString,
    dewPointSensorValueStr                DisplayString,
    dewPointSensorValueInt                Integer32,
    dewPointSensorValueIntF               Integer32,
    dewPointSensorIndex                   Counter32
}

dewPointSensorId OBJECT-TYPE
    SYNTAX     DisplayString (SIZE (0..127))
    MAX-ACCESS read-only
    STATUS     current
    DESCRIPTION
        "The unique id of the sensor."
    ::= { dewPointSensorEntry 1 }

dewPointSensorValue OBJECT-TYPE
    SYNTAX     Integer32 (-500..1000)
    MAX-ACCESS read-only
    STATUS     current
    DESCRIPTION
        "The dew point value measured by the sensor in tenths of a degree Celsius."
    ::= { dewPointSensorEntry 2 }

dewPointSensorErrorStatus OBJECT-TYPE
    SYNTAX     ErrorStatus
    MAX-ACCESS read-only
    STATUS     current
    DESCRIPTION
        "The operational status of the sensor.  If there are no error conditions
         reported for the sensor, the status is normal.  Otherwise, the status is
         reported as the severity value of the highest severity error condition
         that is not resolved for the sensor."
    ::= { dewPointSensorEntry 3 }

dewPointSensorLabel OBJECT-TYPE
    SYNTAX     DisplayString
    MAX-ACCESS read-only
    STATUS     current
    DESCRIPTION
        "The unique label assigned to the sensor."
    ::= { dewPointSensorEntry 4 }

dewPointSensorEncId OBJECT-TYPE
    SYNTAX     DisplayString (SIZE (0..127))
    MAX-ACCESS read-only
    STATUS     current
    DESCRIPTION
        "The id of the physical enclosure containing the sensor."
    ::= { dewPointSensorEntry 5 }

dewPointSensorPortId OBJECT-TYPE
    SYNTAX     DisplayString (SIZE (0..127))
    MAX-ACCESS read-only
    STATUS     current
    DESCRIPTION
        "The id of the port the sensor is plugged into (or empty string
         if it is not plugged into a port)."
    ::= { dewPointSensorEntry 6 }

dewPointSensorValueStr OBJECT-TYPE
    SYNTAX     DisplayString
    MAX-ACCESS read-only
    STATUS     current
    DESCRIPTION
        "The dew point reading, in degrees celsius, shown as a string (or empty string
         if it is not plugged into a port)."
    ::= { dewPointSensorEntry 7 }

dewPointSensorValueInt OBJECT-TYPE
    SYNTAX     Integer32 (-50..100)
    MAX-ACCESS read-only
    STATUS     current
    DESCRIPTION
        "The dew point value measured by the sensor in degrees Celsius."
    ::= { dewPointSensorEntry 8 }

dewPointSensorValueIntF OBJECT-TYPE
    SYNTAX     Integer32 (-40..122)
    MAX-ACCESS read-only
    STATUS     current
    DESCRIPTION
        "The dew point reading in degrees Farenheit, measured by the sensor."
    ::= { dewPointSensorEntry 9 }

dewPointSensorIndex OBJECT-TYPE
    SYNTAX     Counter32
    MAX-ACCESS read-only
    STATUS     current
    DESCRIPTION
        "The index of the sensor."
    ::= { dewPointSensorEntry 10 }


airFlowSensorTable OBJECT-TYPE
    SYNTAX     SEQUENCE OF AirFlowSensorEntry
    MAX-ACCESS not-accessible
    STATUS     current
    DESCRIPTION
        "A list of airflow sensor entries."
    ::= { netBotzNumericSensors 5 }

airFlowSensorEntry OBJECT-TYPE
    SYNTAX     AirFlowSensorEntry
    MAX-ACCESS not-accessible
    STATUS     current
    DESCRIPTION
        "An air flow sensor entry."
    INDEX { airFlowSensorIndex }
    ::= { airFlowSensorTable 1 }

AirFlowSensorEntry ::= SEQUENCE {
    airFlowSensorId                      DisplayString,
    airFlowSensorValue                   Integer32,
    airFlowSensorErrorStatus             ErrorStatus,
    airFlowSensorLabel                   DisplayString,
    airFlowSensorEncId                   DisplayString,
    airFlowSensorPortId                  DisplayString,
    airFlowSensorValueStr                DisplayString,
    airFlowSensorValueInt                Integer32,
    airFlowSensorIndex                   Counter32
}

airFlowSensorId OBJECT-TYPE
    SYNTAX     DisplayString (SIZE (0..127))
    MAX-ACCESS read-only
    STATUS     current
    DESCRIPTION
        "The unique id of the sensor."
    ::= { airFlowSensorEntry 1 }

airFlowSensorValue OBJECT-TYPE
    SYNTAX     Integer32 (0..10000)
    MAX-ACCESS read-only
    STATUS     current
    DESCRIPTION
        "The air flow measured by the sensor in tenths of a meter per minute."
    ::= { airFlowSensorEntry 2 }

airFlowSensorErrorStatus OBJECT-TYPE
    SYNTAX     ErrorStatus
    MAX-ACCESS read-only
    STATUS     current
    DESCRIPTION
        "The error status of the sensor.  If there are no error conditions
         reported for the sensor, the status is normal.  Otherwise, the status is
         reported as the severity value of the highest severity error condition
         that is not resolved for the sensor."
    ::= { airFlowSensorEntry 3 }

airFlowSensorLabel OBJECT-TYPE
    SYNTAX     DisplayString
    MAX-ACCESS read-only
    STATUS     current
    DESCRIPTION
        "The unique label assigned to the sensor."
    ::= { airFlowSensorEntry 4 }

airFlowSensorEncId OBJECT-TYPE
    SYNTAX     DisplayString (SIZE (0..127))
    MAX-ACCESS read-only
    STATUS     current
    DESCRIPTION
        "The id of the physical enclosure containing the sensor."
    ::= { airFlowSensorEntry 5 }

airFlowSensorPortId OBJECT-TYPE
    SYNTAX     DisplayString (SIZE (0..127))
    MAX-ACCESS read-only
    STATUS     current
    DESCRIPTION
        "The id of the port the sensor is plugged into (or empty string
         if it is not plugged into a port)."
    ::= { airFlowSensorEntry 6 }

airFlowSensorValueStr OBJECT-TYPE
    SYNTAX     DisplayString
    MAX-ACCESS read-only
    STATUS     current
    DESCRIPTION
        "The airflow reading, in meters per minute, shown as a string (or empty string
         if it is not plugged into a port)."
    ::= { airFlowSensorEntry 7 }

airFlowSensorValueInt OBJECT-TYPE
    SYNTAX     Integer32 (0..1000)
    MAX-ACCESS read-only
    STATUS     current
    DESCRIPTION
        "The air flow measured by the sensor in meters per minute."
    ::= { airFlowSensorEntry 8 }

airFlowSensorIndex OBJECT-TYPE
    SYNTAX     Counter32
    MAX-ACCESS read-only
    STATUS     current
    DESCRIPTION
        "The index of the sensor."
    ::= { airFlowSensorEntry 9 }

ampDetectSensorTable OBJECT-TYPE
    SYNTAX     SEQUENCE OF AmpDetectSensorEntry
    MAX-ACCESS not-accessible
    STATUS     current
    DESCRIPTION
        "A list of amp detect sensor entries."
    ::= { netBotzNumericSensors 6 }

ampDetectSensorEntry OBJECT-TYPE
    SYNTAX     AmpDetectSensorEntry
    MAX-ACCESS not-accessible
    STATUS     current
    DESCRIPTION
        "An ampere sensor entry."
    INDEX { ampDetectSensorIndex }
    ::= { ampDetectSensorTable 1 }

AmpDetectSensorEntry ::= SEQUENCE {
    ampDetectSensorId                      DisplayString,
    ampDetectSensorValue                   Integer32,
    ampDetectSensorErrorStatus             ErrorStatus,
    ampDetectSensorLabel                   DisplayString,
    ampDetectSensorEncId                   DisplayString,
    ampDetectSensorPortId                  DisplayString,
    ampDetectSensorValueStr                DisplayString,
    ampDetectSensorValueInt                Integer32,
    ampDetectSensorIndex                   Counter32
}

ampDetectSensorId OBJECT-TYPE
    SYNTAX     DisplayString (SIZE (0..127))
    MAX-ACCESS read-only
    STATUS     current
    DESCRIPTION
        "The unique id of the sensor."
    ::= { ampDetectSensorEntry 1 }

ampDetectSensorValue OBJECT-TYPE
    SYNTAX     Integer32 (0..65535)
    MAX-ACCESS read-only
    STATUS     current
    DESCRIPTION
        "The value measured by the sensor in tenths of an ampere."
    ::= { ampDetectSensorEntry 2 }

ampDetectSensorErrorStatus OBJECT-TYPE
    SYNTAX     ErrorStatus
    MAX-ACCESS read-only
    STATUS     current
    DESCRIPTION
        "The operational status of the sensor.  If there are no error conditions
         reported for the sensor, the status is normal.  Otherwise, the status is
         reported as the severity value of the highest severity error condition
         that is not resolved for the sensor."
    ::= { ampDetectSensorEntry 3 }

ampDetectSensorLabel OBJECT-TYPE
    SYNTAX     DisplayString
    MAX-ACCESS read-only
    STATUS     current
    DESCRIPTION
        "The unique label assigned to the sensor."
    ::= { ampDetectSensorEntry 4 }

ampDetectSensorEncId OBJECT-TYPE
    SYNTAX     DisplayString (SIZE (0..127))
    MAX-ACCESS read-only
    STATUS     current
    DESCRIPTION
        "The id of the physical enclosure containing the sensor."
    ::= { ampDetectSensorEntry 5 }

ampDetectSensorPortId OBJECT-TYPE
    SYNTAX     DisplayString (SIZE (0..127))
    MAX-ACCESS read-only
    STATUS     current
    DESCRIPTION
        "The id of the port the sensor is plugged into (or empty string
         if it is not plugged into a port)."
    ::= { ampDetectSensorEntry 6 }

ampDetectSensorValueStr OBJECT-TYPE
    SYNTAX     DisplayString
    MAX-ACCESS read-only
    STATUS     current
    DESCRIPTION
        "The amp detect reading, in amperes, shown as a string (or empty string
         if it is not plugged into a port)."
    ::= { ampDetectSensorEntry 7 }

ampDetectSensorValueInt OBJECT-TYPE
    SYNTAX     Integer32 (0..6554)
    MAX-ACCESS read-only
    STATUS     current
    DESCRIPTION
        "The value measured by the sensor in amperes."
    ::= { ampDetectSensorEntry 8 }

ampDetectSensorIndex OBJECT-TYPE
    SYNTAX     Counter32
    MAX-ACCESS read-only
    STATUS     current
    DESCRIPTION
        "The index of the sensor."
    ::= { ampDetectSensorEntry 9 }

--
--  Table Index 7 is allocated to "analogInputSensorTable"
--  but has not ever been implemented
--


otherNumericSensorTable OBJECT-TYPE
    SYNTAX     SEQUENCE OF OtherNumericSensorEntry
    MAX-ACCESS not-accessible
    STATUS     current
    DESCRIPTION
        "A list of other numeric sensor entries."
    ::= { netBotzNumericSensors 10 }

otherNumericSensorEntry OBJECT-TYPE
    SYNTAX     OtherNumericSensorEntry
    MAX-ACCESS not-accessible
    STATUS     current
    DESCRIPTION
        "Other numeric sensor entry."
    INDEX { otherNumericSensorIndex }
    ::= { otherNumericSensorTable 1 }

OtherNumericSensorEntry ::= SEQUENCE {
    otherNumericSensorId                      DisplayString,
    otherNumericSensorValue                   Integer32,
    otherNumericSensorErrorStatus             ErrorStatus,
    otherNumericSensorLabel                   DisplayString,
    otherNumericSensorEncId                   DisplayString,
    otherNumericSensorPortId                  DisplayString,
    otherNumericSensorValueStr                DisplayString,
    otherNumericSensorValueInt                Integer32,
    otherNumericSensorUnits                   DisplayString,
    otherNumericSensorValueIntX1000           Integer32,
    otherNumericSensorValueIntX1000000        Integer32,
    otherNumericSensorIndex                   Counter32
}

otherNumericSensorId OBJECT-TYPE
    SYNTAX     DisplayString (SIZE (0..127))
    MAX-ACCESS read-only
    STATUS     current
    DESCRIPTION
        "The unique id of the sensor."
    ::= { otherNumericSensorEntry 1 }

otherNumericSensorValue OBJECT-TYPE
    SYNTAX     Integer32
    MAX-ACCESS read-only
    STATUS     current
    DESCRIPTION
        "The value measured by the sensor in tenths of the unit of measure."
    ::= { otherNumericSensorEntry 2 }

otherNumericSensorErrorStatus OBJECT-TYPE
    SYNTAX     ErrorStatus
    MAX-ACCESS read-only
    STATUS     current
    DESCRIPTION
        "The operational status of the sensor.  If there are no error conditions
         reported for the sensor, the status is normal.  Otherwise, the status is
         reported as the severity value of the highest severity error condition
         that is not resolved for the sensor."
    ::= { otherNumericSensorEntry 3 }

otherNumericSensorLabel OBJECT-TYPE
    SYNTAX     DisplayString
    MAX-ACCESS read-only
    STATUS     current
    DESCRIPTION
        "The unique label assigned to the sensor."
    ::= { otherNumericSensorEntry 4 }

otherNumericSensorEncId OBJECT-TYPE
    SYNTAX     DisplayString (SIZE (0..127))
    MAX-ACCESS read-only
    STATUS     current
    DESCRIPTION
        "The id of the physical enclosure containing the sensor."
    ::= { otherNumericSensorEntry 5 }

otherNumericSensorPortId OBJECT-TYPE
    SYNTAX     DisplayString (SIZE (0..127))
    MAX-ACCESS read-only
    STATUS     current
    DESCRIPTION
        "The id of the port the sensor is plugged into (or empty string
         if it is not plugged into a port)."
    ::= { otherNumericSensorEntry 6 }

otherNumericSensorValueStr OBJECT-TYPE
    SYNTAX     DisplayString
    MAX-ACCESS read-only
    STATUS     current
    DESCRIPTION
        "The sensor reading shown as a string (or empty string
         if it is not plugged into a port)."
    ::= { otherNumericSensorEntry 7 }

otherNumericSensorValueInt OBJECT-TYPE
    SYNTAX     Integer32
    MAX-ACCESS read-only
    STATUS     current
    DESCRIPTION
        "The value measured by the sensor in the unit of measure (1/10 of otherNumericSensorValue)"
    ::= { otherNumericSensorEntry 8 }

otherNumericSensorUnits OBJECT-TYPE
    SYNTAX     DisplayString
    MAX-ACCESS read-only
    STATUS     current
    DESCRIPTION
        "The unit of measure for the sensor value."
    ::= { otherNumericSensorEntry 9 }

otherNumericSensorValueIntX1000 OBJECT-TYPE
    SYNTAX     Integer32
    MAX-ACCESS read-only
    STATUS     current
    DESCRIPTION
        "The value measured by the sensor in thousandths of the unit of measure (100 times otherNumericSensorValue)"
    ::= { otherNumericSensorEntry 10 }

otherNumericSensorValueIntX1000000 OBJECT-TYPE
    SYNTAX     Integer32
    MAX-ACCESS read-only
    STATUS     current
    DESCRIPTION
        "The value measured by the sensor in millionths of the unit of measure (100000 times otherNumericSensorValue)"
    ::= { otherNumericSensorEntry 11 }

otherNumericSensorIndex OBJECT-TYPE
    SYNTAX     Counter32
    MAX-ACCESS read-only
    STATUS     current
    DESCRIPTION
        "The index of the sensor."
    ::= { otherNumericSensorEntry 12 }


-- RSSI
--

rssiSensorTable OBJECT-TYPE
    SYNTAX     SEQUENCE OF RssiSensorEntry
    MAX-ACCESS not-accessible
    STATUS     current
    DESCRIPTION
        "A list of wireless network RSSI entries."
    ::= { netBotzNumericSensors 11 }

rssiSensorEntry OBJECT-TYPE
    SYNTAX     RssiSensorEntry
    MAX-ACCESS not-accessible
    STATUS     current
    DESCRIPTION
        "RSSI sensor entry."
    INDEX { rssiSensorIndex }
    ::= { rssiSensorTable 1 }

RssiSensorEntry ::= SEQUENCE {
    rssiSensorId                      DisplayString,
    rssiSensorValue                   Integer32,
    rssiSensorErrorStatus             ErrorStatus,
    rssiSensorLabel                   DisplayString,
    rssiSensorEncId                   DisplayString,
    rssiSensorPortId                  DisplayString,
    rssiSensorValueStr                DisplayString,
    rssiSensorValueInt                Integer32,
    rssiSensorUnits                   DisplayString,
    rssiSensorIndex                   Counter32
}

rssiSensorId OBJECT-TYPE
    SYNTAX     DisplayString (SIZE (0..127))
    MAX-ACCESS read-only
    STATUS     current
    DESCRIPTION
        "The unique id of the sensor."
    ::= { rssiSensorEntry 1 }

rssiSensorValue OBJECT-TYPE
    SYNTAX     Integer32
    MAX-ACCESS read-only
    STATUS     current
    DESCRIPTION
        "The value measured by the sensor in tenths of the unit of measure."
    ::= { rssiSensorEntry 2 }

rssiSensorErrorStatus OBJECT-TYPE
    SYNTAX     ErrorStatus
    MAX-ACCESS read-only
    STATUS     current
    DESCRIPTION
        "The operational status of the sensor.  If there are no error conditions
         reported for the sensor, the status is normal.  Otherwise, the status is
         reported as the severity value of the highest severity error condition
         that is not resolved for the sensor."
    ::= { rssiSensorEntry 3 }

rssiSensorLabel OBJECT-TYPE
    SYNTAX     DisplayString
    MAX-ACCESS read-only
    STATUS     current
    DESCRIPTION
        "The unique label assigned to the sensor."
    ::= { rssiSensorEntry 4 }

rssiSensorEncId OBJECT-TYPE
    SYNTAX     DisplayString (SIZE (0..127))
    MAX-ACCESS read-only
    STATUS     current
    DESCRIPTION
        "The id of the physical enclosure containing the sensor."
    ::= { rssiSensorEntry 5 }

rssiSensorPortId OBJECT-TYPE
    SYNTAX     DisplayString (SIZE (0..127))
    MAX-ACCESS read-only
    STATUS     current
    DESCRIPTION
        "The id of the port the sensor is plugged into (or empty string
         if it is not plugged into a port)."
    ::= { rssiSensorEntry 6 }

rssiSensorValueStr OBJECT-TYPE
    SYNTAX     DisplayString
    MAX-ACCESS read-only
    STATUS     current
    DESCRIPTION
        "The sensor reading shown as a string (or empty string
         if it is not plugged into a port)."
    ::= { rssiSensorEntry 7 }

rssiSensorValueInt OBJECT-TYPE
    SYNTAX     Integer32
    MAX-ACCESS read-only
    STATUS     current
    DESCRIPTION
        "The value measured by the sensor in the unit of measure (1/10 of rssiSensorValue)"
    ::= { rssiSensorEntry 8 }

rssiSensorUnits OBJECT-TYPE
    SYNTAX     DisplayString
    MAX-ACCESS read-only
    STATUS     current
    DESCRIPTION
        "The unit of measure for the sensor value."
    ::= { rssiSensorEntry 9 }

rssiSensorIndex OBJECT-TYPE
    SYNTAX     Counter32
    MAX-ACCESS read-only
    STATUS     current
    DESCRIPTION
        "The index of the sensor."
    ::= { rssiSensorEntry 10 }

-- current input
--

currentInputSensorTable OBJECT-TYPE
    SYNTAX     SEQUENCE OF CurrentInputSensorEntry
    MAX-ACCESS not-accessible
    STATUS     current
    DESCRIPTION
        "A list of current input sensor entries."
    ::= { netBotzNumericSensors 12 }

currentInputSensorEntry OBJECT-TYPE
    SYNTAX     CurrentInputSensorEntry
    MAX-ACCESS not-accessible
    STATUS     current
    DESCRIPTION
        "Current Input sensor entry."
    INDEX { currentInputSensorIndex }
    ::= { currentInputSensorTable 1 }

CurrentInputSensorEntry ::= SEQUENCE {
    currentInputSensorId                      DisplayString,
    currentInputSensorValue                   Integer32,
    currentInputSensorErrorStatus             ErrorStatus,
    currentInputSensorLabel                   DisplayString,
    currentInputSensorEncId                   DisplayString,
    currentInputSensorPortId                  DisplayString,
    currentInputSensorValueStr                DisplayString,
    currentInputSensorValueInt                Integer32,
    currentInputSensorUnits                   DisplayString,
    currentInputSensorValueIntX1000           Integer32,
    currentInputSensorValueIntX1000000        Integer32,
    currentInputSensorIndex                   Counter32
}

currentInputSensorId OBJECT-TYPE
    SYNTAX     DisplayString (SIZE (0..127))
    MAX-ACCESS read-only
    STATUS     current
    DESCRIPTION
        "The unique id of the sensor."
    ::= { currentInputSensorEntry 1 }

currentInputSensorValue OBJECT-TYPE
    SYNTAX     Integer32
    MAX-ACCESS read-only
    STATUS     current
    DESCRIPTION
        "The value measured by the sensor in tenths of the unit of measure."
    ::= { currentInputSensorEntry 2 }

currentInputSensorErrorStatus OBJECT-TYPE
    SYNTAX     ErrorStatus
    MAX-ACCESS read-only
    STATUS     current
    DESCRIPTION
        "The operational status of the sensor.  If there are no error conditions
         reported for the sensor, the status is normal.  Otherwise, the status is
         reported as the severity value of the highest severity error condition
         that is not resolved for the sensor."
    ::= { currentInputSensorEntry 3 }

currentInputSensorLabel OBJECT-TYPE
    SYNTAX     DisplayString
    MAX-ACCESS read-only
    STATUS     current
    DESCRIPTION
        "The unique label assigned to the sensor."
    ::= { currentInputSensorEntry 4 }

currentInputSensorEncId OBJECT-TYPE
    SYNTAX     DisplayString (SIZE (0..127))
    MAX-ACCESS read-only
    STATUS     current
    DESCRIPTION
        "The id of the physical enclosure containing the sensor."
    ::= { currentInputSensorEntry 5 }

currentInputSensorPortId OBJECT-TYPE
    SYNTAX     DisplayString (SIZE (0..127))
    MAX-ACCESS read-only
    STATUS     current
    DESCRIPTION
        "The id of the port the sensor is plugged into (or empty string
         if it is not plugged into a port)."
    ::= { currentInputSensorEntry 6 }

currentInputSensorValueStr OBJECT-TYPE
    SYNTAX     DisplayString
    MAX-ACCESS read-only
    STATUS     current
    DESCRIPTION
        "The sensor reading shown as a string (or empty string
         if it is not plugged into a port)."
    ::= { currentInputSensorEntry 7 }

currentInputSensorValueInt OBJECT-TYPE
    SYNTAX     Integer32
    MAX-ACCESS read-only
    STATUS     current
    DESCRIPTION
        "The value measured by the sensor in the unit of measure (1/10 of currentInputSensorValue)"
    ::= { currentInputSensorEntry 8 }

currentInputSensorUnits OBJECT-TYPE
    SYNTAX     DisplayString
    MAX-ACCESS read-only
    STATUS     current
    DESCRIPTION
        "The unit of measure for the sensor value."
    ::= { currentInputSensorEntry 9 }

currentInputSensorValueIntX1000 OBJECT-TYPE
    SYNTAX     Integer32
    MAX-ACCESS read-only
    STATUS     current
    DESCRIPTION
        "The value measured by the sensor in thousandths of the unit of measure (100 times currentInputSensorValue)"
    ::= { currentInputSensorEntry 10 }

currentInputSensorValueIntX1000000 OBJECT-TYPE
    SYNTAX     Integer32
    MAX-ACCESS read-only
    STATUS     current
    DESCRIPTION
        "The value measured by the sensor in millionths of the unit of measure (100000 times currentInputSensorValue)"
    ::= { currentInputSensorEntry 11 }

currentInputSensorIndex OBJECT-TYPE
    SYNTAX     Counter32
    MAX-ACCESS read-only
    STATUS     current
    DESCRIPTION
        "The index of the sensor."
    ::= { currentInputSensorEntry 12 }

-- voltage
--

voltageSensorTable OBJECT-TYPE
    SYNTAX     SEQUENCE OF   VoltageSensorEntry
    MAX-ACCESS not-accessible
    STATUS     current
    DESCRIPTION
        "A list of current input sensor entries."
    ::= { netBotzNumericSensors 13 }

voltageSensorEntry OBJECT-TYPE
    SYNTAX     VoltageSensorEntry
    MAX-ACCESS not-accessible
    STATUS     current
    DESCRIPTION
        "Voltage sensor entry."
    INDEX { voltageSensorIndex }
    ::= { voltageSensorTable 1 }

VoltageSensorEntry ::= SEQUENCE {
    voltageSensorId                      DisplayString,
    voltageSensorValue                   Integer32,
    voltageSensorErrorStatus             ErrorStatus,
    voltageSensorLabel                   DisplayString,
    voltageSensorEncId                   DisplayString,
    voltageSensorPortId                  DisplayString,
    voltageSensorValueStr                DisplayString,
    voltageSensorValueInt                Integer32,
    voltageSensorUnits                   DisplayString,
    voltageSensorValueIntX1000           Integer32,
    voltageSensorValueIntX1000000        Integer32,
    voltageSensorIndex                   Counter32
}

voltageSensorId OBJECT-TYPE
    SYNTAX     DisplayString (SIZE (0..127))
    MAX-ACCESS read-only
    STATUS     current
    DESCRIPTION
        "The unique id of the sensor."
    ::= { voltageSensorEntry 1 }

voltageSensorValue OBJECT-TYPE
    SYNTAX     Integer32
    MAX-ACCESS read-only
    STATUS     current
    DESCRIPTION
        "The value measured by the sensor in tenths of the unit of measure."
    ::= { voltageSensorEntry 2 }

voltageSensorErrorStatus OBJECT-TYPE
    SYNTAX     ErrorStatus
    MAX-ACCESS read-only
    STATUS     current
    DESCRIPTION
        "The operational status of the sensor.  If there are no error conditions
         reported for the sensor, the status is normal.  Otherwise, the status is
         reported as the severity value of the highest severity error condition
         that is not resolved for the sensor."
    ::= { voltageSensorEntry 3 }

voltageSensorLabel OBJECT-TYPE
    SYNTAX     DisplayString
    MAX-ACCESS read-only
    STATUS     current
    DESCRIPTION
        "The unique label assigned to the sensor."
    ::= { voltageSensorEntry 4 }

voltageSensorEncId OBJECT-TYPE
    SYNTAX     DisplayString (SIZE (0..127))
    MAX-ACCESS read-only
    STATUS     current
    DESCRIPTION
        "The id of the physical enclosure containing the sensor."
    ::= { voltageSensorEntry 5 }

voltageSensorPortId OBJECT-TYPE
    SYNTAX     DisplayString (SIZE (0..127))
    MAX-ACCESS read-only
    STATUS     current
    DESCRIPTION
        "The id of the port the sensor is plugged into (or empty string
         if it is not plugged into a port)."
    ::= { voltageSensorEntry 6 }

voltageSensorValueStr OBJECT-TYPE
    SYNTAX     DisplayString
    MAX-ACCESS read-only
    STATUS     current
    DESCRIPTION
        "The sensor reading shown as a string (or empty string
         if it is not plugged into a port)."
    ::= { voltageSensorEntry 7 }

voltageSensorValueInt OBJECT-TYPE
    SYNTAX     Integer32
    MAX-ACCESS read-only
    STATUS     current
    DESCRIPTION
        "The value measured by the sensor in the unit of measure (1/10 of voltageSensorValue)"
    ::= { voltageSensorEntry 8 }

voltageSensorUnits OBJECT-TYPE
    SYNTAX     DisplayString
    MAX-ACCESS read-only
    STATUS     current
    DESCRIPTION
        "The unit of measure for the sensor value."
    ::= { voltageSensorEntry 9 }

voltageSensorValueIntX1000 OBJECT-TYPE
    SYNTAX     Integer32
    MAX-ACCESS read-only
    STATUS     current
    DESCRIPTION
        "The value measured by the sensor in thousandths of the unit of measure (100 times voltageSensorValue)"
    ::= { voltageSensorEntry 10 }

voltageSensorValueIntX1000000 OBJECT-TYPE
    SYNTAX     Integer32
    MAX-ACCESS read-only
    STATUS     current
    DESCRIPTION
        "The value measured by the sensor in millionths of the unit of measure (100000 times voltageSensorValue)"
    ::= { voltageSensorEntry 11 }

voltageSensorIndex OBJECT-TYPE
    SYNTAX     Counter32
    MAX-ACCESS read-only
    STATUS     current
    DESCRIPTION
        "The index of the sensor."
    ::= { voltageSensorEntry 12 }

-- battery
--

batterySensorTable OBJECT-TYPE
    SYNTAX     SEQUENCE OF BatterySensorEntry
    MAX-ACCESS not-accessible
    STATUS     current
    DESCRIPTION
        "A list of current input sensor entries."
    ::= { netBotzNumericSensors 14 }

batterySensorEntry OBJECT-TYPE
    SYNTAX     BatterySensorEntry
    MAX-ACCESS not-accessible
    STATUS     current
    DESCRIPTION
        "Battery sensor entry."
    INDEX { batterySensorIndex }
    ::= { batterySensorTable 1 }

BatterySensorEntry ::= SEQUENCE {
    batterySensorId                      DisplayString,
    batterySensorValue                   Integer32,
    batterySensorErrorStatus             ErrorStatus,
    batterySensorLabel                   DisplayString,
    batterySensorEncId                   DisplayString,
    batterySensorPortId                  DisplayString,
    batterySensorValueStr                DisplayString,
    batterySensorValueInt                Integer32,
    batterySensorUnits                   DisplayString,
    batterySensorValueIntX1000           Integer32,
    batterySensorValueIntX1000000        Integer32,
    batterySensorIndex                   Counter32
}

batterySensorId OBJECT-TYPE
    SYNTAX     DisplayString (SIZE (0..127))
    MAX-ACCESS read-only
    STATUS     current
    DESCRIPTION
        "The unique id of the sensor."
    ::= { batterySensorEntry 1 }

batterySensorValue OBJECT-TYPE
    SYNTAX     Integer32
    MAX-ACCESS read-only
    STATUS     current
    DESCRIPTION
        "The value measured by the sensor in tenths of the unit of measure."
    ::= { batterySensorEntry 2 }

batterySensorErrorStatus OBJECT-TYPE
    SYNTAX     ErrorStatus
    MAX-ACCESS read-only
    STATUS     current
    DESCRIPTION
        "The operational status of the sensor.  If there are no error conditions
         reported for the sensor, the status is normal.  Otherwise, the status is
         reported as the severity value of the highest severity error condition
         that is not resolved for the sensor."
    ::= { batterySensorEntry 3 }

batterySensorLabel OBJECT-TYPE
    SYNTAX     DisplayString
    MAX-ACCESS read-only
    STATUS     current
    DESCRIPTION
        "The unique label assigned to the sensor."
    ::= { batterySensorEntry 4 }

batterySensorEncId OBJECT-TYPE
    SYNTAX     DisplayString (SIZE (0..127))
    MAX-ACCESS read-only
    STATUS     current
    DESCRIPTION
        "The id of the physical enclosure containing the sensor."
    ::= { batterySensorEntry 5 }

batterySensorPortId OBJECT-TYPE
    SYNTAX     DisplayString (SIZE (0..127))
    MAX-ACCESS read-only
    STATUS     current
    DESCRIPTION
        "The id of the port the sensor is plugged into (or empty string
         if it is not plugged into a port)."
    ::= { batterySensorEntry 6 }

batterySensorValueStr OBJECT-TYPE
    SYNTAX     DisplayString
    MAX-ACCESS read-only
    STATUS     current
    DESCRIPTION
        "The sensor reading shown as a string (or empty string
         if it is not plugged into a port)."
    ::= { batterySensorEntry 7 }

batterySensorValueInt OBJECT-TYPE
    SYNTAX     Integer32
    MAX-ACCESS read-only
    STATUS     current
    DESCRIPTION
        "The value measured by the sensor in the unit of measure (1/10 of batterySensorValue)"
    ::= { batterySensorEntry 8 }

batterySensorUnits OBJECT-TYPE
    SYNTAX     DisplayString
    MAX-ACCESS read-only
    STATUS     current
    DESCRIPTION
        "The unit of measure for the sensor value."
    ::= { batterySensorEntry 9 }

batterySensorValueIntX1000 OBJECT-TYPE
    SYNTAX     Integer32
    MAX-ACCESS read-only
    STATUS     current
    DESCRIPTION
        "The value measured by the sensor in thousandths of the unit of measure (100 times batterySensorValue)"
    ::= { batterySensorEntry 10 }

batterySensorValueIntX1000000 OBJECT-TYPE
    SYNTAX     Integer32
    MAX-ACCESS read-only
    STATUS     current
    DESCRIPTION
        "The value measured by the sensor in millionths of the unit of measure (100000 times batterySensorValue)"
    ::= { batterySensorEntry 11 }

batterySensorIndex OBJECT-TYPE
    SYNTAX     Counter32
    MAX-ACCESS read-only
    STATUS     current
    DESCRIPTION
        "The index of the sensor."
    ::= { batterySensorEntry 12 }

--
--
-- State Sensors Group
-- This group defines sensors having an integer value which is
-- a defined state id or index.

dryContactSensorTable OBJECT-TYPE
    SYNTAX     SEQUENCE OF DryContactSensorEntry
    MAX-ACCESS not-accessible
    STATUS     current
    DESCRIPTION
        "A list of dry contact sensor entries."
    ::= { netBotzStateSensors 1 }

dryContactSensorEntry OBJECT-TYPE
    SYNTAX     DryContactSensorEntry
    MAX-ACCESS not-accessible
    STATUS     current
    DESCRIPTION
        "Dry contact sensor entry."
    INDEX { dryContactSensorIndex }
    ::= { dryContactSensorTable 1 }

DryContactSensorEntry ::= SEQUENCE {
    dryContactSensorId                      DisplayString,
    dryContactSensorValue                   INTEGER,
    dryContactSensorErrorStatus             ErrorStatus,
    dryContactSensorLabel                   DisplayString,
    dryContactSensorEncId                   DisplayString,
    dryContactSensorPortId                  DisplayString,
    dryContactSensorValueStr                DisplayString,
    dryContactSensorIndex                   Counter32
}

dryContactSensorId OBJECT-TYPE
    SYNTAX     DisplayString (SIZE (0..127))
    MAX-ACCESS read-only
    STATUS     current
    DESCRIPTION
        "The unique id of the sensor."
    ::= { dryContactSensorEntry 1 }

dryContactSensorValue OBJECT-TYPE
    SYNTAX     INTEGER { undefined(-1), open(0), closed(1) }
    MAX-ACCESS read-only
    STATUS     current
    DESCRIPTION
        "Whether the dry sensor contact is open or closed."
    ::= { dryContactSensorEntry 2 }

dryContactSensorErrorStatus OBJECT-TYPE
    SYNTAX     ErrorStatus
    MAX-ACCESS read-only
    STATUS     current
    DESCRIPTION
        "The operational status of the sensor.  If there are no error conditions
         reported for the sensor, the status is normal.  Otherwise, the status is
         reported as the severity value of the highest severity error condition
         that is not resolved for the sensor."
    ::= { dryContactSensorEntry 3 }

dryContactSensorLabel OBJECT-TYPE
    SYNTAX     DisplayString
    MAX-ACCESS read-only
    STATUS     current
    DESCRIPTION
        "The unique label assigned to the sensor."
    ::= { dryContactSensorEntry 4 }

dryContactSensorEncId OBJECT-TYPE
    SYNTAX     DisplayString (SIZE (0..127))
    MAX-ACCESS read-only
    STATUS     current
    DESCRIPTION
        "The id of the physical enclosure containing the sensor."
    ::= { dryContactSensorEntry 5 }

dryContactSensorPortId OBJECT-TYPE
    SYNTAX     DisplayString (SIZE (0..127))
    MAX-ACCESS read-only
    STATUS     current
    DESCRIPTION
        "The id of the port the sensor is plugged into (or empty string
         if it is not plugged into a port)."
    ::= { dryContactSensorEntry 6 }

dryContactSensorValueStr OBJECT-TYPE
    SYNTAX     DisplayString
    MAX-ACCESS read-only
    STATUS     current
    DESCRIPTION
        "The enum value label for the state reported by the sensor."
    ::= { dryContactSensorEntry 7 }

dryContactSensorIndex OBJECT-TYPE
    SYNTAX     Counter32
    MAX-ACCESS read-only
    STATUS     current
    DESCRIPTION
        "The index of the sensor."
    ::= { dryContactSensorEntry 8 }

doorSwitchSensorTable OBJECT-TYPE
    SYNTAX     SEQUENCE OF DoorSwitchSensorEntry
    MAX-ACCESS not-accessible
    STATUS     current
    DESCRIPTION
        "A list of door switch sensor entries."
    ::= { netBotzStateSensors 2 }

doorSwitchSensorEntry OBJECT-TYPE
    SYNTAX     DoorSwitchSensorEntry
    MAX-ACCESS not-accessible
    STATUS     current
    DESCRIPTION
        "Door switch sensor entry."
    INDEX { doorSwitchSensorIndex }
    ::= { doorSwitchSensorTable 1 }

DoorSwitchSensorEntry ::= SEQUENCE {
    doorSwitchSensorId                      DisplayString,
    doorSwitchSensorValue                   INTEGER,
    doorSwitchSensorErrorStatus             ErrorStatus,
    doorSwitchSensorLabel                   DisplayString,
    doorSwitchSensorEncId                   DisplayString,
    doorSwitchSensorPortId                  DisplayString,
    doorSwitchSensorValueStr                DisplayString,
    doorSwitchSensorIndex                   Counter32
}

doorSwitchSensorId OBJECT-TYPE
    SYNTAX     DisplayString (SIZE (0..127))
    MAX-ACCESS read-only
    STATUS     current
    DESCRIPTION
        "The unique id of the sensor."
    ::= { doorSwitchSensorEntry 1 }

doorSwitchSensorValue OBJECT-TYPE
    SYNTAX     INTEGER {  undefined(-1), open(0), closed(1) }
    MAX-ACCESS read-only
    STATUS     current
    DESCRIPTION
        "Whether the door is open or closed."
    ::= { doorSwitchSensorEntry 2 }

doorSwitchSensorErrorStatus OBJECT-TYPE
    SYNTAX     ErrorStatus
    MAX-ACCESS read-only
    STATUS     current
    DESCRIPTION
        "The operational status of the sensor.  If there are no error conditions
         reported for the sensor, the status is normal.  Otherwise, the status is
         reported as the severity value of the highest severity error condition
         that is not resolved for the sensor."
    ::= { doorSwitchSensorEntry 3 }

doorSwitchSensorLabel OBJECT-TYPE
    SYNTAX     DisplayString
    MAX-ACCESS read-only
    STATUS     current
    DESCRIPTION
        "The unique label assigned to the sensor."
    ::= { doorSwitchSensorEntry 4 }

doorSwitchSensorEncId OBJECT-TYPE
    SYNTAX     DisplayString (SIZE (0..127))
    MAX-ACCESS read-only
    STATUS     current
    DESCRIPTION
        "The id of the physical enclosure containing the sensor."
    ::= { doorSwitchSensorEntry 5 }

doorSwitchSensorPortId OBJECT-TYPE
    SYNTAX     DisplayString (SIZE (0..127))
    MAX-ACCESS read-only
    STATUS     current
    DESCRIPTION
        "The id of the port the sensor is plugged into (or empty string
         if it is not plugged into a port)."
    ::= { doorSwitchSensorEntry 6 }

doorSwitchSensorValueStr OBJECT-TYPE
    SYNTAX     DisplayString
    MAX-ACCESS read-only
    STATUS     current
    DESCRIPTION
        "The enum value label for the state reported by the sensor."
    ::= { doorSwitchSensorEntry 7 }

doorSwitchSensorIndex OBJECT-TYPE
    SYNTAX     Counter32
    MAX-ACCESS read-only
    STATUS     current
    DESCRIPTION
        "The index of the sensor."
    ::= { doorSwitchSensorEntry 8 }

--
-- Camera Entry
--

cameraTable OBJECT-TYPE
    SYNTAX     SEQUENCE OF CameraEntry
    MAX-ACCESS not-accessible
    STATUS     current
    DESCRIPTION
        "A list of configured camera's."
    ::= { netBotzCameras 1 }

cameraEntry OBJECT-TYPE
    SYNTAX     CameraEntry
    MAX-ACCESS not-accessible
    STATUS     current
    DESCRIPTION
        "Camera entry."
    INDEX { cameraIndex }
    ::= { cameraTable 1 }

CameraEntry ::= SEQUENCE {
    cameraId                          DisplayString,
    cameraVendor                      DisplayString,
    cameraModel                       DisplayString,
    cameraConnectionStatus            OperStatus,
    cameraErrorStatus                 ErrorStatus,
    cameraLabel                       DisplayString,
    cameraAddress                     DisplayString,
    cameraIndex                       Counter32
}

cameraId OBJECT-TYPE
    SYNTAX     DisplayString (SIZE (0..127))
    MAX-ACCESS read-only
    STATUS     current
    DESCRIPTION
        "The id of the camera."
    ::= { cameraEntry 1 }

cameraVendor OBJECT-TYPE
    SYNTAX     DisplayString (SIZE (0..127))
    MAX-ACCESS read-only
    STATUS     current
    DESCRIPTION
        "The vendor of the camera."
    ::= { cameraEntry 2 }

cameraModel OBJECT-TYPE
    SYNTAX     DisplayString (SIZE (0..127))
    MAX-ACCESS read-only
    STATUS     current
    DESCRIPTION
        "The model of the camera."
    ::= { cameraEntry 3 }

cameraConnectionStatus OBJECT-TYPE
    SYNTAX     OperStatus
    MAX-ACCESS read-only
    STATUS     current
    DESCRIPTION
        "The operational status of the camera."
    ::= { cameraEntry 4 }

cameraErrorStatus OBJECT-TYPE
    SYNTAX     ErrorStatus
    MAX-ACCESS read-only
    STATUS     current
    DESCRIPTION
        "The error status of the camera.  If there are no error conditions
         reported for the camera, the status is normal.  Otherwise, the status is
         reported as the severity value of the highest severity error condition
         that is not resolved for the camera."
    ::= { cameraEntry 5 }

cameraLabel OBJECT-TYPE
    SYNTAX     DisplayString
    MAX-ACCESS read-only
    STATUS     current
    DESCRIPTION
        "The unique label assigned to the camera."
    ::= { cameraEntry 6 }

cameraAddress OBJECT-TYPE
    SYNTAX     DisplayString (SIZE (0..127))
    MAX-ACCESS read-only
    STATUS     current
    DESCRIPTION
        "The address or host name of the camera."
    ::= { cameraEntry 7 }

cameraIndex OBJECT-TYPE
    SYNTAX     Counter32
    MAX-ACCESS read-only
    STATUS     current
    DESCRIPTION
        "The index of the physical enclosure."
    ::= { cameraEntry 8 }

cameraMotionSensorTable OBJECT-TYPE
    SYNTAX     SEQUENCE OF CameraMotionSensorEntry
    MAX-ACCESS not-accessible
    STATUS     current
    DESCRIPTION
        "A list of camera motion sensor entries."
    ::= { netBotzStateSensors 3 }

cameraMotionSensorEntry OBJECT-TYPE
    SYNTAX     CameraMotionSensorEntry
    MAX-ACCESS not-accessible
    STATUS     current
    DESCRIPTION
        "Camera motion sensor entry."
    INDEX { cameraMotionSensorIndex }
    ::= { cameraMotionSensorTable 1 }

CameraMotionSensorEntry ::= SEQUENCE {
    cameraMotionSensorId                      DisplayString,
    cameraMotionSensorValue                   INTEGER,
    cameraMotionSensorErrorStatus             ErrorStatus,
    cameraMotionSensorLabel                   DisplayString,
    cameraMotionSensorEncId                   DisplayString,
    cameraMotionSensorPortId                  DisplayString,
    cameraMotionSensorValueStr                DisplayString,
    cameraMotionSensorIndex                   Counter32
}

cameraMotionSensorId OBJECT-TYPE
    SYNTAX     DisplayString (SIZE (0..127))
    MAX-ACCESS read-only
    STATUS     current
    DESCRIPTION
        "The unique id of the sensor."
    ::= { cameraMotionSensorEntry 1 }

cameraMotionSensorValue OBJECT-TYPE
    SYNTAX     INTEGER {  undefined (-1), noMotion(0), motionDetected(1) }
    MAX-ACCESS read-only
    STATUS     current
    DESCRIPTION
        "Whether motion is detected by the camera sensor."
    ::= { cameraMotionSensorEntry 2 }

cameraMotionSensorErrorStatus OBJECT-TYPE
    SYNTAX     ErrorStatus
    MAX-ACCESS read-only
    STATUS     current
    DESCRIPTION
        "The operational status of the sensor.  If there are no error conditions
         reported for the sensor, the status is normal.  Otherwise, the status is
         reported as the severity value of the highest severity error condition
         that is not resolved for the sensor."
    ::= { cameraMotionSensorEntry 3 }

cameraMotionSensorLabel OBJECT-TYPE
    SYNTAX     DisplayString
    MAX-ACCESS read-only
    STATUS     current
    DESCRIPTION
        "The unique label assigned to the sensor."
    ::= { cameraMotionSensorEntry 4 }

cameraMotionSensorEncId OBJECT-TYPE
    SYNTAX     DisplayString (SIZE (0..127))
    MAX-ACCESS read-only
    STATUS     current
    DESCRIPTION
        "The id of the physical enclosure containing the sensor."
    ::= { cameraMotionSensorEntry 5 }

cameraMotionSensorPortId OBJECT-TYPE
    SYNTAX     DisplayString (SIZE (0..127))
    MAX-ACCESS read-only
    STATUS     current
    DESCRIPTION
        "The id of the port the sensor is plugged into (or empty string
         if it is not plugged into a port)."
    ::= { cameraMotionSensorEntry 6 }

cameraMotionSensorValueStr OBJECT-TYPE
    SYNTAX     DisplayString
    MAX-ACCESS read-only
    STATUS     current
    DESCRIPTION
        "The enum value label for the state reported by the sensor."
    ::= { cameraMotionSensorEntry 7 }

cameraMotionSensorIndex OBJECT-TYPE
    SYNTAX     Counter32
    MAX-ACCESS read-only
    STATUS     current
    DESCRIPTION
        "The index of the sensor."
    ::= { cameraMotionSensorEntry 8 }

otherStateSensorTable OBJECT-TYPE
    SYNTAX     SEQUENCE OF OtherStateSensorEntry
    MAX-ACCESS not-accessible
    STATUS     current
    DESCRIPTION
        "A list of other state sensor entries."
    ::= { netBotzStateSensors 10 }

otherStateSensorEntry OBJECT-TYPE
    SYNTAX     OtherStateSensorEntry
    MAX-ACCESS not-accessible
    STATUS     current
    DESCRIPTION
        "Other state sensor entry."
    INDEX { otherStateSensorIndex }
    ::= { otherStateSensorTable 1 }

OtherStateSensorEntry ::= SEQUENCE {
    otherStateSensorId                      DisplayString,
    otherStateSensorValue                   Integer32,
    otherStateSensorErrorStatus             ErrorStatus,
    otherStateSensorLabel                   DisplayString,
    otherStateSensorEncId                   DisplayString,
    otherStateSensorPortId                  DisplayString,
    otherStateSensorValueStr                DisplayString,
    otherStateSensorIndex                   Counter32
}

otherStateSensorId OBJECT-TYPE
    SYNTAX     DisplayString (SIZE (0..127))
    MAX-ACCESS read-only
    STATUS     current
    DESCRIPTION
        "The unique id of the sensor."
    ::= { otherStateSensorEntry 1 }

otherStateSensorValue OBJECT-TYPE
    SYNTAX     Integer32
    MAX-ACCESS read-only
    STATUS     current
    DESCRIPTION
        "State value reported by the sensor."
    ::= { otherStateSensorEntry 2 }

otherStateSensorErrorStatus OBJECT-TYPE
    SYNTAX     ErrorStatus
    MAX-ACCESS read-only
    STATUS     current
    DESCRIPTION
        "The operational status of the sensor.  If there are no error conditions
         reported for the sensor, the status is normal.  Otherwise, the status is
         reported as the severity value of the highest severity error condition
         that is not resolved for the sensor."
    ::= { otherStateSensorEntry 3 }

otherStateSensorLabel OBJECT-TYPE
    SYNTAX     DisplayString
    MAX-ACCESS read-only
    STATUS     current
    DESCRIPTION
        "The unique label assigned to the sensor."
    ::= { otherStateSensorEntry 4 }

otherStateSensorEncId OBJECT-TYPE
    SYNTAX     DisplayString (SIZE (0..127))
    MAX-ACCESS read-only
    STATUS     current
    DESCRIPTION
        "The id of the physical enclosure containing the sensor."
    ::= { otherStateSensorEntry 5 }

otherStateSensorPortId OBJECT-TYPE
    SYNTAX     DisplayString (SIZE (0..127))
    MAX-ACCESS read-only
    STATUS     current
    DESCRIPTION
        "The id of port the sensor is plugged into (or empty string
         if it is not plugged into a port)."
    ::= { otherStateSensorEntry 6 }

otherStateSensorValueStr OBJECT-TYPE
    SYNTAX     DisplayString
    MAX-ACCESS read-only
    STATUS     current
    DESCRIPTION
        "The enum value label for the state reported by the sensor."
    ::= { otherStateSensorEntry 7 }

otherStateSensorIndex OBJECT-TYPE
    SYNTAX     Counter32
    MAX-ACCESS read-only
    STATUS     current
    DESCRIPTION
        "The index of the sensor."
    ::= { otherStateSensorEntry 8 }


-- Vibration Sensor
--

vibrationSensorTable OBJECT-TYPE
    SYNTAX     SEQUENCE OF VibrationSensorEntry
    MAX-ACCESS not-accessible
    STATUS     current
    DESCRIPTION
        "A list of vibration sensor entries."
    ::= { netBotzStateSensors 11 }


vibrationSensorEntry OBJECT-TYPE
    SYNTAX     VibrationSensorEntry
    MAX-ACCESS not-accessible
    STATUS     current
    DESCRIPTION
        "Vibration sensor entry."
    INDEX { vibrationSensorIndex }
    ::= { vibrationSensorTable 1 }

VibrationSensorEntry ::= SEQUENCE {
    vibrationSensorId                      DisplayString,
    vibrationSensorValue                   INTEGER,
    vibrationSensorErrorStatus             ErrorStatus,
    vibrationSensorLabel                   DisplayString,
    vibrationSensorEncId                   DisplayString,
    vibrationSensorPortId                  DisplayString,
    vibrationSensorValueStr                DisplayString,
    vibrationSensorIndex                   Counter32
}

vibrationSensorId OBJECT-TYPE
    SYNTAX     DisplayString (SIZE (0..127))
    MAX-ACCESS read-only
    STATUS     current
    DESCRIPTION
        "The unique id of the sensor."
    ::= { vibrationSensorEntry 1 }

vibrationSensorValue OBJECT-TYPE
    SYNTAX     INTEGER {  undefined(-1), noVibration(0), vibrationDetected(1) }
    MAX-ACCESS read-only
    STATUS     current
    DESCRIPTION
        "Whether vibration is detected."
    ::= { vibrationSensorEntry 2 }

vibrationSensorErrorStatus OBJECT-TYPE
    SYNTAX     ErrorStatus
    MAX-ACCESS read-only
    STATUS     current
    DESCRIPTION
        "The operational status of the sensor.  If there are no error conditions
         reported for the sensor, the status is normal.  Otherwise, the status is
         reported as the severity value of the highest severity error condition
         that is not resolved for the sensor."
    ::= { vibrationSensorEntry 3 }

vibrationSensorLabel OBJECT-TYPE
    SYNTAX     DisplayString
    MAX-ACCESS read-only
    STATUS     current
    DESCRIPTION
        "The unique label assigned to the sensor."
    ::= { vibrationSensorEntry 4 }

vibrationSensorEncId OBJECT-TYPE
    SYNTAX     DisplayString (SIZE (0..127))
    MAX-ACCESS read-only
    STATUS     current
    DESCRIPTION
        "The id of the physical enclosure containing the sensor."
    ::= { vibrationSensorEntry 5 }

vibrationSensorPortId OBJECT-TYPE
    SYNTAX     DisplayString (SIZE (0..127))
    MAX-ACCESS read-only
    STATUS     current
    DESCRIPTION
        "The id of the port the sensor is plugged into (or empty string
         if it is not plugged into a port)."
    ::= { vibrationSensorEntry 6 }

vibrationSensorValueStr OBJECT-TYPE
    SYNTAX     DisplayString
    MAX-ACCESS read-only
    STATUS     current
    DESCRIPTION
        "The enum value label for the state reported by the sensor."
    ::= { vibrationSensorEntry 7 }

vibrationSensorIndex OBJECT-TYPE
    SYNTAX     Counter32
    MAX-ACCESS read-only
    STATUS     current
    DESCRIPTION
        "The index of the sensor."
    ::= { vibrationSensorEntry 8 }


-- Smoke Sensor
--

smokeSensorTable OBJECT-TYPE
    SYNTAX     SEQUENCE OF SmokeSensorEntry
    MAX-ACCESS not-accessible
    STATUS     current
    DESCRIPTION
        "A list of smoke sensor entries."
    ::= { netBotzStateSensors 12 }

smokeSensorEntry OBJECT-TYPE
    SYNTAX     SmokeSensorEntry
    MAX-ACCESS not-accessible
    STATUS     current
    DESCRIPTION
        "Smoke sensor entry."
    INDEX { smokeSensorIndex }
    ::= { smokeSensorTable 1 }

SmokeSensorEntry ::= SEQUENCE {
    smokeSensorId                      DisplayString,
    smokeSensorValue                   INTEGER,
    smokeSensorErrorStatus             ErrorStatus,
    smokeSensorLabel                   DisplayString,
    smokeSensorEncId                   DisplayString,
    smokeSensorPortId                  DisplayString,
    smokeSensorValueStr                DisplayString,
    smokeSensorIndex                   Counter32
}

smokeSensorId OBJECT-TYPE
    SYNTAX     DisplayString (SIZE (0..127))
    MAX-ACCESS read-only
    STATUS     current
    DESCRIPTION
        "The unique id of the sensor."
    ::= { smokeSensorEntry 1 }

smokeSensorValue OBJECT-TYPE
    SYNTAX     INTEGER {  undefined(-1), noSmoke(0), smokeDetected(1) }
    MAX-ACCESS read-only
    STATUS     current
    DESCRIPTION
        "Whether smoke is detected."
    ::= { smokeSensorEntry 2 }

smokeSensorErrorStatus OBJECT-TYPE
    SYNTAX     ErrorStatus
    MAX-ACCESS read-only
    STATUS     current
    DESCRIPTION
        "The operational status of the sensor.  If there are no error conditions
         reported for the sensor, the status is normal.  Otherwise, the status is
         reported as the severity value of the highest severity error condition
         that is not resolved for the sensor."
    ::= { smokeSensorEntry 3 }

smokeSensorLabel OBJECT-TYPE
    SYNTAX     DisplayString
    MAX-ACCESS read-only
    STATUS     current
    DESCRIPTION
        "The unique label assigned to the sensor."
    ::= { smokeSensorEntry 4 }

smokeSensorEncId OBJECT-TYPE
    SYNTAX     DisplayString (SIZE (0..127))
    MAX-ACCESS read-only
    STATUS     current
    DESCRIPTION
        "The id of the physical enclosure containing the sensor."
    ::= { smokeSensorEntry 5 }

smokeSensorPortId OBJECT-TYPE
    SYNTAX     DisplayString (SIZE (0..127))
    MAX-ACCESS read-only
    STATUS     current
    DESCRIPTION
        "The id of the port the sensor is plugged into (or empty string
         if it is not plugged into a port)."
    ::= { smokeSensorEntry 6 }

smokeSensorValueStr OBJECT-TYPE
    SYNTAX     DisplayString
    MAX-ACCESS read-only
    STATUS     current
    DESCRIPTION
        "The enum value label for the state reported by the sensor."
    ::= { smokeSensorEntry 7 }

smokeSensorIndex OBJECT-TYPE
    SYNTAX     Counter32
    MAX-ACCESS read-only
    STATUS     current
    DESCRIPTION
        "The index of the sensor."
    ::= { smokeSensorEntry 8 }


-- Leak Sensors
--

leakSensorTable OBJECT-TYPE
    SYNTAX     SEQUENCE OF LeakSensorEntry
    MAX-ACCESS not-accessible
    STATUS     current
    DESCRIPTION
        "A list of leak sensor entries."
    ::= { netBotzStateSensors 13 }

leakSensorEntry OBJECT-TYPE
    SYNTAX     LeakSensorEntry
    MAX-ACCESS not-accessible
    STATUS     current
    DESCRIPTION
        "Leak sensor entry."
    INDEX { leakSensorIndex }
    ::= { leakSensorTable 1 }

LeakSensorEntry ::= SEQUENCE {
    leakSensorId                      DisplayString,
    leakSensorValue                   INTEGER,
    leakSensorErrorStatus             ErrorStatus,
    leakSensorLabel                   DisplayString,
    leakSensorEncId                   DisplayString,
    leakSensorPortId                  DisplayString,
    leakSensorValueStr                DisplayString,
    leakSensorIndex                   Counter32
}

leakSensorId OBJECT-TYPE
    SYNTAX     DisplayString (SIZE (0..127))
    MAX-ACCESS read-only
    STATUS     current
    DESCRIPTION
        "The unique id of the sensor."
    ::= { leakSensorEntry 1 }

leakSensorValue OBJECT-TYPE
    SYNTAX     INTEGER {  undefined(-1), noLeak(0), leakDetected(1) }
    MAX-ACCESS read-only
    STATUS     current
    DESCRIPTION
        "Whether a leak is detected."
    ::= { leakSensorEntry 2 }

leakSensorErrorStatus OBJECT-TYPE
    SYNTAX     ErrorStatus
    MAX-ACCESS read-only
    STATUS     current
    DESCRIPTION
        "The operational status of the sensor.  If there are no error conditions
         reported for the sensor, the status is normal.  Otherwise, the status is
         reported as the severity value of the highest severity error condition
         that is not resolved for the sensor."
    ::= { leakSensorEntry 3 }

leakSensorLabel OBJECT-TYPE
    SYNTAX     DisplayString
    MAX-ACCESS read-only
    STATUS     current
    DESCRIPTION
        "The unique label assigned to the sensor."
    ::= { leakSensorEntry 4 }

leakSensorEncId OBJECT-TYPE
    SYNTAX     DisplayString (SIZE (0..127))
    MAX-ACCESS read-only
    STATUS     current
    DESCRIPTION
        "The id of the physical enclosure containing the sensor."
    ::= { leakSensorEntry 5 }

leakSensorPortId OBJECT-TYPE
    SYNTAX     DisplayString (SIZE (0..127))
    MAX-ACCESS read-only
    STATUS     current
    DESCRIPTION
        "The id of the port the sensor is plugged into (or empty string
         if it is not plugged into a port)."
    ::= { leakSensorEntry 6 }

leakSensorValueStr OBJECT-TYPE
    SYNTAX     DisplayString
    MAX-ACCESS read-only
    STATUS     current
    DESCRIPTION
        "The enum value label for the state reported by the sensor."
    ::= { leakSensorEntry 7 }

leakSensorIndex OBJECT-TYPE
    SYNTAX     Counter32
    MAX-ACCESS read-only
    STATUS     current
    DESCRIPTION
        "The index of the sensor."
    ::= { leakSensorEntry 8 }

-- Beacon
--

beaconTable OBJECT-TYPE
    SYNTAX     SEQUENCE OF BeaconEntry
    MAX-ACCESS not-accessible
    STATUS     current
    DESCRIPTION
        "A list of beacon entries."
    ::= { netBotzStateSensors 14 }

beaconEntry OBJECT-TYPE
    SYNTAX     BeaconEntry
    MAX-ACCESS not-accessible
    STATUS     current
    DESCRIPTION
        "Beacon entry."
    INDEX { beaconIndex }
    ::= { beaconTable 1 }

BeaconEntry ::= SEQUENCE {
    beaconId                      DisplayString,
    beaconValue                   INTEGER,
    beaconErrorStatus             ErrorStatus,
    beaconLabel                   DisplayString,
    beaconEncId                   DisplayString,
    beaconPortId                  DisplayString,
    beaconValueStr                DisplayString,
    beaconIndex                   Counter32
}

beaconId OBJECT-TYPE
    SYNTAX     DisplayString (SIZE (0..127))
    MAX-ACCESS read-only
    STATUS     current
    DESCRIPTION
        "The unique id of the beacon."
    ::= { beaconEntry 1 }

beaconValue OBJECT-TYPE
    SYNTAX     INTEGER {  undefined(-1), off(0), on(1) }
    MAX-ACCESS read-only
    STATUS     current
    DESCRIPTION
        "Whether the beacon is flashing."
    ::= { beaconEntry 2 }

beaconErrorStatus OBJECT-TYPE
    SYNTAX     ErrorStatus
    MAX-ACCESS read-only
    STATUS     current
    DESCRIPTION
        "The operational status of the beacon.  If there are no error conditions
         reported for the beacon, the status is normal.  Otherwise, the status is
         reported as the severity value of the highest severity error condition
         that is not resolved for the beacon."
    ::= { beaconEntry 3 }

beaconLabel OBJECT-TYPE
    SYNTAX     DisplayString
    MAX-ACCESS read-only
    STATUS     current
    DESCRIPTION
        "The unique label assigned to the beacon."
    ::= { beaconEntry 4 }

beaconEncId OBJECT-TYPE
    SYNTAX     DisplayString (SIZE (0..127))
    MAX-ACCESS read-only
    STATUS     current
    DESCRIPTION
        "The id of the physical enclosure containing the beacon."
    ::= { beaconEntry 5 }

beaconPortId OBJECT-TYPE
    SYNTAX     DisplayString (SIZE (0..127))
    MAX-ACCESS read-only
    STATUS     current
    DESCRIPTION
        "The id of the port the beacon is plugged into (or empty string
         if it is not plugged into a port)."
    ::= { beaconEntry 6 }

beaconValueStr OBJECT-TYPE
    SYNTAX     DisplayString
    MAX-ACCESS read-only
    STATUS     current
    DESCRIPTION
        "The enum value label for the state reported by the beacon."
    ::= { beaconEntry 7 }

beaconIndex OBJECT-TYPE
    SYNTAX     Counter32
    MAX-ACCESS read-only
    STATUS     current
    DESCRIPTION
        "The index of the beacon."
    ::= { beaconEntry 8 }


-- Switched Outlet
--

switchedOutletTable OBJECT-TYPE
    SYNTAX     SEQUENCE OF SwitchedOutletEntry
    MAX-ACCESS not-accessible
    STATUS     current
    DESCRIPTION
        "A list of switched outlet entries."
    ::= { netBotzStateSensors 15 }

switchedOutletEntry OBJECT-TYPE
    SYNTAX     SwitchedOutletEntry
    MAX-ACCESS not-accessible
    STATUS     current
    DESCRIPTION
        "Switched outlet entry."
    INDEX { switchedOutletIndex }
    ::= { switchedOutletTable 1 }

SwitchedOutletEntry ::= SEQUENCE {
    switchedOutletId                      DisplayString,
    switchedOutletValue                   INTEGER,
    switchedOutletErrorStatus             ErrorStatus,
    switchedOutletLabel                   DisplayString,
    switchedOutletEncId                   DisplayString,
    switchedOutletPortId                  DisplayString,
    switchedOutletValueStr                DisplayString,
    switchedOutletIndex                   Counter32
}

switchedOutletId OBJECT-TYPE
    SYNTAX     DisplayString (SIZE (0..127))
    MAX-ACCESS read-only
    STATUS     current
    DESCRIPTION
        "The unique id of the switched outlet."
    ::= { switchedOutletEntry 1 }

switchedOutletValue OBJECT-TYPE
    SYNTAX     INTEGER { undefined(-1), off(0), on(1) }
    MAX-ACCESS read-only
    STATUS     current
    DESCRIPTION
        "Whether the switched outlet is on or off."
    ::= { switchedOutletEntry 2 }

switchedOutletErrorStatus OBJECT-TYPE
    SYNTAX     ErrorStatus
    MAX-ACCESS read-only
    STATUS     current
    DESCRIPTION
        "The operational status of the switched outlet.  If there are no error conditions
         reported for the switched outlet, the status is normal.  Otherwise, the status is
         reported as the severity value of the highest severity error condition
         that is not resolved for the switched outlet."
    ::= { switchedOutletEntry 3 }

switchedOutletLabel OBJECT-TYPE
    SYNTAX     DisplayString
    MAX-ACCESS read-only
    STATUS     current
    DESCRIPTION
        "The unique label assigned to the switched outlet."
    ::= { switchedOutletEntry 4 }

switchedOutletEncId OBJECT-TYPE
    SYNTAX     DisplayString (SIZE (0..127))
    MAX-ACCESS read-only
    STATUS     current
    DESCRIPTION
        "The id of the physical enclosure containing the switched outlet."
    ::= { switchedOutletEntry 5 }

switchedOutletPortId OBJECT-TYPE
    SYNTAX     DisplayString (SIZE (0..127))
    MAX-ACCESS read-only
    STATUS     current
    DESCRIPTION
        "The id of the port the switched outlet is plugged into (or empty string
         if it is not plugged into a port)."
    ::= { switchedOutletEntry 6 }

switchedOutletValueStr OBJECT-TYPE
    SYNTAX     DisplayString
    MAX-ACCESS read-only
    STATUS     current
    DESCRIPTION
        "The enum value label for the state reported by the switchedOutlet."
    ::= { switchedOutletEntry 7 }

switchedOutletIndex OBJECT-TYPE
    SYNTAX     Counter32
    MAX-ACCESS read-only
    STATUS     current
    DESCRIPTION
        "The index of the switched outlet."
    ::= { switchedOutletEntry 8 }

 -- door lock

doorLockSensorTable OBJECT-TYPE
    SYNTAX     SEQUENCE OF DoorLockSensorEntry
    MAX-ACCESS not-accessible
    STATUS     current
    DESCRIPTION
        "A list of door lock sensor entries."
    ::= { netBotzStateSensors 16 }

doorLockSensorEntry OBJECT-TYPE
    SYNTAX     DoorLockSensorEntry
    MAX-ACCESS not-accessible
    STATUS     current
    DESCRIPTION
        "Door lock sensor entry."
    INDEX { doorLockSensorIndex }
    ::= { doorLockSensorTable 1 }

DoorLockSensorEntry ::= SEQUENCE {
    doorLockSensorId                      DisplayString,
    doorLockSensorValue                   INTEGER,
    doorLockSensorErrorStatus             ErrorStatus,
    doorLockSensorLabel                   DisplayString,
    doorLockSensorEncId                   DisplayString,
    doorLockSensorPortId                  DisplayString,
    doorLockSensorValueStr                DisplayString,
    doorLockSensorIndex                   Counter32
}

doorLockSensorId OBJECT-TYPE
    SYNTAX     DisplayString (SIZE (0..127))
    MAX-ACCESS read-only
    STATUS     current
    DESCRIPTION
        "The unique id of the sensor."
    ::= { doorLockSensorEntry 1 }

doorLockSensorValue OBJECT-TYPE
    SYNTAX     INTEGER {  undefined(-1), unlocked(0), locked(1) }
    MAX-ACCESS read-write
    STATUS     current
    DESCRIPTION
        "When setting this object only unlocked(0) or locked(1) is valid."
    ::= { doorLockSensorEntry 2 }

doorLockSensorErrorStatus OBJECT-TYPE
    SYNTAX     ErrorStatus
    MAX-ACCESS read-only
    STATUS     current
    DESCRIPTION
        "The operational status of the sensor.  If there are no error conditions
         reported for the sensor, the status is normal.  Otherwise, the status is
         reported as the severity value of the highest severity error condition
         that is not resolved for the sensor."
    ::= { doorLockSensorEntry 3 }

doorLockSensorLabel OBJECT-TYPE
    SYNTAX     DisplayString
    MAX-ACCESS read-only
    STATUS     current
    DESCRIPTION
        "The unique label assigned to the sensor."
    ::= { doorLockSensorEntry 4 }

doorLockSensorEncId OBJECT-TYPE
    SYNTAX     DisplayString (SIZE (0..127))
    MAX-ACCESS read-only
    STATUS     current
    DESCRIPTION
        "The id of the physical enclosure containing the sensor."
    ::= { doorLockSensorEntry 5 }

doorLockSensorPortId OBJECT-TYPE
    SYNTAX     DisplayString (SIZE (0..127))
    MAX-ACCESS read-only
    STATUS     current
    DESCRIPTION
        "The id of the port the sensor is plugged into (or empty string
         if it is not plugged into a port)."
    ::= { doorLockSensorEntry 6 }

doorLockSensorValueStr OBJECT-TYPE
    SYNTAX     DisplayString
    MAX-ACCESS read-only
    STATUS     current
    DESCRIPTION
        "The enum value label for the state reported by the sensor."
    ::= { doorLockSensorEntry 7 }

doorLockSensorIndex OBJECT-TYPE
    SYNTAX     Counter32
    MAX-ACCESS read-only
    STATUS     current
    DESCRIPTION
        "The index of the sensor."
    ::= { doorLockSensorEntry 8 }

-- rack handle
rackHandleSensorTable OBJECT-TYPE
    SYNTAX     SEQUENCE OF RackHandleSensorEntry
    MAX-ACCESS not-accessible
    STATUS     current
    DESCRIPTION
        "A list of rack handle sensor entries."
    ::= { netBotzStateSensors 17 }

rackHandleSensorEntry OBJECT-TYPE
    SYNTAX     RackHandleSensorEntry
    MAX-ACCESS not-accessible
    STATUS     current
    DESCRIPTION
        "Rack door handle sensor entry."
    INDEX { rackHandleSensorIndex }
    ::= { rackHandleSensorTable 1 }

RackHandleSensorEntry ::= SEQUENCE {
    rackHandleSensorId                      DisplayString,
    rackHandleSensorValue                   INTEGER,
    rackHandleSensorErrorStatus             ErrorStatus,
    rackHandleSensorLabel                   DisplayString,
    rackHandleSensorEncId                   DisplayString,
    rackHandleSensorPortId                  DisplayString,
    rackHandleSensorValueStr                DisplayString,
    rackHandleSensorIndex                   Counter32
}

rackHandleSensorId OBJECT-TYPE
    SYNTAX     DisplayString (SIZE (0..127))
    MAX-ACCESS read-only
    STATUS     current
    DESCRIPTION
        "The unique id of the sensor."
    ::= { rackHandleSensorEntry 1 }

rackHandleSensorValue OBJECT-TYPE
    SYNTAX     INTEGER {  undefined(-1), open(0), closed(1) }
    MAX-ACCESS read-only
    STATUS     current
    DESCRIPTION
        "Whether the door is open or closed."
    ::= { rackHandleSensorEntry 2 }

rackHandleSensorErrorStatus OBJECT-TYPE
    SYNTAX     ErrorStatus
    MAX-ACCESS read-only
    STATUS     current
    DESCRIPTION
        "The operational status of the sensor.  If there are no error conditions
         reported for the sensor, the status is normal.  Otherwise, the status is
         reported as the severity value of the highest severity error condition
         that is not resolved for the sensor."
    ::= { rackHandleSensorEntry 3 }

rackHandleSensorLabel OBJECT-TYPE
    SYNTAX     DisplayString
    MAX-ACCESS read-only
    STATUS     current
    DESCRIPTION
        "The unique label assigned to the sensor."
    ::= { rackHandleSensorEntry 4 }

rackHandleSensorEncId OBJECT-TYPE
    SYNTAX     DisplayString (SIZE (0..127))
    MAX-ACCESS read-only
    STATUS     current
    DESCRIPTION
        "The id of the physical enclosure containing the sensor."
    ::= { rackHandleSensorEntry 5 }

rackHandleSensorPortId OBJECT-TYPE
    SYNTAX     DisplayString (SIZE (0..127))
    MAX-ACCESS read-only
    STATUS     current
    DESCRIPTION
        "The id of the port the sensor is plugged into (or empty string
         if it is not plugged into a port)."
    ::= { rackHandleSensorEntry 6 }

rackHandleSensorValueStr OBJECT-TYPE
    SYNTAX     DisplayString
    MAX-ACCESS read-only
    STATUS     current
    DESCRIPTION
        "The enum value label for the state reported by the sensor."
    ::= { rackHandleSensorEntry 7 }

rackHandleSensorIndex OBJECT-TYPE
    SYNTAX     Counter32
    MAX-ACCESS read-only
    STATUS     current
    DESCRIPTION
        "The index of the sensor."
    ::= { rackHandleSensorEntry 8 }

-- output relay
outputRelaySensorTable OBJECT-TYPE
    SYNTAX     SEQUENCE OF OutputRelaySensorEntry
    MAX-ACCESS not-accessible
    STATUS     current
    DESCRIPTION
        "A list of output relay entries."
    ::= { netBotzStateSensors 18 }

outputRelaySensorEntry OBJECT-TYPE
    SYNTAX     OutputRelaySensorEntry
    MAX-ACCESS not-accessible
    STATUS     current
    DESCRIPTION
        "Output relay sensor entry."
    INDEX { outputRelaySensorIndex }
    ::= { outputRelaySensorTable 1 }

OutputRelaySensorEntry ::= SEQUENCE {
    outputRelaySensorId                      DisplayString,
    outputRelaySensorValue                   INTEGER,
    outputRelaySensorErrorStatus             ErrorStatus,
    outputRelaySensorLabel                   DisplayString,
    outputRelaySensorEncId                   DisplayString,
    outputRelaySensorPortId                  DisplayString,
    outputRelaySensorValueStr                DisplayString,
    outputRelaySensorIndex                   Counter32
}

outputRelaySensorId OBJECT-TYPE
    SYNTAX     DisplayString (SIZE (0..127))
    MAX-ACCESS read-only
    STATUS     current
    DESCRIPTION
        "The unique id of the sensor."
    ::= { outputRelaySensorEntry 1 }

outputRelaySensorValue OBJECT-TYPE
    SYNTAX     INTEGER {  undefined(-1), open(0), closed(1) }
    MAX-ACCESS read-only
    STATUS     current
    DESCRIPTION
        "Whether the relay is open or closed."
    ::= { outputRelaySensorEntry 2 }

outputRelaySensorErrorStatus OBJECT-TYPE
    SYNTAX     ErrorStatus
    MAX-ACCESS read-only
    STATUS     current
    DESCRIPTION
        "The operational status of the sensor.  If there are no error conditions
         reported for the sensor, the status is normal.  Otherwise, the status is
         reported as the severity value of the highest severity error condition
         that is not resolved for the sensor."
    ::= { outputRelaySensorEntry 3 }

outputRelaySensorLabel OBJECT-TYPE
    SYNTAX     DisplayString
    MAX-ACCESS read-only
    STATUS     current
    DESCRIPTION
        "The unique label assigned to the sensor."
    ::= { outputRelaySensorEntry 4 }

outputRelaySensorEncId OBJECT-TYPE
    SYNTAX     DisplayString (SIZE (0..127))
    MAX-ACCESS read-only
    STATUS     current
    DESCRIPTION
        "The id of the physical enclosure containing the sensor."
    ::= { outputRelaySensorEntry 5 }

outputRelaySensorPortId OBJECT-TYPE
    SYNTAX     DisplayString (SIZE (0..127))
    MAX-ACCESS read-only
    STATUS     current
    DESCRIPTION
        "The id of the port the sensor is plugged into (or empty string
         if it is not plugged into a port)."
    ::= { outputRelaySensorEntry 6 }

outputRelaySensorValueStr OBJECT-TYPE
    SYNTAX     DisplayString
    MAX-ACCESS read-only
    STATUS     current
    DESCRIPTION
        "The enum value label for the state reported by the sensor."
    ::= { outputRelaySensorEntry 7 }

outputRelaySensorIndex OBJECT-TYPE
    SYNTAX     Counter32
    MAX-ACCESS read-only
    STATUS     current
    DESCRIPTION
        "The index of the sensor."
    ::= { outputRelaySensorEntry 8 }
-- Error Conditions Group
--

errorCondTable OBJECT-TYPE
    SYNTAX     SEQUENCE OF ErrorCondEntry
    MAX-ACCESS not-accessible
    STATUS     current
    DESCRIPTION
        "A list of active and resolved error conditions."
    ::= { netBotzErrors 1 }

errorCondEntry OBJECT-TYPE
    SYNTAX     ErrorCondEntry
    MAX-ACCESS not-accessible
    STATUS     current
    DESCRIPTION
        "Error condition entry."
    INDEX { errorCondIndex }
    ::= { errorCondTable 1 }

ErrorCondEntry ::= SEQUENCE {
    errorCondId                          DisplayString,
    errorCondSeverity                    ErrorStatus,
    errorCondTypeId                      DisplayString,
    errorCondStartTime                   DateAndTime,
    errorCondStartTimeStr                DisplayString,
    errorCondResolved                    BoolValue,
    errorCondResolvedTime                DateAndTime,
    errorCondResolvedTimeStr             DisplayString,
    errorCondEncId                       DisplayString,
    errorCondPortId                      DisplayString,
    errorCondSensorId                    DisplayString,
    errorCondIndex                       Counter32
}

errorCondId    OBJECT-TYPE
    SYNTAX     DisplayString (SIZE (0..127))
    MAX-ACCESS read-only
    STATUS     current
    DESCRIPTION
        "The unique id of the error condition."
    ::= { errorCondEntry 1 }

errorCondSeverity OBJECT-TYPE
    SYNTAX     ErrorStatus
    MAX-ACCESS read-only
    STATUS     current
    DESCRIPTION
        "The relative severity of the error condition."
    ::= { errorCondEntry 2 }

errorCondTypeId  OBJECT-TYPE
    SYNTAX     DisplayString (SIZE (0..127))
    MAX-ACCESS read-only
    STATUS     current
    DESCRIPTION
        "The error type id reported for the error condition."
    ::= { errorCondEntry 3 }

errorCondStartTime OBJECT-TYPE
    SYNTAX     DateAndTime
    MAX-ACCESS read-only
    STATUS     current
    DESCRIPTION
        "The start time of the error condition, in msec since 1/1/1970."
    ::= { errorCondEntry 4 }

errorCondStartTimeStr OBJECT-TYPE
    SYNTAX     DisplayString
    MAX-ACCESS read-only
    STATUS     current
    DESCRIPTION
        "The start time of the error condition, as ISO date-time formatted string (UTC)."
    ::= { errorCondEntry 5 }

errorCondResolved OBJECT-TYPE
    SYNTAX     BoolValue
    MAX-ACCESS read-only
    STATUS     current
    DESCRIPTION
        "Whether the error condition was resolved."
    ::= { errorCondEntry 6 }

errorCondResolvedTime OBJECT-TYPE
    SYNTAX     DateAndTime
    MAX-ACCESS read-only
    STATUS     current
    DESCRIPTION
        "The time the error condition was resolved (if it was resolved), in msec since 1/1/1970."
    ::= { errorCondEntry 7 }

errorCondResolvedTimeStr OBJECT-TYPE
    SYNTAX     DisplayString
    MAX-ACCESS read-only
    STATUS     current
    DESCRIPTION
        "The time the error condition was resolved (if it was resolved), as ISO date-time formatted string (UTC)."
    ::= { errorCondEntry 8 }

errorCondEncId OBJECT-TYPE
    SYNTAX     DisplayString (SIZE (0..127))
    MAX-ACCESS read-only
    STATUS     current
    DESCRIPTION
        "The id of the physical enclosure associated with the error."
    ::= { errorCondEntry 9 }

errorCondPortId OBJECT-TYPE
    SYNTAX     DisplayString (SIZE (0..127))
    MAX-ACCESS read-only
    STATUS     current
    DESCRIPTION
        "The id of the port associated with the error (or empty string
         if the error is not associated with a port)."
    ::= { errorCondEntry 10 }

errorCondSensorId OBJECT-TYPE
    SYNTAX     DisplayString (SIZE (0..127))
    MAX-ACCESS read-only
    STATUS     current
    DESCRIPTION
        "The id of the sensor associated with the error (or empty string
         if the error is not associated with a sensor.)"
    ::= { errorCondEntry 11 }

errorCondIndex OBJECT-TYPE
    SYNTAX     Counter32
    MAX-ACCESS read-only
    STATUS     current
    DESCRIPTION
        "The index of the error condition."
    ::= { errorCondEntry 12 }


-- Alert specific definitions
--

netBotzTrapErrorID    OBJECT-TYPE
    SYNTAX        DisplayString (SIZE (0..127))
    MAX-ACCESS        read-only
    STATUS        current
    DESCRIPTION     "Unique ID of error condition that produced the trap"
    ::= { netBotzTrapParms 1 }

netBotzTrapErrorType    OBJECT-TYPE
    SYNTAX        DisplayString (SIZE (0..127))
    MAX-ACCESS        read-only
    STATUS        current
    DESCRIPTION     "Symbolic ID of error type"
    ::= { netBotzTrapParms 2 }


netBotzTrapErrorTypeLabel    OBJECT-TYPE
    SYNTAX        DisplayString
    MAX-ACCESS        read-only
    STATUS        current
    DESCRIPTION     "Label for error type"
    ::= { netBotzTrapParms 3 }


netBotzTrapSensorID    OBJECT-TYPE
    SYNTAX        DisplayString (SIZE (0..127))
    MAX-ACCESS        read-only
    STATUS        current
    DESCRIPTION     "ID of sensor associated with error condition that produced the trap"
    ::= { netBotzTrapParms 4 }

netBotzTrapSensorLabel    OBJECT-TYPE
    SYNTAX        DisplayString
    MAX-ACCESS        read-only
    STATUS        current
    DESCRIPTION     "Label of sensor associated with error condition that produced the trap"
    ::= { netBotzTrapParms 5 }

netBotzTrapContainerID    OBJECT-TYPE
    SYNTAX        DisplayString (SIZE (0..127))
    MAX-ACCESS        read-only
    STATUS        current
    DESCRIPTION     "ID of container associated with error condition that produced the trap"
    ::= { netBotzTrapParms 6 }

netBotzTrapContainerLabel    OBJECT-TYPE
    SYNTAX        DisplayString
    MAX-ACCESS        read-only
    STATUS        current
    DESCRIPTION     "Label of container associated with error condition that produced the trap"
    ::= { netBotzTrapParms 7 }

netBotzTrapPortID    OBJECT-TYPE
    SYNTAX        DisplayString (SIZE (0..127))
    MAX-ACCESS        read-only
    STATUS        current
    DESCRIPTION     "ID of port associated with error condition that produced the trap"
    ::= { netBotzTrapParms 8 }

netBotzTrapPortLabel    OBJECT-TYPE
    SYNTAX        DisplayString
    MAX-ACCESS        read-only
    STATUS        current
    DESCRIPTION     "Label of port associated with error condition that produced the trap"
    ::= { netBotzTrapParms 9 }

netBotzTrapStartTime    OBJECT-TYPE
    SYNTAX        DisplayString
    MAX-ACCESS        read-only
    STATUS        current
    DESCRIPTION    "Start time (in UTC seconds) for error that produced the trap"
    ::= { netBotzTrapParms 10 }

netBotzTrapNotifyTime    OBJECT-TYPE
    SYNTAX        DisplayString
    MAX-ACCESS        read-only
    STATUS        current
    DESCRIPTION    "Notification time (in UTC seconds) for error that produced the trap"
    ::= { netBotzTrapParms 11 }

netBotzTrapResolveTime    OBJECT-TYPE
    SYNTAX        DisplayString
    MAX-ACCESS        read-only
    STATUS        current
    DESCRIPTION    "Resolve time (in UTC seconds) for error that produced the trap"
    ::= { netBotzTrapParms 12 }

netBotzTrapSeverity    OBJECT-TYPE
    SYNTAX        INTEGER {
            ok(0),
            information(1),
            warning(2),
            critical(3)
            }
    MAX-ACCESS        read-only
    STATUS        current
    DESCRIPTION    "Severity of error that produced the trap"
    ::= { netBotzTrapParms 13 }

netBotzTrapSensorValue    OBJECT-TYPE
    SYNTAX        DisplayString
    MAX-ACCESS        read-only
    STATUS        current
    DESCRIPTION     "String presentation of value of sensor"
    ::= { netBotzTrapParms 14 }

netBotzTrapSensorValueInt    OBJECT-TYPE
    SYNTAX        Integer32
    MAX-ACCESS        read-only
    STATUS        current
    DESCRIPTION     "Whole integer representation of value of sensor (without decimal portion)"
    ::= { netBotzTrapParms 15 }

netBotzTrapSensorValueFraction    OBJECT-TYPE
    SYNTAX        Integer32
    MAX-ACCESS        read-only
    STATUS        current
    DESCRIPTION     "Fractional portion of value of sensor (multiplied by 1000000)"
    ::= { netBotzTrapParms 16 }


netBotzTrapData            OBJECT-TYPE
    SYNTAX        DisplayString
    MAX-ACCESS        read-only
    STATUS        current
    DESCRIPTION     "General Purpose Test Trap Data String Field"
    ::= { netBotzTrapParms 17 }



netBotzTempTooHigh NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION "Temperature sensor value too high."
    ::= { netBotzTempSensorPrefix 2 }

netBotzTempTooHighRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION "Temperature sensor value is no longer too high."
    ::= { netBotzTempSensorPrefix 102 }

netBotzTempTooLow NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION "Temperature sensor value too low."
    ::= { netBotzTempSensorPrefix 3 }

netBotzTempTooLowRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION "Temperature sensor value is no longer too low."
    ::= { netBotzTempSensorPrefix 103 }


netBotzTempUnplugged NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Temperature sensor unplugged."
    ::= { netBotzTempSensorPrefix 6 }

netBotzTempReplugged NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Temperature sensor no longer unplugged."
    ::= { netBotzTempSensorPrefix 106 }


netBotzTempError NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Temperature sensor error."
    ::= { netBotzTempSensorPrefix 1 }

netBotzTempErrorRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Temperature sensor error resolved."
    ::= { netBotzTempSensorPrefix 101 }

netBotzHumidityTooHigh NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Humidity sensor value too high."
    ::= { netBotzHumiditySensorPrefix 2 }

netBotzHumidityTooHighRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Humidity sensor value is no longer too high."
    ::= { netBotzHumiditySensorPrefix 102 }

netBotzHumidityTooLow NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Humidity sensor value too low."
    ::= { netBotzHumiditySensorPrefix 3 }

netBotzHumidityTooLowRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Humidity sensor value is no longer too low."
    ::= { netBotzHumiditySensorPrefix 103 }

netBotzHumidityUnplugged NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Humidity sensor unplugged."
    ::= { netBotzHumiditySensorPrefix 6 }

netBotzHumidityReplugged NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Humidity sensor no longer unplugged."
    ::= { netBotzHumiditySensorPrefix 106 }

netBotzHumidityError NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Humidity sensor error."
    ::= { netBotzHumiditySensorPrefix 1 }

netBotzHumidityErrorRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Humidity sensor error resolved."
    ::= { netBotzHumiditySensorPrefix 101 }

netBotzDewPointTooHigh NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "DewPoint sensor value too high."
    ::= { netBotzDewPointSensorPrefix 2 }

netBotzDewPointTooHighRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "DewPoint sensor value is no longer too high."
    ::= { netBotzDewPointSensorPrefix 102 }

netBotzDewPointTooLow NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "DewPoint sensor value too low."
    ::= { netBotzDewPointSensorPrefix 3 }

netBotzDewPointTooLowRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "DewPoint sensor value is no longer too low."
    ::= { netBotzDewPointSensorPrefix 103 }

netBotzDewPointUnplugged NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "DewPoint sensor unplugged."
    ::= { netBotzDewPointSensorPrefix 6 }

netBotzDewPointReplugged NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "DewPoint sensor no longer unplugged."
    ::= { netBotzDewPointSensorPrefix 106 }

netBotzDewPointError NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "DewPoint sensor error."
    ::= { netBotzDewPointSensorPrefix 1 }

netBotzDewPointErrorRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "DewPoint sensor error resolved."
    ::= { netBotzDewPointSensorPrefix 101 }

netBotzAirFlowTooHigh NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "AirFlow sensor value too high."
    ::= { netBotzAirFlowSensorPrefix 2 }

netBotzAirFlowTooHighRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "AirFlow sensor value is no longer too high."
    ::= { netBotzAirFlowSensorPrefix 102 }

netBotzAirFlowTooLow NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "AirFlow sensor value too low."
    ::= { netBotzAirFlowSensorPrefix 3 }

netBotzAirFlowTooLowRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "AirFlow sensor value is no longer too low."
    ::= { netBotzAirFlowSensorPrefix 103 }

netBotzAirFlowUnplugged NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "AirFlow sensor unplugged."
    ::= { netBotzAirFlowSensorPrefix 6 }

netBotzAirFlowReplugged NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "AirFlow sensor no longer unplugged."
    ::= { netBotzAirFlowSensorPrefix 106 }

netBotzAirFlowError NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "AirFlow sensor error."
    ::= { netBotzAirFlowSensorPrefix 1 }

netBotzAirFlowErrorRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "AirFlow sensor error resolved."
    ::= { netBotzAirFlowSensorPrefix 101 }



netBotzAmpDetectTooHigh NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Amp Detectsensor value too high."
    ::= { netBotzAmpDetectSensorPrefix 2 }

netBotzAmpDetectTooHighRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Amp Detectsensor value is no longer too high."
    ::= { netBotzAmpDetectSensorPrefix 102 }

netBotzAmpDetectTooLow NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Amp Detectsensor value too low."
    ::= { netBotzAmpDetectSensorPrefix 3 }

netBotzAmpDetectTooLowRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Amp Detectsensor value is no longer too low."
    ::= { netBotzAmpDetectSensorPrefix 103 }

netBotzAmpDetectUnplugged NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Amp Detectsensor unplugged."
    ::= { netBotzAmpDetectSensorPrefix 6 }

netBotzAmpDetectReplugged NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Amp Detectsensor no longer unplugged."
    ::= { netBotzAmpDetectSensorPrefix 106 }

netBotzAmpDetectError NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Amp Detectsensor error."
    ::= { netBotzAmpDetectSensorPrefix 1 }

netBotzAmpDetectErrorRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Amp Detectsensor error resolved."
    ::= { netBotzAmpDetectSensorPrefix 101 }

netBotzDryContactUnplugged NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Dry Contact sensor unplugged."
    ::= { netBotzDryContactSensorPrefix 6 }

netBotzDryContactReplugged NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Dry Contact sensor no longer unplugged."
    ::= { netBotzDryContactSensorPrefix 106 }

netBotzDryContactError NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Dry Contact sensor error."
    ::= { netBotzDryContactSensorPrefix 1 }

netBotzDryContactErrorRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Dry Contact sensor error resolved."
    ::= { netBotzDryContactSensorPrefix 101 }

netBotzDryContactValueError NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Dry Contact sensor value error."
    ::= { netBotzDryContactSensorPrefix 10 }

netBotzDryContactValueErrorRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Dry Contact sensor value error resolved."
    ::= { netBotzDryContactSensorPrefix 110 }

netBotzCameraMotionSensorUnplugged NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Camera Motion Sensor unplugged."
    ::= { netBotzCameraMotionSensorPrefix 6 }

netBotzCameraMotionSensorReplugged NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Camera Motion Sensor no longer unplugged."
    ::= { netBotzCameraMotionSensorPrefix 106 }

netBotzCameraMotionSensorError NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Camera Motion Sensor error."
    ::= { netBotzCameraMotionSensorPrefix 1 }

netBotzCameraMotionSensorErrorRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Camera Motion Sensor error resolved."
    ::= { netBotzCameraMotionSensorPrefix 101 }

netBotzCameraMotionSensorValueError NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Camera Motion Sensor value error."
    ::= { netBotzCameraMotionSensorPrefix 10 }

netBotzCameraMotionSensorValueErrorRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Camera Motion Sensor value error resolved."
    ::= { netBotzCameraMotionSensorPrefix 110 }

netBotzDoorSensorUnplugged NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Door Sensor unplugged."
    ::= { netBotzDoorSensorPrefix 6 }

netBotzDoorSensorReplugged NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Door Sensor no longer unplugged."
    ::= { netBotzDoorSensorPrefix 106 }

netBotzDoorSensorError NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Door Sensor error."
    ::= { netBotzDoorSensorPrefix 1 }

netBotzDoorSensorErrorRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Door Sensor error resolved."
    ::= { netBotzDoorSensorPrefix 101 }

netBotzDoorSensorValueError NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Door Sensor value error."
    ::= { netBotzDoorSensorPrefix 10 }

netBotzDoorSensorValueErrorRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Door Sensor value error resolved."
    ::= { netBotzDoorSensorPrefix 110 }

netBotzPodUnplugged NOTIFICATION-TYPE
    OBJECTS {
        netBotzTrapErrorID,
        netBotzTrapErrorType,
        netBotzTrapErrorTypeLabel,
        netBotzTrapContainerID,
        netBotzTrapContainerLabel,
        netBotzTrapPortID,
        netBotzTrapPortLabel,
        netBotzTrapStartTime,
        netBotzTrapNotifyTime,
        netBotzTrapResolveTime,
        netBotzTrapSeverity
        }
    STATUS        current
    DESCRIPTION
    "Pod unplugged."
    ::= { netBotzPodPrefix 7 }

netBotzPodReplugged NOTIFICATION-TYPE
    OBJECTS {
        netBotzTrapErrorID,
        netBotzTrapErrorType,
        netBotzTrapErrorTypeLabel,
        netBotzTrapContainerID,
        netBotzTrapContainerLabel,
        netBotzTrapPortID,
        netBotzTrapPortLabel,
        netBotzTrapStartTime,
        netBotzTrapNotifyTime,
        netBotzTrapResolveTime,
        netBotzTrapSeverity
        }
    STATUS        current
    DESCRIPTION
    "Pod no longer unplugged."
    ::= { netBotzPodPrefix 107 }

netBotzSensorPodUnplugged NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Sensor Pod unplugged."
    ::= { netBotzSensorPodPrefix 7 }

netBotzSensorPodReplugged NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Sensor Pod no longer unplugged."
    ::= { netBotzSensorPodPrefix 107 }

netBotzCameraUnplugged NOTIFICATION-TYPE
    OBJECTS {
        netBotzTrapErrorID,
        netBotzTrapErrorType,
        netBotzTrapErrorTypeLabel,
        netBotzTrapContainerID,
        netBotzTrapContainerLabel,
        netBotzTrapPortID,
        netBotzTrapPortLabel,
        netBotzTrapStartTime,
        netBotzTrapNotifyTime,
        netBotzTrapResolveTime,
        netBotzTrapSeverity
        }
    STATUS        current
    DESCRIPTION
    "Camera Pod unplugged."
    ::= { netBotzCameraPrefix 7 }

netBotzCameraReplugged NOTIFICATION-TYPE
    OBJECTS {
        netBotzTrapErrorID,
        netBotzTrapErrorType,
        netBotzTrapErrorTypeLabel,
        netBotzTrapContainerID,
        netBotzTrapContainerLabel,
        netBotzTrapPortID,
        netBotzTrapPortLabel,
        netBotzTrapStartTime,
        netBotzTrapNotifyTime,
        netBotzTrapResolveTime,
        netBotzTrapSeverity
        }
    STATUS        current
    DESCRIPTION
    "Camera Pod no longer unplugged."
    ::= { netBotzCameraPrefix 107 }

netBotzFourToTwentymAPodUnplugged NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "4-20mA Pod unplugged."
    ::= { netBotz4to20mAPodPrefix 7 }

netBotzFourToTwentymAPodReplugged NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "4-20mA Pod no longer unplugged."
    ::= { netBotz4to20mAPodPrefix 107 }

netBotzFourToTwentymAPodError NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "4-20mA Pod error."
    ::= { netBotz4to20mAPodPrefix 1 }

netBotzFourToTwentymAPodErrorRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "4-20mA Pod error resolved."
    ::= { netBotz4to20mAPodPrefix 101 }

netBotzFourToTwentymAPodTooLow NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "4-20mA Pod value too low."
    ::= { netBotz4to20mAPodPrefix 10 }

netBotzFourToTwentymAPodTooLowRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "4-20mA Pod value is no longer too low."
    ::= { netBotz4to20mAPodPrefix 110 }

netBotzFourToTwentymAPodTooHigh NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "4-20mA Pod value too high."
    ::= { netBotz4to20mAPodPrefix 3 }

netBotzFourToTwentymAPodTooHighRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "4-20mA Pod value is no longer too high."
    ::= { netBotz4to20mAPodPrefix 103 }

netBotzLogonError NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Multiple failed logon attempts."
    ::= { netBotzPodPrefix 11 }

netBotzLogonErrorResolved NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Failed logon attempts stopped, or logon succeeded."
    ::= { netBotzPodPrefix 111 }


netBotzRmtLinkError NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Configured remote link has failed."
    ::= { netBotzPodPrefix 13 }

netBotzRmtLinkErrorResolved NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Configured remote link has returned to normal."
    ::= { netBotzPodPrefix 113 }

netBotzWirelessStatusSensorUnplugged NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Wireless Status Sensor unplugged."
    ::= { netBotzWirelessStatusSensorPrefix 6 }

netBotzWirelessStatusSensorReplugged NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Wireless Status Sensor no longer unplugged."
    ::= { netBotzWirelessStatusSensorPrefix 106 }

netBotzWirelessStatusSensorError NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Wireless Status Sensor error."
    ::= { netBotzWirelessStatusSensorPrefix 1 }

netBotzWirelessStatusSensorErrorRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Wireless Status Sensor error resolved."
    ::= { netBotzWirelessStatusSensorPrefix 101 }

netBotzWirelessStatusSensorValueError NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Wireless Status Sensor value error."
    ::= { netBotzWirelessStatusSensorPrefix 10 }

netBotzWirelessStatusSensorValueErrorRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Wireless Status Sensor value error resolved."
    ::= { netBotzWirelessStatusSensorPrefix 110 }

netBotzOutputControlSensorUnplugged NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Output Control Sensor unplugged."
    ::= { netBotzOutputControlSensorPrefix 6 }

netBotzOutputControlSensorReplugged NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Output Control Sensor no longer unplugged."
    ::= { netBotzOutputControlSensorPrefix 106 }

netBotzOutputControlSensorError NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Output Control Sensor error."
    ::= { netBotzOutputControlSensorPrefix 1 }

netBotzOutputControlSensorErrorRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Output Control Sensor error resolved."
    ::= { netBotzOutputControlSensorPrefix 101 }

netBotzOutputControlSensorValueError NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Output Control Sensor value error."
    ::= { netBotzOutputControlSensorPrefix 10 }

netBotzOutputControlSensorValueErrorRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Output Control Sensor value error resolved."
    ::= { netBotzOutputControlSensorPrefix 110 }

netBotzLoopVoltageTooHigh NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Loop Voltage sensor value too high."
    ::= { netBotzLoopVoltageSensorPrefix 2 }

netBotzLoopVoltageTooHighRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Loop Voltage sensor value is no longer too high."
    ::= { netBotzLoopVoltageSensorPrefix 102 }

netBotzLoopVoltageTooLow NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Loop Voltage sensor value too low."
    ::= { netBotzLoopVoltageSensorPrefix 3 }

netBotzLoopVoltageTooLowRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Loop Voltage sensor value is no longer too low."
    ::= { netBotzLoopVoltageSensorPrefix 103 }

netBotzLoopVoltageUnplugged NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Loop Voltage sensor unplugged."
    ::= { netBotzLoopVoltageSensorPrefix 6 }

netBotzLoopVoltageReplugged NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Loop Voltage sensor no longer unplugged."
    ::= { netBotzLoopVoltageSensorPrefix 106 }

netBotzLoopVoltageError NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Loop Voltage sensor error."
    ::= { netBotzLoopVoltageSensorPrefix 1 }

netBotzLoopVoltageErrorRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Loop Voltage sensor error resolved."
    ::= { netBotzLoopVoltageSensorPrefix 101 }

netBotzRopeLeakSensorUnplugged NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Rope Leak Sensor unplugged."
    ::= { netBotzRopeLeakSensorPrefix 6 }

netBotzRopeLeakSensorReplugged NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Rope Leak Sensor no longer unplugged."
    ::= { netBotzRopeLeakSensorPrefix 106 }

netBotzRopeLeakSensorError NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Rope Leak Sensor error."
    ::= { netBotzRopeLeakSensorPrefix 1 }

netBotzRopeLeakSensorErrorRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Rope Leak Sensor error resolved."
    ::= { netBotzRopeLeakSensorPrefix 101 }

netBotzRopeLeakSensorValueError NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Rope Leak Sensor value error."
    ::= { netBotzRopeLeakSensorPrefix 10 }

netBotzRopeLeakSensorValueErrorRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Rope Leak Sensor value error resolved."
    ::= { netBotzRopeLeakSensorPrefix 110 }

netBotzSpotLeakSensorUnplugged NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Spot Leak Sensor unplugged."
    ::= { netBotzSpotLeakSensorPrefix 6 }

netBotzSpotLeakSensorReplugged NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Spot Leak sensor no longer unplugged."
    ::= { netBotzSpotLeakSensorPrefix 106 }

netBotzSpotLeakSensorError NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Spot Leak sensor error."
    ::= { netBotzSpotLeakSensorPrefix 1 }

netBotzSpotLeakSensorErrorRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Spot Leak sensor error resolved."
    ::= { netBotzSpotLeakSensorPrefix 101 }

netBotzSpotLeakSensorValueError NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Spot Leak sensor value error."
    ::= { netBotzSpotLeakSensorPrefix 10 }

netBotzSpotLeakSensorValueErrorRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Spot Leak sensor value error resolved."
    ::= { netBotzSpotLeakSensorPrefix 110 }

netBotzRSSITooLow NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "RSSI sensor value too low."
    ::= { netBotzRSSISensorPrefix 3 }

netBotzRSSITooLowRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "RSSI sensor value is no longer too low."
    ::= { netBotzRSSISensorPrefix 103 }

netBotzRSSISensorValueError NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "RSSI sensor value error."
    ::= { netBotzRSSISensorPrefix 10 }

netBotzRSSISensorValueErrorRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "RSSI sensor value error resolved."
    ::= { netBotzRSSISensorPrefix 110 }

netBotzBatterySensorError NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Battery Leak sensor error."
    ::= { netBotzBatterySensorPrefix 1 }

netBotzBatterySensorErrorRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Battery Leak sensor error resolved."
    ::= { netBotzBatterySensorPrefix 101 }

netBotzBatterySensorValueError NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Battery Leak sensor value error."
    ::= { netBotzBatterySensorPrefix 10 }

netBotzBatterySensorValueErrorRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Battery Leak sensor value error resolved."
    ::= { netBotzBatterySensorPrefix 110 }

netBotzBatteryTooLow NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Battery sensor value too low."
    ::= { netBotzBatterySensorPrefix 3 }

netBotzBatteryTooLowRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Battery sensor value is no longer too low."
    ::= { netBotzBatterySensorPrefix 103 }

netBotzBeaconUnplugged NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Beacon unplugged."
    ::= { netBotzBeaconPrefix 6 }

netBotzBeaconReplugged NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Beacon no longer unplugged."
    ::= { netBotzBeaconPrefix 106 }

netBotzBeaconError NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Beacon error."
    ::= { netBotzBeaconPrefix 1 }

netBotzBeaconErrorRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Beacon error resolved."
    ::= { netBotzBeaconPrefix 101 }

netBotzBeaconValueError NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Beacin value error."
    ::= { netBotzBeaconPrefix 10 }

netBotzBeaconValueErrorRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Beacon value error resolved."
    ::= { netBotzBeaconPrefix 110 }


netBotzOutletSensorError NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Outlet sensor error."
    ::= { netBotzOutletSensorPrefix 1 }

netBotzOutletSensorErrorRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Outlet sensor error resolved."
    ::= { netBotzOutletSensorPrefix 101 }

netBotzOutletSensorValueError NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Outlet sensor value error."
    ::= { netBotzOutletSensorPrefix 10 }

netBotzOutletSensorValueErrorRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Outlet sensor value error resolved."
    ::= { netBotzOutletSensorPrefix 110 }

netBotzSmokeSensorUnplugged NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Smoke sensor unplugged."
    ::= { netBotzSmokeSensorPrefix 6 }

netBotzSmokeSensorReplugged NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Smoke sensor replugged."
    ::= { netBotzSmokeSensorPrefix 106 }

netBotzSmokeSensorError NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Smoke sensor error."
    ::= { netBotzSmokeSensorPrefix 1 }

netBotzSmokeSensorErrorRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Smoke sensor error resolved."
    ::= { netBotzSmokeSensorPrefix 101 }

netBotzSmokeSensorValueError NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Smoke sensor value error."
    ::= { netBotzSmokeSensorPrefix 10 }

netBotzSmokeSensorValueErrorRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Smoke sensor value error resolved."
    ::= { netBotzSmokeSensorPrefix 110 }

netBotzVibrationSensorUnplugged NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Vibration sensor unplugged."
    ::= { netBotzVibrationSensorPrefix 6 }

netBotzVibrationSensorReplugged NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Vibration sensor replugged."
    ::= { netBotzVibrationSensorPrefix 106 }

netBotzVibrationSensorError NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Vibration sensor error."
    ::= { netBotzVibrationSensorPrefix 1 }

netBotzVibrationSensorErrorRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Vibration sensor error resolved."
    ::= { netBotzVibrationSensorPrefix 101 }

netBotzVibrationSensorValueError NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Vibration sensor value error."
    ::= { netBotzVibrationSensorPrefix 10 }

netBotzVibrationSensorValueErrorRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Vibration sensor value error resolved."
    ::= { netBotzVibrationSensorPrefix 110 }


--
-- Rack Access
--
netBotzDoorSensorForcedEntryError NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Door sensor forced entry detected. TrapErrorTypeLabel indicates rack access user label"
    ::= { netBotzRackAccessPrefix 10 }

netBotzDoorSensorForcedEntryErrorRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Door sensor forced entry returned to normal. TrapErrorTypeLabel indicates rack access user label."
    ::= { netBotzRackAccessPrefix 110 }

netBotzRackHandleSensorOpenError NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Rack handle sensor open error. TrapErrorTypeLabel indicates rack access user label."
    ::= { netBotzRackAccessPrefix 11 }
netBotzRackHandleSensorOpenErrorRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Rack handle sensor open returned to normal. TrapErrorTypeLabel indicates rack access user label."
    ::= { netBotzRackAccessPrefix 111 }

--
-- User Label info for the Authorization Failure is in the ErrorTypeLabel field
--
netBotzCardReaderLocalAuthorizationError NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction

        }
    STATUS        current
    DESCRIPTION
    "Card reader local authorization failure. TrapErrorTypeLabel indicates rack access user label."
    ::= { netBotzRackAccessPrefix 12 }

netBotzCardReaderLocalAuthorizationErrorRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Card reader local authorization succeeded. TrapErrorTypeLabel indicates rack access user label."
    ::= { netBotzRackAccessPrefix 112 }

netBotzCardReaderLdapAuthorizationError NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Card reader LDAP authorization failure. TrapErrorTypeLabel indicates rack access user label."
    ::= { netBotzRackAccessPrefix 13 }

netBotzCardReaderLdapAuthorizationErrorRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Card reader LDAP authorization succeeded. TrapErrorTypeLabel indicates rack access user label."
    ::= { netBotzRackAccessPrefix 113 }

netBotzCardReaderUnplugged NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Card reader unplugged. TrapErrorTypeLabel indicates rack access user label."
    ::= { netBotzRackAccessPrefix 14 }

netBotzCardReaderReplugged NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Card reader replugged. TrapErrorTypeLabel indicates rack access user label."
    ::= { netBotzRackAccessPrefix 15 }

netBotzCardReaderError NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Card reader error. TrapErrorTypeLabel indicates rack access user label."
    ::= { netBotzRackAccessPrefix 16 }

netBotzCardReaderErrorRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Card reader error resolved. TrapErrorTypeLabel indicates rack access user label."
    ::= { netBotzRackAccessPrefix 17 }

netBotzCardReaderValueError NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Card reader value error. TrapErrorTypeLabel indicates rack access user label."
    ::= { netBotzRackAccessPrefix 18 }

netBotzCardReaderValueErrorRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Card reader value error resolved. TrapErrorTypeLabel indicates rack access user label."
    ::= { netBotzRackAccessPrefix 19 }

netBotzRackHandleSensorUnplugged NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Rack handle sensor unplugged. TrapErrorTypeLabel indicates rack access user label."
    ::= { netBotzRackAccessPrefix 20 }

netBotzRackHandleSensorReplugged NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Rack handle sensor replugged. TrapErrorTypeLabel indicates rack access user label."
    ::= { netBotzRackAccessPrefix 21}

netBotzRackHandleSensorError NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Rack handle sensor error. TrapErrorTypeLabel indicates rack access user label."
    ::= { netBotzRackAccessPrefix 22 }

netBotzRackHandleSensorErrorRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Rack handle sensor error resolved. TrapErrorTypeLabel indicates rack access user label."
    ::= { netBotzRackAccessPrefix 23 }

netBotzRackHandleSensorValueError NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Rack handle sensor value error. TrapErrorTypeLabel indicates rack access user label."
    ::= { netBotzRackAccessPrefix 24 }

netBotzRackHandleSensorValueErrorRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Rack handle sensor value error resolved. TrapErrorTypeLabel indicates rack access user label."
    ::= { netBotzRackAccessPrefix 25 }

netBotzLockSensorUnplugged NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Lock sensor unplugged. TrapErrorTypeLabel indicates rack access user label."
    ::= { netBotzRackAccessPrefix 26 }

netBotzLockSensorReplugged NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Lock sensor replugged. TrapErrorTypeLabel indicates rack access user label."
    ::= { netBotzRackAccessPrefix 27 }

netBotzLockSensorError NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Lock sensor error. TrapErrorTypeLabel indicates rack access user label."
    ::= { netBotzRackAccessPrefix 28 }

netBotzLockSensorErrorRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Lock sensor error resolved. TrapErrorTypeLabel indicates rack access user label."
    ::= { netBotzRackAccessPrefix 29 }

netBotzLockSensorValueError NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Lock sensor value error. TrapErrorTypeLabel indicates rack access user label."
    ::= { netBotzRackAccessPrefix 30 }

netBotzLockSensorValueErrorRTN NOTIFICATION-TYPE
    OBJECTS {
        netBotzTrapErrorID,
        netBotzTrapErrorType,
        netBotzTrapErrorTypeLabel,
        netBotzTrapSensorID,
        netBotzTrapSensorLabel,
        netBotzTrapContainerID,
        netBotzTrapContainerLabel,
        netBotzTrapPortID,
        netBotzTrapPortLabel,
        netBotzTrapStartTime,
        netBotzTrapNotifyTime,
        netBotzTrapResolveTime,
        netBotzTrapSeverity,
        netBotzTrapSensorValue,
        netBotzTrapSensorValueInt,
        netBotzTrapSensorValueFraction
        }
    STATUS        current
    DESCRIPTION
    "Lock sensor value error resolved. TrapErrorTypeLabel indicates rack access user label."
    ::= { netBotzRackAccessPrefix 31 }

netBotzRpduUnplugged NOTIFICATION-TYPE
    OBJECTS {
        netBotzTrapErrorID,
        netBotzTrapErrorType,
        netBotzTrapErrorTypeLabel,
        netBotzTrapContainerID,
        netBotzTrapContainerLabel,
        netBotzTrapPortID,
        netBotzTrapPortLabel,
        netBotzTrapStartTime,
        netBotzTrapNotifyTime,
        netBotzTrapResolveTime,
        netBotzTrapSeverity
        }
    STATUS        current
    DESCRIPTION
    "RPDU unplugged."
    ::= { netBotzRpduPrefix 101 }

netBotzRpduReplugged NOTIFICATION-TYPE
    OBJECTS {
        netBotzTrapErrorID,
        netBotzTrapErrorType,
        netBotzTrapErrorTypeLabel,
        netBotzTrapContainerID,
        netBotzTrapContainerLabel,
        netBotzTrapPortID,
        netBotzTrapPortLabel,
        netBotzTrapStartTime,
        netBotzTrapNotifyTime,
        netBotzTrapResolveTime,
        netBotzTrapSeverity
        }
    STATUS        current
    DESCRIPTION
    "RPDU no longer unplugged."
    ::= { netBotzRpduPrefix 102 }

netBotzUpsUnplugged NOTIFICATION-TYPE
    OBJECTS {
        netBotzTrapErrorID,
        netBotzTrapErrorType,
        netBotzTrapErrorTypeLabel,
        netBotzTrapContainerID,
        netBotzTrapContainerLabel,
        netBotzTrapPortID,
        netBotzTrapPortLabel,
        netBotzTrapStartTime,
        netBotzTrapNotifyTime,
        netBotzTrapResolveTime,
        netBotzTrapSeverity
        }
    STATUS        current
    DESCRIPTION
    "UPS unplugged."
    ::= { netBotzUpsPrefix 103 }

netBotzUpsReplugged NOTIFICATION-TYPE
    OBJECTS {
        netBotzTrapErrorID,
        netBotzTrapErrorType,
        netBotzTrapErrorTypeLabel,
        netBotzTrapContainerID,
        netBotzTrapContainerLabel,
        netBotzTrapPortID,
        netBotzTrapPortLabel,
        netBotzTrapStartTime,
        netBotzTrapNotifyTime,
        netBotzTrapResolveTime,
        netBotzTrapSeverity
        }
    STATUS        current
    DESCRIPTION
    "UPS no longer unplugged."
    ::= { netBotzUpsPrefix 104 }

netBotzGenericNotification NOTIFICATION-TYPE
    OBJECTS {
        netBotzTrapErrorID,
        netBotzTrapErrorType,
        netBotzTrapErrorTypeLabel,
        netBotzTrapContainerID,
        netBotzTrapContainerLabel,
        netBotzTrapPortID,
        netBotzTrapPortLabel,
        netBotzTrapStartTime,
        netBotzTrapNotifyTime,
        netBotzTrapResolveTime,
        netBotzTrapSeverity
        }
    STATUS        current
    DESCRIPTION
    "Generic Trap."
    ::= { netBotzGenericPrefix 1 }

netBotzTestNotification NOTIFICATION-TYPE
    OBJECTS {
        netBotzTrapNotifyTime,
        netBotzTrapData

        }
    STATUS        current
    DESCRIPTION
    "Diagnostic Test Trap."
    ::= { netBotzTestPrefix 1 }


--
-- Firmware
--
firmwareTable OBJECT-TYPE
    SYNTAX     SEQUENCE OF FirmwareEntry
    MAX-ACCESS not-accessible
    STATUS     current
    DESCRIPTION
        "A list of firmware versions contained in the NetBotz distribution."
    ::= { netBotzFirmware 1 }

firmwareEntry OBJECT-TYPE
    SYNTAX     FirmwareEntry
    MAX-ACCESS not-accessible
    STATUS     current
    DESCRIPTION
        "Firmware entry."
    INDEX { firmwareIndex }
    ::= { firmwareTable 1 }

FirmwareEntry ::= SEQUENCE {
    firmwareDescription                  DisplayString,
    firmwareVersion                      DisplayString,
    firmwareIndex                        Counter32
}

firmwareDescription OBJECT-TYPE
    SYNTAX     DisplayString (SIZE (0..127))
    MAX-ACCESS read-only
    STATUS     current
    DESCRIPTION
        "Name of of the firmware product."
    ::= { firmwareEntry 1 }

firmwareVersion OBJECT-TYPE
    SYNTAX     DisplayString (SIZE (0..127))
    MAX-ACCESS read-only
    STATUS     current
    DESCRIPTION
        "Version of of the firmware product."
    ::= { firmwareEntry 2 }

firmwareIndex OBJECT-TYPE
    SYNTAX     Counter32
    MAX-ACCESS read-only
    STATUS     current
    DESCRIPTION
        "The index of the firmware."
    ::= { firmwareEntry 3 }
END
