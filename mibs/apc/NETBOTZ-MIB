--
-- NETBOTZ-MIB       module definition
--
NETBOTZ-MIB DEFINITIONS ::= BEGIN
IMPORTS
   OBJECT-TYPE FROM RFC-1212
   DisplayString FROM RFC1213-MIB
   enterprises FROM RFC1155-SMI
   TRAP-TYPE FROM RFC-1215
   TimeTicks FROM RFC1155-SMI
   IpAddress FROM RFC1155-SMI;

netBotz					OBJECT IDENTIFIER
							::= { enterprises 5528 }

netBotz-reg				OBJECT IDENTIFIER
							::= { netBotz 10 }

netBotz-generic			OBJECT IDENTIFIER
							::= { netBotz 20 }

netBotz-products		OBJECT IDENTIFIER
							::= { netBotz 30 }

netBotz-metric			OBJECT IDENTIFIER
							::= { netBotz 32 }

netBotz-snmp			OBJECT IDENTIFIER
							::= { netBotz 40 }

netBotz-device			OBJECT IDENTIFIER
							::= { netBotz 50 }

netBotz-addonapp		OBJECT IDENTIFIER	::= { netBotz 60 }

netBotz-addonapp-trap		OBJECT IDENTIFIER	::= { netBotz 61 }

vendor-netBotz			OBJECT IDENTIFIER	::= { netBotz-addonapp 5528 }

device-crawlers-trap		OBJECT IDENTIFIER 	::= { vendor-netBotz 2 }

branch-checker-trap		OBJECT IDENTIFIER	::= { vendor-netBotz 3 }

device-crawlers-trap-attrib	OBJECT IDENTIFIER	::= { netBotz-addonapp-trap 2 }

branch-checker-trap-attrib	OBJECT IDENTIFIER	::= { netBotz-addonapp-trap 3 }

device-crawlers-trap-target-index OBJECT IDENTIFIER	::= { netBotz-addonapp 2 }

branch-checker-trap-target-index OBJECT IDENTIFIER	::= { netBotz-addonapp 3 }

netBotz-prd-bot		 OBJECT IDENTIFIER
                     ::= { netBotz-products 10 }

netBotz-metric-onboard	 OBJECT IDENTIFIER
		     ::= { netBotz-metric 10 }

netBotz-prd-crawlers OBJECT IDENTIFIER
                     ::= { netBotz-products 20 }

netBotz-prd-crltrap  OBJECT IDENTIFIER
                     ::= { netBotz-products 21 }


netBotz-prd-WallBotz-300	 OBJECT IDENTIFIER
                     ::= { netBotz-products 1000 }

netBotz-prd-RackBotz-300	 OBJECT IDENTIFIER
                     ::= { netBotz-products 1001 }

netBotz-prd-RackBotz-300U	 OBJECT IDENTIFIER
                     ::= { netBotz-products 1002 }

netBotz-prd-WallBotz-400	 OBJECT IDENTIFIER
                     ::= { netBotz-products 1003 }

netBotz-prd-RackBotz-400 	OBJECT IDENTIFIER
                     ::= { netBotz-products 1004 }

netBotz-prd-RackBotz-303	 OBJECT IDENTIFIER
                     ::= { netBotz-products 1006 }

netBotz-prd-WallBotz-310	 OBJECT IDENTIFIER
                     ::= { netBotz-products 1007 }

netBotz-prd-RackBotz-310	 OBJECT IDENTIFIER
                     ::= { netBotz-products 1008 }

netBotz-prd-WallBotz-300B	 OBJECT IDENTIFIER
		     ::= { netBotz-products 1009 }

netBotz-prd-WallBotz-300C	 OBJECT IDENTIFIER
                     ::= { netBotz-products 1100 }

netBotz-prd-RackBotz-300C	 OBJECT IDENTIFIER
                     ::= { netBotz-products 1101 }

netBotz-prd-RackBotz-300UC	 OBJECT IDENTIFIER
                     ::= { netBotz-products 1102 }

netBotz-prd-WallBotz-400C	 OBJECT IDENTIFIER
                     ::= { netBotz-products 1103 }

netBotz-prd-RackBotz-400C 	OBJECT IDENTIFIER
                     ::= { netBotz-products 1104 }

netBotz-prd-RackBotz-303C	 OBJECT IDENTIFIER
                     ::= { netBotz-products 1106 }

netBotz-prd-WallBotz-310C	 OBJECT IDENTIFIER
                     ::= { netBotz-products 1107 }

netBotz-prd-RackBotz-310C	 OBJECT IDENTIFIER
                     ::= { netBotz-products 1108 }

netBotz-prd-WallBotz-300BC	 OBJECT IDENTIFIER
		     ::= { netBotz-products 1109 }

netBotz-prd-WallBotz-300E	 OBJECT IDENTIFIER
                     ::= { netBotz-products 1200 }

netBotz-prd-RackBotz-300E	 OBJECT IDENTIFIER
                     ::= { netBotz-products 1201 }

netBotz-prd-RackBotz-300UE	 OBJECT IDENTIFIER
                     ::= { netBotz-products 1202 }

netBotz-prd-WallBotz-400E	 OBJECT IDENTIFIER
                     ::= { netBotz-products 1203 }

netBotz-prd-RackBotz-400E 	OBJECT IDENTIFIER
                     ::= { netBotz-products 1204 }

netBotz-prd-RackBotz-303E	 OBJECT IDENTIFIER
                     ::= { netBotz-products 1206 }

netBotz-prd-WallBotz-310E	 OBJECT IDENTIFIER
                     ::= { netBotz-products 1207 }

netBotz-prd-RackBotz-310E	 OBJECT IDENTIFIER
                     ::= { netBotz-products 1208 }

netBotz-prd-WallBotz-300BE	 OBJECT IDENTIFIER
		     ::= { netBotz-products 1209 }

netBotz-dev-host	OBJECT-TYPE
	SYNTAX		DisplayString
	ACCESS		read-write
	STATUS		mandatory
	DESCRIPTION 	"NetBotz device's host name."
	REFERENCE 	"NetBotz Host"
	::= { netBotz-device 1 }

netBotz-dev-domain	OBJECT-TYPE
	SYNTAX		DisplayString
	ACCESS		read-write
	STATUS		mandatory
	DESCRIPTION	"NetBotz device's default DNS domain."
	REFERENCE 	"NetBotz Domain"
	::= { netBotz-device 2 }

netBotz-dev-ip		OBJECT-TYPE
	SYNTAX		IpAddress
	ACCESS		read-write
	STATUS		mandatory
	DESCRIPTION	"NetBotz device's IP address."
	REFERENCE 	"NetBotz IP address"
	::= { netBotz-device 3 }

netBotz-dev-netmask	OBJECT-TYPE
	SYNTAX		IpAddress
	ACCESS		read-write
	STATUS		mandatory
	DESCRIPTION	"NetBotz device's netmask."
	REFERENCE 	"NetBotz Device Netmask"
	::= { netBotz-device 4 }

netBotz-dev-gateway	OBJECT-TYPE
	SYNTAX		IpAddress
	ACCESS		read-write
	STATUS		mandatory
	DESCRIPTION	"NetBotz device's default gateway/router. 0.0.0.0 if not defined."
	REFERENCE 	"NetBotz Device Gateway"
	::= { netBotz-device 5 }

netBotz-dev-primarydns	OBJECT-TYPE
	SYNTAX		IpAddress
	ACCESS		read-write
	STATUS		mandatory
	DESCRIPTION	"Primary Domain Name Server. 0.0.0.0 if not defined."
	REFERENCE 	"Primary DNS"
	::= { netBotz-device 6 }

netBotz-dev-secondarydns	OBJECT-TYPE
	SYNTAX		IpAddress
	ACCESS		read-write
	STATUS		mandatory
	DESCRIPTION	"Secondary Domain Name Server. 0.0.0.0 if not defined."
	REFERENCE 	"Secondary DNS"
	::= { netBotz-device 7 }

netBotz-dev-smtp	OBJECT-TYPE
	SYNTAX		DisplayString
	ACCESS		read-write
	STATUS		mandatory
	DESCRIPTION	"SMTP server address.  This is the mail server used for sending alert e-mails."
	REFERENCE 	"SMTP"
	::= { netBotz-device 8 }

netBotz-dev-smtpport	OBJECT-TYPE
	SYNTAX		INTEGER
	ACCESS		read-write
	STATUS		mandatory
	DESCRIPTION	"SMTP port.  Port number of SMTP server used for sending alert e-mails."
	REFERENCE 	"SMTP Port"
	::= { netBotz-device 9 }

netBotz-dev-popport	OBJECT-TYPE
	SYNTAX		INTEGER
	ACCESS		read-write
	STATUS		mandatory
	DESCRIPTION	"POP port.  Currently, not used."
	REFERENCE 	"POP Port"
	::= { netBotz-device 10 }

netBotz-dev-loglevel	OBJECT-TYPE
	SYNTAX		INTEGER
	ACCESS		read-write
	STATUS		mandatory
	DESCRIPTION
	"This field contains the log level of the NetBotz device.
	Log messages will be filtered, so that only same or lower-level
	messages will be passed. The default log level is 5, for warnings
	and lower levels. The log levels are the following:
	1 - emergency
	2 - alert
	3 - critical
	4 - error
	5 - warning
	6 - notice
	7 - info
	8 - trace"
	REFERENCE 	"Log Level"
	::= { netBotz-device 11 }

netBotz-dev-primaryemail	OBJECT-TYPE
	SYNTAX		DisplayString
	ACCESS		read-write
	STATUS		mandatory
	DESCRIPTION	"The primary email addresses for alerts and messages (list separated by commas for multiple addresses)."
	REFERENCE 	"Primary Email"
	::= { netBotz-device 14 }

netBotz-dev-secondaryemail	OBJECT-TYPE
	SYNTAX		DisplayString
	ACCESS		read-write
	STATUS		mandatory
	DESCRIPTION	"The secondary email address for alerts and messages (list separated by commas for multiple addresses)."
	REFERENCE 	"Secondary Email"
	::= { netBotz-device 15 }

netBotz-dev-serialno	OBJECT-TYPE
	SYNTAX		DisplayString
	ACCESS		read-only
	STATUS		mandatory
	DESCRIPTION	"The serial number of the NetBotz device."
	REFERENCE 	"Serial Number"
	::= { netBotz-device 17 }

netBotz-dev-pop	OBJECT-TYPE
	SYNTAX		DisplayString
	ACCESS		read-write
	STATUS		mandatory
	DESCRIPTION	"POP server name.  Currently, not used."
	REFERENCE 	"POP"
	::= { netBotz-device 18 }

netBotz-dev-version OBJECT-TYPE
	SYNTAX		DisplayString
	ACCESS		read-only
	STATUS		mandatory
	DESCRIPTION	"The current NetBotz device firmware version."
	REFERENCE	"Firmware Version"
	::= { netBotz-device 19 }

netBotz-dev-registered OBJECT-TYPE
	SYNTAX		INTEGER
	ACCESS		read-only
	STATUS		mandatory
	DESCRIPTION	"Indicates if the device has been registered with NetBotz, Inc. 1=registered, 0=not registered."
	REFERENCE	"Device Registered"
	::= { netBotz-device 20 }

netBotz-default-applet OBJECT-TYPE
	SYNTAX		INTEGER
	ACCESS		read-write
	STATUS		mandatory
	DESCRIPTION	"Setting to control if default web page should launch applet by default(1) or the HTML status page(0)."
	REFERENCE	"Default Applet"
	::= { netBotz-device 21 }

netBotz-guibar-color OBJECT-TYPE
	SYNTAX		INTEGER
	ACCESS		read-write
	STATUS		mandatory
	DESCRIPTION	"Setting for color of GUI bar (RGB). Value = 0xRRGGBB."
	REFERENCE	"GUI Bar Color"
	::= { netBotz-device 22 }

netBotz-locale OBJECT-TYPE
	SYNTAX		DisplayString
	ACCESS		read-write
	STATUS		mandatory
	DESCRIPTION	"The locale ID of the NetBotz device.  Format is ISO 639 language (lower case),
            an underscore, and ISO 3166 country (upper case).  Some locales are just the ISO 639 language code."
	REFERENCE	"Locale"
	::= { netBotz-device 23 }

netBotz-timezone OBJECT-TYPE
	SYNTAX		DisplayString
	ACCESS		read-write
	STATUS		mandatory
	DESCRIPTION	"The timezone ID of the NetBotz device."
	REFERENCE	"TimeZone"
	::= { netBotz-device 24 }

netBotz-24hourpreferred	OBJECT-TYPE
	SYNTAX		INTEGER
	ACCESS		read-write
	STATUS		mandatory
	DESCRIPTION	"Indicates if 24-hour(1) versus 12-hour(0) time format is preferred."
	REFERENCE 	"24 hour format"
	::= { netBotz-device 25 }

netBotz-utc-clock	OBJECT-TYPE
	SYNTAX		INTEGER
	ACCESS		read-write
	STATUS		mandatory
	DESCRIPTION	"Current time of clock on NetBotz device, in UTC seconds (seconds since 1/1/1970 12:00am GMT)."
	REFERENCE 	"UTC Clock"
	::= { netBotz-device 26 }

netBotz-ismetric	OBJECT-TYPE
	SYNTAX		INTEGER
	ACCESS		read-only
	STATUS		mandatory
	DESCRIPTION	"Units are metric (1) or U.S. (0).  Applies to temperature and airflow rate."
	REFERENCE 	"Metric Units"
	::= { netBotz-device 27 }

netBotz-alert-url OBJECT-TYPE
	SYNTAX		DisplayString
	ACCESS		read-write
	STATUS		mandatory
	DESCRIPTION	"The URL, if defined, to which non-picture alerts are HTTP POSTed"
	REFERENCE	"Alert URL"
	::= { netBotz-device 28 }

netBotz-picture-alert-url OBJECT-TYPE
	SYNTAX		DisplayString
	ACCESS		read-write
	STATUS		mandatory
	DESCRIPTION	"The URL, if defined, to which picture alerts are HTTP POSTed, using multipart/form-data
		encoding."
	REFERENCE	"Picture Alert URL"
	::= { netBotz-device 29 }

netBotz-sensor-data-url OBJECT-TYPE
	SYNTAX		DisplayString
	ACCESS		read-write
	STATUS		mandatory
	DESCRIPTION	"The URL, if defined, to which sensor data is periodically HTTP POSTed."
	REFERENCE	"Sensor Data URL"
	::= { netBotz-device 30 }

netBotz-alert-url-logon OBJECT-TYPE
	SYNTAX		DisplayString
	ACCESS		read-write
	STATUS		mandatory
	DESCRIPTION	"The user ID and password, if defined, used for POSTing non-picture alerts.
		Field is write-only, and formatted /"
	REFERENCE	"Alert URL Logon"
	::= { netBotz-device 31 }

netBotz-picture-alert-url-logon OBJECT-TYPE
	SYNTAX		DisplayString
	ACCESS		read-write
	STATUS		mandatory
	DESCRIPTION	"The user ID and password, if defined, used for POSTing picture alerts.
		Field is write-only, and formatted /"
	REFERENCE	"Picture Alert URL Logon"
	::= { netBotz-device 32 }

netBotz-sensor-data-url-logon OBJECT-TYPE
	SYNTAX		DisplayString
	ACCESS		read-write
	STATUS		mandatory
	DESCRIPTION	"The user ID and password, if defined, used for POSTing sensor data.
		Field is write-only, and formatted /"
	REFERENCE	"Sensor Data URL Logon"
	::= { netBotz-device 33 }

netBotz-sensor-data-url-period	OBJECT-TYPE
	SYNTAX		INTEGER
	ACCESS		read-write
	STATUS		mandatory
	DESCRIPTION	"Default number of minutes between periodic sensor data HTTP POSTs."
	REFERENCE 	"Sensor Data URL Period"
	::= { netBotz-device 34 }

netBotz-sensor-data-url-flags	OBJECT-TYPE
	SYNTAX		INTEGER
	ACCESS		read-write
	STATUS		mandatory
	DESCRIPTION	"Option flags for data POSTs of sensor data.  Bit 0=1 if current picture
		should be included.  Bits 1-31 are reserved."
	REFERENCE 	"Sensor Data URL Flags"
	::= { netBotz-device 35 }

netBotz-dev-backup-smtp	OBJECT-TYPE
	SYNTAX		DisplayString
	ACCESS		read-write
	STATUS		mandatory
	DESCRIPTION	"Backup SMTP server address.  This is the backup mail server used for sending alert e-mails."
	REFERENCE 	"Backup SMTP"
	::= { netBotz-device 36 }

netBotz-dev-tertiarydns	OBJECT-TYPE
	SYNTAX		IpAddress
	ACCESS		read-write
	STATUS		mandatory
	DESCRIPTION	"Tertiary Domain Name Server. 0.0.0.0 if not defined."
	REFERENCE 	"Tertiary DNS"
	::= { netBotz-device 37 }

netBotz-dev-ntp-server	OBJECT-TYPE
	SYNTAX		DisplayString
	ACCESS		read-write
	STATUS		mandatory
	DESCRIPTION	"NTP (Network Time Protocol) Server configured for appliance."
	REFERENCE 	"NTP Server"
	::= { netBotz-device 38 }

netBotz-dev-ntp-period	OBJECT-TYPE
	SYNTAX		INTEGER
	ACCESS		read-write
	STATUS		mandatory
	DESCRIPTION	"Hours between automatic refreshes of the appliance clock using the NTP server."
	REFERENCE 	"NTP refresh period"
	::= { netBotz-device 39 }

netBotz-dev-socks-server	OBJECT-TYPE
	SYNTAX		DisplayString
	ACCESS		read-write
	STATUS		mandatory
	DESCRIPTION	"Socks V4 or V5 proxy server configured for appliance."
	REFERENCE 	"Socks V4/V5 Proxy Server"
	::= { netBotz-device 40 }

netBotz-dev-socks-portnum	OBJECT-TYPE
	SYNTAX		INTEGER
	ACCESS		read-write
	STATUS		mandatory
	DESCRIPTION	"Port number of Socks Proxy."
	REFERENCE 	"Socks V4/V5 Proxy Port"
	::= { netBotz-device 41 }

netBotz-dev-socks-user-id	OBJECT-TYPE
	SYNTAX		DisplayString
	ACCESS		read-write
	STATUS		mandatory
	DESCRIPTION	"User ID for Socks V4 or V5 proxy server configured for appliance."
	REFERENCE 	"Socks V4/V5 Proxy Server User ID"
	::= { netBotz-device 42 }

netBotz-dev-socks-password	OBJECT-TYPE
	SYNTAX		DisplayString
	ACCESS		read-write
	STATUS		mandatory
	DESCRIPTION	"Password for Socks V4 or V5 proxy server configured for appliance."
	REFERENCE 	"Socks V4/V5 Proxy Server Password"
	::= { netBotz-device 43 }

netBotz-alert-ftp-site OBJECT-TYPE
	SYNTAX		DisplayString
	ACCESS		read-write
	STATUS		mandatory
	DESCRIPTION	"The hostname or dotted-decimal IP address of the FTP server to
		deliver alerts to"
	REFERENCE	"Alert FTP Site"
	::= { netBotz-device 44 }

netBotz-alert-ftp-path OBJECT-TYPE
	SYNTAX		DisplayString
	ACCESS		read-write
	STATUS		mandatory
	DESCRIPTION	"The directory on the FTP server to store alerts in."
	REFERENCE	"Alert FTP Path"
	::= { netBotz-device 45 }


netBotz-alert-ftp-filename OBJECT-TYPE
	SYNTAX		DisplayString
	ACCESS		read-write
	STATUS		mandatory
	DESCRIPTION	"The base filename for the files on the FTP server to store alerts in."
	REFERENCE	"Alert FTP Filename"
	::= { netBotz-device 46 }

netBotz-alert-ftp-logon OBJECT-TYPE
	SYNTAX		DisplayString
	ACCESS		read-write
	STATUS		mandatory
	DESCRIPTION	"The user-id and password on the FTP server to store alerts in.
		Field is write-only, and formatted /"
	REFERENCE	"Alert FTP Logon"
	::= { netBotz-device 47 }

netBotz-sensor-ftp-site OBJECT-TYPE
	SYNTAX		DisplayString
	ACCESS		read-write
	STATUS		mandatory
	DESCRIPTION	"The hostname or dotted-decimal IP address of the FTP server to
		deliver periodic sensor reports to"
	REFERENCE	"Sensor FTP Site"
	::= { netBotz-device 48 }

netBotz-sensor-ftp-path OBJECT-TYPE
	SYNTAX		DisplayString
	ACCESS		read-write
	STATUS		mandatory
	DESCRIPTION	"The directory on the FTP server to store periodic sensor reports in."
	REFERENCE	"Sensor FTP Path"
	::= { netBotz-device 49 }

netBotz-sensor-ftp-filename OBJECT-TYPE
	SYNTAX		DisplayString
	ACCESS		read-write
	STATUS		mandatory
	DESCRIPTION	"The base filename for the files on the FTP server to store periodic sensor reports in."
	REFERENCE	"Sensor FTP Filename"
	::= { netBotz-device 50 }

netBotz-sensor-ftp-logon OBJECT-TYPE
	SYNTAX		DisplayString
	ACCESS		read-write
	STATUS		mandatory
	DESCRIPTION	"The user-id and password on the FTP server to store sensor reports in.
		Field is write-only, and formatted /"
	REFERENCE	"Sensor FTP Logon"
	::= { netBotz-device 51 }

netBotz-sensor-ftp-period	OBJECT-TYPE
	SYNTAX		INTEGER
	ACCESS		read-write
	STATUS		mandatory
	DESCRIPTION	"The period, in minutes, between delivery of sensor data reports."
	REFERENCE 	"Sensor FTP Period"
	::= { netBotz-device 52 }

netBotz-use-syslog	OBJECT-TYPE
	SYNTAX		INTEGER
	ACCESS		read-write
	STATUS		mandatory
	DESCRIPTION	"Enable syslog"
	REFERENCE 	"Syslog enable"
	::= { netBotz-device 53 }

netBotz-syslog-address OBJECT-TYPE
	SYNTAX		DisplayString
	ACCESS		read-write
	STATUS		mandatory
	DESCRIPTION	"Host address to use for syslogging"
	REFERENCE	"Syslog Host Address"
	::= { netBotz-device 54 }

netBotz-syslog-facility	OBJECT-TYPE
	SYNTAX		INTEGER
	ACCESS		read-write
	STATUS		mandatory
	DESCRIPTION	"Syslog facility code"
	REFERENCE 	"Syslog facility code"
	::= { netBotz-device 55 }

netBotz-color-balance OBJECT-TYPE
	SYNTAX		DisplayString
	ACCESS		read-write
	STATUS		mandatory
	DESCRIPTION	"Color balance for color camera. AUTO=automatic, FLUOR=fluorescent, DAY=daylight,
			INCAND=incandescent, x/y=Custom (scale red by x/64, scale blue by y/64)"
	REFERENCE	"Color Balance"
	::= { netBotz-device 56 }

netBotz-metric-onboard-model OBJECT-TYPE
	SYNTAX		DisplayString
	ACCESS		read-only
	STATUS		mandatory
	DESCRIPTION	"The model description of the appliance."
	REFERENCE	"NetBotz Metric Model"
	::= { netBotz-metric-onboard 1 }

netBotz-metric-onboard-temp OBJECT-TYPE
	SYNTAX		INTEGER
	ACCESS		read-only
	STATUS		mandatory
	DESCRIPTION	"The reading of the built-in temperature probe, in tenths of a degree C."
	REFERENCE	"NetBotz Metric Temperature Probe"
	::= { netBotz-metric-onboard 2 }

netBotz-metric-onboard-humidity OBJECT-TYPE
	SYNTAX		INTEGER
	ACCESS		read-only
	STATUS		mandatory
	DESCRIPTION	"The reading of the built-in humidity probe, in percent."
	REFERENCE	"NetBotz Metric Humidity Probe"
	::= { netBotz-metric-onboard 3 }

netBotz-metric-onboard-airflow OBJECT-TYPE
	SYNTAX		INTEGER
	ACCESS		read-only
	STATUS		mandatory
	DESCRIPTION	"The reading of the built-in airflow probe, in meters/minute."
	REFERENCE	"NetBotz Metric Airflow Probe"
	::= { netBotz-metric-onboard 4 }

netBotz-metric-onboard-audio OBJECT-TYPE
	SYNTAX		INTEGER
	ACCESS		read-only
	STATUS		mandatory
	DESCRIPTION	"The reading of the built-in audio alarm probe on/off."
	REFERENCE	"NetBotz Metric Audio Probe"
	::= { netBotz-metric-onboard 5 }

netBotz-metric-onboard-doorajar OBJECT-TYPE
	SYNTAX		INTEGER
	ACCESS		read-only
	STATUS		mandatory
	DESCRIPTION	"The reading of the door switch probe open(1) or closed(0)."
	REFERENCE	"NetBotz Metric Door Switch Probe"
	::= { netBotz-metric-onboard 6 }

netBotz-metric-onboard-temp-min OBJECT-TYPE
	SYNTAX		INTEGER
	ACCESS		read-only
	STATUS		mandatory
	DESCRIPTION	"The temperature probe minimum, from 1 to 50 degrees C  in tenths of a degree C."
	REFERENCE	"NetBotz Metric Temperature Probe Minimum"
	::= { netBotz-metric-onboard 7 }

netBotz-metric-onboard-temp-max OBJECT-TYPE
	SYNTAX		INTEGER
	ACCESS		read-only
	STATUS		mandatory
	DESCRIPTION	"The temperature probe maximum, from 1 to 50 degrees C in tenths of a degree C."
	REFERENCE	"NetBotz Metric Temperature Probe Maximum"
	::= { netBotz-metric-onboard 8 }

netBotz-metric-onboard-humidity-min OBJECT-TYPE
	SYNTAX		INTEGER
	ACCESS		read-only
	STATUS		mandatory
	DESCRIPTION	"The humidity probe minimum, from 10 to 90 percent."
	REFERENCE	"NetBotz Metric Humidity Probe Minimum"
	::= { netBotz-metric-onboard 9 }

netBotz-metric-onboard-humidity-max OBJECT-TYPE
	SYNTAX		INTEGER
	ACCESS		read-only
	STATUS		mandatory
	DESCRIPTION	"The humidity probe maximum, from 10 to 90 percent."
	REFERENCE	"NetBotz Metric Humidity Probe Maximum"
	::= { netBotz-metric-onboard 10 }

netBotz-metric-onboard-airflow-mins OBJECT-TYPE
	SYNTAX		INTEGER
	ACCESS		read-only
	STATUS		mandatory
	DESCRIPTION	"Minutes without airflow before alarm set."
	REFERENCE	"NetBotz Metric Airflow Minutes"
	::= { netBotz-metric-onboard 11 }

netBotz-metric-onboard-audio-secs OBJECT-TYPE
	SYNTAX		INTEGER
	ACCESS		read-only
	STATUS		mandatory
	DESCRIPTION	"Seconds of alarm audio before alarm set."
	REFERENCE	"NetBotz Metric Audio Seconds"
	::= { netBotz-metric-onboard 12 }

netBotz-metric-onboard-switch-state OBJECT-TYPE
	SYNTAX		INTEGER
	ACCESS		read-only
	STATUS		mandatory
	DESCRIPTION	"Switch state setting.  The state controls which condition of the door switch indicates an alarm.  If set to 0, alarm is set when the switch is closed.  If set to 1, alarm is set when the switch is open."
	REFERENCE	"NetBotz Metric Switch state setting"
	::= { netBotz-metric-onboard 13 }

netBotz-metric-onboard-audio-level OBJECT-TYPE
	SYNTAX		INTEGER
	ACCESS		read-only
	STATUS		mandatory
	DESCRIPTION	"Audio level setting, this is the relative audio level, from 0-11, above which an alarm will be sent."
	REFERENCE	"NetBotz Metric Audio Level"
	::= { netBotz-metric-onboard 14 }

netBotz-metric-onboard-airflow-level OBJECT-TYPE
	SYNTAX		INTEGER
	ACCESS		read-only
	STATUS		mandatory
	DESCRIPTION	"Airflow alert level.  This is the level, in meters per second,  below which an alarm will be sent."
	REFERENCE	"NetBotz Metric Airflow Level"
	::= { netBotz-metric-onboard 15 }

netBotz-metric-onboard-cam-motion OBJECT-TYPE
	SYNTAX		INTEGER
	ACCESS		read-only
	STATUS		mandatory
	DESCRIPTION	"The current motion reading for the camera motion sensor (0=none, 1=motion detected, -1=not licensed)."
	REFERENCE	"NetBotz Metric Camera Motion"
	::= { netBotz-metric-onboard 16 }

netBotz-metric-onboard-cam-motion-sensitivity OBJECT-TYPE
	SYNTAX		INTEGER
	ACCESS		read-only
	STATUS		mandatory
	DESCRIPTION	"Camera motion sensor sensitivity: 1=max, 15=min, 0=disabled."
	REFERENCE	"NetBotz Metric Camera Motion Sensor Sensitivity"
	::= { netBotz-metric-onboard 17 }

netBotz-prd-bot-temp OBJECT-TYPE
	SYNTAX		INTEGER
	ACCESS		read-only
	STATUS		mandatory
	DESCRIPTION	"The reading of the temperature probe, in degrees F or degrees C (depends on netBotz-ismetric)."
	REFERENCE 	"NetBotz Temperature Probe"
	::= { netBotz-prd-bot 1 }

netBotz-prd-bot-humidity     OBJECT-TYPE
	SYNTAX		INTEGER
	ACCESS		read-only
	STATUS		mandatory
	DESCRIPTION	"The reading of the humidity probe, in percent."
	REFERENCE 	"NetBotz Humidity Probe"
	::= { netBotz-prd-bot 2 }

netBotz-prd-bot-airflow      OBJECT-TYPE
	SYNTAX		INTEGER
	ACCESS		read-only
	STATUS		mandatory
	DESCRIPTION	"The reading of the airflow probe.  Each unit represents approximately 40 feet/minute or
            13 meters/minute of airflow velocity."
	REFERENCE 	"NetBotz Airflow Probe"
	::= { netBotz-prd-bot 3 }

netBotz-prd-bot-audio   OBJECT-TYPE
	SYNTAX		INTEGER
	ACCESS		read-only
	STATUS		mandatory
	DESCRIPTION	"The reading of the audio alarm probe on/off."
	REFERENCE 	"NetBotz Audio Probe"
	::= { netBotz-prd-bot 4 }

netBotz-prd-bot-doorajar     OBJECT-TYPE
	SYNTAX		INTEGER
	ACCESS		read-only
	STATUS		mandatory
	DESCRIPTION	"The reading of the door switch probe open(1) or closed(0)."
	REFERENCE 	"NetBotz Door Switch Probe"
	::= { netBotz-prd-bot 5 }

netBotz-prd-bot-temp-min OBJECT-TYPE
	SYNTAX		INTEGER
	ACCESS		read-write
	STATUS		mandatory
	DESCRIPTION	"The temperature probe minimum, from 35 to 120 degrees F, or 1 to 50 degrees C (depends on netBotz-ismetric)."
	REFERENCE 	"NetBotz Temperature Probe Minimum"
	::= { netBotz-prd-bot 6 }

netBotz-prd-bot-temp-max OBJECT-TYPE
	SYNTAX		INTEGER
	ACCESS		read-write
	STATUS		mandatory
	DESCRIPTION	"The temperature probe maximum, from 35 to 120 degrees F, or 1 to 50 degrees C (depends on netBotz-ismetric)."
	REFERENCE 	"NetBotz Temperature Probe Maximum"
	::= { netBotz-prd-bot 7 }

netBotz-prd-bot-humidity-min OBJECT-TYPE
	SYNTAX		INTEGER
	ACCESS		read-write
	STATUS		mandatory
	DESCRIPTION	"The humidity probe minimum, from 10 to 90 percent."
	REFERENCE 	"NetBotz Humidity Probe Minimum"
	::= { netBotz-prd-bot 8 }

netBotz-prd-bot-humidity-max OBJECT-TYPE
	SYNTAX		INTEGER
	ACCESS		read-write
	STATUS		mandatory
	DESCRIPTION	"The humidity probe maximum, from 10 to 90 percent."
	REFERENCE 	"NetBotz Humidity Probe Maximum"
	::= { netBotz-prd-bot 9 }

netBotz-prd-bot-airflow-mins OBJECT-TYPE
	SYNTAX		INTEGER
	ACCESS		read-write
	STATUS		mandatory
	DESCRIPTION	"Minutes without airflow before alarm set."
	REFERENCE 	"NetBotz|Airflow minutes"
	::= { netBotz-prd-bot 10 }

netBotz-prd-bot-audio-secs OBJECT-TYPE
	SYNTAX		INTEGER
	ACCESS		read-write
	STATUS		mandatory
	DESCRIPTION	"Seconds of alarm audio before alarm set."
	REFERENCE 	"NetBotz|Audio seconds"
	::= { netBotz-prd-bot 11 }

netBotz-prd-bot-temp-enabled OBJECT-TYPE
	SYNTAX		INTEGER
	ACCESS		read-write
	STATUS		mandatory
	DESCRIPTION	"Temperature probe alarm enabled(1) or disabled(0)."
	REFERENCE 	"NetBotz|Temperature Probe Enabled"
	::= { netBotz-prd-bot 12 }

netBotz-prd-bot-hum-enabled OBJECT-TYPE
	SYNTAX		INTEGER
	ACCESS		read-write
	STATUS		mandatory
	DESCRIPTION	"Humidity probe alarm enabled(1) or disabled(0)."
	REFERENCE 	"NetBotz|Humidity Probe Enabled"
	::= { netBotz-prd-bot 13 }

netBotz-prd-bot-air-enabled OBJECT-TYPE
	SYNTAX		INTEGER
	ACCESS		read-write
	STATUS		mandatory
	DESCRIPTION	"Airflow probe alarm enabled(1) or disabled(0)."
	REFERENCE 	"NetBotz|Airflow Probe Enabled"
	::= { netBotz-prd-bot 14 }

netBotz-prd-bot-audio-enabled OBJECT-TYPE
	SYNTAX		INTEGER
	ACCESS		read-write
	STATUS		mandatory
	DESCRIPTION	"Audio probe alarm enabled(1) or disabled(0)."
	REFERENCE 	"NetBotz|Audio Probe Enabled"
	::= { netBotz-prd-bot 15 }

netBotz-prd-bot-switch-state OBJECT-TYPE
	SYNTAX		INTEGER
	ACCESS		read-write
	STATUS		mandatory
	DESCRIPTION
	"Switch state setting. The state controls which
	condition of the door switch indicates an alarm.
	If set to 0, alarm is set when the switch is closed.
	If set to 1, alarm is set when the switch is open."
	REFERENCE 	"NetBotz|Switch state setting"
	::= { netBotz-prd-bot 16 }

netBotz-prd-bot-switch-enabled OBJECT-TYPE
	SYNTAX		INTEGER
	ACCESS		read-write
	STATUS		mandatory
	DESCRIPTION	"Door switch enabled(1) or disabled(0)."
	REFERENCE 	"NetBotz|Door Switch Enabled"
	::= { netBotz-prd-bot 17 }

netBotz-prd-bot-audio-level	OBJECT-TYPE
	SYNTAX		INTEGER
	ACCESS		read-write
	STATUS		mandatory
	DESCRIPTION	"Audio level setting.  This is the relative audio level, from 0-11,
            above which an alarm will be sent."
	REFERENCE 	"NetBotz|Audio Level"
	::= { netBotz-prd-bot 18 }

netBotz-prd-bot-trap-index OBJECT-TYPE
	SYNTAX		INTEGER
	ACCESS		read-only
	STATUS		mandatory
	DESCRIPTION	"The crawler ID of the last trap."
	REFERENCE 	"NetBotz Last Trap Index"
	::= { netBotz-prd-bot 20 }

netBotz-prd-bot-trap-address OBJECT-TYPE
	SYNTAX		IpAddress
	ACCESS		read-only
	STATUS		mandatory
	DESCRIPTION	"The IP address of the last trap."
	REFERENCE 	"NetBotz Last Trap Address"
	::= { netBotz-prd-bot 21 }

netBotz-prd-bot-trap-oid OBJECT-TYPE
	SYNTAX		OBJECT IDENTIFIER
	ACCESS		read-only
	STATUS		mandatory
	DESCRIPTION	"The object id of the last trap."
	REFERENCE 	"NetBotz Last Trap OID"
	::= { netBotz-prd-bot 22 }

netBotz-prd-bot-trap-value OBJECT-TYPE
	SYNTAX		INTEGER
	ACCESS		read-only
	STATUS		mandatory
	DESCRIPTION	"The value of the last object trap."
	REFERENCE 	"NetBotz Last Trap Value"
	::= { netBotz-prd-bot 23 }

netBotz-prd-bot-trap-date OBJECT-TYPE
	SYNTAX		INTEGER
	ACCESS		read-only
	STATUS		mandatory
	DESCRIPTION
	"The date and time of a specific trap. This field
	contains the number of seconds elapsed since
	midnight (00:00:00), January 1, 1970"
	REFERENCE 	"NetBotz Trap Date"
	::= { netBotz-prd-bot 24 }

netBotz-prd-bot-refresh	OBJECT-TYPE
	SYNTAX		INTEGER
	ACCESS		read-write
	STATUS		mandatory
	DESCRIPTION	"Rate of web page refresh, in seconds.  This must be greater than 5 seconds."
	REFERENCE 	"NetBotz|Web Refresh"
	::= { netBotz-prd-bot 26 }


netBotz-prd-bot-airflow-level	OBJECT-TYPE
	SYNTAX		INTEGER
	ACCESS		read-write
	STATUS		mandatory
	DESCRIPTION	"Airflow alert level.  This is the relative level of airflow below which
	an alarm will be sent.  The range is 1-11.  Each unit is approximately 40 feet/second or 13 meters/second of
        airflow velocity."
	REFERENCE 	"NetBotz|Airflow Alert Level"
	::= { netBotz-prd-bot 27 }

netBotz-prd-bot-doorpic-count	OBJECT-TYPE
	SYNTAX		INTEGER
	ACCESS		read-write
	STATUS		mandatory
	DESCRIPTION	"Number of pictures to take when door activated.
        These pictures will be sent as attachments to the door alert e-mail.
	The range is from 0 to 5 pictures."
	REFERENCE 	"NetBotz|Door Picture Count"
	::= { netBotz-prd-bot 28 }

netBotz-prd-bot-amps1 OBJECT-TYPE
	SYNTAX		INTEGER
	ACCESS		read-only
	STATUS		mandatory
	DESCRIPTION	"The reading of the first amperage probe, in milliamps."
	REFERENCE 	"NetBotz Amperage[1] Probe"
	::= { netBotz-prd-bot 29 }

netBotz-prd-bot-amps1-enabled OBJECT-TYPE
	SYNTAX		INTEGER
	ACCESS		read-write
	STATUS		mandatory
	DESCRIPTION	"Amperage[1] probe alarm enabled(1) or disabled(0)."
	REFERENCE 	"NetBotz|Amperage[1] Probe Enabled"
	::= { netBotz-prd-bot 30 }

netBotz-prd-bot-amps1-min OBJECT-TYPE
	SYNTAX		INTEGER
	ACCESS		read-write
	STATUS		mandatory
	DESCRIPTION	"The amperage[1] probe minimum, from 0 to 30000 milliamps."
	REFERENCE 	"NetBotz Amperage[1] Probe Minimum"
	::= { netBotz-prd-bot 31 }

netBotz-prd-bot-amps1-max OBJECT-TYPE
	SYNTAX		INTEGER
	ACCESS		read-write
	STATUS		mandatory
	DESCRIPTION	"The amperage[1] probe maximum, from 0 to 30000 milliamps."
	REFERENCE 	"NetBotz Amperage[1] Probe Maximum"
	::= { netBotz-prd-bot 32 }

netBotz-prd-bot-amps2 OBJECT-TYPE
	SYNTAX		INTEGER
	ACCESS		read-only
	STATUS		mandatory
	DESCRIPTION	"The reading of the second amperage probe, in milliamps."
	REFERENCE 	"NetBotz Amperage[2] Probe"
	::= { netBotz-prd-bot 34 }

netBotz-prd-bot-amps2-enabled OBJECT-TYPE
	SYNTAX		INTEGER
	ACCESS		read-write
	STATUS		mandatory
	DESCRIPTION	"Amperage[2] probe alarm enabled(1) or disabled(0)."
	REFERENCE 	"NetBotz|Amperage[2] Probe Enabled"
	::= { netBotz-prd-bot 35 }

netBotz-prd-bot-amps2-min OBJECT-TYPE
	SYNTAX		INTEGER
	ACCESS		read-write
	STATUS		mandatory
	DESCRIPTION	"The amperage[2] probe minimum, from 0 to 30000 milliamps."
	REFERENCE 	"NetBotz Amperage[2] Probe Minimum"
	::= { netBotz-prd-bot 36 }

netBotz-prd-bot-amps2-max OBJECT-TYPE
	SYNTAX		INTEGER
	ACCESS		read-write
	STATUS		mandatory
	DESCRIPTION	"The amperage[2] probe maximum, from 0 to 30000 milliamps."
	REFERENCE 	"NetBotz Amperage[2] Probe Maximum"
	::= { netBotz-prd-bot 37 }

netBotz-prd-bot-amps3 OBJECT-TYPE
	SYNTAX		INTEGER
	ACCESS		read-only
	STATUS		mandatory
	DESCRIPTION	"The reading of the third amperage probe, in milliamps."
	REFERENCE 	"NetBotz Amperage[3] Probe"
	::= { netBotz-prd-bot 39 }

netBotz-prd-bot-amps3-enabled OBJECT-TYPE
	SYNTAX		INTEGER
	ACCESS		read-write
	STATUS		mandatory
	DESCRIPTION	"Amperage[3] probe alarm enabled(1) or disabled(0)."
	REFERENCE 	"NetBotz|Amperage[3] Probe Enabled"
	::= { netBotz-prd-bot 40 }

netBotz-prd-bot-amps3-min OBJECT-TYPE
	SYNTAX		INTEGER
	ACCESS		read-write
	STATUS		mandatory
	DESCRIPTION	"The amperage[3] probe minimum, from 0 to 30000 milliamps."
	REFERENCE 	"NetBotz Amperage[3] Probe Minimum"
	::= { netBotz-prd-bot 41 }

netBotz-prd-bot-amps3-max OBJECT-TYPE
	SYNTAX		INTEGER
	ACCESS		read-write
	STATUS		mandatory
	DESCRIPTION	"The amperage[3] probe maximum, from 0 to 30000 milliamps."
	REFERENCE 	"NetBotz Amperage[3] Probe Maximum"
	::= { netBotz-prd-bot 42 }

netBotz-prd-bot-amps-total OBJECT-TYPE
	SYNTAX		INTEGER
	ACCESS		read-only
	STATUS		mandatory
	DESCRIPTION	"The total of the readings of all amperage probes, in milliamps."
	REFERENCE 	"NetBotz Total Amperage Probe"
	::= { netBotz-prd-bot 44 }

netBotz-prd-bot-amps-total-enabled OBJECT-TYPE
	SYNTAX		INTEGER
	ACCESS		read-write
	STATUS		mandatory
	DESCRIPTION	"Total amperage alarm enabled(1) or disabled(0)."
	REFERENCE 	"NetBotz|Total Amperage Enabled"
	::= { netBotz-prd-bot 45 }

netBotz-prd-bot-amps-total-min OBJECT-TYPE
	SYNTAX		INTEGER
	ACCESS		read-write
	STATUS		mandatory
	DESCRIPTION	"The total amperage minimum, from 0 to 90000 milliamps."
	REFERENCE 	"NetBotz Total Amperage Minimum"
	::= { netBotz-prd-bot 46 }

netBotz-prd-bot-amps-total-max OBJECT-TYPE
	SYNTAX		INTEGER
	ACCESS		read-write
	STATUS		mandatory
	DESCRIPTION	"The total amperage maximum, from 0 to 90000 milliamps."
	REFERENCE 	"NetBotz Total Amperage Maximum"
	::= { netBotz-prd-bot 47 }

netBotz-prd-bot-amps-total-support-enabled OBJECT-TYPE
	SYNTAX		DisplayString
	ACCESS		read-write
	STATUS		mandatory
	DESCRIPTION	"Total Amperage Support enabled(Y) or disabled(N)."
	REFERENCE 	"NetBotz|Total Amperage Support Enabled"
	::= { netBotz-prd-bot 48 }

netBotz-prd-bot-amps1-uV-per-10mA OBJECT-TYPE
	SYNTAX		INTEGER
	ACCESS		read-write
	STATUS		mandatory
	DESCRIPTION	"The scaling factor used for the first amperage probe to convert microvolts measured from the
        Amp Detect into 10s of milliamps of current.  Needs to be set based on the type of Amp Detect module installed."
	REFERENCE 	"NetBotz uVolts To 10 mAmps 1"
	::= { netBotz-prd-bot 49 }

netBotz-prd-bot-amps2-uV-per-10mA OBJECT-TYPE
	SYNTAX		INTEGER
	ACCESS		read-write
	STATUS		mandatory
	DESCRIPTION	"The scaling factor used for the second amperage probe to convert microvolts measured from the
        Amp Detect into 10s of milliamps of current.  Needs to be set based on the type of Amp Detect module installed."
	REFERENCE 	"NetBotz uVolts To 10 mAmps 2"
	::= { netBotz-prd-bot 50 }

netBotz-prd-bot-amps3-uV-per-mA OBJECT-TYPE
	SYNTAX		INTEGER
	ACCESS		read-write
	STATUS		mandatory
	DESCRIPTION	"The scaling factor used for the third amperage probe to convert microvolts measured from the
        Amp Detect into 10s of milliamps of current.  Needs to be set based on the type of Amp Detect module installed."
	REFERENCE 	"NetBotz uVolts To 10 mAmps 3"
	::= { netBotz-prd-bot 51 }

netBotz-prd-bot-amps1-max-range OBJECT-TYPE
	SYNTAX		INTEGER
	ACCESS		read-write
	STATUS		mandatory
	DESCRIPTION	"The maximum RMS milliamps measureable by the first Amp Detect."
	REFERENCE 	"NetBotz Max milliAmps 1"
	::= { netBotz-prd-bot 52 }

netBotz-prd-bot-amps2-max-range OBJECT-TYPE
	SYNTAX		INTEGER
	ACCESS		read-write
	STATUS		mandatory
	DESCRIPTION	"The maximum RMS milliamps measureable by the second Amp Detect."
	REFERENCE 	"NetBotz Max milliAmps 2"
	::= { netBotz-prd-bot 53 }

netBotz-prd-bot-amps3-max-range OBJECT-TYPE
	SYNTAX		INTEGER
	ACCESS		read-write
	STATUS		mandatory
	DESCRIPTION	"The maximum RMS milliamps measureable by the third Amp Detect."
	REFERENCE 	"NetBotz Max milliAmps 3"
	::= { netBotz-prd-bot 54 }

netBotz-prd-bot-amps4 OBJECT-TYPE
	SYNTAX		INTEGER
	ACCESS		read-only
	STATUS		mandatory
	DESCRIPTION	"The reading of the fourth amperage probe, in milliamps."
	REFERENCE 	"NetBotz Amperage[4] Probe"
	::= { netBotz-prd-bot 55 }

netBotz-prd-bot-amps4-enabled OBJECT-TYPE
	SYNTAX		INTEGER
	ACCESS		read-write
	STATUS		mandatory
	DESCRIPTION	"Amperage[4] probe alarm enabled(1) or disabled(0)."
	REFERENCE 	"NetBotz|Amperage[4] Probe Enabled"
	::= { netBotz-prd-bot 56 }

netBotz-prd-bot-amps4-min OBJECT-TYPE
	SYNTAX		INTEGER
	ACCESS		read-write
	STATUS		mandatory
	DESCRIPTION	"The amperage[4] probe minimum, in milliamps."
	REFERENCE 	"NetBotz Amperage[4] Probe Minimum"
	::= { netBotz-prd-bot 57 }

netBotz-prd-bot-amps4-max OBJECT-TYPE
	SYNTAX		INTEGER
	ACCESS		read-write
	STATUS		mandatory
	DESCRIPTION	"The amperage[4] probe maximum, in milliamps."
	REFERENCE 	"NetBotz Amperage[4] Probe Maximum"
	::= { netBotz-prd-bot 58 }

netBotz-prd-bot-amps4-uV-per-10mA OBJECT-TYPE
	SYNTAX		INTEGER
	ACCESS		read-write
	STATUS		mandatory
	DESCRIPTION	"The scaling factor used for the fourth amperage probe to convert microvolts measured from the
        Amp Detect into 10s of milliamps of current.  Needs to be set based on the type of Amp Detect module installed."
	REFERENCE 	"NetBotz uVolts To 10 mAmps 4"
	::= { netBotz-prd-bot 60 }

netBotz-prd-bot-amps4-max-range OBJECT-TYPE
	SYNTAX		INTEGER
	ACCESS		read-write
	STATUS		mandatory
	DESCRIPTION	"The maximum RMS milliamps measureable by the fourth Amp Detect."
	REFERENCE 	"NetBotz Max milliAmps 4"
	::= { netBotz-prd-bot 61 }

netBotz-prd-bot-ext-temp1 OBJECT-TYPE
	SYNTAX		INTEGER
	ACCESS		read-only
	STATUS		mandatory
	DESCRIPTION	"The reading of the external temperature probe on port 1, in degrees F or degrees C (depends on netBotz-ismetric)."
	REFERENCE 	"NetBotz External Temperature Probe 1"
	::= { netBotz-prd-bot 62 }

netBotz-prd-bot-ext-temp2 OBJECT-TYPE
	SYNTAX		INTEGER
	ACCESS		read-only
	STATUS		mandatory
	DESCRIPTION	"The reading of the external temperature probe on port 2, in degrees F or degrees C (depends on netBotz-ismetric)."
	REFERENCE 	"NetBotz External Temperature Probe 2"
	::= { netBotz-prd-bot 63 }

netBotz-prd-bot-ext-temp3 OBJECT-TYPE
	SYNTAX		INTEGER
	ACCESS		read-only
	STATUS		mandatory
	DESCRIPTION	"The reading of the external temperature probe on port 3, in degrees F or degrees C (depends on netBotz-ismetric)."
	REFERENCE 	"NetBotz External Temperature Probe 3"
	::= { netBotz-prd-bot 64 }

netBotz-prd-bot-ext-temp1-enabled OBJECT-TYPE
	SYNTAX		INTEGER
	ACCESS		read-write
	STATUS		mandatory
	DESCRIPTION	"External temperature probe on port 1 alarm enabled(1) or disabled(0)."
	REFERENCE 	"NetBotz|Ext Temp[1] Probe Enabled"
	::= { netBotz-prd-bot 66 }

netBotz-prd-bot-ext-temp1-min OBJECT-TYPE
	SYNTAX		INTEGER
	ACCESS		read-write
	STATUS		mandatory
	DESCRIPTION	"The external temperature probe on port 1 probe minimum, in degrees F or degrees C (depends on netBotz-ismetric)."
	REFERENCE 	"NetBotz Ext Temp[1] Probe Minimum"
	::= { netBotz-prd-bot 67 }

netBotz-prd-bot-ext-temp1-max OBJECT-TYPE
	SYNTAX		INTEGER
	ACCESS		read-write
	STATUS		mandatory
	DESCRIPTION	"The external temperature probe on port 1 probe maximum, in degrees F or degrees C (depends on netBotz-ismetric)."
	REFERENCE 	"NetBotz Ext Temp[1] Probe Maximum"
	::= { netBotz-prd-bot 68 }

netBotz-prd-bot-ext-temp2-enabled OBJECT-TYPE
	SYNTAX		INTEGER
	ACCESS		read-write
	STATUS		mandatory
	DESCRIPTION	"External temperature probe on port 2 alarm enabled(1) or disabled(0)."
	REFERENCE 	"NetBotz|Ext Temp[2] Probe Enabled"
	::= { netBotz-prd-bot 69 }

netBotz-prd-bot-ext-temp2-min OBJECT-TYPE
	SYNTAX		INTEGER
	ACCESS		read-write
	STATUS		mandatory
	DESCRIPTION	"The external temperature probe on port 2 probe minimum, in degrees F or degrees C (depends on netBotz-ismetric)."
	REFERENCE 	"NetBotz Ext Temp[2] Probe Minimum"
	::= { netBotz-prd-bot 70 }

netBotz-prd-bot-ext-temp2-max OBJECT-TYPE
	SYNTAX		INTEGER
	ACCESS		read-write
	STATUS		mandatory
	DESCRIPTION	"The external temperature probe on port 2 probe maximum, in degrees F or degrees C (depends on netBotz-ismetric)."
	REFERENCE 	"NetBotz Ext Temp[2] Probe Maximum"
	::= { netBotz-prd-bot 71 }

netBotz-prd-bot-ext-temp3-enabled OBJECT-TYPE
	SYNTAX		INTEGER
	ACCESS		read-write
	STATUS		mandatory
	DESCRIPTION	"External temperature probe on port 3 alarm enabled(1) or disabled(0)."
	REFERENCE 	"NetBotz|Ext Temp[3] Probe Enabled"
	::= { netBotz-prd-bot 72 }

netBotz-prd-bot-ext-temp3-min OBJECT-TYPE
	SYNTAX		INTEGER
	ACCESS		read-write
	STATUS		mandatory
	DESCRIPTION	"The external temperature probe on port 3 probe minimum, in degrees F or degrees C (depends on netBotz-ismetric)."
	REFERENCE 	"NetBotz Ext Temp[3] Probe Minimum"
	::= { netBotz-prd-bot 73 }

netBotz-prd-bot-ext-temp3-max OBJECT-TYPE
	SYNTAX		INTEGER
	ACCESS		read-write
	STATUS		mandatory
	DESCRIPTION	"The external temperature probe on port 3 probe maximum, in degrees F or degrees C (depends on netBotz-ismetric)."
	REFERENCE 	"NetBotz Ext Temp[3] Probe Maximum"
	::= { netBotz-prd-bot 74 }

netBotz-prd-bot-ext-temp1-uV-per-degreeC OBJECT-TYPE
	SYNTAX		INTEGER
	ACCESS		read-write
	STATUS		mandatory
	DESCRIPTION	"The scaling factor used for the external temperature probe on port 1 to convert microvolts measured from the
        temperature sensor into degrees C.  Needs to be set based on the type of temperature sensor module installed."
	REFERENCE 	"NetBotz uVolts To degrees C - 1"
	::= { netBotz-prd-bot 78 }

netBotz-prd-bot-ext-temp1-uV-at-0-degreeC OBJECT-TYPE
	SYNTAX		INTEGER
	ACCESS		read-write
	STATUS		mandatory
	DESCRIPTION	"The offset used for the external temperature probe on port 1 of microvolts measured from the
        temperature sensor at zero degrees C.  Needs to be set based on the type of temperature sensor module installed."
	REFERENCE 	"NetBotz uVolts at 0 degrees C - 1"
	::= { netBotz-prd-bot 79 }

netBotz-prd-bot-ext-temp1-max-range OBJECT-TYPE
	SYNTAX		INTEGER
	ACCESS		read-write
	STATUS		mandatory
	DESCRIPTION	"The maximum temperature measureable by the temperature sensor installed on port 1, in tenths of a degree C.
        Needs to be set based on the type of temperature sensor module installed."
	REFERENCE 	"NetBotz Max temperature supported - 1"
	::= { netBotz-prd-bot 81 }

netBotz-prd-bot-ext-temp1-min-range OBJECT-TYPE
	SYNTAX		INTEGER
	ACCESS		read-write
	STATUS		mandatory
	DESCRIPTION	"The minimum temperature measureable by the temperature sensor installed on port 1, in tenths of a degree C.
        Needs to be set based on the type of temperature sensor module installed."
	REFERENCE 	"NetBotz min temperature supported - 1"
	::= { netBotz-prd-bot 80 }

netBotz-prd-bot-ext-temp2-uV-per-degreeC OBJECT-TYPE
	SYNTAX		INTEGER
	ACCESS		read-write
	STATUS		mandatory
	DESCRIPTION	"The scaling factor used for the external temperature probe on port 2 to convert microvolts measured from the
        temperature sensor into degrees C.  Needs to be set based on the type of temperature sensor module installed."
	REFERENCE 	"NetBotz uVolts To degrees C - 2"
	::= { netBotz-prd-bot 82 }

netBotz-prd-bot-ext-temp2-uV-at-0-degreeC OBJECT-TYPE
	SYNTAX		INTEGER
	ACCESS		read-write
	STATUS		mandatory
	DESCRIPTION	"The offset used for the external temperature probe on port 2 of microvolts measured from the
        temperature sensor at zero degrees C.  Needs to be set based on the type of temperature sensor module installed."
	REFERENCE 	"NetBotz uVolts at 0 degrees C - 2"
	::= { netBotz-prd-bot 83 }

netBotz-prd-bot-ext-temp2-max-range OBJECT-TYPE
	SYNTAX		INTEGER
	ACCESS		read-write
	STATUS		mandatory
	DESCRIPTION	"The maximum temperature measureable by the temperature sensor installed on port 2, in tenths of a degree C.
        Needs to be set based on the type of temperature sensor module installed."
	REFERENCE 	"NetBotz Max temperature supported - 2"
	::= { netBotz-prd-bot 85 }

netBotz-prd-bot-ext-temp2-min-range OBJECT-TYPE
	SYNTAX		INTEGER
	ACCESS		read-write
	STATUS		mandatory
	DESCRIPTION	"The minimum temperature measureable by the temperature sensor installed on port 2, in tenths of a degree C.
        Needs to be set based on the type of temperature sensor module installed."
	REFERENCE 	"NetBotz min temperature supported - 2"
	::= { netBotz-prd-bot 84 }

netBotz-prd-bot-ext-temp3-uV-per-degreeC OBJECT-TYPE
	SYNTAX		INTEGER
	ACCESS		read-write
	STATUS		mandatory
	DESCRIPTION	"The scaling factor used for the external temperature probe on port 3 to convert microvolts measured from the
        temperature sensor into degrees C.  Needs to be set based on the type of temperature sensor module installed."
	REFERENCE 	"NetBotz uVolts To degrees C - 3"
	::= { netBotz-prd-bot 86 }

netBotz-prd-bot-ext-temp3-uV-at-0-degreeC OBJECT-TYPE
	SYNTAX		INTEGER
	ACCESS		read-write
	STATUS		mandatory
	DESCRIPTION	"The offset used for the external temperature probe on port 3 of microvolts measured from the
        temperature sensor at zero degrees C.  Needs to be set based on the type of temperature sensor module installed."
	REFERENCE 	"NetBotz uVolts at 0 degrees C - 3"
	::= { netBotz-prd-bot 87 }

netBotz-prd-bot-ext-temp3-max-range OBJECT-TYPE
	SYNTAX		INTEGER
	ACCESS		read-write
	STATUS		mandatory
	DESCRIPTION	"The maximum temperature measureable by the temperature sensor installed on port 3, in tenths of a degree C.
        Needs to be set based on the type of temperature sensor module installed."
	REFERENCE 	"NetBotz Max temperature supported - 3"
	::= { netBotz-prd-bot 89 }

netBotz-prd-bot-ext-temp3-min-range OBJECT-TYPE
	SYNTAX		INTEGER
	ACCESS		read-write
	STATUS		mandatory
	DESCRIPTION	"The minimum temperature measureable by the temperature sensor installed on port 3, in tenths of a degree C.
        Needs to be set based on the type of temperature sensor module installed."
	REFERENCE 	"NetBotz min temperature supported - 3"
	::= { netBotz-prd-bot 88 }

netBotz-prd-bot-ext-port1-module-id OBJECT-TYPE
	SYNTAX		DisplayString
	ACCESS		read-write
	STATUS		mandatory
	DESCRIPTION	"The module ID of the sensor module installed on port 1.  Blank string indicates that no module is installed."
	REFERENCE 	"NetBotz module ID port 1"
	::= { netBotz-prd-bot 94 }

netBotz-prd-bot-ext-port1-module-type OBJECT-TYPE
	SYNTAX		DisplayString
	ACCESS		read-write
	STATUS		mandatory
	DESCRIPTION	"The type of sensor module installed on port 1.  NONE=no module, AMP=AmpDetect module, TEMP=temperature sensor, DRY=dry contact sensor."
	REFERENCE 	"NetBotz module type port 1"
	::= { netBotz-prd-bot 95 }

netBotz-prd-bot-ext-port2-module-id OBJECT-TYPE
	SYNTAX		DisplayString
	ACCESS		read-write
	STATUS		mandatory
	DESCRIPTION	"The module ID of the sensor module installed on port 2.  Blank string indicates that no module is installed."
	REFERENCE 	"NetBotz module ID port 2"
	::= { netBotz-prd-bot 96 }

netBotz-prd-bot-ext-port2-module-type OBJECT-TYPE
	SYNTAX		DisplayString
	ACCESS		read-write
	STATUS		mandatory
	DESCRIPTION	"The type of sensor module installed on port 2.  NONE=no module, AMP=AmpDetect module, TEMP=temperature sensor, DRY=dry contact sensor."
	REFERENCE 	"NetBotz module type port 2"
	::= { netBotz-prd-bot 97 }

netBotz-prd-bot-ext-port3-module-id OBJECT-TYPE
	SYNTAX		DisplayString
	ACCESS		read-write
	STATUS		mandatory
	DESCRIPTION	"The module ID of the sensor module installed on port 3.  Blank string indicates that no module is installed."
	REFERENCE 	"NetBotz module ID port 3"
	::= { netBotz-prd-bot 98 }

netBotz-prd-bot-ext-port3-module-type OBJECT-TYPE
	SYNTAX		DisplayString
	ACCESS		read-write
	STATUS		mandatory
	DESCRIPTION	"The type of sensor module installed on port 3.  NONE=no module, AMP=AmpDetect module, TEMP=temperature sensor, DRY=dry contact sensor."
	REFERENCE 	"NetBotz module type port 3"
	::= { netBotz-prd-bot 99 }

netBotz-prd-bot-amp1-total-amp-seconds OBJECT-TYPE
	SYNTAX		INTEGER
	ACCESS		read-only
	STATUS		mandatory
	DESCRIPTION	"The accumulated total of amp-seconds on the AmpDetect on port 1."
	REFERENCE 	"NetBotz Total Amp-Seconds - 1"
	::= { netBotz-prd-bot 102 }

netBotz-prd-bot-amp1-total-amp-seconds-since-time OBJECT-TYPE
	SYNTAX		INTEGER
	ACCESS		read-write
	STATUS		mandatory
	DESCRIPTION	"The UTC time (seconds since 1/1/1970) of the beginning of the accumulated total of amp-seconds on the AmpDetect on port 1.
        Writing a value to this attribute resets the accumulated total amp-seconds and sets this time to the current time."
	REFERENCE 	"NetBotz Total Amp-Seconds reset time - 1"
	::= { netBotz-prd-bot 103 }

netBotz-prd-bot-amp2-total-amp-seconds OBJECT-TYPE
	SYNTAX		INTEGER
	ACCESS		read-only
	STATUS		mandatory
	DESCRIPTION	"The accumulated total of amp-seconds on the AmpDetect on port 2."
	REFERENCE 	"NetBotz Total Amp-Seconds - 2"
	::= { netBotz-prd-bot 104 }

netBotz-prd-bot-amp2-total-amp-seconds-since-time OBJECT-TYPE
	SYNTAX		INTEGER
	ACCESS		read-write
	STATUS		mandatory
	DESCRIPTION	"The UTC time (seconds since 1/1/1970) of the beginning of the accumulated total of amp-seconds on the AmpDetect on port 2.
        Writing a value to this attribute resets the accumulated total amp-seconds and sets this time to the current time."
	REFERENCE 	"NetBotz Total Amp-Seconds reset time - 2"
	::= { netBotz-prd-bot 105 }

netBotz-prd-bot-amp3-total-amp-seconds OBJECT-TYPE
	SYNTAX		INTEGER
	ACCESS		read-only
	STATUS		mandatory
	DESCRIPTION	"The accumulated total of amp-seconds on the AmpDetect on port 3."
	REFERENCE 	"NetBotz Total Amp-Seconds - 3"
	::= { netBotz-prd-bot 106 }

netBotz-prd-bot-amp3-total-amp-seconds-since-time OBJECT-TYPE
	SYNTAX		INTEGER
	ACCESS		read-write
	STATUS		mandatory
	DESCRIPTION	"The UTC time (seconds since 1/1/1970) of the beginning of the accumulated total of amp-seconds on the AmpDetect on port 3.
        Writing a value to this attribute resets the accumulated total amp-seconds and sets this time to the current time."
	REFERENCE 	"NetBotz Total Amp-Seconds reset time - 3"
	::= { netBotz-prd-bot 107 }

netBotz-prd-bot-amp4-total-amp-seconds OBJECT-TYPE
	SYNTAX		INTEGER
	ACCESS		read-only
	STATUS		mandatory
	DESCRIPTION	"The accumulated total of amp-seconds on the AmpDetect on port 4."
	REFERENCE 	"NetBotz Total Amp-Seconds - 4"
	::= { netBotz-prd-bot 108 }

netBotz-prd-bot-amp4-total-amp-seconds-since-time OBJECT-TYPE
	SYNTAX		INTEGER
	ACCESS		read-write
	STATUS		mandatory
	DESCRIPTION	"The UTC time (seconds since 1/1/1970) of the beginning of the accumulated total of amp-seconds on the AmpDetect on port 4.
        Writing a value to this attribute resets the accumulated total amp-seconds and sets this time to the current time."
	REFERENCE 	"NetBotz Total Amp-Seconds reset time - 4"
	::= { netBotz-prd-bot 109 }

netBotz-prd-bot-amptotal-total-amp-seconds OBJECT-TYPE
	SYNTAX		INTEGER
	ACCESS		read-only
	STATUS		mandatory
	DESCRIPTION	"The accumulated total of amp-seconds on the total of all AmpDetects."
	REFERENCE 	"NetBotz Total Amp-Seconds - total"
	::= { netBotz-prd-bot 110 }

netBotz-prd-bot-amptotal-total-amp-seconds-since-time OBJECT-TYPE
	SYNTAX		INTEGER
	ACCESS		read-write
	STATUS		mandatory
	DESCRIPTION	"The UTC time (seconds since 1/1/1970) of the beginning of the accumulated total of amp-seconds for all AmpDetects.
        Writing a value to this attribute resets the accumulated total amp-seconds and sets this time to the current time."
	REFERENCE 	"NetBotz Total Amp-Seconds reset time - total"
	::= { netBotz-prd-bot 111 }

netBotz-prd-bot-ext-dry1 OBJECT-TYPE
	SYNTAX		INTEGER
	ACCESS		read-only
	STATUS		mandatory
	DESCRIPTION	"The current value of the external dry contact sensor on Ext1: 0=Open, 1=Closed, -1=N/A"
	REFERENCE 	"NetBotz Ext Dry 1"
	::= { netBotz-prd-bot 112 }

netBotz-prd-bot-ext-dry2 OBJECT-TYPE
	SYNTAX		INTEGER
	ACCESS		read-only
	STATUS		mandatory
	DESCRIPTION	"The current value of the external dry contact sensor on Ext2: 0=Open, 1=Closed, -1=N/A"
	REFERENCE 	"NetBotz Ext Dry 2"
	::= { netBotz-prd-bot 113 }

netBotz-prd-bot-ext-dry3 OBJECT-TYPE
	SYNTAX		INTEGER
	ACCESS		read-only
	STATUS		mandatory
	DESCRIPTION	"The current value of the external dry contact sensor on Ext3: 0=Open, 1=Closed, -1=N/A"
	REFERENCE 	"NetBotz Ext Dry 3"
	::= { netBotz-prd-bot 114 }

netBotz-prd-bot-ext-dry4 OBJECT-TYPE
	SYNTAX		INTEGER
	ACCESS		read-only
	STATUS		mandatory
	DESCRIPTION	"The current value of the external dry contact sensor on Ext4: 0=Open, 1=Closed, -1=N/A"
	REFERENCE 	"NetBotz Ext Dry 4"
	::= { netBotz-prd-bot 115 }

netBotz-prd-bot-ext-dry1-alarm-value OBJECT-TYPE
	SYNTAX		INTEGER
	ACCESS		read-write
	STATUS		mandatory
	DESCRIPTION	"The value to generate alarms on for the external dry contact sensor on Ext1: 0=Open, 1=Closed"
	REFERENCE 	"NetBotz Ext Dry 1 Alarm Value"
	::= { netBotz-prd-bot 116 }

netBotz-prd-bot-ext-dry1-enabled OBJECT-TYPE
	SYNTAX		INTEGER
	ACCESS		read-write
	STATUS		mandatory
	DESCRIPTION	"External dry contact sensor on Ext1 alarm enabled(1) or disabled(0)."
	REFERENCE 	"NetBotz Ext Dry 1 Alarm Enabled"
	::= { netBotz-prd-bot 117 }

netBotz-prd-bot-ext-dry2-alarm-value OBJECT-TYPE
	SYNTAX		INTEGER
	ACCESS		read-write
	STATUS		mandatory
	DESCRIPTION	"The value to generate alarms on for the external dry contact sensor on Ext2: 0=Open, 1=Closed"
	REFERENCE 	"NetBotz Ext Dry 2 Alarm Value"
	::= { netBotz-prd-bot 118 }

netBotz-prd-bot-ext-dry2-enabled OBJECT-TYPE
	SYNTAX		INTEGER
	ACCESS		read-write
	STATUS		mandatory
	DESCRIPTION	"External dry contact sensor on Ext2 alarm enabled(1) or disabled(0)."
	REFERENCE 	"NetBotz Ext Dry 2 Alarm Enabled"
	::= { netBotz-prd-bot 119 }

netBotz-prd-bot-ext-dry3-alarm-value OBJECT-TYPE
	SYNTAX		INTEGER
	ACCESS		read-write
	STATUS		mandatory
	DESCRIPTION	"The value to generate alarms on for the external dry contact sensor on Ext3: 0=Open, 1=Closed"
	REFERENCE 	"NetBotz Ext Dry 3 Alarm Value"
	::= { netBotz-prd-bot 120 }

netBotz-prd-bot-ext-dry3-enabled OBJECT-TYPE
	SYNTAX		INTEGER
	ACCESS		read-write
	STATUS		mandatory
	DESCRIPTION	"External dry contact sensor on Ext3 alarm enabled(1) or disabled(0)."
	REFERENCE 	"NetBotz Ext Dry 3 Alarm Enabled"
	::= { netBotz-prd-bot 121 }

netBotz-prd-bot-ext-dry4-alarm-value OBJECT-TYPE
	SYNTAX		INTEGER
	ACCESS		read-write
	STATUS		mandatory
	DESCRIPTION	"The value to generate alarms on for the external dry contact sensor on Ext4: 0=Open, 1=Closed"
	REFERENCE 	"NetBotz Ext Dry 4 Alarm Value"
	::= { netBotz-prd-bot 122 }

netBotz-prd-bot-ext-dry4-enabled OBJECT-TYPE
	SYNTAX		INTEGER
	ACCESS		read-write
	STATUS		mandatory
	DESCRIPTION	"External dry contact sensor on Ext4 alarm enabled(1) or disabled(0)."
	REFERENCE 	"NetBotz Ext Dry 4 Alarm Enabled"
	::= { netBotz-prd-bot 123 }

netBotz-prd-bot-ext-dry1-label OBJECT-TYPE
	SYNTAX		DisplayString
	ACCESS		read-write
	STATUS		mandatory
	DESCRIPTION	"The sensor name/label for the dry contact sensor on Ext1"
	REFERENCE 	"NetBotz Ext Dry 1 Label"
	::= { netBotz-prd-bot 124 }

netBotz-prd-bot-ext-dry1-open-label OBJECT-TYPE
	SYNTAX		DisplayString
	ACCESS		read-write
	STATUS		mandatory
	DESCRIPTION	"The sensor name/label for the open(0) state for the dry contact sensor on Ext1"
	REFERENCE 	"NetBotz Ext Dry 1 Open Label"
	::= { netBotz-prd-bot 125 }

netBotz-prd-bot-ext-dry1-closed-label OBJECT-TYPE
	SYNTAX		DisplayString
	ACCESS		read-write
	STATUS		mandatory
	DESCRIPTION	"The sensor name/label for the closed(0) state for the dry contact sensor on Ext1"
	REFERENCE 	"NetBotz Ext Dry 1 Closed Label"
	::= { netBotz-prd-bot 126 }

netBotz-prd-bot-ext-dry1-open-to-close-millis OBJECT-TYPE
	SYNTAX		INTEGER
	ACCESS		read-write
	STATUS		mandatory
	DESCRIPTION	"The minimum number of milliseconds that the dry contact sensor on Ext1
			must read closed before the state is changed from open to closed."
	REFERENCE 	"NetBotz Ext Dry 1 Open-to-Closed Millis"
	::= { netBotz-prd-bot 127 }

netBotz-prd-bot-ext-dry1-close-to-open-millis OBJECT-TYPE
	SYNTAX		INTEGER
	ACCESS		read-write
	STATUS		mandatory
	DESCRIPTION	"The minimum number of milliseconds that the dry contact sensor on Ext1
			must read openbefore the state is changed from closed to open."
	REFERENCE 	"NetBotz Ext Dry 1 Closed-to-Open Millis"
	::= { netBotz-prd-bot 128 }

netBotz-prd-bot-ext-dry1-response OBJECT-TYPE
	SYNTAX		DisplayString
	ACCESS		read-write
	STATUS		mandatory
	DESCRIPTION	"The type of alert response for the dry contact sensor on Ext1: ALERT=e-mail with no
		pictures, CAMERA=e-mail with pictures from camera."
	REFERENCE 	"NetBotz Ext Dry 1 Response"
	::= { netBotz-prd-bot 129 }

netBotz-prd-bot-ext-dry2-label OBJECT-TYPE
	SYNTAX		DisplayString
	ACCESS		read-write
	STATUS		mandatory
	DESCRIPTION	"The sensor name/label for the dry contact sensor on Ext2"
	REFERENCE 	"NetBotz Ext Dry 2 Label"
	::= { netBotz-prd-bot 130 }

netBotz-prd-bot-ext-dry2-open-label OBJECT-TYPE
	SYNTAX		DisplayString
	ACCESS		read-write
	STATUS		mandatory
	DESCRIPTION	"The sensor name/label for the open(0) state for the dry contact sensor on Ext2"
	REFERENCE 	"NetBotz Ext Dry 2 Open Label"
	::= { netBotz-prd-bot 131 }

netBotz-prd-bot-ext-dry2-closed-label OBJECT-TYPE
	SYNTAX		DisplayString
	ACCESS		read-write
	STATUS		mandatory
	DESCRIPTION	"The sensor name/label for the closed(0) state for the dry contact sensor on Ext2"
	REFERENCE 	"NetBotz Ext Dry 2 Closed Label"
	::= { netBotz-prd-bot 132 }

netBotz-prd-bot-ext-dry2-open-to-close-millis OBJECT-TYPE
	SYNTAX		INTEGER
	ACCESS		read-write
	STATUS		mandatory
	DESCRIPTION	"The minimum number of milliseconds that the dry contact sensor on Ext2
			must read closed before the state is changed from open to closed."
	REFERENCE 	"NetBotz Ext Dry 2 Open-to-Closed Millis"
	::= { netBotz-prd-bot 133 }

netBotz-prd-bot-ext-dry2-close-to-open-millis OBJECT-TYPE
	SYNTAX		INTEGER
	ACCESS		read-write
	STATUS		mandatory
	DESCRIPTION	"The minimum number of milliseconds that the dry contact sensor on Ext2
			must read openbefore the state is changed from closed to open."
	REFERENCE 	"NetBotz Ext Dry 2 Closed-to-Open Millis"
	::= { netBotz-prd-bot 134 }

netBotz-prd-bot-ext-dry2-response OBJECT-TYPE
	SYNTAX		DisplayString
	ACCESS		read-write
	STATUS		mandatory
	DESCRIPTION	"The type of alert response for the dry contact sensor on Ext2: ALERT=e-mail with no
		pictures, CAMERA=e-mail with pictures from camera."
	REFERENCE 	"NetBotz Ext Dry 2 Response"
	::= { netBotz-prd-bot 135 }

netBotz-prd-bot-ext-dry3-label OBJECT-TYPE
	SYNTAX		DisplayString
	ACCESS		read-write
	STATUS		mandatory
	DESCRIPTION	"The sensor name/label for the dry contact sensor on Ext3"
	REFERENCE 	"NetBotz Ext Dry 3 Label"
	::= { netBotz-prd-bot 136 }

netBotz-prd-bot-ext-dry3-open-label OBJECT-TYPE
	SYNTAX		DisplayString
	ACCESS		read-write
	STATUS		mandatory
	DESCRIPTION	"The sensor name/label for the open(0) state for the dry contact sensor on Ext3"
	REFERENCE 	"NetBotz Ext Dry 3 Open Label"
	::= { netBotz-prd-bot 137 }

netBotz-prd-bot-ext-dry3-closed-label OBJECT-TYPE
	SYNTAX		DisplayString
	ACCESS		read-write
	STATUS		mandatory
	DESCRIPTION	"The sensor name/label for the closed(0) state for the dry contact sensor on Ext3"
	REFERENCE 	"NetBotz Ext Dry 3 Closed Label"
	::= { netBotz-prd-bot 138 }

netBotz-prd-bot-ext-dry3-open-to-close-millis OBJECT-TYPE
	SYNTAX		INTEGER
	ACCESS		read-write
	STATUS		mandatory
	DESCRIPTION	"The minimum number of milliseconds that the dry contact sensor on Ext3
			must read closed before the state is changed from open to closed."
	REFERENCE 	"NetBotz Ext Dry 3 Open-to-Closed Millis"
	::= { netBotz-prd-bot 139 }

netBotz-prd-bot-ext-dry3-close-to-open-millis OBJECT-TYPE
	SYNTAX		INTEGER
	ACCESS		read-write
	STATUS		mandatory
	DESCRIPTION	"The minimum number of milliseconds that the dry contact sensor on Ext3
			must read openbefore the state is changed from closed to open."
	REFERENCE 	"NetBotz Ext Dry 3 Closed-to-Open Millis"
	::= { netBotz-prd-bot 140 }

netBotz-prd-bot-ext-dry3-response OBJECT-TYPE
	SYNTAX		DisplayString
	ACCESS		read-write
	STATUS		mandatory
	DESCRIPTION	"The type of alert response for the dry contact sensor on Ext3: ALERT=e-mail with no
		pictures, CAMERA=e-mail with pictures from camera."
	REFERENCE 	"NetBotz Ext Dry 3 Response"
	::= { netBotz-prd-bot 141 }

netBotz-prd-bot-cam-motion OBJECT-TYPE
	SYNTAX		INTEGER
	ACCESS		read-only
	STATUS		mandatory
	DESCRIPTION	"The current motion reading for the camera motion sensor (0=none, 1=motion detected)"
	REFERENCE 	"NetBotz Camera Motion"
	::= { netBotz-prd-bot 148 }

netBotz-prd-bot-cam-motion-enabled OBJECT-TYPE
	SYNTAX		INTEGER
	ACCESS		read-write
	STATUS		mandatory
	DESCRIPTION	"Camera motion sensor alarm enabled(1) or disabled(0)."
	REFERENCE 	"NetBotz Camera Motion Sensor Alarm Enabled"
	::= { netBotz-prd-bot 149 }

netBotz-prd-bot-cam-motion-sensitivity OBJECT-TYPE
	SYNTAX		INTEGER
	ACCESS		read-write
	STATUS		mandatory
	DESCRIPTION	"Camera motion sensor sensitivity: 1=max, 15=min, 0=disabled."
	REFERENCE 	"NetBotz Camera Motion Sensor Sensitivity"
	::= { netBotz-prd-bot 150 }

netBotz-prd-bot-cam-motion-delay OBJECT-TYPE
	SYNTAX		INTEGER
	ACCESS		read-write
	STATUS		mandatory
	DESCRIPTION	"Camera motion sensor delay.  This is the minimum number of milliseconds of detected
		motion required before the alarm is triggered."
	REFERENCE 	"NetBotz Camera Motion Sensor Delay"
	::= { netBotz-prd-bot 151 }

netBotz-prd-bot-camera-event-autocycle OBJECT-TYPE
	SYNTAX		INTEGER
	ACCESS		read-write
	STATUS		mandatory
	DESCRIPTION	"Enables (1) or disables (0) the option to have the camera-based responses to
		alarm conditions automatically cycle as long as the condition persists."
	REFERENCE 	"Auto-cycle camera event response"
	::= { netBotz-prd-bot 152 }

netBotz-prd-bot-num-pix-before-alarm OBJECT-TYPE
	SYNTAX		INTEGER
	ACCESS		read-write
	STATUS		mandatory
	DESCRIPTION	"Controls the number of pictures to be captured before any triggered alarm."
	REFERENCE 	"Pre-Event Alarm Pictures"
	::= { netBotz-prd-bot 153 }

netBotz-prd-bot-delay-before-event-pix OBJECT-TYPE
	SYNTAX		INTEGER
	ACCESS		read-write
	STATUS		mandatory
	DESCRIPTION	"Controls the number of milliseconds before the first picture is captured
		after any triggered alarm."
	REFERENCE 	"Alarm Picture Delay"
	::= { netBotz-prd-bot 154 }

netBotz-prd-bot-delay-between-event-pix OBJECT-TYPE
	SYNTAX		INTEGER
	ACCESS		read-write
	STATUS		mandatory
	DESCRIPTION	"Controls the number of milliseconds between pictures captured
		after any triggered alarm."
	REFERENCE 	"Alarm Picture Interval"
	::= { netBotz-prd-bot 155 }

netBotz-prd-bot-cam-motion-area-of-motion OBJECT-TYPE
	SYNTAX		INTEGER
	ACCESS		read-write
	STATUS		mandatory
	DESCRIPTION	"Camera motion sensor area of motion: 1=max, 15=min, 0=disabled."
	REFERENCE 	"NetBotz Camera Motion Sensor Area of Motion"
	::= { netBotz-prd-bot 156 }

netBotz-prd-bot-cam-pix-for-duration-of-alerts OBJECT-TYPE
	SYNTAX		INTEGER
	ACCESS		read-write
	STATUS		mandatory
	DESCRIPTION	"Camera images gathered for duration of camera related alert: 0=no, 1=yes."
	REFERENCE	"NetBotz Camera Images For Duration of Alert"
	::= { netBotz-prd-bot 157 }

netBotz-prd-bot-camera-enabled OBJECT-TYPE
	SYNTAX		INTEGER
	ACCESS		read-write
	STATUS		mandatory
	DESCRIPTION	"Controls whether the camera is enabled or not: 0=no, 1=yes.  Changing this will reboot the appliance."
	REFERENCE	"NetBotz Camera Enabled"
	::= { netBotz-prd-bot 158 }

netBotz-prd-bot-camera-is-flipped OBJECT-TYPE
	SYNTAX		INTEGER
	ACCESS		read-write
	STATUS		mandatory
	DESCRIPTION	"Controls whether the camera image is flipped 180 degress or not: 0=no, 1=yes.  Changing this will reboot the appliance."
	REFERENCE	"NetBotz Camera Flipped"
	::= { netBotz-prd-bot 159 }

netBotz-prd-bot-camera-brightness OBJECT-TYPE
	SYNTAX		INTEGER
	ACCESS		read-write
	STATUS		mandatory
	DESCRIPTION	"Sets the brightness on the camera, from 20 to 180 (20 is low, 180 is high)."
	REFERENCE	"NetBotz Camera Brightness"
	::= { netBotz-prd-bot 160 }

netBotz-prd-bot-traps OBJECT IDENTIFIER
                     ::= { netBotz-products 100 }

netBotz-prd-bot-temperature-traps OBJECT IDENTIFIER
                     ::= { netBotz-prd-bot-traps 1 }

netBotz-prd-bot-humidity-traps OBJECT IDENTIFIER
                     ::= { netBotz-prd-bot-traps 2 }

netBotz-prd-bot-airflow-traps OBJECT IDENTIFIER
                     ::= { netBotz-prd-bot-traps 3 }

netBotz-prd-bot-audio-traps OBJECT IDENTIFIER
                     ::= { netBotz-prd-bot-traps 4 }

netBotz-prd-bot-door-traps OBJECT IDENTIFIER
                     ::= { netBotz-prd-bot-traps 5 }

netBotz-prd-bot-amp1-traps OBJECT IDENTIFIER
                     ::= { netBotz-prd-bot-traps 6 }

netBotz-prd-bot-amp2-traps OBJECT IDENTIFIER
                     ::= { netBotz-prd-bot-traps 7 }

netBotz-prd-bot-amp3-traps OBJECT IDENTIFIER
                     ::= { netBotz-prd-bot-traps 8 }

netBotz-prd-bot-amp4-traps OBJECT IDENTIFIER
                     ::= { netBotz-prd-bot-traps 9 }

netBotz-prd-bot-amp-total-traps OBJECT IDENTIFIER
                     ::= { netBotz-prd-bot-traps 10 }

netBotz-prd-bot-ext-temp1-traps OBJECT IDENTIFIER
                     ::= { netBotz-prd-bot-traps 11 }

netBotz-prd-bot-ext-temp2-traps OBJECT IDENTIFIER
                     ::= { netBotz-prd-bot-traps 12 }

netBotz-prd-bot-ext-temp3-traps OBJECT IDENTIFIER
                     ::= { netBotz-prd-bot-traps 13 }

netBotz-prd-bot-ext-temp4-traps OBJECT IDENTIFIER
                     ::= { netBotz-prd-bot-traps 14 }

netBotz-prd-bot-ext-dry1-traps OBJECT IDENTIFIER
                     ::= { netBotz-prd-bot-traps 15 }

netBotz-prd-bot-ext-dry2-traps OBJECT IDENTIFIER
                     ::= { netBotz-prd-bot-traps 16 }

netBotz-prd-bot-ext-dry3-traps OBJECT IDENTIFIER
                     ::= { netBotz-prd-bot-traps 17 }

netBotz-prd-bot-ext-dry4-traps OBJECT IDENTIFIER
                     ::= { netBotz-prd-bot-traps 18 }

netBotz-prd-bot-amp5-traps OBJECT IDENTIFIER
                     ::= { netBotz-prd-bot-traps 19 }

netBotz-prd-bot-amp6-traps OBJECT IDENTIFIER
                     ::= { netBotz-prd-bot-traps 20 }

netBotz-prd-bot-amp7-traps OBJECT IDENTIFIER
                     ::= { netBotz-prd-bot-traps 21 }

netBotz-prd-bot-ext-temp5-traps OBJECT IDENTIFIER
                     ::= { netBotz-prd-bot-traps 22 }

netBotz-prd-bot-ext-temp6-traps OBJECT IDENTIFIER
                     ::= { netBotz-prd-bot-traps 23 }

netBotz-prd-bot-ext-temp7-traps OBJECT IDENTIFIER
                     ::= { netBotz-prd-bot-traps 24 }

netBotz-prd-bot-ext-dry5-traps OBJECT IDENTIFIER
                     ::= { netBotz-prd-bot-traps 25 }

netBotz-prd-bot-ext-dry6-traps OBJECT IDENTIFIER
                     ::= { netBotz-prd-bot-traps 26 }

netBotz-prd-bot-ext-dry7-traps OBJECT IDENTIFIER
                     ::= { netBotz-prd-bot-traps 27 }

netBotz-prd-bot-camera-motion-traps OBJECT IDENTIFIER
                     ::= { netBotz-prd-bot-traps 28 }

netBotz-prd-bot-ext-humi1-traps OBJECT IDENTIFIER
		     ::= { netBotz-prd-bot-traps 29 }

netBotz-prd-bot-ext-humi2-traps OBJECT IDENTIFIER
		     ::= { netBotz-prd-bot-traps 30 }

netBotz-prd-bot-ext-humi3-traps OBJECT IDENTIFIER
		     ::= { netBotz-prd-bot-traps 31 }

netBotz-prd-bot-ext-humi4-traps OBJECT IDENTIFIER
		     ::= { netBotz-prd-bot-traps 32 }

netBotz-prd-bot-ext-humi5-traps OBJECT IDENTIFIER
		     ::= { netBotz-prd-bot-traps 33 }

netBotz-prd-bot-ext-humi6-traps OBJECT IDENTIFIER
		     ::= { netBotz-prd-bot-traps 34 }

netBotz-prd-bot-ext-humi7-traps OBJECT IDENTIFIER
		     ::= { netBotz-prd-bot-traps 35 }


netBotz-prd-bot-temperature-low-trap TRAP-TYPE
	ENTERPRISE netBotz-prd-bot-temperature-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Temperature Low Trap. This trap indicates that the lower
	limit for temperature has been exceeded."
	REFERENCE 	"NetBotz Temperature Low Trap"
	::= 1

netBotz-prd-bot-temperature-high-trap TRAP-TYPE
	ENTERPRISE netBotz-prd-bot-temperature-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Temperature High Trap. This trap indicates that the upper
	limit for temperature has been exceeded."
	REFERENCE 	"NetBotz Temperature High Trap"
	::= 2

netBotz-prd-bot-temperature-trap-clear TRAP-TYPE
	ENTERPRISE netBotz-prd-bot-temperature-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Temperature Cleared Trap. The trap has been cleared because
	the temperature value has returned to acceptable limits."
	REFERENCE 	"NetBotz Temperature Cleared Trap"
	::= 3

netBotz-prd-bot-humidity-low-trap TRAP-TYPE
	ENTERPRISE netBotz-prd-bot-humidity-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Humidity Low Trap. This trap indicates that the lower
	limit for humidity has been exceeded."
	REFERENCE 	"NetBotz Humidity Low Trap"
	::= 1

netBotz-prd-bot-humidity-high-trap TRAP-TYPE
	ENTERPRISE netBotz-prd-bot-humidity-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Humidity High Trap. This trap indicates that the upper
	limit for humidity has been exceeded."
	REFERENCE 	"NetBotz Humidity High Trap"
	::= 2

netBotz-prd-bot-humidity-trap-clear TRAP-TYPE
	ENTERPRISE netBotz-prd-bot-humidity-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Humidity Cleared Trap. The trap has been cleared because
	the humidity value has returned to acceptable limits."
	REFERENCE 	"NetBotz Humidity Cleared Trap"
	::= 3

netBotz-prd-bot-airflow-low-trap TRAP-TYPE
	ENTERPRISE netBotz-prd-bot-airflow-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Airflow Low Trap. This trap indicates that the lower
	limit for airflow has been exceeded."
	REFERENCE 	"NetBotz Airflow Low Trap"
	::= 1

netBotz-prd-bot-airflow-trap-clear TRAP-TYPE
	ENTERPRISE netBotz-prd-bot-airflow-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Airflow Cleared Trap. The trap has been cleared because
	the airflow value has returned to acceptable limits."
	REFERENCE 	"NetBotz Airflow Cleared Trap"
	::= 3

netBotz-prd-bot-audio-high-trap TRAP-TYPE
	ENTERPRISE netBotz-prd-bot-audio-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Audio High Trap. This trap indicates that the upper
	limit for audio has been exceeded."
	REFERENCE 	"NetBotz Audio High Trap"
	::= 2

netBotz-prd-bot-audio-trap-clear TRAP-TYPE
	ENTERPRISE netBotz-prd-bot-audio-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Audio Cleared Trap. The trap has been cleared because
	the audio value has returned to acceptable limits."
	REFERENCE 	"NetBotz Audio Cleared Trap"
	::= 3

netBotz-prd-bot-door-trap-tripped TRAP-TYPE
	ENTERPRISE netBotz-prd-bot-door-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Door Sensor Tripped Trap. This trap indicates that the door sensor
	has been triggered (i.e. opened, if the thresdhold has been set to trip on open, closed if otherwise)."
	REFERENCE 	"NetBotz Door Tripped Trap"
	::= 2

netBotz-prd-bot-door-trap-clear TRAP-TYPE
	ENTERPRISE netBotz-prd-bot-door-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Door Cleared Trap. The trap has been cleared because
	the door sensor has returned to normal (i.e. been closed, if the threshold has been set to trip on open)."
	REFERENCE 	"NetBotz Door Cleared Trap"
	::= 3

netBotz-prd-bot-amp1-low-trap TRAP-TYPE
	ENTERPRISE netBotz-prd-bot-amp1-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Amp1 Low Trap. This trap indicates that the lower
	limit for the first amp detect has been exceeded."
	REFERENCE 	"NetBotz Amp1 Low Trap"
	::= 1

netBotz-prd-bot-amp1-high-trap TRAP-TYPE
	ENTERPRISE netBotz-prd-bot-amp1-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Amp1 High Trap. This trap indicates that the upper
	limit for the first amp detect has been exceeded."
	REFERENCE 	"NetBotz Amp1 High Trap"
	::= 2

netBotz-prd-bot-amp1-trap-clear TRAP-TYPE
	ENTERPRISE netBotz-prd-bot-amp1-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Amp1 Cleared Trap. The trap has been cleared because
	the first amp detect value has returned to acceptable limits."
	REFERENCE 	"NetBotz Amp1 Cleared Trap"
	::= 3

netBotz-prd-bot-amp1-sensor-unplugged TRAP-TYPE
	ENTERPRISE netBotz-prd-bot-amp1-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Amp 1 Sensor Unplugged Trap. The sensor for the first AmpDetect is unplugged or malfunctioning."
	REFERENCE 	"NetBotz Amp 1 Unplugged Trap"
	::= 6

netBotz-prd-bot-amp1-sensor-replugged TRAP-TYPE
	ENTERPRISE netBotz-prd-bot-amp1-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Amp 1 Sensor Replugged Trap. The sensor for the first AmpDetect was unplugged, but has been reconnected."
	REFERENCE 	"NetBotz Amp 1 Replugged Trap"
	::= 7

netBotz-prd-bot-amp2-low-trap TRAP-TYPE
	ENTERPRISE netBotz-prd-bot-amp2-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Amp2 Low Trap. This trap indicates that the lower
	limit for the second amp detect has been exceeded."
	REFERENCE 	"NetBotz Amp2 Low Trap"
	::= 1

netBotz-prd-bot-amp2-high-trap TRAP-TYPE
	ENTERPRISE netBotz-prd-bot-amp2-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Amp2 High Trap. This trap indicates that the upper
	limit for the second amp detect has been exceeded."
	REFERENCE 	"NetBotz Amp2 High Trap"
	::= 2

netBotz-prd-bot-amp2-trap-clear TRAP-TYPE
	ENTERPRISE netBotz-prd-bot-amp2-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Amp2 Cleared Trap. The trap has been cleared because
	the second amp detect value has returned to acceptable limits."
	REFERENCE 	"NetBotz Amp2 Cleared Trap"
	::= 3

netBotz-prd-bot-amp2-sensor-unplugged TRAP-TYPE
	ENTERPRISE netBotz-prd-bot-amp2-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Amp 2 Sensor Unplugged Trap. The sensor for the second AmpDetect is unplugged or malfunctioning."
	REFERENCE 	"NetBotz Amp 2 Unplugged Trap"
	::= 6

netBotz-prd-bot-amp2-sensor-replugged TRAP-TYPE
	ENTERPRISE netBotz-prd-bot-amp2-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Amp 2 Sensor Replugged Trap. The sensor for the second AmpDetect was unplugged, but has been reconnected."
	REFERENCE 	"NetBotz Amp 2 Replugged Trap"
	::= 7

netBotz-prd-bot-amp3-low-trap TRAP-TYPE
	ENTERPRISE netBotz-prd-bot-amp3-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Amp3 Low Trap. This trap indicates that the lower
	limit for the third amp detect has been exceeded."
	REFERENCE 	"NetBotz Amp3 Low Trap"
	::= 1

netBotz-prd-bot-amp3-high-trap TRAP-TYPE
	ENTERPRISE netBotz-prd-bot-amp3-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Amp3 High Trap. This trap indicates that the upper
	limit for the third amp detect has been exceeded."
	REFERENCE 	"NetBotz Amp3 High Trap"
	::= 2

netBotz-prd-bot-amp3-trap-clear TRAP-TYPE
	ENTERPRISE netBotz-prd-bot-amp3-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Amp3 Cleared Trap. The trap has been cleared because
	the third amp detect value has returned to acceptable limits."
	REFERENCE 	"NetBotz Amp3 Cleared Trap"
	::= 3

netBotz-prd-bot-amp3-sensor-unplugged TRAP-TYPE
	ENTERPRISE netBotz-prd-bot-amp3-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Amp 3 Sensor Unplugged Trap. The sensor for the third AmpDetect is unplugged or malfunctioning."
	REFERENCE 	"NetBotz Amp 3 Unplugged Trap"
	::= 6

netBotz-prd-bot-amp3-sensor-replugged TRAP-TYPE
	ENTERPRISE netBotz-prd-bot-amp3-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Amp 3 Sensor Replugged Trap. The sensor for the third AmpDetect was unplugged, but has been reconnected."
	REFERENCE 	"NetBotz Amp 3 Replugged Trap"
	::= 7

netBotz-prd-bot-amp4-low-trap TRAP-TYPE
	ENTERPRISE netBotz-prd-bot-amp4-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Amp4 Low Trap. This trap indicates that the lower
	limit for the fourth amp detect has been exceeded."
	REFERENCE 	"NetBotz Amp4 Low Trap"
	::= 1

netBotz-prd-bot-amp4-high-trap TRAP-TYPE
	ENTERPRISE netBotz-prd-bot-amp4-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Amp4 High Trap. This trap indicates that the upper
	limit for the fourth amp detect has been exceeded."
	REFERENCE 	"NetBotz Amp4 High Trap"
	::= 2

netBotz-prd-bot-amp4-trap-clear TRAP-TYPE
	ENTERPRISE netBotz-prd-bot-amp4-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Amp4 Cleared Trap. The trap has been cleared because
	the fourth amp detect value has returned to acceptable limits."
	REFERENCE 	"NetBotz Amp4 Cleared Trap"
	::= 3

netBotz-prd-bot-amp4-sensor-unplugged TRAP-TYPE
	ENTERPRISE netBotz-prd-bot-amp4-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Amp 4 Sensor Unplugged Trap. The sensor for the fourth AmpDetect is unplugged or malfunctioning."
	REFERENCE 	"NetBotz Amp 4 Unplugged Trap"
	::= 6

netBotz-prd-bot-amp4-sensor-replugged TRAP-TYPE
	ENTERPRISE netBotz-prd-bot-amp4-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Amp 4 Sensor Replugged Trap. The sensor for the fourth AmpDetect was unplugged, but has been reconnected."
	REFERENCE 	"NetBotz Amp 4 Replugged Trap"
	::= 7

netBotz-prd-bot-amp5-low-trap TRAP-TYPE
	ENTERPRISE netBotz-prd-bot-amp5-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Amp 5 Low Trap. This trap indicates that the lower
	limit for the fifth amp detect has been exceeded."
	REFERENCE 	"NetBotz Amp 5 Low Trap"
	::= 1

netBotz-prd-bot-amp5-high-trap TRAP-TYPE
	ENTERPRISE netBotz-prd-bot-amp5-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Amp 5 High Trap. This trap indicates that the upper
	limit for the fifth amp detect has been exceeded."
	REFERENCE 	"NetBotz Amp 5 High Trap"
	::= 2

netBotz-prd-bot-amp5-trap-clear TRAP-TYPE
	ENTERPRISE netBotz-prd-bot-amp5-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Amp 5 Cleared Trap. The trap has been cleared because
	the fifth amp detect value has returned to acceptable limits."
	REFERENCE 	"NetBotz Amp 5 Cleared Trap"
	::= 3

netBotz-prd-bot-amp5-sensor-unplugged TRAP-TYPE
	ENTERPRISE netBotz-prd-bot-amp5-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Amp 5 Sensor Unplugged Trap. The sensor for the fifth AmpDetect is unplugged or malfunctioning."
	REFERENCE 	"NetBotz Amp 5 Unplugged Trap"
	::= 6

netBotz-prd-bot-amp5-sensor-replugged TRAP-TYPE
	ENTERPRISE netBotz-prd-bot-amp5-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Amp 5 Sensor Replugged Trap. The sensor for the fifth AmpDetect was unplugged, but has been reconnected."
	REFERENCE 	"NetBotz Amp 5 Replugged Trap"
	::= 7


netBotz-prd-bot-amp6-low-trap TRAP-TYPE
	ENTERPRISE netBotz-prd-bot-amp6-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Amp 6 Low Trap. This trap indicates that the lower
	limit for the sixth amp detect has been exceeded."
	REFERENCE 	"NetBotz Amp 6 Low Trap"
	::= 1

netBotz-prd-bot-amp6-high-trap TRAP-TYPE
	ENTERPRISE netBotz-prd-bot-amp6-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Amp 6 High Trap. This trap indicates that the upper
	limit for the sixth amp detect has been exceeded."
	REFERENCE 	"NetBotz Amp 6 High Trap"
	::= 2

netBotz-prd-bot-amp6-trap-clear TRAP-TYPE
	ENTERPRISE netBotz-prd-bot-amp6-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Amp 6 Cleared Trap. The trap has been cleared because
	the sixth amp detect value has returned to acceptable limits."
	REFERENCE 	"NetBotz Amp 6 Cleared Trap"
	::= 3

netBotz-prd-bot-amp6-sensor-unplugged TRAP-TYPE
	ENTERPRISE netBotz-prd-bot-amp6-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Amp 6 Sensor Unplugged Trap. The sensor for the sixth AmpDetect is unplugged or malfunctioning."
	REFERENCE 	"NetBotz Amp 6 Unplugged Trap"
	::= 6

netBotz-prd-bot-amp6-sensor-replugged TRAP-TYPE
	ENTERPRISE netBotz-prd-bot-amp6-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Amp 6 Sensor Replugged Trap. The sensor for the sixth AmpDetect was unplugged, but has been reconnected."
	REFERENCE 	"NetBotz Amp 6 Replugged Trap"
	::= 7

netBotz-prd-bot-amp7-low-trap TRAP-TYPE
	ENTERPRISE netBotz-prd-bot-amp7-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Amp 7 Low Trap. This trap indicates that the lower
	limit for the seventh amp detect has been exceeded."
	REFERENCE 	"NetBotz Amp 7 Low Trap"
	::= 1

netBotz-prd-bot-amp7-high-trap TRAP-TYPE
	ENTERPRISE netBotz-prd-bot-amp7-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Amp 7 High Trap. This trap indicates that the upper
	limit for the seventh amp detect has been exceeded."
	REFERENCE 	"NetBotz Amp 7 High Trap"
	::= 2

netBotz-prd-bot-amp7-trap-clear TRAP-TYPE
	ENTERPRISE netBotz-prd-bot-amp7-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Amp 7 Cleared Trap. The trap has been cleared because
	the seventh amp detect value has returned to acceptable limits."
	REFERENCE 	"NetBotz Amp 7 Cleared Trap"
	::= 3

netBotz-prd-bot-amp7-sensor-unplugged TRAP-TYPE
	ENTERPRISE netBotz-prd-bot-amp7-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Amp 7 Sensor Unplugged Trap. The sensor for the seventh AmpDetect is unplugged or malfunctioning."
	REFERENCE 	"NetBotz Amp 7 Unplugged Trap"
	::= 6

netBotz-prd-bot-amp7-sensor-replugged TRAP-TYPE
	ENTERPRISE netBotz-prd-bot-amp7-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Amp 7 Sensor Replugged Trap. The sensor for the seventh AmpDetect was unplugged, but has been reconnected."
	REFERENCE 	"NetBotz Amp 7 Replugged Trap"
	::= 7

netBotz-prd-bot-amp-total-low-trap TRAP-TYPE
	ENTERPRISE netBotz-prd-bot-amp-total-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Total Amps Low Trap. This trap indicates that the lower
	limit for the total amperage has been exceeded."
	REFERENCE 	"NetBotz Total Amps Low Trap"
	::= 1

netBotz-prd-bot-amp-total-high-trap TRAP-TYPE
	ENTERPRISE netBotz-prd-bot-amp-total-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Total Amps High Trap. This trap indicates that the upper
	limit for the total amperage has been exceeded."
	REFERENCE 	"NetBotz Total Amps High Trap"
	::= 2

netBotz-prd-bot-amp-total-trap-clear TRAP-TYPE
	ENTERPRISE netBotz-prd-bot-amp-total-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Total Amps Cleared Trap. The trap has been cleared because
	the total amperage value has returned to acceptable limits."
	REFERENCE 	"NetBotz Total Amps Cleared Trap"
	::= 3

netBotz-prd-bot-low-trap TRAP-TYPE
	ENTERPRISE netBotz-prd-bot
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Low Trap. This trap indicates that a lower
	limit has been exceeded."
	REFERENCE 	"NetBotz Low Trap"
	::= 1

netBotz-prd-bot-high-trap TRAP-TYPE
	ENTERPRISE netBotz-prd-bot
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz High Trap. This trap indicates that an upper
	limit has been exceeded."
	REFERENCE 	"NetBotz High Trap"
	::= 2

netBotz-prd-bot-trap-clear TRAP-TYPE
	ENTERPRISE netBotz-prd-bot
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Cleared Trap. The trap has been cleared because
	the value has returned to acceptable limits."
	REFERENCE 	"NetBotz Cleared Trap"
	::= 3

netBotz-prd-bot-offline-trap TRAP-TYPE
	ENTERPRISE netBotz-prd-bot
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Device Offline Trap. This trap indicates that a device or function
	has been determined to be offline."
	REFERENCE 	"NetBotz Offline Trap"
	::= 4

netBotz-prd-bot-online-trap TRAP-TYPE
	ENTERPRISE netBotz-prd-bot
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Device Online Trap. This trap indicates that a device or function
	has been determined to be online."
	REFERENCE 	"NetBotz Online Trap"
	::= 5

netBotz-prd-bot-ext-temp1-low-trap TRAP-TYPE
	ENTERPRISE netBotz-prd-bot-ext-temp1-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Temperature 1 Low Trap. This trap indicates that the lower
	limit for external temperature probe on port 1 has been exceeded."
	REFERENCE 	"NetBotz Ext Temperature 1 Low Trap"
	::= 1

netBotz-prd-bot-ext-temp1-high-trap TRAP-TYPE
	ENTERPRISE netBotz-prd-bot-ext-temp1-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Temperature 1 High Trap. This trap indicates that the upper
	limit for external temperature probe on port 1 has been exceeded."
	REFERENCE 	"NetBotz Ext Temperature 1 High Trap"
	::= 2

netBotz-prd-bot-ext-temp1-trap-clear TRAP-TYPE
	ENTERPRISE netBotz-prd-bot-ext-temp1-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Temperature 1 Cleared Trap. The trap has been cleared because
	the temperature value for the temperature probe on port 1 has returned to acceptable limits."
	REFERENCE 	"NetBotz Ext Temperature 1 Cleared Trap"
	::= 3

netBotz-prd-bot-ext-temp1-sensor-unplugged TRAP-TYPE
	ENTERPRISE netBotz-prd-bot-ext-temp1-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Temperature 1 Sensor Unplugged Trap. The sensor is unplugged or malfunctioning."
	REFERENCE 	"NetBotz Ext Temperature 1 Unplugged Trap"
	::= 6

netBotz-prd-bot-ext-temp1-sensor-replugged TRAP-TYPE
	ENTERPRISE netBotz-prd-bot-ext-temp1-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Temperature 1 Sensor Replugged Trap. The sensor was unplugged, but has been reconnected."
	REFERENCE 	"NetBotz Ext Temperature 1 Replugged Trap"
	::= 7

netBotz-prd-bot-ext-temp2-low-trap TRAP-TYPE
	ENTERPRISE netBotz-prd-bot-ext-temp2-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Temperature 2 Low Trap. This trap indicates that the lower
	limit for external temperature probe on port 2 has been exceeded."
	REFERENCE 	"NetBotz Ext Temperature 2 Low Trap"
	::= 1

netBotz-prd-bot-ext-temp2-high-trap TRAP-TYPE
	ENTERPRISE netBotz-prd-bot-ext-temp2-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Temperature 2 High Trap. This trap indicates that the upper
	limit for external temperature probe on port 2 has been exceeded."
	REFERENCE 	"NetBotz Ext Temperature 2 High Trap"
	::= 2

netBotz-prd-bot-ext-temp2-trap-clear TRAP-TYPE
	ENTERPRISE netBotz-prd-bot-ext-temp2-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Temperature 2 Cleared Trap. The trap has been cleared because
	the temperature value for the temperature probe on port 2 has returned to acceptable limits."
	REFERENCE 	"NetBotz Ext Temperature 2 Cleared Trap"
	::= 3

netBotz-prd-bot-ext-temp2-sensor-unplugged TRAP-TYPE
	ENTERPRISE netBotz-prd-bot-ext-temp2-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Temperature 2 Sensor Unplugged Trap. The sensor is unplugged or malfunctioning."
	REFERENCE 	"NetBotz Ext Temperature 2 Unplugged Trap"
	::= 6

netBotz-prd-bot-ext-temp2-sensor-replugged TRAP-TYPE
	ENTERPRISE netBotz-prd-bot-ext-temp2-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Temperature 2 Sensor Replugged Trap. The sensor was unplugged, but has been reconnected."
	REFERENCE 	"NetBotz Ext Temperature 2 Replugged Trap"
	::= 7

netBotz-prd-bot-ext-temp3-low-trap TRAP-TYPE
	ENTERPRISE netBotz-prd-bot-ext-temp3-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Temperature 3 Low Trap. This trap indicates that the lower
	limit for external temperature probe on port 3 has been exceeded."
	REFERENCE 	"NetBotz Ext Temperature 3 Low Trap"
	::= 1

netBotz-prd-bot-ext-temp3-high-trap TRAP-TYPE
	ENTERPRISE netBotz-prd-bot-ext-temp3-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Temperature 3 High Trap. This trap indicates that the upper
	limit for external temperature probe on port 3 has been exceeded."
	REFERENCE 	"NetBotz Ext Temperature 3 High Trap"
	::= 2

netBotz-prd-bot-ext-temp3-trap-clear TRAP-TYPE
	ENTERPRISE netBotz-prd-bot-ext-temp3-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Temperature 3 Cleared Trap. The trap has been cleared because
	the temperature value for the temperature probe on port 3 has returned to acceptable limits."
	REFERENCE 	"NetBotz Ext Temperature 3 Cleared Trap"
	::= 3

netBotz-prd-bot-ext-temp3-sensor-unplugged TRAP-TYPE
	ENTERPRISE netBotz-prd-bot-ext-temp3-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Temperature 3 Sensor Unplugged Trap. The sensor is unplugged or malfunctioning."
	REFERENCE 	"NetBotz Ext Temperature 3 Unplugged Trap"
	::= 6

netBotz-prd-bot-ext-temp3-sensor-replugged TRAP-TYPE
	ENTERPRISE netBotz-prd-bot-ext-temp3-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Temperature 3 Sensor Replugged Trap. The sensor was unplugged, but has been reconnected."
	REFERENCE 	"NetBotz Ext Temperature 3 Replugged Trap"
	::= 7

netBotz-prd-bot-ext-temp4-low-trap TRAP-TYPE
	ENTERPRISE netBotz-prd-bot-ext-temp4-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Temperature 4 Low Trap. This trap indicates that the lower
	limit for external temperature probe on port 4 has been exceeded."
	REFERENCE 	"NetBotz Ext Temperature 4 Low Trap"
	::= 1

netBotz-prd-bot-ext-temp4-high-trap TRAP-TYPE
	ENTERPRISE netBotz-prd-bot-ext-temp4-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Temperature 4 High Trap. This trap indicates that the upper
	limit for external temperature probe on port 4 has been exceeded."
	REFERENCE 	"NetBotz Ext Temperature 4 High Trap"
	::= 2

netBotz-prd-bot-ext-temp4-trap-clear TRAP-TYPE
	ENTERPRISE netBotz-prd-bot-ext-temp4-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Temperature 4 Cleared Trap. The trap has been cleared because
	the temperature value for the temperature probe on port 4 has returned to acceptable limits."
	REFERENCE 	"NetBotz Ext Temperature 4 Cleared Trap"
	::= 3

netBotz-prd-bot-ext-temp4-sensor-unplugged TRAP-TYPE
	ENTERPRISE netBotz-prd-bot-ext-temp4-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Temperature 4 Sensor Unplugged Trap. The sensor is unplugged or malfunctioning."
	REFERENCE 	"NetBotz Ext Temperature 4 Unplugged Trap"
	::= 6

netBotz-prd-bot-ext-temp4-sensor-replugged TRAP-TYPE
	ENTERPRISE netBotz-prd-bot-ext-temp4-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Temperature 4 Sensor Replugged Trap. The sensor was unplugged, but has been reconnected."
	REFERENCE 	"NetBotz Ext Temperature 4 Replugged Trap"
	::= 7

netBotz-prd-bot-ext-temp5-low-trap TRAP-TYPE
	ENTERPRISE netBotz-prd-bot-ext-temp5-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Temperature 5 Low Trap. This trap indicates that the lower
	limit for external temperature probe on port 5 has been exceeded."
	REFERENCE 	"NetBotz Ext Temperature 5 Low Trap"
	::= 1

netBotz-prd-bot-ext-temp5-high-trap TRAP-TYPE
	ENTERPRISE netBotz-prd-bot-ext-temp5-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Temperature 5 High Trap. This trap indicates that the upper
	limit for external temperature probe on port 5 has been exceeded."
	REFERENCE 	"NetBotz Ext Temperature 5 High Trap"
	::= 2

netBotz-prd-bot-ext-temp5-trap-clear TRAP-TYPE
	ENTERPRISE netBotz-prd-bot-ext-temp5-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Temperature 5 Cleared Trap. The trap has been cleared because
	the temperature value for the temperature probe on port 5 has returned to acceptable limits."
	REFERENCE 	"NetBotz Ext Temperature 5 Cleared Trap"
	::= 3

netBotz-prd-bot-ext-temp5-sensor-unplugged TRAP-TYPE
	ENTERPRISE netBotz-prd-bot-ext-temp5-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Temperature 5 Sensor Unplugged Trap. The sensor is unplugged or malfunctioning."
	REFERENCE 	"NetBotz Ext Temperature 5 Unplugged Trap"
	::= 6

netBotz-prd-bot-ext-temp5-sensor-replugged TRAP-TYPE
	ENTERPRISE netBotz-prd-bot-ext-temp5-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Temperature 5 Sensor Replugged Trap. The sensor was unplugged, but has been reconnected."
	REFERENCE 	"NetBotz Ext Temperature 5 Replugged Trap"
	::= 7

netBotz-prd-bot-ext-temp6-low-trap TRAP-TYPE
	ENTERPRISE netBotz-prd-bot-ext-temp6-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Temperature 6 Low Trap. This trap indicates that the lower
	limit for external temperature probe on port 6 has been exceeded."
	REFERENCE 	"NetBotz Ext Temperature 6 Low Trap"
	::= 1

netBotz-prd-bot-ext-temp6-high-trap TRAP-TYPE
	ENTERPRISE netBotz-prd-bot-ext-temp6-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Temperature 6 High Trap. This trap indicates that the upper
	limit for external temperature probe on port 6 has been exceeded."
	REFERENCE 	"NetBotz Ext Temperature 6 High Trap"
	::= 2

netBotz-prd-bot-ext-temp6-trap-clear TRAP-TYPE
	ENTERPRISE netBotz-prd-bot-ext-temp6-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Temperature 6 Cleared Trap. The trap has been cleared because
	the temperature value for the temperature probe on port 6 has returned to acceptable limits."
	REFERENCE 	"NetBotz Ext Temperature 6 Cleared Trap"
	::= 3

netBotz-prd-bot-ext-temp6-sensor-unplugged TRAP-TYPE
	ENTERPRISE netBotz-prd-bot-ext-temp6-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Temperature 6 Sensor Unplugged Trap. The sensor is unplugged or malfunctioning."
	REFERENCE 	"NetBotz Ext Temperature 6 Unplugged Trap"
	::= 6

netBotz-prd-bot-ext-temp6-sensor-replugged TRAP-TYPE
	ENTERPRISE netBotz-prd-bot-ext-temp6-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Temperature 6 Sensor Replugged Trap. The sensor was unplugged, but has been reconnected."
	REFERENCE 	"NetBotz Ext Temperature 6 Replugged Trap"
	::= 7

netBotz-prd-bot-ext-temp7-low-trap TRAP-TYPE
	ENTERPRISE netBotz-prd-bot-ext-temp7-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Temperature 7 Low Trap. This trap indicates that the lower
	limit for external temperature probe on port 7 has been exceeded."
	REFERENCE 	"NetBotz Ext Temperature 7 Low Trap"
	::= 1

netBotz-prd-bot-ext-temp7-high-trap TRAP-TYPE
	ENTERPRISE netBotz-prd-bot-ext-temp7-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Temperature 7 High Trap. This trap indicates that the upper
	limit for external temperature probe on port 7 has been exceeded."
	REFERENCE 	"NetBotz Ext Temperature 7 High Trap"
	::= 2

netBotz-prd-bot-ext-temp7-trap-clear TRAP-TYPE
	ENTERPRISE netBotz-prd-bot-ext-temp7-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Temperature 7 Cleared Trap. The trap has been cleared because
	the temperature value for the temperature probe on port 7 has returned to acceptable limits."
	REFERENCE 	"NetBotz Ext Temperature 7 Cleared Trap"
	::= 3

netBotz-prd-bot-ext-temp7-sensor-unplugged TRAP-TYPE
	ENTERPRISE netBotz-prd-bot-ext-temp7-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Temperature 7 Sensor Unplugged Trap. The sensor is unplugged or malfunctioning."
	REFERENCE 	"NetBotz Ext Temperature 7 Unplugged Trap"
	::= 6

netBotz-prd-bot-ext-temp7-sensor-replugged TRAP-TYPE
	ENTERPRISE netBotz-prd-bot-ext-temp7-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Temperature 7 Sensor Replugged Trap. The sensor was unplugged, but has been reconnected."
	REFERENCE 	"NetBotz Ext Temperature 7 Replugged Trap"
	::= 7

netBotz-prd-bot-ext-dry1-triggered-trap TRAP-TYPE
	ENTERPRISE netBotz-prd-bot-ext-dry1-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Dry Contact 1 Triggered Trap. This trap indicates that the state of the
	dry contact sensor on Ext1 matches the alarm value."
	REFERENCE 	"NetBotz Ext Dry 1 Triggered Trap"
	::= 2

netBotz-prd-bot-ext-dry1-trap-clear TRAP-TYPE
	ENTERPRISE netBotz-prd-bot-ext-dry1-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Dry Contact 1 Cleared Trap. The trap has been cleared because
	the state of the dry contact sensor on Ext1 no longer matches the alarm value."
	REFERENCE 	"NetBotz Ext Dry 1 Cleared Trap"
	::= 3

netBotz-prd-bot-ext-dry2-triggered-trap TRAP-TYPE
	ENTERPRISE netBotz-prd-bot-ext-dry2-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Dry Contact 2 Triggered Trap. This trap indicates that the state of the
	dry contact sensor on Ext2 matches the alarm value."
	REFERENCE 	"NetBotz Ext Dry 2 Triggered Trap"
	::= 2

netBotz-prd-bot-ext-dry2-trap-clear TRAP-TYPE
	ENTERPRISE netBotz-prd-bot-ext-dry2-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Dry Contact 2 Cleared Trap. The trap has been cleared because
	the state of the dry contact sensor on Ext2 no longer matches the alarm value."
	REFERENCE 	"NetBotz Ext Dry 2 Cleared Trap"
	::= 3

netBotz-prd-bot-ext-dry3-triggered-trap TRAP-TYPE
	ENTERPRISE netBotz-prd-bot-ext-dry3-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Dry Contact 3 Triggered Trap. This trap indicates that the state of the
	dry contact sensor on Ext3 matches the alarm value."
	REFERENCE 	"NetBotz Ext Dry 3 Triggered Trap"
	::= 2

netBotz-prd-bot-ext-dry3-trap-clear TRAP-TYPE
	ENTERPRISE netBotz-prd-bot-ext-dry3-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Dry Contact 3 Cleared Trap. The trap has been cleared because
	the state of the dry contact sensor on Ext3 no longer matches the alarm value."
	REFERENCE 	"NetBotz Ext Dry 3 Cleared Trap"
	::= 3

netBotz-prd-bot-ext-dry4-triggered-trap TRAP-TYPE
	ENTERPRISE netBotz-prd-bot-ext-dry4-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Dry Contact 4 Triggered Trap. This trap indicates that the state of the
	dry contact sensor on Ext4 matches the alarm value."
	REFERENCE 	"NetBotz Ext Dry 4 Triggered Trap"
	::= 2

netBotz-prd-bot-ext-dry4-trap-clear TRAP-TYPE
	ENTERPRISE netBotz-prd-bot-ext-dry4-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Dry Contact 4 Cleared Trap. The trap has been cleared because
	the state of the dry contact sensor on Ext4 no longer matches the alarm value."
	REFERENCE 	"NetBotz Ext Dry 4 Cleared Trap"
	::= 3

netBotz-prd-bot-ext-dry5-triggered-trap TRAP-TYPE
	ENTERPRISE netBotz-prd-bot-ext-dry5-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Dry Contact 5 Triggered Trap. This trap indicates that the state of the
	dry contact sensor on Ext5 matches the alarm value."
	REFERENCE 	"NetBotz Ext Dry 5 Triggered Trap"
	::= 2

netBotz-prd-bot-ext-dry5-trap-clear TRAP-TYPE
	ENTERPRISE netBotz-prd-bot-ext-dry5-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Dry Contact 5 Cleared Trap. The trap has been cleared because
	the state of the dry contact sensor on Ext5 no longer matches the alarm value."
	REFERENCE 	"NetBotz Ext Dry 5 Cleared Trap"
	::= 3

netBotz-prd-bot-ext-dry6-triggered-trap TRAP-TYPE
	ENTERPRISE netBotz-prd-bot-ext-dry6-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Dry Contact 6 Triggered Trap. This trap indicates that the state of the
	dry contact sensor on Ext6 matches the alarm value."
	REFERENCE 	"NetBotz Ext Dry 6 Triggered Trap"
	::= 2

netBotz-prd-bot-ext-dry6-trap-clear TRAP-TYPE
	ENTERPRISE netBotz-prd-bot-ext-dry6-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Dry Contact 6 Cleared Trap. The trap has been cleared because
	the state of the dry contact sensor on Ext6 no longer matches the alarm value."
	REFERENCE 	"NetBotz Ext Dry 6 Cleared Trap"
	::= 3

netBotz-prd-bot-ext-dry7-triggered-trap TRAP-TYPE
	ENTERPRISE netBotz-prd-bot-ext-dry7-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Dry Contact 7 Triggered Trap. This trap indicates that the state of the
	dry contact sensor on Ext7 matches the alarm value."
	REFERENCE 	"NetBotz Ext Dry 7 Triggered Trap"
	::= 2

netBotz-prd-bot-ext-dry7-trap-clear TRAP-TYPE
	ENTERPRISE netBotz-prd-bot-ext-dry7-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Dry Contact 7 Cleared Trap. The trap has been cleared because
	the state of the dry contact sensor on Ext7 no longer matches the alarm value."
	REFERENCE 	"NetBotz Ext Dry 7 Cleared Trap"
	::= 3

netBotz-prd-bot-camera-motion-trap-tripped TRAP-TYPE
	ENTERPRISE netBotz-prd-bot-camera-motion-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Camera Motion Sensor Tripped Trap. This trap indicates that the camera motion sensor
	has been triggered (motion has been detected)."
	REFERENCE 	"NetBotz Camera Motion Tripped Trap"
	::= 2

netBotz-prd-bot-camera-motion-trap-clear TRAP-TYPE
	ENTERPRISE netBotz-prd-bot-camera-motion-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz Camera Motion Cleared Trap. The trap has been cleared because
	the camera motion sensor has returned to normal (no longer is detecting motion)."
	REFERENCE 	"NetBotz Camera Motion Cleared Trap"
	::= 3

netBotz-prd-bot-ext-humi1-low-trap TRAP-TYPE
	ENTERPRISE netBotz-prd-bot-ext-humi1-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Humidity 1 Low Trap. This trap indicates that the lower
	limit for external humidity probe on port 1 has been exceeded."
	REFERENCE 	"NetBotz Ext Humidity 1 Low Trap"
	::= 1

netBotz-prd-bot-ext-humi1-high-trap TRAP-TYPE
	ENTERPRISE netBotz-prd-bot-ext-humi1-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Humidity 1 High Trap. This trap indicates that the upper
	limit for external humidity probe on port 1 has been exceeded."
	REFERENCE 	"NetBotz Ext Humidity 1 High Trap"
	::= 2

netBotz-prd-bot-ext-humi1-trap-clear TRAP-TYPE
	ENTERPRISE netBotz-prd-bot-ext-humi1-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Humidity 1 Cleared Trap. The trap has been cleared because
	the humidity value for the humidity probe on port 1 has returned to acceptable limits."
	REFERENCE 	"NetBotz Ext Humidity 1 Cleared Trap"
	::= 3

netBotz-prd-bot-ext-humi1-sensor-unplugged TRAP-TYPE
	ENTERPRISE netBotz-prd-bot-ext-humi1-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Humidity 1 Sensor Unplugged Trap. The sensor is unplugged or malfunctioning."
	REFERENCE 	"NetBotz Ext Humidity 1 Unplugged Trap"
	::= 6

netBotz-prd-bot-ext-humi1-sensor-replugged TRAP-TYPE
	ENTERPRISE netBotz-prd-bot-ext-humi1-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Humidity 1 Sensor Replugged Trap. The sensor was unplugged, but has been reconnected."
	REFERENCE 	"NetBotz Ext Humidity 1 Replugged Trap"
	::= 7

netBotz-prd-bot-ext-humi2-low-trap TRAP-TYPE
	ENTERPRISE netBotz-prd-bot-ext-humi2-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Humidity 2 Low Trap. This trap indicates that the lower
	limit for external humidity probe on port 2 has been exceeded."
	REFERENCE 	"NetBotz Ext Humidity 2 Low Trap"
	::= 1

netBotz-prd-bot-ext-humi2-high-trap TRAP-TYPE
	ENTERPRISE netBotz-prd-bot-ext-humi2-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Humidity 2 High Trap. This trap indicates that the upper
	limit for external humidity probe on port 2 has been exceeded."
	REFERENCE 	"NetBotz Ext Humidity 2 High Trap"
	::= 2

netBotz-prd-bot-ext-humi2-trap-clear TRAP-TYPE
	ENTERPRISE netBotz-prd-bot-ext-humi2-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Humidity 2 Cleared Trap. The trap has been cleared because
	the humidity value for the humidity probe on port 2 has returned to acceptable limits."
	REFERENCE 	"NetBotz Ext Humidity 2 Cleared Trap"
	::= 3

netBotz-prd-bot-ext-humi2-sensor-unplugged TRAP-TYPE
	ENTERPRISE netBotz-prd-bot-ext-humi2-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Humidity 2 Sensor Unplugged Trap. The sensor is unplugged or malfunctioning."
	REFERENCE 	"NetBotz Ext Humidity 2 Unplugged Trap"
	::= 6

netBotz-prd-bot-ext-humi2-sensor-replugged TRAP-TYPE
	ENTERPRISE netBotz-prd-bot-ext-humi2-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Humidity 2 Sensor Replugged Trap. The sensor was unplugged, but has been reconnected."
	REFERENCE 	"NetBotz Ext Humidity 2 Replugged Trap"
	::= 7

netBotz-prd-bot-ext-humi3-low-trap TRAP-TYPE
	ENTERPRISE netBotz-prd-bot-ext-humi3-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Humidity 3 Low Trap. This trap indicates that the lower
	limit for external humidity probe on port 3 has been exceeded."
	REFERENCE 	"NetBotz Ext Humidity 3 Low Trap"
	::= 1

netBotz-prd-bot-ext-humi3-high-trap TRAP-TYPE
	ENTERPRISE netBotz-prd-bot-ext-humi3-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Humidity 3 High Trap. This trap indicates that the upper
	limit for external humidity probe on port 3 has been exceeded."
	REFERENCE 	"NetBotz Ext Humidity 3 High Trap"
	::= 2

netBotz-prd-bot-ext-humi3-trap-clear TRAP-TYPE
	ENTERPRISE netBotz-prd-bot-ext-humi3-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Humidity 3 Cleared Trap. The trap has been cleared because
	the humidity value for the humidity probe on port 3 has returned to acceptable limits."
	REFERENCE 	"NetBotz Ext Humidity 3 Cleared Trap"
	::= 3

netBotz-prd-bot-ext-humi3-sensor-unplugged TRAP-TYPE
	ENTERPRISE netBotz-prd-bot-ext-humi3-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Humidity 3 Sensor Unplugged Trap. The sensor is unplugged or malfunctioning."
	REFERENCE 	"NetBotz Ext Humidity 3 Unplugged Trap"
	::= 6

netBotz-prd-bot-ext-humi3-sensor-replugged TRAP-TYPE
	ENTERPRISE netBotz-prd-bot-ext-humi3-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Humidity 3 Sensor Replugged Trap. The sensor was unplugged, but has been reconnected."
	REFERENCE 	"NetBotz Ext Humidity 3 Replugged Trap"
	::= 7

netBotz-prd-bot-ext-humi4-low-trap TRAP-TYPE
	ENTERPRISE netBotz-prd-bot-ext-humi4-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Humidity 4 Low Trap. This trap indicates that the lower
	limit for external humidity probe on port 4 has been exceeded."
	REFERENCE 	"NetBotz Ext Humidity 4 Low Trap"
	::= 1

netBotz-prd-bot-ext-humi4-high-trap TRAP-TYPE
	ENTERPRISE netBotz-prd-bot-ext-humi4-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Humidity 4 High Trap. This trap indicates that the upper
	limit for external humidity probe on port 4 has been exceeded."
	REFERENCE 	"NetBotz Ext Humidity 4 High Trap"
	::= 2

netBotz-prd-bot-ext-humi4-trap-clear TRAP-TYPE
	ENTERPRISE netBotz-prd-bot-ext-humi4-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Humidity 4 Cleared Trap. The trap has been cleared because
	the humidity value for the humidity probe on port 4 has returned to acceptable limits."
	REFERENCE 	"NetBotz Ext Humidity 4 Cleared Trap"
	::= 3

netBotz-prd-bot-ext-humi4-sensor-unplugged TRAP-TYPE
	ENTERPRISE netBotz-prd-bot-ext-humi4-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Humidity 4 Sensor Unplugged Trap. The sensor is unplugged or malfunctioning."
	REFERENCE 	"NetBotz Ext Humidity 4 Unplugged Trap"
	::= 6

netBotz-prd-bot-ext-humi4-sensor-replugged TRAP-TYPE
	ENTERPRISE netBotz-prd-bot-ext-humi4-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Humidity 4 Sensor Replugged Trap. The sensor was unplugged, but has been reconnected."
	REFERENCE 	"NetBotz Ext Humidity 4 Replugged Trap"
	::= 7

netBotz-prd-bot-ext-humi5-low-trap TRAP-TYPE
	ENTERPRISE netBotz-prd-bot-ext-humi5-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Humidity 5 Low Trap. This trap indicates that the lower
	limit for external humidity probe on port 5 has been exceeded."
	REFERENCE 	"NetBotz Ext Humidity 5 Low Trap"
	::= 1

netBotz-prd-bot-ext-humi5-high-trap TRAP-TYPE
	ENTERPRISE netBotz-prd-bot-ext-humi5-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Humidity 5 High Trap. This trap indicates that the upper
	limit for external humidity probe on port 5 has been exceeded."
	REFERENCE 	"NetBotz Ext Humidity 5 High Trap"
	::= 2

netBotz-prd-bot-ext-humi5-trap-clear TRAP-TYPE
	ENTERPRISE netBotz-prd-bot-ext-humi5-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Humidity 5 Cleared Trap. The trap has been cleared because
	the humidity value for the humidity probe on port 5 has returned to acceptable limits."
	REFERENCE 	"NetBotz Ext Humidity 5 Cleared Trap"
	::= 3

netBotz-prd-bot-ext-humi5-sensor-unplugged TRAP-TYPE
	ENTERPRISE netBotz-prd-bot-ext-humi5-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Humidity 5 Sensor Unplugged Trap. The sensor is unplugged or malfunctioning."
	REFERENCE 	"NetBotz Ext Humidity 5 Unplugged Trap"
	::= 6

netBotz-prd-bot-ext-humi5-sensor-replugged TRAP-TYPE
	ENTERPRISE netBotz-prd-bot-ext-humi5-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Humidity 5 Sensor Replugged Trap. The sensor was unplugged, but has been reconnected."
	REFERENCE 	"NetBotz Ext Humidity 5 Replugged Trap"
	::= 7

netBotz-prd-bot-ext-humi6-low-trap TRAP-TYPE
	ENTERPRISE netBotz-prd-bot-ext-humi6-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Humidity 6 Low Trap. This trap indicates that the lower
	limit for external humidity probe on port 6 has been exceeded."
	REFERENCE 	"NetBotz Ext Humidity 6 Low Trap"
	::= 1

netBotz-prd-bot-ext-humi6-high-trap TRAP-TYPE
	ENTERPRISE netBotz-prd-bot-ext-humi6-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Humidity 6 High Trap. This trap indicates that the upper
	limit for external humidity probe on port 6 has been exceeded."
	REFERENCE 	"NetBotz Ext Humidity 6 High Trap"
	::= 2

netBotz-prd-bot-ext-humi6-trap-clear TRAP-TYPE
	ENTERPRISE netBotz-prd-bot-ext-humi6-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Humidity 6 Cleared Trap. The trap has been cleared because
	the humidity value for the humidity probe on port 6 has returned to acceptable limits."
	REFERENCE 	"NetBotz Ext Humidity 6 Cleared Trap"
	::= 3

netBotz-prd-bot-ext-humi6-sensor-unplugged TRAP-TYPE
	ENTERPRISE netBotz-prd-bot-ext-humi6-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Humidity 6 Sensor Unplugged Trap. The sensor is unplugged or malfunctioning."
	REFERENCE 	"NetBotz Ext Humidity 6 Unplugged Trap"
	::= 6

netBotz-prd-bot-ext-humi6-sensor-replugged TRAP-TYPE
	ENTERPRISE netBotz-prd-bot-ext-humi6-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Humidity 6 Sensor Replugged Trap. The sensor was unplugged, but has been reconnected."
	REFERENCE 	"NetBotz Ext Humidity 6 Replugged Trap"
	::= 7

netBotz-prd-bot-ext-humi7-low-trap TRAP-TYPE
	ENTERPRISE netBotz-prd-bot-ext-humi7-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Humidity 7 Low Trap. This trap indicates that the lower
	limit for external humidity probe on port 7 has been exceeded."
	REFERENCE 	"NetBotz Ext Humidity 7 Low Trap"
	::= 1

netBotz-prd-bot-ext-humi7-high-trap TRAP-TYPE
	ENTERPRISE netBotz-prd-bot-ext-humi7-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Humidity 7 High Trap. This trap indicates that the upper
	limit for external humidity probe on port 7 has been exceeded."
	REFERENCE 	"NetBotz Ext Humidity 7 High Trap"
	::= 2

netBotz-prd-bot-ext-humi7-trap-clear TRAP-TYPE
	ENTERPRISE netBotz-prd-bot-ext-humi7-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Humidity 7 Cleared Trap. The trap has been cleared because
	the humidity value for the humidity probe on port 7 has returned to acceptable limits."
	REFERENCE 	"NetBotz Ext Humidity 7 Cleared Trap"
	::= 3

netBotz-prd-bot-ext-humi7-sensor-unplugged TRAP-TYPE
	ENTERPRISE netBotz-prd-bot-ext-humi7-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Humidity 7 Sensor Unplugged Trap. The sensor is unplugged or malfunctioning."
	REFERENCE 	"NetBotz Ext Humidity 7 Unplugged Trap"
	::= 6

netBotz-prd-bot-ext-humi7-sensor-replugged TRAP-TYPE
	ENTERPRISE netBotz-prd-bot-ext-humi7-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION
	"NetBotz External Humidity 7 Sensor Replugged Trap. The sensor was unplugged, but has been reconnected."
	REFERENCE 	"NetBotz Ext Humidity 7 Replugged Trap"
	::= 7

expPortTable OBJECT-TYPE
        SYNTAX  SEQUENCE OF ExpPortEntry
        ACCESS  not-accessible
        STATUS  mandatory
        DESCRIPTION
        "A list of expansion port entries."
        ::= { netBotz 31 }

expPortEntry OBJECT-TYPE
        SYNTAX  ExpPortEntry
        ACCESS  not-accessible
        STATUS  mandatory
        DESCRIPTION
        "An expansion port entry for a single port"
        ::= { expPortTable 1 }

ExpPortEntry ::=
        SEQUENCE {
		expPort-module-id
                      DisplayString,
		expPort-module-type
                      DisplayString,
		expPort-label
                      DisplayString,
		expPort-amps
                      INTEGER,
		expPort-total-amp-seconds
                      INTEGER,
		expPort-total-amp-seconds-since-time
                      INTEGER,
		expPort-amps-enabled
                      INTEGER,
		expPort-amps-min
                      INTEGER,
		expPort-amps-max
                      INTEGER,
		expPort-amps-uV-per-10mA
                      INTEGER,
		expPort-amps-max-range
                      INTEGER,
		expPort-ext-temp
                      INTEGER,
		expPort-ext-temp-enabled
                      INTEGER,
		expPort-ext-temp-min
                      INTEGER,
		expPort-ext-temp-max
                      INTEGER,
		expPort-ext-temp-uV-per-degreeC
                      INTEGER,
		expPort-ext-temp-uV-at-0-degreeC
                      INTEGER,
		expPort-ext-temp-min-range
                      INTEGER,
		expPort-ext-temp-max-range
                      INTEGER,
		expPort-ext-dry
			INTEGER,
		expPort-ext-dry-alarm-value
			INTEGER,
		expPort-ext-dry-enabled
			INTEGER,
		expPort-ext-dry-label
			DisplayString,
		expPort-ext-dry-open-label
			DisplayString,
		expPort-ext-dry-closed-label
			DisplayString,
		expPort-ext-dry-open-to-close-millis
			INTEGER,
		expPort-ext-dry-close-to-open-millis
			INTEGER,
		expPort-ext-dry-response
			DisplayString
        }

expPort-module-id OBJECT-TYPE
	SYNTAX		DisplayString
	ACCESS		read-write
	STATUS		mandatory
	DESCRIPTION	"The module ID of the sensor module installed.  Blank string indicates that no module is installed."
	::= { expPortEntry 1 }

expPort-module-type OBJECT-TYPE
	SYNTAX		DisplayString
	ACCESS		read-write
	STATUS		mandatory
	DESCRIPTION	"The type of sensor module installed.  NONE=no module, AMP=AmpDetect module, TEMP=temperature sensor, DRY=dry contact sensor."
	::= { expPortEntry 2 }

expPort-label OBJECT-TYPE
	SYNTAX		DisplayString
	ACCESS		read-write
	STATUS		mandatory
	DESCRIPTION	"The label for the expansion port.  Ports default to the label 'Extn', for port n."
	::= { expPortEntry 3 }

expPort-amps OBJECT-TYPE
	SYNTAX		INTEGER
	ACCESS		read-only
	STATUS		mandatory
	DESCRIPTION	"The reading of the amperage probe, in milliamps."
	::= { expPortEntry 20 }

expPort-total-amp-seconds OBJECT-TYPE
	SYNTAX		INTEGER
	ACCESS		read-only
	STATUS		mandatory
	DESCRIPTION	"The accumulated total of amp-seconds on the AmpDetect."
	::= { expPortEntry 21 }

expPort-total-amp-seconds-since-time OBJECT-TYPE
	SYNTAX		INTEGER
	ACCESS		read-write
	STATUS		mandatory
	DESCRIPTION	"The UTC time (seconds since 1/1/1970) of the beginning of the accumulated total of amp-seconds on the AmpDetect.
        Writing a value to this attribute resets the accumulated total amp-seconds and sets this time to the current time."
	::= { expPortEntry 22 }

expPort-amps-enabled OBJECT-TYPE
	SYNTAX		INTEGER
	ACCESS		read-write
	STATUS		mandatory
	DESCRIPTION	"Amperage probe alarm enabled(1) or disabled(0)."
	::= { expPortEntry 23 }

expPort-amps-min OBJECT-TYPE
	SYNTAX		INTEGER
	ACCESS		read-write
	STATUS		mandatory
	DESCRIPTION	"The amperage probe minimum, from 0 to 30000 milliamps."
	::= { expPortEntry 24 }

expPort-amps-max OBJECT-TYPE
	SYNTAX		INTEGER
	ACCESS		read-write
	STATUS		mandatory
	DESCRIPTION	"The amperage probe maximum, from 0 to 30000 milliamps."
	::= { expPortEntry 25 }

expPort-amps-uV-per-10mA OBJECT-TYPE
	SYNTAX		INTEGER
	ACCESS		read-write
	STATUS		mandatory
	DESCRIPTION	"The scaling factor used for the amperage probe to convert microvolts measured from the
        Amp Detect into 10s of milliamps of current.  Needs to be set based on the type of Amp Detect module installed."
	::= { expPortEntry 26 }

expPort-amps-max-range OBJECT-TYPE
	SYNTAX		INTEGER
	ACCESS		read-write
	STATUS		mandatory
	DESCRIPTION	"The maximum RMS milliamps measureable by the AmpDetect."
	::= { expPortEntry 27 }

expPort-ext-temp OBJECT-TYPE
	SYNTAX		INTEGER
	ACCESS		read-only
	STATUS		mandatory
	DESCRIPTION	"The reading of the external temperature probe, in degrees F or degrees C (depends on netBotz-ismetric)."
	::= { expPortEntry 40 }

expPort-ext-temp-enabled OBJECT-TYPE
	SYNTAX		INTEGER
	ACCESS		read-write
	STATUS		mandatory
	DESCRIPTION	"External temperature probe alarm enabled(1) or disabled(0)."
	::= { expPortEntry 41 }

expPort-ext-temp-min OBJECT-TYPE
	SYNTAX		INTEGER
	ACCESS		read-write
	STATUS		mandatory
	DESCRIPTION	"The external temperature probe minimum, in degrees F or degrees C (depends on netBotz-ismetric)."
	::= { expPortEntry 42 }

expPort-ext-temp-max OBJECT-TYPE
	SYNTAX		INTEGER
	ACCESS		read-write
	STATUS		mandatory
	DESCRIPTION	"The external temperature probe maximum, in degrees F or degrees C (depends on netBotz-ismetric)."
	::= { expPortEntry 43 }


expPort-ext-temp-uV-per-degreeC OBJECT-TYPE
	SYNTAX		INTEGER
	ACCESS		read-write
	STATUS		mandatory
	DESCRIPTION	"The scaling factor used for the external temperature probe to convert microvolts measured from the
        temperature sensor into degrees C.  Needs to be set based on the type of temperature sensor module installed."
	::= { expPortEntry 44 }

expPort-ext-temp-uV-at-0-degreeC OBJECT-TYPE
	SYNTAX		INTEGER
	ACCESS		read-write
	STATUS		mandatory
	DESCRIPTION	"The offset used for the external temperature probe of microvolts measured from the
        temperature sensor at zero degrees C.  Needs to be set based on the type of temperature sensor module installed."
	::= { expPortEntry 45 }

expPort-ext-temp-min-range OBJECT-TYPE
	SYNTAX		INTEGER
	ACCESS		read-write
	STATUS		mandatory
	DESCRIPTION	"The minimum temperature measureable by the temperature sensor, in tenths of a degree C.
        Needs to be set based on the type of temperature sensor module installed."
	::= { expPortEntry 46 }

expPort-ext-temp-max-range OBJECT-TYPE
	SYNTAX		INTEGER
	ACCESS		read-write
	STATUS		mandatory
	DESCRIPTION	"The maximum temperature measureable by the temperature sensor, in tenths of a degree C.
        Needs to be set based on the type of temperature sensor module installed."
	::= { expPortEntry 47 }

expPort-ext-dry OBJECT-TYPE
	SYNTAX		INTEGER
	ACCESS		read-only
	STATUS		mandatory
	DESCRIPTION	"The current value of the external dry contact sensor: 0=Open, 1=Closed, -1=N/A"
	::= { expPortEntry 60 }

expPort-ext-dry-alarm-value OBJECT-TYPE
	SYNTAX		INTEGER
	ACCESS		read-write
	STATUS		mandatory
	DESCRIPTION	"The value to generate alarms on for the external dry contact sensor: 0=Open, 1=Closed"
	::= { expPortEntry 61 }

expPort-ext-dry-enabled OBJECT-TYPE
	SYNTAX		INTEGER
	ACCESS		read-write
	STATUS		mandatory
	DESCRIPTION	"External dry contact sensor alarm enabled(1) or disabled(0)."
	::= { expPortEntry 62 }

expPort-ext-dry-label OBJECT-TYPE
	SYNTAX		DisplayString
	ACCESS		read-write
	STATUS		mandatory
	DESCRIPTION	"The sensor name/label for the dry contact sensor"
	::= { expPortEntry 63 }

expPort-ext-dry-open-label OBJECT-TYPE
	SYNTAX		DisplayString
	ACCESS		read-write
	STATUS		mandatory
	DESCRIPTION	"The sensor name/label for the open(0) state for the dry contact sensor"
	::= { expPortEntry 64 }

expPort-ext-dry-closed-label OBJECT-TYPE
	SYNTAX		DisplayString
	ACCESS		read-write
	STATUS		mandatory
	DESCRIPTION	"The sensor name/label for the closed(0) state for the dry contact sensor"
	::= { expPortEntry 65 }

expPort-ext-dry-open-to-close-millis OBJECT-TYPE
	SYNTAX		INTEGER
	ACCESS		read-write
	STATUS		mandatory
	DESCRIPTION	"The minimum number of milliseconds that the dry contact sensor
			must read closed before the state is changed from open to closed."
	::= { expPortEntry 66 }

expPort-ext-dry-close-to-open-millis OBJECT-TYPE
	SYNTAX		INTEGER
	ACCESS		read-write
	STATUS		mandatory
	DESCRIPTION	"The minimum number of milliseconds that the dry contact sensor
			must read openbefore the state is changed from closed to open."
	::= { expPortEntry 67 }

expPort-ext-dry-response OBJECT-TYPE
	SYNTAX		DisplayString
	ACCESS		read-write
	STATUS		mandatory
	DESCRIPTION	"The type of alert response for the dry contact sensor: ALERT=e-mail with no
		pictures, CAMERA=e-mail with pictures from camera."
	::= { expPortEntry 68 }

expPort-ext-humi OBJECT-TYPE
	SYNTAX		INTEGER
	ACCESS		read-only
	STATUS		mandatory
	DESCRIPTION	"The reading of the external humidity probe, in percent."
	::= { expPortEntry 80 }

expPort-ext-humi-enabled OBJECT-TYPE
	SYNTAX		INTEGER
	ACCESS		read-write
	STATUS		mandatory
	DESCRIPTION	"External humidity probe alarm enabled(1) or disabled(0)."
	::= { expPortEntry 81 }

expPort-ext-humi-min OBJECT-TYPE
	SYNTAX		INTEGER
	ACCESS		read-write
	STATUS		mandatory
	DESCRIPTION	"The external humidity probe minimum, in percent."
	::= { expPortEntry 82 }

expPort-ext-humi-max OBJECT-TYPE
	SYNTAX		INTEGER
	ACCESS		read-write
	STATUS		mandatory
	DESCRIPTION	"The external humidity probe maximum, in percent."
	::= { expPortEntry 83 }


expPort-ext-humi-uV-per-percent OBJECT-TYPE
	SYNTAX		INTEGER
	ACCESS		read-write
	STATUS		mandatory
	DESCRIPTION	"The scaling factor used for the external humidity probe to convert microvolts measured from the
        humidity sensor into percent.  Needs to be set based on the type of humidity sensor module installed."
	::= { expPortEntry 84 }

expPort-ext-humi-uV-at-0-percent OBJECT-TYPE
	SYNTAX		INTEGER
	ACCESS		read-write
	STATUS		mandatory
	DESCRIPTION	"The offset used for the external humidity probe of microvolts measured from the
        humidity sensor at zero percent.  Needs to be set based on the type of humidity sensor module installed."
	::= { expPortEntry 85 }

expPort-ext-humi-min-range OBJECT-TYPE
	SYNTAX		INTEGER
	ACCESS		read-write
	STATUS		mandatory
	DESCRIPTION	"The minimum humidity measureable by the humidity sensor, in percent.
        Needs to be set based on the type of humidity sensor module installed."
	::= { expPortEntry 86 }

expPort-ext-humi-max-range OBJECT-TYPE
	SYNTAX		INTEGER
	ACCESS		read-write
	STATUS		mandatory
	DESCRIPTION	"The maximum humidity measureable by the humidity sensor, in percent.
        Needs to be set based on the type of humidity sensor module installed."
	::= { expPortEntry 87 }

netbotz-crawlers OBJECT IDENTIFIER
                     ::= { netBotz-prd-crawlers 5528 }
netBotz-prd-crl-mib2 OBJECT IDENTIFIER
                     ::= { netbotz-crawlers 1 }
netBotz-prd-crl-mib2if OBJECT IDENTIFIER
                     ::= { netbotz-crawlers 2 }

netBotz-prd-crl-mib2-ping OBJECT-TYPE
	SYNTAX		INTEGER
	ACCESS		read-only
	STATUS		mandatory
	DESCRIPTION	"NetBotz device ping. This object indicates the status of a ping
	on a device monitored by a NetBotz device."
	REFERENCE 	"NetBotz Device Ping"
	::= { netBotz-prd-crl-mib2 3 }

netBotz-prd-crl-mib2-uptime OBJECT-TYPE
	SYNTAX		TimeTicks
	ACCESS		read-only
	STATUS		mandatory
	DESCRIPTION	"The uptime of a device monitored by a NetBotz device."
	REFERENCE 	"NetBotz Uptime"
	::= { netBotz-prd-crl-mib2 8 }

netBotz-prd-crl-mib2-snmpstatus OBJECT-TYPE
	SYNTAX		DisplayString
	ACCESS		read-only
	STATUS		mandatory
	DESCRIPTION	"The SNMP status of a device monitored by a NetBotz device."
	REFERENCE 	"NetBotz SNMP Status"
	::= { netBotz-prd-crl-mib2 9 }

netBotz-prd-crl-mib2if-opstatus OBJECT-TYPE
	SYNTAX		INTEGER
	ACCESS		read-only
	STATUS		mandatory
	DESCRIPTION	"The operational status of a device monitored by a NetBotz device."
	REFERENCE 	"NetBotz Operational Status"
	::= { netBotz-prd-crl-mib2if 6 }

netBotz-prd-crl-trap-index OBJECT-TYPE
	SYNTAX		INTEGER
	ACCESS		read-only
	STATUS		mandatory
	DESCRIPTION	"The ID of the crawler which sent the last trap."
	REFERENCE 	"NetBotz Last Trap ID"
	::= { netBotz-prd-crltrap 20 }

netBotz-prd-crl-trap-address OBJECT-TYPE
	SYNTAX		IpAddress
	ACCESS		read-only
	STATUS		mandatory
	DESCRIPTION	"The IP address of the last trap."
	REFERENCE 	"NetBotz Last Trap Address"
	::= { netBotz-prd-crltrap 21 }

netBotz-prd-crl-trap-oid OBJECT-TYPE
	SYNTAX		OBJECT IDENTIFIER
	ACCESS		read-only
	STATUS		mandatory
	DESCRIPTION	"The object id of the attribute on the target device which is the concern of the last trap."
	REFERENCE 	"NetBotz Target Trap Attribute OID"
	::= { netBotz-prd-crltrap 22 }

netBotz-prd-crl-trap-botoid OBJECT-TYPE
	SYNTAX		OBJECT IDENTIFIER
	ACCESS		read-only
	STATUS		mandatory
	DESCRIPTION	"The object id of the attribute on the NetBotz device which is the concern of the last trap."
	REFERENCE 	"NetBotz Botz Trap Attribute OID"
	::= { netBotz-prd-crltrap 23 }

netBotz-prd-crl-trap-value OBJECT-TYPE
	SYNTAX		INTEGER
	ACCESS		read-only
	STATUS		mandatory
	DESCRIPTION	"The value of the attribute associated with the last trap."
	REFERENCE 	"NetBotz Trap Attribute Value"
	::= { netBotz-prd-crltrap 24 }

netBotz-prd-crl-trap-date OBJECT-TYPE
	SYNTAX		INTEGER
	ACCESS		read-only
	STATUS		mandatory
	DESCRIPTION
	"The date and time of a specific trap. This field
	contains the number of seconds elapsed since
	midnight (00:00:00), January 1, 1970"
	REFERENCE 	"NetBotz Trap Date"
	::= { netBotz-prd-crltrap 25 }

netBotz-prd-crl-trap-attrib OBJECT-TYPE
	SYNTAX		INTEGER
	ACCESS		read-only
	STATUS		mandatory
	DESCRIPTION	"The identification number of the attribute in error"
	REFERENCE 	"NetBotz Trap Attribute ID Number"
	::= { netBotz-prd-crltrap 26 }

netBotz-prd-crl-trap-desc OBJECT-TYPE
	SYNTAX		DisplayString
	ACCESS		read-only
	STATUS		mandatory
	DESCRIPTION	"Description or name of the attribute in error"
	REFERENCE 	"NetBotz Trap Attribute Description"
	::= { netBotz-prd-crltrap 27 }


netBotz-prd-crl-ping-offline-trap TRAP-TYPE
	ENTERPRISE netBotz-prd-crl-mib2-ping
	VARIABLES {
		netBotz-prd-crl-trap-index,
		netBotz-prd-crl-trap-address,
		netBotz-prd-crl-trap-oid,
		netBotz-prd-crl-trap-botoid,
		netBotz-prd-crl-trap-value,
		netBotz-prd-crl-trap-date,
		netBotz-prd-crl-trap-attrib,
		netBotz-prd-crl-trap-desc,
		netBotz-ismetric
		}
	DESCRIPTION
	"NetBotz Ping Trap. This trap indicates that replies to a set of pings were not received from a monitored IP address."
	REFERENCE 	"NetBotz Ping Offline Trap"
	::= 4

netBotz-prd-crl-ping-online-trap TRAP-TYPE
	ENTERPRISE netBotz-prd-crl-mib2-ping
	VARIABLES {
		netBotz-prd-crl-trap-index,
		netBotz-prd-crl-trap-address,
		netBotz-prd-crl-trap-oid,
		netBotz-prd-crl-trap-botoid,
		netBotz-prd-crl-trap-value,
		netBotz-prd-crl-trap-date,
		netBotz-prd-crl-trap-attrib,
		netBotz-prd-crl-trap-desc,
		netBotz-ismetric
		}
	DESCRIPTION
	"NetBotz Ping Trap. This trap indicates that replies to a set of pings were received from a monitored IP address after
	a period when no replies had been received."
	REFERENCE 	"NetBotz Ping Online Trap"
	::= 5

netBotz-prd-crl-snmp-offline-trap TRAP-TYPE
	ENTERPRISE netBotz-prd-crl-mib2-snmpstatus
	VARIABLES {
		netBotz-prd-crl-trap-index,
		netBotz-prd-crl-trap-address,
		netBotz-prd-crl-trap-oid,
		netBotz-prd-crl-trap-botoid,
		netBotz-prd-crl-trap-value,
		netBotz-prd-crl-trap-date,
		netBotz-prd-crl-trap-attrib,
		netBotz-prd-crl-trap-desc,
		netBotz-ismetric
		}
	DESCRIPTION
	"NetBotz SNMP Offline Trap. This trap indicates that an SNMP request was
	not possible on an IP address."
	REFERENCE 	"NetBotz SNMP Offline Trap"
	::= 4

netBotz-prd-crl-snmp-online-trap TRAP-TYPE
	ENTERPRISE netBotz-prd-crl-mib2-snmpstatus
	VARIABLES {
		netBotz-prd-crl-trap-index,
		netBotz-prd-crl-trap-address,
		netBotz-prd-crl-trap-oid,
		netBotz-prd-crl-trap-botoid,
		netBotz-prd-crl-trap-value,
		netBotz-prd-crl-trap-date,
		netBotz-prd-crl-trap-attrib,
		netBotz-prd-crl-trap-desc,
		netBotz-ismetric
		}
	DESCRIPTION
	"NetBotz SNMP Online Trap. This trap indicates that an SNMP request succeeded
	on an IP address where it had previously failed."
	REFERENCE 	"NetBotz SNMP Online Trap"
	::= 5

netBotz-prd-crl-uptime-online-trap TRAP-TYPE
	ENTERPRISE netBotz-prd-crl-mib2-uptime
	VARIABLES {
		netBotz-prd-crl-trap-index,
		netBotz-prd-crl-trap-address,
		netBotz-prd-crl-trap-oid,
		netBotz-prd-crl-trap-botoid,
		netBotz-prd-crl-trap-value,
		netBotz-prd-crl-trap-date,
		netBotz-prd-crl-trap-attrib,
		netBotz-prd-crl-trap-desc,
		netBotz-ismetric
		}
	DESCRIPTION
	"NetBotz Uptime Trap. This trap indicates that a device restart has been detected due to the uptime of the device
        being reported as less than the previously reported reading."
	REFERENCE 	"NetBotz Ping Uptime Trap"
	::= 5

netBotz-prd-crl-opstatus-offline-trap TRAP-TYPE
	ENTERPRISE netBotz-prd-crl-mib2if-opstatus
	VARIABLES {
		netBotz-prd-crl-trap-index,
		netBotz-prd-crl-trap-address,
		netBotz-prd-crl-trap-oid,
		netBotz-prd-crl-trap-botoid,
		netBotz-prd-crl-trap-value,
		netBotz-prd-crl-trap-date,
		netBotz-prd-crl-trap-attrib,
		netBotz-prd-crl-trap-desc,
		netBotz-ismetric
		}
	DESCRIPTION
	"NetBotz Interface Offline Trap. This trap indicates that an interface on a device
	did not respond to an SNMP query on the ifAdminStatus or ifOperStatus objects."
	REFERENCE 	"NetBotz Opstatus Offline Trap"
	::= 4

netBotz-prd-crl-opstatus-mismatch-trap TRAP-TYPE
	ENTERPRISE netBotz-prd-crl-mib2if-opstatus
	VARIABLES {
		netBotz-prd-crl-trap-index,
		netBotz-prd-crl-trap-address,
		netBotz-prd-crl-trap-oid,
		netBotz-prd-crl-trap-botoid,
		netBotz-prd-crl-trap-value,
		netBotz-prd-crl-trap-date,
		netBotz-prd-crl-trap-attrib,
		netBotz-prd-crl-trap-desc,
		netBotz-ismetric
		}
	DESCRIPTION
	"NetBotz Interface Status Mismatch Trap. This trap indicates that the operational
	status of a device interface does not match the administrative status."
	REFERENCE 	"NetBotz Interface Mismatch Trap"
	::= 1

netBotz-prd-crl-opstatus-match-trap TRAP-TYPE
	ENTERPRISE netBotz-prd-crl-mib2if-opstatus
	VARIABLES {
		netBotz-prd-crl-trap-index,
		netBotz-prd-crl-trap-address,
		netBotz-prd-crl-trap-oid,
		netBotz-prd-crl-trap-botoid,
		netBotz-prd-crl-trap-value,
		netBotz-prd-crl-trap-date,
		netBotz-prd-crl-trap-attrib,
		netBotz-prd-crl-trap-desc,
		netBotz-ismetric
		}
	DESCRIPTION
	"NetBotz Interface Status Match Trap. This trap indicates that the operational
	status of a device interface now matches the administrative status. This trap indicates
	a transition from a state in which the administrative and operational status did not match."
	REFERENCE 	"NetBotz Interface Match Trap"
	::= 2

netBotz-snmp-traptarget OBJECT-TYPE
	SYNTAX		IpAddress
	ACCESS		read-write
	STATUS		mandatory
	DESCRIPTION
	"Target of traps from the NetBotz device. This field contains the
	IP address where NetBotz traps are to be sent."
	REFERENCE 	"NetBotz Trap Target"
	::= { netBotz-snmp 1 }

netBotz-snmp-community     OBJECT-TYPE
	SYNTAX		DisplayString
	ACCESS		read-write
	STATUS		mandatory
	DESCRIPTION	"The read/write community of the NetBotz device."
	REFERENCE 	"Read/Write Community"
	::= { netBotz-snmp 2 }

netBotz-snmp-timeout      OBJECT-TYPE
	SYNTAX		INTEGER
	ACCESS		read-write
	STATUS		mandatory
	DESCRIPTION	"SNMP Timeout period."
	REFERENCE 	"SNMP Timeout"
	::= { netBotz-snmp 3 }

netBotz-snmp-retries   OBJECT-TYPE
	SYNTAX		INTEGER
	ACCESS		read-write
	STATUS		mandatory
	DESCRIPTION	"SNMP Retry count."
	REFERENCE 	"SNMP Retries"
	::= { netBotz-snmp 4 }

netBotz-userid-1        OBJECT-TYPE
	SYNTAX		DisplayString
	ACCESS		read-write
	STATUS		mandatory
	DESCRIPTION	"The userID of the supervisor account (write-only)."
	REFERENCE 	"UserID 1"
	::= { netBotz-snmp 5 }

netBotz-password-1      OBJECT-TYPE
	SYNTAX		DisplayString
	ACCESS		read-write
	STATUS		mandatory
	DESCRIPTION	"The password of the supervisor account (write-only)."
	REFERENCE 	"Password 1"
	::= { netBotz-snmp 6 }

netBotz-userid-2        OBJECT-TYPE
	SYNTAX		DisplayString
	ACCESS		read-write
	STATUS		mandatory
	DESCRIPTION	"The userID of the full read access account (write-only)."
	REFERENCE 	"UserID 2"
	::= { netBotz-snmp 7 }

netBotz-password-2      OBJECT-TYPE
	SYNTAX		DisplayString
	ACCESS		read-write
	STATUS		mandatory
	DESCRIPTION	"The password of the full read access account (write-only)."
	REFERENCE 	"Password 2"
	::= { netBotz-snmp 8 }

netBotz-userid-3        OBJECT-TYPE
	SYNTAX		DisplayString
	ACCESS		read-write
	STATUS		mandatory
	DESCRIPTION	"The userID of the minimum read access account (write-only)."
	REFERENCE 	"UserID 3"
	::= { netBotz-snmp 9 }

netBotz-password-3      OBJECT-TYPE
	SYNTAX		DisplayString
	ACCESS		read-write
	STATUS		mandatory
	DESCRIPTION	"The password of the minimum read access account (write-only)."
	REFERENCE 	"Password 3"
	::= { netBotz-snmp 10 }

netBotz-snmp-traptarget2 OBJECT-TYPE
	SYNTAX		IpAddress
	ACCESS		read-write
	STATUS		mandatory
	DESCRIPTION
	"Second target of traps from the NetBotz device. This field contains an additional
	IP address where NetBotz traps are to be sent."
	REFERENCE 	"NetBotz Trap Target 2"
	::= { netBotz-snmp 11 }

netBotz-snmp-read-community     OBJECT-TYPE
	SYNTAX		DisplayString
	ACCESS		read-write
	STATUS		mandatory
	DESCRIPTION	"The read-only community of the NetBotz device."
	REFERENCE 	"Read-only Community"
	::= { netBotz-snmp 12 }

device-crawlers-trap-index OBJECT-TYPE
	SYNTAX		INTEGER
	ACCESS		read-only
	STATUS		mandatory
	DESCRIPTION	"The ID of the device crawler which sent the last trap."
	REFERENCE	"NetBotz Device Crawlers Last Trap ID"
	::= { device-crawlers-trap-attrib 20 }

device-crawlers-trap-address OBJECT-TYPE
	SYNTAX		IpAddress
	ACCESS		read-only
	STATUS		mandatory
	DESCRIPTION	"The IP address of the appliance actually creating the last trap."
	REFERENCE	"NetBotz Device Crawlers Last Trap Address"
	::= { device-crawlers-trap-attrib 21 }

device-crawlers-trap-oid OBJECT-TYPE
	SYNTAX		OBJECT IDENTIFIER
	ACCESS		read-only
	STATUS		mandatory
	DESCRIPTION	"The object id of the attribute on the device crawlers target device which is the concern of the last trap.  The second to last element indicates the index of the source of the problem (1=ICMP Ping, 2=SNMP Agent Status, 256-10239=Network Interfaces 1-9984, 10240 and above, indicates Advanced crawlers data).  The last element is the decimal representation of the IP address of the source of the problem."
	REFERENCE	"NetBotz Device Crawlers Target Trap Attribute OID"
	::= { device-crawlers-trap-attrib 22 }

device-crawlers-trap-botoid OBJECT-TYPE
	SYNTAX		OBJECT IDENTIFIER
	ACCESS		read-only
	STATUS		mandatory
	DESCRIPTION	"The object id of the device crawlers attribute on the NetBotz device which is the concern of the last trap."
	REFERENCE	"NetBotz Device Crawlers Botz Trap Attribute OID"
	::= { device-crawlers-trap-attrib 23 }

device-crawlers-trap-value OBJECT-TYPE
	SYNTAX		INTEGER
	ACCESS		read-only
	STATUS		mandatory
	DESCRIPTION	"The integer value of the device crawlers attribute associated with the last trap."
	REFERENCE	"NetBotz Device Crawlers Attribute Value"
	::= { device-crawlers-trap-attrib 24 }

device-crawlers-trap-stringvalue OBJECT-TYPE
	SYNTAX		DisplayString
	ACCESS		read-only
	STATUS		mandatory
	DESCRIPTION	"The string representation of the value of the device crawlers attribute associated with the last trap."
	REFERENCE	"NetBotz Device Crawlers Attribute String Value"
	::= { device-crawlers-trap-attrib 25 }

device-crawlers-trap-date OBJECT-TYPE
	SYNTAX		INTEGER
	ACCESS		read-only
	STATUS		mandatory
	DESCRIPTION	"The date and time of a specific device crawlers trap.  This field contains the number of seconds elapsed since midnight (00:00:00), January 1, 1970"
	REFERENCE	"NetBotz Device Crawlers Trap Date"
	::= { device-crawlers-trap-attrib 26 }

device-crawlers-trap-attrib-index OBJECT-TYPE
	SYNTAX		INTEGER
	ACCESS		read-only
	STATUS		mandatory
	DESCRIPTION	"The identification number of the device crawlers attribute in error"
	REFERENCE	"NetBotz Device Crawlers Trap Attribute ID Number"
	::= { device-crawlers-trap-attrib 27 }

device-crawlers-crawlers-trap-desc OBJECT-TYPE
	SYNTAX		DisplayString
	ACCESS		read-only
	STATUS		mandatory
	DESCRIPTION	"Description of the Device Crawlers Trap Attribute"
	REFERENCE	"NetBotz Device Crawlers Trap Attribute Description"
	::= { device-crawlers-trap-attrib 28 }

netBotz-device-crawlers-value-low-alert-trap TRAP-TYPE
	ENTERPRISE device-crawlers-trap
	VARIABLES {
		  device-crawlers-trap-index,
		  device-crawlers-trap-address,
		  device-crawlers-trap-oid,
		  device-crawlers-trap-botoid,
		  device-crawlers-trap-value,
		  device-crawlers-trap-stringvalue,
		  device-crawlers-trap-date,
		  device-crawlers-trap-attrib,
		  device-crawlers-trap-desc
		  }
	DESCRIPTION "NetBotz Device Crawlers Value Low Trap. This trap indicates that the lower limit on a monitored value has been exceeded."
	REFERENCE   "NetBotz Device Crawlers Value Low Trap"
	::= 1

netBotz-device-crawlers-value-high-alert-trap TRAP-TYPE
	ENTERPRISE device-crawlers-trap
	VARIABLES {
		  device-crawlers-trap-index,
		  device-crawlers-trap-address,
		  device-crawlers-trap-oid,
		  device-crawlers-trap-botoid,
		  device-crawlers-trap-value,
		  device-crawlers-trap-stringvalue,
		  device-crawlers-trap-date,
		  device-crawlers-trap-attrib,
		  device-crawlers-trap-desc
		  }
	DESCRIPTION "NetBotz Device Crawlers Value High Trap. This trap indicates that the upper limit on a monitored value has been exceeded."
	REFERENCE   "NetBotz Device Crawlers Value High Trap"
	::= 2

netBotz-device-crawlers-clear-alert-trap TRAP-TYPE
	ENTERPRISE device-crawlers-trap
	VARIABLES {
		  device-crawlers-trap-index,
		  device-crawlers-trap-address,
		  device-crawlers-trap-oid,
		  device-crawlers-trap-botoid,
		  device-crawlers-trap-value,
		  device-crawlers-trap-stringvalue,
		  device-crawlers-trap-date,
		  device-crawlers-trap-attrib,
		  device-crawlers-trap-desc
		  }
	DESCRIPTION "NetBotz Device Crawlers Clear Trap. This trap indicates that the previous alert condition has been cleared."
	REFERENCE   "NetBotz Device Crawlers Clear Trap"
	::= 3

netBotz-device-crawlers-offline-alert-trap TRAP-TYPE
	ENTERPRISE device-crawlers-trap
	VARIABLES {
		  device-crawlers-trap-index,
		  device-crawlers-trap-address,
		  device-crawlers-trap-oid,
		  device-crawlers-trap-botoid,
		  device-crawlers-trap-value,
		  device-crawlers-trap-stringvalue,
		  device-crawlers-trap-date,
		  device-crawlers-trap-attrib,
		  device-crawlers-trap-desc
		  }
	DESCRIPTION "NetBotz Device Crawlers Offline Trap. This trap indicates that a monitored target could not be contacted."
	REFERENCE   "NetBotz Device Crawlers Offline Trap"
	::= 4

netBotz-device-crawlers-online-alert-trap TRAP-TYPE
	ENTERPRISE device-crawlers-trap
	VARIABLES {
		  device-crawlers-trap-index,
		  device-crawlers-trap-address,
		  device-crawlers-trap-oid,
		  device-crawlers-trap-botoid,
		  device-crawlers-trap-value,
		  device-crawlers-trap-stringvalue,
		  device-crawlers-trap-date,
		  device-crawlers-trap-attrib,
		  device-crawlers-trap-desc
		  }
	DESCRIPTION "NetBotz Device Crawlers Online Trap. This trap indicates that a monitored target that previously could not be contacted has now been contacted successfully."
	REFERENCE   "NetBotz Device Crawlers Online Trap"
	::= 5

netBotz-device-crawlers-ifopstatus-alert-trap TRAP-TYPE
	ENTERPRISE device-crawlers-trap
	VARIABLES {
		  device-crawlers-trap-index,
		  device-crawlers-trap-address,
		  device-crawlers-trap-oid,
		  device-crawlers-trap-botoid,
		  device-crawlers-trap-value,
		  device-crawlers-trap-stringvalue,
		  device-crawlers-trap-date,
		  device-crawlers-trap-attrib,
		  device-crawlers-trap-desc
		  }
	DESCRIPTION "NetBotz Device Crawlers Interface Operational Status Trap. This trap indicates that one or more of a monitored target's network interfaces operational status is not equal to the desired status."
	REFERENCE   "NetBotz Device Crawlers Interface Operational Status Trap"
	::= 8

branch-checker-trap-index OBJECT-TYPE
	SYNTAX		INTEGER
	ACCESS		read-only
	STATUS		mandatory
	DESCRIPTION	"The ID of the branch checker which sent the last trap."
	REFERENCE	"NetBotz Branch Checker Last Trap ID"
	::= { branch-checker-trap-attrib 20 }

branch-checker-trap-address OBJECT-TYPE
	SYNTAX		IpAddress
	ACCESS		read-only
	STATUS		mandatory
	DESCRIPTION	"The IP address of the appliance actually creating the last trap."
	REFERENCE	"NetBotz Branch Checker Last Trap Address"
	::= { branch-checker-trap-attrib 21 }

branch-checker-trap-oid OBJECT-TYPE
	SYNTAX		OBJECT IDENTIFIER
	ACCESS		read-only
	STATUS		mandatory
	DESCRIPTION	"The object id of the attribute on the branch checker target device which is the concern of the last trap  The second to last element is the index of the source of the problem (256-260=SMTP Server, 1024-1026=DNS Server, 1536-1538=Web Server, 2048-2052=Generic Server). The last element is the decimal representation of the IP address of the source of the problem."
	REFERENCE	"NetBotz Branch Checker Target Trap Attribute OID"
	::= { branch-checker-trap-attrib 22 }

branch-checker-trap-botoid OBJECT-TYPE
	SYNTAX		OBJECT IDENTIFIER
	ACCESS		read-only
	STATUS		mandatory
	DESCRIPTION	"The object id of the branch checker attribute on the NetBotz device which is the concern of the last trap. The second to last element is the index of the source of the problem (256-260=SMTP Server, 1024-1026=DNS Server, 1536-1538=Web Server, 2048-2052=Generic Server). The last element is the decimal representation of the IP address of the source of the problem."
	REFERENCE	"NetBotz Branch Checker Botz Trap Attribute OID"
	::= { branch-checker-trap-attrib 23 }

branch-checker-trap-value OBJECT-TYPE
	SYNTAX		INTEGER
	ACCESS		read-only
	STATUS		mandatory
	DESCRIPTION	"The integer value of the branch checker attribute associated with the last trap."
	REFERENCE	"NetBotz Branch Checker Attribute Value"
	::= { branch-checker-trap-attrib 24 }

branch-checker-trap-stringvalue OBJECT-TYPE
	SYNTAX		DisplayString
	ACCESS		read-only
	STATUS		mandatory
	DESCRIPTION	"The string representation of the value of the branch checker attribute associated with the last trap."
	REFERENCE	"NetBotz Branch Checker Attribute String Value"
	::= { branch-checker-trap-attrib 25 }

branch-checker-trap-date OBJECT-TYPE
	SYNTAX		INTEGER
	ACCESS		read-only
	STATUS		mandatory
	DESCRIPTION	"The date and time of a specific branch checker trap.  This field contains the number of seconds elapsed since midnight (00:00:00), January 1, 1970"
	REFERENCE	"NetBotz Branch Checker Trap Date"
	::= { branch-checker-trap-attrib 26 }

branch-checker-trap-attrib-index OBJECT-TYPE
	SYNTAX		INTEGER
	ACCESS		read-only
	STATUS		mandatory
	DESCRIPTION	"The identification number of the branch checker attribute in error"
	REFERENCE	"NetBotz Branch Checker Trap Attribute ID Number"
	::= { branch-checker-trap-attrib 27 }

branch-checker-trap-desc OBJECT-TYPE
	SYNTAX		DisplayString
	ACCESS		read-only
	STATUS		mandatory
	DESCRIPTION	"Description of the Branch Checker Trap Attribute"
	REFERENCE	"NetBotz Branch Checker Trap Attribute Description"
	::= { branch-checker-trap-attrib 28 }

netBotz-branch-checker-clear-alert-trap TRAP-TYPE
	ENTERPRISE branch-checker-trap
	VARIABLES {
		  branch-checker-trap-index,
		  branch-checker-trap-address,
		  branch-checker-trap-oid,
		  branch-checker-trap-botoid,
		  branch-checker-trap-value,
		  branch-checker-trap-stringvalue,
		  branch-checker-trap-date,
		  branch-checker-trap-attrib,
		  branch-checker-trap-desc
		  }
	DESCRIPTION "NetBotz Branch Checker Clear Trap. This trap indicates that the previous alert condition has been cleared."
	REFERENCE   "NetBotz Branch Checker Clear Trap"
	::= 3

netBotz-branch-checker-offline-alert-trap TRAP-TYPE
	ENTERPRISE branch-checker-trap
	VARIABLES {
		  branch-checker-trap-index,
		  branch-checker-trap-address,
		  branch-checker-trap-oid,
		  branch-checker-trap-botoid,
		  branch-checker-trap-value,
		  branch-checker-trap-stringvalue,
		  branch-checker-trap-date,
		  branch-checker-trap-attrib,
		  branch-checker-trap-desc
		  }
	DESCRIPTION "NetBotz Branch Checker Offline Trap. This trap indicates that a monitored target could not be contacted."
	REFERENCE   "NetBotz Branch Checker Offline Trap"
	::= 4

netBotz-branch-checker-online-alert-trap TRAP-TYPE
	ENTERPRISE branch-checker-trap
	VARIABLES {
		  branch-checker-trap-index,
		  branch-checker-trap-address,
		  branch-checker-trap-oid,
		  branch-checker-trap-botoid,
		  branch-checker-trap-value,
		  branch-checker-trap-stringvalue,
		  branch-checker-trap-date,
		  branch-checker-trap-attrib,
		  branch-checker-trap-desc
		  }
	DESCRIPTION "NetBotz Branch Checker Online Trap. This trap indicates that a monitored target that previously could not be contacted has now been contacted successfully."
	REFERENCE   "NetBotz Branch Checker Online Trap"
	::= 5

netBotz-branch-checker-target-error-trap TRAP-TYPE
	ENTERPRISE branch-checker-trap
	VARIABLES {
		  branch-checker-trap-index,
		  branch-checker-trap-address,
		  branch-checker-trap-oid,
		  branch-checker-trap-botoid,
		  branch-checker-trap-value,
		  branch-checker-trap-stringvalue,
		  branch-checker-trap-date,
		  branch-checker-trap-attrib,
		  branch-checker-trap-desc
		  }
	DESCRIPTION "NetBotz Branch Target Error Trap. This trap indicates that a monitored target could be contacted, but not withing the timeout period specified."
	REFERENCE   "NetBotz Branch Target Error Trap"
	::= 12

END
