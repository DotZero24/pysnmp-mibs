NSCRTV-HFCEMS-LINE-MIB DEFINITIONS ::= BEGIN

IMPORTS
    OBJECT-TYPE
        FROM RFC-1212
    DisplayString
        FROM RFC1213-MIB
    lineIdent
        FROM NSCRTV-ROOT;

    lineVendorOID OBJECT-TYPE
        SYNTAX OBJECT IDENTIFIER
        ACCESS read-only
        STATUS optional
        DESCRIPTION
            ""
        ::= { lineIdent 1 }

    lineRFLevel OBJECT-TYPE
        SYNTAX INTEGER ( 0..127 )
        ACCESS read-only
        STATUS mandatory
        DESCRIPTION
            ""
        ::= {lineIdent 2 }

    lineLinePowerVoltage OBJECT-TYPE
        SYNTAX INTEGER ( 0..65535 )
        ACCESS read-only
        STATUS optional
        DESCRIPTION
            ""
        ::= { lineIdent 3 }

    lineLinePowerCurrent OBJECT-TYPE
        SYNTAX INTEGER ( 0..65535 )
        ACCESS read-only
        STATUS optional
        DESCRIPTION
            ""
        ::= { lineIdent 4 }



    lineNumberDCPowerSupply OBJECT-TYPE
        SYNTAX INTEGER ( 0..16 )
        ACCESS read-only
        STATUS mandatory
        DESCRIPTION
            ""
        ::= { lineIdent 5 }

    lineDCPowerTable OBJECT-TYPE
        SYNTAX SEQUENCE OF LineDCPowerEntry
        ACCESS not-accessible
        STATUS mandatory
        DESCRIPTION
            ""
        ::= { lineIdent 6 }

    lineDCPowerEntry OBJECT-TYPE
        SYNTAX LineDCPowerEntry
        ACCESS not-accessible
        STATUS mandatory
        DESCRIPTION
            ""
        INDEX { lineDCPowerIndex }
        ::= { lineDCPowerTable 1 }

    LineDCPowerEntry ::= SEQUENCE
        {
        lineDCPowerIndex
            INTEGER,
        lineDCPowerVoltage
            INTEGER,
        lineDCPowerCurrent
            INTEGER,
        lineDCPowerName
            DisplayString
        }

    lineDCPowerIndex OBJECT-TYPE
        SYNTAX INTEGER
        ACCESS read-only
        STATUS mandatory
        DESCRIPTION
            ""
        ::= { lineDCPowerEntry 1 }

    lineDCPowerVoltage OBJECT-TYPE
        SYNTAX INTEGER ( -32768..32767 )
        ACCESS read-only
        STATUS mandatory
        DESCRIPTION
            ""
        ::= { lineDCPowerEntry 2 }

    lineDCPowerCurrent OBJECT-TYPE
        SYNTAX INTEGER ( 0..65535 )
        ACCESS read-only
        STATUS optional
        DESCRIPTION
            ""
        ::= { lineDCPowerEntry 3 }

    lineDCPowerName OBJECT-TYPE
        SYNTAX DisplayString
        ACCESS read-only
        STATUS mandatory
        DESCRIPTION
            ""
        ::= { lineDCPowerEntry 4 }


END
