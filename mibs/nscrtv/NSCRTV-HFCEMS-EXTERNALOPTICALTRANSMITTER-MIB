NSCRTV-HFCEMS-EXTERNALOPTICALTRANSMITTER-MIB DEFINITIONS ::= BEGIN

IMPORTS
    OBJECT-TYPE
        FROM RFC-1212
    DisplayString
        FROM RFC1213-MIB
    otxIdent
        FROM NSCRTV-ROOT;

    otxVendorOID OBJECT-TYPE
        SYNTAX OBJECT IDENTIFIER
        ACCESS read-only
        STATUS optional
        DESCRIPTION
            ""
        ::= { otxIdent 1 }

    otxSlotNumber OBJECT-TYPE
        SYNTAX INTEGER
        ACCESS read-only
        STATUS mandatory
        DESCRIPTION
            ""
        ::= { otxIdent 2 }

    otxModuleTable OBJECT-TYPE
        SYNTAX SEQUENCE OF OtxModuleEntry
        ACCESS not-accessible
        STATUS mandatory
        DESCRIPTION
            ""
        ::= { otxIdent 3 }

    otxModuleEntry OBJECT-TYPE
        SYNTAX OtxModuleEntry
        ACCESS not-accessible
        STATUS mandatory
        DESCRIPTION
            ""
        INDEX { otxModuleIndex }
        ::= { otxModuleTable 1 }

    OtxModuleEntry ::= SEQUENCE {
        otxModuleIndex
            INTEGER,
        otxLaserControl
            INTEGER,
        otxConfigurationAGCMode
            INTEGER,
        otxConfigurationOmi
            INTEGER,
        otxConfigurationRfGain
            INTEGER,
        otxConfigurationSbsSuppression
            INTEGER,
        otxConfigurationChannelDistance
            INTEGER,
        otxConfigurationItuFrequency
            INTEGER,
        otxItuFrequencyMin
            INTEGER,
        otxItuFrequencyMax
            INTEGER,
        otxItuFrequencyStep
            INTEGER,
        otxInputRFLevel
            INTEGER,
        otxRfGain
            INTEGER,
        otxLaserCurrent
            INTEGER,
        otxLaserOutputPower
            INTEGER,
        otxLaserTemperature
            INTEGER,
        otxLaserTecCurrent
            INTEGER,
        otxOmi
            INTEGER
        }

    otxModuleIndex OBJECT-TYPE
        SYNTAX INTEGER
        ACCESS read-only
        STATUS mandatory
        DESCRIPTION
            ""
        ::= { otxModuleEntry 1 }

    otxLaserControl OBJECT-TYPE
        SYNTAX INTEGER {on (1), off (2) }
        ACCESS read-write
        STATUS mandatory
        DESCRIPTION
            ""
        ::= { otxModuleEntry 2 }

    otxConfigurationAGCMode OBJECT-TYPE
        SYNTAX INTEGER {
            modeAgcOff (1),
            modeCWUnmodulatedAgcOn (2),
            modeVideoModulatedAgcOn (3)
        }
        ACCESS read-write
        STATUS optional
        DESCRIPTION
            ""
        ::= { otxModuleEntry 3 }

    otxConfigurationOmi OBJECT-TYPE
        SYNTAX INTEGER
        ACCESS read-write
        STATUS optional
        DESCRIPTION
            ""
        ::= { otxModuleEntry 4 }

    otxConfigurationRfGain OBJECT-TYPE
        SYNTAX INTEGER
        ACCESS read-write
        STATUS optional
        DESCRIPTION
            ""
        ::= { otxModuleEntry 5 }

    otxConfigurationSbsSuppression OBJECT-TYPE
        SYNTAX INTEGER
        ACCESS read-write
        STATUS optional
        DESCRIPTION
            ""
        ::= { otxModuleEntry 6 }

    otxConfigurationChannelDistance OBJECT-TYPE
        SYNTAX INTEGER
        ACCESS read-write
        STATUS optional
        DESCRIPTION
            ""
        ::= { otxModuleEntry 7 }

    otxConfigurationItuFrequency OBJECT-TYPE
        SYNTAX INTEGER
        ACCESS read-write
        STATUS optional
        DESCRIPTION
            ""
        ::= { otxModuleEntry 8 }

    otxItuFrequencyMin OBJECT-TYPE
        SYNTAX INTEGER
        ACCESS read-only
        STATUS optional
        DESCRIPTION
            ""
        ::= { otxModuleEntry 9 }

    otxItuFrequencyMax OBJECT-TYPE
        SYNTAX INTEGER
        ACCESS read-only
        STATUS optional
        DESCRIPTION
            ""
        ::= { otxModuleEntry 10 }

    otxItuFrequencyStep OBJECT-TYPE
        SYNTAX INTEGER
        ACCESS read-only
        STATUS optional
        DESCRIPTION
            ""
        ::= { otxModuleEntry 11 }

    otxInputRFLevel OBJECT-TYPE
        SYNTAX INTEGER
        ACCESS read-only
        STATUS optional
        DESCRIPTION
            ""
        ::= { otxModuleEntry 12 }

    otxRfGain OBJECT-TYPE
        SYNTAX INTEGER
        ACCESS read-only
        STATUS optional
        DESCRIPTION
            ""
        ::= { otxModuleEntry 13 }

    otxLaserCurrent OBJECT-TYPE
        SYNTAX INTEGER
        ACCESS read-only
        STATUS mandatory
        DESCRIPTION
            ""
        ::= { otxModuleEntry 14 }

    otxLaserOutputPower OBJECT-TYPE
        SYNTAX INTEGER
        ACCESS read-only
        STATUS mandatory
        DESCRIPTION
            ""
        ::= { otxModuleEntry 15 }

    otxLaserTemperature OBJECT-TYPE
        SYNTAX INTEGER
        ACCESS read-only
        STATUS mandatory
        DESCRIPTION
            ""
        ::= { otxModuleEntry 16 }

    otxLaserTecCurrent OBJECT-TYPE
        SYNTAX INTEGER
        ACCESS read-only
        STATUS mandatory
        DESCRIPTION
            ""
        ::= { otxModuleEntry 17 }

    otxOmi OBJECT-TYPE
        SYNTAX INTEGER
        ACCESS read-only
        STATUS optional
        DESCRIPTION
            ""
        ::= { otxModuleEntry 18 }

    otxFansNumber OBJECT-TYPE
        SYNTAX INTEGER
        ACCESS read-only
        STATUS mandatory
        DESCRIPTION
            ""
        ::= { otxIdent 4 }

    otxFansTable OBJECT-TYPE
        SYNTAX SEQUENCE OF OtxFansEntry
        ACCESS not-accessible
        STATUS optional
        DESCRIPTION
            ""
        ::= { otxIdent 5 }

    otxFansEntry OBJECT-TYPE
        SYNTAX OtxFansEntry
        ACCESS not-accessible
        STATUS optional
        DESCRIPTION
            ""
        INDEX { otxFansIndex }
        ::= { otxFansTable 1 }

    OtxFansEntry ::= SEQUENCE {
        otxFansIndex
            INTEGER,
        otxFansState
            INTEGER,
        otxFansSpeed
            INTEGER,
        otxFansControl
            INTEGER,
        otxFansName
            DisplayString
        }

    otxFansIndex OBJECT-TYPE
        SYNTAX INTEGER
        ACCESS read-only
        STATUS optional
        DESCRIPTION
            ""
        ::= { otxFansEntry 1 }

    otxFansState OBJECT-TYPE
        SYNTAX INTEGER {normal (1), fault (2), off(3)}
        ACCESS read-only
        STATUS optional
        DESCRIPTION
            ""
        ::= { otxFansEntry 2 }

    otxFansSpeed OBJECT-TYPE
        SYNTAX INTEGER
        ACCESS read-only
        STATUS optional
        DESCRIPTION
            ""
        ::= { otxFansEntry 3 }

    otxFansControl OBJECT-TYPE
        SYNTAX INTEGER { on(1), off(2) }
        ACCESS read-write
        STATUS optional
        DESCRIPTION
            ""
        ::= { otxFansEntry 4 }

    otxFansName OBJECT-TYPE
        SYNTAX DisplayString
        ACCESS read-only
        STATUS optional
        DESCRIPTION
            ""
        ::= { otxFansEntry 5 }


    otxNumberDCPowerSupply OBJECT-TYPE
        SYNTAX INTEGER ( 0..16 )
        ACCESS read-only
        STATUS mandatory
        DESCRIPTION
            ""
        ::= { otxIdent 6 }

    otxDCPowerSupplyMode OBJECT-TYPE
        SYNTAX INTEGER { loadsharing(1), switchedRedundant(2), aloneSupply(3) }
        ACCESS read-only
        STATUS optional
        DESCRIPTION
            ""
        ::= { otxIdent 7 }

    otxDCPowerTable OBJECT-TYPE
        SYNTAX SEQUENCE OF OtxDCPowerEntry
        ACCESS not-accessible
        STATUS mandatory
        DESCRIPTION
            ""
        ::= { otxIdent 8 }

    otxDCPowerEntry OBJECT-TYPE
        SYNTAX OtxDCPowerEntry
        ACCESS not-accessible
        STATUS mandatory
        DESCRIPTION
            ""
        INDEX { otxDCPowerIndex }
        ::= { otxDCPowerTable 1 }

    OtxDCPowerEntry ::= SEQUENCE
    {
        otxDCPowerIndex
            INTEGER,
        otxDCPowerVoltage
            INTEGER,
        otxDCPowerCurrent
            INTEGER,
        otxDCPowerName
            DisplayString
    }

    otxDCPowerIndex OBJECT-TYPE
        SYNTAX INTEGER
        ACCESS read-only
        STATUS mandatory
        DESCRIPTION
            ""
        ::= { otxDCPowerEntry 1 }

    otxDCPowerVoltage OBJECT-TYPE
        SYNTAX INTEGER ( -32768..32767 )
        ACCESS read-only
        STATUS mandatory
        DESCRIPTION
            ""
        ::= { otxDCPowerEntry 2 }

    otxDCPowerCurrent OBJECT-TYPE
        SYNTAX INTEGER ( 0..65535 )
        ACCESS read-only
        STATUS optional
        DESCRIPTION
            ""
        ::= { otxDCPowerEntry 3 }

    otxDCPowerName OBJECT-TYPE
        SYNTAX DisplayString
        ACCESS read-only
        STATUS mandatory
        DESCRIPTION
            ""
        ::= { otxDCPowerEntry 4 }


END
