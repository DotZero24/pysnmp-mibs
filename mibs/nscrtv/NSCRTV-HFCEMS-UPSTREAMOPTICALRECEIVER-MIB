NSCRTV-HFCEMS-UPSTREAMOPTICALRECEIVER-MIB DEFINITIONS ::= BEGIN

IMPORTS
    OBJECT-TYPE
        FROM RFC-1212
    DisplayString
        FROM RFC1213-MIB
    uporIdent
        FROM NSCRTV-ROOT;

    uporVendorOID OBJECT-TYPE
        SYNTAX OBJECT IDENTIFIER
        ACCESS read-only
        STATUS optional
        DESCRIPTION
            ""
        ::= { uporIdent 1 }

    uporSlotNumber OBJECT-TYPE
        SYNTAX INTEGER ( 0..32767 )
        ACCESS read-write
        STATUS mandatory
        DESCRIPTION
            ""
        ::= { uporIdent 2 }

    uporDeviceTable OBJECT-TYPE
        SYNTAX SEQUENCE OF UporDeviceEntry
        ACCESS not-accessible
        STATUS mandatory
        DESCRIPTION
            ""
        ::= { uporIdent 3 }

    uporDeviceEntry OBJECT-TYPE
        SYNTAX UporDeviceEntry
        ACCESS not-accessible
        STATUS mandatory
        DESCRIPTION
            ""
        INDEX { uporIndex }
        ::= { uporDeviceTable 1 }

    UporDeviceEntry ::= SEQUENCE
        {
        uporIndex
            INTEGER,
        uporOpicalInputPower
            INTEGER,
        uporOutputRFAttenuationRange
            INTEGER,
        uporOutputRFAttenuation
            INTEGER,
        uporAGCControl
            INTEGER
        }

    uporIndex OBJECT-TYPE
        SYNTAX INTEGER ( 0..32767 )
        ACCESS read-only
        STATUS mandatory
        DESCRIPTION
            ""
        ::= { uporDeviceEntry 1 }

    uporOpicalInputPower OBJECT-TYPE
        SYNTAX INTEGER ( -32768..32767 )
        ACCESS read-only
        STATUS mandatory
        DESCRIPTION
            ""
        ::= { uporDeviceEntry 2 }

    uporOutputRFAttenuationRange OBJECT-TYPE
        SYNTAX INTEGER ( 0..127 )
        ACCESS read-only
        STATUS optional
        DESCRIPTION
            ""
        ::= { uporDeviceEntry 3 }

    uporOutputRFAttenuation OBJECT-TYPE
        SYNTAX INTEGER ( 0..127 )
        ACCESS read-write
        STATUS optional
        DESCRIPTION
            ""
        ::= { uporDeviceEntry 4 }

    uporAGCControl OBJECT-TYPE
        SYNTAX INTEGER {off(1),on(2)}
        ACCESS read-write
        STATUS optional
        DESCRIPTION
            ""
        ::= { uporDeviceEntry 5 }


    uporNumberDCPowerSupply OBJECT-TYPE
        SYNTAX INTEGER ( 0..16 )
        ACCESS read-only
        STATUS mandatory
        DESCRIPTION
            ""
        ::= { uporIdent 4 }

    uporDCPowerSupplyMode OBJECT-TYPE
        SYNTAX INTEGER { loadsharing(1), switchedRedundant(2),aloneSupply(3) }
        ACCESS read-only
        STATUS optional
        DESCRIPTION
            ""
        ::= { uporIdent 5 }

    uporDCPowerTable OBJECT-TYPE
        SYNTAX SEQUENCE OF UporDCPowerEntry
        ACCESS not-accessible
        STATUS mandatory
        DESCRIPTION
            ""
        ::= { uporIdent 6 }

    uporDCPowerEntry OBJECT-TYPE
        SYNTAX UporDCPowerEntry
        ACCESS not-accessible
        STATUS mandatory
        DESCRIPTION
            ""
        INDEX { uporDCPowerIndex }
        ::= { uporDCPowerTable 1 }

    UporDCPowerEntry ::= SEQUENCE {
        uporDCPowerIndex
            INTEGER,
        uporDCPowerVoltage
            INTEGER,
        uporDCPowerCurrent
            INTEGER,
        uporDCPowerName
            DisplayString
        }

    uporDCPowerIndex OBJECT-TYPE
        SYNTAX INTEGER
        ACCESS read-only
        STATUS mandatory
        DESCRIPTION
            ""
        ::= { uporDCPowerEntry 1 }

    uporDCPowerVoltage OBJECT-TYPE
        SYNTAX INTEGER ( -32768..32767 )
        ACCESS read-only
        STATUS mandatory
        DESCRIPTION
            ""
        ::= { uporDCPowerEntry 2 }

    uporDCPowerCurrent OBJECT-TYPE
        SYNTAX INTEGER ( 0..65535 )
        ACCESS read-only
        STATUS optional
        DESCRIPTION
            ""
        ::= { uporDCPowerEntry 3 }

    uporDCPowerName OBJECT-TYPE
        SYNTAX DisplayString
        ACCESS read-only
        STATUS mandatory
        DESCRIPTION
            ""
        ::= { uporDCPowerEntry 4 }


END
