NSCRTV-HFCEMS-AMPLIFIER-MIB DEFINITIONS ::= BEGIN

IMPORTS
    OBJECT-TYPE
        FROM RFC-1212
    DisplayString
        FROM RFC1213-MIB
    addIdent
        FROM NSCRTV-ROOT;


    addVendorOID OBJECT-TYPE
        SYNTAX OBJECT IDENTIFIER
        ACCESS read-only
        STATUS optional
        DESCRIPTION
            ""
        ::= { addIdent 1 }



    addNumberRFPort OBJECT-TYPE
        SYNTAX INTEGER ( 1..8)
        ACCESS read-only
        STATUS mandatory
        DESCRIPTION
            ""
        ::= { addIdent 2 }

    addPortMasterAttenuationControl OBJECT-TYPE
        SYNTAX INTEGER { none(1), low(2), high(3) }
        ACCESS read-write
        STATUS optional
        DESCRIPTION
            ""
        ::= { addIdent 3 }

    addRFPortTable OBJECT-TYPE
        SYNTAX SEQUENCE OF AddRFPortEntry
        ACCESS not-accessible
        STATUS mandatory
        DESCRIPTION
            ""
        ::= { addIdent 4 }

    addRFPortEntry OBJECT-TYPE
        SYNTAX AddRFPortEntry
        ACCESS not-accessible
        STATUS mandatory
        DESCRIPTION
            ""
        INDEX { addRFPortIndex }
        ::= { addRFPortTable 1 }

    AddRFPortEntry ::=
         SEQUENCE
         {
              addRFPortIndex
                   INTEGER,
              addRFPortControlType
                   INTEGER,
              addRFPortControlLevel
                   INTEGER,
              addRFPortOutputRFLevel
                   INTEGER,
              addRFPortName
                   DisplayString,
              addRFPortReverseAttenuationControl
                   INTEGER,
              addRFPortPowerFeedStatus
                  INTEGER,
              addRFPortInputRFLevel
                  INTEGER,
              addRFPortattenuation1
                  INTEGER,
              addRFPortattenuation2
                  INTEGER,
              addRFPorteq
                  INTEGER

         }

    addRFPortIndex OBJECT-TYPE
        SYNTAX INTEGER
        ACCESS read-only
        STATUS mandatory
        DESCRIPTION
           ""
        ::= { addRFPortEntry 1 }

    addRFPortControlType OBJECT-TYPE
         SYNTAX INTEGER { alc(1), asc(2), agc(3), none(4) }
         ACCESS read-only
         STATUS optional
         DESCRIPTION
            ""
         ::= { addRFPortEntry 2 }

    addRFPortControlLevel OBJECT-TYPE
         SYNTAX INTEGER
        ACCESS read-only
        STATUS optional
        DESCRIPTION
            ""
         ::= { addRFPortEntry 3 }

    addRFPortOutputRFLevel OBJECT-TYPE
         SYNTAX INTEGER ( 0..127 )
         ACCESS read-only
         STATUS optional
         DESCRIPTION
            ""
         ::= { addRFPortEntry 4 }

    addRFPortName OBJECT-TYPE
         SYNTAX DisplayString
         ACCESS read-only
         STATUS mandatory
         DESCRIPTION
            ""
         ::= { addRFPortEntry 5 }

    addRFPortReverseAttenuationControl OBJECT-TYPE
         SYNTAX INTEGER { none(1), low(2), high(3) }
         ACCESS read-write
         STATUS optional
         DESCRIPTION
            ""
        ::= { addRFPortEntry 6 }

    addRFPortPowerFeedStatus OBJECT-TYPE
         SYNTAX INTEGER { on(1),off(2)  }
         ACCESS read-only
         STATUS optional
         DESCRIPTION
             ""
        ::= { addRFPortEntry 7 }

    addRFPortInputRFLevel OBJECT-TYPE
         SYNTAX INTEGER ( 0..127 )
         ACCESS read-only
         STATUS optional
         DESCRIPTION
            ""
         ::= { addRFPortEntry 8 }

    addRFPortattenuation1 OBJECT-TYPE
         SYNTAX INTEGER ( 0..200 )
         ACCESS read-write
         STATUS optional
         DESCRIPTION
            ""
         ::= { addRFPortEntry 9 }

    addRFPortattenuation2 OBJECT-TYPE
         SYNTAX INTEGER ( 0..200 )
         ACCESS read-write
         STATUS optional
         DESCRIPTION
            ""
         ::= { addRFPortEntry 10 }

     addRFPorteq OBJECT-TYPE
         SYNTAX INTEGER ( 0..100 )
         ACCESS read-write
         STATUS optional
         DESCRIPTION
            ""
         ::= { addRFPortEntry 11 }


    addLinePowerVoltage1 OBJECT-TYPE
         SYNTAX INTEGER ( 0..65535 )
         ACCESS read-only
         STATUS optional
         DESCRIPTION
            ""
         ::= { addIdent 5 }

    addLinePowerVoltage2 OBJECT-TYPE
         SYNTAX INTEGER ( 0..65535 )
         ACCESS read-only
         STATUS optional
         DESCRIPTION
            ""
         ::= { addIdent 6 }

    addLinePowerCurrent OBJECT-TYPE
         SYNTAX INTEGER ( 0..65535 )
         ACCESS read-only
         STATUS optional
         DESCRIPTION
             ""
         ::= { addIdent 7 }



    addNumberDCPowerSupply OBJECT-TYPE
         SYNTAX INTEGER ( 0..16 )
         ACCESS read-only
         STATUS mandatory
         DESCRIPTION
             ""
         ::= { addIdent 8 }

    addDCPowerSupplyMode OBJECT-TYPE
         SYNTAX INTEGER { loadsharing(1), switchedRedundant(2), aloneSupply(3) }
         ACCESS read-only
         STATUS optional
         DESCRIPTION
            ""
         ::= { addIdent 9 }

    addDCPowerTable OBJECT-TYPE
         SYNTAX SEQUENCE OF AddDCPowerEntry
         ACCESS not-accessible
         STATUS mandatory
         DESCRIPTION
             ""
         ::= { addIdent 10}

    addDCPowerEntry OBJECT-TYPE
         SYNTAX AddDCPowerEntry
         ACCESS not-accessible
         STATUS mandatory
         DESCRIPTION
             ""
         INDEX { addDCPowerIndex }
         ::= { addDCPowerTable 1 }

    AddDCPowerEntry ::=SEQUENCE
         {
              addDCPowerIndex
                   INTEGER,
              addDCPowerVoltage
                   INTEGER,
              addDCPowerCurrent
                   INTEGER,
              addDCPowerName
                   DisplayString
         }

    addDCPowerIndex OBJECT-TYPE
         SYNTAX INTEGER
         ACCESS read-only
         STATUS mandatory
         DESCRIPTION
             ""
         ::= { addDCPowerEntry 1 }

    addDCPowerVoltage OBJECT-TYPE
         SYNTAX INTEGER ( -32768..32767 )
         ACCESS read-only
         STATUS mandatory
         DESCRIPTION
             ""
         ::= { addDCPowerEntry 2 }

    addDCPowerCurrent OBJECT-TYPE
         SYNTAX INTEGER ( 0..65535 )
         ACCESS read-only
         STATUS optional
         DESCRIPTION
             ""
         ::= { addDCPowerEntry 3 }

    addDCPowerName OBJECT-TYPE
         SYNTAX DisplayString
         ACCESS read-only
         STATUS mandatory
         DESCRIPTION
            ""
         ::= { addDCPowerEntry 4 }

     addChannelNumber OBJECT-TYPE
         SYNTAX INTEGER ( 0..200 )
         ACCESS read-write
         STATUS mandatory
         DESCRIPTION
             ""
         ::= { addIdent 11 }

      addFanControl OBJECT-TYPE
         SYNTAX INTEGER {off(0),on(1)}
         ACCESS read-write
         STATUS mandatory
         DESCRIPTION
             ""
         ::= { addIdent 12 }


-- *****************************************************************************
END
