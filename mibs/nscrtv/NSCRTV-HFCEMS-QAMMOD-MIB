NSCRTV-HFCEMS-QAMMOD-MIB DEFINITIONS ::= BEGIN

IMPORTS
    OBJECT-TYPE
        FROM RFC-1212
    DisplayString
        FROM RFC1213-MIB
    qammodIdent
        FROM NSCRTV-ROOT;

    qamModVendorOID OBJECT-TYPE
        SYNTAX OBJECT IDENTIFIER
        ACCESS read-only
        STATUS optional
        DESCRIPTION
            ""
        ::= { qammodIdent 1 }

    qamModmode OBJECT-TYPE
        SYNTAX INTEGER ( 1..6 )
        ACCESS read-write
        STATUS mandatory
        DESCRIPTION
            ""
        ::= { qammodIdent 2 }

    qamModsymbolrate OBJECT-TYPE
        SYNTAX INTEGER ( 0..65535 )
        ACCESS read-write
        STATUS mandatory
        DESCRIPTION
            ""
        ::= { qammodIdent 3 }

    qamModRFfreq OBJECT-TYPE
        SYNTAX INTEGER
        ACCESS read-write
        STATUS mandatory
        DESCRIPTION
            ""
        ::= { qammodIdent 4 }

    qamModRFLevel OBJECT-TYPE
        SYNTAX INTEGER
        ACCESS read-write
        STATUS optional
        DESCRIPTION
            ""
        ::= { qammodIdent 5 }

    qamModRFLevelatt OBJECT-TYPE
        SYNTAX INTEGER
        ACCESS read-write
        STATUS optional
        DESCRIPTION
            ""
        ::= { qammodIdent 6 }


    qamModInputInterface OBJECT-TYPE
        SYNTAX INTEGER {
            asi(1),
            spi(2),
            ds3(3),
            other(4)
        }
        ACCESS read-only
        STATUS mandatory
        DESCRIPTION
            ""
        ::= { qammodIdent 7 }

    qamInputstatus OBJECT-TYPE
        SYNTAX INTEGER {
            sync(1),
            noSync(2)
        }
        ACCESS read-only
        STATUS mandatory
        DESCRIPTION
            ""
        ::= { qammodIdent 8 }

    qamModTSpacketlen OBJECT-TYPE
        SYNTAX INTEGER {
            bytes188 (1),
            bytes204 (2)
        }
        ACCESS read-write
        STATUS mandatory
        DESCRIPTION
            ""
        ::= { qammodIdent 9 }

    qamPidFilterTable OBJECT-TYPE
        SYNTAX SEQUENCE OF QamPidFilterEntry
        ACCESS not-accessible
        STATUS mandatory
        DESCRIPTION
            ""
        ::= {qammodIdent 10}

    qamPidFilterEntry OBJECT-TYPE
        SYNTAX QamPidFilterEntry
        ACCESS not-accessible
        STATUS mandatory
        DESCRIPTION
            ""
        INDEX{qamPidFilterIndex}
        ::= {qamPidFilterTable 1}

     QamPidFilterEntry::=
        SEQUENCE{
            qamPidFilterIndex
                INTEGER,
            qamInPid
                INTEGER
        }

    qamPidFilterIndex OBJECT-TYPE
        SYNTAX INTEGER
        ACCESS read-only
        STATUS mandatory
        DESCRIPTION
            ""
        ::= {qamPidFilterEntry 1}

    qamInPid OBJECT-TYPE
        SYNTAX INTEGER (1..65535)
        ACCESS read-only
        STATUS mandatory
        DESCRIPTION
            ""
        ::= {qamPidFilterEntry 2}


    qamModNumberDCPowerSupply OBJECT-TYPE
        SYNTAX INTEGER ( 0..16 )
        ACCESS read-only
        STATUS mandatory
        DESCRIPTION
            ""
        ::= { qammodIdent 11 }

    qamModDCPowerSupplyMode OBJECT-TYPE
        SYNTAX INTEGER {
            loadsharing(1),
            switchedRedundant(2),
            aloneSupply(3)
        }
        ACCESS read-only
        STATUS optional
        DESCRIPTION
            ""
        ::= { qammodIdent 12 }

    qamModDCPowerTable OBJECT-TYPE
        SYNTAX SEQUENCE OF QamModDCPowerEntry
        ACCESS not-accessible
        STATUS mandatory
        DESCRIPTION
            ""
        ::= { qammodIdent 13 }

    qamModDCPowerEntry OBJECT-TYPE
        SYNTAX QamModDCPowerEntry
        ACCESS not-accessible
        STATUS mandatory
        DESCRIPTION
            ""
        INDEX { qamModDCPowerIndex }
        ::= { qamModDCPowerTable 1 }

    QamModDCPowerEntry ::=
        SEQUENCE {
            qamModDCPowerIndex
                INTEGER,
            qamModDCPowerVoltage
                INTEGER,
            qamModDCPowerCurrent
                INTEGER,
            qamModDCPowerName
                DisplayString
        }

    qamModDCPowerIndex OBJECT-TYPE
        SYNTAX INTEGER
        ACCESS read-only
        STATUS mandatory
        DESCRIPTION
            ""
        ::= { qamModDCPowerEntry 1 }

    qamModDCPowerVoltage OBJECT-TYPE
        SYNTAX INTEGER ( -32768..32767 )
        ACCESS read-only
        STATUS mandatory
        DESCRIPTION
            ""
        ::= { qamModDCPowerEntry 2 }

    qamModDCPowerCurrent OBJECT-TYPE
        SYNTAX INTEGER ( 0..65535 )
        ACCESS read-only
        STATUS optional
        DESCRIPTION
            ""
        ::= { qamModDCPowerEntry 3 }

    qamModDCPowerName OBJECT-TYPE
        SYNTAX DisplayString
        ACCESS read-only
        STATUS mandatory
        DESCRIPTION
            ""
        ::= { qamModDCPowerEntry 4 }

END
