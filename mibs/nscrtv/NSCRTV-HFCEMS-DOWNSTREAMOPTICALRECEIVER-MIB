NSCRTV-HFCEMS-DOWNSTREAMOPTICALRECEIVER-MIB DEFINITIONS ::= BEGIN


IMPORTS
    OBJECT-TYPE
        FROM RFC-1212
    DisplayString
        FROM RFC1213-MIB
    dorIdent
        FROM NSCRTV-ROOT;

    dorVendorOID OBJECT-TYPE
        SYNTAX OBJECT IDENTIFIER
        ACCESS read-only
        STATUS optional
        DESCRIPTION
            ""
        ::= { dorIdent 1 }

    dorRxInputNumber OBJECT-TYPE
        SYNTAX INTEGER
        ACCESS read-only
        STATUS mandatory
        DESCRIPTION
            ""
        ::= { dorIdent 2 }

    dorRxInputTable OBJECT-TYPE
        SYNTAX SEQUENCE OF DorRxInputEntry
        ACCESS not-accessible
        STATUS mandatory
        DESCRIPTION
            ""
        ::= { dorIdent 3 }

    dorRxInputEntry OBJECT-TYPE
        SYNTAX DorRxInputEntry
        ACCESS not-accessible
        STATUS mandatory
        DESCRIPTION
            ""
        INDEX { dorInputIndex }
        ::= { dorRxInputTable 1 }

    DorRxInputEntry ::= SEQUENCE {
        dorInputIndex
            INTEGER,
        dorInputPower
            INTEGER,
        dorInputWavelengthControl
            INTEGER,
        dorInputStatus
            INTEGER
        }

    dorInputIndex OBJECT-TYPE
        SYNTAX INTEGER
        ACCESS read-only
        STATUS mandatory
        DESCRIPTION
            ""
        ::= { dorRxInputEntry 1 }

    dorInputPower OBJECT-TYPE
        SYNTAX INTEGER
        ACCESS read-only
        STATUS mandatory
        DESCRIPTION
            ""
        ::= { dorRxInputEntry 2 }

    dorInputWavelengthControl OBJECT-TYPE
        SYNTAX INTEGER
        ACCESS read-write
        STATUS mandatory
        DESCRIPTION
            ""
        ::= { dorRxInputEntry 3 }

    dorInputStatus OBJECT-TYPE
        SYNTAX INTEGER
        {
            normal (1),
            fault (2)
        }
        ACCESS read-only
        STATUS mandatory
        DESCRIPTION
            ""
        ::= { dorRxInputEntry 4 }

    dorRxOutputNumber OBJECT-TYPE
        SYNTAX INTEGER
        ACCESS read-only
        STATUS mandatory
        DESCRIPTION
            ""
        ::= { dorIdent 4 }

    dorRxOutputTable OBJECT-TYPE
        SYNTAX SEQUENCE OF DorRxOutputEntry
        ACCESS not-accessible
        STATUS mandatory
        DESCRIPTION
            ""
        ::= { dorIdent 5 }

    dorRxOutputEntry OBJECT-TYPE
        SYNTAX DorRxOutputEntry
        ACCESS not-accessible
        STATUS mandatory
        DESCRIPTION
            ""
        INDEX { dorOutputIndex }
        ::= { dorRxOutputTable 1 }

    DorRxOutputEntry ::= SEQUENCE {
        dorOutputIndex
            INTEGER,
        dorOutputControl
            INTEGER,
        dorOutputGainType
            INTEGER,
        dorOutputLevel
            INTEGER,
        dorConfiguartionOutputLevel
            INTEGER,
        dorOutputRFlevelatt
            INTEGER,
        dorConfigurationOutputRFlevelatt
            INTEGER,
        dorOutputRFName
            DisplayString
    }

    dorOutputIndex OBJECT-TYPE
        SYNTAX INTEGER
        ACCESS read-only
        STATUS mandatory
        DESCRIPTION
            ""
        ::= { dorRxOutputEntry 1 }

    dorOutputControl OBJECT-TYPE
        SYNTAX INTEGER {off (1), on (2)}
        ACCESS read-write
        STATUS mandatory
        DESCRIPTION
            ""
        ::= { dorRxOutputEntry 2 }

    dorOutputGainType OBJECT-TYPE
        SYNTAX INTEGER {
            constantLevel(1),
            constantGain(2)
        }
        ACCESS read-write
        STATUS optional
        DESCRIPTION
            ""
        ::= { dorRxOutputEntry 3 }

    dorOutputLevel OBJECT-TYPE
        SYNTAX INTEGER
        ACCESS read-only
        STATUS mandatory
        DESCRIPTION
            ""
        ::= { dorRxOutputEntry 4 }

    dorConfiguartionOutputLevel OBJECT-TYPE
        SYNTAX INTEGER
        ACCESS read-write
        STATUS optional
        DESCRIPTION
            ""
        ::= { dorRxOutputEntry 5}


    dorOutputRFlevelatt  OBJECT-TYPE
	    SYNTAX INTEGER
	    ACCESS read-write
	    STATUS mandatory
	    DESCRIPTION
		    ""
	    ::= { dorRxOutputEntry 6 }

    dorConfigurationOutputRFlevelatt  OBJECT-TYPE
	    SYNTAX INTEGER
	    ACCESS read-write
	    STATUS optional
	    DESCRIPTION
	        ""
	    ::= { dorRxOutputEntry 7 }

    dorOutputRFName OBJECT-TYPE
	    SYNTAX DisplayString
	    ACCESS read-only
	    STATUS mandatory
	    DESCRIPTION
		    ""
	    ::= { dorRxOutputEntry 8 }


    dorNumberDCPowerSupply OBJECT-TYPE
        SYNTAX INTEGER ( 0..16 )
        ACCESS read-only
        STATUS mandatory
        DESCRIPTION
            ""
        ::= { dorIdent 6 }

    dorDCPowerSupplyMode OBJECT-TYPE
        SYNTAX INTEGER { loadsharing(1), switchedRedundant(2), aloneSupply(3) }
        ACCESS read-only
        STATUS optional
        DESCRIPTION
            ""
        ::= { dorIdent 7 }

    dorDCPowerTable OBJECT-TYPE
        SYNTAX SEQUENCE OF DorDCPowerEntry
        ACCESS not-accessible
        STATUS mandatory
        DESCRIPTION
            ""
        ::= { dorIdent 8 }

    dorDCPowerEntry OBJECT-TYPE
        SYNTAX DorDCPowerEntry
        ACCESS not-accessible
        STATUS mandatory
        DESCRIPTION
            ""
        INDEX { dorDCPowerIndex }
        ::= { dorDCPowerTable 1 }

    DorDCPowerEntry ::=
        SEQUENCE
        {
            dorDCPowerIndex
                INTEGER,
            dorDCPowerVoltage
                INTEGER,
            dorDCPowerCurrent
                INTEGER,
            dorDCPowerName
                DisplayString
        }

    dorDCPowerIndex OBJECT-TYPE
        SYNTAX INTEGER
        ACCESS read-only
        STATUS mandatory
        DESCRIPTION
            ""
        ::= { dorDCPowerEntry 1 }

    dorDCPowerVoltage OBJECT-TYPE
        SYNTAX INTEGER ( -32768..32767 )
        ACCESS read-only
        STATUS mandatory
        DESCRIPTION
            ""
        ::= { dorDCPowerEntry 2 }

    dorDCPowerCurrent OBJECT-TYPE
        SYNTAX INTEGER ( 0..65535 )
        ACCESS read-only
        STATUS optional
        DESCRIPTION
            ""
        ::= { dorDCPowerEntry 3 }

    dorDCPowerName OBJECT-TYPE
        SYNTAX DisplayString
        ACCESS read-only
        STATUS mandatory
        DESCRIPTION
            ""
        ::= { dorDCPowerEntry 4 }

   dorReverseOptPower OBJECT-TYPE
        SYNTAX INTEGER ( -32768..32767 )
        ACCESS read-only
        STATUS mandatory
        DESCRIPTION
            ""
        ::= { dorIdent 9 }
   dorReverseCurrent OBJECT-TYPE
        SYNTAX INTEGER ( 0..65535 )
        ACCESS read-only
        STATUS mandatory
        DESCRIPTION
            ""
        ::= { dorIdent 10 }

   dorChannelNum OBJECT-TYPE
        SYNTAX INTEGER ( 0..65535 )
        ACCESS read-write
        STATUS mandatory
        DESCRIPTION
            ""
        ::= { dorIdent 11 }



END
