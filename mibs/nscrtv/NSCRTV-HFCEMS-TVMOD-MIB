NSCRTV-HFCEMS-TVMOD-MIB DEFINITIONS ::= BEGIN

IMPORTS
    OBJECT-TYPE
        FROM RFC-1212
    DisplayString
        FROM RFC1213-MIB
    tvmodIdent
        FROM NSCRTV-ROOT;

    tvmodVendorOID OBJECT-TYPE
        SYNTAX OBJECT IDENTIFIER
        ACCESS read-only
        STATUS optional
        DESCRIPTION
            ""
        ::= { tvmodIdent 1 }

    tvmodOutputlevel OBJECT-TYPE
        SYNTAX INTEGER ( 0..255 )
        ACCESS read-only
        STATUS mandatory
        DESCRIPTION
            ""
        ::= { tvmodIdent 2 }

    tvmodOutputlevelAtt OBJECT-TYPE
        SYNTAX INTEGER ( 0..255 )
        ACCESS read-write
        STATUS mandatory
        DESCRIPTION
            ""
        ::= { tvmodIdent 3 }

    tvmodAVPower-ratio OBJECT-TYPE
        SYNTAX INTEGER ( -128..127 )
        ACCESS read-write
        STATUS mandatory
        DESCRIPTION
            ""
        ::= { tvmodIdent 4 }

    tvmodfreqdeviation OBJECT-TYPE
        SYNTAX INTEGER ( 0..255 )
        ACCESS read-write
        STATUS mandatory
        DESCRIPTION
            ""
        ::= { tvmodIdent 5 }

    tvmodOperatingFreq OBJECT-TYPE
        SYNTAX INTEGER
        ACCESS read-only
        STATUS mandatory
        DESCRIPTION
            ""
        ::= { tvmodIdent 6 }

    tvmodModulatingDepth OBJECT-TYPE
        SYNTAX INTEGER ( 0..99 )
        ACCESS read-write
        STATUS mandatory
        DESCRIPTION
            ""
        ::= { tvmodIdent 7 }

    tvmodLockalarm OBJECT-TYPE
        SYNTAX INTEGER {
            normal(1),
            alarm(2)
        }
        ACCESS read-only
        STATUS mandatory
        DESCRIPTION
            ""
        ::= { tvmodIdent 8 }



    tvmodNumberDCPowerSupply OBJECT-TYPE
        SYNTAX INTEGER ( 0..16 )
        ACCESS read-only
        STATUS mandatory
        DESCRIPTION
            ""
        ::= { tvmodIdent 9 }

    tvmodDCPowerSupplymode OBJECT-TYPE
        SYNTAX INTEGER { loadsharing(1), switchedRedundant(2) }
        ACCESS read-only
        STATUS optional
        DESCRIPTION
            ""
        ::= { tvmodIdent 10 }

    tvmodDCPowerTable OBJECT-TYPE
        SYNTAX SEQUENCE OF TvmodDCPowerEntry
        ACCESS not-accessible
        STATUS mandatory
        DESCRIPTION
            ""
        ::= { tvmodIdent 11 }

    tvmodDCPowerEntry OBJECT-TYPE
        SYNTAX TvmodDCPowerEntry
        ACCESS not-accessible
        STATUS mandatory
        DESCRIPTION
            ""
        INDEX { tvmodDCPowerIndex }
        ::= { tvmodDCPowerTable 1 }

    TvmodDCPowerEntry ::= SEQUENCE
        {
        tvmodDCPowerIndex
            INTEGER,
        tvmodDCPowerVoltage
            INTEGER,
        tvmodDCPowerCurrent
            INTEGER,
        tvmodDCPowerName
            DisplayString
        }

    tvmodDCPowerIndex OBJECT-TYPE
        SYNTAX INTEGER
        ACCESS read-only
        STATUS mandatory
        DESCRIPTION
            ""
        ::= { tvmodDCPowerEntry 1 }

    tvmodDCPowerVoltage OBJECT-TYPE
        SYNTAX INTEGER ( -32768..32767 )
        ACCESS read-only
        STATUS mandatory
        DESCRIPTION
            ""
        ::= { tvmodDCPowerEntry 2 }

    tvmodDCPowerCurrent OBJECT-TYPE
        SYNTAX INTEGER ( 0..65535 )
        ACCESS read-only
        STATUS optional
        DESCRIPTION
            ""
        ::= { tvmodDCPowerEntry 3 }

    tvmodDCPowerName OBJECT-TYPE
        SYNTAX DisplayString
        ACCESS read-only
        STATUS mandatory
        DESCRIPTION
            ""
        ::= { tvmodDCPowerEntry 4 }


END
