SIGNAMAX-SW0657851-MIB DEFINITIONS ::= BEGIN

IMPORTS
    DisplayString FROM SNMPv2-TC
    MODULE-COMPLIANCE,OBJECT-GROUP, NOTIFICATION-GROUP       FROM SNMPv2-CONF
    enterprises,MODULE-IDENTITY,OBJECT-TYPE,NOTIFICATION-TYPE,Counter32,IpAddress        FROM SNMPv2-SMI
    MacAddress FROM BRIDGE-MIB
    ifIndex    FROM RFC1213-MIB;


signamax MODULE-IDENTITY
        LAST-UPDATED "200812240000Z"
        ORGANIZATION "Signamax LLC"
        CONTACT-INFO
            ""
        DESCRIPTION
            "The MIB module is for Signamax LLC."
        ::= { enterprises 5205 }

switch                       OBJECT IDENTIFIER ::= { signamax 2 }

sw0657851ProductID	        OBJECT IDENTIFIER ::= { switch 34 }

sw0657851Produces            OBJECT IDENTIFIER ::= { sw0657851ProductID 1 }

sw0657851System           	OBJECT IDENTIFIER ::= { sw0657851Produces 1 }

sw0657851CommonSys           	OBJECT IDENTIFIER ::= { sw0657851System 1 }

sw0657851Reboot OBJECT-TYPE
	SYNTAX		INTEGER(0|1|2)
	MAX-ACCESS	    read-write
	STATUS		current
	DESCRIPTION
		"Reboot the system. Get this OID always return zero.
            0 - do nothing
			1 - Reboot without saving start
			2 - Reboot with saving start"
	::= { sw0657851CommonSys 1 }

sw0657851BiosVsersion	OBJECT-TYPE
	SYNTAX		DisplayString
	MAX-ACCESS	    read-only
	STATUS		current
	DESCRIPTION
		"Get the BIOS version of the system."
	::= { sw0657851CommonSys 2 }

sw0657851FirmwareVersion	OBJECT-TYPE
	SYNTAX		DisplayString
	MAX-ACCESS	    read-only
	STATUS		current
	DESCRIPTION
		"Get the firmware version of the system."
	::= { sw0657851CommonSys 3 }

sw0657851HardwareVersion	OBJECT-TYPE
	SYNTAX		DisplayString
	MAX-ACCESS	    read-only
	STATUS		current
	DESCRIPTION
		"Get the hardware version of the system."
	::= { sw0657851CommonSys 4 }

sw0657851MechanicalVersion OBJECT-TYPE
	SYNTAX		DisplayString
	MAX-ACCESS 	    read-only
	STATUS		current
	DESCRIPTION
		"Get the mechanical version of the system."
	::= { sw0657851CommonSys 5 }

sw0657851SerialNumber	OBJECT-TYPE
	SYNTAX		DisplayString
	MAX-ACCESS	    read-only
	STATUS		current
	DESCRIPTION
		"Get the Serial number of the system."
	::= { sw0657851CommonSys 6 }

sw0657851HostMacAddress	OBJECT-TYPE
	SYNTAX		DisplayString
	MAX-ACCESS	    read-only
	STATUS		current
	DESCRIPTION
		"Get the MAC address of the system."
	::= { sw0657851CommonSys 7 }

sw0657851DevicePort	OBJECT-TYPE
	SYNTAX		DisplayString
	MAX-ACCESS  	read-only
	STATUS		current
	DESCRIPTION
		"Get the quantity of ports that this system owns now."
	::= { sw0657851CommonSys 8 }

sw0657851RamSize  OBJECT-TYPE
    SYNTAX      DisplayString
    MAX-ACCESS      read-only
    STATUS      current
    DESCRIPTION
        "Get the RAM size of the system."
	::= { sw0657851CommonSys 9 }

sw0657851FlashSize  OBJECT-TYPE
    SYNTAX      DisplayString
    MAX-ACCESS      read-only
    STATUS      current
    DESCRIPTION
        "Get the flash size of the system."
	::= { sw0657851CommonSys 10 }

sw0657851DeviceName  OBJECT-TYPE
    SYNTAX      DisplayString
    MAX-ACCESS      read-write
    STATUS      current
    DESCRIPTION
        "Get the flash size of the Device Name."
	::= { sw0657851CommonSys 11 }

sw0657851SystemDescription  OBJECT-TYPE
    SYNTAX      DisplayString
    MAX-ACCESS      read-only
    STATUS      current
    DESCRIPTION
        "Get the flash size of the System Description."
	::= { sw0657851CommonSys 12 }

sw0657851IP           	OBJECT IDENTIFIER ::= { sw0657851System 2 }

sw0657851DhcpSetting OBJECT-TYPE
	SYNTAX		    INTEGER(0|1)
	MAX-ACCESS	        read-write
	STATUS		    current
	DESCRIPTION
		"Get/Set DHCP status of the system.
			0 - DHCP disable
			1 - DHCP enable"
	::= { sw0657851IP 1 }

sw0657851IPAddress OBJECT-TYPE
	SYNTAX      IpAddress
	MAX-ACCESS	    read-write
	STATUS		current
	DESCRIPTION
		"Get/Set the IP address of the system.
		 You can't set this OID if DHCP status is enabled."
	::= { sw0657851IP 2 }

sw0657851NetMask OBJECT-TYPE
	SYNTAX      IpAddress
	MAX-ACCESS	    read-write
	STATUS		current
	DESCRIPTION
		"Get/Set the subnet mask of the system.
		 You can't set this OID if DHCP status is enabled."
	::= { sw0657851IP 3 }

sw0657851DefaultGateway OBJECT-TYPE
	SYNTAX      IpAddress
	MAX-ACCESS	    read-write
	STATUS		current
	DESCRIPTION
		"Get/Set the default gateway of the system.
		 You can't set this OID if DHCP status is enabled."
	::= { sw0657851IP 4 }

sw0657851DnsSetting OBJECT-TYPE
	SYNTAX      INTEGER(0|1)
	MAX-ACCESS	    read-write
	STATUS		current
	DESCRIPTION
		"Get/Set the source of DNS server.
		 You can't set this OID if DHCP status is disabled.
			0 - manual, the DNS server is from manual setting
            1 - auto, the DNS server is assigned by DHCP server."
	::= { sw0657851IP 5 }

sw0657851DnsServer OBJECT-TYPE
	SYNTAX      IpAddress
	MAX-ACCESS	    read-write
	STATUS		current
	DESCRIPTION
		"Get/Set the DNS server of the system."
	::= { sw0657851IP 6 }

sw0657851Time           	OBJECT IDENTIFIER ::= { sw0657851System 3 }

sw0657851SystemCurrentTime OBJECT-TYPE
	SYNTAX      DisplayString
	MAX-ACCESS	    read-only
	STATUS		current
	DESCRIPTION
		"Get the current time of the system."
	::= { sw0657851Time 1 }

sw0657851ManualTimeSetting OBJECT-TYPE
	SYNTAX      DisplayString
	MAX-ACCESS	    read-write
	STATUS		current
	DESCRIPTION
		"Get/Set the system time of the device.
        The input format is 'Year/Month/Day/Hour/Minute/Second'.
        ex: 2004/1/1/12/34/25  means 2004/1/1 - 12:24:25 .
        The value range:
        Year    : 2000 - 2036,
        Mouth   : 1 - 12,
        Day     : 1 - 31,
        Hour    : 0 - 23,
        Minute  : 0 - 59,
        Sec     : 0 - 59."
	::= { sw0657851Time 2 }

sw0657851NTPServer OBJECT-TYPE
	SYNTAX      DisplayString
	MAX-ACCESS	    read-write
	STATUS		current
	DESCRIPTION
		"Get/Set the NTP Time Server. You can use the IP address or domain name."
	::= { sw0657851Time 3 }

sw0657851NTPTimeZone OBJECT-TYPE
	SYNTAX      INTEGER(-12..13)
	MAX-ACCESS	    read-write
	STATUS		current
	DESCRIPTION
		"Get/Set the NTP Time Zone.
		The value range is between -12 and 13
		-12 - GMT -12:00,
		-11 - GMT -11:00,
		-10 - GMT -10:00,
		 -9 - GMT -09:00,
		 -8 - GMT -08:00,
		 -7 - GMT -07:00,
		 -6 - GMT -06:00,
		 -5 - GMT -05:00,
		 -4 - GMT -04:00,
		 -3 - GMT -03:00,
		 -2 - GMT -02:00,
		 -1 - GMT -01:00,
		  0 - GMT +00:00,
		  1 - GMT +01:00,
		  2 - GMT +02:00,
		  3 - GMT +03:00,
		  4 - GMT +04:00,
		  5 - GMT +05:00,
		  6 - GMT +06:00,
		  7 - GMT +07:00,
		  8 - GMT +08:00,
		  9 - GMT +09:00,
		 10 - GMT +10:00,
		 11 - GMT +11:00,
		 12 - GMT +12:00,
		 13 - GMT +13:00. "
	::= { sw0657851Time 4 }

sw0657851NTPTimeSync OBJECT-TYPE
	SYNTAX      INTEGER(0|1)
	MAX-ACCESS	    read-write
	STATUS		current
	DESCRIPTION
		"Sync time from NTP Server. Get this OID always return zero.
		Set the Time Server and Time Zone before doing time sync.
		Notice that time server must be correct!
		The value range (0|1):
		1 - sync.
        0 - do nothing."
	::= { sw0657851Time 5 }

sw0657851DaylightSavingTime OBJECT-TYPE
	SYNTAX      INTEGER(-5..5)
	MAX-ACCESS	    read-write
	STATUS		current
	DESCRIPTION
		"Get/Set the daylight saving time.
		The value range is between -5 and 5. (Unit: hour)"
	::= { sw0657851Time 6 }

sw0657851DaylightStartTime OBJECT-TYPE
	SYNTAX      DisplayString
	MAX-ACCESS	    read-write
	STATUS		current
	DESCRIPTION
		"Get/Set the Start time of Daylight Saving.
		The input format is 'MM/DD/HH',
		and daylight saving start month can't equal end month.
		example: month/day/hour   10/01/00
		month: 01~12, day: 01~31, hour: 00~23 ."
	::= { sw0657851Time 7 }

sw0657851DaylightEndTime OBJECT-TYPE
	SYNTAX      DisplayString
	MAX-ACCESS	    read-write
	STATUS		current
	DESCRIPTION
		"Get/Set the End time of Daylight Saving.
		The input format is 'MM/DD/HH',
		and daylight saving start month can't equal end month.
		example: month/day/hour   04/01/00
		month: 01~12, day: 01~31, hour: 00~23 ."
	::= { sw0657851Time 8 }


sw0657851Account           	OBJECT IDENTIFIER ::= { sw0657851System 4 }

sw0657851AccountNumber OBJECT-TYPE
	SYNTAX      INTEGER(1..5)
	MAX-ACCESS	    read-only
	STATUS		current
	DESCRIPTION
		"Get the current account number(s) of the system."
	::= { sw0657851Account 1 }

sw0657851AccountTable	OBJECT-TYPE
	SYNTAX		SEQUENCE OF SW0657851AccountEntry
	MAX-ACCESS	not-accessible
	STATUS		current
	DESCRIPTION
		"This is a list of SW0657851AccountEntry. The numbers of entries are given by
		the value of sw0657851AccountNumber."
	::= { sw0657851Account 2 }

SW0657851AccountEntry ::=
SEQUENCE {
    sw0657851AccountIndex		    INTEGER,
    sw0657851AccountAuthorization	DisplayString,
    sw0657851AccountName             DisplayString,
    sw0657851AccountPassword         DisplayString
}

sw0657851AccountEntry	OBJECT-TYPE
	SYNTAX		SW0657851AccountEntry
	MAX-ACCESS	    not-accessible
	STATUS		current
	DESCRIPTION
		"This is the Entry(s) for account information."
	INDEX {sw0657851AccountIndex}
	::= { sw0657851AccountTable 1 }

sw0657851AccountIndex	OBJECT-TYPE
	SYNTAX		INTEGER(1..5)
	MAX-ACCESS	    read-only
	STATUS		current
	DESCRIPTION
		"This is the index of the account entry."
	::= { sw0657851AccountEntry 1 }

sw0657851AccountAuthorization	OBJECT-TYPE
	SYNTAX		DisplayString
	MAX-ACCESS	    read-only
	STATUS		current
	DESCRIPTION
		"This is the authorization of the account entry."
	::= { sw0657851AccountEntry 2 }

sw0657851AccountName	OBJECT-TYPE
	SYNTAX		DisplayString
	MAX-ACCESS	    read-write
	STATUS		current
	DESCRIPTION
		"This is the username of the account entry."
	::= { sw0657851AccountEntry 3 }

sw0657851AccountPassword	OBJECT-TYPE
	SYNTAX		DisplayString
	MAX-ACCESS	    read-write
	STATUS		current
	DESCRIPTION
		"This is the password of the account entry. The return value is always '********'."
	::= { sw0657851AccountEntry 4 }

sw0657851AccountAddName OBJECT-TYPE
	SYNTAX      DisplayString
	MAX-ACCESS	    read-write
	STATUS		current
	DESCRIPTION
		"This is the account name for adding operation."
	::= { sw0657851Account 3 }

sw0657851AccountAddPassword OBJECT-TYPE
	SYNTAX      DisplayString
	MAX-ACCESS	    read-write
	STATUS		current
	DESCRIPTION
		"This is the account password for adding operation. The return value is always '********'."
	::= { sw0657851Account 4 }

sw0657851DoAccountAdd OBJECT-TYPE
	SYNTAX      INTEGER(0|1)
	MAX-ACCESS	    read-write
	STATUS		current
	DESCRIPTION
		"Add account name. OID sw0657851AccountAddName and sw0657851AccountAddPassword must be
        filled first. Get this OID always return zero.
            1 - add account.
            0 - do nothing."
	::= { sw0657851Account 5 }

sw0657851AccountDel	OBJECT-TYPE
	SYNTAX		INTEGER(2..5)
	MAX-ACCESS	    read-write
	STATUS		current
	DESCRIPTION
		"Delete account. The value is valid sw0657851AccountIndex(Can't delete administrator)."
	::= { sw0657851Account 6 }




sw0657851Snmp           	OBJECT IDENTIFIER ::= { sw0657851Produces 2 }

sw0657851GetCommunity OBJECT-TYPE
	SYNTAX      DisplayString
	MAX-ACCESS	    read-write
	STATUS		current
	DESCRIPTION
		"Get/Set the get-community of the SNMP."
	::= { sw0657851Snmp 1 }

sw0657851SetCommunity OBJECT-TYPE
	SYNTAX      DisplayString
	MAX-ACCESS	    read-write
	STATUS		current
	DESCRIPTION
		"Get/Set the set-community of the SNMP."
	::= { sw0657851Snmp 2 }

sw0657851TrapHostNumber OBJECT-TYPE
	SYNTAX      INTEGER(1..6)
	MAX-ACCESS	    read-only
	STATUS		current
	DESCRIPTION
		"Get the number of trap hosts."
	::= { sw0657851Snmp 3 }

sw0657851TrapHostTable	OBJECT-TYPE
	SYNTAX		SEQUENCE OF SW0657851TrapHostEntry
	MAX-ACCESS	not-accessible
	STATUS		current
	DESCRIPTION
		"A list of trap host entry. The numbers of entries are given by the value of sw0657851TrapHostNumber."
    ::= { sw0657851Snmp 4 }

SW0657851TrapHostEntry ::=
SEQUENCE {
    sw0657851TrapHostIndex		    INTEGER,
    sw0657851TrapHostIP          	IpAddress,
    sw0657851TrapHostPort            INTEGER,
    sw0657851TrapHostCommunity       DisplayString
}

sw0657851TrapHostEntry	OBJECT-TYPE
	SYNTAX		SW0657851TrapHostEntry
	MAX-ACCESS	    not-accessible
	STATUS		current
	DESCRIPTION
		"This is the entry information for trap host."
	INDEX {sw0657851TrapHostIndex}
	::= { sw0657851TrapHostTable 1 }

sw0657851TrapHostIndex	OBJECT-TYPE
	SYNTAX		INTEGER(1..6)
	MAX-ACCESS	    read-only
	STATUS		current
	DESCRIPTION
		"The index of the trap host entry."
	::= { sw0657851TrapHostEntry 1 }

sw0657851TrapHostIP	OBJECT-TYPE
	SYNTAX		IpAddress
	MAX-ACCESS	    read-write
	STATUS		current
	DESCRIPTION
		"This is the IP of the trap host."
	::= { sw0657851TrapHostEntry 2 }


sw0657851TrapHostPort	OBJECT-TYPE
	SYNTAX		INTEGER(1..65535)
	MAX-ACCESS	    read-write
	STATUS		current
	DESCRIPTION
		"This is the receiving-port number of the trap host."
	::= { sw0657851TrapHostEntry 3 }


sw0657851TrapHostCommunity	OBJECT-TYPE
	SYNTAX		DisplayString
	MAX-ACCESS	    read-write
	STATUS		current
	DESCRIPTION
		"The community name for the trap PDU."
	::= { sw0657851TrapHostEntry 4 }



sw0657851Alarm           	OBJECT IDENTIFIER ::= { sw0657851Produces 3 }

sw0657851Event           	OBJECT IDENTIFIER ::= { sw0657851Alarm 1 }

sw0657851EventNumber OBJECT-TYPE
	SYNTAX      INTEGER(1..2147483647)
	MAX-ACCESS	    read-only
	STATUS		current
	DESCRIPTION
		"Get the total number of alarm events."
	::= { sw0657851Event 1 }

sw0657851EventTable	OBJECT-TYPE
	SYNTAX		SEQUENCE OF SW0657851EventEntry
	MAX-ACCESS	not-accessible
	STATUS		current
    DESCRIPTION
        "This is a list of alarm event entry. The numbers of entries are given by the value of sw0657851EventNumber."
	::= { sw0657851Event 2 }

SW0657851EventEntry ::=
SEQUENCE {
    sw0657851EventIndex		    INTEGER,
    sw0657851EventName          	DisplayString,
    sw0657851EventSendEmail      INTEGER,
    sw0657851EventSendTrap       INTEGER
}

sw0657851EventEntry	OBJECT-TYPE
	SYNTAX		SW0657851EventEntry
	MAX-ACCESS	    not-accessible
	STATUS		current
	DESCRIPTION
		"This is the entry information for alarm event."
	INDEX {sw0657851EventIndex}
	::= { sw0657851EventTable 1 }

sw0657851EventIndex	OBJECT-TYPE
	SYNTAX		INTEGER(1..2147483647)
	MAX-ACCESS	    read-only
	STATUS		current
	DESCRIPTION
		"This is the index of the alarm event entry."
	::= { sw0657851EventEntry 1 }

sw0657851EventName	OBJECT-TYPE
	SYNTAX		DisplayString
	MAX-ACCESS	    read-only
	STATUS		current
	DESCRIPTION
		"This is the alarm event name."
	::= { sw0657851EventEntry 2 }

sw0657851EventSendEmail	OBJECT-TYPE
	SYNTAX		INTEGER(0|1)
	MAX-ACCESS	    read-write
	STATUS		current
	DESCRIPTION
		"Send email when alarm event is triggered."
	::= { sw0657851EventEntry 3 }

sw0657851EventSendTrap	OBJECT-TYPE
	SYNTAX		INTEGER(0|1)
	MAX-ACCESS	    read-write
	STATUS		current
	DESCRIPTION
		"Send trap when alarm event is triggered."
	::= { sw0657851EventEntry 4 }




sw0657851Email           	OBJECT IDENTIFIER ::= { sw0657851Alarm 2 }

sw0657851EmailServer OBJECT-TYPE
	SYNTAX      DisplayString
	MAX-ACCESS	    read-write
	STATUS		current
	DESCRIPTION
		"This is the SMTP server for alarm event."
	::= { sw0657851Email 1 }

sw0657851EmailUsername OBJECT-TYPE
	SYNTAX      DisplayString
	MAX-ACCESS	    read-write
	STATUS		current
	DESCRIPTION
		"This is the Username of SMTP server."
	::= { sw0657851Email 2 }

sw0657851EmailPassword OBJECT-TYPE
	SYNTAX      DisplayString
	MAX-ACCESS	    read-write
	STATUS		current
	DESCRIPTION
		"This is the User Password of SMTP server."
	::= { sw0657851Email 3 }

sw0657851EmailUserNumber OBJECT-TYPE
	SYNTAX      INTEGER(1..6)
	MAX-ACCESS	    read-only
	STATUS		current
	DESCRIPTION
		"The number of the email users that you want to send the alarm notification."
	::= { sw0657851Email 4 }

sw0657851EmailUserTable	OBJECT-TYPE
	SYNTAX		SEQUENCE OF SW0657851EmailUserEntry
	MAX-ACCESS	not-accessible
	STATUS		current
    DESCRIPTION
        "This is a list of email user entry. The numbers of entries are given by the value of sw0657851EmailUserNumber."
	::= { sw0657851Email 5 }

SW0657851EmailUserEntry ::=
SEQUENCE {
    sw0657851EmailUserIndex		    INTEGER,
    sw0657851EmailUserAddress       	DisplayString
}

sw0657851EmailUserEntry	OBJECT-TYPE
	SYNTAX		SW0657851EmailUserEntry
	MAX-ACCESS	    not-accessible
	STATUS		current
	DESCRIPTION
		"This is the Entry information for email user entry."
	INDEX {sw0657851EmailUserIndex}
	::= { sw0657851EmailUserTable 1 }

sw0657851EmailUserIndex	OBJECT-TYPE
	SYNTAX		INTEGER(1..6)
	MAX-ACCESS	    read-only
	STATUS		current
	DESCRIPTION
		"This is the index of the email user entry."
	::= { sw0657851EmailUserEntry 1 }

sw0657851EmailUserAddress	OBJECT-TYPE
	SYNTAX		DisplayString
	MAX-ACCESS	    read-write
	STATUS		current
	DESCRIPTION
		"This is the email address of the email user entry."
	::= { sw0657851EmailUserEntry 2 }

sw0657851Configuration           	OBJECT IDENTIFIER ::= { sw0657851Produces 5 }

sw0657851SaveRestore           	OBJECT IDENTIFIER ::= { sw0657851Configuration 1 }

sw0657851SaveStart OBJECT-TYPE
	SYNTAX      INTEGER(0|1)
	MAX-ACCESS	    read-write
	STATUS		current
	DESCRIPTION
		"Save current configuration into flash memory (Save as Start Configuration).
        Get this OID always return zero.
            1 - save.
            0 - do nothing. "
	::= { sw0657851SaveRestore 1 }

sw0657851SaveUser OBJECT-TYPE
	SYNTAX      INTEGER(0|1)
	MAX-ACCESS	    read-write
	STATUS		current
	DESCRIPTION
		"Save current configuration into flash memory (Save as User Configuration).
        Get this OID always return zero.
            1 - save.
            0 - do nothing. "
	::= { sw0657851SaveRestore 2 }

sw0657851RestoreDefault OBJECT-TYPE
	SYNTAX      INTEGER(0|1|2)
	MAX-ACCESS	    read-write
	STATUS		current
	DESCRIPTION
		"Restore factory default configuration.
        Get this OID always return zero.
            2 - restore default included default ip address.
            1 - restore default without changing current ip address.
            0 - do nothing. "
	::= { sw0657851SaveRestore 3 }

sw0657851RestoreUser OBJECT-TYPE
	SYNTAX      INTEGER(0|1)
	MAX-ACCESS	    read-write
	STATUS		current
	DESCRIPTION
		"Restore user configuration.
        Get this OID always return zero.
            1 - restore.
            0 - do nothing. "
	::= { sw0657851SaveRestore 4 }




sw0657851ConfigFile           	OBJECT IDENTIFIER ::= { sw0657851Configuration 2 }

sw0657851ExportIpAddress OBJECT-TYPE
	SYNTAX      IpAddress
	MAX-ACCESS	    read-write
	STATUS		current
	DESCRIPTION
		"Get/Set the export tftp server."
	::= { sw0657851ConfigFile 1 }

sw0657851DoExportConfig OBJECT-TYPE
	SYNTAX      INTEGER(1|2)
	MAX-ACCESS	    read-write
	STATUS		current
	DESCRIPTION
		"Do export-config.
        Get this OID always return zero.
			1	-	export current section.
			2	-	export user section."
	::= { sw0657851ConfigFile 2 }

sw0657851ImportIpAddress OBJECT-TYPE
	SYNTAX      IpAddress
	MAX-ACCESS	    read-write
	STATUS		current
	DESCRIPTION
		"Get/Set the import tftp server."
	::= { sw0657851ConfigFile 3 }

sw0657851ImportConfigName OBJECT-TYPE
	SYNTAX      DisplayString
	MAX-ACCESS	    read-write
	STATUS		current
	DESCRIPTION
        "Get/Set the import file path and name."
	::= { sw0657851ConfigFile 4 }

sw0657851DoImportConfig OBJECT-TYPE
	SYNTAX      INTEGER(1|2)
	MAX-ACCESS	    read-write
	STATUS		current
	DESCRIPTION
		"Do import-config.
        Get this OID always return zero.
			1	-	import current section.
			2	-	import user section."
	::= { sw0657851ConfigFile 5 }




sw0657851Log           	OBJECT IDENTIFIER ::= { sw0657851Produces 7 }

sw0657851ClearLog OBJECT-TYPE
	SYNTAX      INTEGER(0|1)
	MAX-ACCESS	    read-write
	STATUS		current
	DESCRIPTION
		"Clear system log.
        Get this OID always return zero.
            1 - clear log.
            0 - do nothing. "
	::= { sw0657851Log 1 }


sw0657851LogNumber OBJECT-TYPE
	SYNTAX      INTEGER(0..120)
	MAX-ACCESS	    read-only
	STATUS		current
	DESCRIPTION
		"Get the number of current system log. "
	::= { sw0657851Log 4 }

sw0657851LogTable	OBJECT-TYPE
	SYNTAX		SEQUENCE OF SW0657851LogEntry
	MAX-ACCESS	not-accessible
	STATUS		current
    DESCRIPTION
        "This is a list of log entry. The numbers of entries are given by the value of sw0657851LogNumber."
	::= { sw0657851Log 5 }

SW0657851LogEntry ::=
SEQUENCE {
    sw0657851LogIndex		    INTEGER,
    sw0657851LogEvent           	DisplayString
}

sw0657851LogEntry	OBJECT-TYPE
	SYNTAX		SW0657851LogEntry
	MAX-ACCESS	    not-accessible
	STATUS		current
	DESCRIPTION
		"This is the Entry information for system log."
	INDEX {sw0657851LogIndex}
	::= { sw0657851LogTable 1 }

sw0657851LogIndex	OBJECT-TYPE
	SYNTAX		INTEGER(1..120)
	MAX-ACCESS	    not-accessible
	STATUS		current
	DESCRIPTION
		"This is the index of the log entry."
	::= { sw0657851LogEntry 1 }

sw0657851LogEvent	OBJECT-TYPE
	SYNTAX		DisplayString
	MAX-ACCESS	    read-only
	STATUS		current
	DESCRIPTION
		"This is the detail information of the log entry."
	::= { sw0657851LogEntry 2 }



sw0657851Firmware           	OBJECT IDENTIFIER ::= { sw0657851Produces 8 }

sw0657851FirmwareIpAddress OBJECT-TYPE
	SYNTAX      IpAddress
	MAX-ACCESS	    read-write
	STATUS		current
	DESCRIPTION
		"Get/Set the firmware tftp server."
	::= { sw0657851Firmware 1 }

sw0657851FirmwareFileName OBJECT-TYPE
	SYNTAX      DisplayString
	MAX-ACCESS	    read-write
	STATUS		current
	DESCRIPTION
		"Get/Set the path and filename for firmware upgrading."
	::= { sw0657851Firmware 2 }

sw0657851DoFirmwareUpgrade OBJECT-TYPE
	SYNTAX      INTEGER(0|1)
	MAX-ACCESS	    read-write
	STATUS		current
	DESCRIPTION
		"Do firmware upgrade. Get this OID always return zero.
            1 - do firmware upgrade.
            0 - do nothing."
	::= { sw0657851Firmware 3 }



sw0657851Port           	OBJECT IDENTIFIER ::= { sw0657851Produces 9 }

sw0657851PortStatus           	OBJECT IDENTIFIER ::= { sw0657851Port 1 }

sw0657851PortStatusNumber OBJECT-TYPE
	SYNTAX      INTEGER(1..2147483647)
	MAX-ACCESS	    read-only
	STATUS		current
	DESCRIPTION
		"Get the number of port."
	::= { sw0657851PortStatus 1 }

sw0657851PortStatusTable	OBJECT-TYPE
	SYNTAX		SEQUENCE OF SW0657851PortStatusEntry
	MAX-ACCESS	not-accessible
	STATUS		current
    DESCRIPTION
        "This is a list of port status entry. The numbers of entries are given by the value of sw0657851PortStatusNumber."
	::= { sw0657851PortStatus 2 }

SW0657851PortStatusEntry ::=
SEQUENCE {
    sw0657851PortStatusIndex		    INTEGER,
    sw0657851PortStatusMedia          DisplayString,
    sw0657851PortStatusLink           DisplayString,
    sw0657851PortStatusSpdDpx         DisplayString,
    sw0657851PortStatusFlwCtrlRx      DisplayString,
    sw0657851PortStatusFlwCtrlTx      DisplayString,
    sw0657851PortStatuDescription     DisplayString
}

sw0657851PortStatusEntry	OBJECT-TYPE
	SYNTAX		SW0657851PortStatusEntry
	MAX-ACCESS	    not-accessible
	STATUS		current
	DESCRIPTION
		"This is the entry(s) for port status information."
	INDEX {sw0657851PortStatusIndex}
	::= { sw0657851PortStatusTable 1 }

sw0657851PortStatusIndex	OBJECT-TYPE
	SYNTAX		INTEGER(1..2147483647)
	MAX-ACCESS	    read-only
	STATUS		current
	DESCRIPTION
		"This is the index of the port status entry."
	::= { sw0657851PortStatusEntry 1 }

sw0657851PortStatusMedia	OBJECT-TYPE
	SYNTAX		DisplayString
	MAX-ACCESS	    read-only
	STATUS		current
	DESCRIPTION
		"The port media type of the port status entry."
	::= { sw0657851PortStatusEntry 2 }

sw0657851PortStatusLink	OBJECT-TYPE
	SYNTAX		DisplayString
	MAX-ACCESS	    read-only
	STATUS		current
	DESCRIPTION
		"This is the port link of the port status entry."
	::= { sw0657851PortStatusEntry 3 }

sw0657851PortStatusSpdDpx 	OBJECT-TYPE
	SYNTAX		DisplayString
	MAX-ACCESS	    read-only
	STATUS		current
	DESCRIPTION
		"This is the speed/duplex of the port status entry."
	::= { sw0657851PortStatusEntry 4 }

sw0657851PortStatusFlwCtrlRx 	OBJECT-TYPE
	SYNTAX		DisplayString
	MAX-ACCESS	    read-only
	STATUS		current
	DESCRIPTION
		"This is the Rx flow control of the port status entry."
	::= { sw0657851PortStatusEntry 5 }

sw0657851PortStatusFlwCtrlTx 	OBJECT-TYPE
	SYNTAX		DisplayString
	MAX-ACCESS	    read-only
	STATUS		current
	DESCRIPTION
		"This is the Tx flow control of the port status entry."
	::= { sw0657851PortStatusEntry 6 }

sw0657851PortStatuDescription	OBJECT-TYPE
	SYNTAX		DisplayString
	MAX-ACCESS	    read-only
	STATUS		current
	DESCRIPTION
		"This is the description of port."
	::= { sw0657851PortStatusEntry 7 }

sw0657851PortConf           	OBJECT IDENTIFIER ::= { sw0657851Port 2 }

sw0657851PortConfNumber OBJECT-TYPE
	SYNTAX      INTEGER(1..2147483647)
	MAX-ACCESS	    read-only
	STATUS		current
	DESCRIPTION
		"Get the number of port configuration."
	::= { sw0657851PortConf 1 }

sw0657851PortConfTable	OBJECT-TYPE
	SYNTAX		SEQUENCE OF SW0657851PortConfEntry
	MAX-ACCESS	not-accessible
	STATUS		current
    DESCRIPTION
        "This is a list of port configuration entry. The numbers of entries are given by the value of sw0657851PortConfNumber."
	::= { sw0657851PortConf 2 }

SW0657851PortConfEntry ::=
SEQUENCE {
    sw0657851PortConfIndex		    INTEGER,
    sw0657851PortConfPortState        INTEGER,
    sw0657851PortConfSpdDpx           INTEGER,
    sw0657851PortConfFlwCtrl          INTEGER,
    sw0657851PortConfExcessiveCollisionMode      INTEGER,
    sw0657851PortConfDescription      DisplayString
}

sw0657851PortConfEntry	OBJECT-TYPE
	SYNTAX		SW0657851PortConfEntry
	MAX-ACCESS	    not-accessible
	STATUS		current
	DESCRIPTION
		"This is the Entry(s) for port configuration information."
	INDEX {sw0657851PortConfIndex}
	::= { sw0657851PortConfTable 1 }

sw0657851PortConfIndex	OBJECT-TYPE
	SYNTAX		INTEGER(1..2147483647)
	MAX-ACCESS	    read-only
	STATUS		current
	DESCRIPTION
		"This is the index of the port configuration entry."
	::= { sw0657851PortConfEntry 1 }

sw0657851PortConfPortState	OBJECT-TYPE
	SYNTAX		INTEGER(0|1)
	MAX-ACCESS	    read-write
	STATUS		current
	DESCRIPTION
		"This is the port state of the port configuration entry.
		 0 - disabled.
		 1 - enabled. "
	::= { sw0657851PortConfEntry 2 }

sw0657851PortConfSpdDpx	OBJECT-TYPE
	SYNTAX		INTEGER(0..5)
	MAX-ACCESS	    read-write
	STATUS		current
	DESCRIPTION
		"This is the speed/duplex of the port configuration entry.
		 0 - auto.
		 1 - 10M/Half.
		 2 - 10M/Full.
		 3 - 100M/Half.
		 4 - 100M/Full.
		 5 - 1G/Full.  "
	::= { sw0657851PortConfEntry 3 }

sw0657851PortConfFlwCtrl	OBJECT-TYPE
	SYNTAX		INTEGER(0|1)
	MAX-ACCESS	    read-write
	STATUS		current
	DESCRIPTION
		"This is the flow control of the port configuration entry.
		 0 - disabled.
		 1 - enabled.  "
	::= { sw0657851PortConfEntry 4 }

sw0657851PortConfExcessiveCollisionMode	OBJECT-TYPE
	SYNTAX		INTEGER(0|1)
	MAX-ACCESS	    read-write
	STATUS		current
	DESCRIPTION
		"
		 0 - Discard.
		 1 - Restart.  "
	::= { sw0657851PortConfEntry 5 }

sw0657851PortConfDescription	OBJECT-TYPE
	SYNTAX		DisplayString
	MAX-ACCESS	    read-write
	STATUS		current
	DESCRIPTION
		"This is the description of port."
	::= { sw0657851PortConfEntry 6 }

sw0657851SFPInfo           	OBJECT IDENTIFIER ::= { sw0657851Port 3 }

sw0657851SFPInfoNumber OBJECT-TYPE
	SYNTAX      INTEGER(1..2147483647)
	MAX-ACCESS	    read-only
	STATUS		current
	DESCRIPTION
		"Get the number of sfp info entry."
	::= { sw0657851SFPInfo 1 }

sw0657851SFPInfoTable	OBJECT-TYPE
	SYNTAX		SEQUENCE OF SW0657851SFPInfoEntry
	MAX-ACCESS	not-accessible
	STATUS		current
    DESCRIPTION
        "A list of sfp info entry. The numbers of entries are given by the value of sw0657851SFPInfoNumber."
	::= { sw0657851SFPInfo 2 }

SW0657851SFPInfoEntry ::=
SEQUENCE {
    sw0657851SFPInfoIndex INTEGER,
    sw0657851SFPConnectorType DisplayString,
    sw0657851SFPFiberType DisplayString,
    sw0657851SFPWavelength DisplayString,
    sw0657851SFPBaudRate DisplayString,
    sw0657851SFPVendorOUI DisplayString,
    sw0657851SFPVendorName DisplayString,
    sw0657851SFPVendorPN DisplayString,
    sw0657851SFPVendorRev DisplayString,
    sw0657851SFPVendorSN DisplayString,
    sw0657851SFPDateCode DisplayString,
    sw0657851SFPTemperature DisplayString,
    sw0657851SFPVcc DisplayString,
    sw0657851SFPTxBias DisplayString,
    sw0657851SFPTxPWR DisplayString,
    sw0657851SFPRxPWR DisplayString
}

sw0657851SFPInfoEntry	OBJECT-TYPE
	SYNTAX		SW0657851SFPInfoEntry
	MAX-ACCESS	    not-accessible
	STATUS		current
	DESCRIPTION
		"Entry(s) for SFP information."
	INDEX {sw0657851SFPInfoIndex}
	::= { sw0657851SFPInfoTable 1 }

sw0657851SFPInfoIndex	OBJECT-TYPE
	SYNTAX		INTEGER(1..2147483647)
	MAX-ACCESS	    read-only
	STATUS		current
	DESCRIPTION
		"The index of the sfp info entry."
	::= { sw0657851SFPInfoEntry 1 }

sw0657851SFPConnectorType	OBJECT-TYPE
	SYNTAX		DisplayString
	MAX-ACCESS	    read-only
	STATUS		current
	DESCRIPTION
		"Get connector type of the sfp."
	::= { sw0657851SFPInfoEntry 2 }

sw0657851SFPFiberType	OBJECT-TYPE
	SYNTAX		DisplayString
	MAX-ACCESS	    read-only
	STATUS		current
	DESCRIPTION
		"Get fiber type of the sfp."
	::= { sw0657851SFPInfoEntry 3 }

sw0657851SFPWavelength	OBJECT-TYPE
	SYNTAX		DisplayString
	MAX-ACCESS	    read-only
	STATUS		current
	DESCRIPTION
		"Get tx central wavelength of the sfp."
	::= { sw0657851SFPInfoEntry 4 }

sw0657851SFPBaudRate	OBJECT-TYPE
	SYNTAX		DisplayString
	MAX-ACCESS	    read-only
	STATUS		current
	DESCRIPTION
		"Get baud rate of the sfp."
	::= { sw0657851SFPInfoEntry 5 }

sw0657851SFPVendorOUI	OBJECT-TYPE
	SYNTAX		DisplayString
	MAX-ACCESS	    read-only
	STATUS		current
	DESCRIPTION
		"Get vendor OUI of the sfp."
	::= { sw0657851SFPInfoEntry 6 }

sw0657851SFPVendorName	OBJECT-TYPE
	SYNTAX		DisplayString
	MAX-ACCESS	    read-only
	STATUS		current
	DESCRIPTION
		"Get vendor name of the sfp."
	::= { sw0657851SFPInfoEntry 7 }

sw0657851SFPVendorPN	OBJECT-TYPE
	SYNTAX		DisplayString
	MAX-ACCESS	    read-only
	STATUS		current
	DESCRIPTION
		"Get vendor part number of the sfp."
	::= { sw0657851SFPInfoEntry 8 }

sw0657851SFPVendorRev	OBJECT-TYPE
	SYNTAX		DisplayString
	MAX-ACCESS	    read-only
	STATUS		current
	DESCRIPTION
		"Get vendor revision number of the sfp."
	::= { sw0657851SFPInfoEntry 9 }

sw0657851SFPVendorSN	OBJECT-TYPE
	SYNTAX		DisplayString
	MAX-ACCESS	    read-only
	STATUS		current
	DESCRIPTION
		"Get vendor serial number of the sfp."
	::= { sw0657851SFPInfoEntry 10 }

sw0657851SFPDateCode	OBJECT-TYPE
	SYNTAX		DisplayString
	MAX-ACCESS	    read-only
	STATUS		current
	DESCRIPTION
		"Get data code of the sfp."
	::= { sw0657851SFPInfoEntry 11 }

sw0657851SFPTemperature	OBJECT-TYPE
	SYNTAX		DisplayString
	MAX-ACCESS	    read-only
	STATUS		current
	DESCRIPTION
		"Get current temperature of the sfp."
	::= { sw0657851SFPInfoEntry 12 }

sw0657851SFPVcc	OBJECT-TYPE
	SYNTAX		DisplayString
	MAX-ACCESS	    read-only
	STATUS		current
	DESCRIPTION
		"Get current internal supply voltage of the sfp."
	::= { sw0657851SFPInfoEntry 13 }

sw0657851SFPTxBias	OBJECT-TYPE
	SYNTAX		DisplayString
	MAX-ACCESS	    read-only
	STATUS		current
	DESCRIPTION
		"Get current TX Bias of the sfp."
	::= { sw0657851SFPInfoEntry 14 }

sw0657851SFPTxPWR	OBJECT-TYPE
	SYNTAX		DisplayString
	MAX-ACCESS	    read-only
	STATUS		current
	DESCRIPTION
		"Get current TX output power of the sfp."
	::= { sw0657851SFPInfoEntry 15 }

sw0657851SFPRxPWR	OBJECT-TYPE
	SYNTAX		DisplayString
	MAX-ACCESS	    read-only
	STATUS		current
	DESCRIPTION
		"Get current Received Power of the sfp."
	::= { sw0657851SFPInfoEntry 16 }

sw0657851Mirror           	OBJECT IDENTIFIER ::= { sw0657851Produces 10 }

sw0657851MirroringPort OBJECT-TYPE
	SYNTAX      INTEGER(0..2147483647)
	MAX-ACCESS	    read-write
	STATUS		current
	DESCRIPTION
		"Get/Set the mirroring port.
		 The port range is from 1 to 24."
	::= { sw0657851Mirror 1 }

sw0657851MirroredPortsTable	OBJECT-TYPE
	SYNTAX		SEQUENCE OF SW0657851MirroredPortsEntry
	MAX-ACCESS	not-accessible
	STATUS		current
    DESCRIPTION
        "This is a list of port configuration entry. The numbers of entries are given by the value of sw0657851PortConfNumber."
	::= { sw0657851Mirror 2 }

SW0657851MirroredPortsEntry ::=
SEQUENCE {
    sw0657851MirroredPortIndex		    	INTEGER,
    sw0657851MirroredPortSrouceEnable        	INTEGER,
    sw0657851MirroredPortDestinationEnable        INTEGER
}

sw0657851MirroredPortsEntry	OBJECT-TYPE
	SYNTAX		SW0657851MirroredPortsEntry
	MAX-ACCESS	    not-accessible
	STATUS		current
	DESCRIPTION
		"This is the Entry(s) for port configuration information."
	INDEX {sw0657851MirroredPortIndex}
	::= { sw0657851MirroredPortsTable 1 }

sw0657851MirroredPortIndex	OBJECT-TYPE
	SYNTAX		INTEGER(1..24)
	MAX-ACCESS	    read-only
	STATUS		current
	DESCRIPTION
		"This is the index of the mirrored port."
	::= { sw0657851MirroredPortsEntry 1 }

sw0657851MirroredPortSrouceEnable	OBJECT-TYPE
	SYNTAX		INTEGER(0|1)
	MAX-ACCESS	    read-write
	STATUS		current
	DESCRIPTION
		"0 - disabled.
		 1 - enabled."
	::= { sw0657851MirroredPortsEntry 2 }

sw0657851MirroredPortDestinationEnable	OBJECT-TYPE
	SYNTAX		INTEGER(0|1)
	MAX-ACCESS	    read-write
	STATUS		current
	DESCRIPTION
		"0 - disabled.
		 1 - enabled."
	::= { sw0657851MirroredPortsEntry 3 }

sw0657851MaxPktLen           	OBJECT IDENTIFIER ::= { sw0657851Produces 11 }

sw0657851MaxPktLenPortNumber OBJECT-TYPE
	SYNTAX      INTEGER(1..24)
	MAX-ACCESS	    read-only
	STATUS		current
	DESCRIPTION
		"Get the number of Max. packet length."
	::= { sw0657851MaxPktLen 1 }

sw0657851MaxPktLenConfTable	OBJECT-TYPE
	SYNTAX		SEQUENCE OF SW0657851MaxPktLenConfEntry
	MAX-ACCESS	not-accessible
	STATUS		current
    DESCRIPTION
        "This is a list of Max. packet length entry. The numbers of entries are given by the value of sw0657851MaxPktLenPortNumber."
	::= { sw0657851MaxPktLen 2 }

SW0657851MaxPktLenConfEntry ::=
SEQUENCE {
    sw0657851MaxPktLenConfIndex		    INTEGER,
    sw0657851MaxPktLenConfSetting         INTEGER
}

sw0657851MaxPktLenConfEntry	OBJECT-TYPE
	SYNTAX		SW0657851MaxPktLenConfEntry
	MAX-ACCESS	    not-accessible
	STATUS		current
	DESCRIPTION
		"Entry(s) for Max. packet length information."
	INDEX {sw0657851MaxPktLenConfIndex}
	::= { sw0657851MaxPktLenConfTable 1 }

sw0657851MaxPktLenConfIndex	OBJECT-TYPE
	SYNTAX		INTEGER(1..24)
	MAX-ACCESS	    read-only
	STATUS		current
	DESCRIPTION
		"This is the index of the Max. packet length entry."
	::= { sw0657851MaxPktLenConfEntry 1 }

sw0657851MaxPktLenConfSetting	OBJECT-TYPE
	SYNTAX		INTEGER(1518..9600)
	MAX-ACCESS	    read-write
	STATUS		current
	DESCRIPTION
		"Get/Set the Max. packet length.
		 The Max. packet length is 1518~9600.  "
	::= { sw0657851MaxPktLenConfEntry 2 }

sw0657851LoopDetectedConf           	OBJECT IDENTIFIER ::= { sw0657851Produces 12 }

sw0657851LoopDetectedNumber OBJECT-TYPE
	SYNTAX      INTEGER(1..2147483647)
	MAX-ACCESS	    read-only
	STATUS		current
	DESCRIPTION
		"Get the number of loop detected entry."
	::= { sw0657851LoopDetectedConf 1 }

sw0657851LoopDetectedTable	OBJECT-TYPE
	SYNTAX		SEQUENCE OF SW0657851LoopDetectedEntry
	MAX-ACCESS	not-accessible
	STATUS		current
    DESCRIPTION
        "A list of loop detected entry. The numbers of entries are given by the value of sw0657851LoopDetectedNumber."
	::= { sw0657851LoopDetectedConf 2 }

SW0657851LoopDetectedEntry ::=
SEQUENCE {
    sw0657851LoopDetectedfIndex           INTEGER,
    sw0657851LoopDetectedPort             INTEGER,
    sw0657851LoopDetectedLockedPort       INTEGER
}

sw0657851LoopDetectedEntry	OBJECT-TYPE
	SYNTAX		SW0657851LoopDetectedEntry
	MAX-ACCESS	    not-accessible
	STATUS		current
	DESCRIPTION
		"Entry(s) for loop detected information."
	INDEX {sw0657851LoopDetectedfIndex}
	::= { sw0657851LoopDetectedTable 1 }

sw0657851LoopDetectedfIndex	OBJECT-TYPE
	SYNTAX		INTEGER(1..2147483647)
	MAX-ACCESS	    read-only
	STATUS		current
	DESCRIPTION
		"The index of the loop detected entry."
	::= { sw0657851LoopDetectedEntry 1 }

sw0657851LoopDetectedPort	OBJECT-TYPE
	SYNTAX		INTEGER(0|1)
	MAX-ACCESS	    read-write
	STATUS		current
	DESCRIPTION
		"The state of the loop detected entry.
		 0 - disabled.
		 1 - enabled. "
	::= { sw0657851LoopDetectedEntry 2 }

sw0657851LoopDetectedLockedPort	OBJECT-TYPE
	SYNTAX		INTEGER(0|1)
	MAX-ACCESS	    read-write
	STATUS		current
	DESCRIPTION
		"The current status of the loop detected port.
		 Get:
         0 - unlocked
         1 - locked due to the loop condition
         Set:
         0 - unlock the port
         1 - do nothing"
	::= { sw0657851LoopDetectedEntry 3 }


sw0657851ManagementPolicy           	OBJECT IDENTIFIER ::= { sw0657851Produces 13 }

sw0657851ManagementSecurityNumber OBJECT-TYPE
	SYNTAX      INTEGER(0..64)
	MAX-ACCESS	    read-only
	STATUS		current
	DESCRIPTION
		"This is the index of the management security entry."
	::= { sw0657851ManagementPolicy 1 }

sw0657851ManagementSecurityEntryCreate OBJECT-TYPE
	SYNTAX      INTEGER(0..64)
	MAX-ACCESS	    read-write
	STATUS		current
	DESCRIPTION
		"Create management security entry"
	::= { sw0657851ManagementPolicy 2 }

sw0657851ManagementSecurityTable	OBJECT-TYPE
	SYNTAX		SEQUENCE OF SW0657851ManagementSecurityEntry
	MAX-ACCESS	not-accessible
	STATUS		current
    DESCRIPTION
        "This is a list of SW0657851ManagementSecurityEntry. The numbers of entries are given by ManagementSecurityNumber."
	::= { sw0657851ManagementPolicy 3 }

SW0657851ManagementSecurityEntry ::=
SEQUENCE {
    sw0657851ManagementSecurityIndex		       INTEGER,
    sw0657851ManagementSecurityName            DisplayString,
    sw0657851ManagementSecurityIpRange         DisplayString,
    sw0657851ManagementSecurityIncomigPort     DisplayString,
    sw0657851ManagementSecurityAccessType      DisplayString,
    sw0657851ManagementSecurityAction          INTEGER,
    sw0657851ManagementSecurityEntryAction     INTEGER
}

sw0657851ManagementSecurityEntry	OBJECT-TYPE
	SYNTAX		SW0657851ManagementSecurityEntry
	MAX-ACCESS	    not-accessible
	STATUS		current
	DESCRIPTION
		"This is the Entry(s) for Management Security configuration information."
	INDEX {sw0657851ManagementSecurityIndex}
	::= { sw0657851ManagementSecurityTable 1 }

sw0657851ManagementSecurityIndex	OBJECT-TYPE
	SYNTAX		INTEGER(1..64)
	MAX-ACCESS	    read-only
	STATUS		current
	DESCRIPTION
		"This is the index of the management policy configuration entry."
	::= { sw0657851ManagementSecurityEntry 1 }

sw0657851ManagementSecurityName	OBJECT-TYPE
	SYNTAX		DisplayString
	MAX-ACCESS	    read-write
	STATUS		current
	DESCRIPTION
		"This is the username of the management security entry."
	::= { sw0657851ManagementSecurityEntry 2 }

sw0657851ManagementSecurityIpRange	OBJECT-TYPE
	SYNTAX		DisplayString
	MAX-ACCESS	    read-write
	STATUS		current
	DESCRIPTION
		"This is the ip range of the management security entry."
	::= { sw0657851ManagementSecurityEntry 3 }

sw0657851ManagementSecurityIncomigPort	OBJECT-TYPE
	SYNTAX		DisplayString
	MAX-ACCESS	    read-write
	STATUS		current
	DESCRIPTION
		"This is the incoming port of the management security entry."
	::= { sw0657851ManagementSecurityEntry 4 }

sw0657851ManagementSecurityAccessType	OBJECT-TYPE
	SYNTAX		DisplayString
	MAX-ACCESS	    read-write
	STATUS		current
	DESCRIPTION
		"
		 0 - any.
		 1 - http.
		 2 - telnet
		 3 - snmp"
	::= { sw0657851ManagementSecurityEntry 5 }

sw0657851ManagementSecurityAction	OBJECT-TYPE
	SYNTAX		INTEGER(0|1)
	MAX-ACCESS	    read-write
	STATUS		current
	DESCRIPTION
		"
		 0 - deny.
		 1 - accept."
	::= { sw0657851ManagementSecurityEntry 6 }

sw0657851ManagementSecurityEntryAction	OBJECT-TYPE
	SYNTAX		INTEGER(1..3)
	MAX-ACCESS	    read-write
	STATUS		current
	DESCRIPTION
		"
		 1 - active.
		 2 - notInService.
		 3 - delete."
	::= { sw0657851ManagementSecurityEntry 7 }



sw0657851VLAN           	OBJECT IDENTIFIER ::= { sw0657851Produces 14 }

sw0657851VlanConf           	OBJECT IDENTIFIER ::= { sw0657851VLAN 1 }

sw0657851VlanMode OBJECT-TYPE
	SYNTAX      INTEGER(0|1)
	MAX-ACCESS	    read-write
	STATUS		current
	DESCRIPTION
		"This is the VLAN Mode configuration, default is tag base.
		 0 - tag-base
		 1 - port-base"
	::= { sw0657851VlanConf 1 }

sw0657851ManagementVlan OBJECT-TYPE
	SYNTAX      INTEGER(1..4094)
	MAX-ACCESS	    read-write
	STATUS		current
	DESCRIPTION
		"To specify a vlan id that can communicate with the device."
	::= { sw0657851VlanConf 2 }

sw0657851PortIsolation OBJECT-TYPE
	SYNTAX      DisplayString
	MAX-ACCESS	    read-write
	STATUS		current
	DESCRIPTION
		"Selected port(s) only can communicate with unselected port(s).
		Selected port(s) will be isolated with each other."
	::= { sw0657851VlanConf 3 }

sw0657851TagBaseVlanGroup        	OBJECT IDENTIFIER ::= { sw0657851VLAN 2 }

sw0657851TagBaseVlanNumber OBJECT-TYPE
	SYNTAX      INTEGER(1..4094)
	MAX-ACCESS	    read-write
	STATUS		current
	DESCRIPTION
		"The number of tagged-based VLAN."
	::= { sw0657851TagBaseVlanGroup 1 }

sw0657851TagBaseVlanGroupEntryCreate OBJECT-TYPE
	SYNTAX      INTEGER(0..4094)
	MAX-ACCESS	    read-write
	STATUS		current
	DESCRIPTION
		"To create a VLAN entry in the tagged-based VLAN table.
         0 : none,
         1~4094 : specify the vid of the created VLAN."
	::= { sw0657851TagBaseVlanGroup 2 }

sw0657851TagBaseVlanGroupTable	OBJECT-TYPE
	SYNTAX		SEQUENCE OF SW0657851TagBaseVlanGroupEntry
	MAX-ACCESS	not-accessible
	STATUS		current
    DESCRIPTION
        "A list of tagged-based VLAN group entry. The number of entries can be taked from sw0657851TagBaseVlanNumber."
	::= { sw0657851TagBaseVlanGroup 3 }

SW0657851TagBaseVlanGroupEntry ::=
SEQUENCE {
    sw0657851TagBaseVlanVid		        INTEGER,
    sw0657851TagBaseVlanName          DisplayString,
    sw0657851TagBaseVlanIgmpProxy     INTEGER,
    sw0657851TagBaseVlanPrivateVlan   INTEGER,
    sw0657851TagBaseVlanGvrp   		INTEGER,
    sw0657851TagBaseVlanMemberPort    DisplayString,
    sw0657851TagBaseVlanEntryAction   INTEGER
}

sw0657851TagBaseVlanGroupEntry	OBJECT-TYPE
	SYNTAX		SW0657851TagBaseVlanGroupEntry
	MAX-ACCESS	    not-accessible
	STATUS		current
	DESCRIPTION
		"This is the Entry(s) for Tag Base VLAN Group configuration information."
	INDEX {sw0657851TagBaseVlanVid}
	::= { sw0657851TagBaseVlanGroupTable 1 }

sw0657851TagBaseVlanVid	OBJECT-TYPE
	SYNTAX		INTEGER(1..4094)
	MAX-ACCESS	    not-accessible
	STATUS		current
	DESCRIPTION
		"This is the index of the Tag Base VLAN Group configuration entry."
	::= { sw0657851TagBaseVlanGroupEntry 1 }

sw0657851TagBaseVlanName	OBJECT-TYPE
	SYNTAX		DisplayString
	MAX-ACCESS	    read-write
	STATUS		current
	DESCRIPTION
		"This is the name of the VLAN."
	::= { sw0657851TagBaseVlanGroupEntry 2 }

sw0657851TagBaseVlanIgmpProxy	OBJECT-TYPE
	SYNTAX		INTEGER(0|1)
	MAX-ACCESS	    read-write
	STATUS		current
	DESCRIPTION
		"To support IGMP proxy in this VLAN.
		 0 - Disable
		 1 - Enable"
	::= { sw0657851TagBaseVlanGroupEntry 3 }

sw0657851TagBaseVlanPrivateVlan	OBJECT-TYPE
	SYNTAX		INTEGER(0|1)
	MAX-ACCESS	    read-write
	STATUS		current
	DESCRIPTION
		"To apply the port isolation configuration.
		 0 - Disable
		 1 - Enable"
	::= { sw0657851TagBaseVlanGroupEntry 4 }

sw0657851TagBaseVlanGvrp	OBJECT-TYPE
	SYNTAX		INTEGER(0|1)
	MAX-ACCESS	    read-write
	STATUS		current
	DESCRIPTION
		"This VLAN can be propagated by gvrp.
		 0 - Disable
		 1 - Enable"
	::= { sw0657851TagBaseVlanGroupEntry 5 }

sw0657851TagBaseVlanMemberPort	OBJECT-TYPE
	SYNTAX		DisplayString
	MAX-ACCESS	    read-write
	STATUS		current
	DESCRIPTION
		"The member port(s) of this VLAN."
	::= { sw0657851TagBaseVlanGroupEntry 6 }

sw0657851TagBaseVlanEntryAction	OBJECT-TYPE
	SYNTAX		INTEGER(1..3)
	MAX-ACCESS	    read-write
	STATUS		current
	DESCRIPTION
		"The row status of VLAN.
		 1 - active
		 2 - notInService
		 3 - delete"
	::= { sw0657851TagBaseVlanGroupEntry 7 }

sw0657851VlanPortConfTable	OBJECT-TYPE
	SYNTAX		SEQUENCE OF SW0657851VlanPortConfEntry
	MAX-ACCESS	not-accessible
	STATUS		current
    DESCRIPTION
        "This is the port parameters for tagged-based VLAN."
	::= { sw0657851VLAN 3 }

SW0657851VlanPortConfEntry ::=
SEQUENCE {
    sw0657851VlanPortConfIndex		            INTEGER,
    sw0657851VlanPortConfVlanAware            INTEGER,
    sw0657851VlanPortConfIngressFiltering     INTEGER,
    sw0657851VlanPortConfFrameType            INTEGER,
    sw0657851VlanPortConfPvid                 INTEGER,
    sw0657851VlanPortConfRole                 INTEGER,
    sw0657851VlanPortConfUntagVid             INTEGER,
    sw0657851VlanPortConfDoubleTag            INTEGER
}

sw0657851VlanPortConfEntry	OBJECT-TYPE
	SYNTAX		SW0657851VlanPortConfEntry
	MAX-ACCESS	    not-accessible
	STATUS		current
	DESCRIPTION
		"These are the tagged-based VLAN parameters for each ports."
	INDEX {sw0657851VlanPortConfIndex}
	::= { sw0657851VlanPortConfTable 1 }

sw0657851VlanPortConfIndex	OBJECT-TYPE
	SYNTAX		INTEGER(1..24)
	MAX-ACCESS	    not-accessible
	STATUS		current
	DESCRIPTION
		"This is the index of the Port Base VLAN Group configuration entry."
	::= { sw0657851VlanPortConfEntry 1 }

sw0657851VlanPortConfVlanAware	OBJECT-TYPE
	SYNTAX		INTEGER(0|1)
	MAX-ACCESS	    read-write
	STATUS		current
	DESCRIPTION
		"
		 0 - Ignore incoming VLAN tag, using pvid as VLAN classification.
		 1 - Using VLAN tag information first."
	::= { sw0657851VlanPortConfEntry 2 }

sw0657851VlanPortConfIngressFiltering	OBJECT-TYPE
	SYNTAX		INTEGER(0|1)
	MAX-ACCESS	    read-write
	STATUS		current
	DESCRIPTION
		"If the packet is tagged with VLAN information, the ingress port will first determine if the
		 ingress port itself is a member of the tagged VLAN.
		 0 - Disable, don't care about the VLAN information of the packet.
		 1 - Enable."
	::= { sw0657851VlanPortConfEntry 3 }

sw0657851VlanPortConfFrameType	OBJECT-TYPE
	SYNTAX		INTEGER(0|1)
	MAX-ACCESS	    read-write
	STATUS		current
	DESCRIPTION
		"To determine what kind of packet the port should accept.
		 0 - All
		 1 - Only tagged packet"
	::= { sw0657851VlanPortConfEntry 4 }

sw0657851VlanPortConfPvid	OBJECT-TYPE
	SYNTAX		INTEGER(1..4094)
	MAX-ACCESS	    read-write
	STATUS		current
	DESCRIPTION
		"Each physical port has a parameter called PVID.
		All untagged frames are assigned to the LAN specified in the PVID parameter.
		When a tagged frame is received by a port, the tag is respected.
		If the frame is untagged, the value contained in the PVID is considered as a tag. "
	::= { sw0657851VlanPortConfEntry 5 }

sw0657851VlanPortConfRole	OBJECT-TYPE
	SYNTAX		INTEGER(0..2)
	MAX-ACCESS	    read-write
	STATUS		current
	DESCRIPTION
		"
		 0 - Access: won't send packet with tag.
		 1 - Trunk: always send packet with tag.
		 2 - Hybrid: always send packet with tag but one."
	::= { sw0657851VlanPortConfEntry 6 }

sw0657851VlanPortConfUntagVid	OBJECT-TYPE
	SYNTAX		INTEGER(1..4094)
	MAX-ACCESS	    read-write
	STATUS		current
	DESCRIPTION
		"Won't send packet with tag in one specific vid. Only available in hybrid mode.
		 "
	::= { sw0657851VlanPortConfEntry 7 }

sw0657851VlanPortConfDoubleTag	OBJECT-TYPE
	SYNTAX		INTEGER(0..2)
	MAX-ACCESS	    read-write
	STATUS		current
	DESCRIPTION
		"This is the double tag configuration for ports.
		 0 -- Disable,
		  1 -- Service,
		  2 -- Customer
		 "
	::= { sw0657851VlanPortConfEntry 8 }

sw0657851PortBaseVlanGroup        	OBJECT IDENTIFIER ::= { sw0657851VLAN 4 }

sw0657851PortBaseVlanNumber OBJECT-TYPE
	SYNTAX      INTEGER(1..24)
	MAX-ACCESS	    read-write
	STATUS		current
	DESCRIPTION
		"Total numbers for port based vlan."
	::= { sw0657851PortBaseVlanGroup 1 }

sw0657851PortBaseVlanGroupEntryCreate OBJECT-TYPE
	SYNTAX      INTEGER(0..24)
	MAX-ACCESS	    read-write
	STATUS		current
	DESCRIPTION
		"Create a temp vlan in port-based vlan table.
         0 : none,
         1 : create a new port-based vlan."
	::= { sw0657851PortBaseVlanGroup 2 }

sw0657851PortBaseVlanGroupTable	OBJECT-TYPE
	SYNTAX		SEQUENCE OF SW0657851PortBaseVlanGroupEntry
	MAX-ACCESS	not-accessible
	STATUS		current
    DESCRIPTION
        "A list of port base vlan group entry. The numbers of entries are given by the value of sw0657851PortBaseVlanNumber."
	::= { sw0657851PortBaseVlanGroup 3 }

SW0657851PortBaseVlanGroupEntry ::=
SEQUENCE {
    sw0657851PortBaseVlanGroupIndex		      INTEGER,
    sw0657851PortBaseVlanGroupName          DisplayString,
    sw0657851PortBaseVlanGroupMembers       DisplayString,
    sw0657851PortBaseVlanGroupEntryAction   INTEGER
}

sw0657851PortBaseVlanGroupEntry	OBJECT-TYPE
	SYNTAX		SW0657851PortBaseVlanGroupEntry
	MAX-ACCESS	    not-accessible
	STATUS		current
	DESCRIPTION
		"This is the Entry(s) for Port Base VLAN Group configuration information."
	INDEX {sw0657851PortBaseVlanGroupIndex}
	::= { sw0657851PortBaseVlanGroupTable 1 }

sw0657851PortBaseVlanGroupIndex	OBJECT-TYPE
	SYNTAX		INTEGER(1..24)
	MAX-ACCESS	    not-accessible
	STATUS		current
	DESCRIPTION
		"This is the index of the Port Base VLAN Group configuration entry."
	::= { sw0657851PortBaseVlanGroupEntry 1 }

sw0657851PortBaseVlanGroupName	OBJECT-TYPE
	SYNTAX		DisplayString
	MAX-ACCESS	    read-write
	STATUS		current
	DESCRIPTION
		"The name of vlan."
	::= { sw0657851PortBaseVlanGroupEntry 2 }

sw0657851PortBaseVlanGroupMembers	OBJECT-TYPE
	SYNTAX		DisplayString
	MAX-ACCESS	    read-write
	STATUS		current
	DESCRIPTION
		"The member of vlan."
	::= { sw0657851PortBaseVlanGroupEntry 3 }

sw0657851PortBaseVlanGroupEntryAction	OBJECT-TYPE
	SYNTAX		INTEGER(1..3)
	MAX-ACCESS	    read-write
	STATUS		current
	DESCRIPTION
		"The row status of vlan.
		 1 - active
		 2 - notInService
		 3 - delete"
	::= { sw0657851PortBaseVlanGroupEntry 4 }

sw0657851MacTableInfo           	OBJECT IDENTIFIER ::= { sw0657851Produces 15 }

sw0657851MacTableConf           	OBJECT IDENTIFIER ::= { sw0657851MacTableInfo 1 }

sw0657851MacAgeTime OBJECT-TYPE
	SYNTAX      INTEGER(10..1000000)
	MAX-ACCESS	    read-write
	STATUS		current
	DESCRIPTION
		"Set the Mac Table Aging Time (10~1000000 Secs).
         0 : Disable."
	::= { sw0657851MacTableConf 1 }

sw0657851MacTableLearningConfTable	OBJECT-TYPE
	SYNTAX		SEQUENCE OF SW0657851MacTableLearningConfEntry
	MAX-ACCESS	not-accessible
	STATUS		current
    DESCRIPTION
        "A list of Mac Learning entry."
	::= { sw0657851MacTableConf 2 }

SW0657851MacTableLearningConfEntry ::=
SEQUENCE {
    sw0657851MacTableLearningConfIndex   INTEGER,
    sw0657851MacTableLearningConfstate   INTEGER
}

sw0657851MacTableLearningConfEntry	OBJECT-TYPE
	SYNTAX		SW0657851MacTableLearningConfEntry
	MAX-ACCESS	    not-accessible
	STATUS		current
	DESCRIPTION
		"This is the Entry(s) for Mac Learning table information."
	INDEX {sw0657851MacTableLearningConfIndex}
	::= { sw0657851MacTableLearningConfTable 1 }

sw0657851MacTableLearningConfIndex	OBJECT-TYPE
	SYNTAX		INTEGER(1..24)
	MAX-ACCESS	    not-accessible
	STATUS		current
	DESCRIPTION
		"This is the index of the Learning MAC Table Group configuration entry."
	::= { sw0657851MacTableLearningConfEntry 1 }

sw0657851MacTableLearningConfstate	OBJECT-TYPE
	SYNTAX		INTEGER(0|1|2)
	MAX-ACCESS	    read-write
	STATUS		current
	DESCRIPTION
		"
		 0 - Auto
		 1 - Disable
		 2 - Secure"
	::= { sw0657851MacTableLearningConfEntry 2 }

sw0657851MacTableStaticFilter           	OBJECT IDENTIFIER ::= { sw0657851MacTableInfo 2 }

sw0657851MacTableStaticFilterNumber OBJECT-TYPE
	SYNTAX      INTEGER(0..512)
	MAX-ACCESS	    read-only
	STATUS		current
	DESCRIPTION
		"Total numbers for static filter entry of Mac Table."
	::= { sw0657851MacTableStaticFilter 1 }

sw0657851MacTableStaticFilterEntryCreate OBJECT-TYPE
	SYNTAX      INTEGER(0..512)
	MAX-ACCESS	    read-write
	STATUS		current
	DESCRIPTION
		"Create a temp Filter entry in Mac Table.
         0 : none,
         1 : create a new entry"
	::= { sw0657851MacTableStaticFilter 2 }

sw0657851MacTableStaticFilterTable	OBJECT-TYPE
	SYNTAX		SEQUENCE OF SW0657851MacTableStaticFilterEntry
	MAX-ACCESS	not-accessible
	STATUS		current
    DESCRIPTION
        "A list of static filter entry. The numbers of entries are given by the value of sw0657851MacTableStaticFilterNumber."
	::= { sw0657851MacTableStaticFilter 3 }

SW0657851MacTableStaticFilterEntry ::=
SEQUENCE {
    sw0657851MacTableStaticFilterIndex         INTEGER,
    sw0657851MacTableStaticFilterMac           DisplayString,
    sw0657851MacTableStaticFilterVid           INTEGER,
    sw0657851MacTableStaticFilterAlias         DisplayString,
    sw0657851MacTableStaticFilterEntryAction   INTEGER
}

sw0657851MacTableStaticFilterEntry	OBJECT-TYPE
	SYNTAX		SW0657851MacTableStaticFilterEntry
	MAX-ACCESS	    not-accessible
	STATUS		current
	DESCRIPTION
		"This is the Entry(s) for static filter information."
	INDEX {sw0657851MacTableStaticFilterIndex}
	::= { sw0657851MacTableStaticFilterTable 1 }

sw0657851MacTableStaticFilterIndex	OBJECT-TYPE
	SYNTAX		INTEGER(1..512)
	MAX-ACCESS	    not-accessible
	STATUS		current
	DESCRIPTION
		"This is the index of the Static Filter MAC Table Group configuration entry."
	::= { sw0657851MacTableStaticFilterEntry 1 }

sw0657851MacTableStaticFilterMac	OBJECT-TYPE
	SYNTAX		DisplayString
	MAX-ACCESS	    read-write
	STATUS		current
	DESCRIPTION
		"The static filter mac in Mac Table"
	::= { sw0657851MacTableStaticFilterEntry 2 }

sw0657851MacTableStaticFilterVid	OBJECT-TYPE
	SYNTAX		INTEGER(1..4094)
	MAX-ACCESS	    read-write
	STATUS		current
	DESCRIPTION
		"The filter vid in Mac Table"
	::= { sw0657851MacTableStaticFilterEntry 3 }

sw0657851MacTableStaticFilterAlias	OBJECT-TYPE
	SYNTAX		DisplayString
	MAX-ACCESS	    read-write
	STATUS		current
	DESCRIPTION
		"The filter alias name in Mac Table"
	::= { sw0657851MacTableStaticFilterEntry 4 }

sw0657851MacTableStaticFilterEntryAction	OBJECT-TYPE
	SYNTAX		INTEGER(1..3)
	MAX-ACCESS	    read-write
	STATUS		current
	DESCRIPTION
		"The row status of filter entry.
		 1 - active
		 2 - notInService
		 3 - delete"
	::= { sw0657851MacTableStaticFilterEntry 5 }

sw0657851MacTableStaticForward           	OBJECT IDENTIFIER ::= { sw0657851MacTableInfo 3 }

sw0657851MacTableStaticForwardNumber OBJECT-TYPE
	SYNTAX      INTEGER(0..512)
	MAX-ACCESS	    read-only
	STATUS		current
	DESCRIPTION
		"Total numbers for static forward entry of Mac Table."
	::= { sw0657851MacTableStaticForward 1 }

sw0657851MacTableStaticForwardEntryCreate OBJECT-TYPE
	SYNTAX      INTEGER(0..512)
	MAX-ACCESS	    read-write
	STATUS		current
	DESCRIPTION
		"Create a temp forward entry in Mac Table.
         0 : none,
         1 : create a new entry"
	::= { sw0657851MacTableStaticForward 2 }

sw0657851MacTableStaticForwardTable	OBJECT-TYPE
	SYNTAX		SEQUENCE OF SW0657851MacTableStaticForwardEntry
	MAX-ACCESS	not-accessible
	STATUS		current
    DESCRIPTION
        "A list of static forward entry. The numbers of entries are given by the value of sw0657851MacTableStaticForwardNumber."
	::= { sw0657851MacTableStaticForward 3 }

SW0657851MacTableStaticForwardEntry ::=
SEQUENCE {
    sw0657851MacTableStaticForwardIndex         INTEGER,
    sw0657851MacTableStaticForwardMac           DisplayString,
    sw0657851MacTableStaticForwardPort          INTEGER,
    sw0657851MacTableStaticForwardVid           INTEGER,
    sw0657851MacTableStaticForwardAlias         DisplayString,
    sw0657851MacTableStaticForwardEntryAction   INTEGER
}

sw0657851MacTableStaticForwardEntry	OBJECT-TYPE
	SYNTAX		SW0657851MacTableStaticForwardEntry
	MAX-ACCESS	    not-accessible
	STATUS		current
	DESCRIPTION
		" "
	INDEX {sw0657851MacTableStaticForwardIndex}
	::= { sw0657851MacTableStaticForwardTable 1 }

sw0657851MacTableStaticForwardIndex	OBJECT-TYPE
	SYNTAX		INTEGER(1..512)
	MAX-ACCESS	    not-accessible
	STATUS		current
	DESCRIPTION
		"This is the index of the Static Forward MAC Table Group configuration entry."
	::= { sw0657851MacTableStaticForwardEntry 1 }

sw0657851MacTableStaticForwardMac	OBJECT-TYPE
	SYNTAX		DisplayString
	MAX-ACCESS	    read-write
	STATUS		current
	DESCRIPTION
		"The static forwarding Mac in Mac Table"
	::= { sw0657851MacTableStaticForwardEntry 2 }

sw0657851MacTableStaticForwardPort	OBJECT-TYPE
	SYNTAX		INTEGER(1..24)
	MAX-ACCESS	    read-write
	STATUS		current
	DESCRIPTION
		"To specify a destination port for a mac address in mac table."
	::= { sw0657851MacTableStaticForwardEntry 3 }

sw0657851MacTableStaticForwardVid	OBJECT-TYPE
	SYNTAX		INTEGER(1..4094)
	MAX-ACCESS	    read-write
	STATUS		current
	DESCRIPTION
		"To specify a VLAN ID for a mac address in mac table."
	::= { sw0657851MacTableStaticForwardEntry 4 }

sw0657851MacTableStaticForwardAlias	OBJECT-TYPE
	SYNTAX		DisplayString
	MAX-ACCESS	    read-write
	STATUS		current
	DESCRIPTION
		"To specify an alias for a mac address in mac table."
	::= { sw0657851MacTableStaticForwardEntry 5 }

sw0657851MacTableStaticForwardEntryAction	OBJECT-TYPE
	SYNTAX		INTEGER(1..3)
	MAX-ACCESS	    read-write
	STATUS		current
	DESCRIPTION
		"The row status of filter entry.
		 1 - active
		 2 - notInService
		 3 - delete"
	::= { sw0657851MacTableStaticForwardEntry 6 }

sw0657851MacAlias           	OBJECT IDENTIFIER ::= { sw0657851MacTableInfo 4 }

sw0657851MacAliasNumber OBJECT-TYPE
	SYNTAX      INTEGER(0..1024)
	MAX-ACCESS	    read-only
	STATUS		current
	DESCRIPTION
		"Mac Alias Total Nnumber(0~1024)."
	::= { sw0657851MacAlias 1 }

sw0657851MacAliasEntryCreate OBJECT-TYPE
	SYNTAX      INTEGER(0..1024)
	MAX-ACCESS	    read-only
	STATUS		current
	DESCRIPTION
		"Create a temp Mac alias entry in Mac Table.
         0 : none,
         1 : create a new entry"
	::= { sw0657851MacAlias 2 }

sw0657851MacAliasTable	OBJECT-TYPE
	SYNTAX		SEQUENCE OF SW0657851MacAliasEntry
	MAX-ACCESS	not-accessible
	STATUS		current
    DESCRIPTION
        "A list of Mac Alias entry. The numbers of entries are given by the value of sw0657851MacAliasNumber."
	::= { sw0657851MacAlias 3 }

SW0657851MacAliasEntry ::=
SEQUENCE {
    sw0657851MacAliasIndex         INTEGER,
    sw0657851AliasMac              DisplayString,
    sw0657851AliasName             DisplayString,
    sw0657851MacAliasEntryAction   INTEGER
}

sw0657851MacAliasEntry	OBJECT-TYPE
	SYNTAX		SW0657851MacAliasEntry
	MAX-ACCESS	    not-accessible
	STATUS		current
	DESCRIPTION
		"Entry(s) for Mac Alias."
	INDEX {sw0657851MacAliasIndex}
	::= { sw0657851MacAliasTable 1 }

sw0657851MacAliasIndex	OBJECT-TYPE
	SYNTAX		INTEGER(1..1024)
	MAX-ACCESS	    not-accessible
	STATUS		current
	DESCRIPTION
		"The index of the static mac alias entry."
	::= { sw0657851MacAliasEntry 1 }

sw0657851AliasMac	OBJECT-TYPE
	SYNTAX		DisplayString
	MAX-ACCESS	    read-write
	STATUS		current
	DESCRIPTION
		"The Mac of the static mac alias entry."
	::= { sw0657851MacAliasEntry 2 }

sw0657851AliasName	OBJECT-TYPE
	SYNTAX		DisplayString
	MAX-ACCESS	    read-write
	STATUS		current
	DESCRIPTION
		"The alias name of the static mac alias entry."
	::= { sw0657851MacAliasEntry 3 }

sw0657851MacAliasEntryAction	OBJECT-TYPE
	SYNTAX		INTEGER(1..3)
	MAX-ACCESS	    read-write
	STATUS		current
	DESCRIPTION
		"The row status of mac alias entry.
		 1 - active
		 2 - notInService
		 3 - delete"
	::= { sw0657851MacAliasEntry 4 }


sw0657851GVRPInfo           	OBJECT IDENTIFIER ::= { sw0657851Produces 16 }

sw0657851GvrpConf           	OBJECT IDENTIFIER ::= { sw0657851GVRPInfo 1 }

sw0657851GvrpConfState OBJECT-TYPE
	SYNTAX      INTEGER(0|1)
	MAX-ACCESS	    read-write
	STATUS		current
	DESCRIPTION
		"The GVRP state
		 0 - Disable
		 1 - Enable
    "
	::= { sw0657851GvrpConf 1 }

sw0657851GvrpConfTable	OBJECT-TYPE
	SYNTAX		SEQUENCE OF SW0657851GvrpConfEntry
	MAX-ACCESS	not-accessible
	STATUS		current
    DESCRIPTION
        "A list of GVRP entry."
	::= { sw0657851GvrpConf 2 }

SW0657851GvrpConfEntry ::=
SEQUENCE {
    sw0657851GvrpConfIndex             INTEGER,
    sw0657851GvrpConfJoinTime          INTEGER,
    sw0657851GvrpConfLeaveTime         INTEGER,
    sw0657851GvrpConfLeaveAllTime      INTEGER,
    sw0657851GvrpConfDefaultAppMode    INTEGER,
    sw0657851GvrpConfDefaultRegMode    INTEGER,
    sw0657851GvrpConfRestrictedMode    INTEGER
}

sw0657851GvrpConfEntry	OBJECT-TYPE
	SYNTAX		SW0657851GvrpConfEntry
	MAX-ACCESS	    not-accessible
	STATUS		current
	DESCRIPTION
		"This is the Entry(s) for gvrp information."
	INDEX {sw0657851GvrpConfIndex}
	::= { sw0657851GvrpConfTable 1 }

sw0657851GvrpConfIndex	OBJECT-TYPE
	SYNTAX		INTEGER(1..24)
	MAX-ACCESS	    not-accessible
	STATUS		current
	DESCRIPTION
		"This is the index of the gvrp entry."
	::= { sw0657851GvrpConfEntry 1 }

sw0657851GvrpConfJoinTime	OBJECT-TYPE
	SYNTAX		INTEGER(20..100)
	MAX-ACCESS	    read-write
	STATUS		current
	DESCRIPTION
		"This is the join-time of the gvrp entry."
	::= { sw0657851GvrpConfEntry 2 }

sw0657851GvrpConfLeaveTime	OBJECT-TYPE
	SYNTAX		INTEGER(60..300)
	MAX-ACCESS	    read-write
	STATUS		current
	DESCRIPTION
		"This is the leave-time of the gvrp entry.
		default:60 centisecond"
	::= { sw0657851GvrpConfEntry 3 }

sw0657851GvrpConfLeaveAllTime	OBJECT-TYPE
	SYNTAX		INTEGER(1000..5000)
	MAX-ACCESS	    read-write
	STATUS		current
	DESCRIPTION
		" default: 1000 unit time"
	::= { sw0657851GvrpConfEntry 4 }

sw0657851GvrpConfDefaultAppMode	OBJECT-TYPE
	SYNTAX		INTEGER(0|1)
	MAX-ACCESS	    read-write
	STATUS		current
	DESCRIPTION
		"    [default: Normal]
		 0 - Normal
		 1 - Non-Participant"
	::= { sw0657851GvrpConfEntry 5 }

sw0657851GvrpConfDefaultRegMode	OBJECT-TYPE
	SYNTAX		INTEGER(0|1|2)
	MAX-ACCESS	    read-write
	STATUS		current
	DESCRIPTION
		"    [default: Normal]
		 0 - Normal
		 1 - Fixed
		 2 - Forbidden"
	::= { sw0657851GvrpConfEntry 6 }

sw0657851GvrpConfRestrictedMode	OBJECT-TYPE
	SYNTAX		INTEGER(0|1)
	MAX-ACCESS	    read-write
	STATUS		current
	DESCRIPTION
		"    [default: Disable]
		 0 - Disable
		 1 - Enable"
	::= { sw0657851GvrpConfEntry 7 }

sw0657851GvrpCounter           	OBJECT IDENTIFIER ::= { sw0657851GVRPInfo 2 }

sw0657851GvrpCounterTable	OBJECT-TYPE
	SYNTAX		SEQUENCE OF SW0657851GvrpCounterEntry
	MAX-ACCESS	not-accessible
	STATUS		current
    DESCRIPTION
        "This is a list of SW0657851GvrpCounterEntry."
	::= { sw0657851GvrpCounter 1 }

SW0657851GvrpCounterEntry ::=
SEQUENCE {
    sw0657851GvrpCounterIndex              INTEGER,
    sw0657851GvrpCounterRxTotalGvrpPkts    Counter32,
    sw0657851GvrpCounterRxInvalidGvrpPkts  Counter32,
    sw0657851GvrpCounterRxLeaveAllMsg      Counter32,
    sw0657851GvrpCounterRxJoinEmptyMsg     Counter32,
    sw0657851GvrpCounterRxJoinInMsg        Counter32,
    sw0657851GvrpCounterRxLeaveEmptyMsg    Counter32,
    sw0657851GvrpCounterRxEmptyMsg         Counter32,
    sw0657851GvrpCounterTxTotalGvrpPkts    Counter32,
    sw0657851GvrpCounterTxLeaveAllMsg      Counter32,
    sw0657851GvrpCounterTxJoinEmptyMsg     Counter32,
    sw0657851GvrpCounterTxJoinInMsg        Counter32,
    sw0657851GvrpCounterTxLeaveEmptyMsg    Counter32,
    sw0657851GvrpCounterTxEmptyMsg         Counter32
}

sw0657851GvrpCounterEntry	OBJECT-TYPE
	SYNTAX		SW0657851GvrpCounterEntry
	MAX-ACCESS	    not-accessible
	STATUS		current
	DESCRIPTION
		"This is the Entry(s) for gvrp counter information."
	INDEX {sw0657851GvrpCounterIndex}
	::= { sw0657851GvrpCounterTable 1 }

sw0657851GvrpCounterIndex	OBJECT-TYPE
	SYNTAX		INTEGER(1..24)
	MAX-ACCESS	    not-accessible
	STATUS		current
	DESCRIPTION
		"This is the index of the gvrp counter entry."
	::= { sw0657851GvrpCounterEntry 1 }

sw0657851GvrpCounterRxTotalGvrpPkts	OBJECT-TYPE
	SYNTAX		Counter32
	MAX-ACCESS	    read-only
	STATUS		current
	DESCRIPTION
		"Get the amount of all received gvrp packets of the gvrp counter entry."
	::= { sw0657851GvrpCounterEntry 2 }

sw0657851GvrpCounterRxInvalidGvrpPkts	OBJECT-TYPE
	SYNTAX		Counter32
	MAX-ACCESS	    read-only
	STATUS		current
	DESCRIPTION
		"Get the amount of received invalid gvrp packets of the gvrp counter entry."
	::= { sw0657851GvrpCounterEntry 3 }

sw0657851GvrpCounterRxLeaveAllMsg	OBJECT-TYPE
	SYNTAX		Counter32
	MAX-ACCESS	    read-only
	STATUS		current
	DESCRIPTION
		"Get the amount of received leave-all-message of the gvrp counter entry."
	::= { sw0657851GvrpCounterEntry 4 }

sw0657851GvrpCounterRxJoinEmptyMsg	OBJECT-TYPE
	SYNTAX		Counter32
	MAX-ACCESS	    read-only
	STATUS		current
	DESCRIPTION
		"Get the amount of received join-empty-message of the gvrp counter entry."
	::= { sw0657851GvrpCounterEntry 5 }

sw0657851GvrpCounterRxJoinInMsg	OBJECT-TYPE
	SYNTAX		Counter32
	MAX-ACCESS	    read-only
	STATUS		current
	DESCRIPTION
		"Get the amount of received join-in-message of the gvrp counter entry."
	::= { sw0657851GvrpCounterEntry 6 }

sw0657851GvrpCounterRxLeaveEmptyMsg	OBJECT-TYPE
	SYNTAX		Counter32
	MAX-ACCESS	    read-only
	STATUS		current
	DESCRIPTION
		"Get the amount of received leave-empty-message of the gvrp counter entry."
	::= { sw0657851GvrpCounterEntry 7 }

sw0657851GvrpCounterRxEmptyMsg	OBJECT-TYPE
	SYNTAX		Counter32
	MAX-ACCESS	    read-only
	STATUS		current
	DESCRIPTION
		"Get the amount of received empty-message of the gvrp counter entry."
	::= { sw0657851GvrpCounterEntry 8 }

sw0657851GvrpCounterTxTotalGvrpPkts	OBJECT-TYPE
	SYNTAX		Counter32
	MAX-ACCESS	    read-only
	STATUS		current
	DESCRIPTION
		"Get the amount of all transmitted gvrp packets of the gvrp counter entry."
	::= { sw0657851GvrpCounterEntry 9 }

sw0657851GvrpCounterTxLeaveAllMsg	OBJECT-TYPE
	SYNTAX		Counter32
	MAX-ACCESS	    read-only
	STATUS		current
	DESCRIPTION
		"Get the amount of transmitted leave-all-message of the gvrp counter entry."
	::= { sw0657851GvrpCounterEntry 10 }

sw0657851GvrpCounterTxJoinEmptyMsg	OBJECT-TYPE
	SYNTAX		Counter32
	MAX-ACCESS	    read-only
	STATUS		current
	DESCRIPTION
		"Get the amount of transmitted join-empty-message of the gvrp counter entry."
	::= { sw0657851GvrpCounterEntry 11 }

sw0657851GvrpCounterTxJoinInMsg	OBJECT-TYPE
	SYNTAX		Counter32
	MAX-ACCESS	    read-only
	STATUS		current
	DESCRIPTION
		"Get the amount of transmitted join-in-message of the gvrp counter entry."
	::= { sw0657851GvrpCounterEntry 12 }

sw0657851GvrpCounterTxLeaveEmptyMsg	OBJECT-TYPE
	SYNTAX		Counter32
	MAX-ACCESS	    read-only
	STATUS		current
	DESCRIPTION
		"Get the amount of transmitted leave-empty-message of the gvrp counter entry."
	::= { sw0657851GvrpCounterEntry 13 }

sw0657851GvrpCounterTxEmptyMsg	OBJECT-TYPE
	SYNTAX		Counter32
	MAX-ACCESS	    read-only
	STATUS		current
	DESCRIPTION
		"Get the amount of transmitted empty-message of the gvrp counter entry."
	::= { sw0657851GvrpCounterEntry 14 }

sw0657851GvrpGroup           	OBJECT IDENTIFIER ::= { sw0657851GVRPInfo 3 }

sw0657851GvrpGroupNumber	OBJECT-TYPE
	SYNTAX		INTEGER(0..4094)
	MAX-ACCESS	    read-only
	STATUS		current
	DESCRIPTION
		"Get the number of the gvrp group entry."
	::= { sw0657851GvrpGroup 1 }

sw0657851GvrpGroupTable	OBJECT-TYPE
	SYNTAX		SEQUENCE OF SW0657851GvrpGroupEntry
	MAX-ACCESS	not-accessible
	STATUS		current
    DESCRIPTION
        "This is a list of SW0657851GvrpGroupEntry."
	::= { sw0657851GvrpGroup 2 }

SW0657851GvrpGroupEntry ::=
SEQUENCE {
    sw0657851GvrpGroupId            INTEGER,
    sw0657851GvrpGroupVid           INTEGER,
    sw0657851GvrpGroupMemberPort    DisplayString
}

sw0657851GvrpGroupEntry	OBJECT-TYPE
	SYNTAX		SW0657851GvrpGroupEntry
	MAX-ACCESS	    not-accessible
	STATUS		current
	DESCRIPTION
		"This is the Entry(s) for gvrp group information."
	INDEX {sw0657851GvrpGroupId}
	::= { sw0657851GvrpGroupTable 1 }

sw0657851GvrpGroupId	OBJECT-TYPE
	SYNTAX		INTEGER(1..4094)
	MAX-ACCESS	    read-only
	STATUS		current
	DESCRIPTION
		"This is the index of the gvrp group entry."
	::= { sw0657851GvrpGroupEntry 1 }

sw0657851GvrpGroupVid	OBJECT-TYPE
	SYNTAX		INTEGER(1..4094)
	MAX-ACCESS	    read-only
	STATUS		current
	DESCRIPTION
		"This is the vlan id of the gvrp grout entry."
	::= { sw0657851GvrpGroupEntry 2 }

sw0657851GvrpGroupMemberPort	OBJECT-TYPE
	SYNTAX		DisplayString
	MAX-ACCESS	    read-only
	STATUS		current
	DESCRIPTION
		"The member ports of the gvrp grout entry."
	::= { sw0657851GvrpGroupEntry 3 }

sw0657851GvrpGroupAdministrativeCtrlTable	OBJECT-TYPE
	SYNTAX		SEQUENCE OF SW0657851GvrpGroupAdministrativeCtrlEntry
	MAX-ACCESS	not-accessible
	STATUS		current
    DESCRIPTION
        "This is a list of SW0657851GvrpGroupAdministrativeCtrlEntry."
	::= { sw0657851GvrpGroup 3 }

SW0657851GvrpGroupAdministrativeCtrlEntry ::=
SEQUENCE {
    sw0657851GvrpGroupAdministrativeCtrlVid    INTEGER,
    sw0657851GvrpGroupAdministrativeCtrlPort   INTEGER,
    sw0657851GvrpGroupAdministrativeCtrlApp    INTEGER,
    sw0657851GvrpGroupAdministrativeCtrlReg    INTEGER
}

sw0657851GvrpGroupAdministrativeCtrlEntry	OBJECT-TYPE
	SYNTAX		SW0657851GvrpGroupAdministrativeCtrlEntry
	MAX-ACCESS	    not-accessible
	STATUS		current
	DESCRIPTION
		"This is the Entry(s) for gvrp group administrative information."
	INDEX {sw0657851GvrpGroupAdministrativeCtrlVid, sw0657851GvrpGroupAdministrativeCtrlPort}
	::= { sw0657851GvrpGroupAdministrativeCtrlTable 1 }

sw0657851GvrpGroupAdministrativeCtrlVid	OBJECT-TYPE
	SYNTAX		INTEGER(1..4094)
	MAX-ACCESS	    read-only
	STATUS		current
	DESCRIPTION
		"This is the vlan id of the gvrp-group-admin entry."
	::= { sw0657851GvrpGroupAdministrativeCtrlEntry 1 }

sw0657851GvrpGroupAdministrativeCtrlPort	OBJECT-TYPE
	SYNTAX		INTEGER(1..24)
	MAX-ACCESS	    read-only
	STATUS		current
	DESCRIPTION
		"This is the port number of the gvrp-group-admin entry."
	::= { sw0657851GvrpGroupAdministrativeCtrlEntry 2 }

sw0657851GvrpGroupAdministrativeCtrlApp	OBJECT-TYPE
	SYNTAX		INTEGER(0|1)
	MAX-ACCESS	    read-write
	STATUS		current
	DESCRIPTION
		"Set gvrp applicant.
		 0 - Normal
		 1 - Non-Participant"
	::= { sw0657851GvrpGroupAdministrativeCtrlEntry 3 }

sw0657851GvrpGroupAdministrativeCtrlReg	OBJECT-TYPE
	SYNTAX		INTEGER(0..2)
	MAX-ACCESS	    read-write
	STATUS		current
	DESCRIPTION
		"Set gvrp registrar.
		 0 - Normal
		 1 - Fixed
		 2 - Forbidden"
	::= { sw0657851GvrpGroupAdministrativeCtrlEntry 4 }

sw0657851QosInfo           	OBJECT IDENTIFIER ::= { sw0657851Produces 17 }

sw0657851QosPortConf           	OBJECT IDENTIFIER ::= { sw0657851QosInfo 1 }

sw0657851QosNumOfClasses OBJECT-TYPE
	SYNTAX      INTEGER(1|2|4)
	MAX-ACCESS	    read-write
	STATUS		current
	DESCRIPTION
		"Effective class number, it can be set 1, 2, or 4.
		1 means only one class available, all packets will be treat the same.
		2 means two classes available, packets will be divided into high and low queue.
		4 means for classes available, packets will be divided into low/normal/medium/high queue"
	::= { sw0657851QosPortConf 1 }

sw0657851QosPortConfTable	OBJECT-TYPE
	SYNTAX		SEQUENCE OF SW0657851QosPortConfEntry
	MAX-ACCESS	not-accessible
	STATUS		current
    DESCRIPTION
        "QoS parameter for ports."
	::= { sw0657851QosPortConf 2 }

SW0657851QosPortConfEntry ::=
SEQUENCE {
    sw0657851QosPortConfIndex                INTEGER,
    sw0657851QosPortConfDefaultClasses       INTEGER,
    sw0657851QosPortConfQCL                  INTEGER,
    sw0657851QosPortConfUserPriority         INTEGER,
    sw0657851QosPortConfQueuingMode          INTEGER,
    sw0657851QosPortConfQueueWeightedLow     INTEGER,
    sw0657851QosPortConfQueueWeightedNormal  INTEGER,
    sw0657851QosPortConfQueueWeightedMedium  INTEGER,
    sw0657851QosPortConfQueueWeightedHigh    INTEGER
}

sw0657851QosPortConfEntry	OBJECT-TYPE
	SYNTAX		SW0657851QosPortConfEntry
	MAX-ACCESS	    not-accessible
	STATUS		current
	DESCRIPTION
		"QoS parameter for ports."
	INDEX {sw0657851QosPortConfIndex}
	::= { sw0657851QosPortConfTable 1 }

sw0657851QosPortConfIndex	OBJECT-TYPE
	SYNTAX		INTEGER(1..24)
	MAX-ACCESS	    not-accessible
	STATUS		current
	DESCRIPTION
		"This is the port number for QoS configuration."
	::= { sw0657851QosPortConfEntry 1 }

sw0657851QosPortConfDefaultClasses	OBJECT-TYPE
	SYNTAX		INTEGER(0..3)
	MAX-ACCESS	    read-write
	STATUS		current
	DESCRIPTION
		"This is the default class for packets mismatch the specified QCL setting.
		 0 - Low
		 1 - Normal
		 2 - Medium
		 3 - High"
	::= { sw0657851QosPortConfEntry 2 }

sw0657851QosPortConfQCL	OBJECT-TYPE
	SYNTAX		INTEGER(1..24)
	MAX-ACCESS	    read-write
	STATUS		current
	DESCRIPTION
		"This is where to specify the QoS Control List the port should apply."
	::= { sw0657851QosPortConfEntry 3 }

sw0657851QosPortConfUserPriority	OBJECT-TYPE
	SYNTAX		INTEGER(0..7)
	MAX-ACCESS	    read-write
	STATUS		current
	DESCRIPTION
		"This is the default ingress VLAN tag priority"
	::= { sw0657851QosPortConfEntry 4 }

sw0657851QosPortConfQueuingMode	OBJECT-TYPE
	SYNTAX		INTEGER(0|1)
	MAX-ACCESS	    read-write
	STATUS		current
	DESCRIPTION
		"
		 0 - Strict Priority
		 1 - Weighted Fair"
	::= { sw0657851QosPortConfEntry 5 }

sw0657851QosPortConfQueueWeightedLow	OBJECT-TYPE
	SYNTAX		INTEGER(1|2|4|8)
	MAX-ACCESS	    read-write
	STATUS		current
	DESCRIPTION
		"To specify how many quotas the low queue can be distributed.
		 Only available when the queueing mode is Weighted Fair."
	::= { sw0657851QosPortConfEntry 6 }

sw0657851QosPortConfQueueWeightedNormal	OBJECT-TYPE
	SYNTAX		INTEGER(1|2|4|8)
	MAX-ACCESS	    read-write
	STATUS		current
	DESCRIPTION
		"To specify how many quotas the normal queue can be distributed.
		 Only available when the queueing mode is Weighted Fair."
	::= { sw0657851QosPortConfEntry 7 }

sw0657851QosPortConfQueueWeightedMedium	OBJECT-TYPE
	SYNTAX		INTEGER(1|2|4|8)
	MAX-ACCESS	    read-write
	STATUS		current
	DESCRIPTION
		"To specify how many quotas the medium queue can be distributed.
		 Only available when the queueing mode is Weighted Fair."
	::= { sw0657851QosPortConfEntry 8 }

sw0657851QosPortConfQueueWeightedHigh	OBJECT-TYPE
	SYNTAX		INTEGER(1|2|4|8)
	MAX-ACCESS	    read-write
	STATUS		current
	DESCRIPTION
		"To specify how many quotas the high queue can be distributed.
		 Only available when the queueing mode is Weighted Fair."
	::= { sw0657851QosPortConfEntry 9 }

sw0657851QosRateLimiters          	OBJECT IDENTIFIER ::= { sw0657851QosInfo 3 }

sw0657851QosRateLimitersTable	OBJECT-TYPE
	SYNTAX		SEQUENCE OF SW0657851QosRateLimitersEntry
	MAX-ACCESS	not-accessible
	STATUS		current
    DESCRIPTION
        "This is the port bandwidth configuration."
	::= { sw0657851QosRateLimiters 1 }

SW0657851QosRateLimitersEntry ::=
SEQUENCE {
    sw0657851QosRateLimitersIndex         INTEGER,
    sw0657851QosRateLimitersPolicer       INTEGER,
    sw0657851QosRateLimitersPolicerRate   INTEGER,
    sw0657851QosRateLimitersShaper        INTEGER,
    sw0657851QosRateLimitersShaperRate    INTEGER
}

sw0657851QosRateLimitersEntry	OBJECT-TYPE
	SYNTAX		SW0657851QosRateLimitersEntry
	MAX-ACCESS	    not-accessible
	STATUS		current
	DESCRIPTION
		"This is the port bandwidth configuration."
	INDEX {sw0657851QosRateLimitersIndex}
	::= { sw0657851QosRateLimitersTable 1 }

sw0657851QosRateLimitersIndex	OBJECT-TYPE
	SYNTAX		INTEGER(1..24)
	MAX-ACCESS	    not-accessible
	STATUS		current
	DESCRIPTION
		"This is the port number for rate limit configuration"
	::= { sw0657851QosRateLimitersEntry 1 }

sw0657851QosRateLimitersPolicer	OBJECT-TYPE
	SYNTAX		INTEGER(0|1)
	MAX-ACCESS	    read-write
	STATUS		current
	DESCRIPTION
		"This is the ingress bandwidth function for specific port.
		 0 - Disable
		 1 - Enable"
	::= { sw0657851QosRateLimitersEntry 2 }

sw0657851QosRateLimitersPolicerRate	OBJECT-TYPE
	SYNTAX		INTEGER(1..1000000)
	MAX-ACCESS	    read-write
	STATUS		current
	DESCRIPTION
		"To set the ingress bandwidth for specific port.
		 Available value is from 500k to 1000000k"
	::= { sw0657851QosRateLimitersEntry 3 }


sw0657851QosRateLimitersShaper	OBJECT-TYPE
	SYNTAX		INTEGER(0|1)
	MAX-ACCESS	    read-write
	STATUS		current
	DESCRIPTION
		"This is the egress bandwidth function for specific port.
		 0 - Disable
		 1 - Enable"
	::= { sw0657851QosRateLimitersEntry 4 }

sw0657851QosRateLimitersShaperRate	OBJECT-TYPE
	SYNTAX		INTEGER(1..1000000)
	MAX-ACCESS	    read-write
	STATUS		current
	DESCRIPTION
		"To set the ingress bandwidth for specific port.
		 Available value is from 500k to 1000000k"
	::= { sw0657851QosRateLimitersEntry 5 }


sw0657851QosStormCtrl          	OBJECT IDENTIFIER ::= { sw0657851QosInfo 4 }

sw0657851QosStromCtrlFloodedUnicastStatus OBJECT-TYPE
	SYNTAX      INTEGER(0|1)
	MAX-ACCESS	    read-write
	STATUS		current
	DESCRIPTION
		"This is the flooded unicast suppression function for this device.
		 0 - Disable
		 1 - Enable"
	::= { sw0657851QosStormCtrl 1 }

sw0657851QosStromCtrlFloodedUnicastRate OBJECT-TYPE
	SYNTAX      DisplayString
	MAX-ACCESS	    read-write
	STATUS		current
	DESCRIPTION
		"To set the flooded unicast suppression for this device.
		 1 | 2 | 4 | 8 | 16 | 32 | 64 | 128 | 256 | 512 | 1k | 2k | 4k | 8k | 16k | 32k |64k | 128k | 256k | 512k | 1024k(Rate:pps)
    "
	::= { sw0657851QosStormCtrl 2 }

sw0657851QosStromCtrlMulticastStatus OBJECT-TYPE
	SYNTAX      INTEGER(0|1)
	MAX-ACCESS	    read-write
	STATUS		current
	DESCRIPTION
		"This is the multicast suppression function for this device.
		 0 - Disable
		 1 - Enable"
	::= { sw0657851QosStormCtrl 3 }

sw0657851QosStromCtrlMulticastRate OBJECT-TYPE
	SYNTAX      DisplayString
	MAX-ACCESS	    read-write
	STATUS		current
	DESCRIPTION
		"To set the multicast suppression for this device.
		 1 | 2 | 4 | 8 | 16 | 32 | 64 | 128 | 256 | 512 | 1k | 2k | 4k | 8k | 16k | 32k |64k | 128k | 256k | 512k | 1024k(Rate:pps)    "
	::= { sw0657851QosStormCtrl 4 }

sw0657851QosStromCtrlBroadcastStatus OBJECT-TYPE
	SYNTAX      INTEGER(0|1)
	MAX-ACCESS	    read-write
	STATUS		current
	DESCRIPTION
		"This is the broadcast suppression function for this device.
		 0 - Disable
		 1 - Enable"
	::= { sw0657851QosStormCtrl 5 }

sw0657851QosStromCtrlBroadcastRate OBJECT-TYPE
	SYNTAX      DisplayString
	MAX-ACCESS	    read-write
	STATUS		current
	DESCRIPTION
		"To set the broadcast suppression for this device.
		 1 | 2 | 4 | 8 | 16 | 32 | 64 | 128 | 256 | 512 | 1k | 2k | 4k | 8k | 16k | 32k |64k | 128k | 256k | 512k | 1024k(Rate:pps)    "
	::= { sw0657851QosStormCtrl 6 }

sw0657851AclInfo           	OBJECT IDENTIFIER ::= { sw0657851Produces 18 }

sw0657851AclPortsConfTable	OBJECT-TYPE
	SYNTAX		SEQUENCE OF SW0657851AclPortsConfEntry
	MAX-ACCESS	not-accessible
	STATUS		current
    DESCRIPTION
        "This is a list of port configuration entry. "
	::= { sw0657851AclInfo 1 }

SW0657851AclPortsConfEntry ::=
SEQUENCE {
    sw0657851AclPortsConfIndex           INTEGER,
    sw0657851AclPortsConfPolicyId        INTEGER,
    sw0657851AclPortsConfAction          INTEGER,
    sw0657851AclPortsConfRateLimiterId   INTEGER,
    sw0657851AclPortsConfPortCopy        INTEGER,
    sw0657851AclPortsConfCounter         Counter32
}

sw0657851AclPortsConfEntry	OBJECT-TYPE
	SYNTAX		SW0657851AclPortsConfEntry
	MAX-ACCESS	    not-accessible
	STATUS		current
	DESCRIPTION
		"This is the Entry(s) for ACL port information."
	INDEX {sw0657851AclPortsConfIndex}
	::= { sw0657851AclPortsConfTable 1 }

sw0657851AclPortsConfIndex	OBJECT-TYPE
	SYNTAX		INTEGER(1..24)
	MAX-ACCESS	    not-accessible
	STATUS		current
	DESCRIPTION
		"This is the port number of the ACL port entry."
	::= { sw0657851AclPortsConfEntry 1 }

sw0657851AclPortsConfPolicyId	OBJECT-TYPE
	SYNTAX		INTEGER(1..8)
	MAX-ACCESS	    read-write
	STATUS		current
	DESCRIPTION
		"This is the policy id of the ACL port entry."
	::= { sw0657851AclPortsConfEntry 2 }

sw0657851AclPortsConfAction	OBJECT-TYPE
	SYNTAX		INTEGER(0|1)
	MAX-ACCESS	    read-write
	STATUS		current
	DESCRIPTION
		"Set the action of the ACL port entry.
		 0 - Deny
		 1 - Permit"
	::= { sw0657851AclPortsConfEntry 3 }

sw0657851AclPortsConfRateLimiterId	OBJECT-TYPE
	SYNTAX		INTEGER(0..24)
	MAX-ACCESS	    read-write
	STATUS		current
	DESCRIPTION
		" Set the rate limiter id of the ACL port entry.
		 0 - Disable"
	::= { sw0657851AclPortsConfEntry 4 }

sw0657851AclPortsConfPortCopy	OBJECT-TYPE
	SYNTAX		INTEGER(0..24)
	MAX-ACCESS	    read-write
	STATUS		current
	DESCRIPTION
		"Set the mirror port of the ACL port entry.
		 0 - Disable"
	::= { sw0657851AclPortsConfEntry 5 }

sw0657851AclPortsConfCounter	OBJECT-TYPE
	SYNTAX		Counter32
	MAX-ACCESS	    read-only
	STATUS		current
	DESCRIPTION
		"This is the port counter of the ACL port entry.
		 0 - Disable"
	::= { sw0657851AclPortsConfEntry 6 }

sw0657851AclRateLimiter          	OBJECT IDENTIFIER ::= { sw0657851AclInfo 2 }

sw0657851AclRateLimiterTable	OBJECT-TYPE
	SYNTAX		SEQUENCE OF SW0657851AclRateLimiterEntry
	MAX-ACCESS	not-accessible
	STATUS		current
    DESCRIPTION
        "This is a list of SW0657851RateLimiterEntry."
	::= { sw0657851AclRateLimiter 1 }

SW0657851AclRateLimiterEntry ::=
SEQUENCE {
    sw0657851AclRateLimiterIndex        INTEGER,
    sw0657851AclRateLimiterRate         DisplayString
}

sw0657851AclRateLimiterEntry	OBJECT-TYPE
	SYNTAX		SW0657851AclRateLimiterEntry
	MAX-ACCESS	    not-accessible
	STATUS		current
	DESCRIPTION
		"This is the Entry(s) for rate limiter information."
	INDEX {sw0657851AclRateLimiterIndex}
	::= { sw0657851AclRateLimiterTable 1 }

sw0657851AclRateLimiterIndex	OBJECT-TYPE
	SYNTAX		INTEGER(1..24)
	MAX-ACCESS	    not-accessible
	STATUS		current
	DESCRIPTION
		"This is the index of the rate limiter entry."
	::= { sw0657851AclRateLimiterEntry 1 }

sw0657851AclRateLimiterRate	OBJECT-TYPE
	SYNTAX		DisplayString
	MAX-ACCESS	    read-write
	STATUS		current
	DESCRIPTION
		"
		(pps) 1 | 2 | 4 | 8 | 16 | 32 | 64 | 128 | 256 | 512 | 1k | 2k | 4k | 8k | 16k | 32k |64k | 128k | 256k | 512k | 1024k"
	::= { sw0657851AclRateLimiterEntry 2 }

sw0657851IpMacBind           	OBJECT IDENTIFIER ::= { sw0657851Produces 19 }

sw0657851IpMacBindConf          	OBJECT IDENTIFIER ::= { sw0657851IpMacBind 1 }

sw0657851IpMacBindstate	OBJECT-TYPE
	SYNTAX		INTEGER(0|1)
	MAX-ACCESS	    read-write
	STATUS		current
	DESCRIPTION
		" Set ip mac binding state.
		 0 - Disable
		 1 - Enable"
	::= { sw0657851IpMacBindConf 1 }

sw0657851IpMacBindTrustPort	OBJECT-TYPE
	SYNTAX		DisplayString
	MAX-ACCESS	    read-write
	STATUS		current
	DESCRIPTION
		"Set trustport,
		 Port range : 1,5-7, available from 1 to 24"
	::= { sw0657851IpMacBindConf 2 }

sw0657851IpMacBindSetting          	OBJECT IDENTIFIER ::= { sw0657851IpMacBind 2 }

sw0657851IpMacBindSettingNumber	OBJECT-TYPE
	SYNTAX		INTEGER(0..1024)
	MAX-ACCESS	    read-write
	STATUS		current
	DESCRIPTION
		"Get the amount of ip_mac_binding entry."
	::= { sw0657851IpMacBindSetting 1 }

sw0657851IpMacBindSettingEntryCreate	OBJECT-TYPE
	SYNTAX		INTEGER(0..1024)
	MAX-ACCESS	    read-write
	STATUS		current
	DESCRIPTION
		"Create ip_mac_binding entry.
		 0: none
		 1-1024: creat with this index."
	::= { sw0657851IpMacBindSetting 2 }

sw0657851IpMacBindSettingTable	OBJECT-TYPE
	SYNTAX		SEQUENCE OF SW0657851IpMacBindSettingEntry
	MAX-ACCESS	not-accessible
	STATUS		current
    DESCRIPTION
        "This is a list of SW0657851IpMacBindSettingEntry."
	::= { sw0657851IpMacBindSetting 3 }

SW0657851IpMacBindSettingEntry ::=
SEQUENCE {
    sw0657851IpMacBindSettingIndex        INTEGER,
    sw0657851IpMacBindSettingMAC          DisplayString,
    sw0657851IpMacBindSettingIP           IpAddress,
    sw0657851IpMacBindSettingPort         INTEGER,
    sw0657851IpMacBindSettingVID          INTEGER,
    sw0657851IpMacBindSettingEntryAction  INTEGER
}

sw0657851IpMacBindSettingEntry	OBJECT-TYPE
	SYNTAX		SW0657851IpMacBindSettingEntry
	MAX-ACCESS	    not-accessible
	STATUS		current
	DESCRIPTION
		"This is the entry of the ip_mac_binding information."
	INDEX {sw0657851IpMacBindSettingIndex}
	::= { sw0657851IpMacBindSettingTable 1 }

sw0657851IpMacBindSettingIndex	OBJECT-TYPE
	SYNTAX		INTEGER(1..1024)
	MAX-ACCESS	    not-accessible
	STATUS		current
	DESCRIPTION
		"This is the index of the ip_mac_binding entry."
	::= { sw0657851IpMacBindSettingEntry 1 }

sw0657851IpMacBindSettingMAC	OBJECT-TYPE
	SYNTAX		DisplayString
	MAX-ACCESS	    read-write
	STATUS		current
	DESCRIPTION
		"This is the mac address of the ip_mac_binding entry."
	::= { sw0657851IpMacBindSettingEntry 2 }

sw0657851IpMacBindSettingIP	OBJECT-TYPE
	SYNTAX		IpAddress
	MAX-ACCESS	    read-write
	STATUS		current
	DESCRIPTION
		"This is the ip address of the ip_mac_binding entry."
	::= { sw0657851IpMacBindSettingEntry 3 }

sw0657851IpMacBindSettingPort	OBJECT-TYPE
	SYNTAX		INTEGER(1..24)
	MAX-ACCESS	    read-write
	STATUS		current
	DESCRIPTION
		"This is the port number of the ip_mac_binding entry."
	::= { sw0657851IpMacBindSettingEntry 4 }

sw0657851IpMacBindSettingVID	OBJECT-TYPE
	SYNTAX		INTEGER(1..4094)
	MAX-ACCESS	    read-write
	STATUS		current
	DESCRIPTION
		"This is the vid of the ip_mac_binding entry."
	::= { sw0657851IpMacBindSettingEntry 5 }

sw0657851IpMacBindSettingEntryAction	OBJECT-TYPE
	SYNTAX		INTEGER(1..3)
	MAX-ACCESS	    read-write
	STATUS		current
	DESCRIPTION
		"
		 1 - active
		 2 - notInService
		 3 - delete"
	::= { sw0657851IpMacBindSettingEntry 6 }

sw0657851Dot1X           	OBJECT IDENTIFIER ::= { sw0657851Produces 23 }

sw0657851Dot1XServerConf          	OBJECT IDENTIFIER ::= { sw0657851Dot1X 1 }

sw0657851Dot1XServerConfAuthenticationServerIp	OBJECT-TYPE
	SYNTAX		IpAddress
	MAX-ACCESS	    read-write
	STATUS		current
	DESCRIPTION
		"Get/Set authentication server ip"
	::= { sw0657851Dot1XServerConf 1 }

sw0657851Dot1XServerConfAuthenticationUdpPort	OBJECT-TYPE
	SYNTAX		INTEGER(1..65535)
	MAX-ACCESS	    read-write
	STATUS		current
	DESCRIPTION
		"Get/Set IEEE 802.1X authentication UDP port number"
	::= { sw0657851Dot1XServerConf 2 }

sw0657851Dot1XServerConfAuthenticationSecretKey	OBJECT-TYPE
	SYNTAX		DisplayString
	MAX-ACCESS	    read-write
	STATUS		current
	DESCRIPTION
		"Get/Set IEEE 802.1X authentication secret key"
	::= { sw0657851Dot1XServerConf 3 }

sw0657851Dot1XServerConfAccountingServerIp	OBJECT-TYPE
	SYNTAX		IpAddress
	MAX-ACCESS	    read-write
	STATUS		current
	DESCRIPTION
		"Get/Set IEEE 802.1X accounting service IP"
	::= { sw0657851Dot1XServerConf 4 }

sw0657851Dot1XServerConfAccountingUdpPort	OBJECT-TYPE
	SYNTAX		INTEGER(1..65535)
	MAX-ACCESS	    read-write
	STATUS		current
	DESCRIPTION
		"Get/Set IEEE 802.1X accounting UDP port number"
	::= { sw0657851Dot1XServerConf 5 }

sw0657851Dot1XServerConfAccountingSecretKey	OBJECT-TYPE
	SYNTAX		DisplayString
	MAX-ACCESS	    read-write
	STATUS		current
	DESCRIPTION
		"Get/Set IEEE 802.1X accounting secret key"
	::= { sw0657851Dot1XServerConf 6 }

sw0657851Dot1XPortConfTable	OBJECT-TYPE
	SYNTAX		SEQUENCE OF SW0657851Dot1XPortConfEntry
	MAX-ACCESS	not-accessible
	STATUS		current
    DESCRIPTION
        "A table that contains the configuration objects for the
         Authenticator PAE associated with each port."
	::= { sw0657851Dot1X 2 }

SW0657851Dot1XPortConfEntry ::=
SEQUENCE {
    sw0657851Dot1XPort                INTEGER,
    sw0657851Dot1XPortMode            INTEGER,
    sw0657851Dot1XPortControl         INTEGER,
    sw0657851Dot1XPortreAuthMax       INTEGER,
    sw0657851Dot1XPorttxPeriod        INTEGER,
    sw0657851Dot1XPortquietPeriod     INTEGER,
    sw0657851Dot1XPortreAuthEnabled   INTEGER,
    sw0657851Dot1XPortreAuthPeriod    INTEGER,
    sw0657851Dot1XPortmaxReq          INTEGER,
    sw0657851Dot1XPortsuppTimeout     INTEGER,
    sw0657851Dot1XPortserverTimeout   INTEGER
}

sw0657851Dot1XPortConfEntry	OBJECT-TYPE
	SYNTAX		SW0657851Dot1XPortConfEntry
	MAX-ACCESS	    not-accessible
	STATUS		current
	DESCRIPTION
		"The configuration information for an Authenticator PAE."
	INDEX {sw0657851Dot1XPort}
	::= { sw0657851Dot1XPortConfTable 1 }

sw0657851Dot1XPort	OBJECT-TYPE
	SYNTAX		INTEGER(1..24)
	MAX-ACCESS	    read-write
	STATUS		current
	DESCRIPTION
		 "The port index of 802.1X port configuration table."
	::= { sw0657851Dot1XPortConfEntry 1 }

sw0657851Dot1XPortMode	OBJECT-TYPE
	SYNTAX		INTEGER(0..3)
	MAX-ACCESS	    read-write
	STATUS		current
	DESCRIPTION
		"Get/Set IEEE 802.1X port mode.
		 0 - Disable
		 1 - Normal
		 2 - Advanced
		 3 - Clientless"
	::= { sw0657851Dot1XPortConfEntry 2 }

sw0657851Dot1XPortControl	OBJECT-TYPE
	SYNTAX		INTEGER(0..2)
	MAX-ACCESS	    read-write
	STATUS		current
	DESCRIPTION
		"The current value of the controlled Port
		 control parameter of the Port.
	 0 : ForceUnauthorized,
	 1 : ForceAuthorized,
	 2 : Auto
        "
	::= { sw0657851Dot1XPortConfEntry 3 }

sw0657851Dot1XPortreAuthMax	OBJECT-TYPE
	SYNTAX		INTEGER(1..10)
	MAX-ACCESS	    read-write
	STATUS		current
	DESCRIPTION
		"The value of the reAuthMax constant currently in use by
		 the Authenticator PAE state machine."
	::= { sw0657851Dot1XPortConfEntry 4 }


sw0657851Dot1XPorttxPeriod	OBJECT-TYPE
	SYNTAX		INTEGER(1..65535)
	MAX-ACCESS	    read-write
	STATUS		current
	DESCRIPTION
		"The value, in seconds, of the txPeriod constant
		 currently in use by the Authenticator PAE state
		 machine."
	::= { sw0657851Dot1XPortConfEntry 5 }

sw0657851Dot1XPortquietPeriod	OBJECT-TYPE
	SYNTAX		INTEGER(0..65535)
	MAX-ACCESS	    read-write
	STATUS		current
	DESCRIPTION
		"The value, in seconds, of the quietPeriod constant
		 currently in use by the Authenticator PAE state
		 machine."
	::= { sw0657851Dot1XPortConfEntry 6 }

sw0657851Dot1XPortreAuthEnabled	OBJECT-TYPE
	SYNTAX		INTEGER(0|1)
	MAX-ACCESS	    read-write
	STATUS		current
	DESCRIPTION
		"The enable/disable control used by the Reauthentication
		 Timer state machine.
		 0 - Disable
		 1 - Enable"
	::= { sw0657851Dot1XPortConfEntry 7 }

sw0657851Dot1XPortreAuthPeriod	OBJECT-TYPE
	SYNTAX		INTEGER(1..65535)
	MAX-ACCESS	    read-write
	STATUS		current
	DESCRIPTION
		"The value, in seconds, of the reAuthPeriod constant
		 currently in use by the Reauthentication Timer state
		 machine."
	::= { sw0657851Dot1XPortConfEntry 8 }

sw0657851Dot1XPortmaxReq	OBJECT-TYPE
	SYNTAX		INTEGER(1..10)
	MAX-ACCESS	    read-write
	STATUS		current
	DESCRIPTION
		"The value of the maxReq constant currently in use by
		 the Backend Authentication state machine."
	::= { sw0657851Dot1XPortConfEntry 9 }

sw0657851Dot1XPortsuppTimeout	OBJECT-TYPE
	SYNTAX		INTEGER(1..255)
	MAX-ACCESS	    read-write
	STATUS		current
	DESCRIPTION
		"The value, in seconds, of the suppTimeout constant
		 currently in use by the Backend Authentication state
		 machine."
	::= { sw0657851Dot1XPortConfEntry 10 }

sw0657851Dot1XPortserverTimeout	OBJECT-TYPE
	SYNTAX		INTEGER(1..255)
	MAX-ACCESS	    read-write
	STATUS		current
	DESCRIPTION
		"The value, in seconds, of the serverTimeout constant
		 currently in use by the Backend Authentication state
		 machine."
	::= { sw0657851Dot1XPortConfEntry 11 }


sw0657851Dot1XStatusTable	OBJECT-TYPE
	SYNTAX		SEQUENCE OF SW0657851Dot1XStatusEntry
	MAX-ACCESS	not-accessible
	STATUS		current
    DESCRIPTION
        "A table that contains the status objects for the
         Authenticator PAE associated with each port."
	::= { sw0657851Dot1X 3 }

SW0657851Dot1XStatusEntry ::=
SEQUENCE {
    sw0657851Dot1XStatusIndex   INTEGER,
    sw0657851Dot1XStatusMode    DisplayString,
    sw0657851Dot1XStatusStatus  DisplayString
}

sw0657851Dot1XStatusEntry	OBJECT-TYPE
	SYNTAX		SW0657851Dot1XStatusEntry
	MAX-ACCESS	    not-accessible
	STATUS		current
	DESCRIPTION
		"The status information for an Authenticator PAE."
	INDEX {sw0657851Dot1XStatusIndex}
	::= { sw0657851Dot1XStatusTable 1 }

sw0657851Dot1XStatusIndex	OBJECT-TYPE
	SYNTAX		INTEGER(1..24)
	MAX-ACCESS	    not-accessible
	STATUS		current
	DESCRIPTION
		"The port index of 802.1X status table."
	::= { sw0657851Dot1XStatusEntry 1 }

sw0657851Dot1XStatusMode	OBJECT-TYPE
	SYNTAX		DisplayString
	MAX-ACCESS	    read-only
	STATUS		current
	DESCRIPTION
		"The current mode of the controlled port."
	::= { sw0657851Dot1XStatusEntry 2 }

sw0657851Dot1XStatusStatus	OBJECT-TYPE
	SYNTAX		DisplayString
	MAX-ACCESS	    read-only
	STATUS		current
	DESCRIPTION
		"The current status of the controlled port."
	::= { sw0657851Dot1XStatusEntry 3 }

sw0657851Dot1XStatisticsTable	OBJECT-TYPE
	SYNTAX		SEQUENCE OF SW0657851Dot1XStatisticsEntry
	MAX-ACCESS	not-accessible
	STATUS		current
    DESCRIPTION
        "A table that contains the statistics objects for the
         Authenticator PAE associated with each port."
	::= { sw0657851Dot1X 4 }

SW0657851Dot1XStatisticsEntry ::=
SEQUENCE {
    sw0657851Dot1XStatisticsIndex                        INTEGER,
    sw0657851Dot1XClearCounter                           INTEGER,
    sw0657851Dot1XAuthEntersConnecting                   Counter32,
    sw0657851Dot1XauthEapLogoffsWhileConnecting          Counter32,
    sw0657851Dot1XAuthEntersAuthenticating               Counter32,
    sw0657851Dot1XAuthAuthSuccessesWhileAuthenticating   Counter32,
    sw0657851Dot1XAuthAuthTimeoutsWhileAuthenticating    Counter32,
    sw0657851Dot1XAuthAuthFailWhileAuthenticating        Counter32,
    sw0657851Dot1XAuthAuthEapStartsWhileAuthenticating   Counter32,
    sw0657851Dot1XAuthAuthEapLogoffWhileAuthenticating   Counter32,
    sw0657851Dot1XAuthAuthReauthsWhileAuthenticated      Counter32,
    sw0657851Dot1XAuthAuthEapStartsWhileAuthenticated    Counter32,
    sw0657851Dot1XAuthAuthEapLogoffWhileAuthenticated    Counter32,
    sw0657851Dot1XBackendResponses                       Counter32,
    sw0657851Dot1XBackendAccessChallenges                Counter32,
    sw0657851Dot1XBackendOtherRequestsToSupplicant       Counter32,
    sw0657851Dot1XBackendAuthSuccesses                   Counter32,
    sw0657851Dot1XBackendAuthFails                       Counter32,
    sw0657851Dot1XAuthEapolFramesRx                      Counter32,
    sw0657851Dot1XAuthEapolFramesTx                      Counter32,
    sw0657851Dot1XAuthEapolStartFramesRx                 Counter32,
    sw0657851Dot1XAuthEapolLogoffFramesRx                Counter32,
    sw0657851Dot1XAuthEapolRespIdFramesRx                Counter32,
    sw0657851Dot1XAuthEapolRespFramesRx                  Counter32,
    sw0657851Dot1XAuthEapolReqIdFramesTx                 Counter32,
    sw0657851Dot1XAuthEapolReqFramesTx                   Counter32,
    sw0657851Dot1XAuthInvalidEapolFramesRx               Counter32,
    sw0657851Dot1XAuthEapLengthErrorFramesRx             Counter32,
    sw0657851Dot1XAuthLastEapolFrameVersion              Counter32,
    sw0657851Dot1XAuthLastEapolFrameSource               DisplayString
}

sw0657851Dot1XStatisticsEntry	OBJECT-TYPE
	SYNTAX		SW0657851Dot1XStatisticsEntry
	MAX-ACCESS	    not-accessible
	STATUS		current
	DESCRIPTION
		"The statistics information for an Authenticator PAE."
	INDEX {sw0657851Dot1XStatisticsIndex}
	::= { sw0657851Dot1XStatisticsTable 1 }

sw0657851Dot1XStatisticsIndex	OBJECT-TYPE
	SYNTAX		INTEGER(1..24)
	MAX-ACCESS	    not-accessible
	STATUS		current
	DESCRIPTION
		"The port index of the 802.1X statistics table."
	::= { sw0657851Dot1XStatisticsEntry 1 }

sw0657851Dot1XClearCounter	OBJECT-TYPE
	SYNTAX		INTEGER(0|1)
	MAX-ACCESS	    read-write
	STATUS		current
	DESCRIPTION
		"Reset the 802.1X counter associated with this port.
		 0 - do nothing
		 1 - clear "
	::= { sw0657851Dot1XStatisticsEntry 2 }

sw0657851Dot1XAuthEntersConnecting	OBJECT-TYPE
	SYNTAX		Counter32
	MAX-ACCESS	    read-only
	STATUS		current
	DESCRIPTION
		"Counts the number of times that the state machine
		 transitions to the CONNECTING state from any other
		 state."
	::= { sw0657851Dot1XStatisticsEntry 3 }

sw0657851Dot1XauthEapLogoffsWhileConnecting	OBJECT-TYPE
	SYNTAX		Counter32
	MAX-ACCESS	    read-only
	STATUS		current
	DESCRIPTION
		"Counts the number of times that the state machine
		 transitions from CONNECTING to DISCONNECTED as a result
		 of receiving an EAPOL-Logoff message."
	::= { sw0657851Dot1XStatisticsEntry 4 }

sw0657851Dot1XAuthEntersAuthenticating	OBJECT-TYPE
	SYNTAX		Counter32
	MAX-ACCESS	    read-only
	STATUS		current
	DESCRIPTION
		"Counts the number of times that the state machine
		 transitions from CONNECTING to AUTHENTICATING, as a
		 result of an EAP-Response/Identity message being
		 received from the Supplicant."
	::= { sw0657851Dot1XStatisticsEntry 5 }

sw0657851Dot1XAuthAuthSuccessesWhileAuthenticating	OBJECT-TYPE
	SYNTAX		Counter32
	MAX-ACCESS	    read-only
	STATUS		current
	DESCRIPTION
		"Counts the number of times that the state machine
		 transitions from AUTHENTICATING to AUTHENTICATED, as a
		 result of the Backend Authentication state machine
		 indicating successful authentication of the Supplicant."
	::= { sw0657851Dot1XStatisticsEntry 6 }

sw0657851Dot1XAuthAuthTimeoutsWhileAuthenticating	OBJECT-TYPE
	SYNTAX		Counter32
	MAX-ACCESS	    read-only
	STATUS		current
	DESCRIPTION
		"Counts the number of times that the state machine
		 transitions from AUTHENTICATING to ABORTING, as a result
		 of the Backend Authentication state machine indicating
		 authentication timeout."
	::= { sw0657851Dot1XStatisticsEntry 7 }

sw0657851Dot1XAuthAuthFailWhileAuthenticating	OBJECT-TYPE
	SYNTAX		Counter32
	MAX-ACCESS	    read-only
	STATUS		current
	DESCRIPTION
		"Counts the number of times that the state machine
		 transitions from AUTHENTICATING to HELD, as a result
		 of the Backend Authentication state machine indicating
		 authentication failure."
	::= { sw0657851Dot1XStatisticsEntry 8 }

sw0657851Dot1XAuthAuthEapStartsWhileAuthenticating	OBJECT-TYPE
	SYNTAX		Counter32
	MAX-ACCESS	    read-only
	STATUS		current
	DESCRIPTION
		"Counts the number of times that the state machine
		 transitions from AUTHENTICATING to ABORTING, as a result
		 of an EAPOL-Start message being received from the
		 Supplicant."
	::= { sw0657851Dot1XStatisticsEntry 9 }

sw0657851Dot1XAuthAuthEapLogoffWhileAuthenticating	OBJECT-TYPE
	SYNTAX		Counter32
	MAX-ACCESS	    read-only
	STATUS		current
	DESCRIPTION
		"Counts the number of times that the state machine
		 transitions from AUTHENTICATING to ABORTING, as a result
		 of an EAPOL-Logoff message being received from the
		 Supplicant."
	::= { sw0657851Dot1XStatisticsEntry 10 }

sw0657851Dot1XAuthAuthReauthsWhileAuthenticated	OBJECT-TYPE
	SYNTAX		Counter32
	MAX-ACCESS	    read-only
	STATUS		current
	DESCRIPTION
		"Counts the number of times that the state machine
		 transitions from AUTHENTICATED to CONNECTING, as a
		 result of a reauthentication request."
	::= { sw0657851Dot1XStatisticsEntry 11 }

sw0657851Dot1XAuthAuthEapStartsWhileAuthenticated	OBJECT-TYPE
	SYNTAX		Counter32
	MAX-ACCESS	    read-only
	STATUS		current
	DESCRIPTION
		"Counts the number of times that the state machine
		 transitions from AUTHENTICATED to CONNECTING, as a
		 result of an EAPOL-Start message being received from
		 the Supplicant."
	::= { sw0657851Dot1XStatisticsEntry 12 }

sw0657851Dot1XAuthAuthEapLogoffWhileAuthenticated	OBJECT-TYPE
	SYNTAX		Counter32
	MAX-ACCESS	    read-only
	STATUS		current
	DESCRIPTION
		"Counts the number of times that the state machine
		 transitions from AUTHENTICATED to DISCONNECTED, as a
		 result of an EAPOL-Logoff message being received from
		 the Supplicant."
	::= { sw0657851Dot1XStatisticsEntry 13 }

sw0657851Dot1XBackendResponses	OBJECT-TYPE
	SYNTAX		Counter32
	MAX-ACCESS	    read-only
	STATUS		current
	DESCRIPTION
		"Counts the number of times that the state machine sends
		 an initial Access-Request packet to the Authentication
		 server (i.e., executes sendRespToServer on entry to the
		 RESPONSE state). Indicates that the Authenticator
		 attempted communication with the Authentication Server."
	::= { sw0657851Dot1XStatisticsEntry 14 }

sw0657851Dot1XBackendAccessChallenges	OBJECT-TYPE
	SYNTAX		Counter32
	MAX-ACCESS	    read-only
	STATUS		current
	DESCRIPTION
		"Counts the number of times that the state machine receives
		 an initial Access-Challenge packet from the Authentication
		 server (i.e., aReq becomes TRUE, causing exit from the
		 RESPONSE state). Indicates that the Authentication Server
		 has communication with the Authenticator."
	::= { sw0657851Dot1XStatisticsEntry 15 }

sw0657851Dot1XBackendOtherRequestsToSupplicant	OBJECT-TYPE
	SYNTAX		Counter32
	MAX-ACCESS	    read-only
	STATUS		current
	DESCRIPTION
		"Counts the number of times that the state machine sends
		 an EAP-Request packet (other than Indentity, Notification,
		 Faluire or Success message) to the Supplicant (i.e.,
		 executes txReq on entry to the REQUEST state). Indicates
		 that Authenticator chose an EAP-method."
	::= { sw0657851Dot1XStatisticsEntry 16 }

sw0657851Dot1XBackendAuthSuccesses	OBJECT-TYPE
	SYNTAX		Counter32
	MAX-ACCESS	    read-only
	STATUS		current
	DESCRIPTION
		"Counts the number of times that the state machine receives
		 an EAP-Success message from the Authentication Server (i.e.,
		 aSuccess becomes TRUE, causing a transitions from RESPONSE to
		 SUCCESS). Indicates that the Supplicant has successfully
		 authenticated to the Authentication Server."
	::= { sw0657851Dot1XStatisticsEntry 17 }

sw0657851Dot1XBackendAuthFails	OBJECT-TYPE
	SYNTAX		Counter32
	MAX-ACCESS	    read-only
	STATUS		current
	DESCRIPTION
		"Counts the number of times that the state machine receives
		 an EAP-Failure message from the Authentication Server (i.e.,
		 aFail becomes TRUE, causing a transitions from RESPONSE to
		 FAIL). Indicates that the Supplicant has not authenticated
		 to the Authentication Server."
	::= { sw0657851Dot1XStatisticsEntry 18 }

sw0657851Dot1XAuthEapolFramesRx	OBJECT-TYPE
	SYNTAX		Counter32
	MAX-ACCESS	    read-only
	STATUS		current
	DESCRIPTION
		"The number of valid EAPOL frames of any type
		 that have been received by this Authenticator."
	::= { sw0657851Dot1XStatisticsEntry 19 }

sw0657851Dot1XAuthEapolFramesTx	OBJECT-TYPE
	SYNTAX		Counter32
	MAX-ACCESS	    read-only
	STATUS		current
	DESCRIPTION
		"The number of valid EAPOL frames of any type
		 that have been transmitted by this Authenticator."
	::= { sw0657851Dot1XStatisticsEntry 20 }

sw0657851Dot1XAuthEapolStartFramesRx	OBJECT-TYPE
	SYNTAX		Counter32
	MAX-ACCESS	    read-only
	STATUS		current
	DESCRIPTION
		"The number of EAPOL Start frames that have
		 been received by this Authenticator."
	::= { sw0657851Dot1XStatisticsEntry 21 }

sw0657851Dot1XAuthEapolLogoffFramesRx	OBJECT-TYPE
	SYNTAX		Counter32
	MAX-ACCESS	    read-only
	STATUS		current
	DESCRIPTION
		"The number of EAPOL Logoff frames that have
		 been received by this Authenticator."
	::= { sw0657851Dot1XStatisticsEntry 22 }

sw0657851Dot1XAuthEapolRespIdFramesRx	OBJECT-TYPE
	SYNTAX		Counter32
	MAX-ACCESS	    read-only
	STATUS		current
	DESCRIPTION
		"The number of EAP Resp/Id frames that have
		 been received by this Authenticator."
	::= { sw0657851Dot1XStatisticsEntry 23 }

sw0657851Dot1XAuthEapolRespFramesRx	OBJECT-TYPE
	SYNTAX		Counter32
	MAX-ACCESS	    read-only
	STATUS		current
	DESCRIPTION
		"The number of valid EAP Response frames
		 (other than Resp/Id frames) that have been
		 received by this Authenticator."
	::= { sw0657851Dot1XStatisticsEntry 24 }

sw0657851Dot1XAuthEapolReqIdFramesTx	OBJECT-TYPE
	SYNTAX		Counter32
	MAX-ACCESS	    read-only
	STATUS		current
	DESCRIPTION
		"The number of EAP Req/Id frames that have
		 been transmitted by this Authenticator."
	::= { sw0657851Dot1XStatisticsEntry 25 }

sw0657851Dot1XAuthEapolReqFramesTx	OBJECT-TYPE
	SYNTAX		Counter32
	MAX-ACCESS	    read-only
	STATUS		current
	DESCRIPTION
		"The number of valid EAP Request frames
		 (other than Req/Id frames) that have been
		 transmitted by this Authenticator."
	::= { sw0657851Dot1XStatisticsEntry 26 }

sw0657851Dot1XAuthInvalidEapolFramesRx	OBJECT-TYPE
	SYNTAX		Counter32
	MAX-ACCESS	    read-only
	STATUS		current
	DESCRIPTION
		"The number of EAPOL frames that have been
		 received by this Authenticator in which the
		 frame type is not recognized."
	::= { sw0657851Dot1XStatisticsEntry 27 }

sw0657851Dot1XAuthEapLengthErrorFramesRx	OBJECT-TYPE
	SYNTAX		Counter32
	MAX-ACCESS	    read-only
	STATUS		current
	DESCRIPTION
		"The number of EAPOL frames that have been
		 received by this Authenticator in which the
		 Packet Body Length field is invalid."
	::= { sw0657851Dot1XStatisticsEntry 28 }

sw0657851Dot1XAuthLastEapolFrameVersion	OBJECT-TYPE
	SYNTAX		Counter32
	MAX-ACCESS	    read-only
	STATUS		current
	DESCRIPTION
		"The protocol version number carried in the
		 most recently received EAPOL frames."
	::= { sw0657851Dot1XStatisticsEntry 29 }

sw0657851Dot1XAuthLastEapolFrameSource	OBJECT-TYPE
	SYNTAX		DisplayString
	MAX-ACCESS	    read-only
	STATUS		current
	DESCRIPTION
		"The source MAC address carried in the
		 most recently received EAPOL frames."
	::= { sw0657851Dot1XStatisticsEntry 30 }


sw0657851TrunkInfo       OBJECT IDENTIFIER ::= { sw0657851Produces 24 }

sw0657851TrunkPort      OBJECT IDENTIFIER ::= { sw0657851TrunkInfo 1 }

sw0657851TrunkPortTable	OBJECT-TYPE
	SYNTAX		SEQUENCE OF SW0657851TrunkPortEntry
	MAX-ACCESS	not-accessible
	STATUS		current
    DESCRIPTION
        "This is a list of SW0657851TrunkPortEntry."
	::= { sw0657851TrunkPort 1 }

SW0657851TrunkPortEntry ::=
SEQUENCE {
    sw0657851TrunkPortIndex	INTEGER,
    sw0657851TrunkPortMethod   	INTEGER,
    sw0657851TrunkPortGroup 	INTEGER,
    sw0657851TrunkPortActiveLacp	INTEGER,
    sw0657851TrunkPortAggtr	INTEGER,
    sw0657851TrunkPortStatus	INTEGER,
    sw0657851TrunkPortCurrentMode	INTEGER
}

sw0657851TrunkPortEntry	OBJECT-TYPE
	SYNTAX		SW0657851TrunkPortEntry
	MAX-ACCESS	    not-accessible
	STATUS		current
	DESCRIPTION
        "Entry(s) for trunk table."
	INDEX {sw0657851TrunkPortIndex}
	::= { sw0657851TrunkPortTable 1 }

sw0657851TrunkPortIndex	OBJECT-TYPE
	SYNTAX		INTEGER(1..24)
	MAX-ACCESS	    not-accessible
	STATUS		current
	DESCRIPTION
        "The port index of trunk table."
	::= { sw0657851TrunkPortEntry 1 }

sw0657851TrunkPortMethod  OBJECT-TYPE
    SYNTAX      INTEGER(0..2)
    MAX-ACCESS  read-write
    STATUS      current
    DESCRIPTION
        "The method of trunk port.
	 0 : None,
	 1 : LACP,
	 2 : Static.
        "
    ::= { sw0657851TrunkPortEntry 2 }

sw0657851TrunkPortGroup  OBJECT-TYPE
    SYNTAX      INTEGER(0..12)
    MAX-ACCESS  read-write
    STATUS      current
    DESCRIPTION
        "The group(0~12) of trunk port."
    ::= { sw0657851TrunkPortEntry 3 }

sw0657851TrunkPortActiveLacp  OBJECT-TYPE
    SYNTAX      INTEGER(0|1)
    MAX-ACCESS  read-write
    STATUS      current
    DESCRIPTION
        "The active lacp mode of trunk port.
	 0 : Passive,
	 1 : Active.
        "
    ::= { sw0657851TrunkPortEntry 4 }

sw0657851TrunkPortAggtr  OBJECT-TYPE
    SYNTAX      INTEGER(1..24)
    MAX-ACCESS  read-only
    STATUS      current
    DESCRIPTION
        "The Aggtr of trunk port."
    ::= { sw0657851TrunkPortEntry 5 }

sw0657851TrunkPortStatus  OBJECT-TYPE
    SYNTAX      INTEGER(0|1)
    MAX-ACCESS  read-only
    STATUS      current
    DESCRIPTION
        "The status of trunk port.
         0 : None,
         1 : Ready.
        "
    ::= { sw0657851TrunkPortEntry 6 }

sw0657851TrunkPortCurrentMode  OBJECT-TYPE
    SYNTAX      INTEGER(0..2)
    MAX-ACCESS  read-write
    STATUS      current
    DESCRIPTION
        "The current mode of trunk port entry.
	 0 : Active mode,
	 1 : Edit mode,
	 2 : Do edit.
        "
    ::= { sw0657851TrunkPortEntry 7 }

sw0657851AggregatorView      OBJECT IDENTIFIER ::= { sw0657851TrunkInfo 2 }

sw0657851AggregatorViewTable  OBJECT-TYPE
    SYNTAX      SEQUENCE OF SW0657851AggregatorViewEntry
    MAX-ACCESS  not-accessible
    STATUS      current
    DESCRIPTION
        "This is a list of SW0657851AggregatorViewEntry."
    ::= { sw0657851AggregatorView 1 }

SW0657851AggregatorViewEntry ::=
SEQUENCE {
    sw0657851AggregatorViewIndex		INTEGER,
    sw0657851AggregatorViewMethod 	INTEGER,
    sw0657851AggregatorViewMemberPorts 	DisplayString,
    sw0657851AggregatorViewReadyPorts	DisplayString
}

sw0657851AggregatorViewEntry OBJECT-TYPE
    SYNTAX      SW0657851AggregatorViewEntry
    MAX-ACCESS  not-accessible
    STATUS      current
    DESCRIPTION
        "Entry(s) for aggregator view table."
    INDEX {sw0657851AggregatorViewIndex}
    ::= { sw0657851AggregatorViewTable 1 }

sw0657851AggregatorViewIndex  OBJECT-TYPE
    SYNTAX      INTEGER(1..24)
    MAX-ACCESS  not-accessible
    STATUS      current
    DESCRIPTION
        "The port index of aggregator view table."
    ::= { sw0657851AggregatorViewEntry 1 }

sw0657851AggregatorViewMethod  OBJECT-TYPE
    SYNTAX      INTEGER(0..2)
    MAX-ACCESS  read-only
    STATUS      current
    DESCRIPTION
        "The method of aggregator view table.
         0 : None,
	 1 : LACP,
	 2 : Static.
        "
    ::= { sw0657851AggregatorViewEntry 2 }

sw0657851AggregatorViewMemberPorts  OBJECT-TYPE
    SYNTAX      DisplayString
    MAX-ACCESS  read-only
    STATUS      current
    DESCRIPTION
        "The member ports of aggregator view table."
    ::= { sw0657851AggregatorViewEntry 3 }

sw0657851AggregatorViewReadyPorts  OBJECT-TYPE
    SYNTAX      DisplayString
    MAX-ACCESS  read-only
    STATUS      current
    DESCRIPTION
        "The ready ports of aggregator view table."
    ::= { sw0657851AggregatorViewEntry 4 }

sw0657851LacpSystemPriority	OBJECT-TYPE
	SYNTAX		INTEGER(1..65535)
	MAX-ACCESS	    read-write
	STATUS		current
	DESCRIPTION
		"Set lacp system priority."
	::= { sw0657851TrunkInfo 3 }

sw0657851IGMPInfo           	OBJECT IDENTIFIER ::= { sw0657851Produces 25 }

sw0657851IgmpProxyConfState OBJECT-TYPE
	SYNTAX      INTEGER(0|1)
	MAX-ACCESS	    read-write
	STATUS		current
	DESCRIPTION
		"Get/Set the IGMP Proxy state.
		 0 - disabled.
		 1 - enable.  "
	::= { sw0657851IGMPInfo 1 }

sw0657851IgmpProxyConfUnregIPMCFlooding OBJECT-TYPE
	SYNTAX      INTEGER(0|1)
	MAX-ACCESS	    read-write
	STATUS		current
	DESCRIPTION
		"Get/Set unregistered IP multicast flooding state, 0 - disable, 1 - enable."
	::= { sw0657851IGMPInfo 2 }

sw0657851IgmpProxyConfGeneralQueuyInterval OBJECT-TYPE
	SYNTAX      INTEGER(1..3600)
	MAX-ACCESS	    read-write
	STATUS		current
	DESCRIPTION
		"Get/Set IGMP general query interval(Unit: second)."
	::= { sw0657851IGMPInfo 3 }

sw0657851IgmpProxyConfGeneralQueuyRepTimeout OBJECT-TYPE
	SYNTAX      INTEGER(1..25)
	MAX-ACCESS	    read-write
	STATUS		current
	DESCRIPTION
		"Get/Set IGMP general query response timeout(Unit: second)."
	::= { sw0657851IGMPInfo 4 }

sw0657851IgmpProxyConfGeneralQueuyMaxRepTime OBJECT-TYPE
	SYNTAX      INTEGER(1..25)
	MAX-ACCESS	    read-write
	STATUS		current
	DESCRIPTION
		"Get/Set IGMP general query maximum response time(Unit: second)."
	::= { sw0657851IGMPInfo 5 }

sw0657851IgmpProxyConfLastMemberQueuyCount OBJECT-TYPE
	SYNTAX      INTEGER(1..16)
	MAX-ACCESS	    read-write
	STATUS		current
	DESCRIPTION
		"Get/Set IGMP specific query robust count."
	::= { sw0657851IGMPInfo 6 }

sw0657851IgmpProxyConfLastMemberQueuyInterval OBJECT-TYPE
	SYNTAX      INTEGER(1..25)
	MAX-ACCESS	    read-write
	STATUS		current
	DESCRIPTION
		"Get/Set IGMP specific query interval(Unit: second)."
	::= { sw0657851IGMPInfo 7 }

sw0657851IgmpProxyConfLastMemberQueuyMaxRepTime OBJECT-TYPE
	SYNTAX      INTEGER(1..25)
	MAX-ACCESS	    read-write
	STATUS		current
	DESCRIPTION
		"Get/Set IGMP specific query maximum response time(Unit: second)."
	::= { sw0657851IGMPInfo 8 }

sw0657851IgmpProxyConfRouterPorts OBJECT-TYPE
	SYNTAX      DisplayString
	MAX-ACCESS	    read-write
	STATUS		current
	DESCRIPTION
		" Get/Set IGMP router port(s)."
	::= { sw0657851IGMPInfo 9 }

sw0657851IgmpGroupMembershipNumber OBJECT-TYPE
	SYNTAX      INTEGER(0..1024)
	MAX-ACCESS	    read-write
	STATUS		current
	DESCRIPTION
		"Get the amount of multicast group membership."
	::= { sw0657851IGMPInfo 10 }

sw0657851IgmpGroupMembershipTable  OBJECT-TYPE
    SYNTAX      SEQUENCE OF SW0657851IgmpGroupMembershipEntry
    MAX-ACCESS  not-accessible
    STATUS      current
    DESCRIPTION
        "Get multicast group membership."
    ::= { sw0657851IGMPInfo 11 }

SW0657851IgmpGroupMembershipEntry ::=
SEQUENCE {
    sw0657851IgmpGroupNo		       INTEGER,
    sw0657851IgmpGroupAddress 	   DisplayString,
    sw0657851IgmpGroupVLANId	     INTEGER,
    sw0657851IgmpGroupPortMembers	 DisplayString
}

sw0657851IgmpGroupMembershipEntry OBJECT-TYPE
    SYNTAX      SW0657851IgmpGroupMembershipEntry
    MAX-ACCESS  not-accessible
    STATUS      current
    DESCRIPTION
        "Multicast group membership entry."
    INDEX {sw0657851IgmpGroupNo}
    ::= { sw0657851IgmpGroupMembershipTable 1 }

sw0657851IgmpGroupNo  OBJECT-TYPE
    SYNTAX      INTEGER(1..1024)
    MAX-ACCESS  not-accessible
    STATUS      current
    DESCRIPTION
        "The port index of Igmp Group Membership table."
    ::= { sw0657851IgmpGroupMembershipEntry 1 }

sw0657851IgmpGroupAddress  OBJECT-TYPE
    SYNTAX      DisplayString
    MAX-ACCESS  read-only
    STATUS      current
    DESCRIPTION
        "The group address of multicast group membership entry."
    ::= { sw0657851IgmpGroupMembershipEntry 2 }

sw0657851IgmpGroupVLANId  OBJECT-TYPE
    SYNTAX      INTEGER(1..4094)
    MAX-ACCESS  read-only
    STATUS      current
    DESCRIPTION
        "The vlan id of multicast group membership entry."
    ::= { sw0657851IgmpGroupMembershipEntry 3 }

sw0657851IgmpGroupPortMembers  OBJECT-TYPE
    SYNTAX      DisplayString
    MAX-ACCESS  read-only
    STATUS      current
    DESCRIPTION
        "The port member of multicast group membership entry."
    ::= { sw0657851IgmpGroupMembershipEntry 4 }


sw0657851TrapEntry	       OBJECT IDENTIFIER ::= { sw0657851Produces 20 }

sw0657851UserLogin NOTIFICATION-TYPE
    OBJECTS   {username}
	STATUS		current
	DESCRIPTION
	   "Send the trap when one user logins the system."
	::= { sw0657851TrapEntry 1 }

sw0657851UserLogout NOTIFICATION-TYPE
    OBJECTS   {username}
	STATUS		current
	DESCRIPTION
	   "Send the trap when one user logouts the system."
	::= { sw0657851TrapEntry 2 }

sw0657851ModuleInserted NOTIFICATION-TYPE
    OBJECTS { ifIndex }
	STATUS    current
	DESCRIPTION
	    "Send the trap when a module is inserted to the system. The OID value means
	     the port number."
	::= { sw0657851TrapEntry 3 }

sw0657851ModuleRemoved NOTIFICATION-TYPE
    OBJECTS { ifIndex }
	STATUS    current
	DESCRIPTION
	    "Send the trap when a module is removed from the system. The OID value means
	     the port number."
	::= { sw0657851TrapEntry 4 }

sw0657851DualMediaSwapped NOTIFICATION-TYPE
    OBJECTS { ifIndex }
	STATUS    current
	DESCRIPTION
	    "Send the trap when the dual media port changed. The OID value means the port number."
	::= { sw0657851TrapEntry 5 }

sw0657851LoopDetected NOTIFICATION-TYPE
    OBJECTS { ifIndex }
	STATUS    current
	DESCRIPTION
	    "Send the trap when loop condition has been detected. The OID value means the port number."
	::= { sw0657851TrapEntry 6 }

sw0657851StpStateDisabled NOTIFICATION-TYPE
	STATUS		current
	DESCRIPTION
	   "Send the trap when the operational state of STP is from enabled to disabled. "
	::= { sw0657851TrapEntry 7 }

sw0657851StpStateEnabled NOTIFICATION-TYPE
	STATUS		current
	DESCRIPTION
	   "Send the trap when the operational state of STP is from disabled to enabled. "
	::= { sw0657851TrapEntry 8 }

sw0657851StpTopologyChanged NOTIFICATION-TYPE
    OBJECTS { ifIndex }
	STATUS		current
	DESCRIPTION
	   "Send the trap when RSTP determines a port should enter the FORWARDING state
	    (a topology change occurs). The OID value is the ifIndex of the port that
	    produces the topology change."
	::= { sw0657851TrapEntry 9 }

sw0657851LacpStateDisabled NOTIFICATION-TYPE
    OBJECTS {ifIndex, groupId}
	STATUS		current
	DESCRIPTION
	   "Send the trap when the operational state of LACP is from enabled to disabled.
	    The OID value means the disabled Group ID."
	::= { sw0657851TrapEntry 10 }

sw0657851LacpStateEnabled NOTIFICATION-TYPE
    OBJECTS {ifIndex, groupId}
	STATUS		current
	DESCRIPTION
	   "Send the trap when the operational state of LACP is from disabled to enabled.
	    The OID value means the disabled Group ID."
	::= { sw0657851TrapEntry 11 }

sw0657851LacpPortAdded NOTIFICATION-TYPE
    OBJECTS   { ifIndex, actorkey, partnerkey }
	STATUS		current
	DESCRIPTION
	   "Send the trap when the state of port is in 'trunk ready'."
	::= { sw0657851TrapEntry 12 }

sw0657851LacpPortTrunkFailure NOTIFICATION-TYPE
    OBJECTS   { ifIndex, actorkey, partnerkey}
	STATUS		current
	DESCRIPTION
	   "Send the trap when one port is not able to be aggregated
	    due to duplex-mode of the port."
	::= { sw0657851TrapEntry 13 }

sw0657851GvrpStateDisabled NOTIFICATION-TYPE
	STATUS		current
	DESCRIPTION
	   "Send the trap when the operational state of GVRP is from enabled to disabled."
	::= { sw0657851TrapEntry 14 }

sw0657851GvrpStateEnabled NOTIFICATION-TYPE
	STATUS		current
	DESCRIPTION
	   "Send the trap when the operational state of LACP is from disabled to enabled. "
	::= { sw0657851TrapEntry 15 }

sw0657851VlanStateDisabled NOTIFICATION-TYPE
	STATUS		current
	DESCRIPTION
	   "Send the trap when the operational state of vlan is from enabled to disabled.
	    The OID value means the enabled Group ID. "
	::= { sw0657851TrapEntry 16 }

sw0657851VlanPortBaseEnabled NOTIFICATION-TYPE
	STATUS		current
	DESCRIPTION
	   "Send the trap when the operational state of vlan is changed to port-based vlan."
	::= { sw0657851TrapEntry 17 }

sw0657851VlanTagBaseEnabled NOTIFICATION-TYPE
	STATUS		current
	DESCRIPTION
	   "Send the trap when the operational state of vlan is changed to tag-based vlan."
	::= { sw0657851TrapEntry 18 }

sw0657851IpmbStateEnabled NOTIFICATION-TYPE
	STATUS		current
	DESCRIPTION
	   "Send trap when ip_mac_binding is enabled."
	::= { sw0657851TrapEntry 19 }

sw0657851IpmbStateDisabled NOTIFICATION-TYPE
	STATUS		current
	DESCRIPTION
	   "Send trap when ip_mac_binding is disabled."
	::= { sw0657851TrapEntry 20 }

sw0657851IpmbClientFailure NOTIFICATION-TYPE
    OBJECTS   { ipmacIp, ipmacMac, ifIndex}
	STATUS		current
	DESCRIPTION
	   "Send trap when ip_mac_binding entry not exist."
	::= { sw0657851TrapEntry 21 }

sw0657851IpmbServerFailure NOTIFICATION-TYPE
    OBJECTS   { ipmacClientIp, ipmacClientMac, ifIndex, ipmacServerIp}
	STATUS		current
	DESCRIPTION
	   "Send trap when ip_mac_binding entry not exist."
	::= { sw0657851TrapEntry 22 }

sw0657851TrapVariable	OBJECT IDENTIFIER ::= { sw0657851Produces 22 }

username OBJECT-TYPE
    SYNTAX      DisplayString
	MAX-ACCESS  read-only
	STATUS      current
	DESCRIPTION
	    "System account name."
	::= { sw0657851TrapVariable 1 }

groupId OBJECT-TYPE
    SYNTAX      INTEGER(1..2147483647)
	MAX-ACCESS  read-only
	STATUS      current
	DESCRIPTION
	    "The Trunk group ID of LACP."
	::= { sw0657851TrapVariable 2 }

actorkey OBJECT-TYPE
    SYNTAX	INTEGER(1..2147483647)
	MAX-ACCESS  read-only
	STATUS      current
	DESCRIPTION
	    "This is the actor key information for LACP."
	::= { sw0657851TrapVariable 3 }

partnerkey OBJECT-TYPE
    SYNTAX	INTEGER(1..2147483647)
	MAX-ACCESS  read-only
	STATUS      current
	DESCRIPTION
	    "This is the partner key information for LACP."
	::= { sw0657851TrapVariable 4 }

uplink OBJECT-TYPE
    SYNTAX	DisplayString
	MAX-ACCESS  read-only
	STATUS      current
	DESCRIPTION
	    "Uplink port(s) in the metro-mode vlan."
	::= { sw0657851TrapVariable 5 }

ipmacIp OBJECT-TYPE
    SYNTAX	DisplayString
	MAX-ACCESS  read-only
	STATUS      current
	DESCRIPTION
	    "IP address of the ip_mac_binding entry."
	::= { sw0657851TrapVariable 7 }

ipmacMac OBJECT-TYPE
    SYNTAX	DisplayString
	MAX-ACCESS  read-only
	STATUS      current
	DESCRIPTION
	    "MAC address of the ip_mac_binding entry."
	::= { sw0657851TrapVariable 8 }

ipmacClientIp OBJECT-TYPE
    SYNTAX	DisplayString
	MAX-ACCESS  read-only
	STATUS      current
	DESCRIPTION
	    "IP address of the ip_mac_binding entry."
	::= { sw0657851TrapVariable 9 }

ipmacClientMac OBJECT-TYPE
    SYNTAX	DisplayString
	MAX-ACCESS  read-only
	STATUS      current
	DESCRIPTION
	    "MAC address of the ip_mac_binding entry."
	::= { sw0657851TrapVariable 10 }

ipmacServerIp OBJECT-TYPE
    SYNTAX	DisplayString
	MAX-ACCESS  read-only
	STATUS      current
	DESCRIPTION
	    "IP address of the ip_mac_binding entry."
	::= { sw0657851TrapVariable 11 }

END
