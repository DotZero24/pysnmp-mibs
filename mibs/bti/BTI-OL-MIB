------------------------------------------------------------------------
------------------------------------------------------------------------
--
-- Copyright (C) BTI Systems Inc. 2003-2010. All Rights Reserved.
--
-- The information contained herein is the property of BTI Systems Inc.
-- and is strictly confidential. Except as expressly authorized in
-- writing by BTI Systems Inc., the holder shall keep all information
-- contained herein confidential, shall disclose the information only
-- to its employees with a need to know, and shall protect the
-- information, in whole or in part, from disclosure and dissemination
-- to third parties with the same degree of care it uses to protect
-- its own confidential information, but with no less than reasonable
-- care. Except as expressly authorized in writing by BTI Systems Inc.,
-- the holder is granted no rights to use the information contained
-- herein.
------------------------------------------------------------------------
------------------------------------------------------------------------

BTI-OL-MIB DEFINITIONS ::= BEGIN

IMPORTS
    MODULE-IDENTITY, OBJECT-TYPE, NOTIFICATION-TYPE, IpAddress,
    Unsigned32
        FROM SNMPv2-SMI
    RowStatus, DisplayString, TEXTUAL-CONVENTION, DateAndTime
        FROM SNMPv2-TC
    btiModules
        FROM BTI-MIB
    opticalLayer, olEvtNotifications, olCondNotifications, trapSeqNum,
    evtDateAndTime, evtDescription, evtObjectType, evtCodeType,
    condReportType, condDateAndTime, condSeverity, condServiceAffecting,
    condDescription, condObjectType, condCodeType, tcaIntervalType,
    tcaDateAndTime, tcaMontype, tcaValue, tcaThreshold
        FROM BTI-7000-MIB
    CpType, BERType, AdminStatus, OperStatus, OperStatQlfr,
    HoursAndMinutes, FiberType, FixedX10, FixedX100, PMIntervalType,
    PMValidity, InitializeCmd
        FROM BTI-TC-MIB;

olMib MODULE-IDENTITY
    LAST-UPDATED "201208171200Z"  -- Friday, August 17, 12:00:00 EST 2012
    ORGANIZATION "BTI Systems Inc."
    CONTACT-INFO "Technical Support
                  BTI Systems Inc.
                  50 Northside Road
                  Ottawa, Ontario, Canada  K2H 5Z6
                  (613) 248-9154
                  support@btisystems.com"
    DESCRIPTION  "The external MIB definitions for the managenent of
                  the BTI Dynamic Optical Layer components including DLA-series
                  amplifiers and ROB-series ROADM modules."
    REVISION     "201208171200Z"  -- Friday, August 17, 12:00:00 EST 2012
    DESCRIPTION  "MIB Updates for BTI 7000 Rel 10.1.0:
                  - deleted un-implemented table olDegreeTable
                  - added new traps for Connection Mismatch feature:
                    olPortCondNotification.0.17 - olPortCondNotification.0.20
                  - added new WCH traps for refined add-channel power monitoring:
                    wchCondNotifications.0.13 - wchCondNotifications.0.18"
    REVISION     "201202101200Z"  -- Friday, February 10, 12:00:00 EST 2012
    DESCRIPTION  "MIB Updates for BTI 7000 Rel 9.2.0:
                  - added new object olPortRemoteId"
    REVISION     "201109261200Z"  -- Monday, September 26, 12:00:00 EST 2011
    DESCRIPTION  "Initial version of the Optical Layer MIB."

    ::= { btiModules 6 }


------------------------------------------------------------------------
-- Optical Layer Textual Conventions
------------------------------------------------------------------------

OlGroupType ::= TEXTUAL-CONVENTION
    STATUS       current
    DESCRIPTION  "Identifies the configuration type of an optical layer
                  grouping."
    SYNTAX       INTEGER { none         (1),  -- Applies to an un-configured group
                           noEqlzTerm   (2),  -- Non-equalizing terminal
                           eqlzTerm     (3),  -- Channel equalizing terminal
                           noEqlzLine   (4),  -- Line amplifier node
                           eqlzLine     (5),  -- Channel equalizing line node
                           roadm        (6) } -- Reconfigurable add drop node

OlPortType ::= TEXTUAL-CONVENTION
    STATUS       current
    DESCRIPTION  "Identifies the type of managed optical interface port
                  on an optical layer module."
    SYNTAX       INTEGER { line      (1),
                           client    (2),
                           dcm       (3),
                           channel   (4),
                           expansion (5) }


------------------------------------------------------------------------
-- The Optical Layer Group table is used to provision, de-provision,
-- edit and review optical layer module groupings.
------------------------------------------------------------------------

olGroupTable OBJECT-TYPE
    SYNTAX       SEQUENCE OF OlGroupEntry
    MAX-ACCESS   not-accessible
    STATUS       current
    DESCRIPTION  "This table lists all provisioned optical layer
                  module groupings on the node."
    ::= { opticalLayer 1 }


olGroupEntry OBJECT-TYPE
    SYNTAX       OlGroupEntry
    MAX-ACCESS   not-accessible
    STATUS       current
    DESCRIPTION  "The conceptual row object of the optical layer
                  group table."
    INDEX        { olGroupIdx }
    ::= { olGroupTable 1 }


OlGroupEntry ::= SEQUENCE { olGroupIdx        INTEGER,
                            olGroupType       INTEGER,
                            olGroupId         DisplayString,
                            olGroupCustom1    DisplayString,
                            olGroupCustom2    DisplayString,
                            olGroupCustom3    DisplayString,
                            olGroupRowStatus  RowStatus }


olGroupIdx OBJECT-TYPE
    SYNTAX       INTEGER (1..255)
    MAX-ACCESS   not-accessible
    STATUS       current
    DESCRIPTION  "A number which uniquely identifies the optical layer
                  group within the node."
    ::= { olGroupEntry 1 }


olGroupType OBJECT-TYPE
    SYNTAX       OlGroupType
    MAX-ACCESS   read-create
    STATUS       current
    DESCRIPTION  "The optical layer group configuration type. This is a
                  mandatory object that must be specified when a row of
                  the table is created. The value of none is not
                  applicable for this object."
    ::= { olGroupEntry 2 }


olGroupId OBJECT-TYPE
    SYNTAX       DisplayString (SIZE (0..32))
    MAX-ACCESS   read-create
    STATUS       current
    DESCRIPTION  "Textual data recorded by the user to briefly identify
                  the provisioned optical layer group in a manner useful
                  to the user."
    DEFVAL       { "" }
    ::= { olGroupEntry 3 }


olGroupCustom1 OBJECT-TYPE
    SYNTAX       DisplayString
    MAX-ACCESS   read-create
    STATUS       current
    DESCRIPTION  "A variable length text string for operating company use."
    DEFVAL       { "" }
    ::= { olGroupEntry 4 }


olGroupCustom2 OBJECT-TYPE
    SYNTAX       DisplayString
    MAX-ACCESS   read-create
    STATUS       current
    DESCRIPTION  "A variable length text string for operating company use."
    DEFVAL       { "" }
    ::= { olGroupEntry 5 }


olGroupCustom3 OBJECT-TYPE
    SYNTAX       DisplayString
    MAX-ACCESS   read-create
    STATUS       current
    DESCRIPTION  "A variable length text string for operating company use."
    DEFVAL       { "" }
    ::= { olGroupEntry 6 }


olGroupRowStatus OBJECT-TYPE
    SYNTAX       RowStatus
    MAX-ACCESS   read-create
    STATUS       current
    DESCRIPTION  "Used to control the addition and deletion of entries in the
                  optical layer group table."
    ::= { olGroupEntry 100 }

------------------------------------------------------------------------
-- The Optical Layer Equipment table is used to manage assignments of
-- provisioned equipment modules to optical layer groupings. Create an
-- entry in the table to assign a provisioned equipment module to an
-- optical layer group. Delete the entry to unassign the equipment.
------------------------------------------------------------------------

olEqptTable OBJECT-TYPE
    SYNTAX       SEQUENCE OF OlEqptEntry
    MAX-ACCESS   not-accessible
    STATUS       current
    DESCRIPTION  "This table lists all provisioned equipment modules
                  that are assigned to an optical layer grouping."
    ::= { opticalLayer 3 }


olEqptEntry OBJECT-TYPE
    SYNTAX       OlEqptEntry
    MAX-ACCESS   not-accessible
    STATUS       current
    DESCRIPTION  "The conceptual row object of the optical layer
                  equipment table."
    INDEX        { olEqptCpTypeIdx,  -- CP Type
                   olEqptShelfIdx,   -- Shelf Num
                   olEqptSlotIdx }   -- Slot Num
    ::= { olEqptTable 1 }


OlEqptEntry ::= SEQUENCE { olEqptCpTypeIdx CpType,
                           olEqptShelfIdx  INTEGER,
                           olEqptSlotIdx   INTEGER,
                           olEqptGroupNum  INTEGER,
                           olEqptDegreeNum INTEGER,
                           olEqptRowStatus RowStatus }


olEqptCpTypeIdx OBJECT-TYPE
    SYNTAX       CpType
    MAX-ACCESS   not-accessible
    STATUS       current
    DESCRIPTION  "The type of circuit pack of the equipment module that
                  is assigned to the optical layer group."
    ::= { olEqptEntry 1 }


olEqptShelfIdx OBJECT-TYPE
    SYNTAX       INTEGER (0|1|11|21|31)
    MAX-ACCESS   not-accessible
    STATUS       current
    DESCRIPTION  "The number of the shelf of the equipment module that
                  is assigned to the optical layer group. For equipment
                  modules that do not reside in a shelf (40-channel
                  Mux/Demux), the value of this object is 0."
    ::= { olEqptEntry 2 }


olEqptSlotIdx OBJECT-TYPE
    SYNTAX       INTEGER (1..255)
    MAX-ACCESS   not-accessible
    STATUS       current
    DESCRIPTION  "The number of the slot of the equipment module that is
                  assigned to the optical layer group. For equipment
                  modules that do not reside in an active shelf slot
                  (ex. 40-channel Mux/Demux), this object represents
                  the module index among modules attributed to shelf 0."
    ::= { olEqptEntry 3 }


olEqptGroupNum OBJECT-TYPE
    SYNTAX       INTEGER (1..255)
    MAX-ACCESS   read-create
    STATUS       current
    DESCRIPTION  "The optical layer group to which the equipment modules
                  is assigned."
    ::= { olEqptEntry 4 }


olEqptDegreeNum OBJECT-TYPE
    SYNTAX       INTEGER (1..4)
    MAX-ACCESS   read-create
    STATUS       current
    DESCRIPTION  "The optical layer group degree to which the equipment
                  module is assigned."
    ::= { olEqptEntry 5 }


olEqptRowStatus OBJECT-TYPE
    SYNTAX       RowStatus
    MAX-ACCESS   read-create
    STATUS       current
    DESCRIPTION  "Used to control the addition and deletion of entries
                  in the optical layer equipment table, which in turn,
                  controls the assigning and unassigning of equipment
                  modules to/from an optical layer grouping."
    ::= { olEqptEntry 100 }


------------------------------------------------------------------------
-- The Optical Layer Port table is used to manage optical ports on
-- equipment modules assigned to optical layer groupings. Most entries
-- in the optical layer port table are auto-created when the supporting
-- equipment module is assigned to an optical layer group. Manual
-- provisioning and de-provisioning of client port C2 is supported on
-- ROB packs assigned to a Channel-equalizing Terminal or Reconfigurable
-- Add/Drop node group configuration.
------------------------------------------------------------------------


olPortTable OBJECT-TYPE
    SYNTAX       SEQUENCE OF OlPortEntry
    MAX-ACCESS   not-accessible
    STATUS       current
    DESCRIPTION  "This table lists all managed ports on equipment modules
                  assigned to optical layer groupings."
    ::= { opticalLayer 4 }


olPortEntry OBJECT-TYPE
    SYNTAX       OlPortEntry
    MAX-ACCESS   not-accessible
    STATUS       current
    DESCRIPTION  "The conceptual row object of the optical layer port
                  table."
    INDEX        { olPortCpTypeIdx,  -- CP Type
                   olPortShelfIdx,   -- Shelf Num
                   olPortSlotIdx,    -- Slot Num
                   olPortTypeIdx,    -- Port Type
                   olPortIdx }       -- Port Num
    ::= { olPortTable 1 }


OlPortEntry ::= SEQUENCE { olPortCpTypeIdx     CpType,
                           olPortShelfIdx      INTEGER,
                           olPortSlotIdx       INTEGER,
                           olPortTypeIdx       OlPortType,
                           olPortIdx           INTEGER,
                           olPortId            DisplayString,
                           olPortCustom1       DisplayString,
                           olPortCustom2       DisplayString,
                           olPortCustom3       DisplayString,
                           olPortDWDMType      INTEGER,
                           olPortGrid          INTEGER,
                           olPortWavelength    FixedX100,
                           olPortFrequency     FixedX100,
                           olPortOperStatus    OperStatus,
                           olPortOperStatQlfr  OperStatQlfr,
                           olPortRemoteId      DisplayString,
                           olPortExpCnxDegree  INTEGER,
                           olPortActCnxDegree  INTEGER,
                           olPortRowStatus     RowStatus }


olPortCpTypeIdx OBJECT-TYPE
    SYNTAX       CpType
    MAX-ACCESS   not-accessible
    STATUS       current
    DESCRIPTION  "The type of circuit pack on which the optical layer
                  port is located."
    ::= { olPortEntry 1 }


olPortShelfIdx OBJECT-TYPE
    SYNTAX       INTEGER (0|1|11|21|31)
    MAX-ACCESS   not-accessible
    STATUS       current
    DESCRIPTION  "The number of the shelf on which the optical layer
                  port is located."
    ::= { olPortEntry 2 }


olPortSlotIdx OBJECT-TYPE
    SYNTAX       INTEGER (1..255)
    MAX-ACCESS   not-accessible
    STATUS       current
    DESCRIPTION  "The number of the slot on which the optical layer
                  port is located."
    ::= { olPortEntry 3 }


olPortTypeIdx OBJECT-TYPE
    SYNTAX       OlPortType
    MAX-ACCESS   not-accessible
    STATUS       current
    DESCRIPTION  "The type of optical layer port according to the
                  function it provides."
    ::= { olPortEntry 4 }


olPortIdx OBJECT-TYPE
    SYNTAX       INTEGER (1..600)
    MAX-ACCESS   not-accessible
    STATUS       current
    DESCRIPTION  "The number of the optical layer port of the specified
                  port type."
    ::= { olPortEntry 5 }


olPortId OBJECT-TYPE
    SYNTAX       DisplayString (SIZE (0..32))
    MAX-ACCESS   read-create
    STATUS       current
    DESCRIPTION  "Textual data recorded by the user to briefly identify
                  the provisioned optical layer port in a manner useful
                  to the user."
    DEFVAL       { "" }
    ::= { olPortEntry 6 }


olPortCustom1 OBJECT-TYPE
    SYNTAX       DisplayString
    MAX-ACCESS   read-create
    STATUS       current
    DESCRIPTION  "A variable length text string for operating company use."
    DEFVAL       { "" }
    ::= { olPortEntry 7 }


olPortCustom2 OBJECT-TYPE
    SYNTAX       DisplayString
    MAX-ACCESS   read-create
    STATUS       current
    DESCRIPTION  "A variable length text string for operating company use."
    DEFVAL       { "" }
    ::= { olPortEntry 8 }


olPortCustom3 OBJECT-TYPE
    SYNTAX       DisplayString
    MAX-ACCESS   read-create
    STATUS       current
    DESCRIPTION  "A variable length text string for operating company use."
    DEFVAL       { "" }
    ::= { olPortEntry 9 }


olPortDWDMType OBJECT-TYPE
    SYNTAX       INTEGER { native (1),
                           alien  (2) }
    MAX-ACCESS   read-create
    STATUS       current
    DESCRIPTION  "Used to configure the port for the type of DWDM composite
                  to which it is inter-connection. By default, all ports are
                  inter-connected with native optical layer DWDM composites.
                  For some configurations, client port 2 of ROB2 pack and
                  ROB4 modules may be configured for alien DWDM type."
    DEFVAL       { native }
    ::= { olPortEntry 10 }


olPortGrid OBJECT-TYPE
    SYNTAX       INTEGER { ghz100 (1),
                           ghz50  (2) }
    MAX-ACCESS   read-write
    STATUS       current
    DESCRIPTION  "The DWDM grid spacing on the port."
    DEFVAL       { ghz100 }
    ::= { olPortEntry 11 }


olPortWavelength OBJECT-TYPE
    SYNTAX       FixedX100
    UNITS        "nanometers/100"
    MAX-ACCESS   read-only
    STATUS       current
    DESCRIPTION  "The wavelength of the channel carried by the port.
                  This object exists only in table entries for channel
                  ports on Mux/Demux modules."
    ::= { olPortEntry 12 }


olPortFrequency OBJECT-TYPE
    SYNTAX       FixedX100
    UNITS        "terahertz/100"
    MAX-ACCESS   read-only
    STATUS       current
    DESCRIPTION  "The frequency of the channel carried by the port.
                  This object exists only in table entries for channel
                  ports on Mux/Demux modules."
    ::= { olPortEntry 13 }


olPortOperStatus OBJECT-TYPE
    SYNTAX       OperStatus
    MAX-ACCESS   read-only
    STATUS       current
    DESCRIPTION  "The reported operational status of the optical layer port."
    ::= { olPortEntry 14 }


olPortOperStatQlfr OBJECT-TYPE
    SYNTAX       OperStatQlfr
    MAX-ACCESS   read-only
    STATUS       current
    DESCRIPTION  "This is a textual list of qualifiers about the reported
                  operational status of the optical layer port."
    ::= { olPortEntry 15 }


olPortRemoteId OBJECT-TYPE
    SYNTAX       DisplayString
    MAX-ACCESS   read-create
    STATUS       current
    DESCRIPTION  "Identifies the remote node and port to which the
                  optical layer port is connected, in the format
                  prescribed by the PSM network management system."
    DEFVAL       { "" }
    ::= { olPortEntry 16 }


olPortExpCnxDegree OBJECT-TYPE
    SYNTAX       INTEGER (2..4)
    MAX-ACCESS   accessible-for-notify
    STATUS       current
    DESCRIPTION  "The expected degree number of the equipment that is
                  inter-connected on the port."
    ::= { olPortEntry 17 }


olPortActCnxDegree OBJECT-TYPE
    SYNTAX       INTEGER (2..4)
    MAX-ACCESS   accessible-for-notify
    STATUS       current
    DESCRIPTION  "The actual degree number of the equipment that is
                  inter-connected on the port."
    ::= { olPortEntry 18 }


olPortRowStatus OBJECT-TYPE
    SYNTAX       RowStatus
    MAX-ACCESS   read-create
    STATUS       current
    DESCRIPTION  "Used to control the addition and deletion of entries
                  in the Optical Layer Port table. Manual creation and
                  deletion is supported only for the client 2 port on
                  ROB packs assigned to a Channel-equalizing Terminal
                  or Reconfigurable Add/Drop node group."
    ::= { olPortEntry 100 }



------------------------------------------------------------------------
-- The equipment connection table lists all intra-group optical fiber
-- patch connections that must be in place to inter-connect equipment
-- modules assigned to optical layer groupings.
------------------------------------------------------------------------


eqptConnTable OBJECT-TYPE
    SYNTAX       SEQUENCE OF EqptConnEntry
    MAX-ACCESS   not-accessible
    STATUS       current
    DESCRIPTION  "This table lists all intra-group optical fiber patch
                  connections between ports on equipment modules assigned
                  to optical layer groupings."
    ::= { opticalLayer 5 }


eqptConnEntry OBJECT-TYPE
    SYNTAX       EqptConnEntry
    MAX-ACCESS   not-accessible
    STATUS       current
    DESCRIPTION  "The conceptual row object of the equipment connection
                  table."
    INDEX        { eqptConnSrcCpTypeIdx,   -- Source CP Type
                   eqptConnSrcShelfIdx,    -- Source Shelf Num
                   eqptConnSrcSlotIdx,     -- Source Slot Num
                   eqptConnSrcPortTypeIdx, -- Source Port Type
                   eqptConnSrcIdx,         -- Source Port Num
                   eqptConnDstCpTypeIdx,   -- Destination CP Type
                   eqptConnDstShelfIdx,    -- Destination Shelf Num
                   eqptConnDstSlotIdx,     -- Destination Slot Num
                   eqptConnDstPortTypeIdx, -- Destination Port Type
                   eqptConnDstIdx }        -- Destination Port Num
    ::= { eqptConnTable 1 }


EqptConnEntry ::= SEQUENCE { eqptConnSrcCpTypeIdx   CpType,
                             eqptConnSrcShelfIdx    INTEGER,
                             eqptConnSrcSlotIdx     INTEGER,
                             eqptConnSrcPortTypeIdx OlPortType,
                             eqptConnSrcIdx         INTEGER,
                             eqptConnDstCpTypeIdx   CpType,
                             eqptConnDstShelfIdx    INTEGER,
                             eqptConnDstSlotIdx     INTEGER,
                             eqptConnDstPortTypeIdx OlPortType,
                             eqptConnDstIdx         INTEGER,
                             eqptConnType           INTEGER,
                             eqptConnRowStatus      RowStatus }


eqptConnSrcCpTypeIdx OBJECT-TYPE
    SYNTAX       CpType
    MAX-ACCESS   not-accessible
    STATUS       current
    DESCRIPTION  "The type of circuit pack on which the source port
                  of the equipment connection is located."
    ::= { eqptConnEntry 1 }


eqptConnSrcShelfIdx OBJECT-TYPE
    SYNTAX       INTEGER (0|1|11|21|31)
    MAX-ACCESS   not-accessible
    STATUS       current
    DESCRIPTION  "The number of the shelf on which the source port
                  of the equipment connection is located."
    ::= { eqptConnEntry 2 }


eqptConnSrcSlotIdx OBJECT-TYPE
    SYNTAX       INTEGER (1..255)
    MAX-ACCESS   not-accessible
    STATUS       current
    DESCRIPTION  "The number of the slot on which the source port
                  of the equipment connection is located."
    ::= { eqptConnEntry 3 }


eqptConnSrcPortTypeIdx OBJECT-TYPE
    SYNTAX       OlPortType
    MAX-ACCESS   not-accessible
    STATUS       current
    DESCRIPTION  "The type of the source port of the equipment connection,
                  according to the function it provides."
    ::= { eqptConnEntry 4 }


eqptConnSrcIdx OBJECT-TYPE
    SYNTAX       INTEGER (1..600)
    MAX-ACCESS   not-accessible
    STATUS       current
    DESCRIPTION  "The number of the port of the specified port type
                  of the source port of the equipment connection."
    ::= { eqptConnEntry 5 }


eqptConnDstCpTypeIdx OBJECT-TYPE
    SYNTAX       CpType
    MAX-ACCESS   not-accessible
    STATUS       current
    DESCRIPTION  "The type of circuit pack on which the destination port
                  of the equipment connection is located."
    ::= { eqptConnEntry 6 }


eqptConnDstShelfIdx OBJECT-TYPE
    SYNTAX       INTEGER (0|1|11|21|31)
    MAX-ACCESS   not-accessible
    STATUS       current
    DESCRIPTION  "The number of the shelf on which the destination port
                  of the equipment connection is located."
    ::= { eqptConnEntry 7 }


eqptConnDstSlotIdx OBJECT-TYPE
    SYNTAX       INTEGER (1..255)
    MAX-ACCESS   not-accessible
    STATUS       current
    DESCRIPTION  "The number of the slot on which the destination port
                  of the equipment connection is located."
    ::= { eqptConnEntry 8 }


eqptConnDstPortTypeIdx OBJECT-TYPE
    SYNTAX       OlPortType
    MAX-ACCESS   not-accessible
    STATUS       current
    DESCRIPTION  "The type of the destination port of the equipment
                  connection, according to the function it provides."
    ::= { eqptConnEntry 9 }


eqptConnDstIdx OBJECT-TYPE
    SYNTAX       INTEGER (1..600)
    MAX-ACCESS   not-accessible
    STATUS       current
    DESCRIPTION  "The number of the port of the specified port type
                  of the destination port of the equipment connection."
    ::= { eqptConnEntry 10 }


eqptConnType OBJECT-TYPE
    SYNTAX       INTEGER { duplex   (1),
                           loopback (2) }
    MAX-ACCESS   read-only
    STATUS       current
    DESCRIPTION  "The type of optical fiber patch cable for the equipment
                  connection entry."
    ::= { eqptConnEntry 11 }


eqptConnRowStatus OBJECT-TYPE
    SYNTAX       RowStatus
    MAX-ACCESS   accessible-for-notify
    STATUS       current
    DESCRIPTION  "The equipment connection table RowStatus object is not
                  readable or writeable because all entries in the table
                  are automatically created and deleted as equipment
                  modules are assigned and unassigned to optical layer
                  groupings. This equipment connection row status object
                  is used only in database change notifications to
                  indicate if the row has been created or deleted."
    ::= { eqptConnEntry 100 }



------------------------------------------------------------------------
-- The Optical Layer OSC table is used to configure and monitor OSC
-- managed objects on optical layer equipment modules.
------------------------------------------------------------------------


olOSCTable OBJECT-TYPE
    SYNTAX       SEQUENCE OF OlOSCEntry
    MAX-ACCESS   not-accessible
    STATUS       current
    DESCRIPTION  "This table lists all OSC managed objects that have
                  been created on the optical layer equipment modules."
    ::= { opticalLayer 6 }


olOSCEntry OBJECT-TYPE
    SYNTAX       OlOSCEntry
    MAX-ACCESS   not-accessible
    STATUS       current
    DESCRIPTION  "The conceptual row object of the optical laye OSC table."
    INDEX        { olOSCCpTypeIdx,  -- CP Type
                   olOSCShelfIdx,   -- Shelf Num
                   olOSCSlotIdx,    -- Slot Num
                   olOSCLineIdx }   -- Line Num
    ::= { olOSCTable 1 }


OlOSCEntry ::= SEQUENCE { olOSCCpTypeIdx           CpType,
                          olOSCShelfIdx            INTEGER,
                          olOSCSlotIdx             INTEGER,
                          olOSCLineIdx             INTEGER,
                          olOSCAdminStatus         AdminStatus,
                          olOSCOperStatus          OperStatus,
                          olOSCOperStatQlfr        OperStatQlfr,
                          olOSCAutoEnableTimer     HoursAndMinutes,
                          olOSCActAutoEnableTimer  HoursAndMinutes,
                          olOSCId                  DisplayString,
                          olOSCCustom1             DisplayString,
                          olOSCCustom2             DisplayString,
                          olOSCCustom3             DisplayString,
                          olOSCFEIMMon             INTEGER,
                          olOSCExpFESysName        DisplayString,
                          olOSCExpFEIPAddr         IpAddress,
                          olOSCExpFEGrp            INTEGER,
                          olOSCExpFEDegr           INTEGER,
                          olOSCFESysName           DisplayString,
                          olOSCFEIPAddr            IpAddress,
                          olOSCFEGrp               INTEGER,
                          olOSCFEDegr              INTEGER,
                          olOSCFEGrpType           OlGroupType,
                          olOSCRowStatus           RowStatus }


olOSCCpTypeIdx OBJECT-TYPE
    SYNTAX       CpType
    MAX-ACCESS   not-accessible
    STATUS       current
    DESCRIPTION  "The type of circuit pack on which the OSC is located."
    ::= { olOSCEntry 1 }


olOSCShelfIdx OBJECT-TYPE
    SYNTAX       INTEGER (1|11|21|31)
    MAX-ACCESS   not-accessible
    STATUS       current
    DESCRIPTION  "The number of the shelf in which the OSC is located."
    ::= { olOSCEntry 2 }


olOSCSlotIdx OBJECT-TYPE
    SYNTAX       INTEGER (1..20)
    MAX-ACCESS   not-accessible
    STATUS       current
    DESCRIPTION  "The number of the slot in which the OSC is located."
    ::= { olOSCEntry 3 }


olOSCLineIdx OBJECT-TYPE
    SYNTAX       INTEGER (1)
    MAX-ACCESS   not-accessible
    STATUS       current
    DESCRIPTION  "The line number of the OSC."
    ::= { olOSCEntry 4 }


olOSCAdminStatus OBJECT-TYPE
    SYNTAX       AdminStatus
    MAX-ACCESS   read-write
    STATUS       current
    DESCRIPTION  "The administrative status of the OSC. The default value
                  is autoEnabled if the supporting equipment is enabled
                  or autoEnabled, otherwise it is disabled."
    ::= { olOSCEntry 5 }


olOSCOperStatus OBJECT-TYPE
    SYNTAX       OperStatus
    MAX-ACCESS   read-only
    STATUS       current
    DESCRIPTION  "The reported operational status of the OSC."
    ::= { olOSCEntry 6 }


olOSCOperStatQlfr OBJECT-TYPE
    SYNTAX       OperStatQlfr
    MAX-ACCESS   read-only
    STATUS       current
    DESCRIPTION  "This is a textual list of qualifiers about the reported
                  operational status of the OSC."
    ::= { olOSCEntry 7 }


olOSCAutoEnableTimer OBJECT-TYPE
    SYNTAX       HoursAndMinutes
    MAX-ACCESS   read-write
    STATUS       current
    DESCRIPTION  "Specifies the auto-enable timer for the targeted OSC.
                  This value only applies if the olOSCAdminStatus object
                  is set to autoEnabled, in which case the default value is
                  008-00, otherwise, it is 000-00."
    ::= { olOSCEntry 8 }


olOSCActAutoEnableTimer OBJECT-TYPE
    SYNTAX       HoursAndMinutes
    MAX-ACCESS   read-only
    STATUS       current
    DESCRIPTION  "Indicates the time remaining on the auto-enable timer if
                  it is actively counting down. Otherwise, the value returned
                  is 000-00."
    ::= { olOSCEntry 9 }


olOSCId OBJECT-TYPE
    SYNTAX       DisplayString (SIZE (0..32))
    MAX-ACCESS   read-write
    STATUS       current
    DESCRIPTION  "Textual data recorded by the user to briefly identify the
                  OSC object in a manner useful to the user."
    DEFVAL       { "" }
    ::= { olOSCEntry 10 }


olOSCCustom1 OBJECT-TYPE
    SYNTAX       DisplayString
    MAX-ACCESS   read-write
    STATUS       current
    DESCRIPTION  "A variable length text string for operating company use."
    DEFVAL       { "" }
    ::= { olOSCEntry 11 }


olOSCCustom2 OBJECT-TYPE
    SYNTAX       DisplayString
    MAX-ACCESS   read-write
    STATUS       current
    DESCRIPTION  "A variable length text string for operating company use."
    DEFVAL       { "" }
    ::= { olOSCEntry 12 }


olOSCCustom3 OBJECT-TYPE
    SYNTAX       DisplayString
    MAX-ACCESS   read-write
    STATUS       current
    DESCRIPTION  "A variable length text string for operating company use."
    DEFVAL       { "" }
    ::= { olOSCEntry 13 }


olOSCFEIMMon OBJECT-TYPE
    SYNTAX       INTEGER { enabled  (1),
                           disabled (2) }
    MAX-ACCESS   read-write
    STATUS       current
    DESCRIPTION  "This object is used to control the monitoring of the Far
                  End Node Mismatch Identifier condition. When enabled, the
                  received far-end node identification attributes will be
                  monitored and compared to the expected far-end node
                  identification attribites, and a condition is raised if
                  attributes do no match."
    DEFVAL       { disabled }
    ::= { olOSCEntry 14 }


olOSCExpFESysName OBJECT-TYPE
    SYNTAX       DisplayString (SIZE (0..20))
    MAX-ACCESS   read-write
    STATUS       current
    DESCRIPTION  "The expected far-end node system identifier."
    DEFVAL       { "" }
    ::= { olOSCEntry 15 }


olOSCExpFEIPAddr OBJECT-TYPE
    SYNTAX       IpAddress
    MAX-ACCESS   read-write
    STATUS       current
    DESCRIPTION  "The expected far-end node IP address."
    DEFVAL       { 0 }
    ::= { olOSCEntry 16 }


olOSCExpFEGrp OBJECT-TYPE
    SYNTAX       INTEGER (0..255)
    MAX-ACCESS   read-write
    STATUS       current
    DESCRIPTION  "The expected far-end node optical layer group number."
    DEFVAL       { 0 }
    ::= { olOSCEntry 17 }


olOSCExpFEDegr OBJECT-TYPE
    SYNTAX       INTEGER (0..4)
    MAX-ACCESS   read-write
    STATUS       current
    DESCRIPTION  "The expected far-end node optical layer degree number."
    DEFVAL       { 0 }
    ::= { olOSCEntry 18 }


olOSCFESysName OBJECT-TYPE
    SYNTAX       DisplayString (SIZE (0..20))
    MAX-ACCESS   read-only
    STATUS       current
    DESCRIPTION  "The actual far-end node system identifier."
    ::= { olOSCEntry 19 }


olOSCFEIPAddr OBJECT-TYPE
    SYNTAX       IpAddress
    MAX-ACCESS   read-only
    STATUS       current
    DESCRIPTION  "The actual far-end node IP address."
    ::= { olOSCEntry 20 }


olOSCFEGrp OBJECT-TYPE
    SYNTAX       INTEGER (0..255)
    MAX-ACCESS   read-only
    STATUS       current
    DESCRIPTION  "The actual far-end node optical layer group number."
    ::= { olOSCEntry 21 }


olOSCFEDegr OBJECT-TYPE
    SYNTAX       INTEGER (0..4)
    MAX-ACCESS   read-only
    STATUS       current
    DESCRIPTION  "The actual far-end node optical layer degree number."
    ::= { olOSCEntry 22 }


olOSCFEGrpType OBJECT-TYPE
    SYNTAX       OlGroupType
    MAX-ACCESS   read-only
    STATUS       current
    DESCRIPTION  "The actual far-end node optical layer group
                  configuration type."
    ::= { olOSCEntry 23 }


olOSCRowStatus OBJECT-TYPE
    SYNTAX       RowStatus
    MAX-ACCESS   accessible-for-notify
    STATUS       current
    DESCRIPTION  "The Optical Layer OSC table RowStatus object is not
                  readable or writeable because all entries in the table
                  are automatically created and deleted when the
                  supporting DLA or ROB equipment is provisioned. This
                  optical layer OSC row status object is used only in
                  database change notifications to indicate if the
                  row has been created or deleted."
    ::= { olOSCEntry 100 }



------------------------------------------------------------------------
-- The ODCC table is used to provision and administer the OSC data
-- communications channel on an optical layer OSC object which is used
-- for management communications.
------------------------------------------------------------------------


odccTable OBJECT-TYPE
    SYNTAX       SEQUENCE OF OdccEntry
    MAX-ACCESS   not-accessible
    STATUS       current
    DESCRIPTION  "This table lists all provisioned ODCC objects on
                  equipment modules assigned to optical layer groupings."
    ::= { opticalLayer 7 }


odccEntry OBJECT-TYPE
    SYNTAX       OdccEntry
    MAX-ACCESS   not-accessible
    STATUS       current
    DESCRIPTION  "The conceptual row object of the ODCC table."
    INDEX        { odccCpTypeIdx,  -- CP Type
                   odccShelfIdx,   -- Shelf Num
                   odccSlotIdx,    -- Slot Num
                   odccLineIdx }   -- Line Num
    ::= { odccTable 1 }


OdccEntry ::= SEQUENCE { odccCpTypeIdx    CpType,
                         odccShelfIdx     INTEGER,
                         odccSlotIdx      INTEGER,
                         odccLineIdx      INTEGER,
                         odccAdminStatus  AdminStatus,
                         odccRowStatus    RowStatus }


odccCpTypeIdx OBJECT-TYPE
    SYNTAX       CpType
    MAX-ACCESS   not-accessible
    STATUS       current
    DESCRIPTION  "The type of circuit pack on which the ODCC is located."
    ::= { odccEntry 1 }


odccShelfIdx OBJECT-TYPE
    SYNTAX       INTEGER (1|11|21|31)
    MAX-ACCESS   not-accessible
    STATUS       current
    DESCRIPTION  "The number of the shelf in which the ODCC is located."
    ::= { odccEntry 2 }


odccSlotIdx OBJECT-TYPE
    SYNTAX       INTEGER (1..20)
    MAX-ACCESS   not-accessible
    STATUS       current
    DESCRIPTION  "The number of the slot in which the ODC is located."
    ::= { odccEntry 3 }


odccLineIdx OBJECT-TYPE
    SYNTAX       INTEGER (1)
    MAX-ACCESS   not-accessible
    STATUS       current
    DESCRIPTION  "The line number of the ODCC."
    ::= { odccEntry 4 }


odccAdminStatus OBJECT-TYPE
    SYNTAX       AdminStatus
    MAX-ACCESS   read-create
    STATUS       current
    DESCRIPTION  "The administrative status of the ODCC. The default value
                  is disabled if the supporting ODC is disabled, otherwise
                  it is enabled."
    ::= { odccEntry 5 }


odccRowStatus OBJECT-TYPE
    SYNTAX       RowStatus
    MAX-ACCESS   read-create
    STATUS       current
    DESCRIPTION  "Used to control the addition and deletion of entries in the
                  ODCC table, which in turn controls the provisioning
                  and de-provisioning of ODCC objects."
    ::= { odccEntry 100 }



------------------------------------------------------------------------
-- The WDM table is used to configure and monitor WDM managed
-- objects on equipment modules assigned to optical layer groupings.
------------------------------------------------------------------------


wdmTable OBJECT-TYPE
    SYNTAX       SEQUENCE OF WdmEntry
    MAX-ACCESS   not-accessible
    STATUS       current
    DESCRIPTION  "This table lists all WDM managed objects that
                  have been created on optical layer equipment."
    ::= { opticalLayer 8 }


wdmEntry OBJECT-TYPE
    SYNTAX       WdmEntry
    MAX-ACCESS   not-accessible
    STATUS       current
    DESCRIPTION  "The conceptual row object of the WDM table."
    INDEX        { wdmCpTypeIdx,  -- CP Type
                   wdmShelfIdx,   -- Shelf Num
                   wdmSlotIdx,    -- Slot Num
                   wdmLineIdx }   -- Line Num
    ::= { wdmTable 1 }


WdmEntry ::= SEQUENCE { wdmCpTypeIdx           CpType,
                        wdmShelfIdx            INTEGER,
                        wdmSlotIdx             INTEGER,
                        wdmLineIdx             INTEGER,
                        wdmAdminStatus         AdminStatus,
                        wdmOperStatus          OperStatus,
                        wdmOperStatQlfr        OperStatQlfr,
                        wdmAutoEnableTimer     HoursAndMinutes,
                        wdmActAutoEnableTimer  HoursAndMinutes,
                        wdmId                  DisplayString,
                        wdmCustom1             DisplayString,
                        wdmCustom2             DisplayString,
                        wdmCustom3             DisplayString,
                        wdmFiberType           INTEGER,
                        wdmSpanLength          Unsigned32,
                        wdmSpanLossRxHighTh    FixedX10,
                        wdmSpanLossSpecMax     FixedX10,
                        wdmNumChannels         INTEGER,
                        wdmRowStatus           RowStatus }


wdmCpTypeIdx OBJECT-TYPE
    SYNTAX       CpType
    MAX-ACCESS   not-accessible
    STATUS       current
    DESCRIPTION  "The type of circuit pack on which the WDM is located."
    ::= { wdmEntry 1 }


wdmShelfIdx OBJECT-TYPE
    SYNTAX       INTEGER (1|11|21|31)
    MAX-ACCESS   not-accessible
    STATUS       current
    DESCRIPTION  "The number of the shelf in which the WDM is located."
    ::= { wdmEntry 2 }


wdmSlotIdx OBJECT-TYPE
    SYNTAX       INTEGER (1..20)
    MAX-ACCESS   not-accessible
    STATUS       current
    DESCRIPTION  "The number of the slot in which the WDM is located."
    ::= { wdmEntry 3 }


wdmLineIdx OBJECT-TYPE
    SYNTAX       INTEGER (1)
    MAX-ACCESS   not-accessible
    STATUS       current
    DESCRIPTION  "The line number of the WDM."
    ::= { wdmEntry 4 }


wdmAdminStatus OBJECT-TYPE
    SYNTAX       AdminStatus
    MAX-ACCESS   read-write
    STATUS       current
    DESCRIPTION  "The administrative status of the WDM. The default value
                  is autoEnabled if the supporting equipment is enabled
                  or autoEnabled, otherwise it is disabled."
    ::= { wdmEntry 5 }


wdmOperStatus OBJECT-TYPE
    SYNTAX       OperStatus
    MAX-ACCESS   read-only
    STATUS       current
    DESCRIPTION  "The reported operational status of the WDM."
    ::= { wdmEntry 6 }


wdmOperStatQlfr OBJECT-TYPE
    SYNTAX       OperStatQlfr
    MAX-ACCESS   read-only
    STATUS       current
    DESCRIPTION  "This is a textual list of qualifiers about the reported
                  operational status of the WDM."
    ::= { wdmEntry 7 }


wdmAutoEnableTimer OBJECT-TYPE
    SYNTAX       HoursAndMinutes
    MAX-ACCESS   read-write
    STATUS       current
    DESCRIPTION  "Specifies the auto-enable timer for the targeted WDM.
                  This value only applies if the wdmAdminStatus object
                  is set to autoEnabled, in which case the default value is
                  008-00, otherwise, it is 000-00."
    ::= { wdmEntry 8 }


wdmActAutoEnableTimer OBJECT-TYPE
    SYNTAX       HoursAndMinutes
    MAX-ACCESS   read-only
    STATUS       current
    DESCRIPTION  "Indicates the time remaining on the auto-enable timer if
                  it is actively counting down. Otherwise, the value returned
                  is 000-00."
    ::= { wdmEntry 9 }


wdmId OBJECT-TYPE
    SYNTAX       DisplayString (SIZE (0..32))
    MAX-ACCESS   read-write
    STATUS       current
    DESCRIPTION  "Textual data recorded by the user to briefly identify the
                  WDM object in a manner useful to the user."
    DEFVAL       { "" }
    ::= { wdmEntry 10 }


wdmCustom1 OBJECT-TYPE
    SYNTAX       DisplayString
    MAX-ACCESS   read-write
    STATUS       current
    DESCRIPTION  "A variable length text string for operating company use."
    DEFVAL       { "" }
    ::= { wdmEntry 11 }


wdmCustom2 OBJECT-TYPE
    SYNTAX       DisplayString
    MAX-ACCESS   read-write
    STATUS       current
    DESCRIPTION  "A variable length text string for operating company use."
    DEFVAL       { "" }
    ::= { wdmEntry 12 }


wdmCustom3 OBJECT-TYPE
    SYNTAX       DisplayString
    MAX-ACCESS   read-write
    STATUS       current
    DESCRIPTION  "A variable length text string for operating company use."
    DEFVAL       { "" }
    ::= { wdmEntry 13 }


wdmFiberType OBJECT-TYPE
    SYNTAX       INTEGER { smf (1) }
    MAX-ACCESS   read-write
    STATUS       current
    DESCRIPTION  "The fiber type of the span fiber."
    DEFVAL       { smf }
    ::= { wdmEntry 14 }


wdmSpanLength OBJECT-TYPE
    SYNTAX       Unsigned32
    UNITS        "kilometers"
    MAX-ACCESS   read-only
    STATUS       current
    DESCRIPTION  "The measured length of the receive span fiber."
    ::= { wdmEntry 15 }


wdmSpanLossRxHighTh OBJECT-TYPE
    SYNTAX       FixedX10
    UNITS        "dB/10"
    MAX-ACCESS   read-write
    STATUS       current
    DESCRIPTION  "The high threshold setting for the loss on the receive
                  fiber of the Line span. The setting for this object is
                  used to evaluate the olPortLossRxHighThCond trap. When
                  the value of this object is set to 0, the
                  olPortLossRxHighThCond trap is disabled."
    ::= { wdmEntry 16 }


wdmSpanLossSpecMax OBJECT-TYPE
    SYNTAX       FixedX10
    UNITS        "dB/10"
    MAX-ACCESS   read-only
    STATUS       current
    DESCRIPTION  "The specified maximum supported loss on the Line span.
                  The value of this object is dependent on the optical
                  layer group configurations of the local and far-end nodes."
    ::= { wdmEntry 17 }


wdmNumChannels OBJECT-TYPE
    SYNTAX       INTEGER (0..44)
    MAX-ACCESS   read-only
    STATUS       current
    DESCRIPTION  "The actual number of channels that the WDM is currently
                  provisioned to carry."
    ::= { wdmEntry 18 }


wdmRowStatus OBJECT-TYPE
    SYNTAX       RowStatus
    MAX-ACCESS   accessible-for-notify
    STATUS       current
    DESCRIPTION  "The WDM table RowStatus object is not readable or
                  writeable because all entries in the table are
                  automatically created and deleted when the supporting
                  DLA or ROB circuit pack is assigned and unassigned
                  to an optical layer grouping. This WDM row status
                  object is used only in database change notifications
                  to indicate if the row has been created or deleted."
    ::= { wdmEntry 100 }



------------------------------------------------------------------------
-- The Wavelength Channel Cross Connection table is used to provision
-- and retrieve wavelength channel cross-connections. Wavelength channel
-- cross-connections are configured to route add/drop and pass-through
-- optical channels through ROB-equipped optical layer groupings.
------------------------------------------------------------------------


wchXCTable OBJECT-TYPE
    SYNTAX       SEQUENCE OF WchXCEntry
    MAX-ACCESS   not-accessible
    STATUS       current
    DESCRIPTION  "This table lists all configured wavelength channel
                  cross-connections configured on optical layer equipment."
    ::= { opticalLayer 9 }


wchXCEntry OBJECT-TYPE
    SYNTAX       WchXCEntry
    MAX-ACCESS   not-accessible
    STATUS       current
    DESCRIPTION  "The conceptual row object of the wavelength channel
                  cross-connection table."
    INDEX        { wchXCSrcCpTypeIdx,    -- Source CP Type
                   wchXCSrcShelfIdx,     -- Source Shelf Num
                   wchXCSrcSlotIdx,      -- Source Slot Num
                   wchXCSrcPortTypeIdx,  -- Source Port Type
                   wchXCSrcPortIdx,      -- Source Port Num
                   wchXCSrcChannelIdx,   -- Source Channel Num
                   wchXCDstCpTypeIdx,    -- Destination CP Type
                   wchXCDstShelfIdx,     -- Destination Shelf Num
                   wchXCDstSlotIdx,      -- Destination Slot Num
                   wchXCDstPortTypeIdx,  -- Destination Port Type
                   wchXCDstPortIdx,      -- Destination Port Num
                   wchXCDstChannelIdx }  -- Destination Channel Num
    ::= { wchXCTable 1 }


WchXCEntry ::= SEQUENCE { wchXCSrcCpTypeIdx   CpType,
                          wchXCSrcShelfIdx    INTEGER,
                          wchXCSrcSlotIdx     INTEGER,
                          wchXCSrcPortTypeIdx OlPortType,
                          wchXCSrcPortIdx     INTEGER,
                          wchXCSrcChannelIdx  INTEGER,
                          wchXCDstCpTypeIdx   CpType,
                          wchXCDstShelfIdx    INTEGER,
                          wchXCDstSlotIdx     INTEGER,
                          wchXCDstPortTypeIdx OlPortType,
                          wchXCDstPortIdx     INTEGER,
                          wchXCDstChannelIdx  INTEGER,
                          wchXCServiceName    DisplayString,
                          wchXCRowStatus      RowStatus }


wchXCSrcCpTypeIdx OBJECT-TYPE
    SYNTAX       CpType
    MAX-ACCESS   not-accessible
    STATUS       current
    DESCRIPTION  "The type of circuit pack on which the source wavelength
                  channel of the cross-connection is located."
    ::= { wchXCEntry 1 }


wchXCSrcShelfIdx OBJECT-TYPE
    SYNTAX       INTEGER (0|1|11|21|31)
    MAX-ACCESS   not-accessible
    STATUS       current
    DESCRIPTION  "The number of the shelf on which the source wavelength
                  channel of the cross-connection is located."
    ::= { wchXCEntry 2 }


wchXCSrcSlotIdx OBJECT-TYPE
    SYNTAX       INTEGER (1..255)
    MAX-ACCESS   not-accessible
    STATUS       current
    DESCRIPTION  "The number of the slot on which the source wavelength
                  channel of the cross-connection is located."
    ::= { wchXCEntry 3 }


wchXCSrcPortTypeIdx OBJECT-TYPE
    SYNTAX       OlPortType
    MAX-ACCESS   not-accessible
    STATUS       current
    DESCRIPTION  "The type of port on which the source wavelength channel
                  of the cross-connection is located."
    ::= { wchXCEntry 4 }


wchXCSrcPortIdx OBJECT-TYPE
    SYNTAX       INTEGER (1..600)
    MAX-ACCESS   not-accessible
    STATUS       current
    DESCRIPTION  "The number of the port on which the source wavelength channel
                  of the cross-connection is located."
    ::= { wchXCEntry 5 }


wchXCSrcChannelIdx OBJECT-TYPE
    SYNTAX       INTEGER (135..610)
    MAX-ACCESS   not-accessible
    STATUS       current
    DESCRIPTION  "The channel number of the source wavelength channel of the
                  cross-connection."
    ::= { wchXCEntry 6 }


wchXCDstCpTypeIdx OBJECT-TYPE
    SYNTAX       CpType
    MAX-ACCESS   not-accessible
    STATUS       current
    DESCRIPTION  "The type of circuit pack on which the destination wavelength
                  channel of the cross-connection is located."
    ::= { wchXCEntry 7 }


wchXCDstShelfIdx OBJECT-TYPE
    SYNTAX       INTEGER (0|1|11|21|31)
    MAX-ACCESS   not-accessible
    STATUS       current
    DESCRIPTION  "The number of the shelf on which the destination wavelength
                  channel of the cross-connection is located."
    ::= { wchXCEntry 8 }


wchXCDstSlotIdx OBJECT-TYPE
    SYNTAX       INTEGER (1..255)
    MAX-ACCESS   not-accessible
    STATUS       current
    DESCRIPTION  "The number of the slot on which the destination wavelength
                  channel of the cross-connection is located."
    ::= { wchXCEntry 9 }


wchXCDstPortTypeIdx OBJECT-TYPE
    SYNTAX       OlPortType
    MAX-ACCESS   not-accessible
    STATUS       current
    DESCRIPTION  "The type of port on which the destination wavelength channel
                  of the cross-connection is located."
    ::= { wchXCEntry 10 }


wchXCDstPortIdx OBJECT-TYPE
    SYNTAX       INTEGER (1..600)
    MAX-ACCESS   not-accessible
    STATUS       current
    DESCRIPTION  "The number of the port on which the destination wavelength
                  channel of the cross-connection is located."
    ::= { wchXCEntry 11 }


wchXCDstChannelIdx OBJECT-TYPE
    SYNTAX       INTEGER (135..610)
    MAX-ACCESS   not-accessible
    STATUS       current
    DESCRIPTION  "The channel number of the destination wavelength channel
                  of the cross-connection."
    ::= { wchXCEntry 12 }


wchXCServiceName OBJECT-TYPE
    SYNTAX       DisplayString (SIZE (0..32))
    MAX-ACCESS   read-create
    STATUS       current
    DESCRIPTION  "Name of end-to-end wavelength service of which this cross-
                  connection is a part."
    DEFVAL       { "" }
    ::= { wchXCEntry 13 }


wchXCRowStatus OBJECT-TYPE
    SYNTAX       RowStatus
    MAX-ACCESS   read-create
    STATUS       current
    DESCRIPTION  "Used to control the addition and deletion of entries
                  in the wavelength channel cross-connection table."
    ::= { wchXCEntry 100 }



------------------------------------------------------------------------
-- The Wavelength Channel table is used to manage wavelength channel
-- objects which support provisioned wavelength channel cross-connections.
------------------------------------------------------------------------

wchTable OBJECT-TYPE
    SYNTAX       SEQUENCE OF WchEntry
    MAX-ACCESS   not-accessible
    STATUS       current
    DESCRIPTION  "This table lists all managed wavelength channels on
                  equipment modules assigned to optical layer groupings."
    ::= { opticalLayer 10 }


wchEntry OBJECT-TYPE
    SYNTAX       WchEntry
    MAX-ACCESS   not-accessible
    STATUS       current
    DESCRIPTION  "The conceptual row object of the wavelength channel
                  table."
    INDEX        { wchCpTypeIdx,   -- CP Type
                   wchShelfIdx,    -- Shelf Num
                   wchSlotIdx,     -- Slot Num
                   wchPortTypeIdx, -- Port Type
                   wchPortIdx,     -- Port Num
                   wchIdx }        -- Channel Num
    ::= { wchTable 1 }


WchEntry ::= SEQUENCE { wchCpTypeIdx           CpType,
                        wchShelfIdx            INTEGER,
                        wchSlotIdx             INTEGER,
                        wchPortTypeIdx         OlPortType,
                        wchPortIdx             INTEGER,
                        wchIdx                 INTEGER,
                        wchAdminStatus         AdminStatus,
                        wchOperStatus          OperStatus,
                        wchOperStatQlfr        OperStatQlfr,
                        wchAutoEnableTimer     HoursAndMinutes,
                        wchActAutoEnableTimer  HoursAndMinutes,
                        wchId                  DisplayString,
                        wchCustom1             DisplayString,
                        wchCustom2             DisplayString,
                        wchCustom3             DisplayString,
                        wchBitrate             INTEGER,
                        wchGrid                INTEGER,
                        wchWavelength          FixedX100,
                        wchFrequency           FixedX100,
                        wchRowStatus           RowStatus }


wchCpTypeIdx OBJECT-TYPE
    SYNTAX       CpType
    MAX-ACCESS   not-accessible
    STATUS       current
    DESCRIPTION  "The type of circuit pack on which the wavelength channel
                  is located."
    ::= { wchEntry 1 }


wchShelfIdx OBJECT-TYPE
    SYNTAX       INTEGER (1|11|21|31)
    MAX-ACCESS   not-accessible
    STATUS       current
    DESCRIPTION  "The number of the shelf on which the wavelength channel
                  is located."
    ::= { wchEntry 2 }


wchSlotIdx OBJECT-TYPE
    SYNTAX       INTEGER (1..20)
    MAX-ACCESS   not-accessible
    STATUS       current
    DESCRIPTION  "The number of the slot on which the wavelength channel
                  is located."
    ::= { wchEntry 3 }


wchPortTypeIdx OBJECT-TYPE
    SYNTAX       OlPortType
    MAX-ACCESS   not-accessible
    STATUS       current
    DESCRIPTION  "The type of port on which the wavelength channel is
                  located."
    ::= { wchEntry 4 }


wchPortIdx OBJECT-TYPE
    SYNTAX       INTEGER (1..4)
    MAX-ACCESS   not-accessible
    STATUS       current
    DESCRIPTION  "The number of the port on which the wavelength channel
                  is located."
    ::= { wchEntry 5 }


wchIdx OBJECT-TYPE
    SYNTAX       INTEGER (135..610)
    MAX-ACCESS   not-accessible
    STATUS       current
    DESCRIPTION  "The number of the targeted wavelength channel."
    ::= { wchEntry 6 }


wchAdminStatus OBJECT-TYPE
    SYNTAX       AdminStatus
    MAX-ACCESS   read-write
    STATUS       current
    DESCRIPTION  "The administrative status of the wavelength channel.
                  The default value is autoEnabled if the supporting WDM
                  is enabled or autoEnabled, otherwise it is disabled."
    ::= { wchEntry 7 }


wchOperStatus OBJECT-TYPE
    SYNTAX       OperStatus
    MAX-ACCESS   read-only
    STATUS       current
    DESCRIPTION  "The reported operational status of the wavelength channel."
    ::= { wchEntry 8 }


wchOperStatQlfr OBJECT-TYPE
    SYNTAX       OperStatQlfr
    MAX-ACCESS   read-only
    STATUS       current
    DESCRIPTION  "This is a textual list of qualifiers about the reported
                  operational status of the wavelength channel."
    ::= { wchEntry 9 }


wchAutoEnableTimer OBJECT-TYPE
    SYNTAX       HoursAndMinutes
    MAX-ACCESS   read-write
    STATUS       current
    DESCRIPTION  "Specifies the auto-enable timer for the targeted wavelength
                  channel. This value only applies if the wchAdminStatus object
                  is set to autoEnabled, in which case the default value is
                  008-00, otherwise, it is 000-00."
    ::= { wchEntry 10 }


wchActAutoEnableTimer OBJECT-TYPE
    SYNTAX       HoursAndMinutes
    MAX-ACCESS   read-only
    STATUS       current
    DESCRIPTION  "Indicates the time remaining on the auto-enable timer if
                  it is actively counting down. Otherwise, the value returned
                  is 000-00."
    ::= { wchEntry 11 }


wchId OBJECT-TYPE
    SYNTAX       DisplayString (SIZE (0..32))
    MAX-ACCESS   read-write
    STATUS       current
    DESCRIPTION  "Textual data recorded by the user to briefly identify the
                  wavelength channel object in a manner useful to the user."
    DEFVAL       { "" }
    ::= { wchEntry 12 }


wchCustom1 OBJECT-TYPE
    SYNTAX       DisplayString
    MAX-ACCESS   read-write
    STATUS       current
    DESCRIPTION  "A variable length text string for operating company use."
    DEFVAL       { "" }
    ::= { wchEntry 13 }


wchCustom2 OBJECT-TYPE
    SYNTAX       DisplayString
    MAX-ACCESS   read-write
    STATUS       current
    DESCRIPTION  "A variable length text string for operating company use."
    DEFVAL       { "" }
    ::= { wchEntry 14 }


wchCustom3 OBJECT-TYPE
    SYNTAX       DisplayString
    MAX-ACCESS   read-write
    STATUS       current
    DESCRIPTION  "A variable length text string for operating company use."
    DEFVAL       { "" }
    ::= { wchEntry 15 }


wchBitrate OBJECT-TYPE
    SYNTAX       INTEGER { tenGig (1) }
    MAX-ACCESS   read-write
    STATUS       current
    DESCRIPTION  "The bitrate of the signal carried by the wavelength channel.
                  A value of tenGig applies to all signal bitrates of
                  10Gb/sec or less."
    DEFVAL       { tenGig }
    ::= { wchEntry 16 }


wchGrid OBJECT-TYPE
    SYNTAX       INTEGER { ghz100 (1),
                           ghz50  (2) }
    MAX-ACCESS   read-write
    STATUS       current
    DESCRIPTION  "The minimum grid spacing with which the channel is compatible."
    DEFVAL       { ghz100 }
    ::= { wchEntry 17 }


wchWavelength OBJECT-TYPE
    SYNTAX       FixedX100
    UNITS        "nanometers/100"
    MAX-ACCESS   read-only
    STATUS       current
    DESCRIPTION  "The wavelength of the channel."
    ::= { wchEntry 18 }


wchFrequency OBJECT-TYPE
    SYNTAX       FixedX100
    UNITS        "terahertz/100"
    MAX-ACCESS   read-only
    STATUS       current
    DESCRIPTION  "The frequency of the channel."
    ::= { wchEntry 19 }


wchRowStatus OBJECT-TYPE
    SYNTAX       RowStatus
    MAX-ACCESS   accessible-for-notify
    STATUS       current
    DESCRIPTION  "The Wavelength Channel table RowStatus object is not readable or
                  writeable because all entries in the Wavelength Channel table are
                  automatically created and deleted when an wavelength channel
                  cross-connection involving the wavelength channel is created or
                  deleted. This Wavelength Channel row status object is used only
                  in database change notifications to indicate if the row has
                  been created or deleted."
    ::= { wchEntry 100 }


------------------------------------------------------------------------
-- The objects of the Optical Layer Group Merge branch are used to invoke
-- an optical layer group merge operation.
------------------------------------------------------------------------

olGroupMerge OBJECT IDENTIFIER ::= { opticalLayer 11 }

olGroupMergeCmd OBJECT-TYPE
    SYNTAX       INTEGER { idle   (1),
                           invoke (2) }
    MAX-ACCESS   read-write
    STATUS       current
    DESCRIPTION  "This object is used to invoke an optical layer group
                  merge operation. The optical layer group merge is
                  activated when this object is set to invoke(2). The
                  values of the olGroupMergePrimary and olGroupMergeSecondary
                  objects must be set in the same set request as this object.
                  When a get is performed on this object, the value returned
                  is idle(1)."
    ::= { olGroupMerge 1 }


olGroupMergePrimary OBJECT-TYPE
    SYNTAX       INTEGER (1..255)
    MAX-ACCESS   read-write
    STATUS       current
    DESCRIPTION  "The identifier of the primary optical layer group
                  of the merge."
    ::= { olGroupMerge 2 }


olGroupMergeSecondary OBJECT-TYPE
    SYNTAX       INTEGER (1..255)
    MAX-ACCESS   read-write
    STATUS       current
    DESCRIPTION  "The identifier of the secondary optical layer group
                  of the merge."
    ::= { olGroupMerge 3 }


------------------------------------------------------------------------
-- The Optical Layer Performance branch contains all tables used to
-- access performance monitoring measurements and configuration for
-- monitored optical layer objects.
------------------------------------------------------------------------

olPerformance OBJECT IDENTIFIER ::= { opticalLayer 12 }


-----------------------------------------------------------------------
-- Objects used to retrieve current optical layer OSC
-- Performance Monitoring statistics.
-----------------------------------------------------------------------


olOSCCrntPMTable OBJECT-TYPE
    SYNTAX       SEQUENCE OF OlOSCCrntPMEntry
    MAX-ACCESS   not-accessible
    STATUS       current
    DESCRIPTION  "A table of current performance monitoring statistics
                  collected for the optical layer OSC objects on the NE."
    ::= { olPerformance 1 }


olOSCCrntPMEntry OBJECT-TYPE
    SYNTAX       OlOSCCrntPMEntry
    MAX-ACCESS   not-accessible
    STATUS       current
    DESCRIPTION  "The row entry object of the optical layer OSC current
                  performance monitoring table. Each row of this table
                  contains a full set of PM statistics and related data
                  for a current measurement interval for a given optical
                  layer OSC object."
    INDEX        { olOSCCrntPMCpTypeIdx,
                   olOSCCrntPMShelfIdx,
                   olOSCCrntPMSlotIdx,
                   olOSCCrntPMLineIdx,
                   olOSCCrntPMIntervalTypeIdx }
    ::= { olOSCCrntPMTable 1 }


OlOSCCrntPMEntry ::= SEQUENCE { olOSCCrntPMCpTypeIdx               CpType,
                                olOSCCrntPMShelfIdx                INTEGER,
                                olOSCCrntPMSlotIdx                 INTEGER,
                                olOSCCrntPMLineIdx                 INTEGER,
                                olOSCCrntPMIntervalTypeIdx         PMIntervalType,
                                olOSCCrntPMOPRValue                FixedX10,
                                olOSCCrntPMOPRTimeStamp            DateAndTime,
                                olOSCCrntPMOPRValidity             PMValidity,
                                olOSCCrntPMOPTValue                FixedX10,
                                olOSCCrntPMOPTTimeStamp            DateAndTime,
                                olOSCCrntPMOPTValidity             PMValidity,
                                olOSCCrntPMOBRValue                FixedX10,
                                olOSCCrntPMOBRTimeStamp            DateAndTime,
                                olOSCCrntPMOBRValidity             PMValidity,
                                olOSCCrntPMCVSValue                Unsigned32,
                                olOSCCrntPMCVSTimeStamp            DateAndTime,
                                olOSCCrntPMCVSValidity             PMValidity,
                                olOSCCrntPMCVSInitialize           InitializeCmd,
                                olOSCCrntPMESSValue                Unsigned32,
                                olOSCCrntPMESSTimeStamp            DateAndTime,
                                olOSCCrntPMESSValidity             PMValidity,
                                olOSCCrntPMESSInitialize           InitializeCmd,
                                olOSCCrntPMSESSValue               Unsigned32,
                                olOSCCrntPMSESSTimeStamp           DateAndTime,
                                olOSCCrntPMSESSValidity            PMValidity,
                                olOSCCrntPMSESSInitialize          InitializeCmd,
                                olOSCCrntPMSEFSSValue              Unsigned32,
                                olOSCCrntPMSEFSSTimeStamp          DateAndTime,
                                olOSCCrntPMSEFSSValidity           PMValidity,
                                olOSCCrntPMSEFSSInitialize         InitializeCmd,
                                olOSCCrntPMUASSValue               Unsigned32,
                                olOSCCrntPMUASSTimeStamp           DateAndTime,
                                olOSCCrntPMUASSValidity            PMValidity,
                                olOSCCrntPMUASSInitialize          InitializeCmd }


olOSCCrntPMCpTypeIdx OBJECT-TYPE
    SYNTAX       CpType
    MAX-ACCESS   not-accessible
    STATUS       current
    DESCRIPTION  "The type of circuit pack on which the optical layer OSC
                  targeted for PMs is located."
    ::= { olOSCCrntPMEntry 1 }


olOSCCrntPMShelfIdx OBJECT-TYPE
    SYNTAX       INTEGER (1|11|21|31)
    MAX-ACCESS   not-accessible
    STATUS       current
    DESCRIPTION  "The number of the shelf in which the optical layer OSC
                  targeted for PMs is located."
    ::= { olOSCCrntPMEntry 2 }


olOSCCrntPMSlotIdx OBJECT-TYPE
    SYNTAX       INTEGER (1..20)
    MAX-ACCESS   not-accessible
    STATUS       current
    DESCRIPTION  "The number of the slot in which the optical layer OSC
                  targeted for PMs is located."
    ::= { olOSCCrntPMEntry 3 }


olOSCCrntPMLineIdx OBJECT-TYPE
    SYNTAX       INTEGER (1)
    MAX-ACCESS   not-accessible
    STATUS       current
    DESCRIPTION  "The line number of the OSC targeted for PMs."
    ::= { olOSCCrntPMEntry 4 }


olOSCCrntPMIntervalTypeIdx OBJECT-TYPE
    SYNTAX       PMIntervalType
    MAX-ACCESS   not-accessible
    STATUS       current
    DESCRIPTION  "The type of PM bin according to interval length."
    ::= { olOSCCrntPMEntry 5 }


olOSCCrntPMOPRValue OBJECT-TYPE
    SYNTAX       FixedX10
    UNITS        "dBm/10"
    MAX-ACCESS   read-only
    STATUS       current
    DESCRIPTION  "The OSC optical power received on the Line port."
    ::= { olOSCCrntPMEntry 6 }


olOSCCrntPMOPRTimeStamp OBJECT-TYPE
    SYNTAX       DateAndTime
    MAX-ACCESS   read-only
    STATUS       current
    DESCRIPTION  "The date and time stamp of the optical power received value."
    ::= { olOSCCrntPMEntry 7 }


olOSCCrntPMOPRValidity OBJECT-TYPE
    SYNTAX       PMValidity
    MAX-ACCESS   read-only
    STATUS       current
    DESCRIPTION  "Indicates the validity of the provided optical power received
                  value."
    ::= { olOSCCrntPMEntry 8 }


olOSCCrntPMOPTValue OBJECT-TYPE
    SYNTAX       FixedX10
    UNITS        "dBm/10"
    MAX-ACCESS   read-only
    STATUS       current
    DESCRIPTION  "The OSC optical power transmitted at the output of the
                  Line port."
    ::= { olOSCCrntPMEntry 9 }


olOSCCrntPMOPTTimeStamp OBJECT-TYPE
    SYNTAX       DateAndTime
    MAX-ACCESS   read-only
    STATUS       current
    DESCRIPTION  "The date and time stamp of the optical power transmitted
                  value."
    ::= { olOSCCrntPMEntry 10 }


olOSCCrntPMOPTValidity OBJECT-TYPE
    SYNTAX       PMValidity
    MAX-ACCESS   read-only
    STATUS       current
    DESCRIPTION  "Indicates the validity of the provided optical power
                  transmitted value."
    ::= { olOSCCrntPMEntry 11 }


olOSCCrntPMOBRValue OBJECT-TYPE
    SYNTAX       FixedX10
    UNITS        "dB/10"
    MAX-ACCESS   read-only
    STATUS       current
    DESCRIPTION  "The OSC optical back-reflected power."
    ::= { olOSCCrntPMEntry 12 }


olOSCCrntPMOBRTimeStamp OBJECT-TYPE
    SYNTAX       DateAndTime
    MAX-ACCESS   read-only
    STATUS       current
    DESCRIPTION  "The date and time stamp of the optical back-reflected
                  power value."
    ::= { olOSCCrntPMEntry 13 }


olOSCCrntPMOBRValidity OBJECT-TYPE
    SYNTAX       PMValidity
    MAX-ACCESS   read-only
    STATUS       current
    DESCRIPTION  "Indicates the validity of the provided optical back-reflected
                  power value."
    ::= { olOSCCrntPMEntry 14 }


olOSCCrntPMCVSValue OBJECT-TYPE
    SYNTAX       Unsigned32
    MAX-ACCESS   read-write
    STATUS       current
    DESCRIPTION  "The count of coding violations at the section layer of
                  the received OSC signal."
    ::= { olOSCCrntPMEntry 15 }


olOSCCrntPMCVSTimeStamp OBJECT-TYPE
    SYNTAX       DateAndTime
    MAX-ACCESS   read-only
    STATUS       current
    DESCRIPTION  "The date and time stamp of the section layer coding violations
                  value."
    ::= { olOSCCrntPMEntry 16 }


olOSCCrntPMCVSValidity OBJECT-TYPE
    SYNTAX       PMValidity
    MAX-ACCESS   read-only
    STATUS       current
    DESCRIPTION  "Indicates the validity of the provided section layer coding
                  violations value."
    ::= { olOSCCrntPMEntry 17 }


olOSCCrntPMCVSInitialize OBJECT-TYPE
    SYNTAX       InitializeCmd
    MAX-ACCESS   read-write
    STATUS       current
    DESCRIPTION  "Used to initialize the value of the olOSCCrntPMCVSValue object
                  to 0."
    ::= { olOSCCrntPMEntry 18 }


olOSCCrntPMESSValue OBJECT-TYPE
    SYNTAX       Unsigned32
    MAX-ACCESS   read-write
    STATUS       current
    DESCRIPTION  "The count of errored seconds at the section layer of
                  the received OSC signal."
    ::= { olOSCCrntPMEntry 19 }


olOSCCrntPMESSTimeStamp OBJECT-TYPE
    SYNTAX       DateAndTime
    MAX-ACCESS   read-only
    STATUS       current
    DESCRIPTION  "The date and time stamp of the section layer errored seconds
                  value."
    ::= { olOSCCrntPMEntry 20 }


olOSCCrntPMESSValidity OBJECT-TYPE
    SYNTAX       PMValidity
    MAX-ACCESS   read-only
    STATUS       current
    DESCRIPTION  "Indicates the validity of the provided section layer errored
                  seconds value."
    ::= { olOSCCrntPMEntry 21 }


olOSCCrntPMESSInitialize OBJECT-TYPE
    SYNTAX       InitializeCmd
    MAX-ACCESS   read-write
    STATUS       current
    DESCRIPTION  "Used to initialize the value of the olOSCCrntPMESSValue object
                  to 0."
    ::= { olOSCCrntPMEntry 22 }


olOSCCrntPMSESSValue OBJECT-TYPE
    SYNTAX       Unsigned32
    MAX-ACCESS   read-write
    STATUS       current
    DESCRIPTION  "The count of severely errored seconds at the section layer
                  of the received OSC signal."
    ::= { olOSCCrntPMEntry 23 }


olOSCCrntPMSESSTimeStamp OBJECT-TYPE
    SYNTAX       DateAndTime
    MAX-ACCESS   read-only
    STATUS       current
    DESCRIPTION  "The date and time stamp of the section layer severely errored
                  seconds value."
    ::= { olOSCCrntPMEntry 24 }


olOSCCrntPMSESSValidity OBJECT-TYPE
    SYNTAX       PMValidity
    MAX-ACCESS   read-only
    STATUS       current
    DESCRIPTION  "Indicates the validity of the provided section layer severely
                  errored seconds value."
    ::= { olOSCCrntPMEntry 25 }


olOSCCrntPMSESSInitialize OBJECT-TYPE
    SYNTAX       InitializeCmd
    MAX-ACCESS   read-write
    STATUS       current
    DESCRIPTION  "Used to initialize the value of the olOSCCrntPMSESSValue object
                  to 0."
    ::= { olOSCCrntPMEntry 26 }


olOSCCrntPMSEFSSValue OBJECT-TYPE
    SYNTAX       Unsigned32
    MAX-ACCESS   read-write
    STATUS       current
    DESCRIPTION  "The count of severely errored framing seconds at the section
                  layer of the received OSC signal."
    ::= { olOSCCrntPMEntry 27 }


olOSCCrntPMSEFSSTimeStamp OBJECT-TYPE
    SYNTAX       DateAndTime
    MAX-ACCESS   read-only
    STATUS       current
    DESCRIPTION  "The date and time stamp of the section layer severely errored
                  framing seconds value."
    ::= { olOSCCrntPMEntry 28 }


olOSCCrntPMSEFSSValidity OBJECT-TYPE
    SYNTAX       PMValidity
    MAX-ACCESS   read-only
    STATUS       current
    DESCRIPTION  "Indicates the validity of the provided section layer severely
                  errored framing seconds value."
    ::= { olOSCCrntPMEntry 29 }


olOSCCrntPMSEFSSInitialize OBJECT-TYPE
    SYNTAX       InitializeCmd
    MAX-ACCESS   read-write
    STATUS       current
    DESCRIPTION  "Used to initialize the value of the olOSCCrntPMSEFSSValue object
                  to 0."
    ::= { olOSCCrntPMEntry 30 }


olOSCCrntPMUASSValue OBJECT-TYPE
    SYNTAX       Unsigned32
    MAX-ACCESS   read-write
    STATUS       current
    DESCRIPTION  "The count of unavailable seconds at the section layer
                  of the received OSC signal."
    ::= { olOSCCrntPMEntry 31 }


olOSCCrntPMUASSTimeStamp OBJECT-TYPE
    SYNTAX       DateAndTime
    MAX-ACCESS   read-only
    STATUS       current
    DESCRIPTION  "The date and time stamp of the section layer unavailable
                  seconds value."
    ::= { olOSCCrntPMEntry 32 }


olOSCCrntPMUASSValidity OBJECT-TYPE
    SYNTAX       PMValidity
    MAX-ACCESS   read-only
    STATUS       current
    DESCRIPTION  "Indicates the validity of the provided section layer unavailable
                  seconds value."
    ::= { olOSCCrntPMEntry 33 }


olOSCCrntPMUASSInitialize OBJECT-TYPE
    SYNTAX       InitializeCmd
    MAX-ACCESS   read-write
    STATUS       current
    DESCRIPTION  "Used to initialize the value of the olOSCCrntPMUASSValue
                  object to 0."
    ::= { olOSCCrntPMEntry 34 }



-----------------------------------------------------------------------
-- Objects used to retrieve historical Optical Layer OSC
-- Performance Monitoring statistics.
-----------------------------------------------------------------------


olOSCHistPMTable OBJECT-TYPE
    SYNTAX       SEQUENCE OF OlOSCHistPMEntry
    MAX-ACCESS   not-accessible
    STATUS       current
    DESCRIPTION  "A table of historical performance monitoring statistics
                  collected for the optical layer OSC objects on the NE."
    ::= { olPerformance 2 }


olOSCHistPMEntry OBJECT-TYPE
    SYNTAX       OlOSCHistPMEntry
    MAX-ACCESS   not-accessible
    STATUS       current
    DESCRIPTION  "The row entry object of the optical layer OSC historical
                  performance monitoring table. Each row of this table
                  contains a full set of PM statistics and related data
                  for a historical measurement interval for a given optical
                  layer OSC object."
    INDEX        { olOSCHistPMCpTypeIdx,
                   olOSCHistPMShelfIdx,
                   olOSCHistPMSlotIdx,
                   olOSCHistPMLineIdx,
                   olOSCHistPMIntervalTypeIdx,
                   olOSCHistPMIntervalIdx }
    ::= { olOSCHistPMTable 1 }


OlOSCHistPMEntry ::= SEQUENCE { olOSCHistPMCpTypeIdx               CpType,
                                olOSCHistPMShelfIdx                INTEGER,
                                olOSCHistPMSlotIdx                 INTEGER,
                                olOSCHistPMLineIdx                 INTEGER,
                                olOSCHistPMIntervalTypeIdx         PMIntervalType,
                                olOSCHistPMIntervalIdx             INTEGER,
                                olOSCHistPMOPRValue                FixedX10,
                                olOSCHistPMOPRTimeStamp            DateAndTime,
                                olOSCHistPMOPRValidity             PMValidity,
                                olOSCHistPMOPTValue                FixedX10,
                                olOSCHistPMOPTTimeStamp            DateAndTime,
                                olOSCHistPMOPTValidity             PMValidity,
                                olOSCHistPMOBRValue                FixedX10,
                                olOSCHistPMOBRTimeStamp            DateAndTime,
                                olOSCHistPMOBRValidity             PMValidity,
                                olOSCHistPMCVSValue                Unsigned32,
                                olOSCHistPMCVSTimeStamp            DateAndTime,
                                olOSCHistPMCVSValidity             PMValidity,
                                olOSCHistPMCVSInitialize           InitializeCmd,
                                olOSCHistPMESSValue                Unsigned32,
                                olOSCHistPMESSTimeStamp            DateAndTime,
                                olOSCHistPMESSValidity             PMValidity,
                                olOSCHistPMESSInitialize           InitializeCmd,
                                olOSCHistPMSESSValue               Unsigned32,
                                olOSCHistPMSESSTimeStamp           DateAndTime,
                                olOSCHistPMSESSValidity            PMValidity,
                                olOSCHistPMSESSInitialize          InitializeCmd,
                                olOSCHistPMSEFSSValue              Unsigned32,
                                olOSCHistPMSEFSSTimeStamp          DateAndTime,
                                olOSCHistPMSEFSSValidity           PMValidity,
                                olOSCHistPMSEFSSInitialize         InitializeCmd,
                                olOSCHistPMUASSValue               Unsigned32,
                                olOSCHistPMUASSTimeStamp           DateAndTime,
                                olOSCHistPMUASSValidity            PMValidity,
                                olOSCHistPMUASSInitialize          InitializeCmd }


olOSCHistPMCpTypeIdx OBJECT-TYPE
    SYNTAX       CpType
    MAX-ACCESS   not-accessible
    STATUS       current
    DESCRIPTION  "The type of circuit pack on which the optical layer OSC
                  targeted for PMs is located."
    ::= { olOSCHistPMEntry 1 }


olOSCHistPMShelfIdx OBJECT-TYPE
    SYNTAX       INTEGER (1|11|21|31)
    MAX-ACCESS   not-accessible
    STATUS       current
    DESCRIPTION  "The number of the shelf in which the optical layer OSC
                  targeted for PMs is located."
    ::= { olOSCHistPMEntry 2 }


olOSCHistPMSlotIdx OBJECT-TYPE
    SYNTAX       INTEGER (1..20)
    MAX-ACCESS   not-accessible
    STATUS       current
    DESCRIPTION  "The number of the slot in which the optical layer OSC
                  targeted for PMs is located."
    ::= { olOSCHistPMEntry 3 }


olOSCHistPMLineIdx OBJECT-TYPE
    SYNTAX       INTEGER (1)
    MAX-ACCESS   not-accessible
    STATUS       current
    DESCRIPTION  "The line number of the OSC targeted for PMs."
    ::= { olOSCHistPMEntry 4 }


olOSCHistPMIntervalTypeIdx OBJECT-TYPE
    SYNTAX       PMIntervalType
    MAX-ACCESS   not-accessible
    STATUS       current
    DESCRIPTION  "The type of PM bin according to interval length."
    ::= { olOSCHistPMEntry 5 }


olOSCHistPMIntervalIdx OBJECT-TYPE
    SYNTAX       INTEGER (1..96)
    MAX-ACCESS   not-accessible
    STATUS       current
    DESCRIPTION  "The specific PM bin number. The range is 1 to 96 for the
                  15-minute historical bins. For the 1-day historical bin, the
                  value is 1."
    ::= { olOSCHistPMEntry 6 }


olOSCHistPMOPRValue OBJECT-TYPE
    SYNTAX       FixedX10
    UNITS        "dBm/10"
    MAX-ACCESS   read-only
    STATUS       current
    DESCRIPTION  "The OSC optical power received on the Line port."
    ::= { olOSCHistPMEntry 7 }


olOSCHistPMOPRTimeStamp OBJECT-TYPE
    SYNTAX       DateAndTime
    MAX-ACCESS   read-only
    STATUS       current
    DESCRIPTION  "The date and time stamp of the optical power received value."
    ::= { olOSCHistPMEntry 8 }


olOSCHistPMOPRValidity OBJECT-TYPE
    SYNTAX       PMValidity
    MAX-ACCESS   read-only
    STATUS       current
    DESCRIPTION  "Indicates the validity of the provided optical power received
                  value."
    ::= { olOSCHistPMEntry 9 }


olOSCHistPMOPTValue OBJECT-TYPE
    SYNTAX       FixedX10
    UNITS        "dBm/10"
    MAX-ACCESS   read-only
    STATUS       current
    DESCRIPTION  "The OSC optical power transmitted at the output of the
                  Line port."
    ::= { olOSCHistPMEntry 10 }


olOSCHistPMOPTTimeStamp OBJECT-TYPE
    SYNTAX       DateAndTime
    MAX-ACCESS   read-only
    STATUS       current
    DESCRIPTION  "The date and time stamp of the optical power transmitted
                  value."
    ::= { olOSCHistPMEntry 11 }


olOSCHistPMOPTValidity OBJECT-TYPE
    SYNTAX       PMValidity
    MAX-ACCESS   read-only
    STATUS       current
    DESCRIPTION  "Indicates the validity of the provided optical power
                  transmitted value."
    ::= { olOSCHistPMEntry 12 }


olOSCHistPMOBRValue OBJECT-TYPE
    SYNTAX       FixedX10
    UNITS        "dBm/10"
    MAX-ACCESS   read-only
    STATUS       current
    DESCRIPTION  "The OSC optical back-reflected power."
    ::= { olOSCHistPMEntry 13 }


olOSCHistPMOBRTimeStamp OBJECT-TYPE
    SYNTAX       DateAndTime
    MAX-ACCESS   read-only
    STATUS       current
    DESCRIPTION  "The date and time stamp of the optical back-reflected
                  power value."
    ::= { olOSCHistPMEntry 14 }


olOSCHistPMOBRValidity OBJECT-TYPE
    SYNTAX       PMValidity
    MAX-ACCESS   read-only
    STATUS       current
    DESCRIPTION  "Indicates the validity of the provided optical back-reflected
                  power value."
    ::= { olOSCHistPMEntry 15 }


olOSCHistPMCVSValue OBJECT-TYPE
    SYNTAX       Unsigned32
    MAX-ACCESS   read-write
    STATUS       current
    DESCRIPTION  "The count of coding violations at the section layer of
                  the received OSC signal."
    ::= { olOSCHistPMEntry 16 }


olOSCHistPMCVSTimeStamp OBJECT-TYPE
    SYNTAX       DateAndTime
    MAX-ACCESS   read-only
    STATUS       current
    DESCRIPTION  "The date and time stamp of the section layer coding violations
                  value."
    ::= { olOSCHistPMEntry 17 }


olOSCHistPMCVSValidity OBJECT-TYPE
    SYNTAX       PMValidity
    MAX-ACCESS   read-only
    STATUS       current
    DESCRIPTION  "Indicates the validity of the provided section layer coding
                  violations value."
    ::= { olOSCHistPMEntry 18 }


olOSCHistPMCVSInitialize OBJECT-TYPE
    SYNTAX       InitializeCmd
    MAX-ACCESS   read-write
    STATUS       current
    DESCRIPTION  "Used to initialize the value of the olOSCHistPMCVSValue object
                  to 0."
    ::= { olOSCHistPMEntry 19 }


olOSCHistPMESSValue OBJECT-TYPE
    SYNTAX       Unsigned32
    MAX-ACCESS   read-write
    STATUS       current
    DESCRIPTION  "The count of errored seconds at the section layer of
                  the received OSC signal."
    ::= { olOSCHistPMEntry 20 }


olOSCHistPMESSTimeStamp OBJECT-TYPE
    SYNTAX       DateAndTime
    MAX-ACCESS   read-only
    STATUS       current
    DESCRIPTION  "The date and time stamp of the section layer errored seconds
                  value."
    ::= { olOSCHistPMEntry 21 }


olOSCHistPMESSValidity OBJECT-TYPE
    SYNTAX       PMValidity
    MAX-ACCESS   read-only
    STATUS       current
    DESCRIPTION  "Indicates the validity of the provided section layer errored
                  seconds value."
    ::= { olOSCHistPMEntry 22 }


olOSCHistPMESSInitialize OBJECT-TYPE
    SYNTAX       InitializeCmd
    MAX-ACCESS   read-write
    STATUS       current
    DESCRIPTION  "Used to initialize the value of the olOSCHistPMESSValue object
                  to 0."
    ::= { olOSCHistPMEntry 23 }


olOSCHistPMSESSValue OBJECT-TYPE
    SYNTAX       Unsigned32
    MAX-ACCESS   read-write
    STATUS       current
    DESCRIPTION  "The count of severely errored seconds at the section layer
                  of the received OSC signal."
    ::= { olOSCHistPMEntry 24 }


olOSCHistPMSESSTimeStamp OBJECT-TYPE
    SYNTAX       DateAndTime
    MAX-ACCESS   read-only
    STATUS       current
    DESCRIPTION  "The date and time stamp of the section layer severely errored
                  seconds value."
    ::= { olOSCHistPMEntry 25 }


olOSCHistPMSESSValidity OBJECT-TYPE
    SYNTAX       PMValidity
    MAX-ACCESS   read-only
    STATUS       current
    DESCRIPTION  "Indicates the validity of the provided section layer severely
                  errored seconds value."
    ::= { olOSCHistPMEntry 26 }


olOSCHistPMSESSInitialize OBJECT-TYPE
    SYNTAX       InitializeCmd
    MAX-ACCESS   read-write
    STATUS       current
    DESCRIPTION  "Used to initialize the value of the olOSCHistPMSESSValue object
                  to 0."
    ::= { olOSCHistPMEntry 27 }


olOSCHistPMSEFSSValue OBJECT-TYPE
    SYNTAX       Unsigned32
    MAX-ACCESS   read-write
    STATUS       current
    DESCRIPTION  "The count of severely errored framing seconds at the section
                  layer of the received OSC signal."
    ::= { olOSCHistPMEntry 28 }


olOSCHistPMSEFSSTimeStamp OBJECT-TYPE
    SYNTAX       DateAndTime
    MAX-ACCESS   read-only
    STATUS       current
    DESCRIPTION  "The date and time stamp of the section layer severely errored
                  framing seconds value."
    ::= { olOSCHistPMEntry 29 }


olOSCHistPMSEFSSValidity OBJECT-TYPE
    SYNTAX       PMValidity
    MAX-ACCESS   read-only
    STATUS       current
    DESCRIPTION  "Indicates the validity of the provided section layer severely
                  errored framing seconds value."
    ::= { olOSCHistPMEntry 30 }


olOSCHistPMSEFSSInitialize OBJECT-TYPE
    SYNTAX       InitializeCmd
    MAX-ACCESS   read-write
    STATUS       current
    DESCRIPTION  "Used to initialize the value of the olOSCHistPMSEFSSValue object
                  to 0."
    ::= { olOSCHistPMEntry 31 }


olOSCHistPMUASSValue OBJECT-TYPE
    SYNTAX       Unsigned32
    MAX-ACCESS   read-write
    STATUS       current
    DESCRIPTION  "The count of unavailable seconds at the section layer
                  of the received OSC signal."
    ::= { olOSCHistPMEntry 32 }


olOSCHistPMUASSTimeStamp OBJECT-TYPE
    SYNTAX       DateAndTime
    MAX-ACCESS   read-only
    STATUS       current
    DESCRIPTION  "The date and time stamp of the section layer unavailable
                  seconds value."
    ::= { olOSCHistPMEntry 33 }


olOSCHistPMUASSValidity OBJECT-TYPE
    SYNTAX       PMValidity
    MAX-ACCESS   read-only
    STATUS       current
    DESCRIPTION  "Indicates the validity of the provided section layer unavailable
                  seconds value."
    ::= { olOSCHistPMEntry 34 }


olOSCHistPMUASSInitialize OBJECT-TYPE
    SYNTAX       InitializeCmd
    MAX-ACCESS   read-write
    STATUS       current
    DESCRIPTION  "Used to initialize the value of the olOSCHistPMUASSValue
                  object to 0."
    ::= { olOSCHistPMEntry 35 }



-----------------------------------------------------------------------
-- Objects used to manage Optical Layer OSC Performance
-- Monitoring Threshold Levels
-----------------------------------------------------------------------


olOSCPMThresholdTable OBJECT-TYPE
    SYNTAX       SEQUENCE OF OlOSCPMThresholdEntry
    MAX-ACCESS   not-accessible
    STATUS       current
    DESCRIPTION  "A table of threshold levels for performance monitoring
                  counter values on Optical Layer OSC objects, that are
                  used in the generation of threshold crossing alerts."
    ::= { olPerformance 3 }


olOSCPMThresholdEntry OBJECT-TYPE
    SYNTAX       OlOSCPMThresholdEntry
    MAX-ACCESS   not-accessible
    STATUS       current
    DESCRIPTION  "The row entry object of the optical layer OSC performance
                  monitoring threshold table. Each row of this table
                  contains a set of PM thresholds for a given interval
                  type that applies to an individual optical layer OSC
                  object."
    INDEX        { olOSCPMThresholdCpTypeIdx,
                   olOSCPMThresholdShelfIdx,
                   olOSCPMThresholdSlotIdx,
                   olOSCPMThresholdLineIdx,
                   olOSCPMThresholdIntervalTypeIdx }
    ::= { olOSCPMThresholdTable 1 }


OlOSCPMThresholdEntry ::= SEQUENCE { olOSCPMThresholdCpTypeIdx        CpType,
                                     olOSCPMThresholdShelfIdx         INTEGER,
                                     olOSCPMThresholdSlotIdx          INTEGER,
                                     olOSCPMThresholdLineIdx          INTEGER,
                                     olOSCPMThresholdIntervalTypeIdx  PMIntervalType,
                                     olOSCPMThresholdCVSValue         Unsigned32,
                                     olOSCPMThresholdESSValue         Unsigned32,
                                     olOSCPMThresholdSESSValue        Unsigned32,
                                     olOSCPMThresholdSEFSSValue       Unsigned32,
                                     olOSCPMThresholdUASSValue        Unsigned32 }


olOSCPMThresholdCpTypeIdx OBJECT-TYPE
    SYNTAX       CpType
    MAX-ACCESS   not-accessible
    STATUS       current
    DESCRIPTION  "The type of circuit pack on which the optical layer
                  OSC targeted for PM thresholds is located."
    ::= { olOSCPMThresholdEntry 1 }


olOSCPMThresholdShelfIdx OBJECT-TYPE
    SYNTAX       INTEGER (1|11|21|31)
    MAX-ACCESS   not-accessible
    STATUS       current
    DESCRIPTION  "The number of the shelf in which the optical layer
                  OSC targeted for PM thresholds is located."
    ::= { olOSCPMThresholdEntry 2 }


olOSCPMThresholdSlotIdx OBJECT-TYPE
    SYNTAX       INTEGER (1..20)
    MAX-ACCESS   not-accessible
    STATUS       current
    DESCRIPTION  "The number of the slot in which the optical layer OSC
                  targeted for PM thresholds is located."
    ::= { olOSCPMThresholdEntry 3 }


olOSCPMThresholdLineIdx OBJECT-TYPE
    SYNTAX       INTEGER (1)
    MAX-ACCESS   not-accessible
    STATUS       current
    DESCRIPTION  "The line number of the OSC targeted for PM thresholds."
    ::= { olOSCPMThresholdEntry 4 }


olOSCPMThresholdIntervalTypeIdx OBJECT-TYPE
    SYNTAX       PMIntervalType
    MAX-ACCESS   not-accessible
    STATUS       current
    DESCRIPTION  "The type of PM bin according to interval length. Thresholds
                  are supported for the 15-minute and 1-day PM bins only."
    ::= { olOSCPMThresholdEntry 5 }


olOSCPMThresholdCVSValue OBJECT-TYPE
    SYNTAX       Unsigned32
    MAX-ACCESS   read-write
    STATUS       current
    DESCRIPTION  "The threshold for the count of coding violations at the
                  section layer."
    ::= { olOSCPMThresholdEntry 6 }


olOSCPMThresholdESSValue OBJECT-TYPE
    SYNTAX       Unsigned32
    MAX-ACCESS   read-write
    STATUS       current
    DESCRIPTION  "The threshold for the count of errored seconds at the
                  section layer."
    ::= { olOSCPMThresholdEntry 7 }


olOSCPMThresholdSESSValue OBJECT-TYPE
    SYNTAX       Unsigned32
    MAX-ACCESS   read-write
    STATUS       current
    DESCRIPTION  "The threshold for the count of severely errored seconds at the
                  section layer."
    ::= { olOSCPMThresholdEntry 8 }


olOSCPMThresholdSEFSSValue OBJECT-TYPE
    SYNTAX       Unsigned32
    MAX-ACCESS   read-write
    STATUS       current
    DESCRIPTION  "The threshold for the count of severely errored framing
                  seconds at the section layer."
    ::= { olOSCPMThresholdEntry 9 }


olOSCPMThresholdUASSValue OBJECT-TYPE
    SYNTAX       Unsigned32
    MAX-ACCESS   read-write
    STATUS       current
    DESCRIPTION  "The threshold for the count of unavailable seconds at the
                  section layer."
    ::= { olOSCPMThresholdEntry 10 }



-----------------------------------------------------------------------
-- Objects used to retrieve current Performance Monitoring statistics
-- for Optical Layer Ports.
-----------------------------------------------------------------------


olPortCrntPMTable OBJECT-TYPE
    SYNTAX       SEQUENCE OF OlPortCrntPMEntry
    MAX-ACCESS   not-accessible
    STATUS       current
    DESCRIPTION  "A table of current performance monitoring statistics
                  collected for ports on equipment modules assigned
                  to optical layer groupings."
    ::= { olPerformance 4 }


olPortCrntPMEntry OBJECT-TYPE
    SYNTAX       OlPortCrntPMEntry
    MAX-ACCESS   not-accessible
    STATUS       current
    DESCRIPTION  "The row entry object of the optical layer port current
                  performance monitoring table. Each row of this table
                  contains a full set of PM statistics and related data
                  for a current measurement interval for a given optical
                  layer port."
    INDEX        { olPortCrntPMCpTypeIdx,
                   olPortCrntPMShelfIdx,
                   olPortCrntPMSlotIdx,
                   olPortCrntPMTypeIdx,
                   olPortCrntPMIdx,
                   olPortCrntPMIntervalTypeIdx }
    ::= { olPortCrntPMTable 1 }


OlPortCrntPMEntry ::= SEQUENCE { olPortCrntPMCpTypeIdx               CpType,
                                 olPortCrntPMShelfIdx                INTEGER,
                                 olPortCrntPMSlotIdx                 INTEGER,
                                 olPortCrntPMTypeIdx                 OlPortType,
                                 olPortCrntPMIdx                     INTEGER,
                                 olPortCrntPMIntervalTypeIdx         PMIntervalType,
                                 olPortCrntPMOPRValue                FixedX10,
                                 olPortCrntPMOPRTimeStamp            DateAndTime,
                                 olPortCrntPMOPRValidity             PMValidity,
                                 olPortCrntPMOPRMinValue             FixedX10,
                                 olPortCrntPMOPRMinTimeStamp         DateAndTime,
                                 olPortCrntPMOPRMinValidity          PMValidity,
                                 olPortCrntPMOPRMaxValue             FixedX10,
                                 olPortCrntPMOPRMaxTimeStamp         DateAndTime,
                                 olPortCrntPMOPRMaxValidity          PMValidity,
                                 olPortCrntPMOPRAvgValue             FixedX10,
                                 olPortCrntPMOPRAvgTimeStamp         DateAndTime,
                                 olPortCrntPMOPRAvgValidity          PMValidity,
                                 olPortCrntPMOPRStdDevValue          FixedX10,
                                 olPortCrntPMOPRStdDevTimeStamp      DateAndTime,
                                 olPortCrntPMOPRStdDevValidity       PMValidity,
                                 olPortCrntPMOPTValue                FixedX10,
                                 olPortCrntPMOPTTimeStamp            DateAndTime,
                                 olPortCrntPMOPTValidity             PMValidity,
                                 olPortCrntPMOPTMinValue             FixedX10,
                                 olPortCrntPMOPTMinTimeStamp         DateAndTime,
                                 olPortCrntPMOPTMinValidity          PMValidity,
                                 olPortCrntPMOPTMaxValue             FixedX10,
                                 olPortCrntPMOPTMaxTimeStamp         DateAndTime,
                                 olPortCrntPMOPTMaxValidity          PMValidity,
                                 olPortCrntPMOPTAvgValue             FixedX10,
                                 olPortCrntPMOPTAvgTimeStamp         DateAndTime,
                                 olPortCrntPMOPTAvgValidity          PMValidity,
                                 olPortCrntPMOPTStdDevValue          FixedX10,
                                 olPortCrntPMOPTStdDevTimeStamp      DateAndTime,
                                 olPortCrntPMOPTStdDevValidity       PMValidity,
                                 olPortCrntPMLossRxValue             FixedX10,
                                 olPortCrntPMLossRxTimeStamp         DateAndTime,
                                 olPortCrntPMLossRxValidity          PMValidity,
                                 olPortCrntPMLossTxValue             FixedX10,
                                 olPortCrntPMLossTxTimeStamp         DateAndTime,
                                 olPortCrntPMLossTxValidity          PMValidity,
                                 olPortCrntPMInitializeAll           InitializeCmd }


olPortCrntPMCpTypeIdx OBJECT-TYPE
    SYNTAX       CpType
    MAX-ACCESS   not-accessible
    STATUS       current
    DESCRIPTION  "The type of circuit pack on which the port
                  targeted for PMs is located."
    ::= { olPortCrntPMEntry 1 }


olPortCrntPMShelfIdx OBJECT-TYPE
    SYNTAX       INTEGER (1|11|21|31)
    MAX-ACCESS   not-accessible
    STATUS       current
    DESCRIPTION  "The number of the shelf in which the port
                  targeted for PMs is located."
    ::= { olPortCrntPMEntry 2 }


olPortCrntPMSlotIdx OBJECT-TYPE
    SYNTAX       INTEGER (1..20)
    MAX-ACCESS   not-accessible
    STATUS       current
    DESCRIPTION  "The number of the slot in which the port
                  targeted for PMs is located."
    ::= { olPortCrntPMEntry 3 }


olPortCrntPMTypeIdx OBJECT-TYPE
    SYNTAX       OlPortType
    MAX-ACCESS   not-accessible
    STATUS       current
    DESCRIPTION  "The type of port targeted for PMs."
    ::= { olPortCrntPMEntry 4 }


olPortCrntPMIdx OBJECT-TYPE
    SYNTAX       INTEGER (1..4)
    MAX-ACCESS   not-accessible
    STATUS       current
    DESCRIPTION  "The number of the port of the specified
                  port type targeted for PMs."
    ::= { olPortCrntPMEntry 5 }


olPortCrntPMIntervalTypeIdx OBJECT-TYPE
    SYNTAX       PMIntervalType
    MAX-ACCESS   not-accessible
    STATUS       current
    DESCRIPTION  "The type of PM bin according to interval length."
    ::= { olPortCrntPMEntry 6 }


olPortCrntPMOPRValue OBJECT-TYPE
    SYNTAX       FixedX10
    UNITS        "dBm/10"
    MAX-ACCESS   read-only
    STATUS       current
    DESCRIPTION  "The instantaneous optical power received on the port."
    ::= { olPortCrntPMEntry 7 }


olPortCrntPMOPRTimeStamp OBJECT-TYPE
    SYNTAX       DateAndTime
    MAX-ACCESS   read-only
    STATUS       current
    DESCRIPTION  "The date and time stamp of the instantaneous optical
                  power received value."
    ::= { olPortCrntPMEntry 8 }


olPortCrntPMOPRValidity OBJECT-TYPE
    SYNTAX       PMValidity
    MAX-ACCESS   read-only
    STATUS       current
    DESCRIPTION  "Indicates the validity of the provided instantaneous
                  optical power received value."
    ::= { olPortCrntPMEntry 9 }


olPortCrntPMOPRMinValue OBJECT-TYPE
    SYNTAX       FixedX10
    UNITS        "dBm/10"
    MAX-ACCESS   read-only
    STATUS       current
    DESCRIPTION  "The minimum optical power received on the port over
                  the interval."
    ::= { olPortCrntPMEntry 10 }


olPortCrntPMOPRMinTimeStamp OBJECT-TYPE
    SYNTAX       DateAndTime
    MAX-ACCESS   read-only
    STATUS       current
    DESCRIPTION  "The date and time stamp of the minimum optical
                  power received value."
    ::= { olPortCrntPMEntry 11 }


olPortCrntPMOPRMinValidity OBJECT-TYPE
    SYNTAX       PMValidity
    MAX-ACCESS   read-only
    STATUS       current
    DESCRIPTION  "Indicates the validity of the provided minimum
                  optical power received value."
    ::= { olPortCrntPMEntry 12 }


olPortCrntPMOPRMaxValue OBJECT-TYPE
    SYNTAX       FixedX10
    UNITS        "dBm/10"
    MAX-ACCESS   read-only
    STATUS       current
    DESCRIPTION  "The maximum optical power received on the port over
                  the interval."
    ::= { olPortCrntPMEntry 13 }


olPortCrntPMOPRMaxTimeStamp OBJECT-TYPE
    SYNTAX       DateAndTime
    MAX-ACCESS   read-only
    STATUS       current
    DESCRIPTION  "The date and time stamp of the maximum optical
                  power received value."
    ::= { olPortCrntPMEntry 14 }


olPortCrntPMOPRMaxValidity OBJECT-TYPE
    SYNTAX       PMValidity
    MAX-ACCESS   read-only
    STATUS       current
    DESCRIPTION  "Indicates the validity of the provided maximum
                  optical power received value."
    ::= { olPortCrntPMEntry 15 }


olPortCrntPMOPRAvgValue OBJECT-TYPE
    SYNTAX       FixedX10
    UNITS        "dBm/10"
    MAX-ACCESS   read-only
    STATUS       current
    DESCRIPTION  "The average optical power received on the port over
                  the interval."
    ::= { olPortCrntPMEntry 16 }


olPortCrntPMOPRAvgTimeStamp OBJECT-TYPE
    SYNTAX       DateAndTime
    MAX-ACCESS   read-only
    STATUS       current
    DESCRIPTION  "The date and time stamp of the average optical
                  power received value."
    ::= { olPortCrntPMEntry 17 }


olPortCrntPMOPRAvgValidity OBJECT-TYPE
    SYNTAX       PMValidity
    MAX-ACCESS   read-only
    STATUS       current
    DESCRIPTION  "Indicates the validity of the provided average
                  optical power received value."
    ::= { olPortCrntPMEntry 18 }


olPortCrntPMOPRStdDevValue OBJECT-TYPE
    SYNTAX       FixedX10
    UNITS        "dB/10"
    MAX-ACCESS   read-only
    STATUS       current
    DESCRIPTION  "The standard deviation from the average of the optical
                  power received on the port over the interval."
    ::= { olPortCrntPMEntry 19 }


olPortCrntPMOPRStdDevTimeStamp OBJECT-TYPE
    SYNTAX       DateAndTime
    MAX-ACCESS   read-only
    STATUS       current
    DESCRIPTION  "The date and time stamp of the standard deviation value
                  for the optical power received."
    ::= { olPortCrntPMEntry 20 }


olPortCrntPMOPRStdDevValidity OBJECT-TYPE
    SYNTAX       PMValidity
    MAX-ACCESS   read-only
    STATUS       current
    DESCRIPTION  "Indicates the validity of the provided standard deviation
                  value for the optical power received."
    ::= { olPortCrntPMEntry 21 }


olPortCrntPMOPTValue OBJECT-TYPE
    SYNTAX       FixedX10
    UNITS        "dBm/10"
    MAX-ACCESS   read-only
    STATUS       current
    DESCRIPTION  "The instantaneous optical power transmitted on the port."
    ::= { olPortCrntPMEntry 22 }


olPortCrntPMOPTTimeStamp OBJECT-TYPE
    SYNTAX       DateAndTime
    MAX-ACCESS   read-only
    STATUS       current
    DESCRIPTION  "The date and time stamp of the instantaneous optical
                  power transmitted value."
    ::= { olPortCrntPMEntry 23 }


olPortCrntPMOPTValidity OBJECT-TYPE
    SYNTAX       PMValidity
    MAX-ACCESS   read-only
    STATUS       current
    DESCRIPTION  "Indicates the validity of the provided instantaneous
                  optical power transmitted value."
    ::= { olPortCrntPMEntry 24 }


olPortCrntPMOPTMinValue OBJECT-TYPE
    SYNTAX       FixedX10
    UNITS        "dBm/10"
    MAX-ACCESS   read-only
    STATUS       current
    DESCRIPTION  "The minimum optical power transmitted on the port over
                  the interval."
    ::= { olPortCrntPMEntry 25 }


olPortCrntPMOPTMinTimeStamp OBJECT-TYPE
    SYNTAX       DateAndTime
    MAX-ACCESS   read-only
    STATUS       current
    DESCRIPTION  "The date and time stamp of the minimum optical
                  power transmitted value."
    ::= { olPortCrntPMEntry 26 }


olPortCrntPMOPTMinValidity OBJECT-TYPE
    SYNTAX       PMValidity
    MAX-ACCESS   read-only
    STATUS       current
    DESCRIPTION  "Indicates the validity of the provided minimum
                  optical power transmitted value."
    ::= { olPortCrntPMEntry 27 }


olPortCrntPMOPTMaxValue OBJECT-TYPE
    SYNTAX       FixedX10
    UNITS        "dBm/10"
    MAX-ACCESS   read-only
    STATUS       current
    DESCRIPTION  "The maximum optical power transmitted on the port over
                  the interval."
    ::= { olPortCrntPMEntry 28 }


olPortCrntPMOPTMaxTimeStamp OBJECT-TYPE
    SYNTAX       DateAndTime
    MAX-ACCESS   read-only
    STATUS       current
    DESCRIPTION  "The date and time stamp of the maximum optical
                  power transmitted value."
    ::= { olPortCrntPMEntry 29 }


olPortCrntPMOPTMaxValidity OBJECT-TYPE
    SYNTAX       PMValidity
    MAX-ACCESS   read-only
    STATUS       current
    DESCRIPTION  "Indicates the validity of the provided maximum
                  optical power transmitted value."
    ::= { olPortCrntPMEntry 30 }


olPortCrntPMOPTAvgValue OBJECT-TYPE
    SYNTAX       FixedX10
    UNITS        "dBm/10"
    MAX-ACCESS   read-only
    STATUS       current
    DESCRIPTION  "The average optical power transmitted on the port over
                  the interval."
    ::= { olPortCrntPMEntry 31 }


olPortCrntPMOPTAvgTimeStamp OBJECT-TYPE
    SYNTAX       DateAndTime
    MAX-ACCESS   read-only
    STATUS       current
    DESCRIPTION  "The date and time stamp of the average optical
                  power transmitted value."
    ::= { olPortCrntPMEntry 32 }


olPortCrntPMOPTAvgValidity OBJECT-TYPE
    SYNTAX       PMValidity
    MAX-ACCESS   read-only
    STATUS       current
    DESCRIPTION  "Indicates the validity of the provided average
                  optical power transmitted value."
    ::= { olPortCrntPMEntry 33 }


olPortCrntPMOPTStdDevValue OBJECT-TYPE
    SYNTAX       FixedX10
    UNITS        "dB/10"
    MAX-ACCESS   read-only
    STATUS       current
    DESCRIPTION  "The standard deviation from the average of the optical
                  power transmitted on the port over the interval."
    ::= { olPortCrntPMEntry 34 }


olPortCrntPMOPTStdDevTimeStamp OBJECT-TYPE
    SYNTAX       DateAndTime
    MAX-ACCESS   read-only
    STATUS       current
    DESCRIPTION  "The date and time stamp of the standard deviation value
                  for the optical power transmitted."
    ::= { olPortCrntPMEntry 35 }


olPortCrntPMOPTStdDevValidity OBJECT-TYPE
    SYNTAX       PMValidity
    MAX-ACCESS   read-only
    STATUS       current
    DESCRIPTION  "Indicates the validity of the provided standard deviation
                  value for the optical power transmitted."
    ::= { olPortCrntPMEntry 36 }


olPortCrntPMLossRxValue OBJECT-TYPE
    SYNTAX       FixedX10
    UNITS        "dB/10"
    MAX-ACCESS   read-only
    STATUS       current
    DESCRIPTION  "The optical power loss measured on the port in the
                  receive direction. For a Line port, this represents
                  the span loss. For a DCM port, this is the DCM loss.
                  For a client port, this is the loss of the receive
                  inter-connection fiber."
    ::= { olPortCrntPMEntry 37 }


olPortCrntPMLossRxTimeStamp OBJECT-TYPE
    SYNTAX       DateAndTime
    MAX-ACCESS   read-only
    STATUS       current
    DESCRIPTION  "The date and time stamp of the receive loss value."
    ::= { olPortCrntPMEntry 38 }


olPortCrntPMLossRxValidity OBJECT-TYPE
    SYNTAX       PMValidity
    MAX-ACCESS   read-only
    STATUS       current
    DESCRIPTION  "Indicates the validity of the provided receive loss
                  value."
    ::= { olPortCrntPMEntry 39 }


olPortCrntPMLossTxValue OBJECT-TYPE
    SYNTAX       FixedX10
    UNITS        "dB/10"
    MAX-ACCESS   read-only
    STATUS       current
    DESCRIPTION  "The optical power loss measured on the port in the
                  transmit direction. For a Line port, this represents
                  the far-end span loss. For a client port, this is the
                  loss of the transmit inter-connection fiber."
    ::= { olPortCrntPMEntry 40 }


olPortCrntPMLossTxTimeStamp OBJECT-TYPE
    SYNTAX       DateAndTime
    MAX-ACCESS   read-only
    STATUS       current
    DESCRIPTION  "The date and time stamp of the transmit loss value."
    ::= { olPortCrntPMEntry 41 }


olPortCrntPMLossTxValidity OBJECT-TYPE
    SYNTAX       PMValidity
    MAX-ACCESS   read-only
    STATUS       current
    DESCRIPTION  "Indicates the validity of the provided transmit loss
                  value."
    ::= { olPortCrntPMEntry 42 }


olPortCrntPMInitializeAll OBJECT-TYPE
    SYNTAX       InitializeCmd
    MAX-ACCESS   read-write
    STATUS       current
    DESCRIPTION  "Used to initialize all binned PM values for a given
                  entry in the table."
    ::= { olPortCrntPMEntry 43 }



-----------------------------------------------------------------------
-- Objects used to retrieve historical performance monitoring statistics
-- for ports on equipment modules assigned to optical layer groupings.
-----------------------------------------------------------------------


olPortHistPMTable OBJECT-TYPE
    SYNTAX       SEQUENCE OF OlPortHistPMEntry
    MAX-ACCESS   not-accessible
    STATUS       current
    DESCRIPTION  "A table of historical performance monitoring statistics
                  collected for optical layer ports."
    ::= { olPerformance 5 }


olPortHistPMEntry OBJECT-TYPE
    SYNTAX       OlPortHistPMEntry
    MAX-ACCESS   not-accessible
    STATUS       current
    DESCRIPTION  "The row entry object of the Optical Layer Port
                  Historical Performance Monitoring table. Each row of
                  this table contains a full set of PM statistics and
                  related data for an historical measurement interval
                  for a given optical layer port."
    INDEX        { olPortHistPMCpTypeIdx,
                   olPortHistPMShelfIdx,
                   olPortHistPMSlotIdx,
                   olPortHistPMTypeIdx,
                   olPortHistPMIdx,
                   olPortHistPMIntervalTypeIdx,
                   olPortHistPMIntervalIdx }
    ::= { olPortHistPMTable 1 }


OlPortHistPMEntry ::= SEQUENCE { olPortHistPMCpTypeIdx               CpType,
                                 olPortHistPMShelfIdx                INTEGER,
                                 olPortHistPMSlotIdx                 INTEGER,
                                 olPortHistPMTypeIdx                 OlPortType,
                                 olPortHistPMIdx                     INTEGER,
                                 olPortHistPMIntervalTypeIdx         PMIntervalType,
                                 olPortHistPMIntervalIdx             INTEGER,
                                 olPortHistPMOPRValue                FixedX10,
                                 olPortHistPMOPRTimeStamp            DateAndTime,
                                 olPortHistPMOPRValidity             PMValidity,
                                 olPortHistPMOPRMinValue             FixedX10,
                                 olPortHistPMOPRMinTimeStamp         DateAndTime,
                                 olPortHistPMOPRMinValidity          PMValidity,
                                 olPortHistPMOPRMaxValue             FixedX10,
                                 olPortHistPMOPRMaxTimeStamp         DateAndTime,
                                 olPortHistPMOPRMaxValidity          PMValidity,
                                 olPortHistPMOPRAvgValue             FixedX10,
                                 olPortHistPMOPRAvgTimeStamp         DateAndTime,
                                 olPortHistPMOPRAvgValidity          PMValidity,
                                 olPortHistPMOPRStdDevValue          FixedX10,
                                 olPortHistPMOPRStdDevTimeStamp      DateAndTime,
                                 olPortHistPMOPRStdDevValidity       PMValidity,
                                 olPortHistPMOPTValue                FixedX10,
                                 olPortHistPMOPTTimeStamp            DateAndTime,
                                 olPortHistPMOPTValidity             PMValidity,
                                 olPortHistPMOPTMinValue             FixedX10,
                                 olPortHistPMOPTMinTimeStamp         DateAndTime,
                                 olPortHistPMOPTMinValidity          PMValidity,
                                 olPortHistPMOPTMaxValue             FixedX10,
                                 olPortHistPMOPTMaxTimeStamp         DateAndTime,
                                 olPortHistPMOPTMaxValidity          PMValidity,
                                 olPortHistPMOPTAvgValue             FixedX10,
                                 olPortHistPMOPTAvgTimeStamp         DateAndTime,
                                 olPortHistPMOPTAvgValidity          PMValidity,
                                 olPortHistPMOPTStdDevValue          FixedX10,
                                 olPortHistPMOPTStdDevTimeStamp      DateAndTime,
                                 olPortHistPMOPTStdDevValidity       PMValidity,
                                 olPortHistPMLossRxValue             FixedX10,
                                 olPortHistPMLossRxTimeStamp         DateAndTime,
                                 olPortHistPMLossRxValidity          PMValidity,
                                 olPortHistPMLossTxValue             FixedX10,
                                 olPortHistPMLossTxTimeStamp         DateAndTime,
                                 olPortHistPMLossTxValidity          PMValidity,
                                 olPortHistPMInitializeAll           InitializeCmd }


olPortHistPMCpTypeIdx OBJECT-TYPE
    SYNTAX       CpType
    MAX-ACCESS   not-accessible
    STATUS       current
    DESCRIPTION  "The type of circuit pack on which the port
                  targeted for PMs is located."
    ::= { olPortHistPMEntry 1 }


olPortHistPMShelfIdx OBJECT-TYPE
    SYNTAX       INTEGER (1|11|21|31)
    MAX-ACCESS   not-accessible
    STATUS       current
    DESCRIPTION  "The number of the shelf in which the port
                  targeted for PMs is located."
    ::= { olPortHistPMEntry 2 }


olPortHistPMSlotIdx OBJECT-TYPE
    SYNTAX       INTEGER (1..20)
    MAX-ACCESS   not-accessible
    STATUS       current
    DESCRIPTION  "The number of the slot in which the port
                  targeted for PMs is located."
    ::= { olPortHistPMEntry 3 }


olPortHistPMTypeIdx OBJECT-TYPE
    SYNTAX       OlPortType
    MAX-ACCESS   not-accessible
    STATUS       current
    DESCRIPTION  "The type of port targeted for PMs."
    ::= { olPortHistPMEntry 4 }


olPortHistPMIdx OBJECT-TYPE
    SYNTAX       INTEGER (1..4)
    MAX-ACCESS   not-accessible
    STATUS       current
    DESCRIPTION  "The number of the port of the specified
                  port type targeted for PMs."
    ::= { olPortHistPMEntry 5 }


olPortHistPMIntervalTypeIdx OBJECT-TYPE
    SYNTAX       PMIntervalType
    MAX-ACCESS   not-accessible
    STATUS       current
    DESCRIPTION  "The type of PM bin according to interval length."
    ::= { olPortHistPMEntry 6 }


olPortHistPMIntervalIdx OBJECT-TYPE
    SYNTAX       INTEGER (1..96)
    MAX-ACCESS   not-accessible
    STATUS       current
    DESCRIPTION  "The specific PM bin number. The range is 1 to 96 for the
                  15-minute historical bins. For the 1-day historical bin, the
                  value is 1."
    ::= { olPortHistPMEntry 7 }


olPortHistPMOPRValue OBJECT-TYPE
    SYNTAX       FixedX10
    UNITS        "dBm/10"
    MAX-ACCESS   read-only
    STATUS       current
    DESCRIPTION  "The instantaneous optical power received on the port."
    ::= { olPortHistPMEntry 8 }


olPortHistPMOPRTimeStamp OBJECT-TYPE
    SYNTAX       DateAndTime
    MAX-ACCESS   read-only
    STATUS       current
    DESCRIPTION  "The date and time stamp of the instantaneous optical
                  power received value."
    ::= { olPortHistPMEntry 9 }


olPortHistPMOPRValidity OBJECT-TYPE
    SYNTAX       PMValidity
    MAX-ACCESS   read-only
    STATUS       current
    DESCRIPTION  "Indicates the validity of the provided instantaneous
                  optical power received value."
    ::= { olPortHistPMEntry 10 }


olPortHistPMOPRMinValue OBJECT-TYPE
    SYNTAX       FixedX10
    UNITS        "dBm/10"
    MAX-ACCESS   read-only
    STATUS       current
    DESCRIPTION  "The minimum optical power received on the port over
                  the interval."
    ::= { olPortHistPMEntry 11 }


olPortHistPMOPRMinTimeStamp OBJECT-TYPE
    SYNTAX       DateAndTime
    MAX-ACCESS   read-only
    STATUS       current
    DESCRIPTION  "The date and time stamp of the minimum optical
                  power received value."
    ::= { olPortHistPMEntry 12 }


olPortHistPMOPRMinValidity OBJECT-TYPE
    SYNTAX       PMValidity
    MAX-ACCESS   read-only
    STATUS       current
    DESCRIPTION  "Indicates the validity of the provided minimum
                  optical power received value."
    ::= { olPortHistPMEntry 13 }


olPortHistPMOPRMaxValue OBJECT-TYPE
    SYNTAX       FixedX10
    UNITS        "dBm/10"
    MAX-ACCESS   read-only
    STATUS       current
    DESCRIPTION  "The maximum optical power received on the port over
                  the interval."
    ::= { olPortHistPMEntry 14 }


olPortHistPMOPRMaxTimeStamp OBJECT-TYPE
    SYNTAX       DateAndTime
    MAX-ACCESS   read-only
    STATUS       current
    DESCRIPTION  "The date and time stamp of the maximum optical
                  power received value."
    ::= { olPortHistPMEntry 15 }


olPortHistPMOPRMaxValidity OBJECT-TYPE
    SYNTAX       PMValidity
    MAX-ACCESS   read-only
    STATUS       current
    DESCRIPTION  "Indicates the validity of the provided maximum
                  optical power received value."
    ::= { olPortHistPMEntry 16 }


olPortHistPMOPRAvgValue OBJECT-TYPE
    SYNTAX       FixedX10
    UNITS        "dBm/10"
    MAX-ACCESS   read-only
    STATUS       current
    DESCRIPTION  "The average optical power received on the port over
                  the interval."
    ::= { olPortHistPMEntry 17 }


olPortHistPMOPRAvgTimeStamp OBJECT-TYPE
    SYNTAX       DateAndTime
    MAX-ACCESS   read-only
    STATUS       current
    DESCRIPTION  "The date and time stamp of the average optical
                  power received value."
    ::= { olPortHistPMEntry 18 }


olPortHistPMOPRAvgValidity OBJECT-TYPE
    SYNTAX       PMValidity
    MAX-ACCESS   read-only
    STATUS       current
    DESCRIPTION  "Indicates the validity of the provided average
                  optical power received value."
    ::= { olPortHistPMEntry 19 }


olPortHistPMOPRStdDevValue OBJECT-TYPE
    SYNTAX       FixedX10
    UNITS        "dB/10"
    MAX-ACCESS   read-only
    STATUS       current
    DESCRIPTION  "The standard deviation from the average of the optical
                  power received on the port over the interval."
    ::= { olPortHistPMEntry 20 }


olPortHistPMOPRStdDevTimeStamp OBJECT-TYPE
    SYNTAX       DateAndTime
    MAX-ACCESS   read-only
    STATUS       current
    DESCRIPTION  "The date and time stamp of the standard deviation value
                  for the optical power received."
    ::= { olPortHistPMEntry 21 }


olPortHistPMOPRStdDevValidity OBJECT-TYPE
    SYNTAX       PMValidity
    MAX-ACCESS   read-only
    STATUS       current
    DESCRIPTION  "Indicates the validity of the provided standard deviation
                  value for the optical power received."
    ::= { olPortHistPMEntry 22 }


olPortHistPMOPTValue OBJECT-TYPE
    SYNTAX       FixedX10
    UNITS        "dBm/10"
    MAX-ACCESS   read-only
    STATUS       current
    DESCRIPTION  "The instantaneous optical power transmitted on the port."
    ::= { olPortHistPMEntry 23 }


olPortHistPMOPTTimeStamp OBJECT-TYPE
    SYNTAX       DateAndTime
    MAX-ACCESS   read-only
    STATUS       current
    DESCRIPTION  "The date and time stamp of the instantaneous optical
                  power transmitted value."
    ::= { olPortHistPMEntry 24 }


olPortHistPMOPTValidity OBJECT-TYPE
    SYNTAX       PMValidity
    MAX-ACCESS   read-only
    STATUS       current
    DESCRIPTION  "Indicates the validity of the provided instantaneous
                  optical power transmitted value."
    ::= { olPortHistPMEntry 25 }


olPortHistPMOPTMinValue OBJECT-TYPE
    SYNTAX       FixedX10
    UNITS        "dBm/10"
    MAX-ACCESS   read-only
    STATUS       current
    DESCRIPTION  "The minimum optical power transmitted on the port over
                  the interval."
    ::= { olPortHistPMEntry 26 }


olPortHistPMOPTMinTimeStamp OBJECT-TYPE
    SYNTAX       DateAndTime
    MAX-ACCESS   read-only
    STATUS       current
    DESCRIPTION  "The date and time stamp of the minimum optical
                  power transmitted value."
    ::= { olPortHistPMEntry 27 }


olPortHistPMOPTMinValidity OBJECT-TYPE
    SYNTAX       PMValidity
    MAX-ACCESS   read-only
    STATUS       current
    DESCRIPTION  "Indicates the validity of the provided minimum
                  optical power transmitted value."
    ::= { olPortHistPMEntry 28 }


olPortHistPMOPTMaxValue OBJECT-TYPE
    SYNTAX       FixedX10
    UNITS        "dBm/10"
    MAX-ACCESS   read-only
    STATUS       current
    DESCRIPTION  "The maximum optical power transmitted on the port over
                  the interval."
    ::= { olPortHistPMEntry 29 }


olPortHistPMOPTMaxTimeStamp OBJECT-TYPE
    SYNTAX       DateAndTime
    MAX-ACCESS   read-only
    STATUS       current
    DESCRIPTION  "The date and time stamp of the maximum optical
                  power transmitted value."
    ::= { olPortHistPMEntry 30 }


olPortHistPMOPTMaxValidity OBJECT-TYPE
    SYNTAX       PMValidity
    MAX-ACCESS   read-only
    STATUS       current
    DESCRIPTION  "Indicates the validity of the provided maximum
                  optical power transmitted value."
    ::= { olPortHistPMEntry 31 }


olPortHistPMOPTAvgValue OBJECT-TYPE
    SYNTAX       FixedX10
    UNITS        "dBm/10"
    MAX-ACCESS   read-only
    STATUS       current
    DESCRIPTION  "The average optical power transmitted on the port over
                  the interval."
    ::= { olPortHistPMEntry 32 }


olPortHistPMOPTAvgTimeStamp OBJECT-TYPE
    SYNTAX       DateAndTime
    MAX-ACCESS   read-only
    STATUS       current
    DESCRIPTION  "The date and time stamp of the average optical
                  power transmitted value."
    ::= { olPortHistPMEntry 33 }


olPortHistPMOPTAvgValidity OBJECT-TYPE
    SYNTAX       PMValidity
    MAX-ACCESS   read-only
    STATUS       current
    DESCRIPTION  "Indicates the validity of the provided average
                  optical power transmitted value."
    ::= { olPortHistPMEntry 34 }


olPortHistPMOPTStdDevValue OBJECT-TYPE
    SYNTAX       FixedX10
    UNITS        "dB/10"
    MAX-ACCESS   read-only
    STATUS       current
    DESCRIPTION  "The standard deviation from the average of the optical
                  power transmitted on the port over the interval."
    ::= { olPortHistPMEntry 35 }


olPortHistPMOPTStdDevTimeStamp OBJECT-TYPE
    SYNTAX       DateAndTime
    MAX-ACCESS   read-only
    STATUS       current
    DESCRIPTION  "The date and time stamp of the standard deviation value
                  for the optical power transmitted."
    ::= { olPortHistPMEntry 36 }


olPortHistPMOPTStdDevValidity OBJECT-TYPE
    SYNTAX       PMValidity
    MAX-ACCESS   read-only
    STATUS       current
    DESCRIPTION  "Indicates the validity of the provided standard deviation
                  value for the optical power transmitted."
    ::= { olPortHistPMEntry 37 }


olPortHistPMLossRxValue OBJECT-TYPE
    SYNTAX       FixedX10
    UNITS        "dB/10"
    MAX-ACCESS   read-only
    STATUS       current
    DESCRIPTION  "The optical power loss measured on the port in the
                  receive direction. For a Line port, this represents
                  the span loss. For a DCM port, this is the DCM loss.
                  For a client port, this is the loss of the receive
                  inter-connection fiber."
    ::= { olPortHistPMEntry 38 }


olPortHistPMLossRxTimeStamp OBJECT-TYPE
    SYNTAX       DateAndTime
    MAX-ACCESS   read-only
    STATUS       current
    DESCRIPTION  "The date and time stamp of the receive loss value."
    ::= { olPortHistPMEntry 39 }


olPortHistPMLossRxValidity OBJECT-TYPE
    SYNTAX       PMValidity
    MAX-ACCESS   read-only
    STATUS       current
    DESCRIPTION  "Indicates the validity of the provided receive loss
                  value."
    ::= { olPortHistPMEntry 40 }


olPortHistPMLossTxValue OBJECT-TYPE
    SYNTAX       FixedX10
    UNITS        "dB/10"
    MAX-ACCESS   read-only
    STATUS       current
    DESCRIPTION  "The optical power loss measured on the port in the
                  transmit direction. For a Line port, this represents
                  the far-end span loss. For a client port, this is the
                  loss of the transmit inter-connection fiber."
    ::= { olPortHistPMEntry 41 }


olPortHistPMLossTxTimeStamp OBJECT-TYPE
    SYNTAX       DateAndTime
    MAX-ACCESS   read-only
    STATUS       current
    DESCRIPTION  "The date and time stamp of the transmit loss value."
    ::= { olPortHistPMEntry 42 }


olPortHistPMLossTxValidity OBJECT-TYPE
    SYNTAX       PMValidity
    MAX-ACCESS   read-only
    STATUS       current
    DESCRIPTION  "Indicates the validity of the provided transmit loss
                  value."
    ::= { olPortHistPMEntry 43 }


olPortHistPMInitializeAll OBJECT-TYPE
    SYNTAX       InitializeCmd
    MAX-ACCESS   read-write
    STATUS       current
    DESCRIPTION  "Used to initialize all binned PM values for a given
                  entry in the table."
    ::= { olPortHistPMEntry 44 }



-----------------------------------------------------------------------
-- Objects used to retrieve current performance monitoring statistics
-- for wavelength channels on equipment modules assigned to optical
-- layer groupings.
-----------------------------------------------------------------------


wchCrntPMTable OBJECT-TYPE
    SYNTAX       SEQUENCE OF WchCrntPMEntry
    MAX-ACCESS   not-accessible
    STATUS       current
    DESCRIPTION  "A table of current performance monitoring statistics
                  collected for wavelength channels."
    ::= { olPerformance 6 }


wchCrntPMEntry OBJECT-TYPE
    SYNTAX       WchCrntPMEntry
    MAX-ACCESS   not-accessible
    STATUS       current
    DESCRIPTION  "The row entry object of the Wavelength Channel Current
                  Performance Monitoring table. Each row of this table
                  contains a full set of PM statistics and related data
                  for a current measurement interval for a wavelength
                  channel object in an optical layer grouping."
    INDEX        { wchCrntPMCpTypeIdx,
                   wchCrntPMShelfIdx,
                   wchCrntPMSlotIdx,
                   wchCrntPMPortTypeIdx,
                   wchCrntPMPortIdx,
                   wchCrntPMIdx,
                   wchCrntPMIntervalTypeIdx }
    ::= { wchCrntPMTable 1 }


WchCrntPMEntry ::= SEQUENCE { wchCrntPMCpTypeIdx               CpType,
                              wchCrntPMShelfIdx                INTEGER,
                              wchCrntPMSlotIdx                 INTEGER,
                              wchCrntPMPortTypeIdx             OlPortType,
                              wchCrntPMPortIdx                 INTEGER,
                              wchCrntPMIdx                     INTEGER,
                              wchCrntPMIntervalTypeIdx         PMIntervalType,
                              wchCrntPMOPRValue                FixedX10,
                              wchCrntPMOPRTimeStamp            DateAndTime,
                              wchCrntPMOPRValidity             PMValidity,
                              wchCrntPMOPRMinValue             FixedX10,
                              wchCrntPMOPRMinTimeStamp         DateAndTime,
                              wchCrntPMOPRMinValidity          PMValidity,
                              wchCrntPMOPRMinInitialize        InitializeCmd,
                              wchCrntPMOPRMaxValue             FixedX10,
                              wchCrntPMOPRMaxTimeStamp         DateAndTime,
                              wchCrntPMOPRMaxValidity          PMValidity,
                              wchCrntPMOPRMaxInitialize        InitializeCmd,
                              wchCrntPMOPTValue                FixedX10,
                              wchCrntPMOPTTimeStamp            DateAndTime,
                              wchCrntPMOPTValidity             PMValidity,
                              wchCrntPMOPTMinValue             FixedX10,
                              wchCrntPMOPTMinTimeStamp         DateAndTime,
                              wchCrntPMOPTMinValidity          PMValidity,
                              wchCrntPMOPTMinInitialize        InitializeCmd,
                              wchCrntPMOPTMaxValue             FixedX10,
                              wchCrntPMOPTMaxTimeStamp         DateAndTime,
                              wchCrntPMOPTMaxValidity          PMValidity,
                              wchCrntPMOPTMaxInitialize        InitializeCmd }


wchCrntPMCpTypeIdx OBJECT-TYPE
    SYNTAX       CpType
    MAX-ACCESS   not-accessible
    STATUS       current
    DESCRIPTION  "The type of circuit pack on which the wavelength channel
                  targeted for PMs is located."
    ::= { wchCrntPMEntry 1 }


wchCrntPMShelfIdx OBJECT-TYPE
    SYNTAX       INTEGER (1|11|21|31)
    MAX-ACCESS   not-accessible
    STATUS       current
    DESCRIPTION  "The number of the shelf in which the wavelength channel
                  targeted for PMs is located."
    ::= { wchCrntPMEntry 2 }


wchCrntPMSlotIdx OBJECT-TYPE
    SYNTAX       INTEGER (1..20)
    MAX-ACCESS   not-accessible
    STATUS       current
    DESCRIPTION  "The number of the slot in which the wavelength channel
                  targeted for PMs is located."
    ::= { wchCrntPMEntry 3 }


wchCrntPMPortTypeIdx OBJECT-TYPE
    SYNTAX       OlPortType
    MAX-ACCESS   not-accessible
    STATUS       current
    DESCRIPTION  "The type of port in which the wavelength channel targeted
                  for PMs is located."
    ::= { wchCrntPMEntry 4 }


wchCrntPMPortIdx OBJECT-TYPE
    SYNTAX       INTEGER (1..4)
    MAX-ACCESS   not-accessible
    STATUS       current
    DESCRIPTION  "The number of the port of the specified port type in
                  which the wavelength channel targeted for PMs is located."
    ::= { wchCrntPMEntry 5 }


wchCrntPMIdx OBJECT-TYPE
    SYNTAX       INTEGER (135..610)
    MAX-ACCESS   not-accessible
    STATUS       current
    DESCRIPTION  "The number of the wavelength channel targeted for PMs."
    ::= { wchCrntPMEntry 6 }


wchCrntPMIntervalTypeIdx OBJECT-TYPE
    SYNTAX       PMIntervalType
    MAX-ACCESS   not-accessible
    STATUS       current
    DESCRIPTION  "The type of PM bin according to interval length."
    ::= { wchCrntPMEntry 7 }


wchCrntPMOPRValue OBJECT-TYPE
    SYNTAX       FixedX10
    UNITS        "dBm/10"
    MAX-ACCESS   read-only
    STATUS       current
    DESCRIPTION  "The instantaneous optical power received on the
                  channel."
    ::= { wchCrntPMEntry 8 }


wchCrntPMOPRTimeStamp OBJECT-TYPE
    SYNTAX       DateAndTime
    MAX-ACCESS   read-only
    STATUS       current
    DESCRIPTION  "The date and time stamp of the instantaneous optical
                  power received value."
    ::= { wchCrntPMEntry 9 }


wchCrntPMOPRValidity OBJECT-TYPE
    SYNTAX       PMValidity
    MAX-ACCESS   read-only
    STATUS       current
    DESCRIPTION  "Indicates the validity of the provided instantaneous
                  optical power received value."
    ::= { wchCrntPMEntry 10 }


wchCrntPMOPRMinValue OBJECT-TYPE
    SYNTAX       FixedX10
    UNITS        "dBm/10"
    MAX-ACCESS   read-write
    STATUS       current
    DESCRIPTION  "The minimum optical power received on the channel
                  over the interval. Can be set to the value 0 to initialize."
    ::= { wchCrntPMEntry 11 }


wchCrntPMOPRMinTimeStamp OBJECT-TYPE
    SYNTAX       DateAndTime
    MAX-ACCESS   read-only
    STATUS       current
    DESCRIPTION  "The date and time stamp of the minimum optical
                  power received value."
    ::= { wchCrntPMEntry 12 }


wchCrntPMOPRMinValidity OBJECT-TYPE
    SYNTAX       PMValidity
    MAX-ACCESS   read-only
    STATUS       current
    DESCRIPTION  "Indicates the validity of the provided minimum
                  optical power received value."
    ::= { wchCrntPMEntry 13 }


wchCrntPMOPRMinInitialize OBJECT-TYPE
    SYNTAX       InitializeCmd
    MAX-ACCESS   read-write
    STATUS       current
    DESCRIPTION  "Used to initialize the value of the wchCrntPMOPRMinValue
                  object."
    ::= { wchCrntPMEntry 14 }


wchCrntPMOPRMaxValue OBJECT-TYPE
    SYNTAX       FixedX10
    UNITS        "dBm/10"
    MAX-ACCESS   read-write
    STATUS       current
    DESCRIPTION  "The maximum optical power received on the
                  channel over the interval. Can be set to the
                  value 0 to initialize."
    ::= { wchCrntPMEntry 15 }


wchCrntPMOPRMaxTimeStamp OBJECT-TYPE
    SYNTAX       DateAndTime
    MAX-ACCESS   read-only
    STATUS       current
    DESCRIPTION  "The date and time stamp of the maximum optical
                  power received value."
    ::= { wchCrntPMEntry 16 }


wchCrntPMOPRMaxValidity OBJECT-TYPE
    SYNTAX       PMValidity
    MAX-ACCESS   read-write
    STATUS       current
    DESCRIPTION  "Indicates the validity of the provided maximum
                  optical power received value."
    ::= { wchCrntPMEntry 17 }


wchCrntPMOPRMaxInitialize OBJECT-TYPE
    SYNTAX       InitializeCmd
    MAX-ACCESS   read-write
    STATUS       current
    DESCRIPTION  "Used to initialize the value of the wchCrntPMOPRMaxValue
                  object."
    ::= { wchCrntPMEntry 18 }


wchCrntPMOPTValue OBJECT-TYPE
    SYNTAX       FixedX10
    UNITS        "dBm/10"
    MAX-ACCESS   read-only
    STATUS       current
    DESCRIPTION  "The instantaneous optical power transmitted on the
                  channel."
    ::= { wchCrntPMEntry 19 }


wchCrntPMOPTTimeStamp OBJECT-TYPE
    SYNTAX       DateAndTime
    MAX-ACCESS   read-only
    STATUS       current
    DESCRIPTION  "The date and time stamp of the instantaneous optical
                  power transmitted value."
    ::= { wchCrntPMEntry 20 }


wchCrntPMOPTValidity OBJECT-TYPE
    SYNTAX       PMValidity
    MAX-ACCESS   read-only
    STATUS       current
    DESCRIPTION  "Indicates the validity of the provided instantaneous
                  optical power transmitted value."
    ::= { wchCrntPMEntry 21 }


wchCrntPMOPTMinValue OBJECT-TYPE
    SYNTAX       FixedX10
    UNITS        "dBm/10"
    MAX-ACCESS   read-write
    STATUS       current
    DESCRIPTION  "The minimum optical power transmitted on the channel
                  over the interval. Can be set to the value 0 to initialize."
    ::= { wchCrntPMEntry 22 }


wchCrntPMOPTMinTimeStamp OBJECT-TYPE
    SYNTAX       DateAndTime
    MAX-ACCESS   read-only
    STATUS       current
    DESCRIPTION  "The date and time stamp of the minimum optical
                  power transmitted value."
    ::= { wchCrntPMEntry 23 }


wchCrntPMOPTMinValidity OBJECT-TYPE
    SYNTAX       PMValidity
    MAX-ACCESS   read-only
    STATUS       current
    DESCRIPTION  "Indicates the validity of the provided minimum
                  optical power transmitted value."
    ::= { wchCrntPMEntry 24 }


wchCrntPMOPTMinInitialize OBJECT-TYPE
    SYNTAX       InitializeCmd
    MAX-ACCESS   read-write
    STATUS       current
    DESCRIPTION  "Used to initialize the value of the wchCrntPMOPTMinValue
                  object."
    ::= { wchCrntPMEntry 25 }


wchCrntPMOPTMaxValue OBJECT-TYPE
    SYNTAX       FixedX10
    UNITS        "dBm/10"
    MAX-ACCESS   read-write
    STATUS       current
    DESCRIPTION  "The maximum optical power transmitted on the channel
                  over the interval. Can be set to the value 0 to initialize."
    ::= { wchCrntPMEntry 26 }


wchCrntPMOPTMaxTimeStamp OBJECT-TYPE
    SYNTAX       DateAndTime
    MAX-ACCESS   read-only
    STATUS       current
    DESCRIPTION  "The date and time stamp of the maximum optical
                  power transmitted value."
    ::= { wchCrntPMEntry 27 }


wchCrntPMOPTMaxValidity OBJECT-TYPE
    SYNTAX       PMValidity
    MAX-ACCESS   read-only
    STATUS       current
    DESCRIPTION  "Indicates the validity of the provided maximum
                  optical power transmitted value."
    ::= { wchCrntPMEntry 28 }


wchCrntPMOPTMaxInitialize OBJECT-TYPE
    SYNTAX       InitializeCmd
    MAX-ACCESS   read-write
    STATUS       current
    DESCRIPTION  "Used to initialize the value of the wchCrntPMOPTMaxValue
                  object."
    ::= { wchCrntPMEntry 29 }



-----------------------------------------------------------------------
-- Objects used to retrieve historical performance monitoring
-- statistics for wavelength channels on equipment modules assigned
-- to optical layer groupings.
-----------------------------------------------------------------------


wchHistPMTable OBJECT-TYPE
    SYNTAX       SEQUENCE OF WchHistPMEntry
    MAX-ACCESS   not-accessible
    STATUS       current
    DESCRIPTION  "A table of historical performance monitoring statistics
                  collected for wavelength channels."
    ::= { olPerformance 7 }


wchHistPMEntry OBJECT-TYPE
    SYNTAX       WchHistPMEntry
    MAX-ACCESS   not-accessible
    STATUS       current
    DESCRIPTION  "The row entry object of the Wavelength Channel
                  Historical Performance Monitoring table. Each row of
                  this table contains a full set of PM statistics and
                  related data for a wavelength channel object in an
                  optical layer grouping."
    INDEX        { wchHistPMCpTypeIdx,
                   wchHistPMShelfIdx,
                   wchHistPMSlotIdx,
                   wchHistPMPortTypeIdx,
                   wchHistPMPortIdx,
                   wchHistPMIdx,
                   wchHistPMIntervalTypeIdx,
                   wchHistPMIntervalIdx }
    ::= { wchHistPMTable 1 }


WchHistPMEntry ::= SEQUENCE { wchHistPMCpTypeIdx               CpType,
                              wchHistPMShelfIdx                INTEGER,
                              wchHistPMSlotIdx                 INTEGER,
                              wchHistPMPortTypeIdx             OlPortType,
                              wchHistPMPortIdx                 INTEGER,
                              wchHistPMIdx                     INTEGER,
                              wchHistPMIntervalTypeIdx         PMIntervalType,
                              wchHistPMIntervalIdx             INTEGER,
                              wchHistPMOPRValue                FixedX10,
                              wchHistPMOPRTimeStamp            DateAndTime,
                              wchHistPMOPRValidity             PMValidity,
                              wchHistPMOPRMinValue             FixedX10,
                              wchHistPMOPRMinTimeStamp         DateAndTime,
                              wchHistPMOPRMinValidity          PMValidity,
                              wchHistPMOPRMinInitialize        InitializeCmd,
                              wchHistPMOPRMaxValue             FixedX10,
                              wchHistPMOPRMaxTimeStamp         DateAndTime,
                              wchHistPMOPRMaxValidity          PMValidity,
                              wchHistPMOPRMaxInitialize        InitializeCmd,
                              wchHistPMOPTValue                FixedX10,
                              wchHistPMOPTTimeStamp            DateAndTime,
                              wchHistPMOPTValidity             PMValidity,
                              wchHistPMOPTMinValue             FixedX10,
                              wchHistPMOPTMinTimeStamp         DateAndTime,
                              wchHistPMOPTMinValidity          PMValidity,
                              wchHistPMOPTMinInitialize        InitializeCmd,
                              wchHistPMOPTMaxValue             FixedX10,
                              wchHistPMOPTMaxTimeStamp         DateAndTime,
                              wchHistPMOPTMaxValidity          PMValidity,
                              wchHistPMOPTMaxInitialize        InitializeCmd }


wchHistPMCpTypeIdx OBJECT-TYPE
    SYNTAX       CpType
    MAX-ACCESS   not-accessible
    STATUS       current
    DESCRIPTION  "The type of circuit pack on which the wavelength channel
                  targeted for PMs is located."
    ::= { wchHistPMEntry 1 }


wchHistPMShelfIdx OBJECT-TYPE
    SYNTAX       INTEGER (1|11|21|31)
    MAX-ACCESS   not-accessible
    STATUS       current
    DESCRIPTION  "The number of the shelf in which the wavelength channel
                  targeted for PMs is located."
    ::= { wchHistPMEntry 2 }


wchHistPMSlotIdx OBJECT-TYPE
    SYNTAX       INTEGER (1..20)
    MAX-ACCESS   not-accessible
    STATUS       current
    DESCRIPTION  "The number of the slot in which the wavelength channel
                  targeted for PMs is located."
    ::= { wchHistPMEntry 3 }


wchHistPMPortTypeIdx OBJECT-TYPE
    SYNTAX       OlPortType
    MAX-ACCESS   not-accessible
    STATUS       current
    DESCRIPTION  "The type of port in which the wavelength channel targeted
                  for PMs is located."
    ::= { wchHistPMEntry 4 }


wchHistPMPortIdx OBJECT-TYPE
    SYNTAX       INTEGER (1..4)
    MAX-ACCESS   not-accessible
    STATUS       current
    DESCRIPTION  "The number of the port of the specified port type in
                  which the wavelength channel targeted for PMs is located."
    ::= { wchHistPMEntry 5 }


wchHistPMIdx OBJECT-TYPE
    SYNTAX       INTEGER (135..610)
    MAX-ACCESS   not-accessible
    STATUS       current
    DESCRIPTION  "The number of the wavelength channel targeted for PMs."
    ::= { wchHistPMEntry 6 }


wchHistPMIntervalTypeIdx OBJECT-TYPE
    SYNTAX       PMIntervalType
    MAX-ACCESS   not-accessible
    STATUS       current
    DESCRIPTION  "The type of PM bin according to interval length."
    ::= { wchHistPMEntry 7 }


wchHistPMIntervalIdx OBJECT-TYPE
    SYNTAX       INTEGER (1..96)
    MAX-ACCESS   not-accessible
    STATUS       current
    DESCRIPTION  "The specific PM bin number. The range is 1 to 96 for the
                  15-minute historical bins. For the 1-day historical bin, the
                  value is 1."
    ::= { wchHistPMEntry 8 }


wchHistPMOPRValue OBJECT-TYPE
    SYNTAX       FixedX10
    UNITS        "dBm/10"
    MAX-ACCESS   read-only
    STATUS       current
    DESCRIPTION  "The instantaneous optical power received on the
                  channel."
    ::= { wchHistPMEntry 9 }


wchHistPMOPRTimeStamp OBJECT-TYPE
    SYNTAX       DateAndTime
    MAX-ACCESS   read-only
    STATUS       current
    DESCRIPTION  "The date and time stamp of the instantaneous optical
                  power received value."
    ::= { wchHistPMEntry 10 }


wchHistPMOPRValidity OBJECT-TYPE
    SYNTAX       PMValidity
    MAX-ACCESS   read-only
    STATUS       current
    DESCRIPTION  "Indicates the validity of the provided instantaneous
                  optical power received value."
    ::= { wchHistPMEntry 11 }


wchHistPMOPRMinValue OBJECT-TYPE
    SYNTAX       FixedX10
    UNITS        "dBm/10"
    MAX-ACCESS   read-write
    STATUS       current
    DESCRIPTION  "The minimum optical power received on the channel
                  over the interval. Can be set to the value 0 to initialize
                  the object."
    ::= { wchHistPMEntry 12 }


wchHistPMOPRMinTimeStamp OBJECT-TYPE
    SYNTAX       DateAndTime
    MAX-ACCESS   read-only
    STATUS       current
    DESCRIPTION  "The date and time stamp of the minimum optical
                  power received value."
    ::= { wchHistPMEntry 13 }


wchHistPMOPRMinValidity OBJECT-TYPE
    SYNTAX       PMValidity
    MAX-ACCESS   read-only
    STATUS       current
    DESCRIPTION  "Indicates the validity of the provided minimum
                  optical power received value."
    ::= { wchHistPMEntry 14 }


wchHistPMOPRMinInitialize OBJECT-TYPE
    SYNTAX       InitializeCmd
    MAX-ACCESS   read-write
    STATUS       current
    DESCRIPTION  "Used to initialize the value of the wchHistPMOPRMinValue
                  object."
    ::= { wchHistPMEntry 15 }


wchHistPMOPRMaxValue OBJECT-TYPE
    SYNTAX       FixedX10
    UNITS        "dBm/10"
    MAX-ACCESS   read-write
    STATUS       current
    DESCRIPTION  "The maximum optical power received on the
                  channel over the interval. Can be set to the
                  value 0 to initialize the object."
    ::= { wchHistPMEntry 16 }


wchHistPMOPRMaxTimeStamp OBJECT-TYPE
    SYNTAX       DateAndTime
    MAX-ACCESS   read-only
    STATUS       current
    DESCRIPTION  "The date and time stamp of the maximum optical
                  power received value."
    ::= { wchHistPMEntry 17 }


wchHistPMOPRMaxValidity OBJECT-TYPE
    SYNTAX       PMValidity
    MAX-ACCESS   read-only
    STATUS       current
    DESCRIPTION  "Indicates the validity of the provided maximum
                  optical power received value."
    ::= { wchHistPMEntry 18 }


wchHistPMOPRMaxInitialize OBJECT-TYPE
    SYNTAX       InitializeCmd
    MAX-ACCESS   read-write
    STATUS       current
    DESCRIPTION  "Used to initialize the value of the wchHistPMOPRMaxValue
                  object."
    ::= { wchHistPMEntry 19 }


wchHistPMOPTValue OBJECT-TYPE
    SYNTAX       FixedX10
    UNITS        "dBm/10"
    MAX-ACCESS   read-only
    STATUS       current
    DESCRIPTION  "The instantaneous optical power transmitted on the
                  channel."
    ::= { wchHistPMEntry 20 }


wchHistPMOPTTimeStamp OBJECT-TYPE
    SYNTAX       DateAndTime
    MAX-ACCESS   read-only
    STATUS       current
    DESCRIPTION  "The date and time stamp of the instantaneous optical
                  power transmitted value."
    ::= { wchHistPMEntry 21 }


wchHistPMOPTValidity OBJECT-TYPE
    SYNTAX       PMValidity
    MAX-ACCESS   read-only
    STATUS       current
    DESCRIPTION  "Indicates the validity of the provided instantaneous
                  optical power transmitted value."
    ::= { wchHistPMEntry 22 }


wchHistPMOPTMinValue OBJECT-TYPE
    SYNTAX       FixedX10
    UNITS        "dBm/10"
    MAX-ACCESS   read-write
    STATUS       current
    DESCRIPTION  "The minimum optical power transmitted on the channel
                  over the interval. Can be set to the value 0 to initialize
                  the object."
    ::= { wchHistPMEntry 23 }


wchHistPMOPTMinTimeStamp OBJECT-TYPE
    SYNTAX       DateAndTime
    MAX-ACCESS   read-only
    STATUS       current
    DESCRIPTION  "The date and time stamp of the minimum optical
                  power transmitted value."
    ::= { wchHistPMEntry 24 }


wchHistPMOPTMinValidity OBJECT-TYPE
    SYNTAX       PMValidity
    MAX-ACCESS   read-only
    STATUS       current
    DESCRIPTION  "Indicates the validity of the provided minimum
                  optical power transmitted value."
    ::= { wchHistPMEntry 25 }


wchHistPMOPTMinInitialize OBJECT-TYPE
    SYNTAX       InitializeCmd
    MAX-ACCESS   read-write
    STATUS       current
    DESCRIPTION  "Used to initialize the value of the wchHistPMOPTMinValue
                  object."
    ::= { wchHistPMEntry 26 }


wchHistPMOPTMaxValue OBJECT-TYPE
    SYNTAX       FixedX10
    UNITS        "dBm/10"
    MAX-ACCESS   read-write
    STATUS       current
    DESCRIPTION  "The maximum optical power transmitted on the channel
                  over the interval. Can be set to the value 0 to initialize
                  the object."
    ::= { wchHistPMEntry 27 }


wchHistPMOPTMaxTimeStamp OBJECT-TYPE
    SYNTAX       DateAndTime
    MAX-ACCESS   read-only
    STATUS       current
    DESCRIPTION  "The date and time stamp of the maximum optical
                  power transmitted value."
    ::= { wchHistPMEntry 28 }


wchHistPMOPTMaxValidity OBJECT-TYPE
    SYNTAX       PMValidity
    MAX-ACCESS   read-only
    STATUS       current
    DESCRIPTION  "Indicates the validity of the provided maximum
                  optical power transmitted value."
    ::= { wchHistPMEntry 29 }


wchHistPMOPTMaxInitialize OBJECT-TYPE
    SYNTAX       InitializeCmd
    MAX-ACCESS   read-write
    STATUS       current
    DESCRIPTION  "Used to initialize the value of the wchHistPMOPTMaxValue
                  object."
    ::= { wchHistPMEntry 30 }



-----------------------------------------------------------------------
-- Optical Layer Trap Definitions.
-----------------------------------------------------------------------

olOSCEvtNotifications    OBJECT IDENTIFIER ::= { olEvtNotifications 1 }
olPortEvtNotifications   OBJECT IDENTIFIER ::= { olEvtNotifications 2 }
wdmEvtNotifications      OBJECT IDENTIFIER ::= { olEvtNotifications 3 }
wchEvtNotifications      OBJECT IDENTIFIER ::= { olEvtNotifications 4 }

olOSCCondNotifications   OBJECT IDENTIFIER ::= { olCondNotifications 1 }
olPortCondNotifications  OBJECT IDENTIFIER ::= { olCondNotifications 2 }
wdmCondNotifications     OBJECT IDENTIFIER ::= { olCondNotifications 3 }
wchCondNotifications     OBJECT IDENTIFIER ::= { olCondNotifications 4 }


-----------------------------------------------------------------------
-- Optical Layer Event Traps.
-----------------------------------------------------------------------


olOSCStatusChangeEvt NOTIFICATION-TYPE
    OBJECTS      { olOSCCpTypeIdx,
                   olOSCShelfIdx,
                   olOSCSlotIdx,
                   olOSCLineIdx,
                   olOSCOperStatus,
                   olOSCOperStatQlfr,
                   evtDateAndTime,
                   trapSeqNum,
                   evtDescription,
                   evtObjectType,
                   evtCodeType }
    STATUS       current
    DESCRIPTION  "Notification of a change in the operational status or
                  operational status qualifier or an optical layer OSC
                  facility."
    ::= { olOSCEvtNotifications 0 1 }


olOSCTcaEvt NOTIFICATION-TYPE
    OBJECTS      { olOSCCpTypeIdx,
                   olOSCShelfIdx,
                   olOSCSlotIdx,
                   olOSCLineIdx,
                   tcaIntervalType,
                   tcaDateAndTime,
                   tcaMontype,
                   tcaValue,
                   tcaThreshold,
                   evtDateAndTime,
                   trapSeqNum,
                   evtDescription,
                   evtObjectType,
                   evtCodeType }
    STATUS       current
    DESCRIPTION  "This trap provides a threshold crossing alert for a
                  performance monitoring statistic on an optical layer
                  OSC facility."
    ::= { olOSCEvtNotifications 0 2 }



olPortStatusChangeEvt NOTIFICATION-TYPE
    OBJECTS      { olPortCpTypeIdx,
                   olPortShelfIdx,
                   olPortSlotIdx,
                   olPortTypeIdx,
                   olPortIdx,
                   olPortOperStatus,
                   olPortOperStatQlfr,
                   evtDateAndTime,
                   trapSeqNum,
                   evtDescription,
                   evtObjectType,
                   evtCodeType }
    STATUS       current
    DESCRIPTION  "Notification of a change in the operational status or
                  operational status qualifier or an optical layer port."
    ::= { olPortEvtNotifications 0 1 }


wdmStatusChangeEvt NOTIFICATION-TYPE
    OBJECTS      { wdmCpTypeIdx,
                   wdmShelfIdx,
                   wdmSlotIdx,
                   wdmLineIdx,
                   olPortIdx,
                   wdmOperStatus,
                   wdmOperStatQlfr,
                   evtDateAndTime,
                   trapSeqNum,
                   evtDescription,
                   evtObjectType,
                   evtCodeType }
    STATUS       current
    DESCRIPTION  "Notification of a change in the operational status or
                  operational status qualifier or an optical layer WDM
                  object."
    ::= { wdmEvtNotifications 0 1 }


wchStatusChangeEvt NOTIFICATION-TYPE
    OBJECTS      { wchCpTypeIdx,
                   wchShelfIdx,
                   wchSlotIdx,
                   wchPortTypeIdx,
                   wchPortIdx,
                   wchIdx,
                   wchOperStatus,
                   wchOperStatQlfr,
                   evtDateAndTime,
                   trapSeqNum,
                   evtDescription,
                   evtObjectType,
                   evtCodeType }
    STATUS       current
    DESCRIPTION  "Notification of a change in the operational status or
                  operational status qualifier or an optical layer WDM
                  object."
    ::= { wchEvtNotifications 0 1 }



-----------------------------------------------------------------------
-- Optical Layer Condition Traps.
-----------------------------------------------------------------------


olOSCLossOfLightRxCond NOTIFICATION-TYPE
    OBJECTS      { olOSCCpTypeIdx,
                   olOSCShelfIdx,
                   olOSCSlotIdx,
                   olOSCLineIdx,
                   condReportType,
                   condDateAndTime,
                   condSeverity,
                   condServiceAffecting,
                   trapSeqNum,
                   condDescription,
                   condObjectType,
                   condCodeType }
    STATUS       current
    DESCRIPTION  "There is no input signal detected for the identified OSC."
    ::= { olOSCCondNotifications 0 1 }


olOSCLossOfLightRxClear NOTIFICATION-TYPE
    OBJECTS      { olOSCCpTypeIdx,
                   olOSCShelfIdx,
                   olOSCSlotIdx,
                   olOSCLineIdx,
                   condReportType,
                   condDateAndTime,
                   condSeverity,
                   condServiceAffecting,
                   trapSeqNum,
                   condDescription,
                   condObjectType,
                   condCodeType }
    STATUS       current
    DESCRIPTION  "A previously active optical layer OSC Receive Loss of Light
                  condition has cleared."
    ::= { olOSCCondNotifications 0 2 }


olOSCLossOfFrameCond NOTIFICATION-TYPE
    OBJECTS      { olOSCCpTypeIdx,
                   olOSCShelfIdx,
                   olOSCSlotIdx,
                   olOSCLineIdx,
                   condReportType,
                   condDateAndTime,
                   condSeverity,
                   condServiceAffecting,
                   trapSeqNum,
                   condDescription,
                   condObjectType,
                   condCodeType }
    STATUS       current
    DESCRIPTION  "There input OSC signal cannot be framed."
    ::= { olOSCCondNotifications 0 3 }


olOSCLossOfFrameClear NOTIFICATION-TYPE
    OBJECTS      { olOSCCpTypeIdx,
                   olOSCShelfIdx,
                   olOSCSlotIdx,
                   olOSCLineIdx,
                   condReportType,
                   condDateAndTime,
                   condSeverity,
                   condServiceAffecting,
                   trapSeqNum,
                   condDescription,
                   condObjectType,
                   condCodeType }
    STATUS       current
    DESCRIPTION  "A previously active optical layer OSC Loss of Frame
                  condition has cleared."
    ::= { olOSCCondNotifications 0 4 }


olOSCLossOfLightTxCond NOTIFICATION-TYPE
    OBJECTS      { olOSCCpTypeIdx,
                   olOSCShelfIdx,
                   olOSCSlotIdx,
                   olOSCLineIdx,
                   condReportType,
                   condDateAndTime,
                   condSeverity,
                   condServiceAffecting,
                   trapSeqNum,
                   condDescription,
                   condObjectType,
                   condCodeType }
    STATUS       current
    DESCRIPTION  "There is no transmitted signal power detected for the
                  identified OSC."
    ::= { olOSCCondNotifications 0 5 }


olOSCLossOfLightTxClear NOTIFICATION-TYPE
    OBJECTS      { olOSCCpTypeIdx,
                   olOSCShelfIdx,
                   olOSCSlotIdx,
                   olOSCLineIdx,
                   condReportType,
                   condDateAndTime,
                   condSeverity,
                   condServiceAffecting,
                   trapSeqNum,
                   condDescription,
                   condObjectType,
                   condCodeType }
    STATUS       current
    DESCRIPTION  "A previously active optical layer OSC Transmit Loss of
                  Light condition has cleared."
    ::= { olOSCCondNotifications 0 6 }


olOSCFarEndIdMismatchCond NOTIFICATION-TYPE
    OBJECTS      { olOSCCpTypeIdx,
                   olOSCShelfIdx,
                   olOSCSlotIdx,
                   olOSCLineIdx,
                   condReportType,
                   condDateAndTime,
                   condSeverity,
                   condServiceAffecting,
                   trapSeqNum,
                   condDescription,
                   condObjectType,
                   condCodeType }
    STATUS       current
    DESCRIPTION  "The identifying attributes received for the far-end node
                  do not match the expected identifying attributes."
    ::= { olOSCCondNotifications 0 7 }


olOSCFarEndIdMismatchClear NOTIFICATION-TYPE
    OBJECTS      { olOSCCpTypeIdx,
                   olOSCShelfIdx,
                   olOSCSlotIdx,
                   olOSCLineIdx,
                   condReportType,
                   condDateAndTime,
                   condSeverity,
                   condServiceAffecting,
                   trapSeqNum,
                   condDescription,
                   condObjectType,
                   condCodeType }
    STATUS       current
    DESCRIPTION  "A previously active optical layer OSC Far End Identification
                  Mismatch condition has cleared."
    ::= { olOSCCondNotifications 0 8 }


olOSCFarEndNodeCnfgInconsistentCond NOTIFICATION-TYPE
    OBJECTS      { olOSCCpTypeIdx,
                   olOSCShelfIdx,
                   olOSCSlotIdx,
                   olOSCLineIdx,
                   condReportType,
                   condDateAndTime,
                   condSeverity,
                   condServiceAffecting,
                   trapSeqNum,
                   condDescription,
                   condObjectType,
                   condCodeType }
    STATUS       current
    DESCRIPTION  "The optical layer group configuration type for the far-end
                  node is inconsistent with the configuration type of
                  the local optical layer group."
    ::= { olOSCCondNotifications 0 9 }


olOSCFarEndNodeCnfgInconsistentClear NOTIFICATION-TYPE
    OBJECTS      { olOSCCpTypeIdx,
                   olOSCShelfIdx,
                   olOSCSlotIdx,
                   olOSCLineIdx,
                   condReportType,
                   condDateAndTime,
                   condSeverity,
                   condServiceAffecting,
                   trapSeqNum,
                   condDescription,
                   condObjectType,
                   condCodeType }
    STATUS       current
    DESCRIPTION  "A previously active optical layer OSC Far End Node
                  Configuration Inconsistent condition has cleared."
    ::= { olOSCCondNotifications 0 10 }


olOSCSpanContCommCond NOTIFICATION-TYPE
    OBJECTS      { olOSCCpTypeIdx,
                   olOSCShelfIdx,
                   olOSCSlotIdx,
                   olOSCLineIdx,
                   condReportType,
                   condDateAndTime,
                   condSeverity,
                   condServiceAffecting,
                   trapSeqNum,
                   condDescription,
                   condObjectType,
                   condCodeType }
    STATUS       current
    DESCRIPTION  "Bi-directional control communications with the node at the
                  opposite end of the span section have failed."
    ::= { olOSCCondNotifications 0 11 }


olOSCSpanContCommClear NOTIFICATION-TYPE
    OBJECTS      { olOSCCpTypeIdx,
                   olOSCShelfIdx,
                   olOSCSlotIdx,
                   olOSCLineIdx,
                   condReportType,
                   condDateAndTime,
                   condSeverity,
                   condServiceAffecting,
                   trapSeqNum,
                   condDescription,
                   condObjectType,
                   condCodeType }
    STATUS       current
    DESCRIPTION  "A previously active optical layer OSC Section Control
                  Communications condition has cleared."
    ::= { olOSCCondNotifications 0 12 }


olOSCEqlzContCommCond NOTIFICATION-TYPE
    OBJECTS      { olOSCCpTypeIdx,
                   olOSCShelfIdx,
                   olOSCSlotIdx,
                   olOSCLineIdx,
                   condReportType,
                   condDateAndTime,
                   condSeverity,
                   condServiceAffecting,
                   trapSeqNum,
                   condDescription,
                   condObjectType,
                   condCodeType }
    STATUS       current
    DESCRIPTION  "Bi-directional control communications with the node at the
                  opposite end of the equalization section have failed."
    ::= { olOSCCondNotifications 0 13 }


olOSCEqlzContCommClear NOTIFICATION-TYPE
    OBJECTS      { olOSCCpTypeIdx,
                   olOSCShelfIdx,
                   olOSCSlotIdx,
                   olOSCLineIdx,
                   condReportType,
                   condDateAndTime,
                   condSeverity,
                   condServiceAffecting,
                   trapSeqNum,
                   condDescription,
                   condObjectType,
                   condCodeType }
    STATUS       current
    DESCRIPTION  "A previously active optical layer OSC Equalization Control
                  Communications condition has cleared."
    ::= { olOSCCondNotifications 0 14 }


olOSCOpticalBackReflOutOfSpecCond NOTIFICATION-TYPE
    OBJECTS      { olOSCCpTypeIdx,
                   olOSCShelfIdx,
                   olOSCSlotIdx,
                   olOSCLineIdx,
                   condReportType,
                   condDateAndTime,
                   condSeverity,
                   condServiceAffecting,
                   trapSeqNum,
                   condDescription,
                   condObjectType,
                   condCodeType }
    STATUS       current
    DESCRIPTION  "The measured optical back reflection of the transmitted
                  OSC signal exceeds the specified maximum."
    ::= { olOSCCondNotifications 0 15 }


olOSCOpticalBackReflOutOfSpecClear NOTIFICATION-TYPE
    OBJECTS      { olOSCCpTypeIdx,
                   olOSCShelfIdx,
                   olOSCSlotIdx,
                   olOSCLineIdx,
                   condReportType,
                   condDateAndTime,
                   condSeverity,
                   condServiceAffecting,
                   trapSeqNum,
                   condDescription,
                   condObjectType,
                   condCodeType }
    STATUS       current
    DESCRIPTION  "A previously active optical layer OSC Optical Back
                  Reflection Out of Specification condition has cleared."
    ::= { olOSCCondNotifications 0 16 }


olOSCOpticalBackReflHighThCond NOTIFICATION-TYPE
    OBJECTS      { olOSCCpTypeIdx,
                   olOSCShelfIdx,
                   olOSCSlotIdx,
                   olOSCLineIdx,
                   condReportType,
                   condDateAndTime,
                   condSeverity,
                   condServiceAffecting,
                   trapSeqNum,
                   condDescription,
                   condObjectType,
                   condCodeType }
    STATUS       current
    DESCRIPTION  "The measured optical back reflection of the transmitted
                  OSC signal exceeds the high threshold."
    ::= { olOSCCondNotifications 0 17 }


olOSCOpticalBackReflHighThClear NOTIFICATION-TYPE
    OBJECTS      { olOSCCpTypeIdx,
                   olOSCShelfIdx,
                   olOSCSlotIdx,
                   olOSCLineIdx,
                   condReportType,
                   condDateAndTime,
                   condSeverity,
                   condServiceAffecting,
                   trapSeqNum,
                   condDescription,
                   condObjectType,
                   condCodeType }
    STATUS       current
    DESCRIPTION  "A previously active optical layer OSC Optical Back
                  Reflection High Threshold condition has cleared."
    ::= { olOSCCondNotifications 0 18 }


olPortPowerOutOfSpecRxCond NOTIFICATION-TYPE
    OBJECTS      { olPortCpTypeIdx,
                   olPortShelfIdx,
                   olPortSlotIdx,
                   olPortTypeIdx,
                   olPortIdx,
                   condReportType,
                   condDateAndTime,
                   condSeverity,
                   condServiceAffecting,
                   trapSeqNum,
                   condDescription,
                   condObjectType,
                   condCodeType }
    STATUS       current
    DESCRIPTION  "The power received on the optical port is outside the
                  operating range."
    ::= { olPortCondNotifications 0 1 }


olPortPowerOutOfSpecRxClear NOTIFICATION-TYPE
    OBJECTS      { olPortCpTypeIdx,
                   olPortShelfIdx,
                   olPortSlotIdx,
                   olPortTypeIdx,
                   olPortIdx,
                   condReportType,
                   condDateAndTime,
                   condSeverity,
                   condServiceAffecting,
                   trapSeqNum,
                   condDescription,
                   condObjectType,
                   condCodeType }
    STATUS       current
    DESCRIPTION  "A previously active optical layer port Received Power
                  Out Of Specification condition has cleared."
    ::= { olPortCondNotifications 0 2 }


olPortLossOfLightRxCond NOTIFICATION-TYPE
    OBJECTS      { olPortCpTypeIdx,
                   olPortShelfIdx,
                   olPortSlotIdx,
                   olPortTypeIdx,
                   olPortIdx,
                   condReportType,
                   condDateAndTime,
                   condSeverity,
                   condServiceAffecting,
                   trapSeqNum,
                   condDescription,
                   condObjectType,
                   condCodeType }
    STATUS       current
    DESCRIPTION  "There is no received optical power detected for the port."
    ::= { olPortCondNotifications 0 3 }


olPortLossOfLightRxClear NOTIFICATION-TYPE
    OBJECTS      { olPortCpTypeIdx,
                   olPortShelfIdx,
                   olPortSlotIdx,
                   olPortTypeIdx,
                   olPortIdx,
                   condReportType,
                   condDateAndTime,
                   condSeverity,
                   condServiceAffecting,
                   trapSeqNum,
                   condDescription,
                   condObjectType,
                   condCodeType }
    STATUS       current
    DESCRIPTION  "A previously active optical layer port Receive Loss of Light
                  condition has cleared."
    ::= { olPortCondNotifications 0 4 }


olPortLossRxOutOfSpecCond NOTIFICATION-TYPE
    OBJECTS      { olPortCpTypeIdx,
                   olPortShelfIdx,
                   olPortSlotIdx,
                   olPortTypeIdx,
                   olPortIdx,
                   condReportType,
                   condDateAndTime,
                   condSeverity,
                   condServiceAffecting,
                   trapSeqNum,
                   condDescription,
                   condObjectType,
                   condCodeType }
    STATUS       current
    DESCRIPTION  "The optical power loss measured over the span or
                  fiber connection terminating on the port in the
                  receive direction is outside the specification range."
    ::= { olPortCondNotifications 0 5 }


olPortLossRxOutOfSpecClear NOTIFICATION-TYPE
    OBJECTS      { olPortCpTypeIdx,
                   olPortShelfIdx,
                   olPortSlotIdx,
                   olPortTypeIdx,
                   olPortIdx,
                   condReportType,
                   condDateAndTime,
                   condSeverity,
                   condServiceAffecting,
                   trapSeqNum,
                   condDescription,
                   condObjectType,
                   condCodeType }
    STATUS       current
    DESCRIPTION  "A previously active optical layer port Receive Loss out of
                  Specification condition has cleared."
    ::= { olPortCondNotifications 0 6 }


olPortLossRxHighThCond NOTIFICATION-TYPE
    OBJECTS      { olPortCpTypeIdx,
                   olPortShelfIdx,
                   olPortSlotIdx,
                   olPortTypeIdx,
                   olPortIdx,
                   condReportType,
                   condDateAndTime,
                   condSeverity,
                   condServiceAffecting,
                   trapSeqNum,
                   condDescription,
                   condObjectType,
                   condCodeType }
    STATUS       current
    DESCRIPTION  "The optical power loss measured over the span terminating
                  on the line port in the receive direction is above
                  the high threshold level."
    ::= { olPortCondNotifications 0 7 }


olPortLossRxHighThClear NOTIFICATION-TYPE
    OBJECTS      { olPortCpTypeIdx,
                   olPortShelfIdx,
                   olPortSlotIdx,
                   olPortTypeIdx,
                   olPortIdx,
                   condReportType,
                   condDateAndTime,
                   condSeverity,
                   condServiceAffecting,
                   trapSeqNum,
                   condDescription,
                   condObjectType,
                   condCodeType }
    STATUS       current
    DESCRIPTION  "A previously active optical layer port Receive Loss
                  High Threshold condition has cleared."
    ::= { olPortCondNotifications 0 8 }


olPortAPSDCond NOTIFICATION-TYPE
    OBJECTS      { olPortCpTypeIdx,
                   olPortShelfIdx,
                   olPortSlotIdx,
                   olPortTypeIdx,
                   olPortIdx,
                   condReportType,
                   condDateAndTime,
                   condSeverity,
                   condServiceAffecting,
                   trapSeqNum,
                   condDescription,
                   condObjectType,
                   condCodeType }
    STATUS       current
    DESCRIPTION  "An automatic power shutdown has been automatically operated
                  on the optical layer port for safety reasons."
    ::= { olPortCondNotifications 0 9 }


olPortAPSDClear NOTIFICATION-TYPE
    OBJECTS      { olPortCpTypeIdx,
                   olPortShelfIdx,
                   olPortSlotIdx,
                   olPortTypeIdx,
                   olPortIdx,
                   condReportType,
                   condDateAndTime,
                   condSeverity,
                   condServiceAffecting,
                   trapSeqNum,
                   condDescription,
                   condObjectType,
                   condCodeType }
    STATUS       current
    DESCRIPTION  "A previously active optical layer port Automatic Power Shutdown
                  condition has cleared."
    ::= { olPortCondNotifications 0 10 }


olPortPayloadMissingIndCond NOTIFICATION-TYPE
    OBJECTS      { olPortCpTypeIdx,
                   olPortShelfIdx,
                   olPortSlotIdx,
                   olPortTypeIdx,
                   olPortIdx,
                   condReportType,
                   condDateAndTime,
                   condSeverity,
                   condServiceAffecting,
                   trapSeqNum,
                   condDescription,
                   condObjectType,
                   condCodeType }
    STATUS       current
    DESCRIPTION  "A Payload Missing Indication has been received on the
                  optical layer port input."
    ::= { olPortCondNotifications 0 11 }


olPortPayloadMissingIndClear NOTIFICATION-TYPE
    OBJECTS      { olPortCpTypeIdx,
                   olPortShelfIdx,
                   olPortSlotIdx,
                   olPortTypeIdx,
                   olPortIdx,
                   condReportType,
                   condDateAndTime,
                   condSeverity,
                   condServiceAffecting,
                   trapSeqNum,
                   condDescription,
                   condObjectType,
                   condCodeType }
    STATUS       current
    DESCRIPTION  "A previously active optical layer port Payload Missing
                  Indication condition has cleared."
    ::= { olPortCondNotifications 0 12 }


olPortBackwardDefectIndCond NOTIFICATION-TYPE
    OBJECTS      { olPortCpTypeIdx,
                   olPortShelfIdx,
                   olPortSlotIdx,
                   olPortTypeIdx,
                   olPortIdx,
                   condReportType,
                   condDateAndTime,
                   condSeverity,
                   condServiceAffecting,
                   trapSeqNum,
                   condDescription,
                   condObjectType,
                   condCodeType }
    STATUS       current
    DESCRIPTION  "A Backward Defect Indication has been received on the
                  optical layer port input."
    ::= { olPortCondNotifications 0 13 }


olPortBackwardDefectIndClear NOTIFICATION-TYPE
    OBJECTS      { olPortCpTypeIdx,
                   olPortShelfIdx,
                   olPortSlotIdx,
                   olPortTypeIdx,
                   olPortIdx,
                   condReportType,
                   condDateAndTime,
                   condSeverity,
                   condServiceAffecting,
                   trapSeqNum,
                   condDescription,
                   condObjectType,
                   condCodeType }
    STATUS       current
    DESCRIPTION  "A previously active optical layer port Backward Defect
                  Indication condition has cleared."
    ::= { olPortCondNotifications 0 14 }


olPortChannelCountDeficiencyCond NOTIFICATION-TYPE
    OBJECTS      { olPortCpTypeIdx,
                   olPortShelfIdx,
                   olPortSlotIdx,
                   olPortTypeIdx,
                   olPortIdx,
                   condReportType,
                   condDateAndTime,
                   condSeverity,
                   condServiceAffecting,
                   trapSeqNum,
                   condDescription,
                   condObjectType,
                   condCodeType }
    STATUS       current
    DESCRIPTION  "A channel count deficiency condition has been raised against
                  the port. This indicates that the number of channels
                  received on the port is less than the number required to
                  maintain stable optical control given the high span loss
                  level detected on the receive span fiber."
    ::= { olPortCondNotifications 0 15 }


olPortChannelCountDeficiencyClear NOTIFICATION-TYPE
    OBJECTS      { olPortCpTypeIdx,
                   olPortShelfIdx,
                   olPortSlotIdx,
                   olPortTypeIdx,
                   olPortIdx,
                   condReportType,
                   condDateAndTime,
                   condSeverity,
                   condServiceAffecting,
                   trapSeqNum,
                   condDescription,
                   condObjectType,
                   condCodeType }
    STATUS       current
    DESCRIPTION  "A previously active optical layer port Channel Count
                  Deficiency condition has cleared."
    ::= { olPortCondNotifications 0 16 }


olPortConnectionMismatchCond NOTIFICATION-TYPE
    OBJECTS      { olPortCpTypeIdx,
                   olPortShelfIdx,
                   olPortSlotIdx,
                   olPortTypeIdx,
                   olPortIdx,
                   olPortExpCnxDegree,
                   olPortActCnxDegree,
                   condReportType,
                   condDateAndTime,
                   condSeverity,
                   condServiceAffecting,
                   trapSeqNum,
                   condDescription,
                   condObjectType,
                   condCodeType }
    STATUS       current
    DESCRIPTION  "The identified optical layer port is incorrectly
                  connected and must be re-connected to a different
                  remote end port."
    ::= { olPortCondNotifications 0 17 }


olPortConnectionMismatchClear NOTIFICATION-TYPE
    OBJECTS      { olPortCpTypeIdx,
                   olPortShelfIdx,
                   olPortSlotIdx,
                   olPortTypeIdx,
                   olPortIdx,
                   condReportType,
                   condDateAndTime,
                   condSeverity,
                   condServiceAffecting,
                   trapSeqNum,
                   condDescription,
                   condObjectType,
                   condCodeType }
    STATUS       current
    DESCRIPTION  "A previously active optical layer port Connection
                  Mismatch condition has cleared."
    ::= { olPortCondNotifications 0 18 }


olPortConnectionValidationTimeoutCond NOTIFICATION-TYPE
    OBJECTS      { olPortCpTypeIdx,
                   olPortShelfIdx,
                   olPortSlotIdx,
                   olPortTypeIdx,
                   olPortIdx,
                   condReportType,
                   condDateAndTime,
                   condSeverity,
                   condServiceAffecting,
                   trapSeqNum,
                   condDescription,
                   condObjectType,
                   condCodeType }
    STATUS       current
    DESCRIPTION  "Connection validation could not be performed on the
                  identified optical layer port, which may mean that the
                  port is incorrectly connected."
    ::= { olPortCondNotifications 0 19 }


olPortConnectionValidationTimeoutClear NOTIFICATION-TYPE
    OBJECTS      { olPortCpTypeIdx,
                   olPortShelfIdx,
                   olPortSlotIdx,
                   olPortTypeIdx,
                   olPortIdx,
                   condReportType,
                   condDateAndTime,
                   condSeverity,
                   condServiceAffecting,
                   trapSeqNum,
                   condDescription,
                   condObjectType,
                   condCodeType }
    STATUS       current
    DESCRIPTION  "A previously active optical layer port Connection
                  Validation Timeout condition has cleared."
    ::= { olPortCondNotifications 0 20 }


wdmInvalidPreAmpOperCnfgCond NOTIFICATION-TYPE
    OBJECTS      { wdmCpTypeIdx,
                   wdmShelfIdx,
                   wdmSlotIdx,
                   wdmLineIdx,
                   condReportType,
                   condDateAndTime,
                   condSeverity,
                   condServiceAffecting,
                   trapSeqNum,
                   condDescription,
                   condObjectType,
                   condCodeType }
    STATUS       current
    DESCRIPTION  "The WDM optical pre-amplifier is operating at a configuration
                  which is invalid for the detected loss."
    ::= { wdmCondNotifications 0 1 }


wdmInvalidPreAmpOperCnfgClear NOTIFICATION-TYPE
    OBJECTS      { wdmCpTypeIdx,
                   wdmShelfIdx,
                   wdmSlotIdx,
                   wdmLineIdx,
                   condReportType,
                   condDateAndTime,
                   condSeverity,
                   condServiceAffecting,
                   trapSeqNum,
                   condDescription,
                   condObjectType,
                   condCodeType }
    STATUS       current
    DESCRIPTION  "A previously active WDM Invalid Pre-Amplifier Operating
                  Configuration condition has cleared."
    ::= { wdmCondNotifications 0 2 }


wdmInvalidMidAmpOperCnfgCond NOTIFICATION-TYPE
    OBJECTS      { wdmCpTypeIdx,
                   wdmShelfIdx,
                   wdmSlotIdx,
                   wdmLineIdx,
                   condReportType,
                   condDateAndTime,
                   condSeverity,
                   condServiceAffecting,
                   trapSeqNum,
                   condDescription,
                   condObjectType,
                   condCodeType }
    STATUS       current
    DESCRIPTION  "The WDM optical mid-amplifier is operating at a configuration
                  which is invalid for the detected loss."
    ::= { wdmCondNotifications 0 3 }


wdmInvalidMidAmpOperCnfgClear NOTIFICATION-TYPE
    OBJECTS      { wdmCpTypeIdx,
                   wdmShelfIdx,
                   wdmSlotIdx,
                   wdmLineIdx,
                   condReportType,
                   condDateAndTime,
                   condSeverity,
                   condServiceAffecting,
                   trapSeqNum,
                   condDescription,
                   condObjectType,
                   condCodeType }
    STATUS       current
    DESCRIPTION  "A previously active WDM Invalid Mid-Amplifier Operating
                  Configuration condition has cleared."
    ::= { wdmCondNotifications 0 4 }


wdmInvalidBoostAmpOperCnfgCond NOTIFICATION-TYPE
    OBJECTS      { wdmCpTypeIdx,
                   wdmShelfIdx,
                   wdmSlotIdx,
                   wdmLineIdx,
                   condReportType,
                   condDateAndTime,
                   condSeverity,
                   condServiceAffecting,
                   trapSeqNum,
                   condDescription,
                   condObjectType,
                   condCodeType }
    STATUS       current
    DESCRIPTION  "The WDM optical booster-amplifier is operating at a configuration
                  which is invalid for the detected loss."
    ::= { wdmCondNotifications 0 5 }


wdmInvalidBoostAmpOperCnfgClear NOTIFICATION-TYPE
    OBJECTS      { wdmCpTypeIdx,
                   wdmShelfIdx,
                   wdmSlotIdx,
                   wdmLineIdx,
                   condReportType,
                   condDateAndTime,
                   condSeverity,
                   condServiceAffecting,
                   trapSeqNum,
                   condDescription,
                   condObjectType,
                   condCodeType }
    STATUS       current
    DESCRIPTION  "A previously active WDM Invalid Booster-Amplifier Operating
                  Configuration condition has cleared."
    ::= { wdmCondNotifications 0 6 }


wchPowerOutOfSpecRxCond NOTIFICATION-TYPE
    OBJECTS      { wchCpTypeIdx,
                   wchShelfIdx,
                   wchSlotIdx,
                   wchPortTypeIdx,
                   wchPortIdx,
                   wchIdx,
                   condReportType,
                   condDateAndTime,
                   condSeverity,
                   condServiceAffecting,
                   trapSeqNum,
                   condDescription,
                   condObjectType,
                   condCodeType }
    STATUS       deprecated
    DESCRIPTION  "The power received for the wavelength channel is outside the
                  operating range."
    ::= { wchCondNotifications 0 1 }


wchPowerOutOfSpecRxClear NOTIFICATION-TYPE
    OBJECTS      { wchCpTypeIdx,
                   wchShelfIdx,
                   wchSlotIdx,
                   wchPortTypeIdx,
                   wchPortIdx,
                   wchIdx,
                   condReportType,
                   condDateAndTime,
                   condSeverity,
                   condServiceAffecting,
                   trapSeqNum,
                   condDescription,
                   condObjectType,
                   condCodeType }
    STATUS       deprecated
    DESCRIPTION  "A previously active Wavelength Channel Received Power Out Of
                  Specification condition has cleared."
    ::= { wchCondNotifications 0 2 }


wchLossOfLightRxCond NOTIFICATION-TYPE
    OBJECTS      { wchCpTypeIdx,
                   wchShelfIdx,
                   wchSlotIdx,
                   wchPortTypeIdx,
                   wchPortIdx,
                   wchIdx,
                   condReportType,
                   condDateAndTime,
                   condSeverity,
                   condServiceAffecting,
                   trapSeqNum,
                   condDescription,
                   condObjectType,
                   condCodeType }
    STATUS       current
    DESCRIPTION  "There is no received optical power detected for the channel."
    ::= { wchCondNotifications 0 3 }


wchLossOfLightRxClear NOTIFICATION-TYPE
    OBJECTS      { wchCpTypeIdx,
                   wchShelfIdx,
                   wchSlotIdx,
                   wchPortTypeIdx,
                   wchPortIdx,
                   wchIdx,
                   condReportType,
                   condDateAndTime,
                   condSeverity,
                   condServiceAffecting,
                   trapSeqNum,
                   condDescription,
                   condObjectType,
                   condCodeType }
    STATUS       current
    DESCRIPTION  "A previously active wavelength channel Receive Loss of Light condition
                  has cleared."
    ::= { wchCondNotifications 0 4 }


wchPowerOutOfSpecTxCond NOTIFICATION-TYPE
    OBJECTS      { wchCpTypeIdx,
                   wchShelfIdx,
                   wchSlotIdx,
                   wchPortTypeIdx,
                   wchPortIdx,
                   wchIdx,
                   condReportType,
                   condDateAndTime,
                   condSeverity,
                   condServiceAffecting,
                   trapSeqNum,
                   condDescription,
                   condObjectType,
                   condCodeType }
    STATUS       current
    DESCRIPTION  "The power transmitted for the wavelength channel is outside the
                  operating range."
    ::= { wchCondNotifications 0 5 }


wchPowerOutOfSpecTxClear NOTIFICATION-TYPE
    OBJECTS      { wchCpTypeIdx,
                   wchShelfIdx,
                   wchSlotIdx,
                   wchPortTypeIdx,
                   wchPortIdx,
                   wchIdx,
                   condReportType,
                   condDateAndTime,
                   condSeverity,
                   condServiceAffecting,
                   trapSeqNum,
                   condDescription,
                   condObjectType,
                   condCodeType }
    STATUS       current
    DESCRIPTION  "A previously active Wavelength Channel Transmitted Power Out Of
                  Specification condition has cleared."
    ::= { wchCondNotifications 0 6 }


wchLossOfLightTxCond NOTIFICATION-TYPE
    OBJECTS      { wchCpTypeIdx,
                   wchShelfIdx,
                   wchSlotIdx,
                   wchPortTypeIdx,
                   wchPortIdx,
                   wchIdx,
                   condReportType,
                   condDateAndTime,
                   condSeverity,
                   condServiceAffecting,
                   trapSeqNum,
                   condDescription,
                   condObjectType,
                   condCodeType }
    STATUS       current
    DESCRIPTION  "There is no transmitted optical power detected for the channel."
    ::= { wchCondNotifications 0 7 }


wchLossOfLightTxClear NOTIFICATION-TYPE
    OBJECTS      { wchCpTypeIdx,
                   wchShelfIdx,
                   wchSlotIdx,
                   wchPortTypeIdx,
                   wchPortIdx,
                   wchIdx,
                   condReportType,
                   condDateAndTime,
                   condSeverity,
                   condServiceAffecting,
                   trapSeqNum,
                   condDescription,
                   condObjectType,
                   condCodeType }
    STATUS       current
    DESCRIPTION  "A previously active wavelength channel Transmitted Loss of Light
                  condition has cleared."
    ::= { wchCondNotifications 0 8 }


wchUnequippedCond NOTIFICATION-TYPE
    OBJECTS      { wchCpTypeIdx,
                   wchShelfIdx,
                   wchSlotIdx,
                   wchPortTypeIdx,
                   wchPortIdx,
                   wchIdx,
                   condReportType,
                   condDateAndTime,
                   condSeverity,
                   condServiceAffecting,
                   trapSeqNum,
                   condDescription,
                   condObjectType,
                   condCodeType }
    STATUS       current
    DESCRIPTION  "An unequipped indication for the wavelength channel has been
                  received from the far-end node of the line span."
    ::= { wchCondNotifications 0 9 }


wchUnequippedClear NOTIFICATION-TYPE
    OBJECTS      { wchCpTypeIdx,
                   wchShelfIdx,
                   wchSlotIdx,
                   wchPortTypeIdx,
                   wchPortIdx,
                   wchIdx,
                   condReportType,
                   condDateAndTime,
                   condSeverity,
                   condServiceAffecting,
                   trapSeqNum,
                   condDescription,
                   condObjectType,
                   condCodeType }
    STATUS       current
    DESCRIPTION  "A previously active wavelength channel unequipped indication
                  condition has cleared."
    ::= { wchCondNotifications 0 10 }


wchAISCond NOTIFICATION-TYPE
    OBJECTS      { wchCpTypeIdx,
                   wchShelfIdx,
                   wchSlotIdx,
                   wchPortTypeIdx,
                   wchPortIdx,
                   wchIdx,
                   condReportType,
                   condDateAndTime,
                   condSeverity,
                   condServiceAffecting,
                   trapSeqNum,
                   condDescription,
                   condObjectType,
                   condCodeType }
    STATUS       current
    DESCRIPTION  "An alarm indication signal for the wavelength channel has been
                  received from the far-end node of the line span."
    ::= { wchCondNotifications 0 11 }


wchAISClear NOTIFICATION-TYPE
    OBJECTS      { wchCpTypeIdx,
                   wchShelfIdx,
                   wchSlotIdx,
                   wchPortTypeIdx,
                   wchPortIdx,
                   wchIdx,
                   condReportType,
                   condDateAndTime,
                   condSeverity,
                   condServiceAffecting,
                   trapSeqNum,
                   condDescription,
                   condObjectType,
                   condCodeType }
    STATUS       current
    DESCRIPTION  "A previously active wavelength channel alarm indication signal
                  condition has cleared."
    ::= { wchCondNotifications 0 12 }


wchPowerOutOfSpecRxHighCond NOTIFICATION-TYPE
    OBJECTS      { wchCpTypeIdx,
                   wchShelfIdx,
                   wchSlotIdx,
                   wchPortTypeIdx,
                   wchPortIdx,
                   wchIdx,
                   condReportType,
                   condDateAndTime,
                   condSeverity,
                   condServiceAffecting,
                   trapSeqNum,
                   condDescription,
                   condObjectType,
                   condCodeType }
    STATUS       deprecated
    DESCRIPTION  "The power received for the wavelength channel exceeds the
                  upper limit of the normal operating range."
    ::= { wchCondNotifications 0 13 }


wchPowerOutOfSpecRxHighClear NOTIFICATION-TYPE
    OBJECTS      { wchCpTypeIdx,
                   wchShelfIdx,
                   wchSlotIdx,
                   wchPortTypeIdx,
                   wchPortIdx,
                   wchIdx,
                   condReportType,
                   condDateAndTime,
                   condSeverity,
                   condServiceAffecting,
                   trapSeqNum,
                   condDescription,
                   condObjectType,
                   condCodeType }
    STATUS       deprecated
    DESCRIPTION  "A previously active Wavelength Channel Received Power Out Of
                  Specification High condition has cleared."
    ::= { wchCondNotifications 0 14 }


wchPowerOutOfSpecRxLowCond NOTIFICATION-TYPE
    OBJECTS      { wchCpTypeIdx,
                   wchShelfIdx,
                   wchSlotIdx,
                   wchPortTypeIdx,
                   wchPortIdx,
                   wchIdx,
                   condReportType,
                   condDateAndTime,
                   condSeverity,
                   condServiceAffecting,
                   trapSeqNum,
                   condDescription,
                   condObjectType,
                   condCodeType }
    STATUS       deprecated
    DESCRIPTION  "The power received for the wavelength channel is below the
                  lower limit of the normal operating range."
    ::= { wchCondNotifications 0 15 }


wchPowerOutOfSpecRxLowClear NOTIFICATION-TYPE
    OBJECTS      { wchCpTypeIdx,
                   wchShelfIdx,
                   wchSlotIdx,
                   wchPortTypeIdx,
                   wchPortIdx,
                   wchIdx,
                   condReportType,
                   condDateAndTime,
                   condSeverity,
                   condServiceAffecting,
                   trapSeqNum,
                   condDescription,
                   condObjectType,
                   condCodeType }
    STATUS       deprecated
    DESCRIPTION  "A previously active Wavelength Channel Received Power Out Of
                  Specification Low condition has cleared."
    ::= { wchCondNotifications 0 16 }


wchPowerRxHighFailCond NOTIFICATION-TYPE
    OBJECTS      { wchCpTypeIdx,
                   wchShelfIdx,
                   wchSlotIdx,
                   wchPortTypeIdx,
                   wchPortIdx,
                   wchIdx,
                   condReportType,
                   condDateAndTime,
                   condSeverity,
                   condServiceAffecting,
                   trapSeqNum,
                   condDescription,
                   condObjectType,
                   condCodeType }
    STATUS       deprecated
    DESCRIPTION  "The power received for the wavelength channel exceeds the
                  maximum allowable level. The wavelength channel is declared
                  to be failed at this power level."
    ::= { wchCondNotifications 0 17 }


wchPowerRxHighFailClear NOTIFICATION-TYPE
    OBJECTS      { wchCpTypeIdx,
                   wchShelfIdx,
                   wchSlotIdx,
                   wchPortTypeIdx,
                   wchPortIdx,
                   wchIdx,
                   condReportType,
                   condDateAndTime,
                   condSeverity,
                   condServiceAffecting,
                   trapSeqNum,
                   condDescription,
                   condObjectType,
                   condCodeType }
    STATUS       deprecated
    DESCRIPTION  "A previously active Wavelength Channel Received Power
                  High Fail condition has cleared."
    ::= { wchCondNotifications 0 18 }



END -- End of BTI-OL-MIB Module, must a /NL character at the end this line!
