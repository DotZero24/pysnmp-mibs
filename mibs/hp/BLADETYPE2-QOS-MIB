-- COPYRIGHT NOTICE
-- Copyright (c) Hewlett Packard Company, 2004
-- All rights reserved
--
--

BLADETYPE2-QOS-MIB DEFINITIONS ::= BEGIN

IMPORTS
    MODULE-IDENTITY, OBJECT-TYPE, Integer32, Unsigned32, Counter32, Gauge32, TimeTicks
        FROM SNMPv2-SMI
    DisplayString, PhysAddress
        FROM SNMPv2-TC
    BridgeId
        FROM BRIDGE-MIB
    hpSwitchBladeType2-Mgmt
        FROM HP-SWITCH-PL-MIB;

qos  MODULE-IDENTITY
    LAST-UPDATED "200312050000Z" --  5 December 2003
    ORGANIZATION "Hewlett Packard Company"
    CONTACT-INFO "customerservice@hp.com"
    DESCRIPTION
        "The MIB module for the QOS configuration, statistics and
         information ."
    ::= { hpSwitchBladeType2-Mgmt 8 }

-- MIB_INSERT_START
-- ----------------------------------------------------------------------------
-- { INSERT:  bt2qos
-- ----------------------------------------------------------------------------

qosConfigs     OBJECT IDENTIFIER ::= { qos 1 }
qosStats       OBJECT IDENTIFIER ::= { qos 2 }
qosInfo        OBJECT IDENTIFIER ::= { qos 3 }
qosOper        OBJECT IDENTIFIER ::= { qos 4 }

qos8021p   OBJECT IDENTIFIER ::= { qosConfigs 1 }
aclCfg  OBJECT IDENTIFIER ::= { qosConfigs 2 }

-- QOS Configuration

qosCurCfgPortPriorityTable OBJECT-TYPE
    SYNTAX SEQUENCE OF QoSCurCfgPortPriorityEntry
    MAX-ACCESS not-accessible
    STATUS current
    DESCRIPTION
        "The table of QOS Port Priority configuration."
    ::= { qos8021p  1 }

qosCurCfgPortPriorityEntry OBJECT-TYPE
    SYNTAX QoSCurCfgPortPriorityEntry
    MAX-ACCESS not-accessible
    STATUS current
    DESCRIPTION
        "Information about a particular QOS Port Priority configuration."
    INDEX { qosCurCfgPortIndex }
    ::= { qosCurCfgPortPriorityTable 1 }

QoSCurCfgPortPriorityEntry ::= SEQUENCE {
    qosCurCfgPortIndex      Integer32,
    qosCurCfgPortPriority   INTEGER
    }

qosCurCfgPortIndex  OBJECT-TYPE
    SYNTAX  Integer32
    MAX-ACCESS  read-only
    STATUS  current
    DESCRIPTION
        "Switch Port Number"
    ::= { qosCurCfgPortPriorityEntry 1 }

qosCurCfgPortPriority  OBJECT-TYPE
    SYNTAX  INTEGER  (0..7)
    MAX-ACCESS  read-only
    STATUS  current
    DESCRIPTION
        "Switch Port Priority Should be between 0 and 7"
    ::= { qosCurCfgPortPriorityEntry 2 }

qosNewCfgPortPriorityTable OBJECT-TYPE
    SYNTAX SEQUENCE OF QoSNewCfgPortPriorityEntry
    MAX-ACCESS not-accessible
    STATUS current
    DESCRIPTION
        "The table of QOS Port Priority configuration."
    ::= { qos8021p  2 }

qosNewCfgPortPriorityEntry OBJECT-TYPE
    SYNTAX QoSNewCfgPortPriorityEntry
    MAX-ACCESS not-accessible
    STATUS current
    DESCRIPTION
        "Information about a particular QOS Port Priority configuration."
    INDEX { qosNewCfgPortIndex }
    ::= { qosNewCfgPortPriorityTable 1 }

QoSNewCfgPortPriorityEntry ::= SEQUENCE {
    qosNewCfgPortIndex      Integer32,
    qosNewCfgPortPriority   INTEGER
    }

qosNewCfgPortIndex  OBJECT-TYPE
    SYNTAX  Integer32
    MAX-ACCESS  read-only
    STATUS  current
    DESCRIPTION
        "Switch Port Number"
    ::= { qosNewCfgPortPriorityEntry 1 }

qosNewCfgPortPriority  OBJECT-TYPE
    SYNTAX  INTEGER  (0..7)
    MAX-ACCESS  read-write
    STATUS  current
    DESCRIPTION
        "Switch Port Priority Should be between 0 and 7"
    ::= { qosNewCfgPortPriorityEntry 2 }

qosCurCfgPriorityCoSTable OBJECT-TYPE
    SYNTAX SEQUENCE OF QoSCurCfgPriorityCoSEntry
    MAX-ACCESS not-accessible
    STATUS current
    DESCRIPTION
        "The table of Frame Priority and COSq configuration."
    ::= { qos8021p  3 }

qosCurCfgPriorityCoSEntry OBJECT-TYPE
    SYNTAX QoSCurCfgPriorityCoSEntry
    MAX-ACCESS not-accessible
    STATUS current
    DESCRIPTION
        "Information about a particular Frame Priority and COSq configuration."
    INDEX { qosCurCfgPriorityIndex }
    ::= { qosCurCfgPriorityCoSTable 1 }

QoSCurCfgPriorityCoSEntry ::= SEQUENCE {
    qosCurCfgPriorityIndex INTEGER,
    qosCurCfgPriorityCoSq  INTEGER
    }

qosCurCfgPriorityIndex  OBJECT-TYPE
    SYNTAX  INTEGER  (0..7)
    MAX-ACCESS  read-only
    STATUS  current
    DESCRIPTION
        "Frame priority Number"
    ::= { qosCurCfgPriorityCoSEntry 1 }

qosCurCfgPriorityCoSq  OBJECT-TYPE
    SYNTAX  INTEGER  (0..7)
    MAX-ACCESS  read-only
    STATUS  current
    DESCRIPTION
        "CoSq for a Frame Priority Should be between 0 and 7"
    ::= { qosCurCfgPriorityCoSEntry 2 }

qosNewCfgPriorityCoSTable OBJECT-TYPE
    SYNTAX SEQUENCE OF QoSNewCfgPriorityCoSEntry
    MAX-ACCESS not-accessible
    STATUS current
    DESCRIPTION
        "The table of Frame Priority and COSq configuration."
    ::= { qos8021p  4 }

qosNewCfgPriorityCoSEntry OBJECT-TYPE
    SYNTAX QoSNewCfgPriorityCoSEntry
    MAX-ACCESS not-accessible
    STATUS current
    DESCRIPTION
        "Information about a particular Frame Priority and COSq configuration."
    INDEX { qosNewCfgPriorityIndex }
    ::= { qosNewCfgPriorityCoSTable 1 }

QoSNewCfgPriorityCoSEntry ::= SEQUENCE {
    qosNewCfgPriorityIndex INTEGER,
    qosNewCfgPriorityCoSq  INTEGER
    }

qosNewCfgPriorityIndex  OBJECT-TYPE
    SYNTAX  INTEGER  (0..7)
    MAX-ACCESS  read-only
    STATUS  current
    DESCRIPTION
        "Frame priority Number"
    ::= { qosNewCfgPriorityCoSEntry 1 }

qosNewCfgPriorityCoSq  OBJECT-TYPE
    SYNTAX  INTEGER  (0..7)
    MAX-ACCESS  read-write
    STATUS  current
    DESCRIPTION
        "CoSq for a Frame Priority Should be between 0 and 7"
    ::= { qosNewCfgPriorityCoSEntry 2 }

qosCurCfgCosWeightTable OBJECT-TYPE
    SYNTAX SEQUENCE OF QoSCurCfgCosWeightEntry
    MAX-ACCESS not-accessible
    STATUS current
    DESCRIPTION
        "The table of CoSq and Weight configuration."
    ::= { qos8021p  5 }

qosCurCfgCosWeightEntry OBJECT-TYPE
    SYNTAX QoSCurCfgCosWeightEntry
    MAX-ACCESS not-accessible
    STATUS current
    DESCRIPTION
        "Information about a particular CoSq and Weight configuration."
    INDEX { qosCurCfgCosIndex }
    ::= { qosCurCfgCosWeightTable 1 }

QoSCurCfgCosWeightEntry ::= SEQUENCE {
    qosCurCfgCosIndex    INTEGER,
    qosCurCfgCosWeight   INTEGER
    }

qosCurCfgCosIndex  OBJECT-TYPE
    SYNTAX  INTEGER  (0..7)
    MAX-ACCESS  read-only
    STATUS  current
    DESCRIPTION
        "CoSq Number"
    ::= { qosCurCfgCosWeightEntry 1 }

qosCurCfgCosWeight  OBJECT-TYPE
    SYNTAX  INTEGER  (0..15)
    MAX-ACCESS  read-only
    STATUS  current
    DESCRIPTION
        "Weight of CoSq"
    ::= { qosCurCfgCosWeightEntry 2 }

qosNewCfgCosWeightTable OBJECT-TYPE
    SYNTAX SEQUENCE OF QoSNewCfgCosWeightEntry
    MAX-ACCESS not-accessible
    STATUS current
    DESCRIPTION
        "The table of CoSq and Weight configuration."
    ::= { qos8021p  6 }

qosNewCfgCosWeightEntry OBJECT-TYPE
    SYNTAX QoSNewCfgCosWeightEntry
    MAX-ACCESS not-accessible
    STATUS current
    DESCRIPTION
        "Information about a particular CoSq and Weight configuration."
    INDEX { qosNewCfgCosIndex }
    ::= { qosNewCfgCosWeightTable 1 }

QoSNewCfgCosWeightEntry ::= SEQUENCE {
    qosNewCfgCosIndex    INTEGER,
    qosNewCfgCosWeight   INTEGER
    }

qosNewCfgCosIndex  OBJECT-TYPE
    SYNTAX INTEGER  (0..7)
    MAX-ACCESS read-only
    STATUS  current
    DESCRIPTION
        "CoSq Number"
    ::= { qosNewCfgCosWeightEntry 1 }

qosNewCfgCosWeight  OBJECT-TYPE
    SYNTAX INTEGER  (0..15)
    MAX-ACCESS  read-write
    STATUS  current
    DESCRIPTION
        "Weight of CoSq"
    ::= { qosNewCfgCosWeightEntry 2 }

qosCurCfgCosNum OBJECT-TYPE
    SYNTAX  INTEGER {
	num2(2),
	num8(8)
	}
    MAX-ACCESS  read-only
    STATUS  current
    DESCRIPTION
        "Number of CoSq."
    ::= { qos8021p 7 }

qosNewCfgCosNum OBJECT-TYPE
    SYNTAX  INTEGER {
	num2(2),
	num8(8)
	}
    MAX-ACCESS  read-write
    STATUS  current
    DESCRIPTION
        "Number of CoSq."
    ::= { qos8021p 8 }

aclCurCfgPortTable OBJECT-TYPE
    SYNTAX SEQUENCE OF AclCurCfgPortTableEntry
    MAX-ACCESS not-accessible
    STATUS current
    DESCRIPTION
        "The table of port acl groups configuration."
    ::= { aclCfg 1 }

aclCurCfgPortTableEntry OBJECT-TYPE
    SYNTAX AclCurCfgPortTableEntry
    MAX-ACCESS not-accessible
    STATUS current
    DESCRIPTION
        "Information about a particular port acl groups configuration."
    INDEX { aclCurCfgPortIndex }
    ::= { aclCurCfgPortTable 1 }

AclCurCfgPortTableEntry ::= SEQUENCE {
    aclCurCfgPortIndex    Integer32,
    aclCurCfgPortAclBmap  OCTET STRING,
    aclCurCfgPortAclBlkBmap  OCTET STRING,
    aclCurCfgPortAclGrpBmap  OCTET STRING
    }

aclCurCfgPortIndex OBJECT-TYPE
    SYNTAX Integer32
    MAX-ACCESS read-only
    STATUS current
    DESCRIPTION
        "The identifier of a particular port.  This is also
         index to the entLogicalTable of Entity MIB."
    ::= { aclCurCfgPortTableEntry 1 }

aclCurCfgPortAclBmap OBJECT-TYPE
    SYNTAX  OCTET STRING (SIZE(0..512))
    MAX-ACCESS  read-only
    STATUS  current
    DESCRIPTION
        "The acls applied to the port.  The acls are
         presented in bitmap format. This string displays acl number
         from 1 to 4096.

         in receiving order:

             OCTET 1  OCTET 2  .....
             xxxxxxxx xxxxxxxx .....
             ||    || |_ acl 9
             ||    ||
             ||    ||___ acl 8
             ||    |____ acl 7
             ||      .    .   .
             ||_________ acl 2
             |__________ acl 1

         where x : 1 - The represented acl applied to the port.
                   0 - The represented acl not applied to the port."
    ::= { aclCurCfgPortTableEntry 2 }


aclCurCfgPortAclBlkBmap OBJECT-TYPE
    SYNTAX  OCTET STRING (SIZE(0..512))
    MAX-ACCESS  read-only
    STATUS  current
    DESCRIPTION
        "The acl blocks applied to the port.  The acl blocks are
         presented in bitmap format. This string displays acl number
         from 1 to 4096.

         in receiving order:

             OCTET 1  OCTET 2  .....
             xxxxxxxx xxxxxxxx .....
             ||    || |_ aclblk 9
             ||    ||
             ||    ||___ aclblk 8
             ||    |____ aclblk 7
             ||      .    .   .
             ||_________ aclblk 2
             |__________ aclblk 1

         where x : 1 - The represented acl block applied to the port.
                   0 - The represented acl block not applied to the port."
    ::= { aclCurCfgPortTableEntry 3 }


aclCurCfgPortAclGrpBmap OBJECT-TYPE
    SYNTAX  OCTET STRING (SIZE(0..512))
    MAX-ACCESS  read-only
    STATUS  current
    DESCRIPTION
        "The acl groups applied to the port.  The acls are
         presented in bitmap format. This string displays acl number
         from 1 to 4096.

         in receiving order:

             OCTET 1  OCTET 2  .....
             xxxxxxxx xxxxxxxx .....
             ||    || |_ aclgrp 9
             ||    ||
             ||    ||___ aclgrp 8
             ||    |____ aclgrp 7
             ||      .    .   .
             ||_________ aclgrp 2
             |__________ aclgrp 1

         where x : 1 - The represented acl applied to the port.
                   0 - The represented acl not applied to the port."
    ::= { aclCurCfgPortTableEntry 4 }

aclNewCfgPortTable OBJECT-TYPE
    SYNTAX SEQUENCE OF AclNewCfgPortTableEntry
    MAX-ACCESS not-accessible
    STATUS current
    DESCRIPTION
        "The table of port acl groups configuration."
    ::= { aclCfg 2 }

aclNewCfgPortTableEntry OBJECT-TYPE
    SYNTAX AclNewCfgPortTableEntry
    MAX-ACCESS not-accessible
    STATUS current
    DESCRIPTION
        "Information about a particular port acl groups configuration."
    INDEX { aclNewCfgPortIndex }
    ::= { aclNewCfgPortTable 1 }

AclNewCfgPortTableEntry ::= SEQUENCE {
    aclNewCfgPortIndex         Integer32,
    aclNewCfgPortAddAcl        Unsigned32,
    aclNewCfgPortAddAclBlk     Unsigned32,
    aclNewCfgPortAddAclGrp     Unsigned32,
    aclNewCfgPortRemoveAcl     Unsigned32,
    aclNewCfgPortRemoveAclBlk  Unsigned32,
    aclNewCfgPortRemoveAclGrp  Unsigned32,
    aclNewCfgPortAclBmap       OCTET STRING,
    aclNewCfgPortAclBlkBmap    OCTET STRING,
    aclNewCfgPortAclGrpBmap    OCTET STRING
    }

aclNewCfgPortIndex  OBJECT-TYPE
    SYNTAX Integer32
    MAX-ACCESS read-only
    STATUS current
    DESCRIPTION
        "The identifier of a particular port. This is also
         index to the entLogicalTable of Entity MIB."
    ::= { aclNewCfgPortTableEntry 1 }

aclNewCfgPortAddAcl OBJECT-TYPE
    SYNTAX  Unsigned32
    MAX-ACCESS  read-write
    STATUS  current
    DESCRIPTION
        "The acl to be added to the specified port.  A
         '0' value is returned when read."
    ::= {aclNewCfgPortTableEntry 2 }

aclNewCfgPortAddAclBlk OBJECT-TYPE
    SYNTAX  Unsigned32
    MAX-ACCESS  read-write
    STATUS  current
    DESCRIPTION
        "The acl block to be added to the specified port.  A
         '0' value is returned when read."
    ::= {aclNewCfgPortTableEntry 3 }

aclNewCfgPortAddAclGrp OBJECT-TYPE
    SYNTAX  Unsigned32
    MAX-ACCESS  read-write
    STATUS  current
    DESCRIPTION
        "The acl group to be added to the specified port.  A
         '0' value is returned when read."
    ::= {aclNewCfgPortTableEntry 4 }

aclNewCfgPortRemoveAcl OBJECT-TYPE
    SYNTAX  Unsigned32
    MAX-ACCESS  read-write
    STATUS  current
    DESCRIPTION
        "The acl to be removed from the specified port.
         A '0' value is returned when read."
    ::= { aclNewCfgPortTableEntry 5 }

aclNewCfgPortRemoveAclBlk OBJECT-TYPE
    SYNTAX  Unsigned32
    MAX-ACCESS  read-write
    STATUS  current
    DESCRIPTION
        "The acl block to be removed from the specified port.
         A '0' value is returned when read."
    ::= { aclNewCfgPortTableEntry 6 }

aclNewCfgPortRemoveAclGrp OBJECT-TYPE
    SYNTAX  Unsigned32
    MAX-ACCESS  read-write
    STATUS  current
    DESCRIPTION
        "The acl group to be removed from the specified port.
         A '0' value is returned when read."
    ::= { aclNewCfgPortTableEntry 7 }

aclNewCfgPortAclBmap OBJECT-TYPE
    SYNTAX  OCTET STRING (SIZE(0..512))
    MAX-ACCESS  read-only
    STATUS  current
    DESCRIPTION
        "The acls applied to the port.  The acls are
         presented in bitmap format. This string displays acl number
         from 1 to 4096.

         in receiving order:

             OCTET 1  OCTET 2  .....
             xxxxxxxx xxxxxxxx .....
             ||    || |_ acl 9
             ||    ||
             ||    ||___ acl 8
             ||    |____ acl 7
             ||      .    .   .
             ||_________ acl 2
             |__________ acl 1

         where x : 1 - The represented acl applied to the port.
                   0 - The represented acl not applied to the port."
    ::= { aclNewCfgPortTableEntry 8 }

aclNewCfgPortAclBlkBmap OBJECT-TYPE
    SYNTAX  OCTET STRING (SIZE(0..512))
    MAX-ACCESS  read-only
    STATUS  current
    DESCRIPTION
        "The acl blocks applied to the port.  The acl blocks are
         presented in bitmap format. This string displays block number
         from 1 to 4096.

         in receiving order:

             OCTET 1  OCTET 2  .....
             xxxxxxxx xxxxxxxx .....
             ||    || |_ aclblk 9
             ||    ||
             ||    ||___ aclblk 8
             ||    |____ aclblk 7
             ||      .    .   .
             ||_________ aclblk 2
             |__________ aclblk 1

         where x : 1 - The represented acl block applied to the port.
                   0 - The represented acl block not applied to the port."
    ::= { aclNewCfgPortTableEntry 9 }

aclNewCfgPortAclGrpBmap OBJECT-TYPE
    SYNTAX  OCTET STRING (SIZE(0..512))
    MAX-ACCESS  read-only
    STATUS  current
    DESCRIPTION
        "The acl groups applied to the port.  The acl groups are
         presented in bitmap format. This string displays group number
         from 1 to 4096.

         in receiving order:

             OCTET 1  OCTET 2  .....
             xxxxxxxx xxxxxxxx .....
             ||    || |_ aclgrp 9
             ||    ||
             ||    ||___ aclgrp 8
             ||    |____ aclgrp 7
             ||      .    .   .
             ||_________ aclgrp 2
             |__________ aclgrp 1

         where x : 1 - The represented acl group applied to the port.
                   0 - The represented acl group not applied to the port."
    ::= { aclNewCfgPortTableEntry 10 }

aclCurCfgPortAclMeterTable OBJECT-TYPE
    SYNTAX  SEQUENCE OF AclCurCfgPortAclMeterTableEntry
    MAX-ACCESS  not-accessible
    STATUS  current
    DESCRIPTION
        "The table of port acl meter configuration in the current_config."
    ::= { aclCfg 3 }

aclCurCfgPortAclMeterTableEntry OBJECT-TYPE
    SYNTAX  AclCurCfgPortAclMeterTableEntry
    MAX-ACCESS  not-accessible
    STATUS  current
    DESCRIPTION
        "Information about acl meter configuration of a particular port."
    INDEX   { aclCurCfgPortMeterConfigIndex, aclCurCfgAclMeterIndex }
    ::= { aclCurCfgPortAclMeterTable 1 }

AclCurCfgPortAclMeterTableEntry ::= SEQUENCE {
    aclCurCfgPortMeterConfigIndex          Integer32,
    aclCurCfgAclMeterIndex                 Integer32,
    aclCurCfgAclMeterCommitRate       INTEGER,
    aclCurCfgAclMeterMaxBurstSize     INTEGER,
    aclCurCfgAclMeterStatus           INTEGER,
    aclCurCfgAclMeterDropOrPass            INTEGER,
    aclCurCfgAclMeterAclBmap               OCTET STRING,
    aclCurCfgAclMeterAclBlkBmap            OCTET STRING,
    aclCurCfgAclMeterAclGrpBmap            OCTET STRING
	}

aclCurCfgPortMeterConfigIndex OBJECT-TYPE
    SYNTAX Integer32
    MAX-ACCESS read-only
    STATUS current
    DESCRIPTION
        "The identifier of a particular port.  This is also
         index to the entLogicalTable of Entity MIB."
    ::= { aclCurCfgPortAclMeterTableEntry 1 }

aclCurCfgAclMeterIndex OBJECT-TYPE
    SYNTAX Integer32
    MAX-ACCESS read-only
    STATUS current
    DESCRIPTION
        "The acl meter identifier of a particular port."
    ::= { aclCurCfgPortAclMeterTableEntry 2 }

aclCurCfgAclMeterCommitRate OBJECT-TYPE
    SYNTAX INTEGER (1000..1000000)
    MAX-ACCESS read-only
    STATUS current
    DESCRIPTION
        "Committed rate of acl meter for specified port in kilobits/sec."
    ::= { aclCurCfgPortAclMeterTableEntry 3 }

aclCurCfgAclMeterMaxBurstSize OBJECT-TYPE
    SYNTAX INTEGER {
        k32(32),
        k64(64),
        k128(128),
        k256(256),
        k512(512),
        k1024(1024),
        k2048(2048),
        k4096(4096)
        }
    MAX-ACCESS read-only
    STATUS current
    DESCRIPTION
        "Maximum burst size of acl meter for specified port in kilobits."
    ::= { aclCurCfgPortAclMeterTableEntry 4 }

aclCurCfgAclMeterStatus OBJECT-TYPE
    SYNTAX  INTEGER {
	enabled(1),
	disabled(2)
	}
    MAX-ACCESS read-only
    STATUS current
    DESCRIPTION
       "The metering status of acl meter for specified port."
    ::= { aclCurCfgPortAclMeterTableEntry 5 }

aclCurCfgAclMeterDropOrPass OBJECT-TYPE
    SYNTAX  INTEGER {
	none(1),
	drop(2),
	pass(3)
	}
    MAX-ACCESS read-only
    STATUS current
    DESCRIPTION
       "The state of out profile to drop or pass for acl meter of a
        specified port."
    ::= { aclCurCfgPortAclMeterTableEntry 6 }

aclCurCfgAclMeterAclBmap OBJECT-TYPE
    SYNTAX  OCTET STRING (SIZE(0..512))
    MAX-ACCESS  read-only
    STATUS  current
    DESCRIPTION
        "The acls assigned to this meter.  The acls are
         presented in bitmap format. This string displays acl number
         from 1 to 4096.

         in receiving order:

             OCTET 1  OCTET 2  .....
             xxxxxxxx xxxxxxxx .....
             ||    || |_ acl 9
             ||    ||
             ||    ||___ acl 8
             ||    |____ acl 7
             ||      .    .   .
             ||_________ acl 2
             |__________ acl 1

         where x : 1 - The represented acl assigned to the meter.
                   0 - The represented acl not assigned to the meter."
    ::= { aclCurCfgPortAclMeterTableEntry 7 }

aclCurCfgAclMeterAclBlkBmap OBJECT-TYPE
    SYNTAX  OCTET STRING (SIZE(0..512))
    MAX-ACCESS  read-only
    STATUS  current
    DESCRIPTION
        "The acl blocks assigned to this meter.  The blocks are
         presented in bitmap format. This string displays block number
         from 1 to 4096.

         in receiving order:

             OCTET 1  OCTET 2  .....
             xxxxxxxx xxxxxxxx .....
             ||    || |_ aclblk 9
             ||    ||
             ||    ||___ aclblk 8
             ||    |____ aclblk 7
             ||      .    .   .
             ||_________ aclblk 2
             |__________ aclblk 1

         where x : 1 - The represented acl block assigned to the meter.
                   0 - The represented acl blocknot assigned to the meter."
    ::= { aclCurCfgPortAclMeterTableEntry 8 }

aclCurCfgAclMeterAclGrpBmap OBJECT-TYPE
    SYNTAX  OCTET STRING (SIZE(0..512))
    MAX-ACCESS  read-only
    STATUS  current
    DESCRIPTION
        "The acl groups assigned to this meter.  The groups are
         presented in bitmap format. This string displays group number
         from 1 to 4096.

         in receiving order:

             OCTET 1  OCTET 2  .....
             xxxxxxxx xxxxxxxx .....
             ||    || |_ aclgrp 9
             ||    ||
             ||    ||___ aclgrp 8
             ||    |____ aclgrp 7
             ||      .    .   .
             ||_________ aclgrp 2
             |__________ aclgrp 1

         where x : 1 - The represented acl group assigned to the meter.
                   0 - The represented acl group not assigned to the meter."
    ::= { aclCurCfgPortAclMeterTableEntry 9 }


aclNewCfgPortAclMeterTable OBJECT-TYPE
    SYNTAX  SEQUENCE OF AclNewCfgPortAclMeterTableEntry
    MAX-ACCESS  not-accessible
    STATUS  current
    DESCRIPTION
        "The table of port acl meter configuration in the new_config."
    ::= { aclCfg 4 }

aclNewCfgPortAclMeterTableEntry OBJECT-TYPE
    SYNTAX  AclNewCfgPortAclMeterTableEntry
    MAX-ACCESS  not-accessible
    STATUS  current
    DESCRIPTION
        "Information about acl meter configuration of a particular port."
    INDEX   { aclNewCfgPortMeterConfigIndex, aclNewCfgAclMeterIndex }
    ::= { aclNewCfgPortAclMeterTable 1 }

AclNewCfgPortAclMeterTableEntry ::= SEQUENCE {
    aclNewCfgPortMeterConfigIndex          Integer32,
    aclNewCfgAclMeterIndex           Integer32,
    aclNewCfgAclMeterCommitRate      INTEGER,
    aclNewCfgAclMeterMaxBurstSize    INTEGER,
    aclNewCfgAclMeterStatus          INTEGER,
    aclNewCfgAclMeterDropOrPass            INTEGER,
    aclNewCfgAclMeterAssignAcl             Unsigned32,
    aclNewCfgAclMeterAssignAclBlk          Unsigned32,
    aclNewCfgAclMeterAssignAclGrp          Unsigned32,
    aclNewCfgAclMeterUnAssignAcl           Unsigned32,
    aclNewCfgAclMeterUnAssignAclBlk        Unsigned32,
    aclNewCfgAclMeterUnAssignAclGrp        Unsigned32,
    aclNewCfgAclMeterAclBmap               OCTET STRING,
    aclNewCfgAclMeterAclBlkBmap            OCTET STRING,
    aclNewCfgAclMeterAclGrpBmap            OCTET STRING
	}

aclNewCfgPortMeterConfigIndex OBJECT-TYPE
    SYNTAX Integer32
    MAX-ACCESS read-only
    STATUS current
    DESCRIPTION
        "The identifier of a particular port.  This is also
         index to the entLogicalTable of Entity MIB."
    ::= { aclNewCfgPortAclMeterTableEntry 1 }

aclNewCfgAclMeterIndex OBJECT-TYPE
    SYNTAX Integer32
    MAX-ACCESS read-only
    STATUS current
    DESCRIPTION
        "The acl meter identifier of a particular port."
    ::= { aclNewCfgPortAclMeterTableEntry 2 }

aclNewCfgAclMeterCommitRate OBJECT-TYPE
    SYNTAX INTEGER (1000..1000000)
    MAX-ACCESS read-write
    STATUS current
    DESCRIPTION
        "Committed rate of acl meter for specified port in kilobits/sec."
    ::= { aclNewCfgPortAclMeterTableEntry 3 }

aclNewCfgAclMeterMaxBurstSize OBJECT-TYPE
    SYNTAX INTEGER {
        k32(32),
        k64(64),
        k128(128),
        k256(256),
        k512(512),
        k1024(1024),
        k2048(2048),
        k4096(4096)
        }
    MAX-ACCESS read-write
    STATUS current
    DESCRIPTION
        "Maximum burst size of acl meter for specified port in kilobits."
    ::= { aclNewCfgPortAclMeterTableEntry 4 }

aclNewCfgAclMeterStatus OBJECT-TYPE
    SYNTAX  INTEGER {
	enabled(1),
	disabled(2)
	}
    MAX-ACCESS read-write
    STATUS current
    DESCRIPTION
       "The metering status of acl meter for specified port."
    ::= { aclNewCfgPortAclMeterTableEntry 5 }

aclNewCfgAclMeterDropOrPass OBJECT-TYPE
    SYNTAX  INTEGER {
	none(1),
	drop(2),
	pass(3)
	}
    MAX-ACCESS read-write
    STATUS current
    DESCRIPTION
       "The state of out profile to drop or pass for acl meter of a
        specified port."
    ::= { aclNewCfgPortAclMeterTableEntry 6 }

aclNewCfgAclMeterAssignAcl OBJECT-TYPE
    SYNTAX Unsigned32
    MAX-ACCESS read-write
    STATUS current
    DESCRIPTION
        "Assign acl meter for specified port to acl."
    ::= { aclNewCfgPortAclMeterTableEntry 7 }

aclNewCfgAclMeterAssignAclBlk OBJECT-TYPE
    SYNTAX Unsigned32
    MAX-ACCESS read-write
    STATUS current
    DESCRIPTION
        "Assign acl meter for specified port to acl block."
    ::= { aclNewCfgPortAclMeterTableEntry 8 }

aclNewCfgAclMeterAssignAclGrp OBJECT-TYPE
    SYNTAX Unsigned32
    MAX-ACCESS read-write
    STATUS current
    DESCRIPTION
        "Assign acl meter for specified port to acl group."
    ::= { aclNewCfgPortAclMeterTableEntry 9 }

aclNewCfgAclMeterUnAssignAcl OBJECT-TYPE
    SYNTAX Unsigned32
    MAX-ACCESS read-write
    STATUS current
    DESCRIPTION
        "Unassign acl meter for specified port from acl."
    ::= { aclNewCfgPortAclMeterTableEntry 10 }

aclNewCfgAclMeterUnAssignAclBlk OBJECT-TYPE
    SYNTAX Unsigned32
    MAX-ACCESS read-write
    STATUS current
    DESCRIPTION
        "Unassign acl meter for specified port from acl block."
    ::= { aclNewCfgPortAclMeterTableEntry 11 }

aclNewCfgAclMeterUnAssignAclGrp OBJECT-TYPE
    SYNTAX Unsigned32
    MAX-ACCESS read-write
    STATUS current
    DESCRIPTION
        "Unassign acl meter for specified port from acl group."
    ::= { aclNewCfgPortAclMeterTableEntry 12 }

aclNewCfgAclMeterAclBmap OBJECT-TYPE
    SYNTAX  OCTET STRING (SIZE(0..512))
    MAX-ACCESS  read-only
    STATUS  current
    DESCRIPTION
        "The acls assigned to this meter.  The acls are
         presented in bitmap format. This string displays acl number
         from 1 to 4096.

         in receiving order:

             OCTET 1  OCTET 2  .....
             xxxxxxxx xxxxxxxx .....
             ||    || |_ acl 9
             ||    ||
             ||    ||___ acl 8
             ||    |____ acl 7
             ||      .    .   .
             ||_________ acl 2
             |__________ acl 1

         where x : 1 - The represented acl assigned to the meter.
                   0 - The represented acl not assigned to the meter."
    ::= { aclNewCfgPortAclMeterTableEntry 13 }

aclNewCfgAclMeterAclBlkBmap OBJECT-TYPE
    SYNTAX  OCTET STRING (SIZE(0..512))
    MAX-ACCESS  read-only
    STATUS  current
    DESCRIPTION
        "The acl blocks assigned to this meter.  The blocks are
         presented in bitmap format. This string displays block number
         from 1 to 4096.

         in receiving order:

             OCTET 1  OCTET 2  .....
             xxxxxxxx xxxxxxxx .....
             ||    || |_ aclblk 9
             ||    ||
             ||    ||___ aclblk 8
             ||    |____ aclblk 7
             ||      .    .   .
             ||_________ aclblk 2
             |__________ aclblk 1

         where x : 1 - The represented acl block assigned to the meter.
                   0 - The represented acl blocknot assigned to the meter."
    ::= { aclNewCfgPortAclMeterTableEntry 14 }

aclNewCfgAclMeterAclGrpBmap OBJECT-TYPE
    SYNTAX  OCTET STRING (SIZE(0..512))
    MAX-ACCESS  read-only
    STATUS  current
    DESCRIPTION
        "The acl groups assigned to this meter.  The groups are
         presented in bitmap format. This string displays group number
         from 1 to 4096.

         in receiving order:

             OCTET 1  OCTET 2  .....
             xxxxxxxx xxxxxxxx .....
             ||    || |_ aclgrp 9
             ||    ||
             ||    ||___ aclgrp 8
             ||    |____ aclgrp 7
             ||      .    .   .
             ||_________ aclgrp 2
             |__________ aclgrp 1

         where x : 1 - The represented acl group assigned to the meter.
                   0 - The represented acl group not assigned to the meter."
    ::= { aclNewCfgPortAclMeterTableEntry 15 }


aclCurCfgPortAclRemarkTable OBJECT-TYPE
    SYNTAX  SEQUENCE OF AclCurCfgPortAclRemarkTableEntry
    MAX-ACCESS  not-accessible
    STATUS  current
    DESCRIPTION
        "The table of port acl remark configuration in the current_config."
    ::= { aclCfg 5 }

aclCurCfgPortAclRemarkTableEntry OBJECT-TYPE
    SYNTAX  AclCurCfgPortAclRemarkTableEntry
    MAX-ACCESS  not-accessible
    STATUS  current
    DESCRIPTION
        "Information about acl meter configuration of a particular port."
    INDEX   { aclCurCfgPortRemarkConfigIndex, aclCurCfgAclRemarkIndex }
    ::= { aclCurCfgPortAclRemarkTable 1 }

AclCurCfgPortAclRemarkTableEntry ::= SEQUENCE {
    aclCurCfgPortRemarkConfigIndex         Integer32,
    aclCurCfgAclRemarkIndex                Integer32,
    aclCurCfgAclRemarkInProfUpdatePri      INTEGER,
    aclCurCfgAclRemarkInProfUpdateTosPrec  INTEGER,
    aclCurCfgAclRemarkInProfUpdateDscp     INTEGER,
    aclCurCfgAclRemarkOutProfUpdateDscp    INTEGER,
    aclCurCfgAclRemarkAclBmap              OCTET STRING,
    aclCurCfgAclRemarkAclBlkBmap           OCTET STRING,
    aclCurCfgAclRemarkAclGrpBmap           OCTET STRING
        }

aclCurCfgPortRemarkConfigIndex OBJECT-TYPE
    SYNTAX Integer32
    MAX-ACCESS read-only
    STATUS current
    DESCRIPTION
        "The identifier of a particular port.  This is also
         index to the entLogicalTable of Entity MIB."
    ::= { aclCurCfgPortAclRemarkTableEntry 1 }

aclCurCfgAclRemarkIndex OBJECT-TYPE
    SYNTAX Integer32
    MAX-ACCESS read-only
    STATUS current
    DESCRIPTION
        "The acl remark identifier for a particular port."
    ::= { aclCurCfgPortAclRemarkTableEntry 2 }

aclCurCfgAclRemarkInProfUpdatePri OBJECT-TYPE
    SYNTAX INTEGER (0..7)
    MAX-ACCESS read-only
    STATUS current
    DESCRIPTION
        "Re-Mark in profile user priority for acl re-mark of a specified port."
    ::= { aclCurCfgPortAclRemarkTableEntry 3 }

aclCurCfgAclRemarkInProfUpdateTosPrec OBJECT-TYPE
    SYNTAX  INTEGER {
        enabled(1),
        disabled(2)
        }
    MAX-ACCESS read-only
    STATUS current
    DESCRIPTION
       "The state of Re-Mark in profile tos precedence for acl re-mark of
        a specified port."
    ::= { aclCurCfgPortAclRemarkTableEntry 4 }

aclCurCfgAclRemarkInProfUpdateDscp OBJECT-TYPE
    SYNTAX INTEGER (0..63)
    MAX-ACCESS read-only
    STATUS current
    DESCRIPTION
        "Re-Mark in profile dscp for acl re-mark of a specified port."
    ::= { aclCurCfgPortAclRemarkTableEntry 5 }

aclCurCfgAclRemarkOutProfUpdateDscp OBJECT-TYPE
    SYNTAX INTEGER (0..63)
    MAX-ACCESS read-only
    STATUS current
    DESCRIPTION
        "Re-Mark out profile dscp for acl re-mark of a specified port."
    ::= { aclCurCfgPortAclRemarkTableEntry 6 }

aclCurCfgAclRemarkAclBmap OBJECT-TYPE
    SYNTAX  OCTET STRING (SIZE(0..512))
    MAX-ACCESS  read-only
    STATUS  current
    DESCRIPTION
        "The acls assigned to this re-mark.  The acls are
         presented in bitmap format. This string displays acl number
         from 1 to 4096.

         in receiving order:

             OCTET 1  OCTET 2  .....
             xxxxxxxx xxxxxxxx .....
             ||    || |_ acl 9
             ||    ||
             ||    ||___ acl 8
             ||    |____ acl 7
             ||      .    .   .
             ||_________ acl 2
             |__________ acl 1

         where x : 1 - The represented acl assigned to the re-mark.
                   0 - The represented acl not assigned to the re-mark."
    ::= { aclCurCfgPortAclRemarkTableEntry 7 }

aclCurCfgAclRemarkAclBlkBmap OBJECT-TYPE
    SYNTAX  OCTET STRING (SIZE(0..512))
    MAX-ACCESS  read-only
    STATUS  current
    DESCRIPTION
        "The acl blocks assigned to this re-mark.  The blocks are
         presented in bitmap format. This string displays block number
         from 1 to 4096.

         in receiving order:

             OCTET 1  OCTET 2  .....
             xxxxxxxx xxxxxxxx .....
             ||    || |_ aclblk 9
             ||    ||
             ||    ||___ aclblk 8
             ||    |____ aclblk 7
             ||      .    .   .
             ||_________ aclblk 2
             |__________ aclblk 1

         where x : 1 - The represented acl block assigned to the re-mark.
                   0 - The represented acl blocknot assigned to the re-mark."
    ::= { aclCurCfgPortAclRemarkTableEntry 8 }

aclCurCfgAclRemarkAclGrpBmap OBJECT-TYPE
    SYNTAX  OCTET STRING (SIZE(0..512))
    MAX-ACCESS  read-only
    STATUS  current
    DESCRIPTION
        "The acl groups assigned to this re-mark.  The groups are
         presented in bitmap format. This string displays group number
         from 1 to 4096.

         in receiving order:

             OCTET 1  OCTET 2  .....
             xxxxxxxx xxxxxxxx .....
             ||    || |_ aclgrp 9
             ||    ||
             ||    ||___ aclgrp 8
             ||    |____ aclgrp 7
             ||      .    .   .
             ||_________ aclgrp 2
             |__________ aclgrp 1

         where x : 1 - The represented acl group assigned to the re-mark.
                   0 - The represented acl group not assigned to the re-mark."
    ::= { aclCurCfgPortAclRemarkTableEntry 9 }

aclNewCfgPortAclRemarkTable OBJECT-TYPE
    SYNTAX  SEQUENCE OF AclNewCfgPortAclRemarkTableEntry
    MAX-ACCESS  not-accessible
    STATUS  current
    DESCRIPTION
        "The table of port acl remark configuration in the new_config."
    ::= { aclCfg 6 }

aclNewCfgPortAclRemarkTableEntry OBJECT-TYPE
    SYNTAX  AclNewCfgPortAclRemarkTableEntry
    MAX-ACCESS  not-accessible
    STATUS  current
    DESCRIPTION
        "Information about acl remark configuration of a particular port."
    INDEX   { aclNewCfgPortRemarkConfigIndex, aclNewCfgAclRemarkIndex }
    ::= { aclNewCfgPortAclRemarkTable 1 }

AclNewCfgPortAclRemarkTableEntry ::= SEQUENCE {
    aclNewCfgPortRemarkConfigIndex         Integer32,
    aclNewCfgAclRemarkIndex                Integer32,
    aclNewCfgAclRemarkInProfUpdatePri      INTEGER,
    aclNewCfgAclRemarkInProfUpdateTosPrec  INTEGER,
    aclNewCfgAclRemarkInProfUpdateDscp     INTEGER,
    aclNewCfgAclRemarkOutProfUpdateDscp    INTEGER,
    aclNewCfgAclRemarkAssignAcl            Unsigned32,
    aclNewCfgAclRemarkAssignAclBlk         Unsigned32,
    aclNewCfgAclRemarkAssignAclGrp         Unsigned32,
    aclNewCfgAclRemarkUnAssignAcl          Unsigned32,
    aclNewCfgAclRemarkUnAssignAclBlk       Unsigned32,
    aclNewCfgAclRemarkUnAssignAclGrp       Unsigned32,
    aclNewCfgAclRemarkAclBmap              OCTET STRING,
    aclNewCfgAclRemarkAclBlkBmap           OCTET STRING,
    aclNewCfgAclRemarkAclGrpBmap           OCTET STRING,
    aclNewCfgAclRemarkReset               INTEGER
        }

aclNewCfgPortRemarkConfigIndex OBJECT-TYPE
    SYNTAX Integer32
    MAX-ACCESS read-only
    STATUS current
    DESCRIPTION
        "The identifier of a particular port.  This is also
         index to the entLogicalTable of Entity MIB."
    ::= { aclNewCfgPortAclRemarkTableEntry 1 }

aclNewCfgAclRemarkIndex OBJECT-TYPE
    SYNTAX Integer32
    MAX-ACCESS read-only
    STATUS current
    DESCRIPTION
        "The acl remark identifier for a particular port."
    ::= { aclNewCfgPortAclRemarkTableEntry 2 }

aclNewCfgAclRemarkInProfUpdatePri OBJECT-TYPE
    SYNTAX INTEGER (0..7)
    MAX-ACCESS read-write
    STATUS current
    DESCRIPTION
        "Re-Mark in profile user priority for acl re-mark of a specified port."
    ::= { aclNewCfgPortAclRemarkTableEntry 3 }

aclNewCfgAclRemarkInProfUpdateTosPrec OBJECT-TYPE
    SYNTAX  INTEGER {
        enabled(1),
        disabled(2)
        }
    MAX-ACCESS read-write
    STATUS current
    DESCRIPTION
       "The state of Re-Mark in profile tos precedence for acl re-mark of
        a specified port."
    ::= { aclNewCfgPortAclRemarkTableEntry 4 }

aclNewCfgAclRemarkInProfUpdateDscp OBJECT-TYPE
    SYNTAX INTEGER (0..63)
    MAX-ACCESS read-write
    STATUS current
    DESCRIPTION
        "Re-Mark in profile dscp for acl re-mark of a specified port."
    ::= { aclNewCfgPortAclRemarkTableEntry 5 }

aclNewCfgAclRemarkOutProfUpdateDscp OBJECT-TYPE
    SYNTAX INTEGER (0..63)
    MAX-ACCESS read-write
    STATUS current
    DESCRIPTION
        "Re-Mark out profile dscp for acl re-mark of a specified port."
    ::= { aclNewCfgPortAclRemarkTableEntry 6 }

aclNewCfgAclRemarkAssignAcl OBJECT-TYPE
    SYNTAX Unsigned32
    MAX-ACCESS read-write
    STATUS current
    DESCRIPTION
        "Assign acl re-mark for specified port to acl."
    ::= { aclNewCfgPortAclRemarkTableEntry 7 }

aclNewCfgAclRemarkAssignAclBlk OBJECT-TYPE
    SYNTAX Unsigned32
    MAX-ACCESS read-write
    STATUS current
    DESCRIPTION
        "Assign acl re-mark for specified port to acl block."
    ::= { aclNewCfgPortAclRemarkTableEntry 8 }

aclNewCfgAclRemarkAssignAclGrp OBJECT-TYPE
    SYNTAX Unsigned32
    MAX-ACCESS read-write
    STATUS current
    DESCRIPTION
        "Assign acl re-mark for specified port to acl group."
    ::= { aclNewCfgPortAclRemarkTableEntry 9 }

aclNewCfgAclRemarkUnAssignAcl OBJECT-TYPE
    SYNTAX Unsigned32
    MAX-ACCESS read-write
    STATUS current
    DESCRIPTION
        "Unassign acl re-mark for specified port from acl."
    ::= { aclNewCfgPortAclRemarkTableEntry 10 }

aclNewCfgAclRemarkUnAssignAclBlk OBJECT-TYPE
    SYNTAX Unsigned32
    MAX-ACCESS read-write
    STATUS current
    DESCRIPTION
        "Unassign acl re-mark for specified port from acl block."
    ::= { aclNewCfgPortAclRemarkTableEntry 11 }

aclNewCfgAclRemarkUnAssignAclGrp OBJECT-TYPE
    SYNTAX Unsigned32
    MAX-ACCESS read-write
    STATUS current
    DESCRIPTION
        "Unassign acl re-mark for specified port from acl group."
    ::= { aclNewCfgPortAclRemarkTableEntry 12 }

aclNewCfgAclRemarkAclBmap OBJECT-TYPE
    SYNTAX  OCTET STRING (SIZE(0..512))
    MAX-ACCESS  read-only
    STATUS  current
    DESCRIPTION
        "The acls assigned to this re-mark.  The acls are
         presented in bitmap format. This string displays acl number
         from 1 to 4096.

         in receiving order:

             OCTET 1  OCTET 2  .....
             xxxxxxxx xxxxxxxx .....
             ||    || |_ acl 9
             ||    ||
             ||    ||___ acl 8
             ||    |____ acl 7
             ||      .    .   .
             ||_________ acl 2
             |__________ acl 1

         where x : 1 - The represented acl assigned to the re-mark.
                   0 - The represented acl not assigned to the re-mark."
    ::= { aclNewCfgPortAclRemarkTableEntry 13 }

aclNewCfgAclRemarkAclBlkBmap OBJECT-TYPE
    SYNTAX  OCTET STRING (SIZE(0..512))
    MAX-ACCESS  read-only
    STATUS  current
    DESCRIPTION
        "The acl blocks assigned to this re-mark.  The blocks are
         presented in bitmap format. This string displays block number
         from 1 to 4096.

         in receiving order:

             OCTET 1  OCTET 2  .....
             xxxxxxxx xxxxxxxx .....
             ||    || |_ aclblk 9
             ||    ||
             ||    ||___ aclblk 8
             ||    |____ aclblk 7
             ||      .    .   .
             ||_________ aclblk 2
             |__________ aclblk 1

         where x : 1 - The represented acl block assigned to the re-mark.
                   0 - The represented acl blocknot assigned to the re-mark."
    ::= { aclNewCfgPortAclRemarkTableEntry 14 }

aclNewCfgAclRemarkAclGrpBmap OBJECT-TYPE
    SYNTAX  OCTET STRING (SIZE(0..512))
    MAX-ACCESS  read-only
    STATUS  current
    DESCRIPTION
        "The acl groups assigned to this re-mark.  The groups are
         presented in bitmap format. This string displays group number
         from 1 to 4096.

         in receiving order:

             OCTET 1  OCTET 2  .....
             xxxxxxxx xxxxxxxx .....
             ||    || |_ aclgrp 9
             ||    ||
             ||    ||___ aclgrp 8
             ||    |____ aclgrp 7
             ||      .    .   .
             ||_________ aclgrp 2
             |__________ aclgrp 1

         where x : 1 - The represented acl group assigned to the re-mark.
                   0 - The represented acl group not assigned to the re-mark."
    ::= { aclNewCfgPortAclRemarkTableEntry 15 }

aclNewCfgAclRemarkReset OBJECT-TYPE
    SYNTAX      INTEGER {
                    other(1),
                    reset(2)
                }
    MAX-ACCESS  read-write
    STATUS      current
    DESCRIPTION
        "This is an action object to reset an ACL remark entry.  A value of
        other(1) is always returned when this object is read."
    ::= { aclNewCfgPortAclRemarkTableEntry 16 }

-- ----------------------------------------------------------------------------
-- } INSERT:  bt2qos
-- ----------------------------------------------------------------------------

END
