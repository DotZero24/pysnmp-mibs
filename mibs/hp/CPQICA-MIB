--
--                Compaq Intelligent Cluster Administrator
--         Management Information Base for SNMP Network Management
--
--
--      Copyright 1999, Compaq Computer Corporation.
--      All Rights Reserved.
--
--      The information in this document is subject to change without notice.
--
--      COMPAQ COMPUTER CORPORATION SHALL NOT BE LIABLE FOR TECHNICAL
--      OR EDITORIAL ERRORS OR OMISSIONS CONTAINED HEREIN; NOR FOR INCIDENTAL
--      OR CONSEQUENTIAL DAMAGES RESULTING FROM THE FURNISHING, PERFORMANCE,
--      OR USE OF THIS MATERIAL.
--
--      Refer to the READMIB.RDM file for more information about the
--      organization of the information in the Compaq Enterprise.
--
--      The Compaq Enterprise number is 232.
--      The ASN.1 prefix to, and including the Compaq Enterprise is:
--           1.3.6.1.4.1.232
--
-- ****************************************************************************

CPQICA-MIB DEFINITIONS ::= BEGIN

    IMPORTS
        compaq                  FROM CPQHOST-MIB
        enterprises             FROM RFC1155-SMI
        Counter                 FROM RFC1155-SMI
        Gauge                   FROM RFC1155-SMI
        DisplayString           FROM RFC1213-MIB
        OBJECT-TYPE             FROM RFC-1212
        TRAP-TYPE               FROM RFC-1215
        sysName                 FROM RFC1213-MIB
        cpqHoTrapFlags          FROM CPQHOST-MIB;

--  compaq              OBJECT IDENTIFIER ::= { enterprises 232 }

    cpqICA              OBJECT IDENTIFIER ::= { compaq 140 }
    cpqICAMibRev        OBJECT IDENTIFIER ::= { cpqICA 1 }
    cpqICAComponent     OBJECT IDENTIFIER ::= { cpqICA 2 }

    cpqICAInterface     OBJECT IDENTIFIER ::= { cpqICAComponent 1 }
    cpqICAICA           OBJECT IDENTIFIER ::= { cpqICAComponent 2 }

    cpqICAOsCommon      OBJECT IDENTIFIER ::= { cpqICAInterface 4 }

-- ****************************************************************************
--  ICA MIB Revision
--  ====================
--
-- The compaq enterprise               (1.3.6.1.4.1.232)
--      cpqICA Group                   (1.3.6.1.4.1.232.140)
--       cpqICAMibRev Group            (1.3.6.1.4.1.232.140.1)
--
--      An SNMP agent conforming to this document will return a
--      cpqICAMibRevMajor of one (1) and a cpqICAMibRevMinor of zero (0).
--
--      Implementation of the cpqICAMibRev group is mandatory for all agents
--      supporting the ICA MIB.
--
-- ****************************************************************************

    cpqICAMibRevMajor OBJECT-TYPE
        SYNTAX  INTEGER (1..65535)
        ACCESS  read-only
        STATUS  mandatory
        DESCRIPTION
            "The Major Revision level.
             A change in the major revision level represents a major change
             in the architecture of the MIB.  A change in the major revision
             level may indicate a significant change in the information
             supported and/or the meaning of the supported information,
             correct interpretation of data may require a MIB document with
             the same major revision level."
        ::= { cpqICAMibRev 1 }

    cpqICAMibRevMinor OBJECT-TYPE
        SYNTAX  INTEGER (0..65535)
        ACCESS  read-only
        STATUS  mandatory
        DESCRIPTION
            "The Minor Revision level.
             A change in the minor revision level may represent some minor
             additional support, no changes to any pre-existing information
             has occurred."
        ::= { cpqICAMibRev 2 }

    cpqICAMibCondition OBJECT-TYPE
        SYNTAX  INTEGER {
            other(1),
            ok(2),
            degraded(3),
            failed(4)
            }
        ACCESS  read-only
        STATUS  mandatory
        DESCRIPTION
            "The overall condition (status) of the system represented by
            this MIB."
        ::= { cpqICAMibRev 3 }


-- ****************************************************************************
--    ICA Common Group
--    ================
--
-- The compaq enterprise               (1.3.6.1.4.1.232)
--      cpqICA Group                   (1.3.6.1.4.1.232.140)
--       cpqICAComponent Group         (1.3.6.1.4.1.232.140.2)
--        cpqICAInterface Group        (1.3.6.1.4.1.232.140.2.1)
--         cpqICAOsCommon Group        (1.3.6.1.4.1.232.140.2.1.4)
--
--  The cpqICAOsCommon group describes the interface to the ICA
--  components.  This information describes the interface modules
--  and general OS interface architectural information.
--
--
-- ****************************************************************************

    cpqICAOsCommonPollFreq OBJECT-TYPE
        SYNTAX  INTEGER (0..65535)
        ACCESS  read-write
        STATUS  mandatory
        DESCRIPTION
            "The Insight Agent's polling frequency.

            The frequency, in seconds, at which the Insight Agent requests
            information from the device driver.  A frequency of zero (0)
            indicates that the Insight Agent retrieves the information upon
            request of a management station, it does not poll the device
            driver at a specific interval.

            If the poll frequency is zero (0) all attempts to write to
            this object will fail.  If the poll frequency is non-zero,
            setting this value will change the polling frequency of the
            Insight Agent.  Setting the poll frequency to zero (0) will
            always fail, an agent may also choose to fail any request to
            change the poll frequency to a value that would severely impact
            system performance."
        ::= { cpqICAOsCommon 1 }

-- ****************************************************************************
--    ICA Common Module
--    =================
--
-- The compaq enterprise               (1.3.6.1.4.1.232)
--      cpqICA Group                   (1.3.6.1.4.1.232.140)
--       cpqICAComponent Group         (1.3.6.1.4.1.232.140.2)
--        cpqICAInterface Group        (1.3.6.1.4.1.232.140.2.1)
--         cpqICAOsCommon Group        (1.3.6.1.4.1.232.140.2.1.4)
--          cpqICAOsCommonModuleTable  (1.3.6.1.4.1.232.140.2.1.4.2)
--
-- ****************************************************************************

    cpqICAOsCommonModuleTable OBJECT-TYPE
        SYNTAX  SEQUENCE OF CpqICAOsCommonModuleEntry
        ACCESS  not-accessible
        STATUS  mandatory
        DESCRIPTION
            "A table of software modules that provide an interface to the
            device this MIB describes."
        ::= { cpqICAOsCommon 2 }

    cpqICAOsCommonModuleEntry OBJECT-TYPE
        SYNTAX  CpqICAOsCommonModuleEntry
        ACCESS  not-accessible
        STATUS  mandatory
        DESCRIPTION
            "A description of a software module that provides an interface
            to the device this MIB describes."
        INDEX   { cpqICAOsCommonModuleIndex }
        ::= { cpqICAOsCommonModuleTable 1 }

        CpqICAOsCommonModuleEntry ::= SEQUENCE {
            cpqICAOsCommonModuleIndex       INTEGER,
            cpqICAOsCommonModuleName        DisplayString,
            cpqICAOsCommonModuleVersion     DisplayString,
            cpqICAOsCommonModuleDate        OCTET STRING,
            cpqICAOsCommonModulePurpose     DisplayString
        }

    cpqICAOsCommonModuleIndex OBJECT-TYPE
        SYNTAX  INTEGER (0..255)
        ACCESS  read-only
        STATUS  mandatory
        DESCRIPTION
            "A unique index for this module description."
        ::= { cpqICAOsCommonModuleEntry 1 }

    cpqICAOsCommonModuleName OBJECT-TYPE
        SYNTAX  DisplayString (SIZE (0..255))
        ACCESS  read-only
        STATUS  mandatory
        DESCRIPTION
            "The module name."
        ::= { cpqICAOsCommonModuleEntry 2 }

    cpqICAOsCommonModuleVersion OBJECT-TYPE
        SYNTAX  DisplayString (SIZE (0..5))
        ACCESS  read-only
        STATUS  mandatory
        DESCRIPTION
            "The module version in XX.YY format.

            Where XX is the major version number and YY is the minor version
            number.  This field will be a null (size 0) string if the agent
            cannot provide the module version."
        ::= { cpqICAOsCommonModuleEntry 3 }

    cpqICAOsCommonModuleDate OBJECT-TYPE
        SYNTAX  OCTET STRING (SIZE (7))
        ACCESS  read-only
        STATUS  mandatory
        DESCRIPTION
            "The module date.

             field  octets  contents                  range
             =====  ======  ========                  =====
               1      1-2   year                      0..65536
               2       3    month                     1..12
               3       4    day                       1..31
               4       5    hour                      0..23
               5       6    minute                    0..59
               6       7    second                    0..60
                            (use 60 for leap-second)


            This field will be set to year = 0 if the agent cannot provide
            the module date.  The hour, minute, and second field will be set
            to zero (0) if they are not relevant.  The year field is set
            with the most significant octet first."
        ::= { cpqICAOsCommonModuleEntry 4 }

    cpqICAOsCommonModulePurpose OBJECT-TYPE
        SYNTAX  DisplayString (SIZE (0..255))
        ACCESS  read-only
        STATUS  mandatory
        DESCRIPTION
            "The purpose of the module described in this entry."
        ::= { cpqICAOsCommonModuleEntry 5 }


-- **************************************************************************
--  Compaq ICA Trap Definitions
--  ===========================
--
--  The compaq enterprise               (1.3.6.1.4.1.232)
--
--  The SNMP trap messages must not be bigger than 484 octets (bytes).
--
-- **************************************************************************

    cpqICAAdd TRAP-TYPE
        ENTERPRISE compaq

        DESCRIPTION
            "ICA Object Addition.

            This trap signifies that the Intelligent Cluster Administrator
	     added an object to the cluster."

        ::= 140001

    cpqICADelete TRAP-TYPE
        ENTERPRISE compaq

        DESCRIPTION
            "ICA Object Deletion.

            This trap signifies that the Intelligent Cluster Administrator
	     has deleted an object in the cluster."

        ::= 140002


    cpqICAPropertyChange TRAP-TYPE
        ENTERPRISE compaq

        DESCRIPTION
            "ICA Property Change Occurred.

            This trap signifies that the Intelligent Cluster Administrator
	     has performed one or more property changes on the cluster."

        ::= 140003


    cpqICAMove TRAP-TYPE
        ENTERPRISE compaq

        DESCRIPTION
            "ICA Move Action Occurred.

            This trap signifies that the Intelligent Cluster Administrator
	     has performed a move action on the cluster."

        ::= 140004


    cpqICAImportRestoreStart TRAP-TYPE
        ENTERPRISE compaq

        DESCRIPTION
            "ICA Import Action Starting.

            This trap signifies that the Intelligent Cluster Administrator
	     is starting an import operation on the cluster."

        ::= 140005


    cpqICAImportRestoreEnd TRAP-TYPE
        ENTERPRISE compaq

        DESCRIPTION
            "ICA Import Action Ended.

            This trap signifies that the Intelligent Cluster Administrator
	     has finished an import operation on the cluster."

        ::= 140006
END
