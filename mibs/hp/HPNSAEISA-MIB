-- ****************************************************************************
-- HP NSA EISA Information MIB
-- September 7, 1994
--
-- Copyright Hewlett-Packard Company 1994.
-- All rights reserved.
--
-- The information in this document is subject to change without notice.
--
-- The HP enterprise number is 11. The ASN.1 prefix to, and including,
-- the HP enterprise ID is 1.3.6.1.4.1.11.
--
-- ****************************************************************************
-- Summary of objects in the HP NSA EISA Information MIB
-- ****************************************************************************
-- hp                                             (1.3.6.1.4.1.11)
--    nm                                          (hp.2)
--       hpnsa                                    (nm.23)
--          hpnsaEISA Group                       (hpnsa.9)
--             hpnsaEISAMibRev Group              (hpnsa.9.1)
--                hpnsaEISAMibRevMajor            (hpnsa.9.1.1)
--                hpnsaEISAMibRevMinor            (hpnsa.9.1.2)
--             hpnsaEISAAgent Group               (hpnsa.9.2)
--                hpnsaEISAAgentTable             (hpnsa.9.2.1)
--                   hpnsaEISAAgentEntry          (hpnsa.9.2.1.1)
--                      hpnsaEISAAgentIndex       (hpnsa.9.2.1.1.1)
--                      hpnsaEISAAgentName        (hpnsa.9.2.1.1.2)
--                      hpnsaEISAAgentVersion     (hpnsa.9.2.1.1.3)
--                      hpnsaEISAAgentDate        (hpnsa.9.2.1.1.4)
--             hpnsaEISACfgUtilRev Group          (hpnsa.9.3)
--                hpnsaEISACfgUtilRevMajor        (hpnsa.9.3.1)
--                hpnsaEISACfgUtilRevMinor        (hpnsa.9.3.2)
--             hpnsaEISASlotInfo Group            (hpnsa.9.4)
--                hpnsaEISABoardTable             (hpnsa.9.4.1)
--                   hpnsaEISABoardEntry          (hpnsa.9.4.1.1)
--                      hpnsaEISASlotIndex        (hpnsa.9.4.1.1.1)
--                      hpnsaEISASlotType         (hpnsa.9.4.1.1.2)
--                      hpnsaEISACfgRevMajor      (hpnsa.9.4.1.1.3)
--                      hpnsaEISACfgRevMinor      (hpnsa.9.4.1.1.4)
--                      hpnsaEISABoardID          (hpnsa.9.4.1.1.5)
--                      hpnsaEISABoardDupCfg      (hpnsa.9.4.1.1.6)
--                      hpnsaEISANumFunctions     (hpnsa.9.4.1.1.7)
--                hpnsaEISASlotFunctionTable      (hpnsa.9.4.2)
--                   hpnsaEISAFunctEntry          (hpnsa.9.4.2.1)
--                      hpnsaEISAFunctSlotIndex   (hpnsa.9.4.2.1.1)
--                      hpnsaEISAFunctIndex       (hpnsa.9.4.2.1.2)
--                      hpnsaEISAFunctStatus      (hpnsa.9.4.2.1.3)
--                      hpnsaEISAFunctType        (hpnsa.9.4.2.1.4)
--                hpnsaEISASlotMemTable           (hpnsa.9.4.3)
--                   hpnsaEISAMemEntry            (hpnsa.9.4.3.1)
--                      hpnsaEISAMemSlotIndex     (hpnsa.9.4.3.1.1)
--                      hpnsaEISAMemFunctIndex    (hpnsa.9.4.3.1.2)
--                      hpnsaEISAMemAllocIndex    (hpnsa.9.4.3.1.3)
--                      hpnsaEISAMemStartAddr     (hpnsa.9.4.3.1.4)
--                      hpnsaEISAMemSize          (hpnsa.9.4.3.1.5)
--                      hpnsaEISAMemShare         (hpnsa.9.4.3.1.6)
--                      hpnsaEISAMemType          (hpnsa.9.4.3.1.7)
--                      hpnsaEISAMemCache         (hpnsa.9.4.3.1.8)
--                      hpnsaEISAMemAccess        (hpnsa.9.4.3.1.9)
--                hpnsaEISASlotIntTable           (hpnsa.9.4.4)
--                   hpnsaEISAIntEntry            (hpnsa.9.4.4.1)
--                      hpnsaEISAIntSlotIndex     (hpnsa.9.4.4.1.1)
--                      hpnsaEISAIntFunctIndex    (hpnsa.9.4.4.1.2)
--                      hpnsaEISAIntAllocIndex    (hpnsa.9.4.4.1.3)
--                      hpnsaEISAIntNum           (hpnsa.9.4.4.1.4)
--                      hpnsaEISAIntShare         (hpnsa.9.4.4.1.5)
--                      hpnsaEISAIntTrigger       (hpnsa.9.4.4.1.6)
--                hpnsaEISASlotDMATable           (hpnsa.9.4.5)
--                   hpnsaEISADmaEntry            (hpnsa.9.4.5.1)
--                      hpnsaEISADmaSlotIndex     (hpnsa.9.4.5.1.1)
--                      hpnsaEISADmaFunctIndex    (hpnsa.9.4.5.1.2)
--                      hpnsaEISADmaAllocIndex    (hpnsa.9.4.5.1.3)
--                      hpnsaEISADmaChannelNum    (hpnsa.9.4.5.1.4)
--                      hpnsaEISADmaShare         (hpnsa.9.4.5.1.5)
--                      hpnsaEISADmaTiming        (hpnsa.9.4.5.1.6)
--                      hpnsaEISADmaXferSize      (hpnsa.9.4.5.1.7)
--                hpnsaEISAPortTable              (hpnsa.9.4.6)
--                   hpnsaEISAPortEntry           (hpnsa.9.4.6.1)
--                      hpnsaEISAPortSlotIndex    (hpnsa.9.4.6.1.1)
--                      hpnsaEISAPortFunctIndex   (hpnsa.9.4.6.1.2)
--                      hpnsaEISAPortEntryIndex   (hpnsa.9.4.6.1.3)
--                      hpnsaEISAPortAddress      (hpnsa.9.4.6.1.4)
--                      hpnsaEISAPortSize         (hpnsa.9.4.6.1.5)
--                      hpnsaEISAPortShared       (hpnsa.9.4.6.1.6)
--                hpnsaEISAPortInitTable            (hpnsa.9.4.7)
--                   hpnsaEISAPortInitEntry         (hpnsa.9.4.7.1)
--                      hpnsaEISAPortInitSlotIndex  (hpnsa.9.4.7.1.1)
--                      hpnsaEISAPortInitFunctIndex (hpnsa.9.4.7.1.2)
--                      hpnsaEISAPortInitEntryIndex (hpnsa.9.4.7.1.3)
--                      hpnsaEISAPortInitData       (hpnsa.9.4.7.1.4)
--
-- ****************************************************************************

HPNSAEISA-MIB DEFINITIONS ::= BEGIN
   IMPORTS
      enterprises    FROM RFC1155-SMI
      DisplayString  FROM RFC1213-MIB
      OBJECT-TYPE    FROM RFC-1212;

   hp                OBJECT IDENTIFIER ::= { enterprises 11 }
   nm                OBJECT IDENTIFIER ::= { hp 2 }
   hpnsa             OBJECT IDENTIFIER ::= { nm 23 }
   hpnsaEISA         OBJECT IDENTIFIER ::= { hpnsa 9 }
   hpnsaEISAMibRev   OBJECT IDENTIFIER ::= { hpnsaEISA 1 }
   hpnsaEISAAgent    OBJECT IDENTIFIER ::= { hpnsaEISA 2 }
   hpnsaEISACfgUtil  OBJECT IDENTIFIER ::= { hpnsaEISA 3 }
   hpnsaEISASlotInfo OBJECT IDENTIFIER ::= { hpnsaEISA 4 }

-- ****************************************************************************
-- HP NSA EISA Information MIB Revision
-- ====================================
--
-- hp                                             (1.3.6.1.4.1.11)
--    nm                                          (hp.2)
--       hpnsa                                    (nm.23)
--          hpnsaEISA Group                       (hpnsa.9)
--             hpnsaEISAMibRev Group              (hpnsa.9.1)
--                hpnsaEISAMibRevMajor            (hpnsa.9.1.1)
--                hpnsaEISAMibRevMinor            (hpnsa.9.1.2)
--
-- Implementation of the MibRev group is mandatory for all HP NSA Agents
-- supporting the HP EISA System Information MIB.
--
-- An HP NSA Agent conforming to this document will return a
-- hpnsaEISAMibRevMajor of 1 and a hpnsaEISAMibRevMinor of 0.
--
-- ****************************************************************************

   hpnsaEISAMibRevMajor OBJECT-TYPE
      SYNTAX INTEGER (1..65535)
      ACCESS read-only
      STATUS mandatory
      DESCRIPTION
         "The major revision level of the MIB."
   ::= { hpnsaEISAMibRev 1 }

   hpnsaEISAMibRevMinor OBJECT-TYPE
      SYNTAX INTEGER (0..65535)
      ACCESS read-only
      STATUS mandatory
      DESCRIPTION
         "The minor revision level of the MIB."
   ::= { hpnsaEISAMibRev 2 }

-- ****************************************************************************
-- HP NSA EISA Info MIB Agent Information
-- ======================================
--
-- hp                                             (1.3.6.1.4.1.11)
--    nm                                          (hp.2)
--       hpnsa                                    (nm.23)
--          hpnsaEISA Group                       (hpnsa.9)
--             hpnsaEISAAgent Group               (hpnsa.9.2)
--                hpnsaEISAAgentTable             (hpnsa.9.2.1)
--                   hpnsaEISAAgentEntry          (hpnsa.9.2.1.1)
--                      hpnsaEISAAgentIndex       (hpnsa.9.2.1.1.1)
--                      hpnsaEISAAgentName        (hpnsa.9.2.1.1.2)
--                      hpnsaEISAAgentVersion     (hpnsa.9.2.1.1.3)
--                      hpnsaEISAAgentDate        (hpnsa.9.2.1.1.4)
--
-- Implementation of the EISA Agent group is mandatory for all HP NSA Agents
-- supporting the HP NSA EISA Information MIB.
--
--*****************************************************************************

   hpnsaEISAAgentTable OBJECT-TYPE
      SYNTAX SEQUENCE OF HPnsaEISAAgentEntry
      ACCESS not-accessible
      STATUS mandatory
      DESCRIPTION
         "A table of SNMP agents that satisfy requests for this MIB."
   ::= { hpnsaEISAAgent 1 }

   hpnsaEISAAgentEntry OBJECT-TYPE
      SYNTAX HPnsaEISAAgentEntry
      ACCESS not-accessible
      STATUS mandatory
      DESCRIPTION
         "A description of the agent/agents that access EISA information."
      INDEX { hpnsaEISAAgentIndex }
   ::= { hpnsaEISAAgentTable 1 }

   HPnsaEISAAgentEntry ::= SEQUENCE {
      hpnsaEISAAgentIndex       INTEGER,
      hpnsaEISAAgentName        DisplayString,
      hpnsaEISAAgentVersion     DisplayString,
      hpnsaEISAAgentDate        OCTET STRING
   }

   hpnsaEISAAgentIndex OBJECT-TYPE
      SYNTAX INTEGER (0..255)
      ACCESS read-only
      STATUS mandatory
      DESCRIPTION
         "A unique index for this agent."
   ::= { hpnsaEISAAgentEntry 1 }

   hpnsaEISAAgentName OBJECT-TYPE
      SYNTAX DisplayString (SIZE (0..255))
      ACCESS read-only
      STATUS mandatory
      DESCRIPTION
         "Name of the agent/agents satisfying SNMP requests for this MIB."
   ::= { hpnsaEISAAgentEntry 2 }

   hpnsaEISAAgentVersion OBJECT-TYPE
      SYNTAX DisplayString (SIZE (0..10))
      ACCESS read-only
      STATUS mandatory
      DESCRIPTION
         "Version number of the agent/agents satisfying SNMP requests for
         this MIB."
   ::= { hpnsaEISAAgentEntry 3 }

   hpnsaEISAAgentDate OBJECT-TYPE
      SYNTAX OCTET STRING (SIZE (6))
      ACCESS read-only
      STATUS mandatory
      DESCRIPTION
         "The date on which this agent was created.

         field  octets  contents                  range
         _________________________________________________
            1       1    years since 1900          0..255
            2       2    month                     1..12
            3       3    day                       1..31
            4       4    hour                      0..23
            5       5    minute                    0..59
            6       6    second                    0..59"
   ::= { hpnsaEISAAgentEntry 4 }

-- ****************************************************************************
-- HP NSA EISA Information Config Util Revision
-- ============================================
--
-- hp                                             (1.3.6.1.4.1.11)
--    nm                                          (hp.2)
--       hpnsa                                    (nm.23)
--          hpnsaEISA Group                       (hpnsa.9)
--             hpnsaEISACfgUtilRev Group          (hpnsa.9.3)
--                hpnsaEISACfgUtilRevMajor        (hpnsa.9.3.1)
--                hpnsaEISACfgUtilRevMinor        (hpnsa.9.3.2)
--
-- Implementation of the EISA Cfg Util group is mandatory for all HP NSA Agents
-- supporting the HP EISA System Information MIB.
--
-- ****************************************************************************

   hpnsaEISACfgUtilRevMajor OBJECT-TYPE
      SYNTAX INTEGER (1..65535)
      ACCESS read-only
      STATUS mandatory
      DESCRIPTION
         "The major revision level of the EISA Config Utility."
   ::= { hpnsaEISACfgUtil 1 }

   hpnsaEISACfgUtilRevMinor OBJECT-TYPE
      SYNTAX INTEGER (0..65535)
      ACCESS read-only
      STATUS mandatory
      DESCRIPTION
         "The minor revision level of the EISA Config Utility."
   ::= { hpnsaEISACfgUtil 2 }

-- ****************************************************************************
-- HP NSA EISA Information MIB Parameters
-- ======================================
--
-- hp                                             (1.3.6.1.4.1.11)
--    nm                                          (hp.2)
--       hpnsa                                    (nm.23)
--          hpnsaEISA Group                       (hpnsa.9)
--             hpnsaEISASlotInfo Group            (hpnsa.9.4)
--                hpnsaEISABoardTable             (hpnsa.9.4.1)
--                   hpnsaEISABoardEntry          (hpnsa.9.4.1.1)
--                      hpnsaEISASlotIndex        (hpnsa.9.4.1.1.1)
--                      hpnsaEISASlotType         (hpnsa.9.4.1.1.2)
--                      hpnsaEISACfgRevMajor      (hpnsa.9.4.1.1.3)
--                      hpnsaEISACfgRevMinor      (hpnsa.9.4.1.1.4)
--                      hpnsaEISABoardID          (hpnsa.9.4.1.1.5)
--                      hpnsaEISABoardDupCfg      (hpnsa.9.4.1.1.6)
--                      hpnsaEISANumFunctions     (hpnsa.9.4.1.1.7)
--
-- Implementation of the EISA slot info group is mandatory for all
-- HP NSA Agents supporting the HP NSA EISA information MIB.
--
-- ****************************************************************************

   hpnsaEISABoardTable OBJECT-TYPE
      SYNTAX SEQUENCE OF HPnsaEISABoardEntry
      ACCESS not-accessible
      STATUS mandatory
      DESCRIPTION
         "Plug in EISA board information table."
   ::= { hpnsaEISASlotInfo 1 }

   hpnsaEISABoardEntry OBJECT-TYPE
      SYNTAX HPnsaEISABoardEntry
      ACCESS not-accessible
      STATUS mandatory
      DESCRIPTION
         "Information for each of the EISA boards in the system."
      INDEX { hpnsaEISASlotIndex }
   ::= { hpnsaEISABoardTable 1 }

   HPnsaEISABoardEntry ::= SEQUENCE {
      hpnsaEISASlotIndex        INTEGER,
      hpnsaEISASlotType         INTEGER,
      hpnsaEISACfgRevMajor      INTEGER,
      hpnsaEISACfgRevMinor      INTEGER,
      hpnsaEISABoardID          DisplayString,
      hpnsaEISABoardDupCfg      INTEGER,
      hpnsaEISANumFunctions     INTEGER
   }

   hpnsaEISASlotIndex OBJECT-TYPE
      SYNTAX INTEGER
      ACCESS read-only
      STATUS mandatory
      DESCRIPTION
         "Number of this slot."
   ::= { hpnsaEISABoardEntry 1 }

   hpnsaEISASlotType OBJECT-TYPE
      SYNTAX INTEGER{
         expansion(0),
         embedded(1),
         virtual(2),
         reserved(3)
      }
      ACCESS read-only
      STATUS mandatory
      DESCRIPTION
         "Type of slot this board is installed in."
   ::= { hpnsaEISABoardEntry 2 }

   hpnsaEISACfgRevMajor OBJECT-TYPE
      SYNTAX INTEGER
      ACCESS read-only
      STATUS mandatory
      DESCRIPTION
         "Major CFG file revision level; 0 if no CFG file."
   ::= { hpnsaEISABoardEntry 3 }

   hpnsaEISACfgRevMinor OBJECT-TYPE
      SYNTAX INTEGER
      ACCESS read-only
      STATUS mandatory
      DESCRIPTION
         "Minor CFG file revision level; 0 if no CFG file."
   ::= { hpnsaEISABoardEntry 4 }

   hpnsaEISABoardID OBJECT-TYPE
      SYNTAX DisplayString (SIZE (7))
      ACCESS read-only
      STATUS mandatory
      DESCRIPTION
         "Seven-character EISA board ID.  First three characters are
         manufacturer's ID, followed by three characters product ID,
         followed by one character CFG file revision level."
   ::= { hpnsaEISABoardEntry 5 }

   hpnsaEISABoardDupCfg OBJECT-TYPE
      SYNTAX INTEGER
      ACCESS read-only
      STATUS mandatory
      DESCRIPTION
         "Specifies the duplicate CFG filenumber.  0 - No duplicate filenames,
         1 - 15 number of the duplicate file."
   ::= { hpnsaEISABoardEntry 6 }

   hpnsaEISANumFunctions OBJECT-TYPE
      SYNTAX INTEGER
      ACCESS read-only
      STATUS mandatory
      DESCRIPTION
         "Specifies the number of functions this board implements."
   ::= { hpnsaEISABoardEntry 7 }

-- ****************************************************************************
-- HP NSA EISA Board Function Table
-- ================================
--
-- hp                                             (1.3.6.1.4.1.11)
--    nm                                          (hp.2)
--       hpnsa                                    (nm.23)
--          hpnsaEISA Group                       (hpnsa.9)
--             hpnsaEISASlotInfo Group            (hpnsa.9.4)
--                hpnsaEISASlotFunctionTable      (hpnsa.9.4.2)
--                   hpnsaEISAFunctEntry          (hpnsa.9.4.2.1)
--                      hpnsaEISAFunctSlotIndex   (hpnsa.9.4.2.1.1)
--                      hpnsaEISAFunctIndex       (hpnsa.9.4.2.1.2)
--                      hpnsaEISAFunctStatus      (hpnsa.9.4.2.1.3)
--                      hpnsaEISAFunctType        (hpnsa.9.4.2.1.4)
--
-- Implementation of the EISA Board Function Table is mandatory for all
-- HP NSA Agents supporting the HP NSA EISA information MIB.
--
-- ****************************************************************************

   hpnsaEISAFunctTable OBJECT-TYPE
      SYNTAX SEQUENCE OF HpnsaEISAFunctEntry
      ACCESS not-accessible
      STATUS mandatory
      DESCRIPTION
         "A table of EISA function information entries."
   ::= { hpnsaEISASlotInfo 2 }

   hpnsaEISAFunctEntry OBJECT-TYPE
      SYNTAX HpnsaEISAFunctEntry
      ACCESS not-accessible
      STATUS mandatory
      DESCRIPTION
         "Information describing an EISA function."
      INDEX { hpnsaEISAFunctSlotIndex, hpnsaEISAFunctIndex }
   ::= { hpnsaEISAFunctTable 1 }

   HpnsaEISAFunctEntry ::= SEQUENCE {
      hpnsaEISAFunctSlotIndex   INTEGER,
      hpnsaEISAFunctIndex       INTEGER,
      hpnsaEISAFunctStatus      INTEGER,
      hpnsaEISAFunctType        DisplayString
   }

   hpnsaEISAFunctSlotIndex OBJECT-TYPE
      SYNTAX INTEGER (0..255)
      ACCESS read-only
      STATUS mandatory
      DESCRIPTION
         "The EISA slot number that registered this function."
   ::= { hpnsaEISAFunctEntry 1 }

   hpnsaEISAFunctIndex OBJECT-TYPE
      SYNTAX INTEGER (0..255)
      ACCESS read-only
      STATUS mandatory
      DESCRIPTION
         "The index of the function this entry describes."
   ::= { hpnsaEISAFunctEntry 2 }

   hpnsaEISAFunctStatus OBJECT-TYPE
      SYNTAX INTEGER {
         disabled(2),
         enabled(3)
      }
      ACCESS read-only
      STATUS mandatory
      DESCRIPTION
         "Specifies whether this function is enabled or disabled."
   ::= { hpnsaEISAFunctEntry 3 }

   hpnsaEISAFunctType OBJECT-TYPE
      SYNTAX DisplayString (SIZE (0..79))
      ACCESS read-only
      STATUS mandatory
      DESCRIPTION
         "The type of the function.

         The type may be followed by one or more subtype description
         fields. Some currently defined types are:

         Type            Meaning
         ==============  ==================================================
         COM             Communication device
         CPU             Microprocessor
         KEY             Keyboard
         MFC             Multifunction board
         MSD             Mass storage device
         NET             Network board
         PAR             ISA compatible parallel port
         PTR             Pointing device
         SYS             System board
         VID             Video board

         This list describes some of the more common types found. It is not
         an exhaustive list."
   ::= { hpnsaEISAFunctEntry 4 }

-- ****************************************************************************
-- HP NSA EISA Slot Memory Table
-- =============================
--
-- hp                                             (1.3.6.1.4.1.11)
--    nm                                          (hp.2)
--       hpnsa                                    (nm.23)
--          hpnsaEISA Group                       (hpnsa.9)
--             hpnsaEISASlotInfo Group            (hpnsa.9.4)
--                hpnsaEISASlotMemTable           (hpnsa.9.4.3)
--                   hpnsaEISAMemEntry            (hpnsa.9.4.3.1)
--                      hpnsaEISAMemSlotIndex     (hpnsa.9.4.3.1.1)
--                      hpnsaEISAMemFunctIndex    (hpnsa.9.4.3.1.2)
--                      hpnsaEISAMemAllocIndex    (hpnsa.9.4.3.1.3)
--                      hpnsaEISAMemStartAddr     (hpnsa.9.4.3.1.4)
--                      hpnsaEISAMemSize          (hpnsa.9.4.3.1.5)
--                      hpnsaEISAMemShare         (hpnsa.9.4.3.1.6)
--                      hpnsaEISAMemType          (hpnsa.9.4.3.1.7)
--                      hpnsaEISAMemCache         (hpnsa.9.4.3.1.8)
--                      hpnsaEISAMemAccess        (hpnsa.9.4.3.1.9)
--
-- Implementation of the EISA Slot Memory Table is mandatory for all
-- HP NSA Agents supporting the HP NSA EISA information MIB.
--
-- ****************************************************************************

   hpnsaEISAMemTable OBJECT-TYPE
      SYNTAX SEQUENCE OF HpnsaEISAMemEntry
      ACCESS not-accessible
      STATUS mandatory
      DESCRIPTION
         "A list of EISA function memory configuration entries."
   ::= { hpnsaEISASlotInfo 3 }

   hpnsaEISAMemEntry OBJECT-TYPE
      SYNTAX HpnsaEISAMemEntry
      ACCESS not-accessible
      STATUS mandatory
      DESCRIPTION
         "A description of an EISA function memory configuration."
      INDEX { hpnsaEISAMemSlotIndex, hpnsaEISAMemFunctIndex,
               hpnsaEISAMemAllocIndex }
   ::= { hpnsaEISAMemTable 1 }

   HpnsaEISAMemEntry ::= SEQUENCE {
      hpnsaEISAMemSlotIndex         INTEGER,
      hpnsaEISAMemFunctIndex        INTEGER,
      hpnsaEISAMemAllocIndex        INTEGER,
      hpnsaEISAMemStartAddr         INTEGER,
      hpnsaEISAMemSize              INTEGER,
      hpnsaEISAMemShare             INTEGER,
      hpnsaEISAMemType              INTEGER,
      hpnsaEISAMemCache             INTEGER,
      hpnsaEISAMemAccess            INTEGER
   }

   hpnsaEISAMemSlotIndex OBJECT-TYPE
      SYNTAX INTEGER (0..255)
      ACCESS read-only
      STATUS mandatory
      DESCRIPTION
         "The EISA slot number of the board that registered the memory
         configuration this entry describes."
   ::= { hpnsaEISAMemEntry 1 }

   hpnsaEISAMemFunctIndex OBJECT-TYPE
      SYNTAX INTEGER (0..255)
      ACCESS read-only
      STATUS mandatory
      DESCRIPTION
         "The function in which this memory configuration was registered."
   ::= { hpnsaEISAMemEntry 2 }

   hpnsaEISAMemAllocIndex OBJECT-TYPE
      SYNTAX INTEGER (0..255)
      ACCESS read-only
      STATUS mandatory
      DESCRIPTION
         "The index for this memory allocation entry in the EISA function
         block."
   ::= { hpnsaEISAMemEntry 3 }

   hpnsaEISAMemStartAddr OBJECT-TYPE
      SYNTAX INTEGER
      ACCESS read-only
      STATUS mandatory
      DESCRIPTION
         "The starting address of the memory configuration, in KB."
   ::= { hpnsaEISAMemEntry 4 }

   hpnsaEISAMemSize OBJECT-TYPE
      SYNTAX INTEGER
      ACCESS read-only
      STATUS mandatory
      DESCRIPTION
         "The size of the memory configuration, in KB."
   ::= { hpnsaEISAMemEntry 5 }

   hpnsaEISAMemShare OBJECT-TYPE
      SYNTAX INTEGER {
         nonshareable(0),
         shareable(1)
      }
      ACCESS read-only
      STATUS mandatory
      DESCRIPTION
         "This value indicates if the memory is shareable."
   ::= { hpnsaEISAMemEntry 6 }

   hpnsaEISAMemType OBJECT-TYPE
      SYNTAX INTEGER {
         unknown(0),
         systemBaseOrExtended(1),
         expanded(2),
         virtual(3)
      }
      ACCESS read-only
      STATUS mandatory
      DESCRIPTION
         "The type of memory."
   ::= { hpnsaEISAMemEntry 7 }

   hpnsaEISAMemCache OBJECT-TYPE
      SYNTAX INTEGER {
         notCached(1),
         writeThroughCached(2),
         writeBackCached(3)
      }
      ACCESS read-only
      STATUS mandatory
      DESCRIPTION
         "This value indicates if and how the memory is cached."
   ::= { hpnsaEISAMemEntry 8 }

   hpnsaEISAMemAccess OBJECT-TYPE
      SYNTAX INTEGER {
         readOnly(1),
         readWrite(2)
      }
      ACCESS read-only
      STATUS mandatory
      DESCRIPTION
         "The type of access permitted for this memory."
   ::= { hpnsaEISAMemEntry 9 }

-- ****************************************************************************
-- HP NSA EISA Slot Interrupt Table
-- ================================
--
-- hp                                             (1.3.6.1.4.1.11)
--    nm                                          (hp.2)
--       hpnsa                                    (nm.23)
--          hpnsaEISA Group                       (hpnsa.9)
--             hpnsaEISASlotInfo Group            (hpnsa.9.4)
--                hpnsaEISASlotIntTable           (hpnsa.9.4.4)
--                   hpnsaEISAIntEntry            (hpnsa.9.4.4.1)
--                      hpnsaEISAIntSlotIndex     (hpnsa.9.4.4.1.1)
--                      hpnsaEISAIntFunctIndex    (hpnsa.9.4.4.1.2)
--                      hpnsaEISAIntAllocIndex    (hpnsa.9.4.4.1.3)
--                      hpnsaEISAIntNum           (hpnsa.9.4.4.1.4)
--                      hpnsaEISAIntShare         (hpnsa.9.4.4.1.5)
--                      hpnsaEISAIntTrigger       (hpnsa.9.4.4.1.6)
--
-- Implementation of the EISA Slot Interrupt Table is mandatory for all
-- HP NSA Agents supporting the HP NSA EISA information MIB.
--
-- ****************************************************************************

   hpnsaEISAIntTable OBJECT-TYPE
      SYNTAX SEQUENCE OF HpnsaEISAIntEntry
      ACCESS not-accessible
      STATUS mandatory
      DESCRIPTION
         "A list of EISA function interrupt configuration entries."
   ::= { hpnsaEISASlotInfo 4 }

   hpnsaEISAIntEntry OBJECT-TYPE
      SYNTAX HpnsaEISAIntEntry
      ACCESS not-accessible
      STATUS mandatory
      DESCRIPTION
         "A description of an EISA function interrupt configuration."
      INDEX { hpnsaEISAIntSlotIndex, hpnsaEISAIntFunctIndex,
                  hpnsaEISAIntAllocIndex }
   ::= { hpnsaEISAIntTable 1 }

   HpnsaEISAIntEntry ::= SEQUENCE {
      hpnsaEISAIntSlotIndex          INTEGER,
      hpnsaEISAIntFunctIndex         INTEGER,
      hpnsaEISAIntAllocIndex         INTEGER,
      hpnsaEISAIntNum                INTEGER,
      hpnsaEISAIntShare              INTEGER,
      hpnsaEISAIntTrigger            INTEGER
   }

   hpnsaEISAIntSlotIndex OBJECT-TYPE
      SYNTAX INTEGER (0..255)
      ACCESS read-only
      STATUS mandatory
      DESCRIPTION
         "The EISA slot number of the board that registered the interrupt
         configuration this entry describes."
   ::= { hpnsaEISAIntEntry 1 }

   hpnsaEISAIntFunctIndex OBJECT-TYPE
      SYNTAX INTEGER (0..255)
      ACCESS read-only
      STATUS mandatory
      DESCRIPTION
         "The function in which this interrupt configuration was
         registered."
   ::= { hpnsaEISAIntEntry 2 }

   hpnsaEISAIntAllocIndex OBJECT-TYPE
      SYNTAX INTEGER (0..255)
      ACCESS read-only
      STATUS mandatory
      DESCRIPTION
         "The index for this interrupt allocation entry in the EISA
         function block."
     ::= { hpnsaEISAIntEntry 3 }

   hpnsaEISAIntNum OBJECT-TYPE
      SYNTAX INTEGER (0..65535)
      ACCESS read-only
      STATUS mandatory
      DESCRIPTION
         "The interrupt number described in this entry."
   ::= { hpnsaEISAIntEntry 4 }

   hpnsaEISAIntShare OBJECT-TYPE
      SYNTAX INTEGER {
         notShared(0),
         shared(1)
      }
      ACCESS read-only
      STATUS mandatory
      DESCRIPTION
         "This value indicates if the interrupt is shareable."
   ::= { hpnsaEISAIntEntry 5 }

   hpnsaEISAIntTrigger OBJECT-TYPE
      SYNTAX INTEGER {
         edgeTriggered(0),
         levelTriggered(1)
      }
      ACCESS read-only
      STATUS mandatory
      DESCRIPTION
         "This value indicates whether the interrupt is edge or level
         triggered."
   ::= { hpnsaEISAIntEntry 6 }

-- ****************************************************************************
-- HP NSA EISA Slot DMA Table
-- ==========================
--
-- hp                                             (1.3.6.1.4.1.11)
--    nm                                          (hp.2)
--       hpnsa                                    (nm.23)
--          hpnsaEISA Group                       (hpnsa.9)
--             hpnsaEISASlotInfo Group            (hpnsa.9.4)
--                hpnsaEISASlotDMATable           (hpnsa.9.4.5)
--                   hpnsaEISADmaEntry            (hpnsa.9.4.5.1)
--                      hpnsaEISADmaSlotIndex     (hpnsa.9.4.5.1.1)
--                      hpnsaEISADmaFunctIndex    (hpnsa.9.4.5.1.2)
--                      hpnsaEISADmaAllocIndex    (hpnsa.9.4.5.1.3)
--                      hpnsaEISADmaChannelNum    (hpnsa.9.4.5.1.4)
--                      hpnsaEISADmaShare         (hpnsa.9.4.5.1.5)
--                      hpnsaEISADmaTiming        (hpnsa.9.4.5.1.6)
--                      hpnsaEISADmaXferSize      (hpnsa.9.4.5.1.7)
--
-- Implementation of the EISA Slot Dma Table is mandatory for all
-- HP NSA Agents supporting the HP NSA EISA information MIB.
--
-- ****************************************************************************

   hpnsaEISADmaTable OBJECT-TYPE
      SYNTAX SEQUENCE OF HpnsaEISADmaEntry
      ACCESS not-accessible
      STATUS mandatory
      DESCRIPTION
         "A list of EISA function DMA configuration entries."
   ::= { hpnsaEISASlotInfo 5 }

   hpnsaEISADmaEntry OBJECT-TYPE
      SYNTAX HpnsaEISADmaEntry
      ACCESS not-accessible
      STATUS mandatory
      DESCRIPTION
         "A description of an EISA function DMA configuration."
      INDEX { hpnsaEISADmaSlotIndex, hpnsaEISADmaFunctIndex,
         hpnsaEISADmaAllocIndex }
   ::= { hpnsaEISADmaTable 1 }

   HpnsaEISADmaEntry ::= SEQUENCE {
      hpnsaEISADmaSlotIndex        INTEGER,
      hpnsaEISADmaFunctIndex       INTEGER,
      hpnsaEISADmaAllocIndex       INTEGER,
      hpnsaEISADmaChannelNum       INTEGER,
      hpnsaEISADmaShare            INTEGER,
      hpnsaEISADmaTiming           INTEGER,
      hpnsaEISADmaXferSize         INTEGER
   }

   hpnsaEISADmaSlotIndex OBJECT-TYPE
      SYNTAX INTEGER (0..255)
      ACCESS read-only
      STATUS mandatory
      DESCRIPTION
         "The EISA slot number of the board that registered the DMA
         configuration this entry describes."
   ::= { hpnsaEISADmaEntry 1 }

   hpnsaEISADmaFunctIndex OBJECT-TYPE
      SYNTAX INTEGER (0..255)
      ACCESS read-only
      STATUS mandatory
      DESCRIPTION
         "The function in which this DMA configuration was registered."
   ::= { hpnsaEISADmaEntry 2 }

   hpnsaEISADmaAllocIndex OBJECT-TYPE
      SYNTAX INTEGER (0..255)
      ACCESS read-only
      STATUS mandatory
      DESCRIPTION
         "The index for this DMA channel allocation entry in the EISA
         function block."
     ::= { hpnsaEISADmaEntry 3 }

   hpnsaEISADmaChannelNum OBJECT-TYPE
      SYNTAX INTEGER (0..65535)
      ACCESS read-only
      STATUS mandatory
      DESCRIPTION
         "The DMA channel number described in this entry."
   ::= { hpnsaEISADmaEntry 4 }

   hpnsaEISADmaShare OBJECT-TYPE
      SYNTAX INTEGER {
         notShared(0),
         shared(1)
      }
      ACCESS read-only
      STATUS mandatory
      DESCRIPTION
         "This value indicates whether the DMA channel is shared."
   ::= { hpnsaEISADmaEntry 5 }

   hpnsaEISADmaTiming OBJECT-TYPE
      SYNTAX INTEGER {
         defaultISACompat(0),
         typeA(1),
         typeB(2),
         burstC(3)
      }
      ACCESS read-only
      STATUS mandatory
      DESCRIPTION
         "DMA timing type."
   ::= { hpnsaEISADmaEntry 6 }

   hpnsaEISADmaXferSize OBJECT-TYPE
      SYNTAX INTEGER {
         eightBit(0),
         sixteenBit(1),
         thirtyTwoBit(2)
      }
      ACCESS read-only
      STATUS mandatory
      DESCRIPTION
         "DMA transfer size."
   ::= { hpnsaEISADmaEntry 7 }

-- ****************************************************************************
-- HP NSA EISA Port Table
-- ======================
--
-- hp                                             (1.3.6.1.4.1.11)
--    nm                                          (hp.2)
--       hpnsa                                    (nm.23)
--          hpnsaEISA Group                       (hpnsa.9)
--             hpnsaEISASlotInfo Group            (hpnsa.9.4)
--                hpnsaEISAPortTable              (hpnsa.9.4.6)
--                   hpnsaEISAPortEntry           (hpnsa.9.4.6.1)
--                      hpnsaEISAPortSlotIndex    (hpnsa.9.4.6.1.1)
--                      hpnsaEISAPortFunctIndex   (hpnsa.9.4.6.1.2)
--                      hpnsaEISAPortEntryIndex   (hpnsa.9.4.6.1.3)
--                      hpnsaEISAPortAddress      (hpnsa.9.4.6.1.4)
--                      hpnsaEISAPortSize         (hpnsa.9.4.6.1.5)
--                      hpnsaEISAPortShared       (hpnsa.9.4.6.1.6)
--
-- Implementation of the EISA Port Init table is mandatory for all
-- HP NSA Agents supporting the HP NSA EISA information MIB.
--
-- ****************************************************************************

   hpnsaEISAPortTable OBJECT-TYPE
      SYNTAX SEQUENCE OF HPnsaEISAPortEntry
      ACCESS not-accessible
      STATUS mandatory
      DESCRIPTION
         "Table containing port information."
   ::= { hpnsaEISASlotInfo 6 }

   hpnsaEISAPortEntry OBJECT-TYPE
      SYNTAX HPnsaEISAPortEntry
      ACCESS not-accessible
      STATUS mandatory
      DESCRIPTION
         "Address of port for the card."
      INDEX { hpnsaEISAPortSlotIndex, hpnsaEISAPortFunctIndex,
         hpnsaEISAPortEntryIndex }
   ::= { hpnsaEISAPortTable 1 }

   HPnsaEISAPortEntry ::= SEQUENCE {
      hpnsaEISAPortSlotIndex  INTEGER,
      hpnsaEISAPortFunctIndex INTEGER,
      hpnsaEISAPortEntryIndex INTEGER,
      hpnsaEISAPortAddress    INTEGER,
      hpnsaEISAPortSize       INTEGER,
      hpnsaEISAPortShared     INTEGER
   }

   hpnsaEISAPortSlotIndex OBJECT-TYPE
      SYNTAX INTEGER
      ACCESS read-only
      STATUS mandatory
      DESCRIPTION
         "Number of the slot for this port entry."
   ::= { hpnsaEISAPortEntry 1 }

   hpnsaEISAPortFunctIndex OBJECT-TYPE
      SYNTAX INTEGER
      ACCESS read-only
      STATUS mandatory
      DESCRIPTION
         "Number of the function for this port entry."
   ::= { hpnsaEISAPortEntry 2 }

   hpnsaEISAPortEntryIndex OBJECT-TYPE
      SYNTAX INTEGER
      ACCESS read-only
      STATUS mandatory
      DESCRIPTION
         "Index of the entry in the entry table."
   ::= { hpnsaEISAPortEntry 3 }

   hpnsaEISAPortAddress OBJECT-TYPE
      SYNTAX INTEGER
      ACCESS read-only
      STATUS mandatory
      DESCRIPTION
         "Port address."
   ::= { hpnsaEISAPortEntry 4 }

   hpnsaEISAPortSize OBJECT-TYPE
      SYNTAX INTEGER
      ACCESS read-only
      STATUS mandatory
      DESCRIPTION
         "0-based number of ports (i.e., 0 means 1 port)."
   ::= { hpnsaEISAPortEntry 5 }

   hpnsaEISAPortShared OBJECT-TYPE
      SYNTAX INTEGER {
         notShared(0),
         shared(1)
      }
      ACCESS read-only
      STATUS mandatory
      DESCRIPTION
         "Indicates whether port is shared."
   ::= { hpnsaEISAPortEntry 6 }

--********************************************************************************
-- HP NSA EISA Port Initialization Table
-- =====================================
--
-- hp                                             (1.3.6.1.4.1.11)
--    nm                                          (hp.2)
--       hpnsa                                    (nm.23)
--          hpnsaEISA Group                       (hpnsa.9)
--             hpnsaEISASlotInfo Group            (hpnsa.9.4)
--                hpnsaEISAPortInitTable            (hpnsa.9.4.7)
--                   hpnsaEISAPortInitEntry         (hpnsa.9.4.7.1)
--                      hpnsaEISAPortInitSlotIndex  (hpnsa.9.4.7.1.1)
--                      hpnsaEISAPortInitFunctIndex (hpnsa.9.4.7.1.2)
--                      hpnsaEISAPortInitEntryIndex (hpnsa.9.4.7.1.3)
--                      hpnsaEISAPortInitData       (hpnsa.9.4.7.1.4)
--
-- Implementation of the EISA Port Init table is mandatory for all
-- HP NSA Agents supporting the HP NSA EISA information MIB.
--
--********************************************************************************

   hpnsaEISAPortInitTable OBJECT-TYPE
      SYNTAX SEQUENCE OF HPnsaEISAPortInitEntry
      ACCESS not-accessible
      STATUS mandatory
      DESCRIPTION
         "Table containing port init values."
   ::= { hpnsaEISASlotInfo 7 }

   hpnsaEISAPortInitEntry OBJECT-TYPE
      SYNTAX HPnsaEISAPortInitEntry
      ACCESS not-accessible
      STATUS mandatory
      DESCRIPTION
         "Table entry of port init values."
      INDEX { hpnsaEISAPortInitSlotIndex, hpnsaEISAPortInitFunctIndex,
         hpnsaEISAPortInitEntryIndex}
   ::= { hpnsaEISAPortInitTable 1 }

   HPnsaEISAPortInitEntry ::= SEQUENCE {
      hpnsaEISAPortInitSlotIndex   INTEGER,
      hpnsaEISAPortInitFunctIndex  INTEGER,
      hpnsaEISAPortInitEntryIndex  INTEGER,
      hpnsaEISAPortInitData        OCTET STRING
   }

   hpnsaEISAPortInitSlotIndex OBJECT-TYPE
      SYNTAX INTEGER
      ACCESS read-only
      STATUS mandatory
      DESCRIPTION
         "Slot number for this port init entry."
   ::= { hpnsaEISAPortInitEntry 1 }

   hpnsaEISAPortInitFunctIndex OBJECT-TYPE
      SYNTAX INTEGER
      ACCESS read-only
      STATUS mandatory
      DESCRIPTION
         "Function index for this port init entry."
   ::= { hpnsaEISAPortInitEntry 2 }

   hpnsaEISAPortInitEntryIndex OBJECT-TYPE
      SYNTAX INTEGER
      ACCESS read-only
      STATUS mandatory
      DESCRIPTION
         "Index of this port init entry."
   ::= { hpnsaEISAPortInitEntry 3 }

   hpnsaEISAPortInitData OBJECT-TYPE
      SYNTAX OCTET STRING (SIZE(11))
      ACCESS read-only
      STATUS mandatory
      DESCRIPTION
         "Port initialization data.
         Byte 0      Initialization Type
         Byte 1      LSB of port I/O address
         Byte 2      MSB of port I/O address

         Byte 3 - 10 port value/mask"
   ::= { hpnsaEISAPortInitEntry 4 }

END
