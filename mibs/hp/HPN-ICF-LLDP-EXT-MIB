-- ============================================================================
-- Copyright (c) 2010-2013 Hewlett-Packard Development Company, L.P.
--
-- Description: There are three standard MIB definitions, "LLDP-MIB", "LLDP-EXT-
--     DOT1-MIB", "LLDP-EXT-DOT3-MIB", define almost all MIB objects of LLDP.
--     This document defines more MIB objects privately For LLDP implementation.
--      1)LLDP default global status is disabled, a management object needed to
--        enable it.
--      2)LLDP needs to be compliable with CDP (Non standard IEEE link layer di-
--        scovery protocol). A management object needed to enable or disable co-
--        mpliance.
--      3)For compliance with CDP, port based control management object is need-
--        ed.
--
-- Reference:
-- Version: V1.0
-- History:
-- V1.0 created by qizhenglin 2009-03-20
-- ============================================================================
HPN-ICF-LLDP-EXT-MIB DEFINITIONS ::= BEGIN

IMPORTS
    MODULE-IDENTITY, OBJECT-TYPE, Integer32, Counter32
        FROM SNMPv2-SMI
    TruthValue
        FROM SNMPv2-TC
    hpnicfCommon
        FROM  HPN-ICF-OID-MIB
    LldpPortNumber
        FROM LLDP-MIB;

hpnicflldp MODULE-IDENTITY
    LAST-UPDATED "200903210000Z"
    ORGANIZATION
        ""
    CONTACT-INFO
        ""
    DESCRIPTION
        "LLDP extended management infomation."
    REVISION  "200903210000Z"
    DESCRIPTION ""
    ::= { hpnicfCommon 100 }

hpnicflldpObjects                    OBJECT IDENTIFIER ::= { hpnicflldp 1 }

--
-- LLDP extended MIB Objects
--
hpnicflldpConfiguration              OBJECT IDENTIFIER ::= { hpnicflldpObjects 1 }

--
-- LLDP extended global configuration
--
hpnicflldpAdminStatus OBJECT-TYPE
    SYNTAX TruthValue
    MAX-ACCESS  read-write
    STATUS      current
    DESCRIPTION
        "The global administratively desired status of the local LLDP agent."
    ::= { hpnicflldpConfiguration 1 }

hpnicflldpComplianceCDPStatus OBJECT-TYPE
    SYNTAX TruthValue
    MAX-ACCESS  read-write
    STATUS      current
    DESCRIPTION
        "The global administratively desired status of CDP Compliance."
    ::= { hpnicflldpConfiguration 2 }

--
-- hpnicflldpPortConfigTable: LLDP configuration on a per port basis
--

hpnicflldpPortConfigTable   OBJECT-TYPE
    SYNTAX      SEQUENCE OF HpnicflldpPortConfigEntry
    MAX-ACCESS  not-accessible
    STATUS      current
    DESCRIPTION
        "The port-based table that controls extended functions."
    ::= { hpnicflldpConfiguration 3 }

hpnicflldpPortConfigEntry   OBJECT-TYPE
    SYNTAX      HpnicflldpPortConfigEntry
    MAX-ACCESS  not-accessible
    STATUS      current
    DESCRIPTION
        "LLDP extended configuration information for a particular port. This co-
        nfiguration parameter controls compliance with other non-standard link
        layer discovery protocol such as CDP."
    INDEX  { hpnicflldpPortConfigPortNum }
    ::= { hpnicflldpPortConfigTable 1 }

HpnicflldpPortConfigEntry ::= SEQUENCE {
    hpnicflldpPortConfigPortNum         LldpPortNumber,
    hpnicflldpPortConfigCDPComplianceStatus        INTEGER }

hpnicflldpPortConfigPortNum   OBJECT-TYPE
    SYNTAX      LldpPortNumber
    MAX-ACCESS  not-accessible
    STATUS      current
    DESCRIPTION
        "The index value used to identify the port component associated with th-
         is entry."
    ::= { hpnicflldpPortConfigEntry 1 }

hpnicflldpPortConfigCDPComplianceStatus  OBJECT-TYPE
    SYNTAX INTEGER {
       txAndRx(1),
       disabled(2)
    }
    MAX-ACCESS read-write
    STATUS     current
    DESCRIPTION
        "The administratively desired CDP Compliance status of the local LLDP a-
        gent. If the associated hpnicflldpPortConfigCDPComplianceStatus object has
        a value of 'txAndRx', then the LLDP agent will receive CDP frames on th-
        is port, and will transmit CDP frames only after receive a CDP frames.
        If the associated lldpPortConfigAdminStatus object has a value of 'disa-
        bled', LLDP agent will not transmit or receive CDP frames on this port."
   DEFVAL  { disabled }
   ::= { hpnicflldpPortConfigEntry 2 }

END
