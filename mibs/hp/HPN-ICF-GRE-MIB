-- =================================================================
-- Copyright (c) 2010-2013 Hewlett-Packard Development Company, L.P.
--
-- Description: Generic Routing Encapsulation configuration MIB
-- Reference: IF-MIB
-- Version: V1.0
-- History:
-- V1.0 created by Sun Ludong
--   2005-06-04 Initial version
-- =================================================================
HPN-ICF-GRE-MIB DEFINITIONS ::= BEGIN

IMPORTS
    hpnicfCommon
        FROM HPN-ICF-OID-MIB
    Unsigned32, OBJECT-TYPE, MODULE-IDENTITY
        FROM SNMPv2-SMI
    ifIndex
        FROM IF-MIB;

hpnicfGre MODULE-IDENTITY
    LAST-UPDATED
        "200506040000Z"                        -- June 4, 2005 at 00:00 GMT
    ORGANIZATION
        ""
    CONTACT-INFO
        ""
    DESCRIPTION
        "This MIB contains objects to Manage configuration and
        Monitor running state for GRE.
        "
    REVISION
        "200506040000Z"                        -- June 4, 2005 at 00:00 GMT
    DESCRIPTION
        "The initial revision of this MIB module.
        "
    ::= { hpnicfCommon 54 }

    hpnicfGreObjects OBJECT IDENTIFIER ::= { hpnicfGre 1 }

    hpnicfGreTable  OBJECT-TYPE
    SYNTAX SEQUENCE OF HpnicfGreEntry
    MAX-ACCESS not-accessible
    STATUS current
    DESCRIPTION
        "A table of Generic Routing Encapsulation(GRE) configuration.
        It contains configuration of GRE Key, and enable flags of Key
        and Checksum. The detail of Key and Checksum is described in
        RFC2784 and RFC2890.
        "
    ::= { hpnicfGreObjects 1 }

    hpnicfGreEntry OBJECT-TYPE
    SYNTAX HpnicfGreEntry
    MAX-ACCESS not-accessible
    STATUS current
    DESCRIPTION
        "The entry of hpnicfGreTable
        "
    INDEX { ifIndex }
    ::= { hpnicfGreTable 1 }

    HpnicfGreEntry ::= SEQUENCE {
        hpnicfGreKeyValue
            Unsigned32,
        hpnicfGreKey
            INTEGER,
        hpnicfGreChecksum
            INTEGER
    }
    hpnicfGreKeyValue OBJECT-TYPE
    SYNTAX Unsigned32
    MAX-ACCESS read-write
    STATUS current
    DESCRIPTION
        "The value of GRE key
        "
    ::= { hpnicfGreEntry 1 }

    hpnicfGreKey OBJECT-TYPE
        SYNTAX INTEGER{
            enable(1),
            disable(2)
        }
        MAX-ACCESS read-write
        STATUS current
        DESCRIPTION
        "The enable flag of GRE key
        "
    ::= { hpnicfGreEntry 2 }

    hpnicfGreChecksum OBJECT-TYPE
        SYNTAX INTEGER{
            enable(1),
            disable(2)
        }
        MAX-ACCESS read-write
        STATUS current
        DESCRIPTION
            "The enable flag of GRE Checksum
            "
        ::= { hpnicfGreEntry 3 }

END
