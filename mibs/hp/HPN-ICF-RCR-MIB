-- =================================================================
-- Copyright (c) 2010-2013 Hewlett-Packard Development Company, L.P.
--
-- Description: Resilient Controllable Routing MIB
-- Reference:
-- Version: V1.1
-- History:
--   V1.0 2005-04-06 created by ZhangQiang
--     Initial version
--   V1.1 2005-06-28 modified by TanZhi and DaiRuiqiang
--     Rewrite the whole MIB
-- =================================================================
HPN-ICF-RCR-MIB DEFINITIONS ::= BEGIN

    IMPORTS
        hpnicfCommon
            FROM HPN-ICF-OID-MIB
        InterfaceIndex
            FROM IF-MIB
        InetAddressType, InetAddress
            FROM INET-ADDRESS-MIB
        Integer32, OBJECT-TYPE, MODULE-IDENTITY, NOTIFICATION-TYPE
            FROM SNMPv2-SMI;

    hpnicfRcr MODULE-IDENTITY
        LAST-UPDATED "200506281936Z"        -- June 28, 2005 at 19:36 GMT
        ORGANIZATION
            ""
        CONTACT-INFO
            ""
        DESCRIPTION
            "This MIB is applicable to router-devices. It's made for RCR
            (Resilient Controllable Routing).
            RCR provides an effective resolution which can dynamically auto-adjust
            outbound traffic to the optimal external interface by monitoring the
            performance and traffic load of each external interface. It provides
            the functions of intelligentized traffic load distribution and the optimal external interface
            selection. This can optimally utilize the external interfaces. Furthermore,
            RCR realized the function which can select the optimal external interface
            based on different classes of operation flow."
        REVISION "200506281936Z"        -- June 28, 2005 at 19:36 GMT
        DESCRIPTION
            "The modified revision of this MIB module. Rewrite the whole MIB."
        ::= { hpnicfCommon 48 }
--
-- Node definitions
--


-- The member router-device(MR) information is defined here.
    hpnicfRcrMR OBJECT IDENTIFIER ::= { hpnicfRcr 1 }

-- Scalar MIB objects, which are considered as global variables
-- to all member router-devices, are defined in this section.
-- This group contains global variables of all member router-devices which
-- are controlled by RCR.

    hpnicfRcrMRGroup OBJECT IDENTIFIER ::= {   hpnicfRcrMR 1  }

    hpnicfRcrMRAllMaxUsedBandRate OBJECT-TYPE
        SYNTAX Integer32 (1..100)
        UNITS "%"
        MAX-ACCESS read-write
        STATUS current
        DESCRIPTION
            "The max used band rate of all external interfaces on member
            router-devices(MRs) which are controlled by RCR."
        ::= { hpnicfRcrMRGroup 1 }

    hpnicfRcrMRAllMinUsedBandRate OBJECT-TYPE
        SYNTAX Integer32 (0..100)
        UNITS "%"
        MAX-ACCESS read-write
        STATUS current
        DESCRIPTION
            "The min used band rate of all external interfaces on MRs
            which are controlled by RCR."
        ::= { hpnicfRcrMRGroup 2 }


    hpnicfRcrMRListenTime OBJECT-TYPE
        SYNTAX Integer32 (1..1440)
        UNITS "minute"
        MAX-ACCESS read-write
        STATUS current
        DESCRIPTION
            "The persistent time of a probe on member router-device(MR) which is
            controlled by RCR."
        ::= { hpnicfRcrMRGroup 3 }


    hpnicfRcrMRStateTable OBJECT-TYPE
        SYNTAX SEQUENCE OF HpnicfRcrMRStateEntry
        MAX-ACCESS not-accessible
        STATUS current
        DESCRIPTION
            "This table contains state information of each MR
            which is controlled by RCR."
        ::= { hpnicfRcrMR 2 }

    hpnicfRcrMRStateEntry OBJECT-TYPE
        SYNTAX HpnicfRcrMRStateEntry
        MAX-ACCESS not-accessible
        STATUS current
        DESCRIPTION
            "Entry items"
        INDEX { hpnicfRcrMRName }
        ::= { hpnicfRcrMRStateTable 1 }

    HpnicfRcrMRStateEntry ::=
        SEQUENCE {
            hpnicfRcrMRName
                OCTET STRING,
            hpnicfRcrMRState
                INTEGER,
            hpnicfRcrMRAuthType
                INTEGER,
            hpnicfRcrMRAuthPwd
                OCTET STRING
                 }

    hpnicfRcrMRName OBJECT-TYPE
        SYNTAX OCTET STRING (SIZE(1..32))
        MAX-ACCESS not-accessible
        STATUS current
        DESCRIPTION
            "The name of MR which is controlled by RCR."
        ::= { hpnicfRcrMRStateEntry 1 }

    hpnicfRcrMRState OBJECT-TYPE
        SYNTAX INTEGER
            {
            down(1),
            up(2),
            controlled(3)
            }
        MAX-ACCESS read-only
        STATUS current
        DESCRIPTION
            "The state of MR where identified on the controller
            router-device(CR).
            down: The MR has been enabled but has not connected
                  to the CR with TCP connection.
            up: The MR has already successfully connected to
                the CR but has not been ready for adjusting
                route.
            controlled: The MR has already passed the
                        consultation with the CR and could
                        be controlled by it."
        ::= { hpnicfRcrMRStateEntry 2 }

     hpnicfRcrMRAuthType OBJECT-TYPE
        SYNTAX INTEGER
            {
            simple(1),
            md5(2)
            }
        MAX-ACCESS read-write
        STATUS current
        DESCRIPTION
            "The authentication type of communication packet between CR and MR."
        ::= { hpnicfRcrMRStateEntry 3 }

    hpnicfRcrMRAuthPwd OBJECT-TYPE
        SYNTAX OCTET STRING
        MAX-ACCESS read-write
        STATUS current
        DESCRIPTION
            "The authentication password of communication packet between CR
            and MR.
            Reading this object always results in an OCTET STRING of length zero;
            authentication may not be bypassed by reading the MIB object."
        ::= { hpnicfRcrMRStateEntry 4 }

    hpnicfRcrMROutIfStateTable OBJECT-TYPE
        SYNTAX SEQUENCE OF HpnicfRcrMROutIfStateEntry
        MAX-ACCESS not-accessible
        STATUS current
        DESCRIPTION
            "This table contains the external interface states of each MR
            which is controlled by RCR."
        ::= { hpnicfRcrMR 3 }

    hpnicfRcrMROutIfStateEntry OBJECT-TYPE
        SYNTAX HpnicfRcrMROutIfStateEntry
        MAX-ACCESS not-accessible
        STATUS current
        DESCRIPTION
            "Entry items"
        INDEX { hpnicfRcrMRName, hpnicfRcrMROutIfName }
        ::= { hpnicfRcrMROutIfStateTable 1 }

    HpnicfRcrMROutIfStateEntry ::=
        SEQUENCE {
            hpnicfRcrMROutIfName
                OCTET STRING,
            hpnicfRcrMROutIfState
                INTEGER,
            hpnicfRcrMROutIfMaxUsedBandRate
                Integer32,
            hpnicfRcrMROutIfMinUsedBandRate
                Integer32,
            hpnicfRcrMROutIfUsedBandRate
                Integer32
                 }

    hpnicfRcrMROutIfName OBJECT-TYPE
        SYNTAX OCTET STRING (SIZE(1..48))
        MAX-ACCESS not-accessible
        STATUS current
        DESCRIPTION
            "The name of external interface on each MR."
        ::= { hpnicfRcrMROutIfStateEntry 1 }

    hpnicfRcrMROutIfState OBJECT-TYPE
        SYNTAX INTEGER
            {
            down(1),
            up(2),
            notExist(3)
            }
        MAX-ACCESS read-only
        STATUS current
        DESCRIPTION
            "The state of external interface on each MR."
        ::= { hpnicfRcrMROutIfStateEntry 2 }

    hpnicfRcrMROutIfMaxUsedBandRate OBJECT-TYPE
        SYNTAX Integer32 (1..100)
        UNITS "%"
        MAX-ACCESS read-write
        STATUS current
        DESCRIPTION
            "The max spendable bandwidth rate on external interface."
        ::= { hpnicfRcrMROutIfStateEntry 3 }

    hpnicfRcrMROutIfMinUsedBandRate OBJECT-TYPE
        SYNTAX Integer32 (0..100)
        UNITS "%"
        MAX-ACCESS read-write
        STATUS current
        DESCRIPTION
            "The min spendable bandwidth rate on external interface."
        ::= { hpnicfRcrMROutIfStateEntry 4 }

    hpnicfRcrMROutIfUsedBandRate  OBJECT-TYPE
        SYNTAX Integer32 (0..100)
        UNITS "%"
        MAX-ACCESS read-only
        STATUS current
        DESCRIPTION
            "The used bandwidth rate on external interface."
        ::= { hpnicfRcrMROutIfStateEntry 5 }

-- The controller router-device information are defined here.
   hpnicfRcrCR OBJECT IDENTIFIER ::= { hpnicfRcr 2 }

-- Scalar MIB objects, which are considered as global variables
-- to all member router-devices, are defined in this section.
    hpnicfRcrCRGroup OBJECT IDENTIFIER ::= {   hpnicfRcrCR 1  }

    hpnicfRcrCRState OBJECT-TYPE
        SYNTAX INTEGER
            {
            down(1),
            init(2),
            active(3)
            }
        MAX-ACCESS read-only
        STATUS current
        DESCRIPTION
            "The state of the CR which is controlled
            by RCR.
            down: The CR has been enabled but has not
                  started a TCP connection server.
            init: The CR has started a TCP connection
                  server and has been waiting for MR
                  connection, but has not been ready for adjusting route.
            active: The CR is ready for adjusting route."
        ::= { hpnicfRcrCRGroup 1 }

    hpnicfRcrCRPortNum OBJECT-TYPE
        SYNTAX Integer32
        MAX-ACCESS read-write
        STATUS current
        DESCRIPTION
            "The communication port number between CR and MR."
        ::= { hpnicfRcrCRGroup 2 }

     hpnicfRcrCRCtrlMode OBJECT-TYPE
        SYNTAX INTEGER
            {
            control(1),
            observe(2)
            }
        MAX-ACCESS read-write
        STATUS current
        DESCRIPTION

            "The observe mode or control mode is configured to operate in the CR.
             observe: The CR monitors prefixes and external interfaces based on default
                      and user-defined policies and then reports the status of
                      the network and the decisions that should be made but does
                      not implement any changes.
             controlled: The CR monitors prefixes and external interfaces based on default
                         and user-defined policies and then reports the status
                         of the network and the decisions that should be made
                         and implement any changes."
       ::= { hpnicfRcrCRGroup 3 }

    hpnicfRcrCRChooseMode OBJECT-TYPE
        SYNTAX INTEGER
        {
        good(1),
        best(2)
        }
        MAX-ACCESS read-write
        STATUS current
        DESCRIPTION
            "The algorithm used to choose an alternative external interface for a prefix.
             good: The first external interface that conforms to the policy is selected as
                   the new external interface.
             best: Information is collected from all external interfaces and the best one
                   is selected even though the best external interface may not be in-policy."
        ::= { hpnicfRcrCRGroup 4 }

    hpnicfRcrCRKeepaliveTime OBJECT-TYPE
        SYNTAX Integer32 (1..1000)
        UNITS "second"
        MAX-ACCESS read-write
        STATUS current
        DESCRIPTION
            "The interval time of the transmission of the keepalive communication
             packet between CR and MR."
        ::= { hpnicfRcrCRGroup 5 }


    hpnicfRcrCRPolicyMode OBJECT-TYPE
        SYNTAX INTEGER
            {
            prefix(1),
            operation(2),
            study(3)
            }
        MAX-ACCESS read-write
        STATUS current
        DESCRIPTION
            "The chosen policy mode which decides to change what prefix.
            prefix: An RCR policy is designed to select IP prefixes or to
                     select RCR learn policies using a match clause and then to
                     apply RCR policy configurations using a set clause.
            operation: To deside to adjusted prefixes based on operation
                        which user configured.
            study: To learn and optimize prefixes based on the highest
                    throughput or the highest delay."
        ::= { hpnicfRcrCRGroup 6 }

    hpnicfRcrCRStudyMode OBJECT-TYPE
        SYNTAX INTEGER
            {
            maxThoughout(1),
            maxDelay(2)
            }
        MAX-ACCESS read-write
        STATUS current
        DESCRIPTION
            "The mode of collecting prefix in studying configuration mode.
            It's to collect either the prefix of max thoughtout or the prefix
            of max delay time. It doesn't have a value when CR isn't in studying
            configuration mode."
        ::= { hpnicfRcrCRGroup 7 }

    hpnicfRcrCRStudyIpPrefixNum OBJECT-TYPE
        SYNTAX Integer32 (1..2500)
        MAX-ACCESS read-write
        STATUS current
        DESCRIPTION
            "The max number of collecting prefix in studying configuration mode."
        ::= { hpnicfRcrCRGroup 8 }

	hpnicfRcrCRIpPrefixLen OBJECT-TYPE
        SYNTAX Integer32 (1..32)
        MAX-ACCESS read-write
        STATUS current
        DESCRIPTION
            "The mask length of collecting prefix in configuration mode."
        DEFVAL { 24 }
        ::= { hpnicfRcrCRGroup 9 }

--RCR policy table is defined here.
    hpnicfRcrCRRcrPolicyTable OBJECT-TYPE
        SYNTAX SEQUENCE OF HpnicfRcrCRRcrPolicyEntry
        MAX-ACCESS not-accessible
        STATUS current
        DESCRIPTION
            "This table contains objects to get statistic information
            of interfaces on a device."
        ::= { hpnicfRcrCR 2 }

    hpnicfRcrCRRcrPolicyEntry OBJECT-TYPE
        SYNTAX HpnicfRcrCRRcrPolicyEntry
        MAX-ACCESS not-accessible
        STATUS current
        DESCRIPTION
            "Entry items"
        INDEX { hpnicfRcrCRRcrPlyID }
        ::= { hpnicfRcrCRRcrPolicyTable 1 }

    HpnicfRcrCRRcrPolicyEntry ::=
        SEQUENCE {
            hpnicfRcrCRRcrPlyID
                Integer32,
            hpnicfRcrCRRcrPlyMatchIPListName
                OCTET STRING,
            hpnicfRcrCRRcrPlyMatchStudyEnable
                INTEGER,
            hpnicfRcrCRRcrPlyMatchOperPlyName
                OCTET STRING,
            hpnicfRcrCRRcrAclNumber
                Integer32,
            hpnicfRcrCRRcrPlyDelayTime
                Integer32,
            hpnicfRcrCRRcrPlyLossRate
                Integer32
                  }

    hpnicfRcrCRRcrPlyID OBJECT-TYPE
        SYNTAX Integer32
        MAX-ACCESS not-accessible
        STATUS current
        DESCRIPTION
            "The ID of RCR policy which the user has configured."
        ::= { hpnicfRcrCRRcrPolicyEntry 1 }

    hpnicfRcrCRRcrPlyMatchIPListName OBJECT-TYPE
        SYNTAX OCTET STRING  (SIZE(1..19))
        MAX-ACCESS read-write
        STATUS current
        DESCRIPTION
            "The matched IP prefix list name of RCR policy which the user has
            configured."
        ::= { hpnicfRcrCRRcrPolicyEntry 2 }

    hpnicfRcrCRRcrPlyMatchStudyEnable OBJECT-TYPE
        SYNTAX INTEGER
            {
            disable(1),
            enable(2)
            }
        MAX-ACCESS read-write
        STATUS current
        DESCRIPTION
            "Whether the RCR policy which the user has configured is matched
            for studying prefix mode."
        ::= { hpnicfRcrCRRcrPolicyEntry 3 }

    hpnicfRcrCRRcrPlyMatchOperPlyName OBJECT-TYPE
        SYNTAX OCTET STRING  (SIZE(1..19))
        MAX-ACCESS read-write
        STATUS current
        DESCRIPTION
            "The matched operation policy name of RCR policy which the user
            has configured."
        ::= { hpnicfRcrCRRcrPolicyEntry 4 }

   hpnicfRcrCRRcrAclNumber OBJECT-TYPE
        SYNTAX Integer32 (3000..3999)
        MAX-ACCESS read-write
        STATUS current
        DESCRIPTION
            "The matched acl number of RCR operation policy which the user
            has configured."
        ::= { hpnicfRcrCRRcrPolicyEntry 5 }

    hpnicfRcrCRRcrPlyDelayTime OBJECT-TYPE
        SYNTAX Integer32  (1..10000)
        UNITS "millisecond"
        MAX-ACCESS read-write
        STATUS current
        DESCRIPTION
            "The absolute maximum delay time. The range of values that can be
            configured is from 1 to 10000."
        ::= { hpnicfRcrCRRcrPolicyEntry 6 }

    hpnicfRcrCRRcrPlyLossRate OBJECT-TYPE
        SYNTAX Integer32 (1..100)
        UNITS "%"
        MAX-ACCESS read-write
        STATUS current
        DESCRIPTION
            "The packet loss percent of prefix which the CR concerns."
        ::= { hpnicfRcrCRRcrPolicyEntry 7 }

--Matched prefix performance table define
    hpnicfRcrCRMatPrefixPerfTable OBJECT-TYPE
        SYNTAX SEQUENCE OF HpnicfRcrCRMatPrefixPerfEntry
        MAX-ACCESS not-accessible
        STATUS current
        DESCRIPTION
            "This table contains the matched prefix performance
            information."
        ::= { hpnicfRcrCR 3 }

    hpnicfRcrCRMatPrefixPerfEntry OBJECT-TYPE
        SYNTAX HpnicfRcrCRMatPrefixPerfEntry
        MAX-ACCESS not-accessible
        STATUS current
        DESCRIPTION
            "Entry items"
        INDEX { hpnicfRcrCRMatPrefPerfAddrType, hpnicfRcrCRMatPrefPerfDestIPAddr,
                hpnicfRcrCRMatPrefPerfDestMaskLen }
        ::= { hpnicfRcrCRMatPrefixPerfTable 1 }

    HpnicfRcrCRMatPrefixPerfEntry ::=
        SEQUENCE {
            hpnicfRcrCRMatPrefPerfAddrType
                InetAddressType,
            hpnicfRcrCRMatPrefPerfDestIPAddr
                InetAddress,
            hpnicfRcrCRMatPrefPerfDestMaskLen
                Integer32,
            hpnicfRcrCRMatPrefPerfDelayTime
                Integer32,
            hpnicfRcrCRMatPrefPerfLossRate
                Integer32,
            hpnicfRcrCRMatPrefPerfThroughput
                Integer32
                    }

    hpnicfRcrCRMatPrefPerfAddrType OBJECT-TYPE
        SYNTAX InetAddressType
        MAX-ACCESS not-accessible
        STATUS current
        DESCRIPTION
            "The destination IP addresses type of matched prefix which the CR
            wants (IPv4 or IPv6)."
        ::= { hpnicfRcrCRMatPrefixPerfEntry 1 }

    hpnicfRcrCRMatPrefPerfDestIPAddr OBJECT-TYPE
        SYNTAX InetAddress
        MAX-ACCESS not-accessible
        STATUS current
        DESCRIPTION
            "The destination IP address of matched prefix which the CR wants."
        ::= { hpnicfRcrCRMatPrefixPerfEntry 2 }

    hpnicfRcrCRMatPrefPerfDestMaskLen OBJECT-TYPE
        SYNTAX Integer32 (0..32)
        MAX-ACCESS not-accessible
        STATUS current
        DESCRIPTION
            "The destination IP address mask length of matched prefix which
            the CR wants."
        ::= { hpnicfRcrCRMatPrefixPerfEntry 3 }

    hpnicfRcrCRMatPrefPerfDelayTime OBJECT-TYPE
        SYNTAX Integer32  (1..10000)
        UNITS "second"
        MAX-ACCESS read-only
        STATUS current
        DESCRIPTION
            "The absolute maximum delay time of prefix which the CR has
            configured."
        ::= { hpnicfRcrCRMatPrefixPerfEntry 4 }

    hpnicfRcrCRMatPrefPerfLossRate OBJECT-TYPE
        SYNTAX Integer32 (1..100)
        UNITS "%"
        MAX-ACCESS read-only
        STATUS current
        DESCRIPTION
            "The packet loss percent of prefix which the CR has configured."
        ::= { hpnicfRcrCRMatPrefixPerfEntry 5 }

    hpnicfRcrCRMatPrefPerfThroughput OBJECT-TYPE
        SYNTAX Integer32
        UNITS "kb"
        MAX-ACCESS read-only
        STATUS current
        DESCRIPTION
            "The bandwidth of prefix which the CR has monitored."
        ::= { hpnicfRcrCRMatPrefixPerfEntry 6 }

--Adjusted prefix table define
    hpnicfRcrCRAdjustPrefixTable OBJECT-TYPE
        SYNTAX SEQUENCE OF HpnicfRcrCRAdjustPrefixEntry
        MAX-ACCESS not-accessible
        STATUS current
        DESCRIPTION
            "This table contains objects to get adjusted prefix information
            which the CR controlled."
        ::= { hpnicfRcrCR 4 }

    hpnicfRcrCRAdjustPrefixEntry OBJECT-TYPE
        SYNTAX HpnicfRcrCRAdjustPrefixEntry
        MAX-ACCESS not-accessible
        STATUS current
        DESCRIPTION
            "Entry items"
        INDEX { hpnicfRcrCRAdjuPrefDestAddrType, hpnicfRcrCRAdjuPrefDestAddr,
        	   hpnicfRcrCRAdjuPrefMaskLen, hpnicfRcrCRAdjuPrefPreMRName,
        	   hpnicfRcrCRAdjuPrefPreOutIfName }
        ::= { hpnicfRcrCRAdjustPrefixTable 1 }

    HpnicfRcrCRAdjustPrefixEntry ::=
        SEQUENCE {
            hpnicfRcrCRAdjuPrefDestAddrType
                InetAddressType,
            hpnicfRcrCRAdjuPrefDestAddr
                InetAddress,
            hpnicfRcrCRAdjuPrefMaskLen
                Integer32,
            hpnicfRcrCRAdjuPrefPreMRName
                OCTET STRING,
            hpnicfRcrCRAdjuPrefPreOutIfName
                OCTET STRING,
            hpnicfRcrCRAdjuPrefCurMRName
                OCTET STRING,
            hpnicfRcrCRAdjuPrefCurOutIfName
                OCTET STRING,
            hpnicfRcrCRAdjuPrefPersistTime
                Integer32,
            hpnicfRcrCRAdjuPrefAgeTime
                Integer32
                    }

    hpnicfRcrCRAdjuPrefDestAddrType OBJECT-TYPE
        SYNTAX InetAddressType
        MAX-ACCESS not-accessible
        STATUS current
        DESCRIPTION
            "The IP address type of the adjusted prefix which CR controlled
            (IPv4 or IPv6)."
        ::= { hpnicfRcrCRAdjustPrefixEntry 1 }

    hpnicfRcrCRAdjuPrefDestAddr OBJECT-TYPE
        SYNTAX InetAddress
        MAX-ACCESS not-accessible
        STATUS current
        DESCRIPTION
            "The IP address of the adjusted prefix which CR controlled."
        ::= { hpnicfRcrCRAdjustPrefixEntry 2 }

    hpnicfRcrCRAdjuPrefMaskLen OBJECT-TYPE
        SYNTAX Integer32  (0..32)
        MAX-ACCESS not-accessible
        STATUS current
        DESCRIPTION
            "The IP address mask length of the adjusted prefix which CR
            controlled."
        ::= { hpnicfRcrCRAdjustPrefixEntry 3 }

    hpnicfRcrCRAdjuPrefPreMRName OBJECT-TYPE
        SYNTAX OCTET STRING   (SIZE(1..32))
        MAX-ACCESS not-accessible
        STATUS current
        DESCRIPTION
            "The name of the MR which the previous outbound traffic
            flows through."
        ::= { hpnicfRcrCRAdjustPrefixEntry 4 }

    hpnicfRcrCRAdjuPrefPreOutIfName OBJECT-TYPE
        SYNTAX OCTET STRING (SIZE(1..48))
        MAX-ACCESS not-accessible
        STATUS current
        DESCRIPTION
            "The name of the external interface on the MR which the previous
            outbound traffic flows through."
        ::= { hpnicfRcrCRAdjustPrefixEntry 5 }

    hpnicfRcrCRAdjuPrefCurMRName OBJECT-TYPE
        SYNTAX OCTET STRING   (SIZE(1..32))
        MAX-ACCESS read-only
        STATUS current
        DESCRIPTION
            "The name of the MR which the current outbound traffic flows through."
        ::= { hpnicfRcrCRAdjustPrefixEntry 6 }

    hpnicfRcrCRAdjuPrefCurOutIfName OBJECT-TYPE
        SYNTAX OCTET STRING
        MAX-ACCESS read-only
        STATUS current
        DESCRIPTION
            "The name of the external interface on the MR which the current outbound
            traffic flows through."
        ::= { hpnicfRcrCRAdjustPrefixEntry 7 }

    hpnicfRcrCRAdjuPrefPersistTime OBJECT-TYPE
        SYNTAX Integer32
        UNITS "second"
        MAX-ACCESS read-only
        STATUS current
        DESCRIPTION
            "The persisting time from the time which the adjusted outbound
            traffic has been adjusted by CR to now."
        ::= { hpnicfRcrCRAdjustPrefixEntry 8 }

    hpnicfRcrCRAdjuPrefAgeTime OBJECT-TYPE
        SYNTAX Integer32
        UNITS "second"
        MAX-ACCESS read-only
        STATUS current
        DESCRIPTION
            "The time which the adjusted prefix remains."
        ::= { hpnicfRcrCRAdjustPrefixEntry 9 }
END
