-- ****************************************************************************
--                HP NetServer Tattoo Agent
--        Management Information Base for SNMP Network Management
--
--      Copyright 1999 Hewlett Packard Company.
--      All Rights Reserved.
--
--      The information in this document is subject to change without notice.
--
--      The hp Enterprise number is 11.
--      The ASN.1 prefix to, and including the hp Enterprise is:
--              1.3.6.1.4.1.11
--
-- hp   (1.3.6.1.4.1.11)
--   nm   (1.3.6.1.4.1.11.2)
--     hpnsa  (1.3.6.1.4.1.11.2.23)
--       hpTatAgt (1.3.6.1.4.1.11.2.23.32)
--		   hpTatAgt Version Group (1.3.6.1.4.1.11.2.23.32.1)
--	           hpTatAgtVersion  (1.3.6.1.4.1.11.2.23.32.1.1)
--             hpTatAgtRevision  (1.3.6.1.4.1.11.2.23.32.1.2)
--             hpTatAgtMibVersion  (1.3.6.1.4.1.11.2.23.32.1.3)
--             hpTatAgtMibRevision  (1.3.6.1.4.1.11.2.23.32.1.4)
--		   hpTatAgt Adapter Group (1.3.6.1.4.1.11.2.23.32.2)
--             hpTatAgtnAdapters  (1.3.6.1.4.1.11.2.23.32.2.1)
--             hpTatAgtAdapterTable  (1.3.6.1.4.1.11.2.23.32.2.2)
--                hpTatAgtAdapterEntry  (1.3.6.1.4.1.11.2.23.32.2.2.1)
--                   hpTatAgtAdapterIndex  (1.3.6.1.4.1.11.2.23.32.2.2.1.1)
--                   hpTatAgtAdapterPort  (1.3.6.1.4.1.11.2.23.32.2.2.1.2)
--                   hpTatAgtAdapterName  (1.3.6.1.4.1.11.2.23.32.2.2.1.3)
--                   hpTatAgtAdapterMfg  (1.3.6.1.4.1.11.2.23.32.2.2.1.4)
--                   hpTatAgtDriverVersion  (1.3.6.1.4.1.11.2.23.32.2.2.1.5)
--                   hpTatAgtAdapterClass  (1.3.6.1.4.1.11.2.23.32.2.2.1.6)
--		   hpTatAgt Drive Group (1.3.6.1.4.1.11.2.23.32.3)
--             hpTatAgtnDrives  (1.3.6.1.4.1.11.2.23.32.3.1)
--             hpTatAgtDriveTable  (1.3.6.1.4.1.11.2.23.32.3.2)
--                hpTatAgtAdapterEntry  (1.3.6.1.4.1.11.2.23.32.3.2.1)
--                   hpTatAgtDriveIndex  (1.3.6.1.4.1.11.2.23.32.3.2.1.1)
--                   hpTatAgtDriveAdapter  (1.3.6.1.4.1.11.2.23.32.3.2.1.2)
--                   hpTatAgtDriveChannel  (1.3.6.1.4.1.11.2.23.32.3.2.1.3)
--                   hpTatAgtDriveTargetID  (1.3.6.1.4.1.11.2.23.32.3.2.1.4)
--                   hpTatAgtDriverProdRev  (1.3.6.1.4.1.11.2.23.32.3.2.1.5)
--                   hpTatAgtDriveVendor  (1.3.6.1.4.1.11.2.23.32.3.2.1.6)
--                   hpTatAgtDriveDateCode  (1.3.6.1.4.1.11.2.23.32.3.2.1.7)
--                   hpTatAgtDriveSerialNumber  (1.3.6.1.4.1.11.2.23.32.3.2.1.8)
--                   hpTatAgtDriveHPProductID  (1.3.6.1.4.1.11.2.23.32.3.2.1.9)
--                   hpTatAgtDriveLetters  (1.3.6.1.4.1.11.2.23.32.3.2.1.10)
--                   hpTatAgtDriveRaidLevel  (1.3.6.1.4.1.11.2.23.32.3.2.1.11)
--                   hpTatAgtDriveWasLocated  (1.3.6.1.4.1.11.2.23.32.3.2.1.12)
--				     hpTatAgtDriveDstAvail  (1.3.6.1.4.1.11.2.23.32.3.2.1.13)
--				     hpTatAgtDriveDstPercent  (1.3.6.1.4.1.11.2.23.32.3.2.1.14)
--				     hpTatAgtDriveDstStart  (1.3.6.1.4.1.11.2.23.32.3.2.1.15)
--					 hpTatAgtDriveDstResults  (1.3.6.1.4.1.11.2.23.32.3.2.1.16)
--					 hpTatAgtDriveDstCompletionTime  (1.3.6.1.4.1.11.2.23.32.3.2.1.17)
--					 hpTatAgtDriveDstStartTime (1.3.6.1.4.1.11.2.23.32.3.2.1.18)
--					 hpTatAgtDriveDstEndTime(1.3.6.1.4.1.11.2.23.32.3.2.1.19)
--		  hpTatAgt Refresh Group (1.3.6.1.4.1.11.2.23.32.4)
--			  hpTatAgtRefreshDriveTbl (1.3.6.1.4.1.11.2.23.32.4.1)
--			  hpTatAgtRefreshStatus (1.3.6.1.4.1.11.2.23.32.4.2)
--		  hpTatAgt Status Group					(1.3.6.1.4.1.11.2.23.32.5)
--			  hpTatAgtOverallStatusSeverity		(1.3.6.1.4.1.11.2.23.32.5.1)
--      The Tattoo Agent wakes up periodically to tattoo all drives on the NetServer
--      with predefined configuration information.
-- ****************************************************************************

HPNSATAT-MIB DEFINITIONS ::= BEGIN
    IMPORTS
        enterprises     FROM RFC1155-SMI
		  DisplayString   FROM RFC1213-MIB
		  OBJECT-TYPE     FROM RFC-1212;

	hp                   OBJECT IDENTIFIER ::= {enterprises 11}
	nm                   OBJECT IDENTIFIER ::= {hp 2}
    hpnsa                OBJECT IDENTIFIER ::= {nm 23}
	hpTatAgt             OBJECT IDENTIFIER ::= {hpnsa 32}
	hpTatAgtMibRev         OBJECT IDENTIFIER ::= { hpTatAgt 1 }
	hpTatAgtAdapterInfo    OBJECT IDENTIFIER ::= { hpTatAgt 2 }
	hpTatAgtDriveInfo      OBJECT IDENTIFIER ::= { hpTatAgt 3 }
	hpTatAgtRefreshDrvTbl  OBJECT IDENTIFIER ::= { hpTatAgt 4 }
	hpTatAgtStatusSev	   OBJECT IDENTIFIER ::= { hpTatAgt 5 }
-- ****************************************************************************
--   HP Tattoo Agent MIB Revision Information
--   ========================================
--
-- hp   (1.3.6.1.4.1.11)
--   nm   (1.3.6.1.4.1.11.2)
--     hpnsa  (1.3.6.1.4.1.11.2.23)
--       hpTatAgt (1.3.6.1.4.1.11.2.23.32)
--		   hpTatAgt Version Group (1.3.6.1.4.1.11.2.23.32.1)
--	           hpTatAgtVersion  (1.3.6.1.4.1.11.2.23.32.1.1)
--             hpTatAgtRevision  (1.3.6.1.4.1.11.2.23.32.1.2)
--             hpTatAgtMibVersion  (1.3.6.1.4.1.11.2.23.32.1.3)
--             hpTatAgtMibRevision  (1.3.6.1.4.1.11.2.23.32.1.4)
--
-- Implementation of the MibRev group is mandatory for all HPNSA Agents
-- supporting the HP Tattoo Agent MIB.
-- ****************************************************************************


    hpTatAgtVersion OBJECT-TYPE
        SYNTAX  INTEGER (0..65535)
        ACCESS  read-only
        STATUS  mandatory
        DESCRIPTION
		    "The current version (major) number of the SNMP agent."
        ::= { hpTatAgtMibRev 1 }

    hpTatAgtRevision OBJECT-TYPE
        SYNTAX  INTEGER (0..65535)
        ACCESS  read-only
        STATUS  mandatory
        DESCRIPTION
		    "The current revision (minor) number of the SNMP agent."
        ::= { hpTatAgtMibRev 2 }

    hpTatAgtMibVersion OBJECT-TYPE
        SYNTAX  INTEGER (0..65535)
        ACCESS  read-only
        STATUS  mandatory
        DESCRIPTION
		    "The current version (major) number of the SNMP agent's MIB."
        ::= { hpTatAgtMibRev 3 }

    hpTatAgtMibRevision OBJECT-TYPE
        SYNTAX  INTEGER (0..65535)
        ACCESS  read-only
        STATUS  mandatory
        DESCRIPTION
		    "The current revision (minor) number of the SNMP agent's MIB."
        ::= { hpTatAgtMibRev 4 }


-- ****************************************************************************
--   HP Tattoo Agent Adapter Info
--   ==================================
-- hp   (1.3.6.1.4.1.11)
--   nm   (1.3.6.1.4.1.11.2)
--     hpnsa  (1.3.6.1.4.1.11.2.23)
--       hpTatAgt (1.3.6.1.4.1.11.2.23.32)
--		   hpTatAgt Adapter Group (1.3.6.1.4.1.11.2.23.32.2)
--             hpTatAgtnAdapters  (1.3.6.1.4.1.11.2.23.32.2.1)
--             hpTatAgtAdapterTable  (1.3.6.1.4.1.11.2.23.32.2.2)
--                hpTatAgtAdapterEntry  (1.3.6.1.4.1.11.2.23.32.2.2.1)
--                   hpTatAgtAdapterIndex  (1.3.6.1.4.1.11.2.23.32.2.2.1.1)
--                   hpTatAgtAdapterPort  (1.3.6.1.4.1.11.2.23.32.2.2.1.2)
--                   hpTatAgtAdapterName  (1.3.6.1.4.1.11.2.23.32.2.2.1.3)
--                   hpTatAgtAdapterMfg  (1.3.6.1.4.1.11.2.23.32.2.2.1.4)
--                   hpTatAgtDriverVersion  (1.3.6.1.4.1.11.2.23.32.2.2.1.5)
--                   hpTatAgtAdapterClass  (1.3.6.1.4.1.11.2.23.32.2.2.1.6)

--    Implementation of the Adapter group is mandatory for all HPNSA Agents
--    supporting the HP Tattoo MIB.
--
-- ****************************************************************************

    hpTatAgtnAdapters OBJECT-TYPE
        SYNTAX  INTEGER
        ACCESS  read-only
        STATUS  mandatory
        DESCRIPTION
		    "The number of Adapters present on the system."
        ::= { hpTatAgtAdapterInfo 1 }

    hpTatAgtAdapterTable OBJECT-TYPE
        SYNTAX  SEQUENCE OF HpTatAgtAdapterEntryDef
        ACCESS  not-accessible
        STATUS  mandatory
        DESCRIPTION
		    "A list of the Adapters present on the system."
        ::= { hpTatAgtAdapterInfo 2 }

    hpTatAgtAdapterEntry OBJECT-TYPE
        SYNTAX  HpTatAgtAdapterEntryDef
        ACCESS  not-accessible
        STATUS  mandatory
        DESCRIPTION
		    ""
		INDEX   { hpTatAgtAdapterIndex }
        ::= { hpTatAgtAdapterTable 1 }

    HpTatAgtAdapterEntryDef ::= SEQUENCE
	{
		hpTatAgtAdapterIndex       INTEGER,
		hpTatAgtAdapterPort        INTEGER (0..8),
		hpTatAgtAdapterName        DisplayString,
		hpTatAgtMfg				   DisplayString,
		hpTatAgtDriverVersion	   DisplayString,
		hpTatAgtAdapterClass       INTEGER (0..4)
	}

    hpTatAgtAdapterIndex OBJECT-TYPE
        SYNTAX  INTEGER
        ACCESS  read-only
        STATUS  mandatory
        DESCRIPTION
		    "Index number of this adapter in the table (1 to n)."
        ::= { hpTatAgtAdapterEntry 1 }

    hpTatAgtAdapterPort OBJECT-TYPE
        SYNTAX  INTEGER (0..8)
        ACCESS  read-only
        STATUS  mandatory
        DESCRIPTION
		    "The port number for the adapter/controller"
        ::= { hpTatAgtAdapterEntry 2 }

    hpTatAgtAdapterName OBJECT-TYPE
        SYNTAX  DisplayString
        ACCESS  read-only
        STATUS  mandatory
        DESCRIPTION
		    "The manufacturer's product name for the controller."
        ::= { hpTatAgtAdapterEntry 3 }

    hpTatAgtAdapterMfg OBJECT-TYPE
        SYNTAX  DisplayString
        ACCESS  read-only
        STATUS  mandatory
        DESCRIPTION
		    "A string identifying the manufacturer (or ??? if unknown)."
        ::= { hpTatAgtAdapterEntry 4 }

    hpTatAgtDriverVersion OBJECT-TYPE
        SYNTAX  DisplayString
        ACCESS  read-only
        STATUS  mandatory
        DESCRIPTION
		    "The version string obtained from the device driver file."
        ::= { hpTatAgtAdapterEntry 5 }

    hpTatAgtAdapterClass OBJECT-TYPE
        SYNTAX  INTEGER { AMI(1), MYLEX(2), FIBRECHANNEL(3), SCSIGeneric(4)  }
        ACCESS  read-only
        STATUS  mandatory
        DESCRIPTION
		    "Adapter category"
        ::= { hpTatAgtAdapterEntry 6 }


-- ****************************************************************************
--   HP Tattoo Agent Drive Info
--   ==================================
-- hp   (1.3.6.1.4.1.11)
--   nm   (1.3.6.1.4.1.11.2)
--     hpnsa  (1.3.6.1.4.1.11.2.23)
--       hpTatAgt (1.3.6.1.4.1.11.2.23.32)
--		   hpTatAgt Drive Group (1.3.6.1.4.1.11.2.23.32.2)
--             hpTatAgtnDrives  (1.3.6.1.4.1.11.2.23.32.2.1)
--             hpTatAgtDriveTable  (1.3.6.1.4.1.11.2.23.32.2.2)
--                hpTatAgtDriveEntry  (1.3.6.1.4.1.11.2.23.32.2.2.1)
--                   hpTatAgtDriveIndex  (1.3.6.1.4.1.11.2.23.32.3.2.1.1)
--                   hpTatAgtDriveAdapter  (1.3.6.1.4.1.11.2.23.32.3.2.1.2)
--                   hpTatAgtDriveChannel  (1.3.6.1.4.1.11.2.23.32.3.2.1.3)
--                   hpTatAgtDriveTargetID  (1.3.6.1.4.1.11.2.23.32.3.2.1.4)
--                   hpTatAgtDriverProdRev  (1.3.6.1.4.1.11.2.23.32.3.2.1.5)
--                   hpTatAgtDriveVendor  (1.3.6.1.4.1.11.2.23.32.3.2.1.6)
--                   hpTatAgtDriveDateCode  (1.3.6.1.4.1.11.2.23.32.3.2.1.7)
--                   hpTatAgtDriveSerialNumber  (1.3.6.1.4.1.11.2.23.32.3.2.1.8)
--                   hpTatAgtDriveHPProductID  (1.3.6.1.4.1.11.2.23.32.3.2.1.9)
--                   hpTatAgtDriveLetters  (1.3.6.1.4.1.11.2.23.32.3.2.1.10)
--                   hpTatAgtDriveRaidLevel  (1.3.6.1.4.1.11.2.23.32.3.2.1.11)
--                   hpTatAgtDriveWasLocated  (1.3.6.1.4.1.11.2.23.32.3.2.1.12)

--		     hpTatAgtDriveDstAvail  (1.3.6.1.4.1.11.2.23.32.3.2.1.13)...28.31.0 = DST Is the DST (page 10h) supported
--		     hpTatAgtDriveDstPercent  (1.3.6.1.4.1.11.2.23.32.3.2.1.14)...28.32.0 = DST Get the percent of completion
--		     hpTatAgtDriveDstStart  (1.3.6.1.4.1.11.2.23.32.3.2.1.15)...28.33.0 = DST Start of abort the DST
--		     hpTatAgtDriveDstResults  (1.3.6.1.4.1.11.2.23.32.3.2.1.16)...28.34.0 = DST Get the results from log # (zero for current log)
--		     hpTatAgtDriveDstCompletionTime  (1.3.6.1.4.1.11.2.23.32.3.2.1.17)...28.35.0 = DST Get an estimate for extended test time in seconds

--
--    Implementation of the Drive group is mandatory for all HPNSA Agents
--    supporting the HP Tattoo MIB.
--
-- ****************************************************************************

    hpTatAgtnDrives OBJECT-TYPE
        SYNTAX  INTEGER
        ACCESS  read-only
        STATUS  mandatory
        DESCRIPTION
		    "The number of Drives present on the system."
        ::= { hpTatAgtDriveInfo 1 }

    hpTatAgtDriveTable OBJECT-TYPE
        SYNTAX  SEQUENCE OF HpTatAgtDriveEntryDef
        ACCESS  not-accessible
        STATUS  mandatory
        DESCRIPTION
		    "A list of the Drives present on the system."
        ::= { hpTatAgtDriveInfo 2 }

    hpTatAgtDriveEntry OBJECT-TYPE
        SYNTAX  HpTatAgtDriveEntryDef
        ACCESS  not-accessible
        STATUS  mandatory
        DESCRIPTION
		    ""
		INDEX   { hpTatAgtDriveIndex }
        ::= { hpTatAgtDriveTable 1 }

    HpTatAgtDriveEntryDef ::= SEQUENCE
	{
		hpTatAgtDriveIndex   INTEGER,
        hpTatAgtDriveAdapter  INTEGER(0..8),
        hpTatAgtDriveChannel  INTEGER,
        hpTatAgtDriveTargetID  INTEGER,
        hpTatAgtDriverProdRev  DisplayString,
        hpTatAgtDriveVendor  DisplayString,
        hpTatAgtDriveDateCode  DisplayString,
        hpTatAgtDriveSerialNumber  DisplayString,
        hpTatAgtDriveHPProductID  DisplayString,
        hpTatAgtDriveLetters  DisplayString,
        hpTatAgtDriveRaidLevel  INTEGER,
        hpTatAgtDriveWasLocated  INTEGER,

	hpTatAgtDriveDstAvail INTEGER,
	hpTatAgtDriveDstPercent INTEGER,
	hpTatAgtDriveDstStart INTEGER,
	hpTatAgtDriveDstResults INTEGER,
	hpTatAgtDriveDstCompletionTime INTEGER

	}

    hpTatAgtDriveIndex OBJECT-TYPE
        SYNTAX  INTEGER
        ACCESS  read-only
        STATUS  mandatory
        DESCRIPTION
		    "Index number of this Drive in the table (1 to n)."
        ::= { hpTatAgtDriveEntry 1 }

    hpTatAgtDriveAdapter OBJECT-TYPE
        SYNTAX  INTEGER (0..8)
        ACCESS  read-only
        STATUS  mandatory
        DESCRIPTION
		    "Adapter (SCSI port) number that this drive is connected to."
        ::= { hpTatAgtDriveEntry 2 }

    hpTatAgtDriveChannel OBJECT-TYPE
        SYNTAX  INTEGER
        ACCESS  read-only
        STATUS  mandatory
        DESCRIPTION
		    "Channel number on the adapter that this drive is connected to."
        ::= { hpTatAgtDriveEntry 3 }

    hpTatAgtDriveTargetID OBJECT-TYPE
        SYNTAX  INTEGER
        ACCESS  read-write
        STATUS  mandatory
        DESCRIPTION
		    "This drive's SCSI target ID."
        ::= { hpTatAgtDriveEntry 4 }

    hpTatAgtDriverVersion OBJECT-TYPE
        SYNTAX  DisplayString
        ACCESS  read-only
        STATUS  mandatory
        DESCRIPTION
		    "Manufacturer's product revision string for the drive."
        ::= { hpTatAgtDriveEntry 5 }

    hpTatAgtDriveProdRev OBJECT-TYPE
        SYNTAX  DisplayString
        ACCESS  read-only
        STATUS  mandatory
        DESCRIPTION
		    "Manufacturer's product revision string for the drive."
        ::= { hpTatAgtDriveEntry 6 }

    hpTatAgtDriveDateCode OBJECT-TYPE
        SYNTAX  DisplayString
        ACCESS  read-only
        STATUS  mandatory
        DESCRIPTION
		    "Manufacturer's drive date code (Seagate drives)."
        ::= { hpTatAgtDriveEntry 7 }

    hpTatAgtDriveSerialNumber OBJECT-TYPE
        SYNTAX  DisplayString
        ACCESS  read-only
        STATUS  mandatory
        DESCRIPTION
		    "Manufacturer's Drive serial number"
        ::= { hpTatAgtDriveEntry 8 }

    hpTatAgtDriveHPProductID OBJECT-TYPE
        SYNTAX  DisplayString
        ACCESS  read-only
        STATUS  mandatory
        DESCRIPTION
		    "HP's drive product identifier"
        ::= { hpTatAgtDriveEntry 9 }

    hpTatAgtDriveLetters OBJECT-TYPE
        SYNTAX  INTEGER
        ACCESS  read-only
        STATUS  mandatory
        DESCRIPTION
		    "OS drive letters assigned to volumes on the drive."
        ::= { hpTatAgtDriveEntry 10 }

    hpTatAgtDriveRaidLevel OBJECT-TYPE
        SYNTAX  INTEGER
        ACCESS  read-only
        STATUS  mandatory
        DESCRIPTION
		    "RAID level if appicable."
        ::= { hpTatAgtDriveEntry 11 }

    hpTatAgtDriveWasTattooed OBJECT-TYPE
        SYNTAX  INTEGER
        ACCESS  read-write
		STATUS  mandatory
        DESCRIPTION
		    "Whether the drive was ever located by TopTools before."
        ::= { hpTatAgtDriveEntry 12 }

 hpTatAgtDriveDstAvail OBJECT-TYPE
        SYNTAX  INTEGER
        ACCESS  read-only
		STATUS  mandatory
        DESCRIPTION
		    "Is the DST (page 10h) supported."
        ::= { hpTatAgtDriveEntry 13 }

 hpTatAgtDriveDstPercent OBJECT-TYPE
        SYNTAX  INTEGER
        ACCESS  read-only
		STATUS  mandatory
        DESCRIPTION
		    "The percentage of DST progress"
        ::= { hpTatAgtDriveEntry 14 }

 hpTatAgtDriveDstStart OBJECT-TYPE
        SYNTAX  INTEGER
        ACCESS  read-write
		STATUS  mandatory
        DESCRIPTION
		    "Start or abort DST."
        ::= { hpTatAgtDriveEntry 15 }

 hpTatAgtDriveDstResults OBJECT-TYPE
        SYNTAX  INTEGER
        ACCESS  read-only
		STATUS  mandatory
        DESCRIPTION
		    "DST result"
        ::= { hpTatAgtDriveEntry 16 }

hpTatAgtDriveDstCompletionTime OBJECT-TYPE
        SYNTAX  INTEGER
        ACCESS  read-only
		STATUS  mandatory
        DESCRIPTION
		    "Estimation for extended test time in seconds."
        ::= { hpTatAgtDriveEntry 17 }
hpTatAgtDriveDstStartTime OBJECT-TYPE
        SYNTAX  DisplayString
        ACCESS  read-only
		STATUS  mandatory
        DESCRIPTION
		    "The last time DST starts."
        ::= { hpTatAgtDriveEntry 18 }
hpTatAgtDriveDstEndTime OBJECT-TYPE
        SYNTAX  DisplayString
        ACCESS  read-only
		STATUS  mandatory
        DESCRIPTION
		    "The last time DST ends"
        ::= { hpTatAgtDriveEntry 19 }



-- ****************************************************************************
--   HP Tattoo Agent MIB Refresh Drive Table Information
--   ===================================================
--
-- hp   (1.3.6.1.4.1.11)
--   nm   (1.3.6.1.4.1.11.2)
--     hpnsa  (1.3.6.1.4.1.11.2.23)
--       hpTatAgt (1.3.6.1.4.1.11.2.23.32)
--		   hpTatAgt Refresh Drive Table Group (1.3.6.1.4.1.11.2.23.32.4)
--		  hpTatAgt Refresh Group (1.3.6.1.4.1.11.2.23.32.4)
--			  hpTatAgtRefreshDriveTbl (1.3.6.1.4.1.11.2.23.32.4.1)
--			  hpTatAgtRefreshStatus (1.3.6.1.4.1.11.2.23.32.4.2)
-- Implementation of the MibRev group is mandatory for all HPNSA Agents
-- supporting the HP Tattoo Agent MIB.
-- ****************************************************************************
--		  hpTatAgt Refresh Group (1.3.6.1.4.1.11.2.23.32.4)
--			  hpTatAgtRefreshDriveTbl (1.3.6.1.4.1.11.2.23.32.4.1)
--			  hpTatAgtRefreshStatus (1.3.6.1.4.1.11.2.23.32.4.2)
    hpTatAgtnRefreshDriveTbl OBJECT-TYPE
        SYNTAX  INTEGER
        ACCESS  read-write
        STATUS  mandatory
        DESCRIPTION
		    "Set to regeneration the Drive table."
        ::= { hpTatAgtRefreshDrvTbl 1 }

   hpTatAgtnRefreshStatus OBJECT-TYPE
        SYNTAX  INTEGER
        ACCESS  read-only
        STATUS  mandatory
        DESCRIPTION
		    "The status of drive table regeneration"
        ::= { hpTatAgtRefreshDrvTbl 2 }


-- ****************************************************************************
--   HP Tattoo Agent MIB Overall Status Severity
--   ===================================================
--
-- hp											(1.3.6.1.4.1.11)
--   nm											(1.3.6.1.4.1.11.2)
--     hpnsa									(1.3.6.1.4.1.11.2.23)
--       hpTatAgt								(1.3.6.1.4.1.11.2.23.32)
--		  hpTatAgtStatusSev Group				(1.3.6.1.4.1.11.2.23.32.5)
--			  hpTatAgtOverallStatusSeverity		(1.3.6.1.4.1.11.2.23.32.5.1)
-- ****************************************************************************

    hpTatAgtOverallStatusSeverity OBJECT-TYPE
        SYNTAX  INTEGER
        ACCESS  read-write
        STATUS  mandatory
        DESCRIPTION
		    "Overall status severity."
        ::= { hpTatAgtStatusSev 1 }
END
