HP-ICF-RPVST-MIB DEFINITIONS ::= BEGIN
IMPORTS
            MODULE-IDENTITY, OBJECT-TYPE, TimeTicks, Counter32,
            Integer32 , NOTIFICATION-TYPE
                 FROM SNMPv2-SMI
            DateAndTime, DisplayString FROM  SNMPv2-TC
            MODULE-COMPLIANCE , OBJECT-GROUP, NOTIFICATION-GROUP
                 FROM SNMPv2-CONF
            VlanIndex
            FROM Q-BRIDGE-MIB
            hpSwitch
            FROM  HP-ICF-OID
            BridgeId
            FROM BRIDGE-MIB
            TruthValue,MacAddress,TEXTUAL-CONVENTION
               FROM  SNMPv2-TC
            StpPortRole
            FROM HP-ICF-TC;

    hpicfRpvstMIB MODULE-IDENTITY
            LAST-UPDATED "201708080000Z"
            ORGANIZATION " HP Networking"
            CONTACT-INFO "Hewlett-Packard Company
                          8000 Foothills Blvd.
                          Roseville, CA 95747"
            DESCRIPTION
                "The MIB module Rapid Per VLAN Spanning Tree(RPVST)."

            REVISION "201708080000Z"   -- August 08, 2017
            DESCRIPTION
            "Added object hpicfRpvstPortIeeeRstBpdu.
            Deprecated compliance hpicfRpvstCompliance1.
            Added compliance hpicfRpvstCompliance3.
            Deprecated group hpicfRpvstPortGroup.
            Added hpicfRpvstPortGroup1."

            REVISION "201303210028Z"
            DESCRIPTION
            "Added objects
             	hpicfRpvstLogPortStateTransitions,
       		hpicfRpvstNewPortRole,
       		hpicfRpvstOldPortRole,
       		hpicfRpvstPathCostMode,
       		hpicfRpvstPortRoleChangeCurrentPortRole,
       		hpicfRpvstPortRoleChangeEntry,
       		hpicfRpvstPortRoleChangeIndex,
       		hpicfRpvstPortRoleChangePreviousPortRole,
       		hpicfRpvstPortRoleChangeTable,
       		hpicfRpvstPortRoleChangeTime,
       		hpicfRpvstPortVlanInconsistencyReason,
       		hpicfRpvstSendTopoChangeCtrl,
       		hpicfRpvstTopoChangeTime,
       		hpicfRpvstTopologyChange,
       		hpicfRpvstVlanTopologyChangeRxEntry,
       		hpicfRpvstVlanTopologyChangeRxIndex,
       		hpicfRpvstVlanTopologyChangeRxMacAddress,
       		hpicfRpvstVlanTopologyChangeRxPortId,
       		hpicfRpvstVlanTopologyChangeRxTable,
       		hpicfRpvstVlanTopologyChangeRxTime,
       		hpicfRpvstVlanTopologyChangeTxCurrentPortRole,
       		hpicfRpvstVlanTopologyChangeTxEntry,
       		hpicfRpvstVlanTopologyChangeTxIndex,
       		hpicfRpvstVlanTopologyChangeTxPortId,
       		hpicfRpvstVlanTopologyChangeTxPreviousPortRole,
       		hpicfRpvstVlanTopologyChangeTxTable,
       		hpicfRpvstVlanTopologyChangeTxTime.
             Added groups
                       hpicfRpvstPvst1,
                       hpicfRpvstNotificationGroupPvst1,
                       hpicfRpvstNotificationObjectGrpPvst1,
                       hpicfRpvstTopologyRxGroup,
                       hpicfRpvstTopologyTxGroup,
                       hpicfRpvstPortRoleChangeGroup.
             Added complaince hpicfRpvstCompliance2. "

             REVISION "201108080000Z"
             DESCRIPTION
                 "Initial version of this MIB module"
             ::= { hpSwitch 88 }

    PointToPoint::= TEXTUAL-CONVENTION
         STATUS      current
          DESCRIPTION "
                forceTrue: This value indicates that the
                administrator requires the MAC to be treated as
                if it is connected to a point-to-point LAN segment,
                regardless of any indications to the contrary that
                are generated by the MAC entity.

                forceFalse: This value indicates that the
                administrator requires the MAC to be treated as
                if it is connected to a non-point-to-point LAN
                segment, regardless of any indications to the
                contrary that are generated by the MAC entity.


                auto: This value indicates that the administrator
                requires the point-to-point status of the MAC to be
                determined in accordance with the specific MAC
                procedures defined in 6.5."
       SYNTAX      INTEGER {
                        forceTrue(1),
                        forceFalse(2),
                        auto(3)
                    }


  -- Top-level structure of MIB
   hpicfRpvstNotifications  OBJECT IDENTIFIER ::= { hpicfRpvstMIB 0}
   hpicfRpvstObjects        OBJECT IDENTIFIER ::= { hpicfRpvstMIB 1}
   hpicfRpvstConformance    OBJECT IDENTIFIER ::= { hpicfRpvstMIB 2}


    -- RPVST General Variables

    -- These parameters apply globally to the RPVST

  hpicfRpvstGeneralGroup OBJECT IDENTIFIER ::= {hpicfRpvstObjects 1}

    hpicfRpvstResetCounters OBJECT-TYPE
            SYNTAX          TruthValue
            MAX-ACCESS      read-write
            STATUS          current
            DESCRIPTION  " Setting this object to true(1) will reset
                           all the RPVST counters. Setting this to
                           false(2) is no operation."
            DEFVAL          { false }
            ::= { hpicfRpvstGeneralGroup 1 }


     hpicfRpvstExtendedSystemID OBJECT-TYPE
            SYNTAX          TruthValue
            MAX-ACCESS      read-write
            STATUS          current
            DESCRIPTION  " Indicates whether Extended System ID feature
                           is enabled or not."
            DEFVAL          { true }
            ::= { hpicfRpvstGeneralGroup 2 }

    hpicfRpvstIgnorePVIDInconsistency OBJECT-TYPE
            SYNTAX          TruthValue
            MAX-ACCESS      read-write
            STATUS          current
            DESCRIPTION   "Setting this object to True(1) will  enable RPVST
                           to run  on mismatched PVID links.Once set it will
                           apply to all RPVST instances"

            DEFVAL          { false }
            ::= { hpicfRpvstGeneralGroup 3 }



          hpicfRpvstPathCostMode  OBJECT-TYPE
          SYNTAX      INTEGER {
                             pathCost8021d(1),
                             pathCost8021t(2),
                             proprietary(3)
                         }
            MAX-ACCESS   read-write
            STATUS       current

           DESCRIPTION  "hpicfRpvstPathCostMode controls which pathcost mode to use.
                          A device can function in one of the 2 modes defined below.
                          pathCost8021d  - The device calculates the default path cost for
                          ports based on IEEE 802.1d.

                          pathCost8021t  - The device calculates the default path cost for
                          ports based on IEEE 802.1t.

                          proprietary  -The device calculates the default path cost for
                          ports based on the proprietary standard.

                          Link Speed Vs Pathcost Table
                          ----------------------------------------------------------
                          |Link speed| Pathcost in | Pathcost in | Pathcost in     |
                          |          | IEEE802.1d  | IEEE 802.1t | private standard|
                          ----------------------------------------------------------
                          | 0	     | 65535       | 200,000,000 | 200,000         |
                          ----------------------------------------------------------
                          | 10 Mbps  | 100         | 2,000,000   | 2,000           |
                          ----------------------------------------------------------
                          | 100 Mbp  | 19          | 200,000     | 200             |
                          ----------------------------------------------------------
                          | 1000 Mbp | 4           | 20,000      | 20              |
                          ----------------------------------------------------------
                          | 10 Gbps  | 2           | 2,000       | 2               |
                          ----------------------------------------------------------
                          "

           DEFVAL     { 1 }
                ::= { hpicfRpvstGeneralGroup 5 }

     hpicfRpvstVlanTable OBJECT-TYPE
            SYNTAX          SEQUENCE OF HpicfRpvstVlanEntry
            MAX-ACCESS      not-accessible
            STATUS          current
            DESCRIPTION
                "Information describing the RPVST configuration
                 and statistics of the VLANs."
            ::= { hpicfRpvstObjects 2 }

    hpicfRpvstVlanEntry OBJECT-TYPE
            SYNTAX          HpicfRpvstVlanEntry
            MAX-ACCESS      not-accessible
            STATUS          current
            DESCRIPTION
                "Information describing the RPVST configuration
                 and statistics of each of the VLANs."
            INDEX           { hpicfRpvstVlanId }
            ::= { hpicfRpvstVlanTable 1 }

    HpicfRpvstVlanEntry ::= SEQUENCE {

            hpicfRpvstVlanId
                    VlanIndex,
            hpicfRpvstVlanHelloTime
                    Integer32,
            hpicfRpvstVlanForwardDelay
                    Integer32,
            hpicfRpvstVlanMaxAge
                    Integer32,
            hpicfRpvstVlanPriority
                    Integer32,
            hpicfRpvstVlanRoot
                    INTEGER,
            hpicfRpvstVlanRpvstStatus
                    INTEGER,
            hpicfRpvstVlanResetCounters
                    TruthValue,
            hpicfRpvstVlanOperHelloTime
                    Integer32,
            hpicfRpvstVlanRootPriority
                    Integer32,
            hpicfRpvstVlanRootPort
                    Integer32,
            hpicfRpvstVlanRootPathCost
                    Integer32,
            hpicfRpvstVlanRootMacAddress
                    MacAddress,
            hpicfRpvstVlanRootChangeCounter
                    Counter32,
            hpicfRpvstVlanTimeSinceLastTopoChange
                     TimeTicks,
            hpicfVlanTopoChangeCount
                     Counter32,
            hpicfRpvstSendTopoChangeCtrl
                     TruthValue,
            hpicfRpvstLogPortStateTransitions
                     TruthValue

    }

    hpicfRpvstVlanId OBJECT-TYPE
            SYNTAX          VlanIndex
            MAX-ACCESS      not-accessible
            STATUS          current
            DESCRIPTION
                "A VLAN ID to uniquely identifying the entries.
                "
            ::= { hpicfRpvstVlanEntry 1 }


    hpicfRpvstVlanHelloTime OBJECT-TYPE
            SYNTAX          Integer32 (1..10)
            UNITS           "seconds"
            MAX-ACCESS      read-write
            STATUS          current
            DESCRIPTION "   The amount of time between the
                transmission of configuration BPDUs by this
                node on any port in this VLAN when it is root of
                the spanning tree, or trying to
                become so for this VLAN."
            DEFVAL            { 2 }
           ::= { hpicfRpvstVlanEntry 2 }


    hpicfRpvstVlanForwardDelay OBJECT-TYPE
            SYNTAX          Integer32 (4..30)
            UNITS           "seconds"
            MAX-ACCESS      read-write

            STATUS          current
            DESCRIPTION "   The amount of time between transitioning
               from listening to learning and learning to forwarding
               by this node on any port when it is acting as a
               root for this VLAN."
            DEFVAL           { 15 }
           ::= { hpicfRpvstVlanEntry 3 }

    hpicfRpvstVlanMaxAge OBJECT-TYPE
            SYNTAX          Integer32 (6..40)
            UNITS           "seconds"
            MAX-ACCESS      read-write
            STATUS          current
            DESCRIPTION "   The maximum age of RPVST information
               learned from the network on any port before it is
               discarded."
            DEFVAL          { 20 }
            ::= { hpicfRpvstVlanEntry 4 }

    hpicfRpvstVlanPriority OBJECT-TYPE
            SYNTAX          Integer32 (0..65535)
            MAX-ACCESS      read-write
            STATUS          current
            DESCRIPTION "The value of the write-able portion of the
                  Bridge ID (i.e., the first two octets of the
                  (8 octet long) Bridge ID).
                  The other (last) 6 octets of the Bridge ID are
                  given by the value dot1dBridgeBaseAddress."
            DEFVAL          { 32768 }
            ::= { hpicfRpvstVlanEntry 5 }

    hpicfRpvstVlanRoot OBJECT-TYPE
            SYNTAX          INTEGER{
                             none(0),
                             primary(1),
                             secondary(2)
                            }
            MAX-ACCESS      read-write
            STATUS          current
            DESCRIPTION " To explicitly configure this switch to be
                    primary/secondary root for this VLAN."
            DEFVAL           { none }
            ::= { hpicfRpvstVlanEntry 6 }


   hpicfRpvstVlanRpvstStatus OBJECT-TYPE
            SYNTAX          INTEGER{
                             enabled(1),
                             disabled(2)
                            }
            MAX-ACCESS      read-write
            STATUS          current
            DESCRIPTION "   To enable/disable RPVST on the VLAN."
            DEFVAL          { enabled }
           ::= { hpicfRpvstVlanEntry 7 }

   hpicfRpvstVlanResetCounters OBJECT-TYPE
            SYNTAX          TruthValue
            MAX-ACCESS      read-write
            STATUS          current
            DESCRIPTION  " Setting this object to true(1) will
                           reset the RPVST counters for this VLAN."
            DEFVAL          { false }
            ::= { hpicfRpvstVlanEntry 8 }

   hpicfRpvstVlanOperHelloTime OBJECT-TYPE
            SYNTAX          Integer32 (1..10)
            UNITS           "seconds"
            MAX-ACCESS      read-only
            STATUS          current
            DESCRIPTION  "   The amount of time between the
                      transmission of  BPDUs by this node on
                      any port in this VLAN when it is root of
                      the spanning tree, or trying to become so
                      for this VLAN. This is the actual value
                      that this bridge is using."

            ::= { hpicfRpvstVlanEntry 9 }

    hpicfRpvstVlanRootPriority OBJECT-TYPE
            SYNTAX          Integer32 (0..65535)
            MAX-ACCESS      read-only
            STATUS          current
            DESCRIPTION  "The priority of root bridge in this VLAN."
            DEFVAL          { 32768 }
            ::= { hpicfRpvstVlanEntry 10 }

     hpicfRpvstVlanRootPort OBJECT-TYPE
            SYNTAX          Integer32 (1..65535)
            MAX-ACCESS      read-only
            STATUS          current
            DESCRIPTION  "The  root port for this VLAN."

            ::= { hpicfRpvstVlanEntry 11 }


    hpicfRpvstVlanRootPathCost OBJECT-TYPE
            SYNTAX          Integer32 ( 1..200000000)
            MAX-ACCESS      read-only
            STATUS          current
            DESCRIPTION  "The path cost to the Root from this
                     bridge in this VLAN."

            ::= { hpicfRpvstVlanEntry 12 }



    hpicfRpvstVlanRootMacAddress OBJECT-TYPE
            SYNTAX          MacAddress
            MAX-ACCESS      read-only
            STATUS          current
            DESCRIPTION  "MAC address of the Root in this VLAN."

            ::= { hpicfRpvstVlanEntry 13 }


    hpicfRpvstVlanRootChangeCounter OBJECT-TYPE
            SYNTAX          Counter32
            MAX-ACCESS      read-only
            STATUS          current
            DESCRIPTION  "The number of times the root has changed for this VLAN."
            ::= { hpicfRpvstVlanEntry 14 }

     hpicfRpvstVlanTimeSinceLastTopoChange OBJECT-TYPE
        SYNTAX      TimeTicks
        MAX-ACCESS  read-only
        STATUS      current
        DESCRIPTION "The time (in hundredths of a second) since the
                     last time a topology change was detected by the
                     bridge entity for this VLAN."
        ::= { hpicfRpvstVlanEntry 15 }

     hpicfVlanTopoChangeCount OBJECT-TYPE
        SYNTAX      Counter32
        MAX-ACCESS  read-only
        STATUS      current
        DESCRIPTION "The total number of topology changes detected by
                     this bridge in this VLAN since the management
                     entity was last reset or initialized."
        ::= { hpicfRpvstVlanEntry 16 }


       hpicfRpvstSendTopoChangeCtrl     OBJECT-TYPE
        SYNTAX      TruthValue
        MAX-ACCESS  read-write
        STATUS      current
        DESCRIPTION "Setting this object to true(1) will
                     enable sending of SNMP notifications
                     for all topology change events on this VLAN."
        DEFVAL      { false }
            ::= { hpicfRpvstVlanEntry 17 }

     hpicfRpvstLogPortStateTransitions   OBJECT-TYPE
        SYNTAX      TruthValue
        MAX-ACCESS  read-write
        STATUS      current
        DESCRIPTION "Setting this object to true(1) will
                     enable event logging of PVST port state transitions
                     for this VLAN."
        DEFVAL      { false }
            ::= { hpicfRpvstVlanEntry 18 }



   -- Per Port Configuration

hpicfRpvstPortTable OBJECT-TYPE
            SYNTAX          SEQUENCE OF HpicfRpvstPortEntry
            MAX-ACCESS      not-accessible
            STATUS          current
            DESCRIPTION
                "Information describing the RPVST specific
                 configuration and statistics of the ports."
            ::= { hpicfRpvstObjects 3 }

  hpicfRpvstPortEntry OBJECT-TYPE
            SYNTAX          HpicfRpvstPortEntry
            MAX-ACCESS      not-accessible
            STATUS          current
            DESCRIPTION
                "Information describing the RPVST specific
                 configuration and statistics of the ports."
            INDEX           { hpicfRpvstPortIndex }
            ::= { hpicfRpvstPortTable 1 }

    HpicfRpvstPortEntry ::= SEQUENCE {
            hpicfRpvstPortIndex                Integer32,
            hpicfRpvstPortAdminEdge            TruthValue,
            hpicfRpvstPortAdminPointToPoint    PointToPoint,
            hpicfRpvstPortAutoEdge             TruthValue,
            hpicfRpvstPortBpduFiltering        TruthValue,
            hpicfRpvstPortRestrictedTcn        TruthValue,
            hpicfRpvstPortRootGuard            TruthValue,
            hpicfRpvstPortLoopGuard            TruthValue,
            hpicfRpvstPortBpduProtection       TruthValue,
            hpicfRpvstPortIeeeRstBpdu          TruthValue
          }
    hpicfRpvstPortIndex OBJECT-TYPE
            SYNTAX         Integer32 ( 1..65535)
            MAX-ACCESS     not-accessible
            STATUS          current
            DESCRIPTION "  The port number "
            ::= { hpicfRpvstPortEntry 1 }

    hpicfRpvstPortAdminEdge OBJECT-TYPE
            SYNTAX          TruthValue
            MAX-ACCESS      read-write
            STATUS          current
            DESCRIPTION  "The administrative value of the Edge Port
                 parameter. A value of true(1) indicates that this
                 port should be assumed as an edge-port, and a
                 value of false(2) indicates that this port
                 should be assumed as a non-edge-port.
                 Note that even when this object's value is true(1),
                 the hpicfRpvstOperEdgePort can be false(2) if a
                 BPDU has been received."
           ::= { hpicfRpvstPortEntry 2 }

  hpicfRpvstPortAdminPointToPoint OBJECT-TYPE
          SYNTAX      PointToPoint
          MAX-ACCESS  read-write
          STATUS      current
          DESCRIPTION "Refer the PointToPoint textual-convention."
          REFERENCE
             "IEEE P802.1w; IEEE P802.1t"
          ::= { hpicfRpvstPortEntry 3 }

    hpicfRpvstPortAutoEdge OBJECT-TYPE
            SYNTAX          TruthValue
            MAX-ACCESS      read-write
            STATUS          current

            DESCRIPTION  "It is used by the Bridge
                    detection state machine for the automatic
                    identification of edge ports. "
            REFERENCE
             "IEEE 802.1D-2004"
            ::= { hpicfRpvstPortEntry 4 }

    hpicfRpvstPortBpduFiltering OBJECT-TYPE
            SYNTAX          TruthValue
            MAX-ACCESS      read-write
            STATUS          current
            DESCRIPTION "This value indicates whether or not
                   BPDUs need to be filtered on this port.
                   If the value is true(1) the received BPDUs will
                   be dropped and no BPDUs will be transmitted on
                   the port. If the value is false (2)
                   the BPDUs will be processed as usual. "
            REFERENCE
             "IEEE P802.1w"
            ::= { hpicfRpvstPortEntry 5 }

    hpicfRpvstPortRestrictedTcn OBJECT-TYPE
            SYNTAX          TruthValue
            MAX-ACCESS      read-write
            STATUS          current
            DESCRIPTION " This value indicates whether or not to
                propagate topology changes to other ports.
                true(1) causes the port not to propagate topology
                changes to other ports."
            REFERENCE "IEEE 802.1Q-REV/5.0 (13.25.15)"
            ::= { hpicfRpvstPortEntry 6 }



    hpicfRpvstPortRootGuard OBJECT-TYPE
            SYNTAX          TruthValue
            MAX-ACCESS      read-write
            STATUS          current
            DESCRIPTION " Setting this object to true(1) forces port
                  to not to be selected as root port even if
                  this port has best spanning-tree. "
            DEFVAL          { false }
            ::= { hpicfRpvstPortEntry 7 }

    hpicfRpvstPortLoopGuard OBJECT-TYPE
            SYNTAX          TruthValue
            MAX-ACCESS      read-write
            STATUS          current
            DESCRIPTION " Setting this object to true(1) causes the
                     forwarding port to move to the blocking state
                     and prevent the blocking port to move to
                     forwarding state when no BPDUs are received,
                     instead goes to loop inconsistent state."
            DEFVAL         { false }
            ::= { hpicfRpvstPortEntry 8 }

    hpicfRpvstPortBpduProtection OBJECT-TYPE
            SYNTAX          TruthValue
            MAX-ACCESS      read-write
            STATUS          current
            DESCRIPTION " Setting this true (1) indicates that no
                BPDUs are expected to be received on this port.
                At the reception of BPDUs the BPDU protection
                mechanism will disable this port and port will
                transition into bpduError state."
            DEFVAL         { false }
            ::= { hpicfRpvstPortEntry 9 }

    hpicfRpvstPortIeeeRstBpdu OBJECT-TYPE
            SYNTAX          TruthValue
            MAX-ACCESS      read-write
            STATUS          current
            DESCRIPTION
               "The hpicfRpvstPortIeeeRstBpdu controls, on a per
                port basis, whether or not IEEE RST BPDUs will be
                transmitted and received on VLANs that the port is
                an untagged member of. The value true(1) means that
                the port will allow transmission and reception of
                IEEE RST BPDUs on ports untagged to a VLAN while
                false(2) means it will not."
            DEFVAL         { false }
            ::= { hpicfRpvstPortEntry 10 }
 hpicfRpvstPortVlanTable OBJECT-TYPE
            SYNTAX          SEQUENCE OF HpicfRpvstPortVlanEntry
            MAX-ACCESS      not-accessible
            STATUS          current
            DESCRIPTION
                "Information describing the RPVST configuration
                 and statistics of the ports in the given VLAN."
            ::= { hpicfRpvstObjects 4 }

    hpicfRpvstPortVlanEntry OBJECT-TYPE
            SYNTAX          HpicfRpvstPortVlanEntry
            MAX-ACCESS      not-accessible
            STATUS          current
            DESCRIPTION
                "Information describing the RPVST configuration
                 and statistics of the ports in the given VLAN."
            INDEX           { hpicfRpvstVlanId,
                              hpicfRpvstPortIndex }
            ::= { hpicfRpvstPortVlanTable 1 }

    HpicfRpvstPortVlanEntry ::= SEQUENCE {
            hpicfRpvstPortVlanPathCost
                    Integer32,
            hpicfRpvstPortVlanPriority
                    Integer32,
            hpicfRpvstPortVlanResetCounters
                    TruthValue,
            hpicfRpvstPortVlanRole
                    StpPortRole,
            hpicfRpvstPortVlanState
                    INTEGER,
            hpicfRpvstPortVlanDesigBridge
                    MacAddress,
            hpicfRpvstPortVlanOperPointToPoint
                    TruthValue,
            hpicfRpvstPortVlanOperEdge
                    TruthValue,
            hpicfRpvstPortVlanInconsistencyReason
                    INTEGER

    }

    hpicfRpvstPortVlanPathCost OBJECT-TYPE
            SYNTAX         Integer32 ( 0..200000000)
            MAX-ACCESS      read-write
            STATUS          current
            DESCRIPTION " The contribution of this port to the
                          path cost of paths towards the root
                          which include this port.
                          auto(0)             "
            DEFVAL         { 0 }
            ::= { hpicfRpvstPortVlanEntry 1 }

    hpicfRpvstPortVlanPriority OBJECT-TYPE

            SYNTAX          Integer32 (0..255)
            MAX-ACCESS      read-write
            STATUS          current
            DESCRIPTION  "The value of the port priority field that
                is contained in the first (in network byte order)
                octet of the (2 octet long) Port ID.  "
            DEFVAL         { 128 }
            ::= { hpicfRpvstPortVlanEntry 2 }

   hpicfRpvstPortVlanResetCounters OBJECT-TYPE
            SYNTAX          TruthValue
            MAX-ACCESS      read-write
            STATUS          current
            DESCRIPTION  " Setting this object to true(1) will
                reset the RPVST counters for this port-vlan pair.
                Get on this object will always return false(2)"
            DEFVAL         { false }
            ::= { hpicfRpvstPortVlanEntry 3 }

   hpicfRpvstPortVlanRole OBJECT-TYPE
            SYNTAX         StpPortRole
            MAX-ACCESS     read-only
            STATUS         current
            DESCRIPTION " Role played by the port in a given VLAN."
            ::= { hpicfRpvstPortVlanEntry 4 }

   hpicfRpvstPortVlanState   OBJECT-TYPE
            SYNTAX          INTEGER
                            {
                        disabled(1),
                        blocking(2),
                        listening(3),
                        learning(4),
                        forwarding(5),
                        broken(6),
                        bpduError(7),
                        loopInconsistent(8),
                        pvidInconsistent(9),
                        rootGuard(10)
                    }
            MAX-ACCESS      read-only
            STATUS          current
            DESCRIPTION "The port's current state.
                         This state controls what action a port
                         takes on reception of a frame."
            ::= { hpicfRpvstPortVlanEntry 5 }

    hpicfRpvstPortVlanDesigBridge  OBJECT-TYPE
            SYNTAX          MacAddress
            MAX-ACCESS      read-only
            STATUS          current
            DESCRIPTION  " The Bridge Identifier of the bridge that
                     this port considers to be the Designated
                     Bridge for this port's segment."
            REFERENCE   "12.8.2.1.3"
                        ::= { hpicfRpvstPortVlanEntry 6 }
    hpicfRpvstPortVlanOperPointToPoint OBJECT-TYPE

          SYNTAX    TruthValue
          MAX-ACCESS  read-only
          STATUS      current
          DESCRIPTION "
             true : This value indicates that the MAC is
                    connected to a point-to-point LAN segment;
                    i.e., there is at most one other system
                    attached to the LAN segment.

             false: This value indicates that the MAC is connected
                    to a non-point-to-point LAN segment; i.e.,
                    there can be more than one other system
                    attached to the LAN segment."
         ::= {  hpicfRpvstPortVlanEntry 7 }

    hpicfRpvstPortVlanOperEdge OBJECT-TYPE
            SYNTAX          TruthValue
            MAX-ACCESS      read-only
            STATUS          current
            DESCRIPTION  "The operational status of the edge port
                 parameter. A value of true(1) indicates that this
                 port should be assumed as an edge-port, and a
                 value of false(2) indicates that this port should
                 be assumed as a non-edge-port.
                 "
           ::= {  hpicfRpvstPortVlanEntry 8 }

    hpicfRpvstPortVlanInconsistencyReason OBJECT-TYPE
           SYNTAX          INTEGER{
                             rootProtected(1),
                             loopProtected(2),
                             inconsistentPvidprotected(3)
                            }
           MAX-ACCESS      read-only
           STATUS          current
           DESCRIPTION     "The reason for which port is blocked by spanning tree
                            protection function."
             ::= { hpicfRpvstPortVlanEntry 9 }

    -- Rx Counter Table

      hpicfRpvstPortVlanRxCountersTable OBJECT-TYPE
          SYNTAX       SEQUENCE OF HpicfRpvstPortVlanRxCountersEntry
          MAX-ACCESS      not-accessible
          STATUS          current
          DESCRIPTION     "A table which contains information about
                            each  port-vlan pair."
            ::= { hpicfRpvstObjects 5 }

      hpicfRpvstPortVlanRxCountersEntry OBJECT-TYPE
          SYNTAX        HpicfRpvstPortVlanRxCountersEntry
          MAX-ACCESS    not-accessible
          STATUS        current
          DESCRIPTION   "Statistics for each port-vlan pair."
            INDEX       { hpicfRpvstVlanId,
                          hpicfRpvstPortIndex }
            ::= { hpicfRpvstPortVlanRxCountersTable 1 }

    HpicfRpvstPortVlanRxCountersEntry  ::= SEQUENCE {
         hpicfRpvstPortVlanRpvstBpduRx                 Counter32,
         hpicfRpvstPortVlanRpvstBpduRxLastUpdated      DateAndTime,
         hpicfRpvstPortVlanRstBpduRx                   Counter32,
         hpicfRpvstPortVlanRstBpduRxLastUpdated        DateAndTime,
         hpicfRpvstPortVlanConfigBpduRx                Counter32,
         hpicfRpvstPortVlanConfigBpduRxLastUpdated     DateAndTime,
         hpicfRpvstPortVlanTcnBpduRx                  Counter32,
         hpicfRpvstPortVlanTcnBpduRxLastUpdated        DateAndTime,
         hpicfRpvstPortVlanTcDetectCount               Counter32,
         hpicfRpvstPortVlanTcDetectCountLastUpdated    DateAndTime,
         hpicfRpvstPortVlanTcFlagRx                    Counter32,
         hpicfRpvstPortVlanTcFlagRxLastUpdated         DateAndTime,
         hpicfRpvstPortVlanTcAckFlagRx                 Counter32,
         hpicfRpvstPortVlanTcAckFlagRxLastUpdated      DateAndTime,
         hpicfRpvstPortVlanStarvedBpduCount            Counter32,
         hpicfRpvstPortVlanStarvedBpduCountLastUpdated DateAndTime,
         hpicfRpvstPortVlanInvalidBpduRx               Counter32,
         hpicfRpvstPortVlanInvalidBpduRxLastUpdated    DateAndTime,
         hpicfRpvstPortVlanLoopedBackBpduRx            Counter32,
         hpicfRpvstPortVlanLoopedBackBpduRxLastUpdated DateAndTime,
         hpicfRpvstPortVlanErrantBpduRxCount           Counter32,
         hpicfRpvstPortVlanErrantBpduRxCountLastUpdated DateAndTime,
         hpicfRpvstPortVlanAgedBpduRx                  Counter32,
         hpicfRpvstPortVlanAgedBpduRxLastUpdated       DateAndTime
    }

    hpicfRpvstPortVlanRpvstBpduRx OBJECT-TYPE
            SYNTAX         Counter32
            MAX-ACCESS     read-only
            STATUS         current
            DESCRIPTION    "The number of RPVST BPDUs received on
                           this port-vlan pair."
            ::= {hpicfRpvstPortVlanRxCountersEntry 1}

    hpicfRpvstPortVlanRpvstBpduRxLastUpdated OBJECT-TYPE
            SYNTAX         DateAndTime
            MAX-ACCESS     read-only
            STATUS         current
            DESCRIPTION    "Time when
                            hpicfRpvstPortVlanRpvstBpduRxCount
                            counter was last updated."
            ::= {hpicfRpvstPortVlanRxCountersEntry 2}

   hpicfRpvstPortVlanRstBpduRx OBJECT-TYPE
            SYNTAX         Counter32
            MAX-ACCESS     read-only
            STATUS         current
            DESCRIPTION    "The number of RSTP BPDUs received on
                            this port-vlan pair."
            ::= {hpicfRpvstPortVlanRxCountersEntry 3}

   hpicfRpvstPortVlanRstBpduRxLastUpdated OBJECT-TYPE
            SYNTAX         DateAndTime
            MAX-ACCESS     read-only
            STATUS         current
            DESCRIPTION    "Time when
                            hpicfRpvstPortVlanRstBpduRxCount counter
                            was last updated."
            ::= {hpicfRpvstPortVlanRxCountersEntry 4}

   hpicfRpvstPortVlanConfigBpduRx OBJECT-TYPE
            SYNTAX         Counter32
            MAX-ACCESS     read-only
            STATUS         current
            DESCRIPTION    "The number of STP config BPDUs
                            received on this port-vlan pair."
            ::= {hpicfRpvstPortVlanRxCountersEntry 5}

   hpicfRpvstPortVlanConfigBpduRxLastUpdated OBJECT-TYPE

            SYNTAX         DateAndTime
            MAX-ACCESS     read-only
            STATUS         current
            DESCRIPTION    "Time when
                        hpicfRpvstPortVlanConfigBpduRxCount counter
                        was last updated."
            ::= {hpicfRpvstPortVlanRxCountersEntry 6}


   hpicfRpvstPortVlanTcnBpduRx OBJECT-TYPE
            SYNTAX         Counter32
            MAX-ACCESS     read-only
            STATUS         current
            DESCRIPTION    "The number of Topology Change
                            Notification BPDUs received on this
                            port-vlan pair."
            ::= {hpicfRpvstPortVlanRxCountersEntry 7}

   hpicfRpvstPortVlanTcnBpduRxLastUpdated OBJECT-TYPE
            SYNTAX         DateAndTime
            MAX-ACCESS     read-only
            STATUS         current
            DESCRIPTION    "Time when
                            hpicfRpvstPortVlanTcnBpduRxCount counter
                            was last updated."
            ::= {hpicfRpvstPortVlanRxCountersEntry 8}

   hpicfRpvstPortVlanTcDetectCount OBJECT-TYPE
            SYNTAX         Counter32
            MAX-ACCESS     read-only
            STATUS         current
            DESCRIPTION    "The number of times Topology Change
                            detected on this port-vlan pair."
            ::= {hpicfRpvstPortVlanRxCountersEntry 9}

   hpicfRpvstPortVlanTcDetectCountLastUpdated OBJECT-TYPE
            SYNTAX         DateAndTime
            MAX-ACCESS     read-only
            STATUS         current
            DESCRIPTION    "Time when
                            hpicfRpvstPortVlanTcDetectCount counter
                            was last updated."
            ::= {hpicfRpvstPortVlanRxCountersEntry 10}

   hpicfRpvstPortVlanTcFlagRx OBJECT-TYPE
            SYNTAX         Counter32
            MAX-ACCESS     read-only
            STATUS         current
            DESCRIPTION    "The number of times Topology Change bit
                            was set in the BPDUs received on this
                            port-vlan pair."
            ::= {hpicfRpvstPortVlanRxCountersEntry 11}

   hpicfRpvstPortVlanTcFlagRxLastUpdated OBJECT-TYPE
            SYNTAX         DateAndTime
            MAX-ACCESS     read-only
            STATUS         current
            DESCRIPTION    "Time when
                            hpicfRpvstPortVlanTcFlagRxCount counter
                            was last updated."
            ::= {hpicfRpvstPortVlanRxCountersEntry 12}

   hpicfRpvstPortVlanTcAckFlagRx OBJECT-TYPE
            SYNTAX         Counter32
            MAX-ACCESS     read-only
            STATUS         current
            DESCRIPTION    "The number of times TC-ACK bit was set
                            in the BPDUs received on this port-vlan
                            pair."
            ::= {hpicfRpvstPortVlanRxCountersEntry 13}

   hpicfRpvstPortVlanTcAckFlagRxLastUpdated OBJECT-TYPE
            SYNTAX         DateAndTime
            MAX-ACCESS     read-only
            STATUS         current
            DESCRIPTION  "Time when
                          hpicfRpvstPortVlanTcAckFlagRxCount counter
                          was last updated."
            ::= {hpicfRpvstPortVlanRxCountersEntry 14}


   hpicfRpvstPortVlanStarvedBpduCount OBJECT-TYPE
            SYNTAX         Counter32
            MAX-ACCESS     read-only
            STATUS         current
            DESCRIPTION    "The number of times BPDU was not
                            received at scheduled time on this
                            port-vlan pair."
            ::= {hpicfRpvstPortVlanRxCountersEntry 15}

   hpicfRpvstPortVlanStarvedBpduCountLastUpdated OBJECT-TYPE
            SYNTAX         DateAndTime
            MAX-ACCESS     read-only
            STATUS         current
            DESCRIPTION    "Time when
                            hpicfRpvstPortVlanStarvedBpduRxCount
                            counter was last updated."
            ::= {hpicfRpvstPortVlanRxCountersEntry 16}

   hpicfRpvstPortVlanInvalidBpduRx OBJECT-TYPE
            SYNTAX         Counter32
            MAX-ACCESS     read-only
            STATUS         current
            DESCRIPTION    "The number of invalid BPDUs received
                            on this port-vlan pair."
            ::= {hpicfRpvstPortVlanRxCountersEntry 17}

   hpicfRpvstPortVlanInvalidBpduRxLastUpdated OBJECT-TYPE
            SYNTAX         DateAndTime
            MAX-ACCESS     read-only
            STATUS         current
            DESCRIPTION    "Time when
                            hpicfRpvstPortVlanInvalidBpduRxCount
                            counter was last updated."
            ::= {hpicfRpvstPortVlanRxCountersEntry 18}

   hpicfRpvstPortVlanLoopedBackBpduRx OBJECT-TYPE
            SYNTAX         Counter32
            MAX-ACCESS     read-only
            STATUS         current
            DESCRIPTION    "The number of times a BPDU is received
                            on the same port from where it was sent
                            on the same VLAN."
            ::= {hpicfRpvstPortVlanRxCountersEntry 19}

   hpicfRpvstPortVlanLoopedBackBpduRxLastUpdated OBJECT-TYPE
            SYNTAX         DateAndTime
            MAX-ACCESS     read-only
            STATUS         current
            DESCRIPTION    "Time when
                            hpicfRpvstPortVlanLoopedBackBpduRxCount
                            counter was last updated."
            ::= {hpicfRpvstPortVlanRxCountersEntry 20}

   hpicfRpvstPortVlanErrantBpduRxCount OBJECT-TYPE
            SYNTAX         Counter32
            MAX-ACCESS     read-only
            STATUS         current
            DESCRIPTION    "The number of BPDUs received on a
                            BPDU-filtering
                            or BPDU-protected enabled port."
            ::= {hpicfRpvstPortVlanRxCountersEntry 21}

   hpicfRpvstPortVlanErrantBpduRxCountLastUpdated OBJECT-TYPE
            SYNTAX         DateAndTime
            MAX-ACCESS     read-only
            STATUS         current
            DESCRIPTION    "Time when
                            hpicfRpvstPortVlanErrantBpduRxCount
                            counter was last updated."
            ::= {hpicfRpvstPortVlanRxCountersEntry 22}

   hpicfRpvstPortVlanAgedBpduRx OBJECT-TYPE
            SYNTAX         Counter32

            MAX-ACCESS     read-only
            STATUS         current
            DESCRIPTION    "The number of aged BPDUs received on
                            this port-vlan pair."
            ::= {hpicfRpvstPortVlanRxCountersEntry 23}

   hpicfRpvstPortVlanAgedBpduRxLastUpdated OBJECT-TYPE
            SYNTAX         DateAndTime
            MAX-ACCESS     read-only
            STATUS         current
            DESCRIPTION    "Time when
                            hpicfRpvstPortVlanAgedBpduRx
                            counter was last updated."
            ::= {hpicfRpvstPortVlanRxCountersEntry 24}

  -- Rx debug counter table
     hpicfRpvstPortVlanTxCountersTable OBJECT-TYPE
         SYNTAX   SEQUENCE OF HpicfRpvstPortVlanTxCountersEntry
         MAX-ACCESS      not-accessible
         STATUS          current
         DESCRIPTION     "A table which contains statistics for each
                          port-vlan pair."
            ::= { hpicfRpvstObjects 6 }

    hpicfRpvstPortVlanTxCountersEntry OBJECT-TYPE
            SYNTAX          HpicfRpvstPortVlanTxCountersEntry
            MAX-ACCESS      not-accessible
            STATUS          current
            DESCRIPTION     "A list of statistics for each
                             port-vlan pair."
            INDEX           { hpicfRpvstVlanId,
                              hpicfRpvstPortIndex }
            ::= { hpicfRpvstPortVlanTxCountersTable 1 }

    HpicfRpvstPortVlanTxCountersEntry  ::= SEQUENCE {
           hpicfRpvstPortVlanRpvstBpduTx                Counter32,
           hpicfRpvstPortVlanRpvstBpduTxLastUpdated     DateAndTime,
           hpicfRpvstPortVlanRstBpduTx                  Counter32,
           hpicfRpvstPortVlanRstBpduTxLastUpdated       DateAndTime,
           hpicfRpvstPortVlanConfigBpduTx               Counter32,
           hpicfRpvstPortVlanConfigBpduTxLastUpdated    DateAndTime,
           hpicfRpvstPortVlanTcnBpduTx                  Counter32,
           hpicfRpvstPortVlanTcnBpduTxLastUpdated       DateAndTime,
           hpicfRpvstPortVlanTcFlagTx                   Counter32,
           hpicfRpvstPortVlanTcFlagTxLastUpdated        DateAndTime,
           hpicfRpvstPortVlanTcAckFlagTx                Counter32,
           hpicfRpvstPortVlanTcAckFlagTxLastUpdated     DateAndTime
    }

   hpicfRpvstPortVlanRpvstBpduTx    OBJECT-TYPE
            SYNTAX         Counter32
            MAX-ACCESS     read-only
            STATUS         current
            DESCRIPTION    "The number of RPVST BPDUs sent on this
                            port-vlan pair."
            ::= {hpicfRpvstPortVlanTxCountersEntry 1}

   hpicfRpvstPortVlanRpvstBpduTxLastUpdated OBJECT-TYPE
            SYNTAX         DateAndTime
            MAX-ACCESS     read-only
            STATUS         current
            DESCRIPTION    "The time when hpicfRpvstPortVlanBpduTx
                            counter was last updated."
            ::= {hpicfRpvstPortVlanTxCountersEntry 2}

   hpicfRpvstPortVlanRstBpduTx OBJECT-TYPE
            SYNTAX         Counter32
            MAX-ACCESS     read-only
            STATUS         current
            DESCRIPTION    "The number of RSTP BPDUs sent on this
                            port-vlan pair."
            ::= {hpicfRpvstPortVlanTxCountersEntry 3}

   hpicfRpvstPortVlanRstBpduTxLastUpdated OBJECT-TYPE
            SYNTAX         DateAndTime
            MAX-ACCESS     read-only
            STATUS         current
            DESCRIPTION    "Time when hpicfRpvstPortVlanRstBpduTx
                            was last updated."
            ::= {hpicfRpvstPortVlanTxCountersEntry 4}

   hpicfRpvstPortVlanConfigBpduTx OBJECT-TYPE
            SYNTAX         Counter32
            MAX-ACCESS     read-only
            STATUS         current
            DESCRIPTION    "The number of STP config BPDUs sent on
                            this port-vlan pair."
            ::= {hpicfRpvstPortVlanTxCountersEntry 5}

   hpicfRpvstPortVlanConfigBpduTxLastUpdated OBJECT-TYPE
            SYNTAX         DateAndTime
            MAX-ACCESS     read-only
            STATUS         current
            DESCRIPTION    "Time when
                            hpicfRpvstPortVlanConfigBpduTx counter
                            was last updated."
            ::= {hpicfRpvstPortVlanTxCountersEntry 6}

   hpicfRpvstPortVlanTcnBpduTx OBJECT-TYPE
            SYNTAX         Counter32
            MAX-ACCESS     read-only
            STATUS         current
            DESCRIPTION    "The number of Topology Change
                            Notification BPDUs sent on this
                            port-vlan pair."
            ::= {hpicfRpvstPortVlanTxCountersEntry 7}

   hpicfRpvstPortVlanTcnBpduTxLastUpdated OBJECT-TYPE
            SYNTAX         DateAndTime
            MAX-ACCESS     read-only
            STATUS         current
            DESCRIPTION    "Time when hpicfRpvstPortVlanTcnBpduTx
                            counter was last updated."
            ::= {hpicfRpvstPortVlanTxCountersEntry 8}

   hpicfRpvstPortVlanTcFlagTx OBJECT-TYPE
            SYNTAX         Counter32
            MAX-ACCESS     read-only
            STATUS         current
            DESCRIPTION    "The number of times Topology Change
                            bit was set in BPDUs sent on this
                            port-vlan pair."
            ::= {hpicfRpvstPortVlanTxCountersEntry 9}

   hpicfRpvstPortVlanTcFlagTxLastUpdated OBJECT-TYPE
            SYNTAX         DateAndTime
            MAX-ACCESS     read-only
            STATUS         current
            DESCRIPTION    "Time when hpicfRpvstPortVlanTcFlagTx
                            counter was last updated."
            ::= {hpicfRpvstPortVlanTxCountersEntry 10}

   hpicfRpvstPortVlanTcAckFlagTx OBJECT-TYPE
            SYNTAX         Counter32
            MAX-ACCESS     read-only
            STATUS         current
            DESCRIPTION    "The number of times TC-ACK bit was set
                            in BPDUs sent on this port-vlan pair."
            ::= {hpicfRpvstPortVlanTxCountersEntry 11}

   hpicfRpvstPortVlanTcAckFlagTxLastUpdated OBJECT-TYPE
            SYNTAX         DateAndTime
            MAX-ACCESS     read-only
            STATUS         current
            DESCRIPTION    "Time when hpicfRpvstPortVlanTcAckFlagTx
                           Counter was last updated."
            ::= {hpicfRpvstPortVlanTxCountersEntry 12}


-- Root History Table

    hpicfRpvstVlanRootHistoryTable OBJECT-TYPE
            SYNTAX      SEQUENCE OF HpicfRpvstVlanRootHistoryEntry
            MAX-ACCESS     not-accessible
            STATUS         current
            DESCRIPTION
                "A table containing the information describing the
                 RPVST root history for each VLAN."
            ::= { hpicfRpvstObjects 7 }


    hpicfRpvstVlanRootHistoryEntry OBJECT-TYPE
            SYNTAX          HpicfRpvstVlanRootHistoryEntry
            MAX-ACCESS      not-accessible
            STATUS          current
            DESCRIPTION     "History of the Roots for the VLANs."
            INDEX           { hpicfRpvstVlanId,
                              hpicfRpvstVlanRootHistoryIndex }
            ::= { hpicfRpvstVlanRootHistoryTable 1 }

    HpicfRpvstVlanRootHistoryEntry ::= SEQUENCE {
         hpicfRpvstVlanRootHistoryIndex         Integer32,
         hpicfRpvstVlanRootBridgeId             BridgeId,
         hpicfRpvstVlanRootHistoryTime          DateAndTime
    }

    hpicfRpvstVlanRootHistoryIndex OBJECT-TYPE
            SYNTAX          Integer32 (1..100)
            MAX-ACCESS      not-accessible
            STATUS          current
            DESCRIPTION
                "An index which uniquely identifies a row in root
                 history table.The lowest numerical index always holds
                 the most recent root entry.Currently last 10 entries are
                 supported."
            ::= { hpicfRpvstVlanRootHistoryEntry 1 }

    hpicfRpvstVlanRootBridgeId OBJECT-TYPE
            SYNTAX          BridgeId
            MAX-ACCESS      read-only
            STATUS          current
            DESCRIPTION     "Root bridge Id consisting of Root
                             priority and Root MAC address."
            ::= { hpicfRpvstVlanRootHistoryEntry 2 }

    hpicfRpvstVlanRootHistoryTime OBJECT-TYPE
            SYNTAX          DateAndTime
            MAX-ACCESS      read-only
            STATUS          current
            DESCRIPTION     "Time when a new root was elected."
            ::= { hpicfRpvstVlanRootHistoryEntry 3}

  --  topo change rx table

    hpicfRpvstVlanTopologyChangeRxTable OBJECT-TYPE
            SYNTAX      SEQUENCE OF HpicfRpvstVlanTopologyChangeRxEntry
            MAX-ACCESS     not-accessible
            STATUS         current
            DESCRIPTION
                "A list of entries,one for every topology change
                event that the switch received on per vlan basis.
                This table holds entries for last 10 topology
                change events received on the switch."
            ::= { hpicfRpvstObjects 8 }


    hpicfRpvstVlanTopologyChangeRxEntry OBJECT-TYPE
            SYNTAX          HpicfRpvstVlanTopologyChangeRxEntry
            MAX-ACCESS      not-accessible
            STATUS          current
            DESCRIPTION     "Set of parameters corresponding to topology
                             change event that the switch received on per
                             vlan basis."
            INDEX           { hpicfRpvstVlanId,
                              hpicfRpvstVlanTopologyChangeRxIndex }
            ::= { hpicfRpvstVlanTopologyChangeRxTable 1 }

    HpicfRpvstVlanTopologyChangeRxEntry ::= SEQUENCE {
         hpicfRpvstVlanTopologyChangeRxIndex   Integer32,
         hpicfRpvstVlanTopologyChangeRxTime    DateAndTime,
         hpicfRpvstVlanTopologyChangeRxMacAddress   MacAddress,
         hpicfRpvstVlanTopologyChangeRxPortId    Integer32
    }

   hpicfRpvstVlanTopologyChangeRxIndex OBJECT-TYPE
            SYNTAX          Integer32 (1..65535)
            MAX-ACCESS      not-accessible
            STATUS          current
            DESCRIPTION
                "An index which uniquely identifies a row
                 in VLAN TC history table.
                 Currently only last 10 entries are supported."
            ::= { hpicfRpvstVlanTopologyChangeRxEntry 1 }

    hpicfRpvstVlanTopologyChangeRxTime OBJECT-TYPE
            SYNTAX          DateAndTime
            MAX-ACCESS      read-only
            STATUS          current
            DESCRIPTION     "Time at which topology change
                            event was received ."
            ::= { hpicfRpvstVlanTopologyChangeRxEntry 2}

    hpicfRpvstVlanTopologyChangeRxMacAddress OBJECT-TYPE
            SYNTAX          MacAddress
            MAX-ACCESS      read-only
            STATUS          current
            DESCRIPTION  "MAC address form which TC change is received."

            ::= { hpicfRpvstVlanTopologyChangeRxEntry 3 }

    hpicfRpvstVlanTopologyChangeRxPortId OBJECT-TYPE
            SYNTAX          Integer32
            MAX-ACCESS      read-only
            STATUS          current
            DESCRIPTION  "Port on which an RPVST topology change
                          message is recieved."

            ::= { hpicfRpvstVlanTopologyChangeRxEntry 4 }

 --  topo change tx table

    hpicfRpvstVlanTopologyChangeTxTable OBJECT-TYPE
            SYNTAX      SEQUENCE OF HpicfRpvstVlanTopologyChangeTxEntry
            MAX-ACCESS     not-accessible
            STATUS         current
            DESCRIPTION
                "A list of entries,one for every topology change
                 event that switch originated on per vlan basis .
                 This table holds for last 10 topology change
                 events originated on switch"
            ::= { hpicfRpvstObjects 9 }

    hpicfRpvstVlanTopologyChangeTxEntry OBJECT-TYPE
            SYNTAX          HpicfRpvstVlanTopologyChangeTxEntry
            MAX-ACCESS      not-accessible
            STATUS          current
            DESCRIPTION     "Set of parameters corresponding to topology
                             change event that switch originated on per
                             vlan basis."
            INDEX           { hpicfRpvstVlanId,
                              hpicfRpvstVlanTopologyChangeTxIndex }
            ::= { hpicfRpvstVlanTopologyChangeTxTable 1 }

    HpicfRpvstVlanTopologyChangeTxEntry ::= SEQUENCE {
         hpicfRpvstVlanTopologyChangeTxIndex   Integer32,
         hpicfRpvstVlanTopologyChangeTxCurrentPortRole StpPortRole,
         hpicfRpvstVlanTopologyChangeTxPreviousPortRole StpPortRole,
         hpicfRpvstVlanTopologyChangeTxTime    DateAndTime,
         hpicfRpvstVlanTopologyChangeTxPortId Integer32
    }


    hpicfRpvstVlanTopologyChangeTxIndex OBJECT-TYPE
            SYNTAX          Integer32 (1..65535)
            MAX-ACCESS      not-accessible
            STATUS          current
            DESCRIPTION
                "Agent assigned index to uniquely identify an entry
                 in this table. The lowest numerical index always
                 holds the most recent topoogy change event entry.
                 Currently only last 10 entries are supported."
            ::= { hpicfRpvstVlanTopologyChangeTxEntry 1 }


    hpicfRpvstVlanTopologyChangeTxCurrentPortRole OBJECT-TYPE
            SYNTAX          StpPortRole
            MAX-ACCESS      read-only
            STATUS          current
            DESCRIPTION     "Current port Role in the topology."
            ::= { hpicfRpvstVlanTopologyChangeTxEntry 2 }


    hpicfRpvstVlanTopologyChangeTxPreviousPortRole OBJECT-TYPE
            SYNTAX          StpPortRole
            MAX-ACCESS      read-only
            STATUS          current
            DESCRIPTION     "Previous port Role in the topology"
            ::= { hpicfRpvstVlanTopologyChangeTxEntry 3}

    hpicfRpvstVlanTopologyChangeTxTime OBJECT-TYPE
            SYNTAX          DateAndTime
            MAX-ACCESS      read-only
            STATUS          current
            DESCRIPTION     "Time at which topology change event
                             was generated."
            ::= { hpicfRpvstVlanTopologyChangeTxEntry 4}

    hpicfRpvstVlanTopologyChangeTxPortId OBJECT-TYPE
            SYNTAX          Integer32
            MAX-ACCESS      read-only
            STATUS          current
            DESCRIPTION     "Port on which an RPVST topology change
                             message originated."
            ::= { hpicfRpvstVlanTopologyChangeTxEntry 5}


    --  port role change table

    hpicfRpvstPortRoleChangeTable   OBJECT-TYPE
            SYNTAX      SEQUENCE OF HpicfRpvstPortRoleChangeEntry
            MAX-ACCESS     not-accessible
            STATUS         current
            DESCRIPTION
                "A table containing the information describing the
                 RPVST port change history."
            ::= { hpicfRpvstObjects 10 }

    hpicfRpvstPortRoleChangeEntry   OBJECT-TYPE
            SYNTAX          HpicfRpvstPortRoleChangeEntry
            MAX-ACCESS      not-accessible
            STATUS          current
            DESCRIPTION     "History of the port change state."
            INDEX           { hpicfRpvstVlanId,
                              hpicfRpvstPortIndex,
                              hpicfRpvstPortRoleChangeIndex }
            ::= {hpicfRpvstPortRoleChangeTable 1 }

    HpicfRpvstPortRoleChangeEntry ::= SEQUENCE {
         hpicfRpvstPortRoleChangeIndex    Integer32,
         hpicfRpvstPortRoleChangeCurrentPortRole    StpPortRole,
         hpicfRpvstPortRoleChangePreviousPortRole   StpPortRole,
         hpicfRpvstPortRoleChangeTime    DateAndTime
    }


    hpicfRpvstPortRoleChangeIndex OBJECT-TYPE
            SYNTAX          Integer32 (1..65535)
            MAX-ACCESS      not-accessible
            STATUS          current
            DESCRIPTION
                "An index which uniquely identifies a row
                 in port role change table.
                 Currently only last 10 entries are supported."
            ::= {hpicfRpvstPortRoleChangeEntry 1 }


    hpicfRpvstPortRoleChangeCurrentPortRole OBJECT-TYPE
            SYNTAX          StpPortRole
            MAX-ACCESS      read-only
            STATUS          current
            DESCRIPTION     "Current port Role."
            ::= {hpicfRpvstPortRoleChangeEntry 2 }


    hpicfRpvstPortRoleChangePreviousPortRole OBJECT-TYPE
            SYNTAX          StpPortRole
            MAX-ACCESS      read-only
            STATUS          current
            DESCRIPTION     "Previous port Role ."
            ::= {hpicfRpvstPortRoleChangeEntry 3}

    hpicfRpvstPortRoleChangeTime OBJECT-TYPE
            SYNTAX          DateAndTime
            MAX-ACCESS      read-only
            STATUS          current
            DESCRIPTION     "Time when port role changed took place."
            ::= {hpicfRpvstPortRoleChangeEntry 4}


    -- NOTIFICATIONS

    hpicfRpvstErrantBpduDetector OBJECT-TYPE
        SYNTAX       INTEGER {
                         bpduFilter (1),
                         bpduProtection (2)
                    }
        MAX-ACCESS   accessible-for-notify
        STATUS       current
        DESCRIPTION  "The identifier of the feature generating
                      Errant BPDU trap."
        ::= { hpicfRpvstNotifications 1 }

    hpicfRpvstErrantBpduSrcMac OBJECT-TYPE
        SYNTAX       MacAddress
        MAX-ACCESS   accessible-for-notify
        STATUS       current
        DESCRIPTION "The source MAC address of the port sending
                     Errant BPDU."
        ::= { hpicfRpvstNotifications 2 }

    hpicfRpvstNewRootBridgeId OBJECT-TYPE
        SYNTAX       BridgeId
        MAX-ACCESS   accessible-for-notify
        STATUS       current
        DESCRIPTION  "Bridge ID of the new Root. Bridge Id
                      consists of priority and MAC address."
        ::= { hpicfRpvstNotifications 3 }

    hpicfRpvstPreviousRootBridgeId OBJECT-TYPE
        SYNTAX       BridgeId
        MAX-ACCESS   accessible-for-notify
        STATUS       current
        DESCRIPTION  "Bridge ID of the previous Root. Bridge Id
                      consists of priority and MAC address."
        ::= { hpicfRpvstNotifications 4 }

   hpicfRpvstDesignatedPort   OBJECT-TYPE
        SYNTAX       DisplayString
        MAX-ACCESS   accessible-for-notify
        STATUS       current
        DESCRIPTION  "Designated Port of the Bridge."
        ::= { hpicfRpvstNotifications 5 }

    hpicfRpvstVlanIndex OBJECT-TYPE
        SYNTAX          VlanIndex
        MAX-ACCESS      accessible-for-notify
        STATUS          current
        DESCRIPTION     "VLAN ID "
        ::= { hpicfRpvstNotifications 6 }

    hpicfRpvstPortNumber OBJECT-TYPE
        SYNTAX       Integer32 ( 1..65535)
        MAX-ACCESS   accessible-for-notify
        STATUS       current
        DESCRIPTION  "Port number "
        ::= { hpicfRpvstNotifications 7 }

    hpicfRpvstRootBridgeChangeTimeStamp OBJECT-TYPE
        SYNTAX       DateAndTime
        MAX-ACCESS   accessible-for-notify
        STATUS       current
        DESCRIPTION  "Time when the root changed"
        ::= {hpicfRpvstNotifications 8}

    hpicfRpvstSuperiorBpduSrcMac OBJECT-TYPE
        SYNTAX       MacAddress
        MAX-ACCESS   accessible-for-notify
        STATUS       current
        DESCRIPTION  "The source MAC address of the port sending
                      superior BPDU."
        ::= {hpicfRpvstNotifications 9}

    hpicfRpvstSuperiorBpduSrcPort OBJECT-TYPE
        SYNTAX       Integer32 (1..65535)
        MAX-ACCESS   accessible-for-notify
        STATUS       current
        DESCRIPTION  "Port belonging to the Bridge from which
                      the superior BPDU was received."
        ::= {hpicfRpvstNotifications 10}

    hpicfRpvstErrantBpduReceived NOTIFICATION-TYPE
           OBJECTS     { hpicfRpvstVlanIndex,
                         hpicfRpvstPortNumber,
                         hpicfRpvstPortVlanErrantBpduRxCount,
                         hpicfRpvstPortVlanState,
                         hpicfRpvstPortVlanDesigBridge,
                         hpicfRpvstDesignatedPort,
                         hpicfRpvstErrantBpduSrcMac,
                         hpicfRpvstErrantBpduDetector
                        }
           STATUS      current
           DESCRIPTION
               "This trap generated when an unexpected (errant) BPDU
                has been received on a port.
                hpicfRpvstVlanIndex - VLAN instance to which BPDU belongs.
                hpicfRpvstPortNumber -  Port ID on which BPDU received.
                hpicfRpvstPortVlanErrantBpduRxCount -
                         Total number of errant BPDU received on
                         the port which belongs to VLAN
                         hpicfRpvstVlanId.
                hpicfRpvstPortState - State of this port.
                hpicfRpvstPortVlanDesigBridge -
                         Designated Bridge that transmitted this BPDU.
                hpicfRpvstDesignatedPort -
                         Designated port of the Bridge that transmitted
                         this BPDU.
                hpicfRpvstErrantBpduSrcMac-
                         Source MAC address of the port sending this
                         Errant trap.
                hpicfRpvstErrantBpduDetector -
                         The identifier of the feature generating
                         Errant BPDU Trap."
    ::= { hpicfRpvstNotifications 11 }


    hpicfRpvstNewRoot NOTIFICATION-TYPE
          OBJECTS     { hpicfRpvstVlanIndex,
                        hpicfRpvstNewRootBridgeId,
                        hpicfRpvstPreviousRootBridgeId,
                        hpicfRpvstRootBridgeChangeTimeStamp
                      }
          STATUS      current
          DESCRIPTION
                  "Trap generated when sending agent has become
                   the new root of spanning Tree for the specified VLAN;
                   the notification is sent by a bridge soon after
                   its election as the new root, e.g., upon expiration
                   of the Topology Change Timer, immediately
                   subsequent to its election.

                   hpicfRpvstVlanIndex - VLAN  instance in which new root
                                      is elected.
                   hpicfRpvstNewRootBridgeId -
                                      Bridge ID of the new root elected.
                   hpicfRpvstPreviousRootBridgeId -
                                      Bridge ID of the previous root.
                   hpicfRpvstRootBridgeChangeTimeStamp -
                                      Time when the root bridge changed."
    ::= { hpicfRpvstNotifications 12 }


    hpicfRpvstRootGuardInconsistency NOTIFICATION-TYPE
     OBJECTS     { hpicfRpvstVlanIndex,
                   hpicfRpvstPortNumber,
                   hpicfRpvstSuperiorBpduSrcMac,
                   hpicfRpvstSuperiorBpduSrcPort
                 }
     STATUS      current
     DESCRIPTION
            " Trap generated when a Root Guard feature enabled port
              receives superior BPDUs on its interface for a
              given VLAN instance.

              hpicfRpvstVlanIndex -
                      Vlan Instance to which BPDU belongs.
              hpicfRpvstPortNumber -
                      Port ID where root-inconsistency occurred.
              hpicfRpvstSuperiorBpduSrcMac -
                      The source MAC address of the port sending
                      superior BPDU.
              hpicfRpvstSuperiorBpduSrcPort -
                      Port belonging to the Bridge, which transmitted
                      the superior BPDU."
    ::= { hpicfRpvstNotifications   13 }

    hpicfRpvstLoopGuardInconsistency NOTIFICATION-TYPE
     OBJECTS     { hpicfRpvstVlanIndex,
                   hpicfRpvstPortNumber,
                   hpicfRpvstPortVlanDesigBridge
                 }
     STATUS      current
     DESCRIPTION
            " Trap generated when a Loop Guard feature enabled port
            stops receiving BPDUs from its designated port for a
            given VLAN instance but keeps the port in blocked state.

            hpicfRpvstVlanIndex -
                  Vlan Instance in which no BPDU received.
            hpicfRpvstPortNumber -
                  Port ID where loop-inconsistency occurred.
            hpicfRpvstPortVlanDesigBridge  -
                  Designated Bridge this port was expecting to
            receive the BPDU."
    ::= { hpicfRpvstNotifications   14 }

  hpicfRpvstOldPortRole OBJECT-TYPE
        SYNTAX       Integer32 ( 1..65535)
        MAX-ACCESS   accessible-for-notify
        STATUS       current
        DESCRIPTION  "Old Port state "
        ::= { hpicfRpvstNotifications 15 }

    hpicfRpvstNewPortRole OBJECT-TYPE
        SYNTAX       Integer32 ( 1..65535)
        MAX-ACCESS   accessible-for-notify
        STATUS       current
        DESCRIPTION  "new port state "
        ::= { hpicfRpvstNotifications 16 }

    hpicfRpvstTopoChangeTime OBJECT-TYPE
        SYNTAX       DateAndTime
        MAX-ACCESS   accessible-for-notify
        STATUS       current
        DESCRIPTION  "topo change time "
        ::= { hpicfRpvstNotifications 17 }


    hpicfRpvstTopologyChange NOTIFICATION-TYPE
     OBJECTS     { hpicfRpvstVlanIndex,
                   hpicfRpvstPortNumber,
                   hpicfRpvstOldPortRole,
                   hpicfRpvstNewPortRole,
                   hpicfRpvstTopoChangeTime
                        }
    STATUS      current
    DESCRIPTION
           " Trap generated whenever topology change detected on this port-
             vlan pair.
             hpicfRpvstVlanIndex - Vlan Instance for which topology change detected.
             hpicfRpvstPortNumber - Port ID for which topology change detected.
             hpicfRpvstOldPortRole - Old role of this port before topology change.
             hpicfRpvstNewPortRole - New state of this port after topology change.
             hpicfRpvstTopoChangeTime - Time at which the topology change happened for this port."

    ::= { hpicfRpvstNotifications   18 }


 -- Conformance Information

   hpicfRpvstGroups OBJECT IDENTIFIER ::= { hpicfRpvstConformance 1 }
   hpicfRpvstCompliances OBJECT IDENTIFIER ::= { hpicfRpvstConformance 2 }

    -- Compliance Statements

    hpicfRpvstCompliance1 MODULE-COMPLIANCE
            STATUS          deprecated
            DESCRIPTION     "The compliance statement"
            MODULE          -- this module
            MANDATORY-GROUPS {
                            hpicfRpvstGroup,
                            hpicfRpvstVlanGroup,
                            hpicfRpvstPortVlanGroup,
                            hpicfRpvstPortGroup,
                            hpicfRpvstPortVlanCounterGroup,
                            hpicfRpvstRootHistoryGroup,
                            hpicfRpvstNotificationObjectGrp,
                            hpicfRpvstNotificationGroup
                            }
            ::= { hpicfRpvstCompliances 1 }

    hpicfRpvstCompliance2 MODULE-COMPLIANCE
            STATUS          current
            DESCRIPTION     "The compliance statement"
            MODULE          -- this module
            MANDATORY-GROUPS {
                            hpicfRpvstPvst1,
                            hpicfRpvstNotificationGroupPvst1,
                            hpicfRpvstNotificationObjectGrpPvst1,
                            hpicfRpvstTopologyRxGroup,
                            hpicfRpvstTopologyTxGroup,
                            hpicfRpvstPortRoleChangeGroup
                           }
            ::= { hpicfRpvstCompliances 2 }

    hpicfRpvstCompliance3 MODULE-COMPLIANCE
            STATUS          current
            DESCRIPTION     "The compliance statement"
            MODULE          -- this module
            MANDATORY-GROUPS {
                            hpicfRpvstGroup,
                            hpicfRpvstVlanGroup,
                            hpicfRpvstPortVlanGroup,
                            hpicfRpvstPortGroup1,
                            hpicfRpvstPortVlanCounterGroup,
                            hpicfRpvstRootHistoryGroup,
                            hpicfRpvstNotificationObjectGrp,
                            hpicfRpvstNotificationGroup
                            }
            ::= { hpicfRpvstCompliances 3 }

    -- units of conformance


    hpicfRpvstGroup OBJECT-GROUP
            OBJECTS         {
                              hpicfRpvstResetCounters,
                              hpicfRpvstExtendedSystemID,
                              hpicfRpvstIgnorePVIDInconsistency
                             }
            STATUS          current
            DESCRIPTION
                   "These objects are used for managing/monitoring
                    RPVST global parameters."
            ::= { hpicfRpvstGroups 1 }

    hpicfRpvstVlanGroup OBJECT-GROUP
            OBJECTS         {
                            hpicfRpvstVlanHelloTime,
                            hpicfRpvstVlanForwardDelay,
                            hpicfRpvstVlanMaxAge,
                            hpicfRpvstVlanPriority,
                            hpicfRpvstVlanRoot,
                            hpicfRpvstVlanRpvstStatus,
                            hpicfRpvstVlanResetCounters,
                            hpicfRpvstVlanOperHelloTime,
                            hpicfRpvstVlanRootPriority,
                            hpicfRpvstVlanRootPort,
                            hpicfRpvstVlanRootPathCost,
                            hpicfRpvstVlanRootMacAddress,
                            hpicfRpvstVlanRootChangeCounter,
    			    hpicfRpvstVlanTimeSinceLastTopoChange,
                            hpicfVlanTopoChangeCount
                             }
            STATUS          current
            DESCRIPTION
                "These objects are used for managing/monitoring
                RPVST VLAN parameters."
            ::= { hpicfRpvstGroups 2 }

    hpicfRpvstPortVlanGroup OBJECT-GROUP
            OBJECTS         {
                            hpicfRpvstPortVlanPathCost,
                            hpicfRpvstPortVlanPriority,
                            hpicfRpvstPortVlanResetCounters,
                            hpicfRpvstPortVlanRole,
                            hpicfRpvstPortVlanState,
                            hpicfRpvstPortVlanDesigBridge,
                            hpicfRpvstPortVlanOperPointToPoint,
                            hpicfRpvstPortVlanOperEdge
                            }
            STATUS          current
            DESCRIPTION
                "These objects are used for managing/monitoring
                RPVST port parameters for the VLANs."
            ::= { hpicfRpvstGroups 3 }

    hpicfRpvstPortGroup OBJECT-GROUP
            OBJECTS       {
                           hpicfRpvstPortAdminEdge,
                           hpicfRpvstPortAdminPointToPoint,
                           hpicfRpvstPortAutoEdge,
                           hpicfRpvstPortBpduFiltering,
                           hpicfRpvstPortRestrictedTcn,
                           hpicfRpvstPortRootGuard,
                           hpicfRpvstPortLoopGuard,
                           hpicfRpvstPortBpduProtection
                            }
            STATUS          deprecated
            DESCRIPTION
                "These objects are used for managing/monitoring
                RPVST port parameters"
            ::= { hpicfRpvstGroups 4 }


    hpicfRpvstPortVlanCounterGroup OBJECT-GROUP
            OBJECTS       {
           hpicfRpvstPortVlanRpvstBpduRx                 ,
           hpicfRpvstPortVlanRpvstBpduRxLastUpdated      ,
           hpicfRpvstPortVlanRpvstBpduTx                 ,
           hpicfRpvstPortVlanRpvstBpduTxLastUpdated      ,
           hpicfRpvstPortVlanRstBpduRx                   ,
           hpicfRpvstPortVlanRstBpduRxLastUpdated        ,
           hpicfRpvstPortVlanRstBpduTx                   ,
           hpicfRpvstPortVlanRstBpduTxLastUpdated        ,
           hpicfRpvstPortVlanConfigBpduRx                ,
           hpicfRpvstPortVlanConfigBpduRxLastUpdated     ,
           hpicfRpvstPortVlanConfigBpduTx                ,
           hpicfRpvstPortVlanConfigBpduTxLastUpdated     ,
           hpicfRpvstPortVlanTcnBpduRx                   ,
           hpicfRpvstPortVlanTcnBpduRxLastUpdated        ,
           hpicfRpvstPortVlanTcnBpduTx                   ,
           hpicfRpvstPortVlanTcnBpduTxLastUpdated        ,
           hpicfRpvstPortVlanTcDetectCount               ,
           hpicfRpvstPortVlanTcDetectCountLastUpdated    ,
           hpicfRpvstPortVlanTcFlagRx                    ,
           hpicfRpvstPortVlanTcFlagRxLastUpdated         ,
           hpicfRpvstPortVlanTcFlagTx                    ,
           hpicfRpvstPortVlanTcFlagTxLastUpdated         ,
           hpicfRpvstPortVlanTcAckFlagRx                 ,
           hpicfRpvstPortVlanTcAckFlagRxLastUpdated      ,
           hpicfRpvstPortVlanTcAckFlagTx                 ,
           hpicfRpvstPortVlanTcAckFlagTxLastUpdated      ,
           hpicfRpvstPortVlanAgedBpduRx                  ,
           hpicfRpvstPortVlanAgedBpduRxLastUpdated       ,
           hpicfRpvstPortVlanStarvedBpduCount            ,
           hpicfRpvstPortVlanStarvedBpduCountLastUpdated ,
           hpicfRpvstPortVlanInvalidBpduRx               ,
           hpicfRpvstPortVlanInvalidBpduRxLastUpdated    ,
           hpicfRpvstPortVlanLoopedBackBpduRx            ,
           hpicfRpvstPortVlanLoopedBackBpduRxLastUpdated ,
           hpicfRpvstPortVlanErrantBpduRxCount           ,
           hpicfRpvstPortVlanErrantBpduRxCountLastUpdated


                            }
            STATUS          current
            DESCRIPTION   "Group of port-vlan counter objects."
            ::= { hpicfRpvstGroups 5 }


    hpicfRpvstRootHistoryGroup OBJECT-GROUP
            OBJECTS {
                      hpicfRpvstVlanRootBridgeId ,
                      hpicfRpvstVlanRootHistoryTime
            }
            STATUS          current
            DESCRIPTION   "Group of VLAN Root history objects."
            ::= { hpicfRpvstGroups 6 }

    hpicfRpvstNotificationObjectGrp   OBJECT-GROUP
            OBJECTS {
                      hpicfRpvstErrantBpduDetector,
                      hpicfRpvstErrantBpduSrcMac,
                      hpicfRpvstVlanIndex,
                      hpicfRpvstPortNumber,
                      hpicfRpvstNewRootBridgeId,
                      hpicfRpvstPreviousRootBridgeId,
                      hpicfRpvstDesignatedPort,
                      hpicfRpvstRootBridgeChangeTimeStamp,
                      hpicfRpvstSuperiorBpduSrcMac,
                      hpicfRpvstSuperiorBpduSrcPort
            }
            STATUS          current
            DESCRIPTION   "Group of objects required for
                           notifications."
            ::= { hpicfRpvstGroups 7 }

  hpicfRpvstNotificationGroup   NOTIFICATION-GROUP
            NOTIFICATIONS {
                      hpicfRpvstErrantBpduReceived,
                      hpicfRpvstNewRoot,
                      hpicfRpvstRootGuardInconsistency,
                      hpicfRpvstLoopGuardInconsistency
            }
            STATUS          current
            DESCRIPTION   "Group of notifications."
            ::= { hpicfRpvstGroups 8 }


  hpicfRpvstPvst1   OBJECT-GROUP
            OBJECTS {
                     hpicfRpvstPathCostMode,
                     hpicfRpvstSendTopoChangeCtrl,
                     hpicfRpvstLogPortStateTransitions,
                     hpicfRpvstPortVlanInconsistencyReason
                    }
            STATUS          current
            DESCRIPTION   "Group of object added part of pvst1."
            ::= { hpicfRpvstGroups 9 }

   hpicfRpvstNotificationGroupPvst1   NOTIFICATION-GROUP
            NOTIFICATIONS {
                           hpicfRpvstTopologyChange
            }
            STATUS          current
            DESCRIPTION   "Group of notifications."
            ::= { hpicfRpvstGroups 10 }

   hpicfRpvstNotificationObjectGrpPvst1   OBJECT-GROUP
            OBJECTS {
                   hpicfRpvstOldPortRole,
                   hpicfRpvstNewPortRole,
                   hpicfRpvstTopoChangeTime
            }
            STATUS          current
            DESCRIPTION   "Group of objects required for
                           notifications."
            ::= { hpicfRpvstGroups 11 }

   hpicfRpvstTopologyRxGroup   OBJECT-GROUP
            OBJECTS {
                   hpicfRpvstVlanTopologyChangeRxTime,
                   hpicfRpvstVlanTopologyChangeRxMacAddress,
                   hpicfRpvstVlanTopologyChangeRxPortId
            }
            STATUS          current
            DESCRIPTION   "Group of objects required for
                           vlan topo change rx."
            ::= { hpicfRpvstGroups 12 }
   hpicfRpvstTopologyTxGroup   OBJECT-GROUP
            OBJECTS {
                   hpicfRpvstVlanTopologyChangeTxCurrentPortRole,
                   hpicfRpvstVlanTopologyChangeTxPreviousPortRole,
                   hpicfRpvstVlanTopologyChangeTxTime,
                   hpicfRpvstVlanTopologyChangeTxPortId
            }
            STATUS          current
            DESCRIPTION   "Group of objects required for
                           vlan topo change tx."
            ::= { hpicfRpvstGroups 13 }

    hpicfRpvstPortRoleChangeGroup   OBJECT-GROUP
            OBJECTS {
                   hpicfRpvstPortRoleChangeCurrentPortRole,
                   hpicfRpvstPortRoleChangePreviousPortRole,
                   hpicfRpvstPortRoleChangeTime
            }
            STATUS          current
            DESCRIPTION   "Group of objects required for
                           port role change."
            ::= { hpicfRpvstGroups 14 }

    hpicfRpvstPortGroup1 OBJECT-GROUP
            OBJECTS       {
                           hpicfRpvstPortAdminEdge,
                           hpicfRpvstPortAdminPointToPoint,
                           hpicfRpvstPortAutoEdge,
                           hpicfRpvstPortBpduFiltering,
                           hpicfRpvstPortRestrictedTcn,
                           hpicfRpvstPortRootGuard,
                           hpicfRpvstPortLoopGuard,
                           hpicfRpvstPortBpduProtection,
                           hpicfRpvstPortIeeeRstBpdu
                            }
            STATUS          current
            DESCRIPTION
                "These objects are used for managing/monitoring
                RPVST port parameters"
            ::= { hpicfRpvstGroups 15 }


END
