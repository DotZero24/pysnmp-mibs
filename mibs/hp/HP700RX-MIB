--      HP700RX Config MIB definition.
--      Contact xsupport@waterloo.hp.com
--

        HP700RX-MIB     DEFINITIONS ::= BEGIN

IMPORTS
        enterprises, NetworkAddress, IpAddress, Counter, Gauge,
                TimeTicks
            FROM RFC1065-SMI
        OBJECT-TYPE
                FROM RFC-1212;

--      Define some of the things we need.
--

hp              OBJECT IDENTIFIER ::= { enterprises 11 }
nm              OBJECT IDENTIFIER ::= { hp 2 }
system          OBJECT IDENTIFIER ::= { nm 3 }
interface       OBJECT IDENTIFIER ::= { nm 4 }
icmp            OBJECT IDENTIFIER ::= { nm 7 }
snmp            OBJECT IDENTIFIER ::= { nm 13 }

trap            OBJECT IDENTIFIER ::= { snmp 1 }
snmpdConf       OBJECT IDENTIFIER ::= { snmp 2 }

netPeripherals     OBJECT IDENTIFIER ::= { system 9 }
hpXStation            OBJECT IDENTIFIER ::= { netPeripherals 3 }

config                  OBJECT IDENTIFIER ::= { hpXStation 1 }

-- Now our groups. Each one corresponds to a config screen.

        terminal        OBJECT IDENTIFIER ::= { config 1 }
        network         OBJECT IDENTIFIER ::= { config 2 }
        startup         OBJECT IDENTIFIER ::= { config 3 }
        statistics      OBJECT IDENTIFIER ::= { config 4 }
        preferences     OBJECT IDENTIFIER ::= { config 5 }
        reset	     OBJECT IDENTIFIER ::= { config 6 }


-- the terminal group.
-- This screen has terminal control type config data that is
-- outside the X world and isn't related to the network.

        monitor OBJECT-TYPE
               SYNTAX  INTEGER {
                        a1097(1),
                        hp98754(2),
                        hp98789(3),
                        hpd1187(4),
                        hpa1497(5),
                        hp98753(6),
                        hp98785(7),
                        hpd1188(8),
                        hpd1195(9),
                        hpd1182(10),
                        hp98774(11),
                        hpd1195x1224(12),
                        hpd1195x640(13)
                        }
                ACCESS  read-write
                STATUS  mandatory
                DESCRIPTION
                        "The type of monitor the terminal is configured
                        to drive. Each monitor type varies in resolution,
                        refresh rate, color capability, dots per inch,
                        and synchronization. Some monitors (especially
                        multi-sync types) may produce usable displays
                        at several settings. "
                ::= { terminal 1 }

        monitorDescription OBJECT-TYPE
                SYNTAX  DisplayString
                ACCESS  read-only
                STATUS  mandatory
                DESCRIPTION
                        "The resolution, refresh rate, color capability,
                        dots per inch, and synchronization the terminal
                        is sending to its monitor and the part number
                        of the monitor that works best at these settings. "
                ::= { terminal 2 }

        at2kbLEDControl OBJECT-TYPE
                SYNTAX  INTEGER {
                        client(1),
                        local(2)
                        }
                ACCESS  read-write
                STATUS  mandatory
                DESCRIPTION
                        "Indicates whether the CAPS-LOCK LED on the
                        keyboard (if present) is controlled by
                        the X terminal or the clients (as X LED 3). "
                ::= { terminal 3 }

        at2kbLanguage   OBJECT-TYPE
                SYNTAX  INTEGER {
                        usascii(1),
                        danish(2),
                        french(3),
                        norwegian(4),
                        swissgerman(5),
                        candianfrench(6),
                        english(7),
                        finnish(8),
                        belgian(9),
                        spanish(10),
                        german(11),
                        swedish(12),
                        dutch(13),
                        italian(14),
                        candianenglish(15),
                        swissfrench(16),
                        hangul(17),
                        simplifiedchinese(18),
                        traditionalchinese(19),
                        kanji(20),
			decLK401english(21),
			reserved(22)
                        }
                ACCESS  read-write
                STATUS  mandatory
                DESCRIPTION
                        "The language setting for an AT/2 keyboard
                        attached to this terminal. "
                ::= { terminal 4 }

        serialSpeed     OBJECT-TYPE
                SYNTAX  INTEGER {
                        bps75(1),
                        bps150(2),
                        bps300(3),
                        bps600(4),
                        bps1200(5),
                        bps2400(6),
                        bps4800(7),
                        bps9600(8),
                        bps19200(9),
                        bps38400(10)
                        }
                ACCESS  read-write
                STATUS  mandatory
                DESCRIPTION
                        "The baud rate of the serial port."
                ::= { terminal 5 }

        serialDataBits  OBJECT-TYPE
                SYNTAX  INTEGER {
                        bits7(1),
                        bits8(2)
                        }
                ACCESS  read-write
                STATUS  mandatory
                DESCRIPTION
                        "The number of data bits in each character
                        sent and received over the serial port."
                ::= { terminal 6 }

        serialStopBits  OBJECT-TYPE
                SYNTAX  INTEGER {
                        bits1(1),
                        bits2(2)
                        }
                ACCESS  read-write
                STATUS  mandatory
                DESCRIPTION
                        "The number of stop bits sent at the end of
                        each character sent through the serial port."
                ::= { terminal 7 }

        serialParity    OBJECT-TYPE
                SYNTAX  INTEGER {
                        none(1),
                        even(2),
                        odd(3)
                        }
                ACCESS  read-write
                STATUS  mandatory
                DESCRIPTION
                        "The parity generated and checked on
                        each character sent and received through
                        the serial port."
                ::= { terminal 8 }

        serialPacing    OBJECT-TYPE
                SYNTAX  INTEGER {
                        none(1),
                        xonxoff(2),
                        rtscts(3)
                        }
                ACCESS  read-write
                STATUS  mandatory
                DESCRIPTION
                        "The type of flow control used on the serial port."
                ::= { terminal 9 }

        serialUse       OBJECT-TYPE
                SYNTAX  INTEGER {
                        disabled(1),
                        primary(2),
                        auxiliary(3),
                        diagnostics(4),
                        serialsession(5),
                        slip(6)
                        }
                ACCESS  read-write
                STATUS  mandatory
                DESCRIPTION
                        "What the serial port is being used for. Note
                        that primary and auxiliary use indicate that
                        the serial port is 'connected' to TCP ports
                        9100 and 9101 respectively."
                ::= { terminal 10 }

        parallelUse     OBJECT-TYPE
                SYNTAX  INTEGER {
                        disabled(1),
                        primary(2),
                        auxiliary(3),
                        diagnostics(4)
                        }
                ACCESS  read-write
                STATUS  mandatory
                DESCRIPTION
                        "What the parallel port is being used for. Note
                        that primary and auxiliary use indicate that
                        the serial port is 'connected' to TCP ports
                        9100 and 9101 respectively."
                ::= { terminal 11 }
        portuseEnable   OBJECT-TYPE
                        SYNTAX  INTEGER {
                                enabled(1),
                                disabled(2)
                                }
                        ACCESS  read-write
                        STATUS  mandatory
                        DESCRIPTION
                                "This variable indicates whether remote (through
                                SNMP) serial port use changes are allowed."
                        ::= { terminal 12 }



-- the network group
-- this screen has the network related config information.
--
        networkParamsFrom       OBJECT-TYPE
                SYNTAX  INTEGER {
                        bootp(1),
                        eeprom(2)
                        }
                ACCESS  read-write
                STATUS  mandatory
                DESCRIPTION
                        "Indicates whether the X terminal will use
                        bootp to get its network parameters (IP address,
                        default gateway, boot file, terminal name,
                        domain name, name server addresses, subnet mask,
                        and remote configuration file) at power up or
                        use those stored in EEPROM."
                ::= { network 1 }

        configedAddress OBJECT-TYPE
                SYNTAX  DisplayString
                ACCESS  read-write
                STATUS  mandatory
                DESCRIPTION
                        "The IP address configured for the Ethernet
                        interface on this terminal.

                        The active value for this field is set at
                        startup.  After startup a different value can be
                        saved to terminal memory without being used,
                        therefore the value returned via SNMP is not
                        necessarily the value currently in use. "
                ::= { network 2 }

        configedSubnetMask      OBJECT-TYPE
                SYNTAX  DisplayString
                ACCESS read-write
                STATUS  mandatory
                DESCRIPTION
                        "The subnet mask configured for the Ethernet
                        interface on this terminal.

                        The active value for this field is set at
                        startup.  After startup a different value can be
                        saved to terminal memory without being used,
                        therefore the value returned via SNMP is not
                        necessarily the value currently in use. "
                ::= { network 3 }

-- the configured routing table
--
        configedRouteTable      OBJECT-TYPE
                SYNTAX  SEQUENCE OF RouteTableEntry
                ACCESS  not-accessible
                STATUS  mandatory
                DESCRIPTION
                        "The routes configured for this terminal.

                        At startup the terminal tests the routes
                        in its routing table. If any route fails,
                        it will be discarded, therefore the configured
                        routes may not be the routes in use.
                        There are a number of ways a route can fail
                        the startup tests, including: terminal can't ping
                        the gateway, terminal can't resolve one of the
                        names into an IP address, or a specified gateway
                        is not on a connected subnet."
                ::= { network 4 }

        routeTableEntry OBJECT-TYPE
                SYNTAX  RouteTableEntry
                ACCESS  not-accessible
                STATUS  mandatory
                DESCRIPTION
                        "Each entry reflects one route."
                INDEX   { routeIndex }
                ::= { configedRouteTable 1 }

        RouteTableEntry ::= SEQUENCE {
                routeIndex
                        INTEGER,
                routeGateway
                        DisplayString,
                routeDestination
                        DisplayString
                }

        routeIndex      OBJECT-TYPE
                SYNTAX  INTEGER
                ACCESS  read-only
                STATUS  mandatory
                DESCRIPTION
                        "The number of a row in the gateway table on the
                         Network config screen."
                ::= { routeTableEntry 1 }

        routeGateway    OBJECT-TYPE
                SYNTAX  DisplayString
                ACCESS  read-write
                STATUS  mandatory
                DESCRIPTION
                        "The address of an intermediate machine to
                        send packets to. Note that this is a string
                        and may be either a dotted decimal IP address
                        or a domain name."
                ::= { routeTableEntry 2 }

        routeDestination        OBJECT-TYPE
                SYNTAX  DisplayString
                ACCESS  read-write
                STATUS  mandatory
                DESCRIPTION
                        "The final destination address for this route.
                        This may be a machine or a network. Note that this
                        is a string and may be either a dotted decimal
                        IP address or a domain name."
                ::= { routeTableEntry 3 }

        primaryFileServer       OBJECT-TYPE
                SYNTAX  DisplayString
                ACCESS  read-write
                STATUS  mandatory
                DESCRIPTION
                        "The address of the first file server the terminal
                        attempts to contact at startup. This may be
                        either a node name (in which case it will be
                        resolved to an address using Domain Name
                        Resolution) or it may be an IP address in dotted
                        decimal form. "
                ::= { network 5 }

        primaryAccessMethod     OBJECT-TYPE
                SYNTAX  INTEGER {
                        tftp(1),
                        nfs(2)
                        }
                ACCESS  read-write
                STATUS  mandatory
                DESCRIPTION
                        "The method used to read files from the primary
                        file server. This method may be overridden for
                        individual paths."
                ::= { network 6 }

        alternateFileServer     OBJECT-TYPE
                SYNTAX  DisplayString
                ACCESS  read-write
                STATUS  mandatory
                DESCRIPTION
                        "The address of the file server the terminal
                        will attempt to contact at startup if the primary
                        file server cannot be reached. This address
                        may be the node name (in which case it will be
                        resolved to an address before use using the Domain
                        Name Resolution) or it may be the address in dotted
                        decimal form. "
                ::= {   network 7 }

        alternateAccessMethod   OBJECT-TYPE
                SYNTAX  INTEGER {
                        tftp(1),
                        nfs(2)
                        }
                ACCESS  read-write
                STATUS  mandatory
                DESCRIPTION
                        "The method used to read files from the alternative
                        file server. This method may be overridden for
                        individual pathes."
                ::= { network 8 }

        fileTimeout             OBJECT-TYPE
                SYNTAX  INTEGER
                ACCESS  read-write
                STATUS  mandatory
                DESCRIPTION
                        "The maximum time (in seconds) that the terminal
                        will wait for a response to a request to the file
                        server before giving up. The name resolver timeout
                        is six times the file timeout. "
                ::= {   network 9 }

        primaryNameServer       OBJECT-TYPE
                SYNTAX  DisplayString
                ACCESS  read-write
                STATUS  mandatory
                DESCRIPTION
                        "The primary name server's IP address
                        in dotted decimal format."
                ::= {   network 10 }

        alternateNameServer     OBJECT-TYPE
                SYNTAX  DisplayString
                ACCESS  read-write
                STATUS  mandatory
                DESCRIPTION
                        "The alternative name server's IP address
                        in dotted decimal format. If no answer is received
                        from the primary name server, the terminal attempts
                        to contact this name server."
                ::= {   network 11 }

		domain	OBJECT-TYPE
                SYNTAX  DisplayString
                ACCESS  read-write
                STATUS  mandatory
                DESCRIPTION
                        "The fully qualified domain of the network to
                        which the terminal is connected. This includes
                        all parts following the first '.' (dot) in the
                        fully qualified host name of the terminal.
                        Typical examples are hp.com or waterloo.edu"
                ::= {   network 12 }

        terminalName            OBJECT-TYPE
                SYNTAX  DisplayString
                ACCESS  read-write
                STATUS  mandatory
                DESCRIPTION
                        "The name assigned to this terminal. This
                        name should correspond to the name assigned
                        using the Domain Name service, Network Information
                        Services, and other host address lookup mechanisms."
                ::= {   network 13 }

        slipLocalAddress        OBJECT-TYPE
                SYNTAX  DisplayString
                ACCESS  read-write
                STATUS  mandatory
                DESCRIPTION
                        "The address used for the terminal end of
                        the SLIP connection."
                ::= {   network 14 }

        slipRemoteAddress       OBJECT-TYPE
                SYNTAX  DisplayString
                ACCESS  read-write
                STATUS  mandatory
                DESCRIPTION
                        "The address used for the remote (host) end
                        end of the SLIP connection."
                ::= { network 15 }


        slipMask       OBJECT-TYPE
                SYNTAX  DisplayString
                ACCESS  read-write
                STATUS  mandatory
                DESCRIPTION
                        "The subnet mask configured for the SLIP
                        interface on this terminal.  "
                ::= { network 16 }

--      the startup group
--      This screen contains information related to starting up the
--      terminal and the X server. It also has the X server font path
--      information displayed.
--

        romFonts                OBJECT-TYPE
                SYNTAX  INTEGER {
                        disabled(1),
                        enabled(2)
                        }
                ACCESS  read-write
                STATUS  mandatory
                DESCRIPTION
                        "Controls whether or not fonts are read from
                        the ROM card (if present). "
		::= { startup 1 }

        rgbFileFrom             OBJECT-TYPE
                SYNTAX  INTEGER {
                network(1),
                rom(2)
                }
                ACCESS  read-write
                STATUS  mandatory
                DESCRIPTION
                        "Controls whether or not the rgb.txt file
                        is read from the ROM card (if present). "
                ::= {   startup 2 }

        bootFileFrom            OBJECT-TYPE
                SYNTAX  INTEGER {
                network(1),
                rom(2)
                }
                ACCESS  read-write
                STATUS  mandatory
                DESCRIPTION
                        "Controls whether or not the X server file
                        is read from the ROM card (if present). "
                ::= {   startup 3 }

        bootFileName            OBJECT-TYPE
                SYNTAX  DisplayString
                ACCESS  read-write
                STATUS  mandatory
                DESCRIPTION
                        "The name of the X server file to load.
                        This may be a complete path (starting with /)
                        and may include host and access method overrides."
                ::= {   startup 4 }

        remoteConfigEnabled     OBJECT-TYPE
                SYNTAX  INTEGER {
                        disabled(1),
                        enabled(2)
                        }
                ACCESS  read-write
                STATUS  mandatory
                DESCRIPTION
                        "Controls whether or not the remote config
                        file is read from the file server at startup."
                ::= {   startup 5 }

        remoteConfigFile        OBJECT-TYPE
                SYNTAX  DisplayString
                ACCESS  read-write
                STATUS  mandatory
                DESCRIPTION
                        "The name of the remote config file to load at
                        startup. This may be a complete path (starting
                        with /) and include host and access method overrides."
                ::= {   startup 6 }

        xdmcpEnabled            OBJECT-TYPE
                SYNTAX  INTEGER {
                        disabled(1),
                        enabled(2)
                        }
                ACCESS  read-write
                STATUS  mandatory
                DESCRIPTION
                        "Controls whether or not XDMCP is used to start
                        user sessions on this terminal."
                ::= {   startup 7 }

        xdmcpType               OBJECT-TYPE
                SYNTAX  INTEGER {
                        broadcast(1),
                        direct(2),
                        indirect(3)
                        }
                ACCESS  read-write
                STATUS  mandatory
                DESCRIPTION
                        "Controls the type of XDMCP request sent
                        from the terminal at startup."
                ::= {   startup 8 }

        xdmcpHost               OBJECT-TYPE
                SYNTAX  DisplayString
                ACCESS  read-write
                STATUS  mandatory
                DESCRIPTION
                        "The address of the host to which the terminal
                        sends XDMCP requests at startup. This field is
                        ignored if XDMCP type is BROADCAST."
                ::= {   startup 9 }

        telnetAutoStart         OBJECT-TYPE
                SYNTAX  INTEGER {
                        disabled(1),
                        enabled(2)
                        }
                ACCESS  read-write
                STATUS  mandatory
                DESCRIPTION
                        "Determines whether a TELNET session is auto-
                        started at boot time. TELNET can be used
                        to start a user session, but TELNET cannot be
                        used if XDMCP is enabled."
                ::= {   startup 10 }

        telnetCharSet           OBJECT-TYPE
                SYNTAX  INTEGER {
                        usascii(1),
                        isoLatin1(2),
                        hpRoman8(3)
                        }
                ACCESS  read-write
                STATUS  mandatory
                DESCRIPTION
                        "Controls the character set used to display
                        characters in the TELNET and serial terminal
                        sessions. "
                ::= {   startup 11 }

        telnetHost              OBJECT-TYPE
                SYNTAX  DisplayString
                ACCESS  read-write
                STATUS  mandatory
                DESCRIPTION
                        "The address of the host to attempt to connect
                        to when TELNET is (auto)started. This may be a
                        name or IP address in dotted decimal format."
                ::= {   startup 12 }


--
-- The font path table.
--

        fontPathTable           OBJECT-TYPE
                SYNTAX  SEQUENCE OF FontEntry
                ACCESS  not-accessible
                STATUS  mandatory
                DESCRIPTION
                        "A list of directory paths used when by the X server
                        when searching for fonts"
                ::= {   startup 13 }

        fontEntry       OBJECT-TYPE
                SYNTAX  FontEntry
                ACCESS  not-accessible
                STATUS  mandatory
                DESCRIPTION
                        "An single path to a set of font files."
                INDEX   { fontIndex }
                ::= { fontPathTable 1 }

        FontEntry ::= SEQUENCE {
                        fontIndex
                                INTEGER,
                        fontPath
                                DisplayString
                }

        fontIndex       OBJECT-TYPE
                SYNTAX  INTEGER
                ACCESS  read-only
                STATUS  mandatory
                DESCRIPTION
                        "The index into the list of font paths."
                ::= { fontEntry 1 }

        fontPath        OBJECT-TYPE
                SYNTAX  DisplayString
                ACCESS  read-write
                STATUS  mandatory
                DESCRIPTION
                        "The actual font path in the format appropriate
                        to the operating system in use."
                ::= { fontEntry 2 }



--      the statistics group
--      There are two stats screens that show the values of various
--      counters etc.
--

        memInstalled            OBJECT-TYPE
                SYNTAX  INTEGER
                ACCESS  read-only
                STATUS  mandatory
                DESCRIPTION
                        "The amount of memory installed in the terminal
                        (excluding video memory) in Kbytes."
                ::= {   statistics 1 }

        memFree                 OBJECT-TYPE
                SYNTAX  INTEGER
                ACCESS  read-only
                STATUS  mandatory
                DESCRIPTION
                        "The amount of memory in the free pool (including
                        free video memory). This is the total amount of
                        memory that is not currently in use in the terminal."
                ::= {   statistics 2 }

        memLowMark              OBJECT-TYPE
                SYNTAX  INTEGER
                ACCESS  read-only
                STATUS  mandatory
                DESCRIPTION
                        "The size of the free pool at its smallest since
                        the last time this counter was reset."
                ::= {   statistics 3 }

        memFrags                OBJECT-TYPE
                SYNTAX  INTEGER
                ACCESS  read-only
                STATUS  mandatory
                DESCRIPTION
                        "The number of fragments (of all sizes) in the
                        memory free pool."
                ::= {   statistics 4 }

        memLargestFrag          OBJECT-TYPE
                SYNTAX  INTEGER
                ACCESS  read-only
                STATUS  mandatory
                DESCRIPTION
                        "The size of the largest fragment in the free pool
                        in Kbytes. This represents the largest request for
                        memory that can be fulfilled by the terminal."
                ::= {   statistics 5 }

        memBackingstore         OBJECT-TYPE
                SYNTAX  INTEGER
                ACCESS  read-only
                STATUS  mandatory
                DESCRIPTION
                        "The amount of memory used for backingstore in
                        Kbytes."
                ::= {   statistics 6 }

        memReclaims            OBJECT-TYPE
                SYNTAX  Counter
                ACCESS  read-only
                STATUS  mandatory
                DESCRIPTION
                        "The number of times memory has been reclaimed
                        from backing store for other uses."
                ::= {   statistics 7 }

        serialInOctets          OBJECT-TYPE
                SYNTAX  Counter
                ACCESS  read-only
                STATUS  mandatory
                DESCRIPTION
                        "The number of octets received through the serial
                        port since the last time this counter was reset."
                ::= {   statistics 8 }

        serialOutOctets         OBJECT-TYPE
                SYNTAX  Counter
                ACCESS  read-only
                STATUS  mandatory
                DESCRIPTION
                        "The number of octets sent out the serial port since
                        The last time this counter was reset."
                ::= {   statistics 9 }

        serialInErrors          OBJECT-TYPE
                SYNTAX  Counter
                ACCESS  read-only
                STATUS  mandatory
                DESCRIPTION
                        "The number of errors detected on data received
                        in the serial port."
                ::= {   statistics 10 }

        parallelOutOctets       OBJECT-TYPE
                SYNTAX  Counter
                ACCESS  read-only
                STATUS  mandatory
                DESCRIPTION
                        "The number of octets sent out the parallel port
                        since the last time this counter was reset."
                ::= {   statistics 11 }

        parallelErrors          OBJECT-TYPE
                SYNTAX  Counter
                ACCESS  read-only
                STATUS  mandatory
                DESCRIPTION
                        "The number of errors detected in sending data
                        out the parallel port since the last time this
                        counter was reset."
                ::= {   statistics 12 }

        etherInPackets          OBJECT-TYPE
                SYNTAX  Counter
                ACCESS  read-only
                STATUS  mandatory
                DESCRIPTION
                        "The number of packets received over Ethernet."
                ::= {   statistics 13 }

        etherInCRCErrors        OBJECT-TYPE
                SYNTAX  Counter
                ACCESS  read-only
                STATUS  mandatory
                DESCRIPTION
                        "The number of CRC errors detected in Ethernet
                        packets."
                ::= {   statistics 14 }

        etherInNoBuffers        OBJECT-TYPE
                SYNTAX  Counter
                ACCESS  read-only
                STATUS  mandatory
                DESCRIPTION
                        "The number of time the Ethernet interface hardware
                        could not receive packets because no buffers were
                        available."
                ::= {   statistics 15 }

        etherInRunts            OBJECT-TYPE
                SYNTAX  Counter
                ACCESS  read-only
                STATUS  mandatory
                DESCRIPTION
                        "The number of packets received on the Ethernet
                        interface that were shorter then the shortest
                        permitted packet."
                ::= {   statistics 16 }

        etherInOctets           OBJECT-TYPE
                SYNTAX  Counter
                ACCESS  read-only
                STATUS  mandatory
                DESCRIPTION
                        "The number of octets received on the Ethernet
                        interface."
                ::= {   statistics 17 }

        etherOutPackets         OBJECT-TYPE
                SYNTAX  Counter
                ACCESS  read-only
                STATUS  mandatory
                DESCRIPTION
                        "The number of packets sent out the Ethernet
                        interface."
                ::= {   statistics 18 }

        etherOutOneCollisions    OBJECT-TYPE
                SYNTAX  Counter
                ACCESS  read-only
                STATUS  mandatory
                DESCRIPTION
                        "The number of times the Ethernet interface had
                        to back off once due to a collision."
                ::= {   statistics 19 }

        etherOutTwoCollisions    OBJECT-TYPE
                SYNTAX  Counter
                ACCESS  read-only
                STATUS  mandatory
                DESCRIPTION
                        "The number of times the Ethernet interface had
                        to back off twice due to collisions."
                ::= {   statistics 20 }

        etherOutMoreCollisions  OBJECT-TYPE
                SYNTAX  Counter
                ACCESS  read-only
                STATUS  mandatory
                DESCRIPTION
                        "The number of messages for which the Ethernet
                        interface had to back off more then twice (but less
                        then the maximum number of times) due to collisions."
                ::= {   statistics 21 }

        etherOutMaxCollisions   OBJECT-TYPE
                SYNTAX  Counter
                ACCESS  read-only
                STATUS  mandatory
                DESCRIPTION
                        "The number of times that the Ethernet interface
                        was unable to transmit a packet due to too many
                        collisions."
                ::= {   statistics 22 }

        etherOutNoBuffers       OBJECT-TYPE
                SYNTAX  Counter
                ACCESS  read-only
                STATUS  mandatory
                DESCRIPTION
                        "The number of times that the Ethernet interface
                        software had to drop an outbound packet because
                        there were no more interface transmit buffers."
                ::= {   statistics 23 }

        etherOutOctets          OBJECT-TYPE
                SYNTAX  Counter
                ACCESS  read-only
                STATUS  mandatory
                DESCRIPTION
                        "The number of octets sent out the Ethernet
                        interface."
                ::= {   statistics 24 }

        tftpTimeouts            OBJECT-TYPE
                SYNTAX  Counter
                ACCESS  read-only
                STATUS  mandatory
                DESCRIPTION
                        "The number of times that the tftp driver has not
                        gotten a response within the file timeout period.
                        This is not the number of retransmits performed by
                        the tftp driver but is the number of completely
                        failed requests."
                ::= {   statistics 25 }

        statsTime               OBJECT-TYPE
                SYNTAX  TimeTicks
                ACCESS  read-only
                STATUS  mandatory
                DESCRIPTION
                        "The statistics information can be cleared (to zero)
                        by depressing a button on the statistics
                        screen. This variable indicates the time since this
                        was last done. It is the amount of time over which
                        statistics have been collected."
                ::= {   statistics 26 }

        slipInPackets           OBJECT-TYPE
                SYNTAX  Counter
                ACCESS  read-only
                STATUS  mandatory
                DESCRIPTION
                        "The number of packets received over the serial
                        interface while running SLIP."
                ::= {   statistics 27 }

        slipInOctets            OBJECT-TYPE
                SYNTAX  Counter
                ACCESS  read-only
                STATUS  mandatory
                DESCRIPTION
                        "The number of octets received over the serial
                        interface while running SLIP."
                ::= {   statistics 28 }

        slipInErrs              OBJECT-TYPE
                SYNTAX  Counter
                ACCESS  read-only
                STATUS  mandatory
                DESCRIPTION
                        "The number of errors encountered on received octets
                        on the serial interface while running SLIP."
                ::= {   statistics 29 }

        slipOutPackets          OBJECT-TYPE
                SYNTAX  Counter
                ACCESS  read-only
                STATUS  mandatory
                DESCRIPTION
                        "The number of packets transmitted over the serial
                        interface while running SLIP."
                ::= {   statistics 30 }

        slipOutOctets           OBJECT-TYPE
                SYNTAX  Counter
                ACCESS  read-only
                STATUS  mandatory
                DESCRIPTION
                        "The number of octets transmitted over the serial
                        interface while running SLIP."
                ::= {   statistics 31 }

        slipOutErrors              OBJECT-TYPE
                SYNTAX  Counter
                ACCESS  read-only
                STATUS  mandatory
                DESCRIPTION
                        "The number of errors encountered while transmitting
                        over the serial interface while running SLIP."
                ::= {   statistics 32 }

        etherInAlignErrors            OBJECT-TYPE
                SYNTAX  Counter
                ACCESS  read-only
                STATUS  mandatory
                DESCRIPTION
                        "The number of packets received on the Ethernet
                        interface that were not an integral number of
			octets in length."
                ::= {   statistics 33 }

        etherInCollisions            OBJECT-TYPE
                SYNTAX  Counter
                ACCESS  read-only
                STATUS  mandatory
                DESCRIPTION
                        "The number of collisions detected on the Ethernet
                        interface that were after the start of the normal
                        packet."
                ::= {   statistics 34 }

        clientAuthentication            OBJECT-TYPE
                SYNTAX  INTEGER {
                        disabled(1),
                        enabled(2)
                        }
                ACCESS  read-write
                STATUS  mandatory
                DESCRIPTION
                        "Controls whether MIT-MAGIC-COOKIE authentication
                        is used by the server during client connection. If
                        enabled, the client must pass a valid MAGIC_COOKIE
                        to the server during the connection sequence. This
                        feature can only be used with XDMCP enabled."
                ::= {   preferences 1 }

        accessControls          OBJECT-TYPE
                SYNTAX  INTEGER {
                        disabled(1),
                        enabled(2)
                        }
                ACCESS  read-write
                STATUS  mandatory
                DESCRIPTION
                        "This determines whether host access controls are used
                        by the server during client connection. If enabled, only
                        those clients running on hosts listed in the terminal's
                        access control file will be allowed to connect
                        to the X server. This file is read from the host using
                        the path
                        /usr/tftpdir/usr/lib/X11/700X/etc/ipaddress.hosts."
                ::= {   preferences 2 }

        r3BugCompatability              OBJECT-TYPE
                SYNTAX  INTEGER {
                        disabled(1),
                        enabled(2)
                        }
                ACCESS  read-write
                STATUS  mandatory
                DESCRIPTION
                        "This determines whether the server behaves like an
                        X11R3 server for certain specific operations."
                ::= {   preferences 3 }

        resetEnable          OBJECT-TYPE
                SYNTAX  INTEGER {
                        enabled(1),
                        disabled(2)
                        }
                ACCESS  read-write
                STATUS  mandatory
                DESCRIPTION
			"This variable indicates whether remote (through
			SNMP) resets are allowed."
                ::= {   reset 1 }

        reboot          OBJECT-TYPE
                SYNTAX  INTEGER {
                        reset(1),
                        dont(2)
                        }
                ACCESS  read-write
                STATUS  mandatory
                DESCRIPTION
			"Setting this variable to zero will cause the
			X terminal to reset."
                ::= {   reset 2 }

       END
