-- ==================================================================
-- Copyright (c) 2010-2013 Hewlett-Packard Development Company, L.P.
--
-- Description: Loopback detection MIB
-- Reference:
-- Version: V1.1
-- History:
-- V1.0 2008-09-27 Created by LuoXuefang
-- V1.1 2009-03-30 Added hpnicfLpbkdtTrapPerVlanLoopbacked,
--                 hpnicfLpbkdtTrapPerVlanRecovered and
--                 hpnicfLpbkdtObjects by TongWei.
-- ==================================================================
HPN-ICF-LPBKDT-MIB DEFINITIONS ::= BEGIN

IMPORTS
    hpnicfCommon
        FROM HPN-ICF-OID-MIB
    ifIndex, ifDescr
        FROM IF-MIB
    VlanId
        FROM Q-BRIDGE-MIB
    OBJECT-TYPE, MODULE-IDENTITY, NOTIFICATION-TYPE
        FROM SNMPv2-SMI;

hpnicfLpbkdt MODULE-IDENTITY
    LAST-UPDATED "200903301741Z"        -- March 30, 2009 at 17:41 GMT
    ORGANIZATION
        ""
    CONTACT-INFO
        ""
    DESCRIPTION
        "Loops may cause broadcast storms.  The purpose of loopback detection
         is to detect loops on the device and to protect the network."

    REVISION "200903301741Z"
    DESCRIPTION
        "To fix bugs in the MIB file."
    REVISION "200809271504Z"
    DESCRIPTION
        "The initial revision of this MIB module."
    ::= { hpnicfCommon 95 }

-- ==================================================================
--
-- ======================= definition begin =========================
--
-- ==================================================================

hpnicfLpbkdtNotifications OBJECT IDENTIFIER ::= { hpnicfLpbkdt 1 }
hpnicfLpbkdtObjects       OBJECT IDENTIFIER ::= { hpnicfLpbkdt 2 }
hpnicfLpbkdtTrapPrefix    OBJECT IDENTIFIER ::= { hpnicfLpbkdtNotifications 0 }

hpnicfLpbkdtTrapLoopbacked NOTIFICATION-TYPE
    OBJECTS { ifIndex, ifDescr }
    STATUS current
    DESCRIPTION
        "Trap message is generated when the interface is looped."
    ::= { hpnicfLpbkdtTrapPrefix 1 }

hpnicfLpbkdtTrapRecovered NOTIFICATION-TYPE
    OBJECTS { ifIndex, ifDescr }
    STATUS current
    DESCRIPTION
        "Trap message is generated when the loops on the interface
         are eliminated."
    ::= { hpnicfLpbkdtTrapPrefix 2 }

hpnicfLpbkdtTrapPerVlanLoopbacked NOTIFICATION-TYPE
    OBJECTS { ifIndex, ifDescr, hpnicfLpbkdtVlanID }
    STATUS current
    DESCRIPTION
        "Trap message is generated when the interface is looped in the VLAN."
    ::= { hpnicfLpbkdtTrapPrefix 3 }

hpnicfLpbkdtTrapPerVlanRecovered NOTIFICATION-TYPE
    OBJECTS { ifIndex, ifDescr, hpnicfLpbkdtVlanID }
    STATUS current
    DESCRIPTION
        "Trap message is generated when the loop on the interface
         is eliminated in the VLAN."
    ::= { hpnicfLpbkdtTrapPrefix 4 }

hpnicfLpbkdtVlanID OBJECT-TYPE
    SYNTAX      VlanId
    MAX-ACCESS  accessible-for-notify
    STATUS      current
    DESCRIPTION
        "The ID of VLAN."
    ::= { hpnicfLpbkdtObjects 1 }

END
