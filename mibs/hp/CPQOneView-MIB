-- ****************************************************************************
--
--                           OneView
--         Management Information Base for SNMP Network Management
--
--
--      (C) Copyright 2015 Hewlett Packard Enterprise Development L.P.
--
--      Hewlett-Packard Company shall not be liable for technical or
--      editorial errors or omissions contained herein. The information in
--      this document is provided "as is" without warranty of any kind and
--      is subject to change without notice. The warranties for HP products
--      are set forth in the express limited warranty statements
--      accompanying such products. Nothing herein should be construed as
--      constituting an additional warranty.
--
--      Confidential computer software. Valid license from HP required for
--      possession, use or copying. Consistent with FAR 12.211 and 12.212,
--      Commercial Computer Software, Computer Software Documentation, and
--      Technical Data for Commercial Items are licensed to the U.S.
--      Government under vendor's standard commercial license.
--
--      Refer to the READMIB.RDM file for more information about the
--      organization of the information in the Compaq Enterprise.
--
--      The Compaq Enterprise number is 232.
--      The ASN.1 prefix to, and including the Compaq Enterprise is:
--           1.3.6.1.4.1.232
--
-- ****************************************************************************

CPQOneView-MIB DEFINITIONS ::= BEGIN

    IMPORTS
        compaq                  FROM CPQHOST-MIB
        DisplayString           FROM RFC1213-MIB
        OBJECT-TYPE             FROM RFC-1212
        sysName                 FROM RFC1213-MIB
        cpqHoTrapFlags          FROM CPQHOST-MIB
        TRAP-TYPE               FROM RFC-1215
 --       enterprises             FROM COMPAQ
        NetworkAddress          FROM RFC1155-SMI;

 --   compaq                  OBJECT IDENTIFIER ::= { enterprises 232 }
    cpqOneView              OBJECT IDENTIFIER ::= { compaq 179 }
    cpqOneViewMibRev        OBJECT IDENTIFIER ::= { cpqOneView 1 }
    cpqOneViewComponent     OBJECT IDENTIFIER ::= { cpqOneView 2 }
    cpqOneViewAlert         OBJECT IDENTIFIER ::= { cpqOneViewComponent 1 }
    cpqOneViewAlertDeviceHealth        OBJECT IDENTIFIER ::= { cpqOneViewAlert 100 }

-- ****************************************************************************
--   OneView MIB Revision
--   ===============================
--
-- The compaq enterprise               (1.3.6.1.4.1.232)
--      cpqOneView Group                   (1.3.6.1.4.1.232.179)
--       cpqOneViewMibRev Group             (1.3.6.1.4.1.232.179.1)
--
--
--     An Agent conforming to this document will return a
--     cpqOneViewMibRevmajor of one (1) and a cpqOneViewMibRevMinor of zero-zero (00).
--
-- ****************************************************************************

    cpqOneViewMibRevMajor OBJECT-TYPE
        SYNTAX  INTEGER (1..65535)
        ACCESS  read-only
        STATUS  mandatory
        DESCRIPTION
            "The major revision level of the MIB.

            A change in the major revision level represents a major change
            in the architecture of the MIB.  A change in the major revision
            level may indicate a significant change in the information
            supported and/or the meaning of the supported information,
            correct interpretation of data may require a MIB document with
            the same major revision level."
        ::= { cpqOneViewMibRev 1 }

    cpqOneViewMibRevMinor OBJECT-TYPE
        SYNTAX  INTEGER (0..65535)
        ACCESS  read-only
        STATUS  mandatory
        DESCRIPTION
            "The minor revision level of the MIB.

            A change in the minor revision level may represent some minor
            additional support, no changes to any pre-existing information
            has occurred."
        ::= { cpqOneViewMibRev 2 }

    cpqOneViewMibCondition OBJECT-TYPE
        SYNTAX  INTEGER {
            other(1),
            ok(2),              -- default
            degraded(3),
            failed(4)
            }
        ACCESS  read-only
        STATUS  mandatory
        DESCRIPTION
            "The overall condition.

            This object represents the overall status of the
            information represented by this MIB."
        ::= { cpqOneViewMibRev 3 }



-- ****************************************************************************
--   OneView Alert Group
--   ===========================================
--
-- The compaq enterprise                    (1.3.6.1.4.1.232)
--      cpqOneView Group                    (1.3.6.1.4.1.232.179)
--       cpqOneViewComponent Group          (1.3.6.1.4.1.232.179.2)
--        cpqOneViewAlert Group             (1.3.6.1.4.1.232.179.2.1)
--
--  The cpqOneViewAlert group describes alerts forwarded from HP OneView.
--
-- ****************************************************************************


     cpqOneViewAlertSummary OBJECT-TYPE
         SYNTAX  DisplayString
         ACCESS  read-only
         STATUS  optional
         DESCRIPTION
            "The Alert string from HP OneView."
         ::= { cpqOneViewAlert 1 }

     cpqOneViewAlertResolution OBJECT-TYPE
         SYNTAX  DisplayString
         ACCESS  read-only
         STATUS  optional
         DESCRIPTION
            "The alert resolution string from HP OneView."
         ::= { cpqOneViewAlert 2 }

     cpqOneViewAlertCategory OBJECT-TYPE
         SYNTAX  DisplayString
         ACCESS  read-only
         STATUS  optional
         DESCRIPTION
            "The hardware category for the alert from HP OneView."
         ::= { cpqOneViewAlert 3 }

     cpqOneViewAlertState OBJECT-TYPE
         SYNTAX  DisplayString
         ACCESS  read-only
         STATUS  optional
         DESCRIPTION
            "The state for the alert. For example, cleared or active."
         ::= { cpqOneViewAlert 4 }

     cpqOneViewAlertIsLifecycle OBJECT-TYPE
         SYNTAX  DisplayString
         ACCESS  read-only
         STATUS  optional
         DESCRIPTION
            "The value for the alert lifecycle flag: true or false."
         ::= { cpqOneViewAlert 5 }

     cpqOneViewAlertResourceType OBJECT-TYPE
         SYNTAX  DisplayString
         ACCESS  read-only
         STATUS  optional
         DESCRIPTION
            "The resource type associated with the alert."
         ::= { cpqOneViewAlert 6 }

     cpqOneViewAlertResourceUri OBJECT-TYPE
         SYNTAX  DisplayString
         ACCESS  read-only
         STATUS  optional
         DESCRIPTION
            "The resource URI from the OneView alert."
         ::= { cpqOneViewAlert 7 }

     cpqOneViewAlertCreatedTime OBJECT-TYPE
         SYNTAX  DisplayString
         ACCESS  read-only
         STATUS  optional
         DESCRIPTION
             "The time the alert was created."
         ::= { cpqOneViewAlert 8 }


-- ****************************************************************************
--   OneViewDevice Health Alert Group
--   ===========================================
--
-- The compaq enterprise                    (1.3.6.1.4.1.232)
--      cpqOneView Group                    (1.3.6.1.4.1.232.179)
--       cpqOneViewComponent Group          (1.3.6.1.4.1.232.179.2)
--        cpqOneViewAlert Group             (1.3.6.1.4.1.232.179.2.1)
--         cpqOneViewDeviceHlthAlert Group (1.3.6.1.4.1.232.179.2.1.100)
--
--  The cpqOneViewDeviceHlthAlert group describes device health related alerts forwarded from HP OneView.
--
-- ****************************************************************************
     cpqOneViewAlertSourceIPv4Address OBJECT-TYPE
	          SYNTAX  NetworkAddress
	          ACCESS  read-only
	          STATUS  optional
	          DESCRIPTION
	             "The IPv4 Address of the system associated with the OneView alert"
         ::= { cpqOneViewAlertDeviceHealth 1 }

    cpqOneViewAlertSourceIPv6Address OBJECT-TYPE
	          SYNTAX  NetworkAddress
	          ACCESS  read-only
	          STATUS  optional
	          DESCRIPTION
	             "The IPv6 Address of the system associated with the OneView alert"
         ::= { cpqOneViewAlertDeviceHealth 2 }

    cpqOneViewAlertEnterpriseId OBJECT-TYPE
     	          SYNTAX  DisplayString
     	          ACCESS  read-only
     	          STATUS  optional
     	          DESCRIPTION
     	             "This value specifies the enterprise specific ID of the
              forwarded alert."
         ::= { cpqOneViewAlertDeviceHealth 3 }

    cpqOneViewAlertTypeId OBJECT-TYPE
                SYNTAX  INTEGER
                ACCESS  read-only
                STATUS  optional
                DESCRIPTION
                     "This value specifies the specific ID or name of the
              forwarded alert."
         ::= { cpqOneViewAlertDeviceHealth 4 }

cpqOneViewAlertInfo OBJECT-TYPE
                SYNTAX  INTEGER
                ACCESS  read-only
                STATUS  optional
                DESCRIPTION
                     "This value specifies all the varbinds of the trap for forwarded snmp alert in Json String format.For RIS alert this field does not contain any value as of today."
         ::= { cpqOneViewAlertDeviceHealth 5 }


-- ****************************************************************************
--  OneView MIB Trap Definitions
--  ================================
--
--  The SNMP trap messages must not be bigger than 484 octets (bytes).
--
--  Trap support in an SNMP agent implementation is optional.  An SNMP
--  agent implementation may support all, some, or none of the traps.
--  If traps are supported, The user should be provided with the option of
--  disabling traps.
-- **************************************************************************

    cpqOneViewCriticalAlert TRAP-TYPE
        ENTERPRISE compaq
        VARIABLES  { sysName,
                     cpqOneViewAlertCategory,
                     cpqOneViewAlertState,
                     cpqOneViewAlertSummary,
                     cpqOneViewAlertResolution,
			         cpqOneViewAlertIsLifecycle,
                     cpqOneViewAlertCreatedTime,
                     cpqOneViewAlertResourceType,
                     cpqOneViewAlertResourceUri,
                     cpqOneViewAlertSourceIPv4Address,
			         cpqOneViewAlertSourceIPv6Address,
				     cpqOneViewAlertEnterpriseId,
                     cpqOneViewAlertTypeId,
				     cpqOneViewAlertInfo
					 }
        DESCRIPTION
           "Critical Alert received from HP OneView."

        --#TYPE "OneView Critical Alert"
        --#SUMMARY "Alert with status of Critical received from HP OneView."
        --#ARGUMENTS {}
        --#SEVERITY CRITICAL
        --#TIMEINDEX 99
        --#STATE DEGRADED
        --#SIMPLE_SEVERITY CRITICAL
        --#HWSTATUS_CATEGORY NONE

        ::= 179001

    cpqOneViewWarningAlert TRAP-TYPE
        ENTERPRISE compaq
        VARIABLES  { sysName,
                     cpqOneViewAlertCategory,
                     cpqOneViewAlertState,
                     cpqOneViewAlertSummary,
                     cpqOneViewAlertResolution,
			         cpqOneViewAlertIsLifecycle,
                     cpqOneViewAlertCreatedTime,
                     cpqOneViewAlertResourceType,
                     cpqOneViewAlertResourceUri,
                     cpqOneViewAlertSourceIPv4Address,
			         cpqOneViewAlertSourceIPv6Address,
				     cpqOneViewAlertEnterpriseId,
                     cpqOneViewAlertTypeId,
				     cpqOneViewAlertInfo}
        DESCRIPTION
            "Warning alert received from HP OneView."

        --#TYPE "OneView Warning Alert"
        --#SUMMARY "Alert with status of Warning received from HP OneView."
        --#ARGUMENTS {}
        --#SEVERITY MAJOR
        --#TIMEINDEX 99
        --#STATE DEGRADED
        --#SIMPLE_SEVERITY MAJOR
        --#HWSTATUS_CATEGORY NONE

        ::=  179002


     cpqOneViewOkAlert TRAP-TYPE
        ENTERPRISE compaq
        VARIABLES  { sysName,
                     cpqOneViewAlertCategory,
                     cpqOneViewAlertState,
                     cpqOneViewAlertSummary,
                     cpqOneViewAlertResolution,
			         cpqOneViewAlertIsLifecycle,
                     cpqOneViewAlertCreatedTime,
                     cpqOneViewAlertResourceType,
                     cpqOneViewAlertResourceUri,
                     cpqOneViewAlertSourceIPv4Address,
			         cpqOneViewAlertSourceIPv6Address,
			         cpqOneViewAlertEnterpriseId,
                     cpqOneViewAlertTypeId,
				     cpqOneViewAlertInfo}
        DESCRIPTION
            "OK alert received from HP OneView."

        --#TYPE "OneView OK Alert"
        --#SUMMARY "Alert with status of OK received from HP OneView."
        --#ARGUMENTS {}
        --#SEVERITY INFORMATIONAL
        --#TIMEINDEX 99
        --#STATE OPERATIONAL
        --#SIMPLE_SEVERITY OK
        --#HWSTATUS_CATEGORY NONE

       ::=  179003


     cpqOneViewUnknownAlert TRAP-TYPE
        ENTERPRISE compaq
        VARIABLES  { sysName,
                     cpqOneViewAlertCategory,
                     cpqOneViewAlertState,
                     cpqOneViewAlertSummary,
                     cpqOneViewAlertResolution,
			         cpqOneViewAlertIsLifecycle,
                     cpqOneViewAlertCreatedTime,
                     cpqOneViewAlertResourceType,
                     cpqOneViewAlertResourceUri,
                     cpqOneViewAlertSourceIPv4Address,
			         cpqOneViewAlertSourceIPv6Address,
			         cpqOneViewAlertEnterpriseId,
                     cpqOneViewAlertTypeId,
				     cpqOneViewAlertInfo}
        DESCRIPTION
            "Unknown alert received from HP OneView."

        --#TYPE "OneView Unknown Alert"
        --#SUMMARY "Alert with unknown status received from HP OneView."
        --#ARGUMENTS {}
        --#SEVERITY INFORMATIONAL
        --#TIMEINDEX 99
        --#STATE OPERATIONAL
        --#SIMPLE_SEVERITY UNKNOWN
        --#HWSTATUS_CATEGORY NONE

       ::=  179004

END
