-- ****************************************************************************
--                HP NetServer Parse Log SNMP agent Information
--        Management Information Base for SNMP Network Management
--
--      Copyright 1998 Hewlett Packard Company.
--      All Rights Reserved.
--
--      The information in this document is subject to change without notice.
--
--      The hp Enterprise number is 11.
--      The ASN.1 prefix to, and including the hp Enterprise is:
--              1.3.6.1.4.1.11
--
-- hp   (1.3.6.1.4.1.11)
--    nm   (1.3.6.1.4.1.11.2)
--       hpnsa  (1.3.6.1.4.1.11.2.23)
--          hpSELAgt Group  (1.3.6.1.4.1.11.2.23.29)
--             hpSELAgtVersion		(1.3.6.1.4.1.11.2.23.29.1)
--             hpSELAgtRevision		(1.3.6.1.4.1.11.2.23.29.2)
--             hpSELAgtMibVersion	(1.3.6.1.4.1.11.2.23.29.3)
--             hpSELAgtMibRevision  (1.3.6.1.4.1.11.2.23.29.4)
--             hpSELAgtNumEntries   (1.3.6.1.4.1.11.2.23.29.5)
--             hpSELAgtLogTable		(1.3.6.1.4.1.11.2.23.29.6)
--                hpSELAgtLogEntry			(1.3.6.1.4.1.11.2.23.29.6.1)
--                   hpSELAgtIndex          (1.3.6.1.4.1.11.2.23.29.6.1.1)
--                   hpSELAgtRecordID	    (1.3.6.1.4.1.11.2.23.29.6.1.2)
--                   hpSELAgtRecordType     (1.3.6.1.4.1.11.2.23.29.6.1.3)
--                   hpSELAgtTimestamp      (1.3.6.1.4.1.11.2.23.29.6.1.4)
--                   hpSELAgtGeneratorID    (1.3.6.1.4.1.11.2.23.29.6.1.5)
--                   hpSELAgtGeneratorLUN   (1.3.6.1.4.1.11.2.23.29.6.1.6)
--                   hpSELAgtEventVersion   (1.3.6.1.4.1.11.2.23.29.6.1.7)
--                   hpSELAgtSensorType     (1.3.6.1.4.1.11.2.23.29.6.1.8)
--                   hpSELAgtSensorNumber   (1.3.6.1.4.1.11.2.23.29.6.1.9)
--                   hpSELAgtEventTrigger   (1.3.6.1.4.1.11.2.23.29.6.1.10)
--                   hpSELAgtEventData1     (1.3.6.1.4.1.11.2.23.29.6.1.11)
--                   hpSELAgtEventData2     (1.3.6.1.4.1.11.2.23.29.6.1.12)
--                   hpSELAgtEventData3	    (1.3.6.1.4.1.11.2.23.29.6.1.13)
--                   hpSELAgtLineNum        (1.3.6.1.4.1.11.2.23.29.6.1.14)
--					 hpSELAgtStrInfo        (1.3.6.1.4.1.11.2.23.29.6.1.15)
--					 hpSELAgtSeverity       (1.3.6.1.4.1.11.2.23.29.6.1.16)
--             hpSELAgtFilterSensorType		(1.3.6.1.4.1.11.2.23.29.7)
--             hpSELAgtFilterEventTrigger	(1.3.6.1.4.1.11.2.23.29.8)
--             hpSELAgtFilterOffset			(1.3.6.1.4.1.11.2.23.29.9)
--             hpSELAgtLogFile				(1.3.6.1.4.1.11.2.23.29.10)
--
-- ****************************************************************************

HPNSASEL-MIB DEFINITIONS ::= BEGIN
    IMPORTS
        enterprises     FROM RFC1155-SMI
		  DisplayString   FROM RFC1213-MIB
		  OBJECT-TYPE     FROM RFC-1212;

	 hp                   OBJECT IDENTIFIER ::= {enterprises 11}
	 nm                   OBJECT IDENTIFIER ::= {hp 2}
     hpnsa                OBJECT IDENTIFIER ::= {nm 23}
	 hpSELAgt             OBJECT IDENTIFIER ::= {hpnsa 29}


    hpSELAgtVersion OBJECT-TYPE
        SYNTAX  INTEGER (0..65535)
        ACCESS  read-only
        STATUS  mandatory
        DESCRIPTION
		    "The current version (major) number of the SNMP agent."
        ::= { hpSELAgt 1 }

    hpSELAgtRevision OBJECT-TYPE
        SYNTAX  INTEGER (0..65535)
        ACCESS  read-only
        STATUS  mandatory
        DESCRIPTION
		    "The current revision (minor) number of the SNMP agent."
        ::= { hpSELAgt 2 }

    hpSELAgtMibVersion OBJECT-TYPE
        SYNTAX  INTEGER (0..65535)
        ACCESS  read-only
        STATUS  mandatory
        DESCRIPTION
		    "The current version (major) number of the SNMP agent's MIB."
        ::= { hpSELAgt 3 }

    hpSELAgtMibRevision OBJECT-TYPE
        SYNTAX  INTEGER (0..65535)
        ACCESS  read-only
        STATUS  mandatory
        DESCRIPTION
		    "The current revision (minor) number of the SNMP agent's MIB."
        ::= { hpSELAgt 4 }

	hpSELAgtNumEntries OBJECT-TYPE
        SYNTAX  INTEGER (0..65535)
        ACCESS  read-only
        STATUS  mandatory
        DESCRIPTION
		    "The number filtered of log entries."
        ::= { hpSELAgt 5 }

	hpSELAgtLogTable OBJECT-TYPE
        SYNTAX  SEQUENCE OF HpSELAgtLogEntryDef
        ACCESS  not-accessible
        STATUS  mandatory
        DESCRIPTION
		    "A list of filtered log entries."
        ::= { hpSELAgt 6 }

	hpSELAgtLogEntry OBJECT-TYPE
        SYNTAX  HpSELAgtLogEntryDef
        ACCESS  not-accessible
        STATUS  mandatory
        DESCRIPTION
		    ""
		INDEX   { hpSELAgtIndex }
        ::= { hpSELAgtLogTable 1 }

	HpSELAgtLogEntryDef ::= SEQUENCE
		{
				hpSELAgtIndex           INTEGER,
				hpSELAgtRecordID		INTEGER (0..65535),
				hpSELAgtRecordType		INTEGER (0..255),
				hpSELAgtTimestamp		INTEGER,
				hpSELAgtGeneratorID		INTEGER (0..255),
				hpSELAgtGeneratorLUN	INTEGER (0..255),
				hpSELAgtEventVersion	INTEGER (0..255),
				hpSELAgtSensorType		INTEGER (0..255),
				hpSELAgtSensorNumber	INTEGER (0..255),
				hpSELAgtEventTrigger	INTEGER (0..255),
				hpSELAgtEventData1		INTEGER (0..255),
				hpSELAgtEventData2		INTEGER (0..255),
				hpSELAgtEventData3		INTEGER (0..255),
				hpSELAgtLineNum			INTEGER,
				hpSELAgtStrInfo			DisplayString,
				hpSELAgtSeverity        DisplayString
		}

	hpSELAgtIndex OBJECT-TYPE
        SYNTAX  INTEGER
        ACCESS  read-only
        STATUS  mandatory
        DESCRIPTION
		    "The index number of the filtered log entry"
        ::= { hpSELAgtLogEntry 1 }

	hpSELAgtRecordID OBJECT-TYPE
        SYNTAX  INTEGER (0..65535)
        ACCESS  read-only
        STATUS  mandatory
        DESCRIPTION
		    "The record ID of the filtered log entry"
        ::= { hpSELAgtLogEntry 2 }

	hpSELAgtRecordType OBJECT-TYPE
        SYNTAX  INTEGER (0..255)
        ACCESS  read-only
        STATUS  mandatory
        DESCRIPTION
		    "The record type of the filtered log entry"
        ::= { hpSELAgtLogEntry 3 }

	hpSELAgtTimestamp OBJECT-TYPE
        SYNTAX  INTEGER
        ACCESS  read-only
        STATUS  mandatory
        DESCRIPTION
		    "The timestamp of the filtered log entry"
        ::= { hpSELAgtLogEntry 4 }

	hpSELAgtGeneratorID OBJECT-TYPE
        SYNTAX  INTEGER (0..255)
        ACCESS  read-only
        STATUS  mandatory
        DESCRIPTION
		    "The generator ID of the filtered log entry"
        ::= { hpSELAgtLogEntry 5 }

	hpSELAgtGeneratorLUN OBJECT-TYPE
        SYNTAX  INTEGER (0..255)
        ACCESS  read-only
        STATUS  mandatory
        DESCRIPTION
		    "The generator LUN of the filtered log entry"
        ::= { hpSELAgtLogEntry 6 }

	hpSELAgtEventVersion OBJECT-TYPE
        SYNTAX  INTEGER (0..255)
        ACCESS  read-only
        STATUS  mandatory
        DESCRIPTION
		    "The event version of the filtered log entry"
        ::= { hpSELAgtLogEntry 7 }

	hpSELAgtSensorType OBJECT-TYPE
        SYNTAX  INTEGER (0..255)
        ACCESS  read-only
        STATUS  mandatory
        DESCRIPTION
		    "The sensor type of the filtered log entry"
        ::= { hpSELAgtLogEntry 8 }

	hpSELAgtSensorNumber OBJECT-TYPE
        SYNTAX  INTEGER (0..255)
        ACCESS  read-only
        STATUS  mandatory
        DESCRIPTION
		    "The sensor number of the filtered log entry"
        ::= { hpSELAgtLogEntry 9 }

	hpSELAgtEventTrigger OBJECT-TYPE
        SYNTAX  INTEGER (0..255)
        ACCESS  read-only
        STATUS  mandatory
        DESCRIPTION
		    "The event trigger of the filtered log entry"
        ::= { hpSELAgtLogEntry 10 }

	hpSELAgtEventData1 OBJECT-TYPE
        SYNTAX  INTEGER (0..255)
        ACCESS  read-only
        STATUS  mandatory
        DESCRIPTION
		    "The event data 1 of the filtered log entry"
        ::= { hpSELAgtLogEntry 11 }

	hpSELAgtEventData2 OBJECT-TYPE
        SYNTAX  INTEGER (0..255)
        ACCESS  read-only
        STATUS  mandatory
        DESCRIPTION
		    "The event data 2 of the filtered log entry"
        ::= { hpSELAgtLogEntry 12 }

	hpSELAgtEventData3 OBJECT-TYPE
        SYNTAX  INTEGER (0..255)
        ACCESS  read-only
        STATUS  mandatory
        DESCRIPTION
		    "The event data 3 of the filtered log entry"
        ::= { hpSELAgtLogEntry 13 }

	hpSELAgtLineNum OBJECT-TYPE
        SYNTAX  INTEGER
        ACCESS  read-only
        STATUS  mandatory
        DESCRIPTION
		    "The line number in the file of the filtered log entry"
        ::= { hpSELAgtLogEntry 14 }

	hpSELAgtStrInfo OBJECT-TYPE
        SYNTAX  DisplayString
        ACCESS  read-only
        STATUS  mandatory
        DESCRIPTION
		    "Additional information associated with this event"
        ::= { hpSELAgtLogEntry 15 }

	hpSELAgtSeverity OBJECT-TYPE
        SYNTAX  DisplayString
        ACCESS  read-only
        STATUS  mandatory
        DESCRIPTION
		    "The textual severity of this event"
        ::= { hpSELAgtLogEntry 16 }

	hpSELAgtFilterSensorType OBJECT-TYPE
        SYNTAX  INTEGER (0..255)
        ACCESS  read-write
        STATUS  mandatory
        DESCRIPTION
		    "The sensor type to filter."
        ::= { hpSELAgt 7 }

	hpSELAgtFilterEventTrigger OBJECT-TYPE
        SYNTAX  INTEGER (0..255)
        ACCESS  read-write
        STATUS  mandatory
        DESCRIPTION
		    "The event trigger to filter."
        ::= { hpSELAgt 8 }

	hpSELAgtFilterOffset OBJECT-TYPE
        SYNTAX  INTEGER (0..255)
        ACCESS  read-write
        STATUS  mandatory
        DESCRIPTION
		    "The offset to filter."
        ::= { hpSELAgt 9 }

	hpSELAgtLogFile OBJECT-TYPE
        SYNTAX  DisplayString
        ACCESS  read-only
        STATUS  mandatory
        DESCRIPTION
		    "The name of the event log file being accessed."
        ::= { hpSELAgt 10 }

END
