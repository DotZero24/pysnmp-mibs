HP-ICF-IPV6-RA-GUARD-MIB DEFINITIONS ::= BEGIN

    IMPORTS
        hpSwitch
            FROM HP-ICF-OID
        ifIndex
            FROM IF-MIB
        TruthValue
            FROM SNMPv2-TC
        MODULE-COMPLIANCE, OBJECT-GROUP
            FROM SNMPv2-CONF
        Counter64, OBJECT-TYPE, MODULE-IDENTITY
            FROM SNMPv2-SMI
        ;


hpicfIpv6RAGuard MODULE-IDENTITY
    LAST-UPDATED "201103160524Z"
    ORGANIZATION
        "Hewlett-Packard Company
        HP Networking"
    CONTACT-INFO
        "Hewlett-Packard Company
        8000 Foothills Blvd.
        Roseville, CA 95747"
    DESCRIPTION
        "This MIB module contains HP proprietary
        objects for managing RA Guard."
    REVISION "201103160524Z"
    DESCRIPTION
        "Initial revision."

    ::= { hpSwitch 87 }

--
-- Node definitions
--

hpicfIpv6RAGuardObjects OBJECT IDENTIFIER ::= { hpicfIpv6RAGuard 1 }

hpicfIpv6RAGuardConfig OBJECT IDENTIFIER ::= { hpicfIpv6RAGuardObjects 1 }

hpicfRAGuardPortTable OBJECT-TYPE
    SYNTAX SEQUENCE OF HpicfRAGuardPortEntry
    MAX-ACCESS not-accessible
    STATUS current
    DESCRIPTION
        "Per-interface configuration for RA Guard.
         Ra Guard is used to block IPv6 router advertisements
         and ICMPv6 router redirects. The log option is to enable
         debug logging for troubleshooting. It uses a lot of CPU and
         should be used only for short periods of time. To display debug
         logging, use debug security ra-guard command."
    ::= { hpicfIpv6RAGuardConfig 1 }

hpicfRAGuardPortEntry OBJECT-TYPE
    SYNTAX HpicfRAGuardPortEntry
    MAX-ACCESS not-accessible
    STATUS current
    DESCRIPTION
        "RA Guard configuration information for
        a single port."
    INDEX { ifIndex }
    ::= { hpicfRAGuardPortTable 1 }

HpicfRAGuardPortEntry ::=
    SEQUENCE {
        hpicfRAGuardPortBlocked
            TruthValue,
        hpicfRAGuardPortBlockedRAs
            Counter64,
        hpicfRAGuardPortBlockedRedirs
            Counter64,
        hpicfRAGuardPortLog
            TruthValue,
        hpicfRAGuardLastErrorCode
            INTEGER
     }

hpicfRAGuardPortBlocked OBJECT-TYPE
    SYNTAX TruthValue
    MAX-ACCESS read-write
    STATUS current
    DESCRIPTION
        "This object indicates whether this port is
         blocked for Router Advertisements and Redirects."
    ::= { hpicfRAGuardPortEntry 1 }

hpicfRAGuardPortBlockedRAs OBJECT-TYPE
    SYNTAX Counter64
    MAX-ACCESS read-only
    STATUS current
    DESCRIPTION
        "This number of Router Advertisements blocked for the port."
    ::= { hpicfRAGuardPortEntry 2 }

    hpicfRAGuardPortBlockedRedirs OBJECT-TYPE
    SYNTAX Counter64
    MAX-ACCESS read-only
    STATUS current
    DESCRIPTION
        "This number of Router Redirects blocked for the port."
    ::= { hpicfRAGuardPortEntry 3 }

    hpicfRAGuardPortLog OBJECT-TYPE
    SYNTAX TruthValue
    MAX-ACCESS read-write
    STATUS current
    DESCRIPTION
        "Whether to log RAs and Redirects for the port.
        The log option is to enable debug logging for troubleshooting.
        It uses a lot of CPU and should be used only for short periods
        of time."
    ::= { hpicfRAGuardPortEntry 4 }

hpicfRAGuardLastErrorCode OBJECT-TYPE
    SYNTAX INTEGER {
                        noError(1),
                        insufficientHardwareResources(2),
                        genericError(3)
    }
    MAX-ACCESS read-only
    STATUS current
    DESCRIPTION
                    "Error code of the last error that occurred.  A
                    non-zero value indicates that the last operation
                    performed by this instance did not succeed."
    ::= { hpicfRAGuardPortEntry 5 }


-- Conformance information

hpicfIpv6RAGuardConformance OBJECT IDENTIFIER ::= { hpicfIpv6RAGuard  2 }

hpicfIpv6RAGuardCompliances OBJECT IDENTIFIER ::= { hpicfIpv6RAGuardConformance 1 }
hpicfIpv6RAGuardGroups      OBJECT IDENTIFIER ::= { hpicfIpv6RAGuardConformance 2 }


-- units of conformance

   hpicfIpv6RAGuardGroup OBJECT-GROUP
        OBJECTS {
            hpicfRAGuardPortBlocked,
            hpicfRAGuardPortBlockedRAs,
            hpicfRAGuardPortBlockedRedirs,
            hpicfRAGuardPortLog,
            hpicfRAGuardLastErrorCode
        }
        STATUS     current
        DESCRIPTION
          "A collection of objects providing configuration for Ipv6 RA Guard."
       ::= { hpicfIpv6RAGuardGroups 1 }


-- compliance statements

   hpicfIpv6RAGuardCompliance MODULE-COMPLIANCE
       STATUS  current
       DESCRIPTION
           "The compliance statement for devices support of
           HP-ICF-IPV6-RA-GUARD-MIB."
       MODULE -- This Module

          MANDATORY-GROUPS { hpicfIpv6RAGuardGroup }
       ::= { hpicfIpv6RAGuardCompliances 1 }


END
