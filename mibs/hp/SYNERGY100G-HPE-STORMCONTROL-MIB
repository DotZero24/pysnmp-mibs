--    The proprietary MIB definitions follows:
SYNERGY100G-HPE-STORMCONTROL-MIB DEFINITIONS ::= BEGIN

IMPORTS
    MODULE-IDENTITY, OBJECT-TYPE,
    Counter32, Counter64, Unsigned32, TimeTicks, Integer32,enterprises
        FROM SNMPv2-SMI
    RowStatus, TruthValue,TEXTUAL-CONVENTION
        FROM SNMPv2-TC
    ifIndex   FROM IF-MIB
    EnabledStatus
                   FROM P-BRIDGE-MIB
    MODULE-COMPLIANCE, OBJECT-GROUP
        FROM SNMPv2-CONF
	hpVCSE-100Gb-F32-Module
		FROM HPSVRMGMT-OID;

syn100GhpeStormControl MODULE-IDENTITY
    LAST-UPDATED "201603020000Z"
    ORGANIZATION "Hewlett Packard Enterprise"
    CONTACT-INFO "Hewlett Packard Enterprise Support Center
                 www.hpe.com/support<http://www.hpe.com/support>
                 US, Canada & Caribbean: 1-800-633-3600
                 UK & Ireland: 0845 161 0050
                 Asia Pacific Region: 61-3-8877-5000"
    DESCRIPTION "||syn100GhpeStormControl mib||||"
    REVISION "201506260000Z"
    DESCRIPTION "||||||"

::= { syn100GhpeSynergyStormControlMIBObjects 4110}

-- ------------------------------------------------------------
-- groups in the MIB
-- ------------------------------------------------------------

syn100GhpeSynergyStormControlMIBObjects                   OBJECT IDENTIFIER ::= { hpVCSE-100Gb-F32-Module 1 }

syn100GhpeStormControlGroup                               OBJECT IDENTIFIER ::= { syn100GhpeSynergyStormControlMIBObjects 1 }

syn100GhpeStormControlSystemStatus OBJECT-TYPE
        SYNTAX      INTEGER {
                    disable (0),
                    enable(1)
                    }
        MAX-ACCESS  read-write
        STATUS      current
        DESCRIPTION
        " This object is used to enable or disable the StormControl on system.
        When user disables all storm control configurations will be deleted"

        DEFVAL {disable}

        ::= { syn100GhpeStormControlGroup 1 }

syn100GhpeStormControlSystemRateLimitInPps OBJECT-TYPE
        SYNTAX      Integer32
        MAX-ACCESS  read-write
        STATUS      current
        DESCRIPTION
        "Allows to configure the limiting value for the maximum number of broadcast,
        multicast and destination lookup failure packets that can be received per second
        over the interface. Setting this object to the value zero disables rate
        limiting for broadcast,multicast and destination lookup failure packets on all the
        interfaces. The value that can be set for this object is limited by the underlying hardware"

        DEFVAL {0}

        ::= { syn100GhpeStormControlGroup 2 }

syn100GhpeStormControlSystemPollingInterval OBJECT-TYPE
        SYNTAX      Integer32 (5..300)
        UNITS       "Seconds"
        MAX-ACCESS  read-write
        STATUS      current
        DESCRIPTION
        "This object is used to configure the polling time interval in seconds and this timer interval
        is used to read the multicast,broadcast and destination lookup failure drop packets due to
        the rate limit"

        DEFVAL {5}

        ::= { syn100GhpeStormControlGroup 3 }


syn100GhpeStormControlStatsTable  OBJECT-TYPE
        SYNTAX     SEQUENCE OF Syn100GhpeStormControlStatsEntry
        MAX-ACCESS not-accessible
        STATUS     current
        DESCRIPTION
        "A table to get the multicast,broadcast and destination lookup failure drop counters due to
        the rate limit for each physical interface."

        ::= { syn100GhpeStormControlGroup 4 }

syn100GhpeStormControlStatsEntry OBJECT-TYPE
        SYNTAX     Syn100GhpeStormControlStatsEntry
        MAX-ACCESS not-accessible
        STATUS     current
        DESCRIPTION
        "an entry appears in this table for each physical interface."

        INDEX { ifIndex }

        ::= { syn100GhpeStormControlStatsTable 1 }

Syn100GhpeStormControlStatsEntry ::=
        SEQUENCE {
            syn100GhpeStormControlDLFDropCounters     Counter32,
            syn100GhpeStormControlMCASTDropCounters   Counter32,
            syn100GhpeStormControlBCASTDropCounters   Counter32,
            syn100GhpeStormControlIfStatus            INTEGER
            }


syn100GhpeStormControlDLFDropCounters OBJECT-TYPE
        SYNTAX      Counter32
        MAX-ACCESS  read-only
        STATUS      current
        DESCRIPTION
        "An entry to get the received destination lookup failure packet drop counters due to
        the rate limit for the physical interface."

        ::= { syn100GhpeStormControlStatsEntry 1 }

syn100GhpeStormControlMCASTDropCounters OBJECT-TYPE
         SYNTAX      Counter32
         MAX-ACCESS  read-only
         STATUS      current
         DESCRIPTION
         "An entry to get the received multicast packet drop counters due to
         the rate limit for the physical interface."

         ::= { syn100GhpeStormControlStatsEntry 2 }

syn100GhpeStormControlBCASTDropCounters OBJECT-TYPE
         SYNTAX      Counter32
         MAX-ACCESS  read-only
         STATUS      current
         DESCRIPTION
         "An entry to get the received broad cast packet drop counters due to
         the rate limit for the physical interface."

         ::= { syn100GhpeStormControlStatsEntry 3 }

syn100GhpeStormControlIfStatus  OBJECT-TYPE
        SYNTAX      Integer32
        MAX-ACCESS  read-only
        STATUS      current
        DESCRIPTION
        "An entry to get the current drop status of dlf,bacst and mcast for the physical interface.
         The represntation of reason is as follows
         Bit 0 - dlf Drop Reason
         Bit 1 - mcast Drop Reason
         Bit 2 - bcast Drop Reason
         ifExtReasonCode represents the reason code for each Interface for stormcontrol"

         DEFVAL {0}

        ::= { syn100GhpeStormControlStatsEntry 4 }

-- Notifications or Traps

      syn100GhpeStormControlTrap  OBJECT IDENTIFIER ::= {syn100GhpeStormControl 2}

      syn100GhpestormControlTrap  NOTIFICATION-TYPE
            OBJECTS {
                        ifIndex,
                        syn100GhpeStormControlIfStatus
            }
            STATUS       current
            DESCRIPTION  "This trap is generated when bcast,mcast and dlf drop counters are reached
            the configured rate limit within specified polling interval for each physical interface"
            ::= { syn100GhpeStormControlTrap 1 }
END
