-- ****************************************************************************
--
--                         Rack Information MIB
--         Management Information Base for SNMP Network Management
--
--
--      Copyright 2002,2021 Hewlett Packard Enterprise Development LP
--
--      Hewlett-Packard Enterprise Development LP shall not be liable for technical or
--      editorial errors or omissions contained herein. The information in
--      this document is provided "as is" without warranty of any kind and
--      is subject to change without notice. The warranties for HPE products
--      are set forth in the express limited warranty statements
--      accompanying such products. Nothing herein should be construed as
--      constituting an additional warranty.
--
--      Confidential computer software. Valid license from HPE required for
--      possession, use or copying. Consistent with FAR 12.211 and 12.212,
--      Commercial Computer Software, Computer Software Documentation, and
--      Technical Data for Commercial Items are licensed to the U.S.
--      Government under vendor's standard commercial license.
--
--      Refer to the READMIB.RDM file for more information about the
--      organization of the information in the Compaq Enterprise.
--
--      The Compaq Enterprise number is 232.
--      The ASN.1 prefix to, and including the Compaq Enterprise is:
--           1.3.6.1.4.1.232
--
-- ****************************************************************************

CPQRACK-MIB DEFINITIONS ::= BEGIN

    IMPORTS
        compaq                         FROM CPQHOST-MIB
        DisplayString                  FROM RFC1213-MIB
        OBJECT-TYPE                    FROM RFC-1212
        sysName                        FROM RFC1213-MIB
        cpqHoTrapFlags                 FROM CPQHOST-MIB
        TRAP-TYPE                      FROM RFC-1215
        cpqHoOsType                    FROM CPQHOST-MIB
        cpqHoVersion                   FROM CPQHOST-MIB;

--  compaq                             OBJECT IDENTIFIER ::= { enterprises 232 }
    cpqRackInfo                        OBJECT IDENTIFIER ::= { compaq 22 }
    cpqRackMibRev                      OBJECT IDENTIFIER ::= { cpqRackInfo 1 }
    cpqRackComponent                   OBJECT IDENTIFIER ::= { cpqRackInfo 2 }
    cpqRackSysObjID                    OBJECT IDENTIFIER ::= { cpqRackInfo 3 }
    cpqRackEventInfo                   OBJECT IDENTIFIER ::= { cpqRackInfo 4 }

    cpqRackInterface                   OBJECT IDENTIFIER ::= { cpqRackComponent 1 }
    cpqRackAsset                       OBJECT IDENTIFIER ::= { cpqRackComponent 2 }
    cpqRackEnclosure                   OBJECT IDENTIFIER ::= { cpqRackComponent 3 }
    cpqRackServer                      OBJECT IDENTIFIER ::= { cpqRackComponent 4 }
    cpqRackPower                       OBJECT IDENTIFIER ::= { cpqRackComponent 5 }
    cpqRackNetwork                     OBJECT IDENTIFIER ::= { cpqRackComponent 6 }
    cpqRackHW                          OBJECT IDENTIFIER ::= { cpqRackComponent 7 }
    cpqRackErs			       OBJECT IDENTIFIER ::= { cpqRackComponent 8 }
    cpqRackEnvironmental               OBJECT IDENTIFIER ::= { cpqRackComponent 9 }
    cpqRackCdu                         OBJECT IDENTIFIER ::= { cpqRackComponent 10 }

    cpqRackOsCommon                    OBJECT IDENTIFIER ::= { cpqRackInterface 4 }

    cpqRackCommonEnclosure             OBJECT IDENTIFIER ::= { cpqRackEnclosure 1 }
    cpqRackServerEnclosure             OBJECT IDENTIFIER ::= { cpqRackEnclosure 2 }
    cpqRackPowerEnclosure              OBJECT IDENTIFIER ::= { cpqRackEnclosure 3 }

    cpqRackServerBlade                 OBJECT IDENTIFIER ::= { cpqRackServer 1 }
    cpqRackServerNetworking            OBJECT IDENTIFIER ::= { cpqRackServer 2 }
    cpqRackServerTempSensor            OBJECT IDENTIFIER ::= { cpqRackServer 3 }

    cpqRackPowerSupply                 OBJECT IDENTIFIER ::= { cpqRackPower 1 }

    cpqRackPowerMeter                  OBJECT IDENTIFIER ::= { cpqRackPower 2 }

    cpqRackNetConnector                OBJECT IDENTIFIER ::= { cpqRackNetwork 1 }

    cpqRackThermalController           OBJECT IDENTIFIER ::= { cpqRackEnvironmental 1 }

    cpqRackCduApolloController         OBJECT IDENTIFIER ::= { cpqRackCdu 1 }
    cpqRackCduApolloFacilityWater      OBJECT IDENTIFIER ::= { cpqRackCdu 2 }
    cpqRackCduApolloItWater            OBJECT IDENTIFIER ::= { cpqRackCdu 3 }


-- ****************************************************************************
--   Rack Information MIB Revision
--   =============================
--
-- The compaq enterprise               (1.3.6.1.4.1.232)
--      cpqRackInfo Group              (1.3.6.1.4.1.232.22)
--       cpqRackMibRev Group           (1.3.6.1.4.1.232.22.1)
--
--    Implementation of the MibRev group is mandatory for all Agents
--    supporting the Rack Information MIB.
--
--     An Agent conforming to this document will return a
--     cpqRackMibRevMajor of one (1) and a cpqRackMibRevMinor of twenty five (25).
--
--     Added trap cpqRackEnclosureManagerLinkDown (22083)
--     Added trap cpqRackEnclosureManagerLinkUp   (22084)
--     Added group - cpqRackErs in cpqRackComponent
--     Added group - cpqRackEnvironmental in cpqRackComponent
--     Added group - cpqRackCdu in cpqRackComponent
--     Added group - cpqRackCduApolloController in cpqRackCdu
--     Added group - cpqRackCduApolloFacilityWater in cpqRackCdu
--     Added group - cpqRackCduApolloItWater in cpqRackCdu
--     Added group - cpqRackPowerMeter in cpqRackPower
--     Added group - cpqRackThermalController in cpqRackEnvironmental
--     Added trap cpqRackErsCommFailure           (22085)
--     Added trap cpqRackPowerSubsystemOverloadConditionRepaired (22086)
--     Added trap cpqRackPowerSubsystemRedundancyOk                 (22087)
--     Added trap cpqRackNetConnectorTempDegraded                 (22088)
--     Added trap cpqRackNetConnectorTempOk                 (22089)
--     Updated tags SEVERITY,STATE and SIMPLE_SEVERITY in following traps to align with the Trap Condition value in cpqHoTrapFlags -
--     cpqRackEnclosureFanRemoved, cpqRackPowerSupplyRemoved, cpqRackEnclosureManagerRemoved, cpqRackNetConnectorRemoved,
--     cpqRackNetConnectorInserted and cpqRackServerBladeToLowPower
--     Added cpqRackEnvironmental traps 22090-22102
--     Added cpqRackEnvironmental trap 22103 for critcal leak event
--	   Added cpqRackEnvironmentalTrapDescription to thermal controller traps 22092, 22093, 22094, 22095, 22096, 22099, 22100, 22101
--     to describe the sensor alarming and the low and high thresholds
--     Added trap cpqRackPowerSubsystemReductionModeActivate      (22104)
--     Added trap cpqRackPowerSubsystemReductionModeDeactivate     (22105)
--
-- ****************************************************************************

    cpqRackMibRevMajor OBJECT-TYPE
        SYNTAX  INTEGER (1..65535)
        ACCESS  read-only
        STATUS  mandatory
        DESCRIPTION
            "The major revision level of the MIB.

            A change in the major revision level represents a major change
            in the architecture of the MIB.  A change in the major revision
            level may indicate a significant change in the information
            supported and/or the meaning of the supported information,
            correct interpretation of data may require a MIB document with
            the same major revision level."
        ::= { cpqRackMibRev 1 }

    cpqRackMibRevMinor OBJECT-TYPE
        SYNTAX  INTEGER (0..65535)
        ACCESS  read-only
        STATUS  mandatory
        DESCRIPTION
            "The minor revision level of the MIB.

            A change in the minor revision level may represent some minor
            additional support, no changes to any pre-existing information
            has occurred."
        ::= { cpqRackMibRev 2 }

    cpqRackMibCondition OBJECT-TYPE
        SYNTAX  INTEGER {
            other(1),
            ok(2),              -- default
            degraded(3),
            failed(4)
            }
        ACCESS  read-only
        STATUS  mandatory
        DESCRIPTION
            "The overall condition.

            This object represents the overall status of the
            rack information represented by this MIB."
        ::= { cpqRackMibRev 3 }

-- ****************************************************************************
--   Rack Information Common
--   =======================
--
-- The compaq enterprise               (1.3.6.1.4.1.232)
--      cpqRackInfo Group              (1.3.6.1.4.1.232.22)
--       cpqRackComponent Group        (1.3.6.1.4.1.232.22.2)
--        cpqRackInterface Group       (1.3.6.1.4.1.232.22.2.1)
--         cpqRackOsCommon Group       (1.3.6.1.4.1.232.22.2.1.4)
--
--
--  Implementation of the cpqRackOsCommon group is mandatory for all
--  Agents that support the Rack Information MIB.
--
-- ****************************************************************************

    cpqRackOsCommonPollFreq OBJECT-TYPE
        SYNTAX  INTEGER (0..65535)
        ACCESS  read-write
        STATUS  mandatory
        DESCRIPTION
            "The Management Agent's polling frequency.

            The frequency, in seconds, at which the Agent requests
            information from the device driver.  A frequency of zero (0)
            indicates that the Insight Agent retrieves the information upon
            request of a management station, it does not poll the device
            driver at a specific interval.

            If the poll frequency is zero (0) all attempts to write to this
            object will fail.  If the poll frequency is non-zero,
            setting this value will change the polling frequency of the
            Insight Agent.  Setting the poll frequency to zero (0) will
            always fail, an agent may also choose to fail any request to
            change the poll frequency to a value that would severely impact
            system performance."
        ::= { cpqRackOsCommon 1 }


-- ****************************************************************************
--   Rack Asset Group
--   ================
--
-- The compaq enterprise               (1.3.6.1.4.1.232)
--      cpqRackInfo Group              (1.3.6.1.4.1.232.22)
--       cpqRackComponent Group        (1.3.6.1.4.1.232.22.2)
--        cpqRackAsset Group           (1.3.6.1.4.1.232.22.2.2)
--
--  The cpqRackAsset group contains the serial numbers, names, etc. of any
--  Rack hardware that supports asset management.
--
--  Implementation of the cpqRackAsset group is mandatory for all
--  Agents that support the Rack Information MIB.
--
-- ****************************************************************************

-- ****************************************************************************
--   Rack Asset Table
--   ================
--
-- The compaq enterprise               (1.3.6.1.4.1.232)
--      cpqRackInfo Group              (1.3.6.1.4.1.232.22)
--       cpqRackComponent Group        (1.3.6.1.4.1.232.22.2)
--        cpqRackAsset Group           (1.3.6.1.4.1.232.22.2.2)
--         cpqRackAssetTable           (1.3.6.1.4.1.232.22.2.2.1)
--
-- ****************************************************************************

    cpqRackAssetTable OBJECT-TYPE
        SYNTAX  SEQUENCE OF CpqRackAssetEntry
        ACCESS  not-accessible
        STATUS  mandatory
        DESCRIPTION
            "A table of rack asset information."
        ::= { cpqRackAsset 1 }

    cpqRackAssetEntry OBJECT-TYPE
        SYNTAX  CpqRackAssetEntry
        ACCESS  not-accessible
        STATUS  mandatory
        DESCRIPTION
            "A rack asset description."
        INDEX   { cpqRackAssetIndex }
        ::= { cpqRackAssetTable 1 }

    CpqRackAssetEntry ::= SEQUENCE {
        cpqRackAssetIndex           INTEGER,
        cpqRackName                 DisplayString,
        cpqRackUid                  DisplayString,
        cpqRackSerialNum            DisplayString,
        cpqRackTrapSequenceNum      INTEGER,
        cpqRackHeight               INTEGER,
        cpqRackWidth                INTEGER,
        cpqRackDepth                INTEGER
    }

    cpqRackAssetIndex OBJECT-TYPE
        SYNTAX  INTEGER
        ACCESS  read-only
        STATUS  mandatory
        DESCRIPTION
            "A number that uniquely specifies this rack table entry."
        ::= { cpqRackAssetEntry 1 }

    cpqRackName OBJECT-TYPE
        SYNTAX  DisplayString (SIZE (0..64))
        ACCESS  read-only
        STATUS  mandatory
        DESCRIPTION
            "The customer changeable identifier used to identify the entire
            rack.

            The string will be empty if the system does not report this
            function."
        ::= { cpqRackAssetEntry 2 }

    cpqRackUid OBJECT-TYPE
        SYNTAX  DisplayString (SIZE (0..64))
        ACCESS  read-only
        STATUS  mandatory
        DESCRIPTION
            "The rack unique identifier.

            The string will be empty if the rack does not report the
            UID or if it could not be determined."
        ::= { cpqRackAssetEntry 3 }

    cpqRackSerialNum OBJECT-TYPE
        SYNTAX  DisplayString (SIZE (0..64))
        ACCESS  read-only
        STATUS  mandatory
        DESCRIPTION
            "The rack serial number.

            The string will be empty if the rack does not report the
            serial number."
        ::= { cpqRackAssetEntry 4 }

    cpqRackTrapSequenceNum OBJECT-TYPE
        SYNTAX  INTEGER
        ACCESS  read-only
        STATUS  mandatory
        DESCRIPTION
            "The trap sequence number for rack traps.

            This is used by the management application trap processing.

            This will be -1 if the rack does not report the information or
            it could not be determined."
        ::= { cpqRackAssetEntry 5 }

    cpqRackHeight OBJECT-TYPE
        SYNTAX  INTEGER
        ACCESS  read-only
        STATUS  mandatory
        DESCRIPTION
            "The internal height dimension of the useable rack space expressed
            in millimeters.

            This will be -1 if the rack does not report the information or
            it could not be determined."
        ::= { cpqRackAssetEntry 6 }

    cpqRackWidth OBJECT-TYPE
        SYNTAX  INTEGER
        ACCESS  read-only
        STATUS  mandatory
        DESCRIPTION
            "The internal width dimension of the useable rack space expressed
            in millimeters.

            This will be -1 if the rack does not report the information or
            it could not be determined."
        ::= { cpqRackAssetEntry 7 }

    cpqRackDepth OBJECT-TYPE
        SYNTAX  INTEGER
        ACCESS  read-only
        STATUS  mandatory
        DESCRIPTION
            "The internal depth dimension of the useable rack space expressed
            in millimeters.

            This will be -1 if the rack does not report the information or
            it could not be determined."
        ::= { cpqRackAssetEntry 8 }


-- ****************************************************************************
--   Rack Enclosure Chassis Group
--   ============================
--
-- The compaq enterprise               (1.3.6.1.4.1.232)
--      cpqRackInfo Group              (1.3.6.1.4.1.232.22)
--       cpqRackComponent Group        (1.3.6.1.4.1.232.22.2)
--        cpqRackEnclosure Group       (1.3.6.1.4.1.232.22.2.3)
--
--  The cpqRackEnclosure group contains the information about rack
--  enclosures.
--
-- ****************************************************************************

-- ****************************************************************************
--   Rack Common Enclosure Table
--   ===========================
--
-- The compaq enterprise                 (1.3.6.1.4.1.232)
--      cpqRackInfo Group                (1.3.6.1.4.1.232.22)
--       cpqRackComponent Group          (1.3.6.1.4.1.232.22.2)
--        cpqRackEnclosure Group         (1.3.6.1.4.1.232.22.2.3)
--         cpqRackCommonEnclosure Group  (1.3.6.1.4.1.232.22.2.3.1)
--          cpqRackCommonEnclosureTable  (1.3.6.1.4.1.232.22.2.3.1.1)
--
-- ****************************************************************************

    cpqRackCommonEnclosureTable OBJECT-TYPE
        SYNTAX  SEQUENCE OF CpqRackCommonEnclosureEntry
        ACCESS  not-accessible
        STATUS  mandatory
        DESCRIPTION
            "A table of rack enclosure information."
        ::= { cpqRackCommonEnclosure 1 }

    cpqRackCommonEnclosureEntry OBJECT-TYPE
        SYNTAX  CpqRackCommonEnclosureEntry
        ACCESS  not-accessible
        STATUS  mandatory
        DESCRIPTION
            "A rack enclosure description."
        INDEX   { cpqRackCommonEnclosureRack,
                  cpqRackCommonEnclosureIndex }
        ::= { cpqRackCommonEnclosureTable 1 }

    CpqRackCommonEnclosureEntry ::= SEQUENCE {
        cpqRackCommonEnclosureRack                 INTEGER,
        cpqRackCommonEnclosureIndex                INTEGER,
        cpqRackCommonEnclosureModel                DisplayString,
        cpqRackCommonEnclosureAssetTag             DisplayString,
        cpqRackCommonEnclosurePartNumber           DisplayString,
        cpqRackCommonEnclosureSparePartNumber      DisplayString,
        cpqRackCommonEnclosureSerialNum            DisplayString,
        cpqRackCommonEnclosureFWRev                DisplayString,
        cpqRackCommonEnclosureName                 DisplayString,
        cpqRackCommonEnclosureNeighborNamePrev     DisplayString,
        cpqRackCommonEnclosureNeighborNameNext     DisplayString,
        cpqRackCommonEnclosureHeight               INTEGER,
        cpqRackCommonEnclosureWidth                INTEGER,
        cpqRackCommonEnclosureDepth                INTEGER,
        cpqRackCommonEnclosureTrapSequenceNum      INTEGER,
        cpqRackCommonEnclosureCondition            INTEGER,
        cpqRackCommonEnclosureHasServerBlades      INTEGER,
        cpqRackCommonEnclosureHasPowerSupplies     INTEGER,
        cpqRackCommonEnclosureHasNetConnectors     INTEGER,
        cpqRackCommonEnclosureHasTempSensors       INTEGER,
        cpqRackCommonEnclosureHasFans              INTEGER,
        cpqRackCommonEnclosureHasFuses             INTEGER,
        cpqRackCommonEnclosureMgmtUID              INTEGER,
        cpqRackCommonEnclosureSerialNumPrev        DisplayString,
        cpqRackCommonEnclosureSerialNumNext        DisplayString,
        cpqRackCommonEnclosureAddress              INTEGER,
        cpqRackCommonEnclosureProductId            DisplayString,
        cpqRackCommonEnclosureProductIdPrev        DisplayString,
        cpqRackCommonEnclosureProductIdNext        DisplayString,
        cpqRackCommonEnclosureUUID                 DisplayString,
        cpqRackCommonEnclosureUUIDPrev             DisplayString,
        cpqRackCommonEnclosureUUIDNext             DisplayString,
        cpqRackCommonEnclosureHasManagers          INTEGER
    }

    cpqRackCommonEnclosureRack OBJECT-TYPE
        SYNTAX  INTEGER
        ACCESS  read-only
        STATUS  mandatory
        DESCRIPTION
            "A number that uniquely specifies this rack."
        ::= { cpqRackCommonEnclosureEntry 1 }

    cpqRackCommonEnclosureIndex OBJECT-TYPE
        SYNTAX  INTEGER
        ACCESS  read-only
        STATUS  mandatory
        DESCRIPTION
            "A number that uniquely specifies this enclosure in the rack."
        ::= { cpqRackCommonEnclosureEntry 2 }

    cpqRackCommonEnclosureModel OBJECT-TYPE
        SYNTAX  DisplayString (SIZE (0..64))
        ACCESS  read-only
        STATUS  mandatory
        DESCRIPTION
            "The model name of the enclosure.

            The string will be empty if the enclosure does not report the
            model information."
        ::= { cpqRackCommonEnclosureEntry 3 }

    cpqRackCommonEnclosureAssetTag OBJECT-TYPE
        SYNTAX  DisplayString (SIZE (0..64))
        ACCESS  read-only
        STATUS  mandatory
        DESCRIPTION
            "The customer changeable asset identifier of the enclosure.

            The string will be empty if the system does not report this
            function or if the asset tag has not been set."
        ::= { cpqRackCommonEnclosureEntry 4 }

    cpqRackCommonEnclosurePartNumber OBJECT-TYPE
        SYNTAX  DisplayString (SIZE (0..64))
        ACCESS  read-only
        STATUS  mandatory
        DESCRIPTION
            "The part number of the enclosure.

            The string will be empty if the enclosure does not report this
            function."
        ::= { cpqRackCommonEnclosureEntry 5 }

    cpqRackCommonEnclosureSparePartNumber OBJECT-TYPE
        SYNTAX  DisplayString (SIZE (0..64))
        ACCESS  read-only
        STATUS  mandatory
        DESCRIPTION
            "The spare part number of the enclosure.

            The string will be empty if the enclosure does not report this
            function."
        ::= { cpqRackCommonEnclosureEntry 6 }

    cpqRackCommonEnclosureSerialNum OBJECT-TYPE
        SYNTAX  DisplayString (SIZE (0..64))
        ACCESS  read-only
        STATUS  mandatory
        DESCRIPTION
            "The serial number of the enclosure.

            The string will be empty if the enclosure does not report the
            serial number."
        ::= { cpqRackCommonEnclosureEntry 7 }

    cpqRackCommonEnclosureFWRev OBJECT-TYPE
        SYNTAX  DisplayString (SIZE (0..64))
        ACCESS  read-only
        STATUS  mandatory
        DESCRIPTION
            "The firmware revision of the enclosure.

            The string will be empty if the enclosure does not report the
            firmware revision or does not contain firmware."
        ::= { cpqRackCommonEnclosureEntry 8 }

    cpqRackCommonEnclosureName OBJECT-TYPE
        SYNTAX  DisplayString (SIZE (0..64))
        ACCESS  read-only
        STATUS  mandatory
        DESCRIPTION
            "The name of the enclosure.

            The string will be empty if the enclosure does not report the
            name or it could not be determined."
        ::= { cpqRackCommonEnclosureEntry 9 }

    cpqRackCommonEnclosureNeighborNamePrev OBJECT-TYPE
        SYNTAX  DisplayString (SIZE (0..64))
        ACCESS  read-only
        STATUS  mandatory
        DESCRIPTION
            "The name of the enclosure immediately preceding or above this
            enclosure.

            The string will be empty if the neighbor enclosure name could not be
            determined or there is no enclosure preceding this one."
        ::= { cpqRackCommonEnclosureEntry 10 }

    cpqRackCommonEnclosureNeighborNameNext OBJECT-TYPE
        SYNTAX  DisplayString (SIZE (0..64))
        ACCESS  read-only
        STATUS  mandatory
        DESCRIPTION
            "The name of the enclosure immediately following or below this
            enclosure.

            The string will be empty if the neighbor enclosure name could not be
            determined or there is no enclosure following this one."
        ::= { cpqRackCommonEnclosureEntry 11 }

    cpqRackCommonEnclosureHeight OBJECT-TYPE
        SYNTAX  INTEGER
        ACCESS  read-only
        STATUS  mandatory
        DESCRIPTION
            "The height dimension of the rack space taken by the
            enclosure expressed in millimeters.

            This will be -1 if the rack does not report the information or
            it could not be determined."
        ::= { cpqRackCommonEnclosureEntry 12 }

    cpqRackCommonEnclosureWidth OBJECT-TYPE
        SYNTAX  INTEGER
        ACCESS  read-only
        STATUS  mandatory
        DESCRIPTION
            "The width dimension of the rack space taken by the
            enclosure expressed in millimeters.

            This will be -1 if the rack does not report the information or
            it could not be determined."
        ::= { cpqRackCommonEnclosureEntry 13 }

    cpqRackCommonEnclosureDepth OBJECT-TYPE
        SYNTAX  INTEGER
        ACCESS  read-only
        STATUS  mandatory
        DESCRIPTION
            "The depth dimension of the rack space taken by the
            enclosure expressed in millimeters.

            This will be -1 if the rack does not report the information or
            it could not be determined."
        ::= { cpqRackCommonEnclosureEntry 14 }

    cpqRackCommonEnclosureTrapSequenceNum OBJECT-TYPE
        SYNTAX  INTEGER
        ACCESS  read-only
        STATUS  mandatory
        DESCRIPTION
            "The trap sequence number for the enclosure.

            This is used by the management application trap processing.

            This will be -1 if the rack does not report the information or
            it could not be determined."
        ::= { cpqRackCommonEnclosureEntry 15 }

    cpqRackCommonEnclosureCondition OBJECT-TYPE
        SYNTAX  INTEGER {
            other(1),
            ok(2),
            degraded(3),
            failed(4)
            }
        ACCESS  read-only
        STATUS  mandatory
        DESCRIPTION
            "The overall condition of the enclosure.

            This is the aggregate of the temperature sensors, fans, and
            fuses within the enclosure.

            This value will be one of the following:

            other(1)
              No temperature sensors, fans, or fuses in the enclosure or the
              state could no be determined.

            ok(2)
              All temperature sensors, fans, and fuses are within the normal
              operating range.

            degraded(3)
              One or more temperature sensors, fans, or fuses are outside of
              the normal operating range.  None are failed.

            failed(4)
              The temperature sensor exceeded the critical threshold value,
              a required fan has failed, or a fuse has been tripped.

            The system will automatically shutdown if the failed(4) condition
            results, so it is unlikely that this value will ever be returned
            by the agent."
        ::= { cpqRackCommonEnclosureEntry 16 }

    cpqRackCommonEnclosureHasServerBlades OBJECT-TYPE
        SYNTAX  INTEGER {
            false(1),
            true(2)
            }
        ACCESS  read-only
        STATUS  mandatory
        DESCRIPTION
            "The enclosure can contain server blades.

            This will be true(2) is the enclosure can house server blades.  The
            cpqRackServerEnclosureTable will contain server enclosure specific
            information.

            Match the cpqRackCommonEnclosureSerialNum in this table to the
            serial number in the cpqRackServerEnclosureTable to get complete
            information on the server enclosure."
        ::= { cpqRackCommonEnclosureEntry 17 }

    cpqRackCommonEnclosureHasPowerSupplies OBJECT-TYPE
        SYNTAX  INTEGER {
            false(1),
            true(2)
            }
        ACCESS  read-only
        STATUS  mandatory
        DESCRIPTION
            "The enclosure can contain power supplies.

            This will be true(2) is the enclosure can house power supplies.  The
            cpqRackEnclosurePowerTable will contain power enclosure specific
            information.

            Match the cpqRackCommonEnclosureSerialNum in this table to the
            serial number in the cpqRackEnclosurePowerTable to get complete
            information on the power enclosure."
        ::= { cpqRackCommonEnclosureEntry 18 }

    cpqRackCommonEnclosureHasNetConnectors OBJECT-TYPE
        SYNTAX  INTEGER {
            false(1),
            true(2)
            }
        ACCESS  read-only
        STATUS  mandatory
        DESCRIPTION
            "The enclosure contains network connectivity.

            This will be true(2) is the enclosure contains network connectivity.
            The cpqRackCommonEnclosureNetConnectorTable will contain network
            connectivity specific information.

            Match the cpqRackCommonEnclosureSerialNum in this table to the
            serial number in the cpqRackCommonEnclosureNetConnectorTable to get complete
            information on the network connector enclosure."
        ::= { cpqRackCommonEnclosureEntry 19 }

    cpqRackCommonEnclosureHasTempSensors OBJECT-TYPE
        SYNTAX  INTEGER {
            false(1),
            true(2)
            }
        ACCESS  read-only
        STATUS  mandatory
        DESCRIPTION
            "The enclosure contains temperature sensors.

            This will be true(2) is the enclosure contains
            temperature sensors. The cpqRackCommonEnclosureTempTable will
            contain temperature sensor specific information.

            Match the cpqRackCommonEnclosureSerialNum in this table to the
            serial number in the cpqRackCommonEnclosureTempTable to get complete
            information on the enclosure."
        ::= { cpqRackCommonEnclosureEntry 20 }

    cpqRackCommonEnclosureHasFans OBJECT-TYPE
        SYNTAX  INTEGER {
            false(1),
            true(2)
            }
        ACCESS  read-only
        STATUS  mandatory
        DESCRIPTION
            "The enclosure contains fans.

            This will be true(2) is the enclosure contains fans.
            The cpqRackCommonEnclosureFanTable will contain the fan
            specific information.

            Match the cpqRackCommonEnclosureSerialNum in this table to the
            serial number in the cpqRackCommonEnclosureFanTable to get complete
            information on the enclosure."
        ::= { cpqRackCommonEnclosureEntry 21 }

    cpqRackCommonEnclosureHasFuses OBJECT-TYPE
        SYNTAX  INTEGER {
            false(1),
            true(2)
            }
        ACCESS  read-only
        STATUS  mandatory
        DESCRIPTION
            "The enclosure contains fuses.

            This will be true(2) is the enclosure contains fuses.
            The cpqRackCommonEnclosureFuseTable will contain the fuse
            specific information.

            Match the cpqRackCommonEnclosureSerialNum in this table to the
            serial number in the cpqRackCommonEnclosureFuseTable to get complete
            information on the enclosure."
        ::= { cpqRackCommonEnclosureEntry 22 }

    cpqRackCommonEnclosureMgmtUID OBJECT-TYPE
        SYNTAX  INTEGER {
            other(1),            -- Unknown device or could not be determined
            none(2),             -- No Unit Identifier LED present
            ledOn(3),            -- Unit Identifier LED is On
            ledOff(4)            -- Unit Identifier LED is Off
            }
        ACCESS  read-write
        STATUS  mandatory
        DESCRIPTION
            "The Unit Identifier LED.

            This value will be one of the following:

            other(1)
              The state of the LED could not be determined.  Setting the
              LED state is not allowed.

            none(2)
              The LED is not present.  Setting LED state is not allowed.

            ledOn(3)
              The LED is present and ON.  The LED can be turned off
              by setting the cpqRackCommonEnclosureMgmtUID to ledOff(4).

            ledOff(4)
              The LED is present and OFF.  The LED can be turned on
              by setting the cpqRackCommonEnclosureMgmtUID to ledOn(3)."
        ::= { cpqRackCommonEnclosureEntry 23 }

    cpqRackCommonEnclosureSerialNumPrev OBJECT-TYPE
        SYNTAX  DisplayString (SIZE (0..64))
        ACCESS  read-only
        STATUS  mandatory
        DESCRIPTION
            "The serial number of the enclosure immediately preceding or
            above this enclosure.

            The string will be empty if the neighbor enclosure serial number
            could not be determined or there is no enclosure preceding this one."
        ::= { cpqRackCommonEnclosureEntry 24 }

    cpqRackCommonEnclosureSerialNumNext OBJECT-TYPE
        SYNTAX  DisplayString (SIZE (0..64))
        ACCESS  read-only
        STATUS  mandatory
        DESCRIPTION
            "The serial number of the enclosure immediately following or
            below this enclosure.

            The string will be empty if the neighbor enclosure serial number
            could not be determined or there is no enclosure following this one."
        ::= { cpqRackCommonEnclosureEntry 25 }

    cpqRackCommonEnclosureAddress OBJECT-TYPE
        SYNTAX  INTEGER
        ACCESS  read-only
        STATUS  mandatory
        DESCRIPTION
            "The unique address of the enclosure within the rack.

            This will be -1 if the rack does not report the information or
            it could not be determined."
        ::= { cpqRackCommonEnclosureEntry 26 }

    cpqRackCommonEnclosureProductId OBJECT-TYPE
        SYNTAX  DisplayString (SIZE (0..64))
        ACCESS  read-only
        STATUS  mandatory
        DESCRIPTION
            "The product id string of the enclosure.

            The string will be empty if the enclosure does not report the
            product id string."
        ::= { cpqRackCommonEnclosureEntry 27 }

    cpqRackCommonEnclosureProductIdPrev OBJECT-TYPE
        SYNTAX  DisplayString (SIZE (0..64))
        ACCESS  read-only
        STATUS  mandatory
        DESCRIPTION
            "The product id string of the enclosure immediately preceding or
            above this enclosure.

            The string will be empty if the enclosure does not report the
            product id string."
        ::= { cpqRackCommonEnclosureEntry 28 }

    cpqRackCommonEnclosureProductIdNext OBJECT-TYPE
        SYNTAX  DisplayString (SIZE (0..64))
        ACCESS  read-only
        STATUS  mandatory
        DESCRIPTION
            "The product id string of the enclosure immediately following or
            below this enclosure.

            The string will be empty if the enclosure does not report the
            product id string."
        ::= { cpqRackCommonEnclosureEntry 29 }

    cpqRackCommonEnclosureUUID OBJECT-TYPE
        SYNTAX  DisplayString (SIZE (0..64))
        ACCESS  read-only
        STATUS  mandatory
        DESCRIPTION
            "The universal unique identifier string of the enclosure.

            The string will be empty if the enclosure does not report the
            UUID string."
        ::= { cpqRackCommonEnclosureEntry 30 }

    cpqRackCommonEnclosureUUIDPrev OBJECT-TYPE
        SYNTAX  DisplayString (SIZE (0..64))
        ACCESS  read-only
        STATUS  mandatory
        DESCRIPTION
            "The universal unique identifier string of the enclosure
            immediately preceding or above this enclosure.

            The string will be empty if the enclosure does not report the
            UUID string or if there is no preceding enclosure."
        ::= { cpqRackCommonEnclosureEntry 31 }

    cpqRackCommonEnclosureUUIDNext OBJECT-TYPE
        SYNTAX  DisplayString (SIZE (0..64))
        ACCESS  read-only
        STATUS  mandatory
        DESCRIPTION
            "The universal unique identifier string of the enclosure
            immediately following or below this enclosure.

            The string will be empty if the enclosure does not report the
            UUID string or if there is no following enclosure."
        ::= { cpqRackCommonEnclosureEntry 32 }

    cpqRackCommonEnclosureHasManagers OBJECT-TYPE
        SYNTAX  INTEGER {
            false(1),
            true(2)
            }
        ACCESS  read-only
        STATUS  mandatory
        DESCRIPTION
            "The enclosure contains managers.

            This will be true(2) is the enclosure contains managers.
            The cpqRackCommonEnclosureManagerTable will contain the manager
            specific information.

            Match the cpqRackCommonEnclosureSerialNum in this table to the
            serial number in the cpqRackCommonEnclosureManagerTable to get
            complete information on the enclosure."
        ::= { cpqRackCommonEnclosureEntry 33 }


-- ****************************************************************************
--   Rack Enclosure Common Temperature Sensor Table
--   ==============================================
--
-- The compaq enterprise                     (1.3.6.1.4.1.232)
--      cpqRackInfo Group                    (1.3.6.1.4.1.232.22)
--       cpqRackComponent Group              (1.3.6.1.4.1.232.22.2)
--        cpqRackEnclosure Group             (1.3.6.1.4.1.232.22.2.3)
--         cpqRackCommonEnclosure Group      (1.3.6.1.4.1.232.22.2.3.1)
--          cpqRackCommonEnclosureTempTable  (1.3.6.1.4.1.232.22.2.3.1.2)
--
-- ****************************************************************************

    cpqRackCommonEnclosureTempTable OBJECT-TYPE
        SYNTAX  SEQUENCE OF CpqRackCommonEnclosureTempEntry
        ACCESS  not-accessible
        STATUS  mandatory
        DESCRIPTION
            "A table of rack enclosure temperature sensor information."
        ::= { cpqRackCommonEnclosure 2 }

    cpqRackCommonEnclosureTempEntry OBJECT-TYPE
        SYNTAX  CpqRackCommonEnclosureTempEntry
        ACCESS  not-accessible
        STATUS  mandatory
        DESCRIPTION
            "A rack enclosure temperature sensor description."
        INDEX   { cpqRackCommonEnclosureTempRack,
                  cpqRackCommonEnclosureTempChassis,
                  cpqRackCommonEnclosureTempSensorIndex }
        ::= { cpqRackCommonEnclosureTempTable 1 }

    CpqRackCommonEnclosureTempEntry ::= SEQUENCE {
        cpqRackCommonEnclosureTempRack                      INTEGER,
        cpqRackCommonEnclosureTempChassis                   INTEGER,
        cpqRackCommonEnclosureTempSensorIndex               INTEGER,
        cpqRackCommonEnclosureTempSensorEnclosureName       DisplayString,
        cpqRackCommonEnclosureTempLocation                  DisplayString,
        cpqRackCommonEnclosureTempCurrent                   INTEGER,
        cpqRackCommonEnclosureTempThreshold                 INTEGER,
        cpqRackCommonEnclosureTempCondition                 INTEGER,
        cpqRackCommonEnclosureTempType                      INTEGER,
        cpqRackCommonEnclosureTempSensorEnclosureSerialNum  DisplayString
    }

    cpqRackCommonEnclosureTempRack OBJECT-TYPE
        SYNTAX  INTEGER
        ACCESS  read-only
        STATUS  mandatory
        DESCRIPTION
            "A number that uniquely specifies this rack."
        ::= { cpqRackCommonEnclosureTempEntry 1 }

    cpqRackCommonEnclosureTempChassis OBJECT-TYPE
        SYNTAX  INTEGER
        ACCESS  read-only
        STATUS  mandatory
        DESCRIPTION
            "A number that uniquely specifies this enclosure in the rack."
        ::= { cpqRackCommonEnclosureTempEntry 2 }

    cpqRackCommonEnclosureTempSensorIndex OBJECT-TYPE
        SYNTAX  INTEGER
        ACCESS  read-only
        STATUS  mandatory
        DESCRIPTION
            "A number that uniquely specifies this temperature sensor within
            this enclosure in the rack."
        ::= { cpqRackCommonEnclosureTempEntry 3 }

    cpqRackCommonEnclosureTempSensorEnclosureName OBJECT-TYPE
        SYNTAX  DisplayString (SIZE (0..64))
        ACCESS  read-only
        STATUS  mandatory
        DESCRIPTION
            "The name of the enclosure.

            The string will be empty if the enclosure does not report the
            name or it could not be determined."
        ::= { cpqRackCommonEnclosureTempEntry 4 }

    cpqRackCommonEnclosureTempLocation OBJECT-TYPE
        SYNTAX  DisplayString (SIZE (0..64))
        ACCESS  read-only
        STATUS  mandatory
        DESCRIPTION
            "The location description of the temperature sensor within the
            enclosure.

            The string will be empty if the location could not be
            determined."
        ::= { cpqRackCommonEnclosureTempEntry 5 }

    cpqRackCommonEnclosureTempCurrent OBJECT-TYPE
        SYNTAX  INTEGER
        ACCESS  read-only
        STATUS  mandatory
        DESCRIPTION
            "This is the current temperature sensor reading in degrees
            celsius.

            If this value cannot be determined by software, then a value
            of -1 will be returned."
        ::= { cpqRackCommonEnclosureTempEntry 6 }

    cpqRackCommonEnclosureTempThreshold OBJECT-TYPE
        SYNTAX  INTEGER
        ACCESS  read-only
        STATUS  mandatory
        DESCRIPTION
            "This is the threshold temperature sensor setting
            in degrees celsius.  This is the temperature in which the
            sensor will be considered to be in a tripped state this
            causing some action to occur depending on the type of
            the sensor.  The action of temperature sensor threshold
            will be indicated by the cpqRackCommonEnclosureTempType
            item.  If the type is blowout(5), then the temperature sensor
            will cause the fans to speed up.  If the type is caution(9),
            then the temperature sensor is in a degraded state.  If the
            type is critical(15), then the enclosure will be considered
            as in a failed state.

            If this value cannot be determined by software, then a value
            of -1 will be returned."
        ::= { cpqRackCommonEnclosureTempEntry 7 }

    cpqRackCommonEnclosureTempCondition OBJECT-TYPE
        SYNTAX  INTEGER {
            other(1),
            ok(2),
            degraded(3),
            failed(4)
            }
        ACCESS  read-only
        STATUS  mandatory
        DESCRIPTION
            "The Temperature sensor condition.

            This value will be one of the following:

            other(1)
              Temperature could not be determined.

            ok(2)
              The temperature sensor is within the normal operating range.

            degraded(3)
              The temperature sensor is outside of the normal operating range.

            failed(4)
              The temperature sensor detects a condition that could
              possibly damage the system.

            The system will automatically shutdown if the failed(4) condition
            results, so it is unlikely that this value will ever be returned
            by the agent."
        ::= { cpqRackCommonEnclosureTempEntry 8 }

    cpqRackCommonEnclosureTempType OBJECT-TYPE
        SYNTAX  INTEGER {
            other(1),
            blowout(5),
            caution(9),
            critical(15)
            }
        ACCESS  read-only
        STATUS  mandatory
        DESCRIPTION
            "This specifies the type of this instance of temperature
            sensor.

            This value will be one of the following:

            other(1)
              Temperature threshold type could not be determined.

            blowout(5)
              If a blowout(5) temperature sensor reaches its threshold,
              the fan or fans in the area of the temperature sensor will
              increase in speed in an attempt to reduce the temperature
              before a caution or critical threshold is reached.

            caution(9)
              If a caution(9) temperature sensor reaches its threshold, the
              cpqRackCommonEnclosureTempCondition will be set to degraded(3)
              and the system will either continue or shutdown depending
              on the user preferences.

            critical(15)
              If a critical(15) temperature sensor reaches its threshold,
              the cpqHeTemperatureCondition will be set to failed(4)
              and the system will shutdown."
        ::= { cpqRackCommonEnclosureTempEntry 9 }

    cpqRackCommonEnclosureTempSensorEnclosureSerialNum OBJECT-TYPE
        SYNTAX  DisplayString (SIZE (0..64))
        ACCESS  read-only
        STATUS  mandatory
        DESCRIPTION
            "The serial number of the enclosure containing this temperature
            sensor.

            The string will be empty if the enclosure does not report the
            serial number or it could not be determined."
        ::= { cpqRackCommonEnclosureTempEntry 10 }


-- ****************************************************************************
--   Rack Enclosure Common Fan Table
--   ===============================
--
-- The compaq enterprise                     (1.3.6.1.4.1.232)
--      cpqRackInfo Group                    (1.3.6.1.4.1.232.22)
--       cpqRackComponent Group              (1.3.6.1.4.1.232.22.2)
--        cpqRackEnclosure Group             (1.3.6.1.4.1.232.22.2.3)
--         cpqRackCommonEnclosure Group      (1.3.6.1.4.1.232.22.2.3.1)
--          cpqRackCommonEnclosureFanTable   (1.3.6.1.4.1.232.22.2.3.1.3)
--
-- ****************************************************************************

    cpqRackCommonEnclosureFanTable OBJECT-TYPE
        SYNTAX  SEQUENCE OF CpqRackCommonEnclosureFanEntry
        ACCESS  not-accessible
        STATUS  mandatory
        DESCRIPTION
            "A table of rack enclosure fan information."
        ::= { cpqRackCommonEnclosure 3 }

    cpqRackCommonEnclosureFanEntry OBJECT-TYPE
        SYNTAX  CpqRackCommonEnclosureFanEntry
        ACCESS  not-accessible
        STATUS  mandatory
        DESCRIPTION
            "A rack enclosure fan description."
        INDEX   { cpqRackCommonEnclosureFanRack,
                  cpqRackCommonEnclosureFanChassis,
                  cpqRackCommonEnclosureFanIndex }
        ::= { cpqRackCommonEnclosureFanTable 1 }

    CpqRackCommonEnclosureFanEntry ::= SEQUENCE {
        cpqRackCommonEnclosureFanRack                   INTEGER,
        cpqRackCommonEnclosureFanChassis                INTEGER,
        cpqRackCommonEnclosureFanIndex                  INTEGER,
        cpqRackCommonEnclosureFanEnclosureName          DisplayString,
        cpqRackCommonEnclosureFanLocation               DisplayString,
        cpqRackCommonEnclosureFanPartNumber             DisplayString,
        cpqRackCommonEnclosureFanSparePartNumber        DisplayString,
        cpqRackCommonEnclosureFanPresent                INTEGER,
        cpqRackCommonEnclosureFanRedundant              INTEGER,
        cpqRackCommonEnclosureFanRedundantGroupId       INTEGER,
        cpqRackCommonEnclosureFanCondition              INTEGER,
        cpqRackCommonEnclosureFanEnclosureSerialNum     DisplayString
    }

    cpqRackCommonEnclosureFanRack OBJECT-TYPE
        SYNTAX  INTEGER
        ACCESS  read-only
        STATUS  mandatory
        DESCRIPTION
            "A number that uniquely specifies this rack."
        ::= { cpqRackCommonEnclosureFanEntry 1 }

    cpqRackCommonEnclosureFanChassis OBJECT-TYPE
        SYNTAX  INTEGER
        ACCESS  read-only
        STATUS  mandatory
        DESCRIPTION
            "A number that uniquely specifies this enclosure in the rack."
        ::= { cpqRackCommonEnclosureFanEntry 2 }

    cpqRackCommonEnclosureFanIndex OBJECT-TYPE
        SYNTAX  INTEGER
        ACCESS  read-only
        STATUS  mandatory
        DESCRIPTION
            "A number that uniquely specifies this fan within this
            enclosure in the rack."
        ::= { cpqRackCommonEnclosureFanEntry 3 }

    cpqRackCommonEnclosureFanEnclosureName OBJECT-TYPE
        SYNTAX  DisplayString (SIZE (0..64))
        ACCESS  read-only
        STATUS  mandatory
        DESCRIPTION
            "The name of the enclosure.

            The string will be empty if the enclosure does not report the
            name or it could not be determined."
        ::= { cpqRackCommonEnclosureFanEntry 4 }

    cpqRackCommonEnclosureFanLocation OBJECT-TYPE
        SYNTAX  DisplayString (SIZE (0..64))
        ACCESS  read-only
        STATUS  mandatory
        DESCRIPTION
            "The location description of the fan within the enclosure.

            The string will be empty if the location could not be
            determined."
        ::= { cpqRackCommonEnclosureFanEntry 5 }

    cpqRackCommonEnclosureFanPartNumber OBJECT-TYPE
        SYNTAX  DisplayString (SIZE (0..64))
        ACCESS  read-only
        STATUS  mandatory
        DESCRIPTION
            "The part number of the enclosure fan.

            The string will be empty if the part number could not be
            determined."
        ::= { cpqRackCommonEnclosureFanEntry 6 }

    cpqRackCommonEnclosureFanSparePartNumber OBJECT-TYPE
        SYNTAX  DisplayString (SIZE (0..64))
        ACCESS  read-only
        STATUS  mandatory
        DESCRIPTION
            "The spare part number of the enclosure fan.

            The string will be empty if the part number could not be
            determined."
        ::= { cpqRackCommonEnclosureFanEntry 7 }

    cpqRackCommonEnclosureFanPresent OBJECT-TYPE
        SYNTAX  INTEGER {
            other(1),
            absent(2),
            present(3)
            }
        ACCESS  read-only
        STATUS  mandatory
        DESCRIPTION
            "This specifies if the fan described is present in the system."
        ::= { cpqRackCommonEnclosureFanEntry 8 }

    cpqRackCommonEnclosureFanRedundant OBJECT-TYPE
        SYNTAX  INTEGER {
            other(1),
            notRedundant(2),
            redundant(3)
            }
        ACCESS  read-only
        STATUS  mandatory
        DESCRIPTION
            "This specifies if the fan is in a redundant configuration."
        ::= { cpqRackCommonEnclosureFanEntry 9 }

    cpqRackCommonEnclosureFanRedundantGroupId OBJECT-TYPE
        SYNTAX  INTEGER
        ACCESS  read-only
        STATUS  mandatory
        DESCRIPTION
            "This specifies the group number for redundant fans within this
            enclosure."
        ::= { cpqRackCommonEnclosureFanEntry 10 }

    cpqRackCommonEnclosureFanCondition OBJECT-TYPE
        SYNTAX  INTEGER {
            other(1),
            ok(2),
            degraded(3),
            failed(4)
            }
        ACCESS  read-only
        STATUS  mandatory
        DESCRIPTION
            "The condition of the fan.

            This value will be one of the following:

            other(1)
              Fan status detection is not supported.

            ok(2)
              The fan is operating properly.

            degraded(2)
              A redundant fan is not operating properly.

            failed(4)
              A non-redundant fan is not operating properly."
        ::= { cpqRackCommonEnclosureFanEntry 11 }

    cpqRackCommonEnclosureFanEnclosureSerialNum OBJECT-TYPE
        SYNTAX  DisplayString (SIZE (0..64))
        ACCESS  read-only
        STATUS  mandatory
        DESCRIPTION
            "The serial number of the enclosure containing the fan.

            The string will be empty if the enclosure does not report the
            serial number or it could not be determined."
        ::= { cpqRackCommonEnclosureFanEntry 12 }

-- ****************************************************************************
--   Rack Enclosure Common Fuse Table
--   ================================
--
-- The compaq enterprise                     (1.3.6.1.4.1.232)
--      cpqRackInfo Group                    (1.3.6.1.4.1.232.22)
--       cpqRackComponent Group              (1.3.6.1.4.1.232.22.2)
--        cpqRackEnclosure Group             (1.3.6.1.4.1.232.22.2.3)
--         cpqRackCommonEnclosure Group      (1.3.6.1.4.1.232.22.2.3.1)
--          cpqRackCommonEnclosureFuseTable  (1.3.6.1.4.1.232.22.2.3.1.4)
--
-- ****************************************************************************

    cpqRackCommonEnclosureFuseTable OBJECT-TYPE
        SYNTAX  SEQUENCE OF CpqRackCommonEnclosureFuseEntry
        ACCESS  not-accessible
        STATUS  mandatory
        DESCRIPTION
            "A table of rack enclosure fuse information."
        ::= { cpqRackCommonEnclosure 4 }

    cpqRackCommonEnclosureFuseEntry OBJECT-TYPE
        SYNTAX  CpqRackCommonEnclosureFuseEntry
        ACCESS  not-accessible
        STATUS  mandatory
        DESCRIPTION
            "A rack enclosure fuse description."
        INDEX   { cpqRackCommonEnclosureFuseRack,
                  cpqRackCommonEnclosureFuseChassis,
                  cpqRackCommonEnclosureFuseIndex }
        ::= { cpqRackCommonEnclosureFuseTable 1 }

    CpqRackCommonEnclosureFuseEntry ::= SEQUENCE {
        cpqRackCommonEnclosureFuseRack             INTEGER,
        cpqRackCommonEnclosureFuseChassis          INTEGER,
        cpqRackCommonEnclosureFuseIndex            INTEGER,
        cpqRackCommonEnclosureFuseEnclosureName    DisplayString,
        cpqRackCommonEnclosureFuseLocation         DisplayString,
        cpqRackCommonEnclosureFusePresent          INTEGER,
        cpqRackCommonEnclosureFuseCondition        INTEGER
    }

    cpqRackCommonEnclosureFuseRack OBJECT-TYPE
        SYNTAX  INTEGER
        ACCESS  read-only
        STATUS  mandatory
        DESCRIPTION
            "A number that uniquely specifies this rack."
        ::= { cpqRackCommonEnclosureFuseEntry 1 }

    cpqRackCommonEnclosureFuseChassis OBJECT-TYPE
        SYNTAX  INTEGER
        ACCESS  read-only
        STATUS  mandatory
        DESCRIPTION
            "A number that uniquely specifies this enclosure in the rack."
        ::= { cpqRackCommonEnclosureFuseEntry 2 }

    cpqRackCommonEnclosureFuseIndex OBJECT-TYPE
        SYNTAX  INTEGER
        ACCESS  read-only
        STATUS  mandatory
        DESCRIPTION
            "A number that uniquely specifies the fuse within this enclosure."
        ::= { cpqRackCommonEnclosureFuseEntry 3 }

    cpqRackCommonEnclosureFuseEnclosureName OBJECT-TYPE
        SYNTAX  DisplayString (SIZE (0..64))
        ACCESS  read-only
        STATUS  mandatory
        DESCRIPTION
            "The name of the enclosure.

            The string will be empty if the enclosure does not report the
            name or it could not be determined."
        ::= { cpqRackCommonEnclosureFuseEntry 4 }

    cpqRackCommonEnclosureFuseLocation OBJECT-TYPE
        SYNTAX  DisplayString (SIZE (0..64))
        ACCESS  read-only
        STATUS  mandatory
        DESCRIPTION
            "The location description of the fuse within the enclosure.

            The string will be empty if the location could not be
            determined."
        ::= { cpqRackCommonEnclosureFuseEntry 5 }

    cpqRackCommonEnclosureFusePresent OBJECT-TYPE
        SYNTAX  INTEGER {
            other(1),
            absent(2),
            present(3)
            }
        ACCESS  read-only
        STATUS  mandatory
        DESCRIPTION
            "This specifies if the fuse described is present in the system."
        ::= { cpqRackCommonEnclosureFuseEntry 6 }

    cpqRackCommonEnclosureFuseCondition OBJECT-TYPE
        SYNTAX  INTEGER {
            other(1),
            ok(2),
            failed(4)
            }
        ACCESS  read-only
        STATUS  mandatory
        DESCRIPTION
            "The condition of the fuse.

            This value will be one of the following:

            other(1)
              Fuse status detection is not supported.

            ok(2)
              The fuse is operating properly.

            failed(4)
              A fuse has been tripped or is not operating properly."
        ::= { cpqRackCommonEnclosureFuseEntry 7 }

-- ****************************************************************************
--   Rack Enclosure Common FRU Table
--   ===============================
--
-- The compaq enterprise                     (1.3.6.1.4.1.232)
--      cpqRackInfo Group                    (1.3.6.1.4.1.232.22)
--       cpqRackComponent Group              (1.3.6.1.4.1.232.22.2)
--        cpqRackEnclosure Group             (1.3.6.1.4.1.232.22.2.3)
--         cpqRackCommonEnclosure Group      (1.3.6.1.4.1.232.22.2.3.1)
--          cpqRackCommonEnclosureFruTable   (1.3.6.1.4.1.232.22.2.3.1.5)
--
-- ****************************************************************************

    cpqRackCommonEnclosureFruTable OBJECT-TYPE
        SYNTAX  SEQUENCE OF CpqRackCommonEnclosureFruEntry
        ACCESS  not-accessible
        STATUS  mandatory
        DESCRIPTION
            "A table of rack enclosure field replaceable units information."
        ::= { cpqRackCommonEnclosure 5 }

    cpqRackCommonEnclosureFruEntry OBJECT-TYPE
        SYNTAX  CpqRackCommonEnclosureFruEntry
        ACCESS  not-accessible
        STATUS  mandatory
        DESCRIPTION
            "A rack enclosure field replaceable unit description."
        INDEX   { cpqRackCommonEnclosureFruRack,
                  cpqRackCommonEnclosureFruChassis,
                  cpqRackCommonEnclosureFruIndex }
        ::= { cpqRackCommonEnclosureFruTable 1 }

    CpqRackCommonEnclosureFruEntry ::= SEQUENCE {
        cpqRackCommonEnclosureFruRack                 INTEGER,
        cpqRackCommonEnclosureFruChassis              INTEGER,
        cpqRackCommonEnclosureFruIndex                INTEGER,
        cpqRackCommonEnclosureFruEnclosureName        DisplayString,
        cpqRackCommonEnclosureFruDescription          DisplayString,
        cpqRackCommonEnclosureFruLocation             DisplayString,
        cpqRackCommonEnclosureFruAssemblyPartNumber   DisplayString,
        cpqRackCommonEnclosureFruSparePartNumber      DisplayString,
        cpqRackCommonEnclosureFruAutoRev              DisplayString,
        cpqRackCommonEnclosureFruSerialNum            DisplayString
    }

    cpqRackCommonEnclosureFruRack OBJECT-TYPE
        SYNTAX  INTEGER
        ACCESS  read-only
        STATUS  mandatory
        DESCRIPTION
            "A number that uniquely specifies this rack."
        ::= { cpqRackCommonEnclosureFruEntry 1 }

    cpqRackCommonEnclosureFruChassis OBJECT-TYPE
        SYNTAX  INTEGER
        ACCESS  read-only
        STATUS  mandatory
        DESCRIPTION
            "A number that uniquely specifies this enclosure in the rack."
        ::= { cpqRackCommonEnclosureFruEntry 2 }

    cpqRackCommonEnclosureFruIndex OBJECT-TYPE
        SYNTAX  INTEGER
        ACCESS  read-only
        STATUS  mandatory
        DESCRIPTION
            "A number that uniquely specifies the FRU within this enclosure."
        ::= { cpqRackCommonEnclosureFruEntry 3 }

    cpqRackCommonEnclosureFruEnclosureName OBJECT-TYPE
        SYNTAX  DisplayString (SIZE (0..64))
        ACCESS  read-only
        STATUS  mandatory
        DESCRIPTION
            "The name of the enclosure.

            The string will be empty if the enclosure does not report the
            name or it could not be determined."
        ::= { cpqRackCommonEnclosureFruEntry 4 }

    cpqRackCommonEnclosureFruDescription OBJECT-TYPE
        SYNTAX  DisplayString (SIZE (0..64))
        ACCESS  read-only
        STATUS  mandatory
        DESCRIPTION
            "A description of the FRU component.

            The string will be empty if the enclosure does not report the
            description information."
        ::= { cpqRackCommonEnclosureFruEntry 5 }

    cpqRackCommonEnclosureFruLocation OBJECT-TYPE
        SYNTAX  DisplayString (SIZE (0..64))
        ACCESS  read-only
        STATUS  mandatory
        DESCRIPTION
            "The location description of the FRU within the enclosure.

            The string will be empty if the location could not be
            determined."
        ::= { cpqRackCommonEnclosureFruEntry 6 }

    cpqRackCommonEnclosureFruAssemblyPartNumber OBJECT-TYPE
        SYNTAX  DisplayString (SIZE (0..64))
        ACCESS  read-only
        STATUS  mandatory
        DESCRIPTION
            "The assembly part number of the FRU within the enclosure.

            The string will be empty if the enclosure does not report this
            information."
        ::= { cpqRackCommonEnclosureFruEntry 7 }

    cpqRackCommonEnclosureFruSparePartNumber OBJECT-TYPE
        SYNTAX  DisplayString (SIZE (0..64))
        ACCESS  read-only
        STATUS  mandatory
        DESCRIPTION
            "The spare part number of the FRU within the enclosure.

            The string will be empty if the enclosure does not report this
            information."
        ::= { cpqRackCommonEnclosureFruEntry 8 }

    cpqRackCommonEnclosureFruAutoRev OBJECT-TYPE
        SYNTAX  DisplayString (SIZE (0..64))
        ACCESS  read-only
        STATUS  mandatory
        DESCRIPTION
            "The auto revision number of the FRU within the enclosure.

            The string will be empty if the enclosure does not report this
            information."
        ::= { cpqRackCommonEnclosureFruEntry 9 }

    cpqRackCommonEnclosureFruSerialNum OBJECT-TYPE
        SYNTAX  DisplayString (SIZE (0..64))
        ACCESS  read-only
        STATUS  mandatory
        DESCRIPTION
            "The serial number of the FRU within the enclosure.

            The string will be empty if the enclosure does not report the
            serial number."
        ::= { cpqRackCommonEnclosureFruEntry 10 }

-- ****************************************************************************
--   Rack Enclosure Common Manager Table
--   ===================================
--
-- The compaq enterprise                     (1.3.6.1.4.1.232)
--      cpqRackInfo Group                    (1.3.6.1.4.1.232.22)
--       cpqRackComponent Group              (1.3.6.1.4.1.232.22.2)
--        cpqRackEnclosure Group             (1.3.6.1.4.1.232.22.2.3)
--         cpqRackCommonEnclosure Group      (1.3.6.1.4.1.232.22.2.3.1)
--          cpqRackCommonEnclosureManagerTable   (1.3.6.1.4.1.232.22.2.3.1.6)
--
-- ****************************************************************************

    cpqRackCommonEnclosureManagerTable OBJECT-TYPE
        SYNTAX  SEQUENCE OF CpqRackCommonEnclosureManagerEntry
        ACCESS  not-accessible
        STATUS  mandatory
        DESCRIPTION
            "A table of rack enclosure manager information."
        ::= { cpqRackCommonEnclosure 6 }

    cpqRackCommonEnclosureManagerEntry OBJECT-TYPE
        SYNTAX  CpqRackCommonEnclosureManagerEntry
        ACCESS  not-accessible
        STATUS  mandatory
        DESCRIPTION
            "A rack enclosure manager description."
        INDEX   { cpqRackCommonEnclosureManagerRack,
                  cpqRackCommonEnclosureManagerChassis,
                  cpqRackCommonEnclosureManagerIndex }
        ::= { cpqRackCommonEnclosureManagerTable 1 }

    CpqRackCommonEnclosureManagerEntry ::= SEQUENCE {
        cpqRackCommonEnclosureManagerRack                   INTEGER,
        cpqRackCommonEnclosureManagerChassis                INTEGER,
        cpqRackCommonEnclosureManagerIndex                  INTEGER,
        cpqRackCommonEnclosureManagerEnclosureName          DisplayString,
        cpqRackCommonEnclosureManagerLocation               DisplayString,
        cpqRackCommonEnclosureManagerPartNumber             DisplayString,
        cpqRackCommonEnclosureManagerSparePartNumber        DisplayString,
        cpqRackCommonEnclosureManagerSerialNum              DisplayString,
        cpqRackCommonEnclosureManagerRole                   INTEGER,
        cpqRackCommonEnclosureManagerPresent                INTEGER,
        cpqRackCommonEnclosureManagerRedundant              INTEGER,
        cpqRackCommonEnclosureManagerCondition              INTEGER,
        cpqRackCommonEnclosureManagerEnclosureSerialNum     DisplayString,
        cpqRackCommonEnclosureManagerUUID                   DisplayString,
        cpqRackCommonEnclosureManagerFWRev                  DisplayString
    }

    cpqRackCommonEnclosureManagerRack OBJECT-TYPE
        SYNTAX  INTEGER
        ACCESS  read-only
        STATUS  mandatory
        DESCRIPTION
            "A number that uniquely specifies this rack."
        ::= { cpqRackCommonEnclosureManagerEntry 1 }

    cpqRackCommonEnclosureManagerChassis OBJECT-TYPE
        SYNTAX  INTEGER
        ACCESS  read-only
        STATUS  mandatory
        DESCRIPTION
            "A number that uniquely specifies this enclosure in the rack."
        ::= { cpqRackCommonEnclosureManagerEntry 2 }

    cpqRackCommonEnclosureManagerIndex OBJECT-TYPE
        SYNTAX  INTEGER
        ACCESS  read-only
        STATUS  mandatory
        DESCRIPTION
            "A number that uniquely specifies this manager within this
            enclosure in the rack."
        ::= { cpqRackCommonEnclosureManagerEntry 3 }

    cpqRackCommonEnclosureManagerEnclosureName OBJECT-TYPE
        SYNTAX  DisplayString (SIZE (0..64))
        ACCESS  read-only
        STATUS  mandatory
        DESCRIPTION
            "The name of the enclosure.

            The string will be empty if the enclosure does not report the
            name or it could not be determined."
        ::= { cpqRackCommonEnclosureManagerEntry 4 }

    cpqRackCommonEnclosureManagerLocation OBJECT-TYPE
        SYNTAX  DisplayString (SIZE (0..64))
        ACCESS  read-only
        STATUS  mandatory
        DESCRIPTION
            "The location description of the manager within the enclosure.

            The string will be empty if the location could not be
            determined."
        ::= { cpqRackCommonEnclosureManagerEntry 5 }

    cpqRackCommonEnclosureManagerPartNumber OBJECT-TYPE
        SYNTAX  DisplayString (SIZE (0..64))
        ACCESS  read-only
        STATUS  mandatory
        DESCRIPTION
            "The part number of the enclosure manager.

            The string will be empty if the part number could not be
            determined."
        ::= { cpqRackCommonEnclosureManagerEntry 6 }

    cpqRackCommonEnclosureManagerSparePartNumber OBJECT-TYPE
        SYNTAX  DisplayString (SIZE (0..64))
        ACCESS  read-only
        STATUS  mandatory
        DESCRIPTION
            "The spare part number of the enclosure manager.

            The string will be empty if the part number could not be
            determined."
        ::= { cpqRackCommonEnclosureManagerEntry 7 }

    cpqRackCommonEnclosureManagerSerialNum OBJECT-TYPE
        SYNTAX  DisplayString (SIZE (0..64))
        ACCESS  read-only
        STATUS  mandatory
        DESCRIPTION
            "The serial number of the enclosure manager.

            The string will be empty if the enclosure does not report the
            serial number or it could not be determined."
        ::= { cpqRackCommonEnclosureManagerEntry 8 }

    cpqRackCommonEnclosureManagerRole OBJECT-TYPE
        SYNTAX   INTEGER {
            standby(1),
            active(2)
            }
        ACCESS read-only
        STATUS mandatory
        DESCRIPTION
            "This specifies the current role of the manager."
        ::= { cpqRackCommonEnclosureManagerEntry 9 }

    cpqRackCommonEnclosureManagerPresent OBJECT-TYPE
        SYNTAX  INTEGER {
            other(1),
            absent(2),
            present(3)
            }
        ACCESS  read-only
        STATUS  mandatory
        DESCRIPTION
            "This specifies if the manager described is present in the system."
        ::= { cpqRackCommonEnclosureManagerEntry 10 }

    cpqRackCommonEnclosureManagerRedundant OBJECT-TYPE
        SYNTAX  INTEGER {
            other(1),
            notRedundant(2),
            redundant(3)
            }
        ACCESS  read-only
        STATUS  mandatory
        DESCRIPTION
            "This specifies if the manager is in a redundant configuration."
        ::= { cpqRackCommonEnclosureManagerEntry 11 }

    cpqRackCommonEnclosureManagerCondition OBJECT-TYPE
        SYNTAX  INTEGER {
            other(1),
            ok(2),
            degraded(3),
            failed(4)
            }
        ACCESS  read-only
        STATUS  mandatory
        DESCRIPTION
            "The condition of the manager.

            This value will be one of the following:

            other(1)
              Manager status detection is not supported.

            ok(2)
              The manager is operating properly.

            degraded(2)
              A redundant manager is not operating properly.

            failed(4)
              A non-redundant manager is not operating properly."
        ::= { cpqRackCommonEnclosureManagerEntry 12 }

    cpqRackCommonEnclosureManagerEnclosureSerialNum OBJECT-TYPE
        SYNTAX  DisplayString (SIZE (0..64))
        ACCESS  read-only
        STATUS  mandatory
        DESCRIPTION
            "The serial number of the enclosure containing the manager.

            The string will be empty if the enclosure does not report the
            serial number or it could not be determined."
        ::= { cpqRackCommonEnclosureManagerEntry 13 }

    cpqRackCommonEnclosureManagerUUID OBJECT-TYPE
        SYNTAX  DisplayString (SIZE (0..64))
        ACCESS  read-only
        STATUS  mandatory
        DESCRIPTION
            "The universal unique identifier string of the manager.

            The string will be empty if the enclosure does not report the
            UUID string."
        ::= { cpqRackCommonEnclosureManagerEntry 14 }

    cpqRackCommonEnclosureManagerFWRev OBJECT-TYPE
        SYNTAX  DisplayString (SIZE (0..64))
        ACCESS  read-only
        STATUS  mandatory
        DESCRIPTION
            "The firmware revision of the enclosure manager.

            The string will be empty if the enclosure does not report the
            firmware revision or does not contain firmware."
        ::= { cpqRackCommonEnclosureManagerEntry 15 }

-- ****************************************************************************
--   Rack Enclosure for Servers Table
--   ================================
--
-- The compaq enterprise                 (1.3.6.1.4.1.232)
--      cpqRackInfo Group                (1.3.6.1.4.1.232.22)
--       cpqRackComponent Group          (1.3.6.1.4.1.232.22.2)
--        cpqRackEnclosure Group         (1.3.6.1.4.1.232.22.2.3)
--         cpqRackServerEnclosure Group  (1.3.6.1.4.1.232.22.2.3.2)
--          cpqRackServerEnclosureTable  (1.3.6.1.4.1.232.22.2.3.2.1)
--
-- ****************************************************************************

    cpqRackServerEnclosureTable OBJECT-TYPE
        SYNTAX  SEQUENCE OF CpqRackServerEnclosureEntry
        ACCESS  not-accessible
        STATUS  mandatory
        DESCRIPTION
            "A table of rack enclosure information for servers."
        ::= { cpqRackServerEnclosure 1 }

    cpqRackServerEnclosureEntry OBJECT-TYPE
        SYNTAX  CpqRackServerEnclosureEntry
        ACCESS  not-accessible
        STATUS  mandatory
        DESCRIPTION
            "A server enclosure description."
        INDEX   { cpqRackServerEnclosureRack,
                  cpqRackServerEnclosureIndex }
        ::= { cpqRackServerEnclosureTable 1 }

    CpqRackServerEnclosureEntry ::= SEQUENCE {
        cpqRackServerEnclosureRack                 INTEGER,
        cpqRackServerEnclosureIndex                INTEGER,
        cpqRackServerEnclosureName                 DisplayString,
        cpqRackServerEnclosureMaxNumBlades         INTEGER,
        cpqRackServerEnclosureMaxNumBladesX        INTEGER,
        cpqRackServerEnclosureMaxNumBladesY        INTEGER,
        cpqRackServerEnclosureSolutionsId          OCTET STRING
    }

    cpqRackServerEnclosureRack OBJECT-TYPE
        SYNTAX  INTEGER
        ACCESS  read-only
        STATUS  mandatory
        DESCRIPTION
            "A number that uniquely specifies this rack."
        ::= { cpqRackServerEnclosureEntry 1 }

    cpqRackServerEnclosureIndex OBJECT-TYPE
        SYNTAX  INTEGER
        ACCESS  read-only
        STATUS  mandatory
        DESCRIPTION
            "A number that uniquely specifies this server enclosure in the rack."
        ::= { cpqRackServerEnclosureEntry 2 }

    cpqRackServerEnclosureName OBJECT-TYPE
        SYNTAX  DisplayString (SIZE (0..64))
        ACCESS  read-only
        STATUS  mandatory
        DESCRIPTION
            "The name of the server enclosure.

            The string will be empty if the enclosure does not report the
            name or it could not be determined."
        ::= { cpqRackServerEnclosureEntry 3 }

    cpqRackServerEnclosureMaxNumBlades OBJECT-TYPE
        SYNTAX  INTEGER
        ACCESS  read-only
        STATUS  mandatory
        DESCRIPTION
            "The maximum number of server blades the enclosure can contain.

            The string will be empty if the enclosure does not report the
            name or it could not be determined."
        ::= { cpqRackServerEnclosureEntry 4 }

    cpqRackServerEnclosureMaxNumBladesX OBJECT-TYPE
        SYNTAX  INTEGER
        ACCESS  read-only
        STATUS  mandatory
        DESCRIPTION
            "The maximum number of server blades in x-direction (from left to right)
            the enclosure can contain."

        ::= { cpqRackServerEnclosureEntry 5 }

    cpqRackServerEnclosureMaxNumBladesY OBJECT-TYPE
        SYNTAX  INTEGER
        ACCESS  read-only
        STATUS  mandatory
        DESCRIPTION
            "The maximum number of server blades in y-direction (from top to bottom)
            the enclosure can contain."

        ::= { cpqRackServerEnclosureEntry 6 }

    cpqRackServerEnclosureSolutionsId OBJECT-TYPE
        SYNTAX  OCTET STRING (SIZE (8))
        ACCESS  read-write
        STATUS  optional
        DESCRIPTION
            "The identifier is used to label enclosure as a BladeSystem Matrix enclosure.
               Octet      Values
               ===== ==============================
                 1      Solutions platform identifier
                        Bits[7:4]
                          - 0001b BladeSystem Matrix configured
                          - 0000b reserved
                        Bits[3:0]
                          - 0000b reserved
                 2      major number
                          - 0x01 - 0xff
                 3      minor number
                          - 0x01 - 0xff
                 4      update number
                          - 0x01 - 0xff
                 5     reserved/unused

             The identifier is set to all 0's if the enclosure is
                     not configured as a BladeSystem Matrix enclosure."

        ::= { cpqRackServerEnclosureEntry 7 }


-- ****************************************************************************
--   Rack Enclosure for Power Supplies Table
--   =======================================
--
-- The compaq enterprise                 (1.3.6.1.4.1.232)
--      cpqRackInfo Group                (1.3.6.1.4.1.232.22)
--       cpqRackComponent Group          (1.3.6.1.4.1.232.22.2)
--        cpqRackEnclosure Group         (1.3.6.1.4.1.232.22.2.3)
--         cpqRackPowerEnclosure Group   (1.3.6.1.4.1.232.22.2.3.3)
--          cpqRackPowerEnclosureTable   (1.3.6.1.4.1.232.22.2.3.3.1)
--
-- ****************************************************************************

    cpqRackPowerEnclosureTable OBJECT-TYPE
        SYNTAX  SEQUENCE OF CpqRackPowerEnclosureEntry
        ACCESS  not-accessible
        STATUS  mandatory
        DESCRIPTION
            "A table of rack power enclosure information."
        ::= { cpqRackPowerEnclosure 1 }

    cpqRackPowerEnclosureEntry OBJECT-TYPE
        SYNTAX  CpqRackPowerEnclosureEntry
        ACCESS  not-accessible
        STATUS  mandatory
        DESCRIPTION
            "A rack power enclosure description."
        INDEX   { cpqRackPowerEnclosureRack,
                  cpqRackPowerEnclosureIndex }
        ::= { cpqRackPowerEnclosureTable 1 }

    CpqRackPowerEnclosureEntry ::= SEQUENCE {
        cpqRackPowerEnclosureRack                  INTEGER,
        cpqRackPowerEnclosureIndex                 INTEGER,
        cpqRackPowerEnclosureName                  DisplayString,
        cpqRackPowerEnclosureMgmtBoardSerialNum    DisplayString,
        cpqRackPowerEnclosureRedundant             INTEGER,
        cpqRackPowerEnclosureLoadBalanced          INTEGER,
        cpqRackPowerEnclosureInputPwrType          INTEGER,
        cpqRackPowerEnclosurePwrFeedMax            INTEGER,
        cpqRackPowerEnclosureCondition             INTEGER,
        cpqRackPowerEnclosureBladeAutopoweron      INTEGER
    }

    cpqRackPowerEnclosureRack OBJECT-TYPE
        SYNTAX  INTEGER
        ACCESS  read-only
        STATUS  mandatory
        DESCRIPTION
            "A number that uniquely specifies this rack."
        ::= { cpqRackPowerEnclosureEntry 1 }

    cpqRackPowerEnclosureIndex OBJECT-TYPE
        SYNTAX  INTEGER
        ACCESS  read-only
        STATUS  mandatory
        DESCRIPTION
            "A number that uniquely specifies this power enclosure in the rack."
        ::= { cpqRackPowerEnclosureEntry 2 }

    cpqRackPowerEnclosureName OBJECT-TYPE
        SYNTAX  DisplayString (SIZE (0..64))
        ACCESS  read-only
        STATUS  mandatory
        DESCRIPTION
            "The name of the power enclosure.

            The string will be empty if the enclosure does not report the
            name or it could not be determined."
        ::= { cpqRackPowerEnclosureEntry 3 }

    cpqRackPowerEnclosureMgmtBoardSerialNum OBJECT-TYPE
        SYNTAX  DisplayString (SIZE (0..64))
        ACCESS  read-only
        STATUS  mandatory
        DESCRIPTION
            "The serial number of the enclosure.

            The string will be empty if the enclosure does not report the
            serial number."
        ::= { cpqRackPowerEnclosureEntry 4 }

    cpqRackPowerEnclosureRedundant OBJECT-TYPE
        SYNTAX  INTEGER {
            other(1),
            notRedundant(2),
            redundant(3)
            }
        ACCESS  read-only
        STATUS  mandatory
        DESCRIPTION
            "This indicates if the power supply enclosure is in a redundant
            state."
        ::= { cpqRackPowerEnclosureEntry 5 }

    cpqRackPowerEnclosureLoadBalanced OBJECT-TYPE
        SYNTAX  INTEGER {
            other(1),
            notLoadBalanced(2),
            loadBalanced(3)
            }
        ACCESS  read-only
        STATUS  mandatory
        DESCRIPTION
            "This indicates if the power supply enclosure is in a load
            balanced state."
        ::= { cpqRackPowerEnclosureEntry 6 }

    cpqRackPowerEnclosureInputPwrType OBJECT-TYPE
        SYNTAX  INTEGER {
            other(1),
            singlePhase(2),
            threePhase(3),
            directCurrent(4)
            }
        ACCESS  read-only
        STATUS  mandatory
        DESCRIPTION
            "This indicates type of input facility power."
        ::= { cpqRackPowerEnclosureEntry 7 }

    cpqRackPowerEnclosurePwrFeedMax OBJECT-TYPE
        SYNTAX  INTEGER
        ACCESS  read-only
        STATUS  mandatory
        DESCRIPTION
            "This is the maximum facility power in watts.

            The maximum facility power being fed to this power enclosure.

            The value will be -1 if the power enclosure does not report the
            value or if the value is not known."
        ::= { cpqRackPowerEnclosureEntry 8 }

    cpqRackPowerEnclosureCondition OBJECT-TYPE
        SYNTAX  INTEGER {
            other(1),
            ok(2),
            degraded(3)
            }
        ACCESS  read-only
        STATUS  mandatory
        DESCRIPTION
            "This indicates current condition of the power enclosure.

            other(1)
              The power enclosure condition could not be determined.

            ok(2)
              The power enclosure is operating normally.

            degraded(3)
              The power enclosure is in a degraded state.  The power subsystem
              may not be load balanced or may have lost redundancy."
        ::= { cpqRackPowerEnclosureEntry 9 }

   cpqRackPowerEnclosureBladeAutopoweron OBJECT-TYPE
        SYNTAX  INTEGER {
            other(1),
            disabled(2),
            enabled(3)
            }
        ACCESS  read-write
        STATUS  optional
        DESCRIPTION
            "This indicates current condition of the power enclosure.

            other(1)
              The blade auto power on feature could not be determined.

            disabled(2)
              The enclosure will not automatically power on a blade when inserted.

            enabled(3)
              The enclosure will automatically power on a blade when inserted."
        ::= { cpqRackPowerEnclosureEntry 10 }

-- ****************************************************************************
-- The cpqRackLastEAEEvent holds data for last EAE event
--
-- The compaq enterprise                 (1.3.6.1.4.1.232)
--      cpqRackInfo Group                (1.3.6.1.4.1.232.22)
--       cpqRackComponent Group          (1.3.6.1.4.1.232.22.2)
--        cpqRackEnclosure Group         (1.3.6.1.4.1.232.22.2.3)
--         cpqRackServerEnclosure Group  (1.3.6.1.4.1.232.22.2.3.2)
--          cpqRackLastEAEEvent          (1.3.6.1.4.1.232.22.2.3.2.2)
--
-- Implementation of this group is optional.
--
-- ****************************************************************************
    cpqRackLastEAEEvent OBJECT-TYPE
        SYNTAX  DisplayString (SIZE (0..512))
        ACCESS  read-only
        STATUS  optional
        DESCRIPTION
        "Data for the last EAE event."
--
-- This is the data variable that is sent with the generics EAE trap below.
--
        ::= { cpqRackServerEnclosure 2 }

-- ****************************************************************************
--   Rack Server Blade Table
--   =======================
--
-- The compaq enterprise                 (1.3.6.1.4.1.232)
--      cpqRackInfo Group                (1.3.6.1.4.1.232.22)
--       cpqRackComponent Group          (1.3.6.1.4.1.232.22.2)
--        cpqRackServer Group            (1.3.6.1.4.1.232.22.2.4)
--         cpqRackServerBlade Group      (1.3.6.1.4.1.232.22.2.4.1)
--          cpqRackServerBladeTable      (1.3.6.1.4.1.232.22.2.4.1.1)
--
-- ****************************************************************************

    cpqRackServerBladeTable OBJECT-TYPE
        SYNTAX  SEQUENCE OF CpqRackServerBladeEntry
        ACCESS  not-accessible
        STATUS  mandatory
        DESCRIPTION
            "A table of rack server blade information."
        ::= { cpqRackServerBlade 1 }

    cpqRackServerBladeEntry OBJECT-TYPE
        SYNTAX  CpqRackServerBladeEntry
        ACCESS  not-accessible
        STATUS  mandatory
        DESCRIPTION
            "A rack server blade description."
        INDEX   { cpqRackServerBladeRack,
                  cpqRackServerBladeChassis,
                  cpqRackServerBladeIndex }
        ::= { cpqRackServerBladeTable 1 }

    CpqRackServerBladeEntry ::= SEQUENCE {
        cpqRackServerBladeRack               INTEGER,
        cpqRackServerBladeChassis            INTEGER,
        cpqRackServerBladeIndex              INTEGER,
        cpqRackServerBladeName               DisplayString,
        cpqRackServerBladeEnclosureName      DisplayString,
        cpqRackServerBladePartNumber         DisplayString,
        cpqRackServerBladeSparePartNumber    DisplayString,
        cpqRackServerBladePosition           INTEGER,
        cpqRackServerBladeHeight             INTEGER,
        cpqRackServerBladeWidth              INTEGER,
        cpqRackServerBladeDepth              INTEGER,
        cpqRackServerBladePresent            INTEGER,
        cpqRackServerBladeHasFuses           INTEGER,
        cpqRackServerBladeEnclosureSerialNum DisplayString,
        cpqRackServerBladeSlotsUsed          INTEGER,
        cpqRackServerBladeSerialNum          DisplayString,
        cpqRackServerBladeProductId          DisplayString,
        cpqRackServerBladeUid                DisplayString,
        cpqRackServerBladeSlotsUsedX         INTEGER,
        cpqRackServerBladeSlotsUsedY         INTEGER,
        cpqRackServerBladeStatus             INTEGER,
        cpqRackServerBladeFaultMajor         INTEGER,
        cpqRackServerBladeFaultMinor         INTEGER,
        cpqRackServerBladeFaultDiagnosticString  DisplayString,
        cpqRackServerBladePowered            INTEGER,
        cpqRackServerBladeUIDState                          INTEGER,
        cpqRackServerBladeSystemBIOSRevision                DisplayString,
        cpqRackServerBladeSystemBIOSFlashingStatus          INTEGER,
        cpqRackServerBladeHasManagementDevice               INTEGER,
        cpqRackServerBladeManagementDeviceFirmwareRevision        DisplayString,
        cpqRackServerBladeManagementDeviceFirmwareFlashingStatus  INTEGER,
        cpqRackServerBladeDiagnosticAdaptorPresence               INTEGER,
        cpqRackServerBladeASREnabled                              INTEGER,
        cpqRackServerBladeFrontIOBlankingModeStatus               INTEGER,
        cpqRackServerBladePOSTStatus                              INTEGER,
        cpqRackServerBladePXEBootModeStatus                       INTEGER,
        cpqRackServerBladePendingBootOrderChange                  INTEGER,
        cpqRackServerBladeWattageMax                              INTEGER,
        cpqRackServerBladeWattageAvg                              INTEGER,
        cpqRackServerBladeWattageMin                              INTEGER
    }

    cpqRackServerBladeRack OBJECT-TYPE
        SYNTAX  INTEGER
        ACCESS  read-only
        STATUS  mandatory
        DESCRIPTION
            "A number that uniquely specifies this rack."
        ::= { cpqRackServerBladeEntry 1 }

    cpqRackServerBladeChassis OBJECT-TYPE
        SYNTAX  INTEGER
        ACCESS  read-only
        STATUS  mandatory
        DESCRIPTION
            "A number that uniquely specifies this enclosure in the rack."
        ::= { cpqRackServerBladeEntry 2 }

    cpqRackServerBladeIndex OBJECT-TYPE
        SYNTAX  INTEGER
        ACCESS  read-only
        STATUS  mandatory
        DESCRIPTION
            "A number that uniquely specifies this server blade within the enclosure."
        ::= { cpqRackServerBladeEntry 3 }

    cpqRackServerBladeName OBJECT-TYPE
        SYNTAX  DisplayString (SIZE (0..64))
        ACCESS  read-only
        STATUS  mandatory
        DESCRIPTION
            "The name of the server blade.

            The string will be empty if it could not be determined."
        ::= { cpqRackServerBladeEntry 4 }

    cpqRackServerBladeEnclosureName OBJECT-TYPE
        SYNTAX  DisplayString (SIZE (0..64))
        ACCESS  read-only
        STATUS  mandatory
        DESCRIPTION
            "The name of the enclosure which contains the blade.

            The string will be empty if the enclosure does not report the
            name or it could not be determined."
        ::= { cpqRackServerBladeEntry 5 }

    cpqRackServerBladePartNumber OBJECT-TYPE
        SYNTAX  DisplayString (SIZE (0..64))
        ACCESS  read-only
        STATUS  mandatory
        DESCRIPTION
            "The part number of the server blade.

            The string will be empty if the part number could not be
            determined."
        ::= { cpqRackServerBladeEntry 6 }

    cpqRackServerBladeSparePartNumber OBJECT-TYPE
        SYNTAX  DisplayString (SIZE (0..64))
        ACCESS  read-only
        STATUS  mandatory
        DESCRIPTION
            "The spare part number of the server blade.

            The string will be empty if the part number could not be
            determined."
        ::= { cpqRackServerBladeEntry 7 }

    cpqRackServerBladePosition OBJECT-TYPE
        SYNTAX  INTEGER
        ACCESS  read-only
        STATUS  mandatory
        DESCRIPTION
            "The position or slot number of the server blade within the
            server enclosure.

            This will be -1 if the server enclosure does not report the
            information or it could not be determined."
        ::= { cpqRackServerBladeEntry 8 }

    cpqRackServerBladeHeight OBJECT-TYPE
        SYNTAX  INTEGER
        ACCESS  read-only
        STATUS  mandatory
        DESCRIPTION
            "The height dimension of the rack space taken by the server
            blade expressed in millimeters.

            This will be -1 if the rack does not report the information or
            it could not be determined."
        ::= { cpqRackServerBladeEntry 9 }

    cpqRackServerBladeWidth OBJECT-TYPE
        SYNTAX  INTEGER
        ACCESS  read-only
        STATUS  mandatory
        DESCRIPTION
            "The width dimension of the rack space taken by the server
            blade expressed in millimeters.

            This will be -1 if the rack does not report the information or
            it could not be determined."
        ::= { cpqRackServerBladeEntry 10 }

    cpqRackServerBladeDepth OBJECT-TYPE
        SYNTAX  INTEGER
        ACCESS  read-only
        STATUS  mandatory
        DESCRIPTION
            "The depth dimension of the rack space taken by the server
            blade expressed in millimeters.

            This will be -1 if the rack does not report the information or
            it could not be determined."
        ::= { cpqRackServerBladeEntry 11 }

    cpqRackServerBladePresent OBJECT-TYPE
        SYNTAX  INTEGER {
            other(1),
            absent(2),
            present(3)
            }
        ACCESS  read-only
        STATUS  mandatory
        DESCRIPTION
            "This specifies if the server blade described is present in the
            enclosure."
        ::= { cpqRackServerBladeEntry 12 }

    cpqRackServerBladeHasFuses OBJECT-TYPE
        SYNTAX  INTEGER {
            false(1),
            true(2)
            }
        ACCESS  read-only
        STATUS  mandatory
        DESCRIPTION
            "The server blade contains fuses.

            This will be true(2) is the server blade contains fuses.
            The cpqRackCommonEnclosureFuseTable will contain the fuse
            specific information.

            Match the cpqRackServerBladeEnclosureSerialNum in this table to the
            serial number in the cpqRackCommonEnclosureFanTable to get complete
            information on the fuses."
        ::= { cpqRackServerBladeEntry 13 }

    cpqRackServerBladeEnclosureSerialNum OBJECT-TYPE
        SYNTAX  DisplayString (SIZE (0..64))
        ACCESS  read-only
        STATUS  mandatory
        DESCRIPTION
            "The serial number of the enclosure which contains the blade.

            The string will be empty if the enclosure does not report the
            serial number or it could not be determined."
        ::= { cpqRackServerBladeEntry 14 }

    cpqRackServerBladeSlotsUsed OBJECT-TYPE
        SYNTAX  INTEGER
        ACCESS  read-only
        STATUS  mandatory
        DESCRIPTION
            "The number of slot positions occupied by this server blade.  This
            is used to indicate a server blade which may obscure an adjacent
            blade slot.

            This will be -1 if the rack does not report the information or
            it could not be determined."
        ::= { cpqRackServerBladeEntry 15 }

    cpqRackServerBladeSerialNum OBJECT-TYPE
        SYNTAX  DisplayString (SIZE (0..64))
        ACCESS  read-only
        STATUS  mandatory
        DESCRIPTION
            "The serial number of the server blade.

            The string will be empty if the system does not report the
            serial number function."
        ::= { cpqRackServerBladeEntry 16 }

    cpqRackServerBladeProductId OBJECT-TYPE
        SYNTAX  DisplayString (SIZE (0..64))
        ACCESS  read-only
        STATUS  mandatory
        DESCRIPTION
            "The product id string of the server blade.

            The string will be empty if the system does not report the
            product id function."
        ::= { cpqRackServerBladeEntry 17 }

    cpqRackServerBladeUid OBJECT-TYPE
        SYNTAX  DisplayString (SIZE (0..64))
        ACCESS  read-only
        STATUS  mandatory
        DESCRIPTION
            "The server blade unique identifier (UUID).

            The string will be empty if the blade does not report the
            UUID or if it could not be determined."
        ::= { cpqRackServerBladeEntry 18 }

    cpqRackServerBladeSlotsUsedX OBJECT-TYPE
        SYNTAX  INTEGER
        ACCESS  read-only
        STATUS  mandatory
        DESCRIPTION
            "The number of slot positions in x-direction (from left to right)
            occupied by this server blade.  This is used to indicate a server blade
            which may obscure an adjacent blade slot.

            This will be -1 if the rack does not report the information or
            it could not be determined."
        ::= { cpqRackServerBladeEntry 19 }

    cpqRackServerBladeSlotsUsedY OBJECT-TYPE
        SYNTAX  INTEGER
        ACCESS  read-only
        STATUS  mandatory
        DESCRIPTION
            "The number of slot positions in y-direction (from top to bottom)
            occupied by this server blade.  This is used to indicate a server blade
            which may obscure an adjacent blade slot.

            This will be -1 if the rack does not report the information or
            it could not be determined."
        ::= { cpqRackServerBladeEntry 20 }

    cpqRackServerBladeStatus OBJECT-TYPE
        SYNTAX  INTEGER {
            other(1),
            ok(2),
            degraded(3),
            failed(4)
            }
        ACCESS  read-only
        STATUS  optional
        DESCRIPTION
            "The health status of the blade.

             This will be other(1) if the rack does not report the information
             or if it could not be determined."
        ::= { cpqRackServerBladeEntry 21 }

    cpqRackServerBladeFaultMajor OBJECT-TYPE
        SYNTAX  INTEGER
        ACCESS  read-only
        STATUS  optional
        DESCRIPTION
            "The major fault code of the blade fault
             reported by the enclosure manager.

            This will be -1 if the rack does not report the information or
            if it could not be determined."
        ::= { cpqRackServerBladeEntry 22 }

    cpqRackServerBladeFaultMinor OBJECT-TYPE
        SYNTAX  INTEGER
        ACCESS  read-only
        STATUS  optional
        DESCRIPTION
            "The minor fault code of the blade fault
             reported by the enclosure manager.

             This will be -1 if the rack does not report the information or
             if it could not be determined."
        ::= { cpqRackServerBladeEntry 23 }

    cpqRackServerBladeFaultDiagnosticString OBJECT-TYPE
        SYNTAX  DisplayString (SIZE (0..128))
        ACCESS  read-only
        STATUS  optional
        DESCRIPTION
            "The server blade fault diagnostic string.  This will contain a probable
             cause and potential diagnostic action to be taken to remedy the fault condition.

            The string will be empty if the blade does not report the
            diagnostic string or if it could not be determined."
        ::= { cpqRackServerBladeEntry 24 }

    cpqRackServerBladePowered OBJECT-TYPE
        SYNTAX  INTEGER {
            other(1),
            on(2),
            off(3),
            powerStagedOff(4),
            reboot(5)
            }

        ACCESS  read-write
        STATUS  optional
        DESCRIPTION
            "The power state of the blade.

             This will be other(1) if the rack does not report the information or if it could not be determined."
        ::= { cpqRackServerBladeEntry 25 }

    cpqRackServerBladeUIDState OBJECT-TYPE
        SYNTAX  INTEGER {
            other(1),            -- Unknown device or could not be determined
            none(2),             -- No Unit Identifier LED present
            ledOn(3),            -- Unit Identifier LED is On
            ledOff(4)            -- Unit Identifier LED is Off
            }
        ACCESS  read-write
        STATUS  optional
        DESCRIPTION
            "The Unit Identifier LED.

            This value will be one of the following:

            other(1)
              The state of the LED could not be determined.  Setting the
              LED state is not allowed.

            none(2)
              The LED is not present.  Setting LED state is not allowed.

            ledOn(3)
              The LED is present and ON.  The LED can be turned off
              by setting the cpqRackServerBladeUIDState to ledOff(4).

            ledOff(4)
              The LED is present and OFF.  The LED can be turned on
              by setting the cpqRackServerBladeUIDState to ledOn(3).
                          "
        ::= { cpqRackServerBladeEntry 26 }

    cpqRackServerBladeSystemBIOSRevision OBJECT-TYPE
        SYNTAX  DisplayString (SIZE (0..64))
        ACCESS  read-only
        STATUS  optional
        DESCRIPTION
            "The server blade system bios revision.

             The string will be empty if the blade does not report the
             system bios revision or if it could not be determined."
        ::= { cpqRackServerBladeEntry 27 }

    cpqRackServerBladeSystemBIOSFlashingStatus OBJECT-TYPE
        SYNTAX  INTEGER {
            other(1),               -- Status Unknown  or could not be determined
            normal(2),              -- Blade sytem BIOS not currently in flash mode
            flashing(3)             -- Blade sytem BIOS currently in flash mode
            }
        ACCESS  read-only
        STATUS  optional
        DESCRIPTION
            "Blade server system BIOS flashing / flash mode status indication.

             This will be other(1) if the rack does not report the information or if it could not be determined."
        ::= { cpqRackServerBladeEntry 28 }

   cpqRackServerBladeHasManagementDevice OBJECT-TYPE
        SYNTAX  INTEGER {
            false(1),
            true(2)
            }
        ACCESS  read-only
        STATUS  optional
        DESCRIPTION
            "The blade server contains one or more management devices.

            This will be true(2) if the blade server contains managers and false (1) if not
            or if it can't be detected."
        ::= { cpqRackServerBladeEntry 29 }

   cpqRackServerBladeManagementDeviceFirmwareRevision  OBJECT-TYPE
        SYNTAX  DisplayString (SIZE (0..64))
        ACCESS  read-only
        STATUS  optional
        DESCRIPTION
            "The server blade management device firwmware revision.

             The string will be empty if the blade does not report the
             management device firwmware revision or if it could not be determined."
        ::= { cpqRackServerBladeEntry 30 }

    cpqRackServerBladeManagementDeviceFirmwareFlashingStatus OBJECT-TYPE
        SYNTAX  INTEGER {
            other(1),               -- Status Unknown  or could not be determined
            normal(2),              -- Blade sytem management device not currently in flash mode
            flashing(3)             -- Blade sytem management device currently in flash mode
            }
        ACCESS  read-only
        STATUS  optional
        DESCRIPTION
            "Blade server management device firwmware flashing / flash mode status indication.

             This will be other(1) if the rack does not report this information or if it could not be determined."
        ::= { cpqRackServerBladeEntry 31 }

    cpqRackServerBladeDiagnosticAdaptorPresence OBJECT-TYPE
        SYNTAX  INTEGER {
            other(1),
            absent(2),
            present(3)
            }
        ACCESS  read-only
        STATUS  optional
        DESCRIPTION
            "This specifies if a blade diagnostic adaptor is currently plugged into the system."
        ::= { cpqRackServerBladeEntry 32 }

    cpqRackServerBladeASREnabled OBJECT-TYPE
        SYNTAX  INTEGER {
            false(1),
            true(2)
            }
        ACCESS  read-only
        STATUS  optional
        DESCRIPTION
            "Indicates whether the target blade server has Automatic Service Recovery feature enabled.

            This will be true(2) if the blade server has this feature eanbled and false (1) if not
            or if it can't be detected."
        ::= { cpqRackServerBladeEntry 33 }

    cpqRackServerBladeFrontIOBlankingModeStatus OBJECT-TYPE
        SYNTAX  INTEGER {
            unknown(1),
            inactive(2),
            active(3)
            }
        ACCESS  read-only
        STATUS  optional
        DESCRIPTION
            "Indicates whether the target blade server has the front IO ports blanking feature enabled.

            This will be Active(3) if the blade server has this feature eanbled, Inactive (2) if not,
            or Unknown(1) if it can't be determined."
        ::= { cpqRackServerBladeEntry 34 }

    cpqRackServerBladePOSTStatus   OBJECT-TYPE
        SYNTAX  INTEGER {
            other(1),               -- POST Status Unknown or could not be determined
            started(2),             -- Blade has started Power-on-self-test (POST) process
            completed(3),           -- Blade has finished Power-on-self-test (POST) process
            failed(4)               -- Blade has failed to complete Power-on-self-test (POST) process and halted
            }

        ACCESS  read-only
        STATUS  optional
        DESCRIPTION
            "Blade server power-on self test (POST) status.

             This value will be one of the following:

            other(1)
              The state of the blade POST could not be determined.

            started(2)
              Blade has started Power-on-self-test (POST) process.

            completed(3)
              Blade has finished Power-on-self-test (POST) process.

            failed(4)
              Blade has failed to complete Power-on-self-test (POST) process and halted.

             This will be other(1) if the rack does not report this information or if it could not be determined."
        ::= { cpqRackServerBladeEntry 35 }

     cpqRackServerBladePXEBootModeStatus OBJECT-TYPE
        SYNTAX  INTEGER {
            unknown(1),
            inactive(2),
            active(3)
            }
        ACCESS  read-only
        STATUS  optional
        DESCRIPTION
            "Indicates whether the target blade server is in PXE boot mode.

            This will be Active(3) if the blade server has this feature enbled, Inactive (2) if not,
            or Unknown(1) if it can't be determined."
        ::= { cpqRackServerBladeEntry 36 }

    cpqRackServerBladePendingBootOrderChange   OBJECT-TYPE
        SYNTAX  INTEGER {
            other(1),             --Unknown or cannot be determined
            none(2),              --No Changes
            firstPXE(3),         --Boot To Pre-Boot eXecution (PXE) First
            firstHDD(4),         --First Boot To Local HD
            firstRBSU(5),        --First Boot To ROM Based Setup Utility
            oncePXE(6),          --Boot To Pre-Boot eXecution (PXE) Once
            onceHDD(7),          --Boot To Local HD Once
            onceRBSU(8),         --Boot To ROM Based Setup Utility Once
            alwaysPXE(9),        --Always Boot To Pre-Boot eXecution (PXE)
            alwaysHDD(10),       --Always Boot To Local HD
            alwaysRBSU(11)       --Always Boot To ROM Based Setup Utility
            }
        ACCESS  read-write
        STATUS  optional
        DESCRIPTION
            "Blade server pending boot order setting change state.

            This value will be one of the following:

            other(1) - Unknown or cannot be determined
            none(2) - No Changes
            firstPXE(3)    - Boot To Pre-Boot eXecution (PXE) First
            firstHDD(4)    - First Boot To Local HD
            firstRBSU(5)   - First Boot To ROM Based Setup Utility
            oncePXE(6)     - Boot To Pre-Boot eXecution (PXE) Once
            onceHDD(7)     - Boot To Local HD Once
            onceRBSU(8)    - Boot To ROM Based Setup Utility Once
            alwaysPXE(9)   - Always Boot To Pre-Boot eXecution (PXE)
            alwaysHDD(10)  - Always Boot To Local HD
            alwaysRBSU(11) - Always Boot To ROM Based Setup Utility

            This will be other(1) if the rack does not report this information or if it could not be determined."
        ::= { cpqRackServerBladeEntry 37 }

    cpqRackServerBladeWattageMax OBJECT-TYPE
        SYNTAX  INTEGER
        ACCESS  read-only
        STATUS  optional
        DESCRIPTION
            "Maximum wattage the server has consumed during this power cycle."
        ::= { cpqRackServerBladeEntry 38 }

    cpqRackServerBladeWattageAvg OBJECT-TYPE
        SYNTAX  INTEGER
        ACCESS  read-only
        STATUS  optional
        DESCRIPTION
            "Average wattage the server is consuming, averaged over a period defined by the product."
        ::= { cpqRackServerBladeEntry 39 }

    cpqRackServerBladeWattageMin OBJECT-TYPE
        SYNTAX  INTEGER
        ACCESS  read-only
        STATUS  optional
        DESCRIPTION
            "Minimum wattage the server has consumed, computed from a period defined by the product.  Value
                will be 0 if not supported, but other wattage values are supported."
        ::= { cpqRackServerBladeEntry 40 }

-- ****************************************************************************
--   Rack Server Networking Table
--   =======================
--
-- The compaq enterprise                           (1.3.6.1.4.1.232)
--      cpqRackInfo Group                          (1.3.6.1.4.1.232.22)
--       cpqRackComponent Group                    (1.3.6.1.4.1.232.22.2)
--        cpqRackServer Group                      (1.3.6.1.4.1.232.22.2.4)
--         cpqRackServerNetworking Group           (1.3.6.1.4.1.232.22.2.4.2)
--          cpqRackServerNetworkingTable           (1.3.6.1.4.1.232.22.2.4.2.1)
--
-- ****************************************************************************

    cpqRackServerNetworkingTable OBJECT-TYPE
        SYNTAX  SEQUENCE OF CpqRackServerNetworkingEntry
        ACCESS  not-accessible
        STATUS  optional
        DESCRIPTION
            "A table of rack server networking information."
        ::= { cpqRackServerNetworking 1 }

    cpqRackServerNetworkingEntry OBJECT-TYPE
        SYNTAX  CpqRackServerNetworkingEntry
        ACCESS  not-accessible
        STATUS  optional
        DESCRIPTION
            "A rack server networking description."
        INDEX   { cpqRackServerNetworkingRack,
                  cpqRackServerNetworkingChassis,
                  cpqRackServerNetworkingIndex }
        ::= { cpqRackServerNetworkingTable 1 }

    CpqRackServerNetworkingEntry ::= SEQUENCE {
        cpqRackServerNetworkingRack                   INTEGER,
        cpqRackServerNetworkingChassis                INTEGER,
        cpqRackServerNetworkingIndex                  INTEGER,
        cpqRackServerNetworkingName                   DisplayString,
        cpqRackServerNetworkingEnclosureName          DisplayString,
        cpqRackServerNetworkingEthernetInterfaces     INTEGER,
        cpqRackServerNetworkingEthernetMACAddress     DisplayString
    }

    cpqRackServerNetworkingRack OBJECT-TYPE
        SYNTAX  INTEGER
        ACCESS  read-only
        STATUS  optional
        DESCRIPTION
            "A number that uniquely specifies this rack."
        ::= { cpqRackServerNetworkingEntry 1 }

    cpqRackServerNetworkingChassis OBJECT-TYPE
        SYNTAX  INTEGER
        ACCESS  read-only
        STATUS  mandatory
        DESCRIPTION
            "A number that uniquely specifies this enclosure in the rack."
        ::= { cpqRackServerNetworkingEntry 2 }

    cpqRackServerNetworkingIndex OBJECT-TYPE
        SYNTAX  INTEGER
        ACCESS  read-only
        STATUS  optional
        DESCRIPTION
            "A number that uniquely specifies this server within the enclosure."
        ::= { cpqRackServerNetworkingEntry 3 }

    cpqRackServerNetworkingName OBJECT-TYPE
        SYNTAX  DisplayString (SIZE (0..64))
        ACCESS  read-only
        STATUS  optional
        DESCRIPTION
            "The name of the server.

            The string will be empty if it could not be determined."
        ::= { cpqRackServerNetworkingEntry 4 }

    cpqRackServerNetworkingEnclosureName OBJECT-TYPE
        SYNTAX  DisplayString (SIZE (0..64))
        ACCESS  read-only
        STATUS  optional
        DESCRIPTION
            "The name of the enclosure which contains the server.

            The string will be empty if the enclosure does not report the
            name or if it could not be determined."
        ::= { cpqRackServerNetworkingEntry 5 }

    cpqRackServerNetworkingEthernetInterfaces OBJECT-TYPE
        SYNTAX  INTEGER
        ACCESS  read-only
        STATUS  optional
        DESCRIPTION
            "A number that specifies the amount of
            Ethernet network interfaces in the server."
        ::= { cpqRackServerNetworkingEntry 6 }

    cpqRackServerNetworkingEthernetMACAddress OBJECT-TYPE
        SYNTAX  DisplayString (SIZE (0..64))
        ACCESS  read-only
        STATUS  optional
        DESCRIPTION
            "The MAC address for the Ethernet NIC populated in the server.

            The string will be empty if it could not be determined."
        ::= { cpqRackServerNetworkingEntry 7 }

-- ****************************************************************************
--   Rack Server Temperature Sensor Table
--   =======================
--
-- The compaq enterprise                           (1.3.6.1.4.1.232)
--      cpqRackInfo Group                          (1.3.6.1.4.1.232.22)
--       cpqRackComponent Group                    (1.3.6.1.4.1.232.22.2)
--        cpqRackServer Group                      (1.3.6.1.4.1.232.22.2.4)
--         cpqRackServerTempSensor Group           (1.3.6.1.4.1.232.22.2.4.3)
--          cpqRackServerTempSensorTable           (1.3.6.1.4.1.232.22.2.4.3.1)
--
-- ****************************************************************************

    cpqRackServerTempSensorTable OBJECT-TYPE
        SYNTAX  SEQUENCE OF CpqRackServerTempSensorEntry
        ACCESS  not-accessible
        STATUS  optional
        DESCRIPTION
            "A table of rack server temperature sensor information."
        ::= { cpqRackServerTempSensor 1 }

    cpqRackServerTempSensorEntry OBJECT-TYPE
        SYNTAX  CpqRackServerTempSensorEntry
        ACCESS  not-accessible
        STATUS  optional
        DESCRIPTION
            "A rack server temperature sensor description."
        INDEX   { cpqRackServerTempSensorRack,
                  cpqRackServerTempSensorChassis,
                  cpqRackServerTempSensorIndex }
        ::= { cpqRackServerTempSensorTable 1 }

    CpqRackServerTempSensorEntry ::= SEQUENCE {
        cpqRackServerTempSensorRack                   INTEGER,
        cpqRackServerTempSensorChassis                INTEGER,
        cpqRackServerTempSensorIndex                  INTEGER,
        cpqRackServerTempSensorName                   DisplayString,
        cpqRackServerTempSensorEnclosureName          DisplayString,
        cpqRackServerTempSensorCount                  INTEGER,
        cpqRackServerTempSensorLocation               DisplayString,
        cpqRackServerTempSensorCurrent                INTEGER,
        cpqRackServerTempSensorThreshold              INTEGER,
        cpqRackServerTempSensorCondition              INTEGER,
        cpqRackServerTempSensorType                   INTEGER
                }

    cpqRackServerTempSensorRack OBJECT-TYPE
        SYNTAX  INTEGER
        ACCESS  read-only
        STATUS  optional
        DESCRIPTION
            "A number that uniquely specifies this rack."
        ::= { cpqRackServerTempSensorEntry 1 }

    cpqRackServerTempSensorChassis OBJECT-TYPE
        SYNTAX  INTEGER
        ACCESS  read-only
        STATUS  optional
        DESCRIPTION
            "A number that uniquely specifies this enclosure in the rack."
        ::= { cpqRackServerTempSensorEntry 2 }

    cpqRackServerTempSensorIndex OBJECT-TYPE
        SYNTAX  INTEGER
        ACCESS  read-only
        STATUS  optional
        DESCRIPTION
            "A number that uniquely specifies this server within the enclosure."
        ::= { cpqRackServerTempSensorEntry 3 }

    cpqRackServerTempSensorName OBJECT-TYPE
        SYNTAX  DisplayString (SIZE (0..64))
        ACCESS  read-only
        STATUS  optional
        DESCRIPTION
            "The name of the server.

            The string will be empty if it could not be determined."
        ::= { cpqRackServerTempSensorEntry 4 }

    cpqRackServerTempSensorEnclosureName OBJECT-TYPE
        SYNTAX  DisplayString (SIZE (0..64))
        ACCESS  read-only
        STATUS  optional
        DESCRIPTION
            "The name of the enclosure which contains the server.

            The string will be empty if the enclosure does not report the
            name or if it could not be determined."
        ::= { cpqRackServerTempSensorEntry 5 }

    cpqRackServerTempSensorCount OBJECT-TYPE
        SYNTAX  INTEGER
        ACCESS  read-only
        STATUS  optional
        DESCRIPTION
            "A number that specifies the amount of
            temperature sensors in the server."
        ::= { cpqRackServerTempSensorEntry 6 }

    cpqRackServerTempSensorLocation OBJECT-TYPE
        SYNTAX  DisplayString (SIZE (0..64))
        ACCESS  read-only
        STATUS  optional
        DESCRIPTION
            "The location description of the temperature sensor within the
            blade server.

            The string will be empty if it could not be determined."
        ::= { cpqRackServerTempSensorEntry 7 }

   cpqRackServerTempSensorCurrent OBJECT-TYPE
        SYNTAX  INTEGER
        ACCESS  read-only
        STATUS  optional
        DESCRIPTION
            "This is the current temperature sensor reading in degrees
            celsius.

            If this value cannot be determined by software, then a value
            of -1 will be returned."
        ::= { cpqRackServerTempSensorEntry 8 }

    cpqRackServerTempSensorThreshold OBJECT-TYPE
        SYNTAX  INTEGER
        ACCESS  read-only
        STATUS  optional
        DESCRIPTION
            "This is the threshold temperature sensor setting
            in degrees celsius.  This is the temperature in which the
            sensor will be considered to be in a tripped state this
            causing some action to occur depending on the type of
            the sensor.  The action of temperature sensor threshold
            will be indicated by the cpqRackServerTempSensorType
            item.  If the type is blowout(5), then the temperature sensor
            will cause the fans to speed up.  If the type is caution(9),
            then the temperature sensor is in a degraded state.  If the
            type is critical(15), then the enclosure will be considered
            as in a failed state.

            If this value cannot be determined by software, then a value
            of -1 will be returned."
        ::= { cpqRackServerTempSensorEntry 9 }

    cpqRackServerTempSensorCondition OBJECT-TYPE
        SYNTAX  INTEGER {
            other(1),
            ok(2),
            degraded(3),
            failed(4)
            }
        ACCESS  read-only
        STATUS  optional
        DESCRIPTION
            "The Temperature sensor condition.

            This value will be one of the following:

            other(1)
              Temperature could not be determined.

            ok(2)
              The temperature sensor is within the normal operating range.

            degraded(3)
              The temperature sensor is outside of the normal operating range.

            failed(4)
              The temperature sensor detects a condition that could
              possibly overheat the system.

            The system will automatically shutdown if the failed(4) condition
            results, so it is unlikely that this value will ever be returned
            by the agent."
        ::= { cpqRackServerTempSensorEntry 10 }

    cpqRackServerTempSensorType OBJECT-TYPE
        SYNTAX  INTEGER {
            other(1),
            blowout(5),
            caution(9),
            critical(15)
            }
        ACCESS  read-only
        STATUS  optional
        DESCRIPTION
            "This specifies the type of this instance of temperature
            sensor.

            This value will be one of the following:

            other(1)
              Temperature threshold type could not be determined.

            blowout(5)
              If a blowout(5) temperature sensor reaches its threshold,
              the fan or fans in the area of the temperature sensor will
              increase in speed in an attempt to reduce the temperature
              before a caution or critical threshold is reached.

            caution(9)
              If a caution(9) temperature sensor reaches its threshold, the
              cpqRackServerTempSensorCondition will be set to degraded(3)
              and the system will either continue or shutdown depending
              on the local blade server policy settings.

            critical(15)
              If a critical(15) temperature sensor reaches its threshold,
              cpqRackServerTempSensorCondition will be set to failed(4)
              and the blade server will shutdown."
        ::= { cpqRackServerTempSensorEntry 11 }

-- ****************************************************************************
--   Rack Power Supply Table
--   =======================
--
-- The compaq enterprise                 (1.3.6.1.4.1.232)
--      cpqRackInfo Group                (1.3.6.1.4.1.232.22)
--       cpqRackComponent Group          (1.3.6.1.4.1.232.22.2)
--        cpqRackPower Group             (1.3.6.1.4.1.232.22.2.5)
--         cpqRackPowerSupply Group      (1.3.6.1.4.1.232.22.2.5.1)
--          cpqRackPowerSupplyTable      (1.3.6.1.4.1.232.22.2.5.1.1)
--
-- ****************************************************************************

    cpqRackPowerSupplyTable OBJECT-TYPE
        SYNTAX  SEQUENCE OF CpqRackPowerSupplyEntry
        ACCESS  not-accessible
        STATUS  mandatory
        DESCRIPTION
            "A table of rack power supply information."
        ::= { cpqRackPowerSupply 1 }

    cpqRackPowerSupplyEntry OBJECT-TYPE
        SYNTAX  CpqRackPowerSupplyEntry
        ACCESS  not-accessible
        STATUS  mandatory
        DESCRIPTION
            "A rack power supply description."
        INDEX   { cpqRackPowerSupplyRack,
                  cpqRackPowerSupplyChassis,
                  cpqRackPowerSupplyIndex }
        ::= { cpqRackPowerSupplyTable 1 }

    CpqRackPowerSupplyEntry ::= SEQUENCE {
        cpqRackPowerSupplyRack                  INTEGER,
        cpqRackPowerSupplyChassis               INTEGER,
        cpqRackPowerSupplyIndex                 INTEGER,
        cpqRackPowerSupplyEnclosureName         DisplayString,
        cpqRackPowerSupplySerialNum             DisplayString,
        cpqRackPowerSupplyPartNumber            DisplayString,
        cpqRackPowerSupplySparePartNumber       DisplayString,
        cpqRackPowerSupplyFWRev                 DisplayString,
        cpqRackPowerSupplyMaxPwrOutput          INTEGER,
        cpqRackPowerSupplyCurPwrOutput          INTEGER,
        cpqRackPowerSupplyPosition              INTEGER,
        cpqRackPowerSupplyIntakeTemp            INTEGER,
        cpqRackPowerSupplyExhaustTemp           INTEGER,
        cpqRackPowerSupplyStatus                INTEGER,
        cpqRackPowerSupplyInputLineStatus       INTEGER,
        cpqRackPowerSupplyPresent               INTEGER,
        cpqRackPowerSupplyCondition             INTEGER,
        cpqRackPowerSupplyEnclosureSerialNum    DisplayString,
        cpqRackPowerSupplyMeterPort             INTEGER,
        cpqRackPowerSupplyInputCurrent          INTEGER,
        cpqRackPowerSupplyInputPower            INTEGER,
        cpqRackPowerSupplyInputVoltage          INTEGER,
        cpqRackPowerSupplyOutputCurrent         INTEGER,
        cpqRackPowerSupplyOutputPower           INTEGER,
        cpqRackPowerSupplyOutputVoltage         INTEGER
    }

    cpqRackPowerSupplyRack OBJECT-TYPE
        SYNTAX  INTEGER
        ACCESS  read-only
        STATUS  mandatory
        DESCRIPTION
            "A number that uniquely specifies this rack."
        ::= { cpqRackPowerSupplyEntry 1 }

    cpqRackPowerSupplyChassis OBJECT-TYPE
        SYNTAX  INTEGER
        ACCESS  read-only
        STATUS  mandatory
        DESCRIPTION
            "A number that uniquely specifies this power enclosure in the rack."
        ::= { cpqRackPowerSupplyEntry 2 }

    cpqRackPowerSupplyIndex OBJECT-TYPE
        SYNTAX  INTEGER
        ACCESS  read-only
        STATUS  mandatory
        DESCRIPTION
            "A number that uniquely specifies this power supply in the enclosure."
        ::= { cpqRackPowerSupplyEntry 3 }

    cpqRackPowerSupplyEnclosureName OBJECT-TYPE
        SYNTAX  DisplayString (SIZE (0..64))
        ACCESS  read-only
        STATUS  mandatory
        DESCRIPTION
            "The name of the power supply enclosure in which this power supply
            resides.

            The string will be empty if the enclosure does not report the
            name or it could not be determined."
        ::= { cpqRackPowerSupplyEntry 4 }

    cpqRackPowerSupplySerialNum OBJECT-TYPE
        SYNTAX  DisplayString (SIZE (0..64))
        ACCESS  read-only
        STATUS  mandatory
        DESCRIPTION
            "The serial number of the power supply.

            The string will be empty if the power supply does not report the
            serial number."
        ::= { cpqRackPowerSupplyEntry 5 }

    cpqRackPowerSupplyPartNumber OBJECT-TYPE
        SYNTAX  DisplayString (SIZE (0..64))
        ACCESS  read-only
        STATUS  mandatory
        DESCRIPTION
            "The part number of the power supply.

            The string will be empty if the power supply does not report this
            function."
        ::= { cpqRackPowerSupplyEntry 6 }

    cpqRackPowerSupplySparePartNumber OBJECT-TYPE
        SYNTAX  DisplayString (SIZE (0..64))
        ACCESS  read-only
        STATUS  mandatory
        DESCRIPTION
            "The spare part number of the power supply.

            The string will be empty if the power supply does not report this
            function."
        ::= { cpqRackPowerSupplyEntry 7 }

    cpqRackPowerSupplyFWRev OBJECT-TYPE
        SYNTAX  DisplayString (SIZE (0..64))
        ACCESS  read-only
        STATUS  mandatory
        DESCRIPTION
            "The firmware revision of the power supply.

            The string will be empty if the power supply does not report the
            firmware revision."
        ::= { cpqRackPowerSupplyEntry 8 }

    cpqRackPowerSupplyMaxPwrOutput OBJECT-TYPE
        SYNTAX  INTEGER
        ACCESS  read-only
        STATUS  mandatory
        DESCRIPTION
            "The maximum power output of the power supply in watts.

            The value will be -1 if the power supply does not report the
            value."
        ::= { cpqRackPowerSupplyEntry 9 }

    cpqRackPowerSupplyCurPwrOutput OBJECT-TYPE
        SYNTAX  INTEGER
        ACCESS  read-only
        STATUS  mandatory
        DESCRIPTION
            "The current power output of the power supply in watts.

            The value will be -1 if the power supply does not report the
            value."
        ::= { cpqRackPowerSupplyEntry 10 }

    cpqRackPowerSupplyPosition OBJECT-TYPE
        SYNTAX  INTEGER
        ACCESS  read-only
        STATUS  mandatory
        DESCRIPTION
            "The position of the power supply within the power enclosure.

            This will be -1 if the power enclosure does not report the
            power supply information or it could not be determined."
        ::= { cpqRackPowerSupplyEntry 11 }

    cpqRackPowerSupplyIntakeTemp OBJECT-TYPE
        SYNTAX  INTEGER
        ACCESS  read-only
        STATUS  mandatory
        DESCRIPTION
            "The current air temperature at the intake of the power supply
            in degrees celsius.

            The value will be -1 if the power supply does not report the
            value."
        ::= { cpqRackPowerSupplyEntry 12 }

    cpqRackPowerSupplyExhaustTemp OBJECT-TYPE
        SYNTAX  INTEGER
        ACCESS  read-only
        STATUS  mandatory
        DESCRIPTION
            "The current air temperature at the exhaust of the power supply
            in degrees celsius.

            The value will be -1 if the power supply does not report the
            value."
        ::= { cpqRackPowerSupplyEntry 13 }

    cpqRackPowerSupplyStatus OBJECT-TYPE
        SYNTAX  INTEGER {
            noError(1),
            generalFailure(2),
            bistFailure(3),
            fanFailure(4),
            tempFailure(5),
            interlockOpen(6),
            epromFailed(7),
            vrefFailed(8),
            dacFailed(9),
            ramTestFailed(10),
            voltageChannelFailed(11),
            orringdiodeFailed(12),
            brownOut(13),
            giveupOnStartup(14),
            nvramInvalid(15),
            calibrationTableInvalid(16)
            }
        ACCESS  read-only
        STATUS  mandatory
        DESCRIPTION
            "The status of the power supply."
        ::= { cpqRackPowerSupplyEntry 14 }

    cpqRackPowerSupplyInputLineStatus OBJECT-TYPE
        SYNTAX  INTEGER {
            noError(1),
            lineOverVoltage(2),
            lineUnderVoltage(3),
            lineHit(4),
            brownOut(5),
            linePowerLoss(6)
            }
        ACCESS  read-only
        STATUS  mandatory
        DESCRIPTION
            "The status of line input power."
        ::= { cpqRackPowerSupplyEntry 15 }

    cpqRackPowerSupplyPresent OBJECT-TYPE
        SYNTAX  INTEGER {
            other(1),
            absent(2),
            present(3)
            }
        ACCESS  read-only
        STATUS  mandatory
        DESCRIPTION
            "This specifies if the power supply described is present in the
            enclosure."
        ::= { cpqRackPowerSupplyEntry 16 }

    cpqRackPowerSupplyCondition OBJECT-TYPE
        SYNTAX  INTEGER {
            other(1),
            ok(2),
            degraded(3),
            failed(4)
            }
        ACCESS  read-only
        STATUS  mandatory
        DESCRIPTION
            "The condition of the power supply.

            This value will be one of the following:

            other(1)
              The status could not be determined or not present.

            ok(2)
              The power supply is operating normally.

            degraded(3)
              A temperature sensor, fan or other power supply component is
              outside of normal operating range.

            failed(4)
              A power supply component detects a condition that could
              possibly damage the system."
        ::= { cpqRackPowerSupplyEntry 17 }

    cpqRackPowerSupplyEnclosureSerialNum OBJECT-TYPE
        SYNTAX  DisplayString (SIZE (0..64))
        ACCESS  read-only
        STATUS  mandatory
        DESCRIPTION
            "The serial number of the power supply enclosure in which this
            power supply resides.

            The string will be empty if the enclosure does not report the
            serial number or it could not be determined."
        ::= { cpqRackPowerSupplyEntry 18 }

    cpqRackPowerSupplyMeterPort OBJECT-TYPE
        SYNTAX  INTEGER
        ACCESS  read-only
        STATUS  mandatory
        DESCRIPTION
            "The corresponding meter used to measure current for this power supply

            The integer will be -1 if the enclosure does not report the value
            or it could not be determined."
        ::= { cpqRackPowerSupplyEntry 19 }

    cpqRackPowerSupplyInputCurrent OBJECT-TYPE
        SYNTAX  INTEGER
        ACCESS  read-only
        STATUS  mandatory
        DESCRIPTION
            "Input current for the power supply

            The integer will be -1 if the enclosure does not report the value
            or it could not be determined."
        ::= { cpqRackPowerSupplyEntry 20 }

    cpqRackPowerSupplyInputPower OBJECT-TYPE
        SYNTAX  INTEGER
        ACCESS  read-only
        STATUS  mandatory
        DESCRIPTION
            "Input wattage for the power supply

            The integer will be -1 if the enclosure does not report the value
            or it could not be determined."
        ::= { cpqRackPowerSupplyEntry 21 }

    cpqRackPowerSupplyInputVoltage OBJECT-TYPE
        SYNTAX  INTEGER
        ACCESS  read-only
        STATUS  mandatory
        DESCRIPTION
            "Input voltage for the power supply

            The integer will be -1 if the enclosure does not report the value
            or it could not be determined."
        ::= { cpqRackPowerSupplyEntry 22 }

    cpqRackPowerSupplyOutputCurrent OBJECT-TYPE
        SYNTAX  INTEGER
        ACCESS  read-only
        STATUS  mandatory
        DESCRIPTION
            "Output current for the power supply

            The integer will be -1 if the enclosure does not report the value
            or it could not be determined."
        ::= { cpqRackPowerSupplyEntry 23 }

    cpqRackPowerSupplyOutputPower OBJECT-TYPE
        SYNTAX  INTEGER
        ACCESS  read-only
        STATUS  mandatory
        DESCRIPTION
            "Output wattage for the power supply

            The integer will be -1 if the enclosure does not report the value
            or it could not be determined."
        ::= { cpqRackPowerSupplyEntry 24 }

    cpqRackPowerSupplyOutputVoltage OBJECT-TYPE
        SYNTAX  INTEGER
        ACCESS  read-only
        STATUS  mandatory
        DESCRIPTION
            "Output voltage for the power supply

            The integer will be -1 if the enclosure does not report the value
            or it could not be determined."
        ::= { cpqRackPowerSupplyEntry 25 }

-- ****************************************************************************
--   Rack Power Meter Table
--   =======================
--
-- The compaq enterprise                 (1.3.6.1.4.1.232)
--      cpqRackInfo Group                (1.3.6.1.4.1.232.22)
--       cpqRackComponent Group          (1.3.6.1.4.1.232.22.2)
--        cpqRackPower Group             (1.3.6.1.4.1.232.22.2.5)
--         cpqRackMeter Group            (1.3.6.1.4.1.232.22.2.5.2)
--          cpqRackPowerMeterTable       (1.3.6.1.4.1.232.22.2.5.2.1)
--
-- ****************************************************************************

    cpqRackPowerMeterTable OBJECT-TYPE
        SYNTAX  SEQUENCE OF CpqRackPowerMeterEntry
        ACCESS  not-accessible
        STATUS  mandatory
        DESCRIPTION
            "A table of rack power meter information."
        ::= { cpqRackPowerMeter 1 }

    cpqRackPowerMeterEntry OBJECT-TYPE
        SYNTAX  CpqRackPowerMeterEntry
        ACCESS  not-accessible
        STATUS  mandatory
        DESCRIPTION
            "A rack power meter description."
        INDEX   { cpqRackPowerMeterRack,
                  cpqRackPowerMeterChassis,
                  cpqRackPowerMeterIndex }
        ::= { cpqRackPowerMeterTable 1 }

    CpqRackPowerMeterEntry ::= SEQUENCE {
        cpqRackPowerMeterRack                   INTEGER,
        cpqRackPowerMeterChassis                INTEGER,
        cpqRackPowerMeterIndex                  INTEGER,
        cpqRackPowerMeterType                   DisplayString,
	cpqRackPowerMeterPort                   INTEGER,
        cpqRackPowerMeterStatus                 DisplayString,
        cpqRackPowerMeterCurrent                INTEGER,
        cpqRackPowerMeterWattage                INTEGER
    }

    cpqRackPowerMeterRack OBJECT-TYPE
        SYNTAX  INTEGER
        ACCESS  read-only
        STATUS  mandatory
        DESCRIPTION
            "A number that uniquely specifies this rack."
        ::= { cpqRackPowerMeterEntry 1 }

    cpqRackPowerMeterChassis OBJECT-TYPE
        SYNTAX  INTEGER
        ACCESS  read-only
        STATUS  mandatory
        DESCRIPTION
            "A number that uniquely specifies this power enclosure in the rack."
        ::= { cpqRackPowerMeterEntry 2 }

    cpqRackPowerMeterIndex OBJECT-TYPE
        SYNTAX  INTEGER
        ACCESS  read-only
        STATUS  mandatory
        DESCRIPTION
            "A number that uniquely specifies this power meter in the enclosure."
        ::= { cpqRackPowerMeterEntry 3 }

    cpqRackPowerMeterType OBJECT-TYPE
        SYNTAX  DisplayString (SIZE (0..64))
        ACCESS  read-only
        STATUS  mandatory
        DESCRIPTION
            "Class type of power meter - for example 480V

            The string will be empty if the enclosure does not report the
            name or it could not be determined."
        ::= { cpqRackPowerMeterEntry 4 }

    cpqRackPowerMeterPort OBJECT-TYPE
        SYNTAX  INTEGER
        ACCESS  read-only
        STATUS  mandatory
        DESCRIPTION
            "Which port on the power enclosure interfaces to this meter

            The value will be -1 if the power supply does not report
            this."
        ::= { cpqRackPowerMeterEntry 5 }

    cpqRackPowerMeterStatus OBJECT-TYPE
        SYNTAX  DisplayString (SIZE (0..64))
        ACCESS  read-only
        STATUS  mandatory
        DESCRIPTION
            "Operational status value bit field (in hex) from the power meter.
            Used for diagnostic purposes.
            Bit definitions are as follows:
            bit 3 is for SPI communications - 1 is good, 0 is fault
            bit 2 is for general purpose alert - 1 is alert, 0 is no alert
            bit 1 is e-brake - 1 is e-brake mode, 0 is not e-brake mode
            bit 0 is meter presence - 1 is present, 0 is not present

            The string will be empty if the power supply does not report this
            function."
        ::= { cpqRackPowerMeterEntry 6 }

    cpqRackPowerMeterCurrent OBJECT-TYPE
        SYNTAX  INTEGER
        ACCESS  read-only
        STATUS  mandatory
        DESCRIPTION
            "The current measured by the power meter

            The value will be -1 if the power supply does not report
            this."
        ::= { cpqRackPowerMeterEntry 7 }

    cpqRackPowerMeterWattage OBJECT-TYPE
        SYNTAX  INTEGER
        ACCESS  read-only
        STATUS  mandatory
        DESCRIPTION
            "The total wattage measured by the power meter

            The value will be -1 if the power supply does not report
            this."
        ::= { cpqRackPowerMeterEntry 8 }


-- ****************************************************************************
--   Rack Network
--   ============
--
-- The compaq enterprise                 (1.3.6.1.4.1.232)
--      cpqRackInfo Group                (1.3.6.1.4.1.232.22)
--       cpqRackComponent Group          (1.3.6.1.4.1.232.22.2)
--        cpqRackNetwork Group           (1.3.6.1.4.1.232.22.2.6)
--
-- ****************************************************************************

    cpqRackNetworkAddressesTable OBJECT-TYPE
        SYNTAX  SEQUENCE OF CpqRackNetworkAddressesEntry
        ACCESS  not-accessible
        STATUS  mandatory
        DESCRIPTION
            "A table of rack network addresses."
        ::= { cpqRackNetwork 2}

    cpqRackNetworkAddressesEntry OBJECT-TYPE
        SYNTAX  CpqRackNetworkAddressesEntry
        ACCESS  not-accessible
        STATUS  mandatory
        DESCRIPTION
            "Array of ALL the network addresses of the system generating the indication.

            This may include IPv4 addresses (based on IETF RFC 1208) or IPv6 addresses
            (based on IETF RFC 4291)."
        INDEX  { cpqRackNetworkAddresses }
        ::= { cpqRackNetworkAddressesTable 1}

    CpqRackNetworkAddressesEntry ::= SEQUENCE {
        cpqRackNetworkAddresses                    DisplayString
    }

    cpqRackNetworkAddresses OBJECT-TYPE
        SYNTAX  DisplayString (SIZE (0..50))
        ACCESS  read-only
        STATUS  mandatory
        DESCRIPTION
            "A network address of the system generating the indication."
        ::= { cpqRackNetworkAddressesEntry 1}


-- ****************************************************************************
--   Rack Network Connector Table
--   ============================
--
-- The compaq enterprise                 (1.3.6.1.4.1.232)
--      cpqRackInfo Group                (1.3.6.1.4.1.232.22)
--       cpqRackComponent Group          (1.3.6.1.4.1.232.22.2)
--        cpqRackNetwork Group           (1.3.6.1.4.1.232.22.2.6)
--         cpqRackNetConnector Group     (1.3.6.1.4.1.232.22.2.6.1)
--          cpqRackNetConnectorTable     (1.3.6.1.4.1.232.22.2.6.1.1)
--
-- ****************************************************************************

    cpqRackNetConnectorTable OBJECT-TYPE
        SYNTAX  SEQUENCE OF CpqRackNetConnectorEntry
        ACCESS  not-accessible
        STATUS  mandatory
        DESCRIPTION
            "A table of rack network connector information."
        ::= { cpqRackNetConnector 1 }

    cpqRackNetConnectorEntry OBJECT-TYPE
        SYNTAX  CpqRackNetConnectorEntry
        ACCESS  not-accessible
        STATUS  mandatory
        DESCRIPTION
            "A rack network connector description."
        INDEX   { cpqRackNetConnectorRack,
                  cpqRackNetConnectorChassis,
                  cpqRackNetConnectorIndex }
        ::= { cpqRackNetConnectorTable 1 }

    CpqRackNetConnectorEntry ::= SEQUENCE {
        cpqRackNetConnectorRack                 INTEGER,
        cpqRackNetConnectorChassis              INTEGER,
        cpqRackNetConnectorIndex                INTEGER,
        cpqRackNetConnectorEnclosureName        DisplayString,
        cpqRackNetConnectorName                 DisplayString,
        cpqRackNetConnectorModel                DisplayString,
        cpqRackNetConnectorSerialNum            DisplayString,
        cpqRackNetConnectorPartNumber           DisplayString,
        cpqRackNetConnectorSparePartNumber      DisplayString,
        cpqRackNetConnectorFWRev                DisplayString,
        cpqRackNetConnectorType                 INTEGER,
        cpqRackNetConnectorLocation             DisplayString,
        cpqRackNetConnectorPresent              INTEGER,
        cpqRackNetConnectorHasFuses             INTEGER,
        cpqRackNetConnectorEnclosureSerialNum   DisplayString,
        cpqRackNetConnectorTechnologyType       INTEGER,
        cpqRackNetConnectorDeviceType                   INTEGER
    }

    cpqRackNetConnectorRack OBJECT-TYPE
        SYNTAX  INTEGER
        ACCESS  read-only
        STATUS  mandatory
        DESCRIPTION
            "A number that uniquely specifies this rack."
        ::= { cpqRackNetConnectorEntry 1 }

    cpqRackNetConnectorChassis OBJECT-TYPE
        SYNTAX  INTEGER
        ACCESS  read-only
        STATUS  mandatory
        DESCRIPTION
            "A number that uniquely specifies this server enclosure in the rack."
        ::= { cpqRackNetConnectorEntry 2 }

    cpqRackNetConnectorIndex OBJECT-TYPE
        SYNTAX  INTEGER
        ACCESS  read-only
        STATUS  mandatory
        DESCRIPTION
            "A number that uniquely specifies this network connector in the rack."
        ::= { cpqRackNetConnectorEntry 3 }

    cpqRackNetConnectorEnclosureName OBJECT-TYPE
        SYNTAX  DisplayString (SIZE (0..64))
        ACCESS  read-only
        STATUS  mandatory
        DESCRIPTION
            "The name of the network connector enclosure.

            The string will be empty if the enclosure does not report the
            name or it could not be determined."
        ::= { cpqRackNetConnectorEntry 4 }

    cpqRackNetConnectorName OBJECT-TYPE
        SYNTAX  DisplayString (SIZE (0..64))
        ACCESS  read-only
        STATUS  mandatory
        DESCRIPTION
            "The name of the network connector.

            The string will be empty if the network connector does not report the
            name or it could not be determined."
        ::= { cpqRackNetConnectorEntry 5 }

    cpqRackNetConnectorModel OBJECT-TYPE
        SYNTAX  DisplayString (SIZE (0..64))
        ACCESS  read-only
        STATUS  mandatory
        DESCRIPTION
            "The model name of the network connector.

            The string will be empty if the network connector does not report the
            model information."
        ::= { cpqRackNetConnectorEntry 6 }

    cpqRackNetConnectorSerialNum OBJECT-TYPE
        SYNTAX  DisplayString (SIZE (0..64))
        ACCESS  read-only
        STATUS  mandatory
        DESCRIPTION
            "The serial number of the network connector.

            The string will be empty if the network connector does not report the
            serial number."
        ::= { cpqRackNetConnectorEntry 7 }

    cpqRackNetConnectorPartNumber OBJECT-TYPE
        SYNTAX  DisplayString (SIZE (0..64))
        ACCESS  read-only
        STATUS  mandatory
        DESCRIPTION
            "The part number of the network connector.

            The string will be empty if the enclosure does not report this
            function."
        ::= { cpqRackNetConnectorEntry 8 }

    cpqRackNetConnectorSparePartNumber OBJECT-TYPE
        SYNTAX  DisplayString (SIZE (0..64))
        ACCESS  read-only
        STATUS  mandatory
        DESCRIPTION
            "The spare part number of the network connector.

            The string will be empty if the enclosure does not report this
            function."
        ::= { cpqRackNetConnectorEntry 9 }

    cpqRackNetConnectorFWRev OBJECT-TYPE
        SYNTAX  DisplayString (SIZE (0..64))
        ACCESS  read-only
        STATUS  mandatory
        DESCRIPTION
            "The firmware revision of the network connector.

            The string will be empty if the network connector does not report the
            firmware revision."
        ::= { cpqRackNetConnectorEntry 10 }

    cpqRackNetConnectorType OBJECT-TYPE
        SYNTAX  INTEGER {
            other(1),
            passive(2),
            active(3)
            }
        ACCESS  read-only
        STATUS  mandatory
        DESCRIPTION
            "The type of network connector within the enclosure."
        ::= { cpqRackNetConnectorEntry 11 }

    cpqRackNetConnectorLocation OBJECT-TYPE
        SYNTAX  DisplayString (SIZE (0..64))
        ACCESS  read-only
        STATUS  mandatory
        DESCRIPTION
            "The location of the network connector within the enclosure."
        ::= { cpqRackNetConnectorEntry 12 }

    cpqRackNetConnectorPresent OBJECT-TYPE
        SYNTAX  INTEGER {
            other(1),
            absent(2),
            present(3)
            }
        ACCESS  read-only
        STATUS  mandatory
        DESCRIPTION
            "This specifies if the network connector described is present in the
            enclosure."
        ::= { cpqRackNetConnectorEntry 13 }

    cpqRackNetConnectorHasFuses OBJECT-TYPE
        SYNTAX  INTEGER {
            false(1),
            true(2)
            }
        ACCESS  read-only
        STATUS  mandatory
        DESCRIPTION
            "The network connector contains fuses.

            This will be true(2) is the network connector contains fuses.
            The cpqRackCommonEnclosureFuseTable will contain the fuse
            specific information.

            Match the cpqRackNetworkEnclosureSerialNum in this table to the
            serial number in the cpqRackCommonEnclosureFusTable to get complete
            information on the fuses."
        ::= { cpqRackNetConnectorEntry 14 }

    cpqRackNetConnectorEnclosureSerialNum OBJECT-TYPE
        SYNTAX  DisplayString (SIZE (0..64))
        ACCESS  read-only
        STATUS  mandatory
        DESCRIPTION
            "The serial number of the enclosure containing the network connector.

            The string will be empty if the enclosure does not report the
            serial number or it could not be determined."
        ::= { cpqRackNetConnectorEntry 15 }

    cpqRackNetConnectorTechnologyType OBJECT-TYPE
        SYNTAX  INTEGER {
            other(1),
            passive(2),
            active(3)
            }
        ACCESS  read-only
        STATUS  mandatory
        DESCRIPTION
            "The type of network connector within the enclosure."
        ::= { cpqRackNetConnectorEntry 16 }

     cpqRackNetConnectorDeviceType OBJECT-TYPE
         SYNTAX INTEGER {
             noconnect(1),
             network(2),
             fibrechannel(3),
             sas(4),
             inifiband(5),
             pciexpress(6)
             }
          ACCESS read-only
          STATUS mandatory
          DESCRIPTION
              "The type of interrconnect in the enclosure.

               This will be -1 if it is not reported or can not be deteremined."
          ::= { cpqRackNetConnectorEntry 17 }

-- ****************************************************************************
--   Rack Hardware Information
--   =========================
--
-- The compaq enterprise                 (1.3.6.1.4.1.232)
--      cpqRackInfo Group                (1.3.6.1.4.1.232.22)
--       cpqRackComponent Group          (1.3.6.1.4.1.232.22.2)
--        cpqRackHW Group                (1.3.6.1.4.1.232.22.2.7)
--
-- ****************************************************************************

    cpqRackHWPartNumber OBJECT-TYPE
        SYNTAX  DisplayString (SIZE (0..16))
        ACCESS  read-only
        STATUS  optional
        DESCRIPTION
            "Part number for the hardware generating the indication."
        ::= { cpqRackHW 1 }

    cpqRackHWFirmwareVersionTable OBJECT-TYPE
        SYNTAX  SEQUENCE OF CpqRackHWFirmwareVersionEntry
        ACCESS  not-accessible
        STATUS  optional
        DESCRIPTION
            "A table of rack firmware versions."
        ::= { cpqRackHW 2 }

    cpqRackHWFirmwareVersionEntry OBJECT-TYPE
        SYNTAX  CpqRackHWFirmwareVersionEntry
        ACCESS  not-accessible
        STATUS  optional
        DESCRIPTION
            "Array of versions of firmware for the hardware associated with the indication."
        INDEX { cpqRackHWFirmwareVersion }
        ::= { cpqRackHWFirmwareVersionTable 1 }

    CpqRackHWFirmwareVersionEntry ::= SEQUENCE {
        cpqRackHWFirmwareVersion  DisplayString
    }

    cpqRackHWFirmwareVersion OBJECT-TYPE
        SYNTAX  DisplayString (SIZE (0..30))
        ACCESS  read-only
        STATUS  optional
        DESCRIPTION
           "A version of firmware for the hardware associated with the indication."
        ::= { cpqRackHWFirmwareVersionEntry 1 }

    cpqRackHWManufacturer OBJECT-TYPE
        SYNTAX  DisplayString (SIZE (0..65))
        ACCESS  read-only
        STATUS  optional
        DESCRIPTION
            "Manufacturer of the hardware associated with the indication.Device indication
            hardware manufacturer."
        ::= { cpqRackHW 3 }

    cpqRackHWSerialNumberTable OBJECT-TYPE
        SYNTAX  SEQUENCE OF CpqRackHWSerialNumberEntry
        ACCESS  not-accessible
        STATUS  optional
        DESCRIPTION
            "A table of rack hardware serial numbers."
        ::= { cpqRackHW 4 }

    cpqRackHWSerialNumberEntry OBJECT-TYPE
        SYNTAX  CpqRackHWSerialNumberEntry
        ACCESS  not-accessible
        STATUS  optional
        DESCRIPTION
            "Array of all the serial numbers of the hardware associated with the indication."
        INDEX  { cpqRackHWSerialNumber }
        ::= { cpqRackHWSerialNumberTable 1 }

    CpqRackHWSerialNumberEntry ::= SEQUENCE {
       cpqRackHWSerialNumber  DisplayString
    }

    cpqRackHWSerialNumber OBJECT-TYPE
        SYNTAX  DisplayString (SIZE (0..21))
        ACCESS  read-only
        STATUS  optional
        DESCRIPTION
            "A serial number of the hardware associated with the indication."
        ::= { cpqRackHWSerialNumberEntry 1 }

    cpqRackHWFRUDetails OBJECT-TYPE
        SYNTAX  OCTET STRING (SIZE (0..256))
        ACCESS  read-only
        STATUS  optional
        DESCRIPTION
            "This is used to provide miscellaneous FRU specific details

            Some examples are DIMM size, Processor stepping info etc."
        ::= { cpqRackHW 5 }

    cpqRackHWDevicePermanentNameFormat OBJECT-TYPE
        SYNTAX	INTEGER {
                unknown(1),
                other(2),
                worldWideName(3),
                macAddress(4)
                }
        ACCESS  read-only
        STATUS  optional
        DESCRIPTION
            "The format of the DevicePermanentName property is interpreted based upon
            the value of this property.

            Values are defined as:
            1 - unknown. The format is not meaningfully interpretable by a CIM client
            application.
            2 - other. The format is defined by the value of the OtherPermanentNameFormat
            property.
            3 - worldWideName. The format is a WorldWideName.
            4 - macAddress. The format is a LAN MAC Address."
        ::= { cpqRackHW 6 }

    cpqRackHWOtherPermanentNameFormat OBJECT-TYPE
        SYNTAX  DisplayString ( SIZE (0..64))
        ACCESS  read-only
        STATUS  optional
        DESCRIPTION
           "A string defining other values for DevicePermanentFormat.

           It is empty unless DevicePermanentFormat value is other."
        ::= { cpqRackHW 7 }

-- ****************************************************************************
--   Rack Ers Information
--   =========================
--
-- The compaq enterprise                 (1.3.6.1.4.1.232)
--      cpqRackInfo Group                (1.3.6.1.4.1.232.22)
--       cpqRackComponent Group          (1.3.6.1.4.1.232.22.2)
--        cpqRackErs Group                (1.3.6.1.4.1.232.22.2.8)
--
-- ****************************************************************************

    cpqRackErsTransactionType OBJECT-TYPE
        SYNTAX	INTEGER {
                registration(1),
                serviceEvent(2),
                l2DataCollection(3),
                unregistration(4)
                }

        ACCESS  read-only
        STATUS  mandatory
        DESCRIPTION
            "Embedded Remote Support transaction type.

            The following values are defined:

            registration(1)
                Registration operation with Insight Remote Host or Insight Online Host.

            serviceEvent(2)
                Sending of service event to Insight Remote Host or Insight Online Host.

            l2DataCollection(3)
                L2 Data collection operation.

            unregistration(4)
                Unregistration with Insight Remote Host or Insight Online Host."
        ::= { cpqRackErs 1 }

    cpqRackErsConnectionModel OBJECT-TYPE
        SYNTAX	INTEGER {
                insightOnline(1),
                insightRemoteSupport(2)
                }
        ACCESS  read-only
        STATUS  mandatory
        DESCRIPTION
            "Embedded Remote Support connection model configured on the Onboard Administrator."
        ::= { cpqRackErs 2 }

    cpqRackErsFailureCode OBJECT-TYPE
        SYNTAX	INTEGER{
                genericTransmitError(1),
                clientTransmitTimeout(2),
                clientReceiveTimeout(3),
                proxyConnectError(4),
                remoteHostConnectError(5),
                remoteServiceError(6)
                }
        ACCESS  read-only
        STATUS  mandatory
        DESCRIPTION
            "Embedded Remote Support transaction failure code."
        ::= { cpqRackErs 3 }

    cpqRackErsRemoteHost OBJECT-TYPE
        SYNTAX  DisplayString ( SIZE (0..135))
        ACCESS  read-only
        STATUS  mandatory
        DESCRIPTION
            "Remote destination server's hostname and port as configured on the Onboard Administrator.

             Example: myremotehost.hpe.com:6789"
        ::= { cpqRackErs 4 }

-- ****************************************************************************
--   Rack Environmental Information
--   ==========================================
--
-- The compaq enterprise                 (1.3.6.1.4.1.232)
--      cpqRackInfo Group                (1.3.6.1.4.1.232.22)
--       cpqRackComponent Group          (1.3.6.1.4.1.232.22.2)
--        cpqRackEnvironmental Group     (1.3.6.1.4.1.232.22.2.9)
--
--  The cpqRackEnvironmental group contains the information about rack environmental devices
--
-- ****************************************************************************

-- ****************************************************************************
--   Rack Thermal Controller Information
--   ==========================================
--
-- The compaq enterprise                 (1.3.6.1.4.1.232)
--      cpqRackInfo Group                (1.3.6.1.4.1.232.22)
--       cpqRackComponent Group          (1.3.6.1.4.1.232.22.2)
--        cpqRackEnvironmental Group     (1.3.6.1.4.1.232.22.2.9)
--        cpqRackThermalController Group (1.3.6.1.4.1.232.22.2.9.1)
--
--  The cpqRackThermalController group contains the information about rack thermal devices
--
-- ****************************************************************************


    cpqRackThermalControllerTable OBJECT-TYPE
        SYNTAX  SEQUENCE OF CpqRackThermalControllerEntry
        ACCESS  not-accessible
        STATUS  mandatory
        DESCRIPTION
            "A table containing the envirnomental controllers in the rack"
        ::= { cpqRackThermalController 1 }

    cpqRackThermalControllerEntry OBJECT-TYPE
        SYNTAX  CpqRackThermalControllerEntry
        ACCESS  not-accessible
        STATUS  mandatory
        DESCRIPTION
            "Entry containing thermal sensor readings"
        INDEX   { cpqRackThermalControllerIndex }
        ::= { cpqRackThermalControllerTable 1 }

    CpqRackThermalControllerEntry ::= SEQUENCE {
        cpqRackThermalControllerIndex                INTEGER,
        cpqRackThermalControllerLeakDetect1          INTEGER,
        cpqRackThermalControllerLeakDetect2          INTEGER,
        cpqRackThermalControllerLeakDetect3          INTEGER,
        cpqRackThermalControllerLeakDetectFacility   INTEGER,
	cpqRackThermalControllerDoorSensorFront      INTEGER,
	cpqRackThermalControllerDoorSensorRear       INTEGER,
	cpqRackThermalControllerDoorControlFront     INTEGER,
	cpqRackThermalControllerDoorControlRear1     INTEGER,
	cpqRackThermalControllerDoorControlRear2     INTEGER,
	cpqRackThermalControllerAirTempSensorFront1  INTEGER,
	cpqRackThermalControllerAirTempSensorFront2  INTEGER,
	cpqRackThermalControllerAirTempSensorFront3  INTEGER,
	cpqRackThermalControllerAirTempSensorFront4  INTEGER,
	cpqRackThermalControllerAirTempSensorRear1   INTEGER,
	cpqRackThermalControllerAirTempSensorRear2   INTEGER,
	cpqRackThermalControllerAirTempSensorRear3   INTEGER,
	cpqRackThermalControllerAirTempSensorRear4   INTEGER,
	cpqRackThermalControllerControlValveSupply   INTEGER,
	cpqRackThermalControllerControlValveReturn   INTEGER,
	cpqRackThermalControllerWaterTempSupply      INTEGER,
	cpqRackThermalControllerWaterTempReturn      INTEGER,
	cpqRackThermalControllerITFlowSensor         INTEGER,
	cpqRackThermalControllerCDUFlowSensor        INTEGER,
	cpqRackThermalControllerWaterPressureSupply  INTEGER,
	cpqRackThermalControllerWaterPressureReturn  INTEGER,
	cpqRackThermalControllerARPO                 INTEGER,
	cpqRackThermalControllerChassisRopeSensor1   INTEGER,
	cpqRackThermalControllerChassisRopeSensor2   INTEGER,
	cpqRackThermalControllerChassisRopeSensor3   INTEGER,
	cpqRackThermalControllerChassisRopeSensor4   INTEGER,
	cpqRackThermalControllerOnBoardTemp          INTEGER,
	cpqRackThermalControllerOnBoardHumidity      INTEGER,
	cpqRackThermalControllerBattery              INTEGER,
	cpqRackThermalControllerAPMCommunications    INTEGER,
	cpqRackEnvironmentalTrapDescription			 DisplayString
    }

    cpqRackThermalControllerIndex OBJECT-TYPE
        SYNTAX  INTEGER
        ACCESS  read-only
        STATUS  mandatory
        DESCRIPTION
            "A number that uniquely specifies this thermal controller in the rack."
        ::= { cpqRackThermalControllerEntry 1 }

    cpqRackThermalControllerLeakDetect1 OBJECT-TYPE
        SYNTAX  INTEGER {
            false(1),
            true(2)
            }
        ACCESS  read-only
        STATUS  mandatory
        DESCRIPTION
            "TRUE if sensor 1 detected a leak"
        ::= { cpqRackThermalControllerEntry 2 }

    cpqRackThermalControllerLeakDetect2 OBJECT-TYPE
        SYNTAX  INTEGER {
            false(1),
            true(2)
            }
        ACCESS  read-only
        STATUS  mandatory
        DESCRIPTION
            "TRUE if sensor 2 detected a leak"
        ::= { cpqRackThermalControllerEntry 3 }

    cpqRackThermalControllerLeakDetect3 OBJECT-TYPE
        SYNTAX  INTEGER {
            false(1),
            true(2)
            }
        ACCESS  read-only
        STATUS  mandatory
        DESCRIPTION
            "TRUE if sensor 3 detected a leak"
        ::= { cpqRackThermalControllerEntry 4 }

    cpqRackThermalControllerLeakDetectFacility OBJECT-TYPE
        SYNTAX  INTEGER {
            false(1),
            true(2)
            }
        ACCESS  read-only
        STATUS  mandatory
        DESCRIPTION
            "TRUE if overhead sensor detected a leak"
        ::= { cpqRackThermalControllerEntry 5 }

    cpqRackThermalControllerDoorSensorFront OBJECT-TYPE
        SYNTAX  INTEGER {
            closed(1),
            open(2)
            }
        ACCESS  read-only
        STATUS  mandatory
        DESCRIPTION
            "1 if front door is open"
        ::= { cpqRackThermalControllerEntry 6 }

    cpqRackThermalControllerDoorSensorRear OBJECT-TYPE
        SYNTAX  INTEGER {
            closed(1),
            open(2)
            }
        ACCESS  read-only
        STATUS  mandatory
        DESCRIPTION
            "1 if rear door is open"
        ::= { cpqRackThermalControllerEntry 7 }

    cpqRackThermalControllerDoorControlFront OBJECT-TYPE
        SYNTAX  INTEGER {
            closed(1),
            open(2)
            }
        ACCESS  read-write
        STATUS  mandatory
        DESCRIPTION
            "1 to open front door"
        ::= { cpqRackThermalControllerEntry 8 }

    cpqRackThermalControllerDoorControlRear1 OBJECT-TYPE
        SYNTAX  INTEGER {
            closed(1),
            open(2)
            }
        ACCESS  read-write
        STATUS  mandatory
        DESCRIPTION
            "1 to open rear door"
        ::= { cpqRackThermalControllerEntry 9 }

    cpqRackThermalControllerDoorControlRear2 OBJECT-TYPE
        SYNTAX  INTEGER {
            closed(1),
            open(2)
            }
        ACCESS  read-write
        STATUS  mandatory
        DESCRIPTION
            "1 to open rear door"
        ::= { cpqRackThermalControllerEntry 10 }

    cpqRackThermalControllerAirTempSensorFront1 OBJECT-TYPE
        SYNTAX  INTEGER  ( 0..105 )
        ACCESS  read-only
        STATUS  mandatory
        DESCRIPTION
            "Front air temperature in C"
        ::= { cpqRackThermalControllerEntry 11 }

    cpqRackThermalControllerAirTempSensorFront2 OBJECT-TYPE
        SYNTAX  INTEGER  ( 0..105 )
        ACCESS  read-only
        STATUS  mandatory
        DESCRIPTION
            "Front air temperature in C"
        ::= { cpqRackThermalControllerEntry 12 }

    cpqRackThermalControllerAirTempSensorFront3 OBJECT-TYPE
        SYNTAX  INTEGER  ( 0..105 )
        ACCESS  read-only
        STATUS  mandatory
        DESCRIPTION
            "Front air temperature in C"
        ::= { cpqRackThermalControllerEntry 13 }

    cpqRackThermalControllerAirTempSensorFront4 OBJECT-TYPE
        SYNTAX  INTEGER  ( 0..105 )
        ACCESS  read-only
        STATUS  mandatory
        DESCRIPTION
            "Front air temperature in C"
        ::= { cpqRackThermalControllerEntry 14 }

    cpqRackThermalControllerAirTempSensorRear1 OBJECT-TYPE
        SYNTAX  INTEGER  ( 0..105 )
        ACCESS  read-only
        STATUS  mandatory
        DESCRIPTION
            "Rear air temperature in C"
        ::= { cpqRackThermalControllerEntry 15 }

    cpqRackThermalControllerAirTempSensorRear2 OBJECT-TYPE
        SYNTAX  INTEGER  ( 0..105 )
        ACCESS  read-only
        STATUS  mandatory
        DESCRIPTION
            "Rear air temperature in C"
        ::= { cpqRackThermalControllerEntry 16 }

    cpqRackThermalControllerAirTempSensorRear3 OBJECT-TYPE
        SYNTAX  INTEGER  ( 0..105 )
        ACCESS  read-only
        STATUS  mandatory
        DESCRIPTION
            "Rear air temperature in C"
        ::= { cpqRackThermalControllerEntry 17 }

    cpqRackThermalControllerAirTempSensorRear4 OBJECT-TYPE
        SYNTAX  INTEGER  ( 0..105 )
        ACCESS  read-only
        STATUS  mandatory
        DESCRIPTION
            "Rear air temperature in C"
        ::= { cpqRackThermalControllerEntry 18 }

    cpqRackThermalControllerControlValveSupply OBJECT-TYPE
        SYNTAX  INTEGER  {
		closed(1),
                open(2)
                }
        ACCESS  read-only
        STATUS  mandatory
        DESCRIPTION
            "Supply valve status "
        ::= { cpqRackThermalControllerEntry 19 }

    cpqRackThermalControllerControlValveReturn OBJECT-TYPE
        SYNTAX  INTEGER  {
		closed(1),
                open(2)
                }
        ACCESS  read-only
        STATUS  mandatory
        DESCRIPTION
            "Return valve status"
        ::= { cpqRackThermalControllerEntry 20 }

    cpqRackThermalControllerWaterTempSupply OBJECT-TYPE
        SYNTAX  INTEGER  ( 0..105 )
        ACCESS  read-only
        STATUS  mandatory
        DESCRIPTION
            "Water temperature supply in C"
        ::= { cpqRackThermalControllerEntry 21 }

    cpqRackThermalControllerWaterTempReturn OBJECT-TYPE
        SYNTAX  INTEGER  ( 0..105 )
        ACCESS  read-only
        STATUS  mandatory
        DESCRIPTION
            "Water temperature return in C"
        ::= { cpqRackThermalControllerEntry 22 }

    cpqRackThermalControllerITFlowSensor OBJECT-TYPE
        SYNTAX  INTEGER  {
		low(1),
                high(2)
                }
        ACCESS  read-only
        STATUS  mandatory
        DESCRIPTION
            "Flow sensor to IT equipment"
        ::= { cpqRackThermalControllerEntry 23 }

    cpqRackThermalControllerCDUFlowSensor OBJECT-TYPE
        SYNTAX  INTEGER  {
		low(1),
                high(2)
                }
        ACCESS  read-only
        STATUS  mandatory
        DESCRIPTION
            "Flow sensor to CDU"
        ::= { cpqRackThermalControllerEntry 24 }

    cpqRackThermalControllerWaterPressureSupply OBJECT-TYPE
        SYNTAX  INTEGER  ( 0..3277 )
        ACCESS  read-only
        STATUS  mandatory
        DESCRIPTION
            "Supply water pressure"
        ::= { cpqRackThermalControllerEntry 25 }

    cpqRackThermalControllerWaterPressureReturn OBJECT-TYPE
        SYNTAX  INTEGER  ( 0..3277 )
        ACCESS  read-only
        STATUS  mandatory
        DESCRIPTION
            "Return water pressure"
        ::= { cpqRackThermalControllerEntry 26 }

    cpqRackThermalControllerARPO OBJECT-TYPE
        SYNTAX  INTEGER  {
		rackPowered(1),
                rackPowerDisconnected(2)
                }
        ACCESS  read-only
        STATUS  mandatory
        DESCRIPTION
            "Emergency power off status"
        ::= { cpqRackThermalControllerEntry 27 }

    cpqRackThermalControllerChassisRopeSensor1 OBJECT-TYPE
        SYNTAX  INTEGER  {
		noLeakDetected(1),
                leakDetected(2)
                }
        ACCESS  read-only
        STATUS  mandatory
        DESCRIPTION
            "Leak detected by rope sensor 1"
        ::= { cpqRackThermalControllerEntry 28 }

    cpqRackThermalControllerChassisRopeSensor2 OBJECT-TYPE
        SYNTAX  INTEGER  {
		noLeakDetected(1),
                leakDetected(2)
                }
        ACCESS  read-only
        STATUS  mandatory
        DESCRIPTION
            "Leak detected by rope sensor 2"
        ::= { cpqRackThermalControllerEntry 29 }

    cpqRackThermalControllerChassisRopeSensor3 OBJECT-TYPE
        SYNTAX  INTEGER  {
		noLeakDetected(1),
                leakDetected(2)
                }
        ACCESS  read-only
        STATUS  mandatory
        DESCRIPTION
            "Leak detected by rope sensor 3"
        ::= { cpqRackThermalControllerEntry 30 }
    cpqRackThermalControllerChassisRopeSensor4 OBJECT-TYPE
        SYNTAX  INTEGER  {
		noLeakDetected(1),
                leakDetected(2)
                }
        ACCESS  read-only
        STATUS  mandatory
        DESCRIPTION
            "Leak detected by rope sensor 4"
        ::= { cpqRackThermalControllerEntry 31 }

    cpqRackThermalControllerOnBoardTemp OBJECT-TYPE
        SYNTAX  INTEGER  ( 0..105 )
        ACCESS  read-only
        STATUS  mandatory
        DESCRIPTION
            "Thermal controller board temperature in C"
        ::= { cpqRackThermalControllerEntry 32 }

    cpqRackThermalControllerOnBoardHumidity OBJECT-TYPE
        SYNTAX  INTEGER  ( 0..100 )
        ACCESS  read-only
        STATUS  mandatory
        DESCRIPTION
            "Environmental relative humidity"
        ::= { cpqRackThermalControllerEntry 33 }

    cpqRackThermalControllerBattery OBJECT-TYPE
        SYNTAX  INTEGER  {
		notPresent(1),
                present(2)
                }
        ACCESS  read-only
        STATUS  mandatory
        DESCRIPTION
            "Presence of thermal controller battery"
        ::= { cpqRackThermalControllerEntry 34 }

    cpqRackThermalControllerAPMCommunications OBJECT-TYPE
        SYNTAX  INTEGER  {
		hostUnreachable(1),
                hostNotResponding(2),
                invalidData(3)
                }
        ACCESS  read-only
        STATUS  mandatory
        DESCRIPTION
            "APM Communications Status"
        ::= { cpqRackThermalControllerEntry 35 }

    cpqRackEnvironmentalTrapDescription OBJECT-TYPE
        SYNTAX  DisplayString (SIZE (0..255))
        ACCESS  read-only
        STATUS  mandatory
        DESCRIPTION
            "Trap Description including threshold information:
			Sensor = string, Lo threshold = integer, Hi threshold = integer"
        ::= { cpqRackThermalControllerEntry 36 }

-- ****************************************************************************
--   Rack Cooling Distribution Unit Information
--   ==========================================
--
-- The compaq enterprise                 (1.3.6.1.4.1.232)
--      cpqRackInfo Group                (1.3.6.1.4.1.232.22)
--       cpqRackComponent Group          (1.3.6.1.4.1.232.22.2)
--        cpqRackCdu Group               (1.3.6.1.4.1.232.22.2.10)
--
--  The cpqRackCdu group contains the information about rack Cdu
--
-- ****************************************************************************

-- ****************************************************************************
--   Rack Cdu Apollo Controller Table
--   ===============================
--
-- The compaq enterprise                 (1.3.6.1.4.1.232)
--      cpqRackInfo Group                (1.3.6.1.4.1.232.22)
--       cpqRackComponent Group          (1.3.6.1.4.1.232.22.2)
--        cpqRackCdu Group               (1.3.6.1.4.1.232.22.2.10)
--         cpqRackCduApolloController Table (1.3.6.1.4.1.232.22.2.10.1)
--
-- ****************************************************************************
    cpqRackCduApolloControllerTable OBJECT-TYPE
        SYNTAX  SEQUENCE OF CpqRackCduApolloControllerEntry
        ACCESS  not-accessible
        STATUS  mandatory
        DESCRIPTION
            "A table of rack Cdu controller information."
        ::= { cpqRackCduApolloController 1 }

    cpqRackCduApolloControllerEntry OBJECT-TYPE
        SYNTAX  CpqRackCduApolloControllerEntry
        ACCESS  not-accessible
        STATUS  mandatory
        DESCRIPTION
            "A rack Cdu controller description."
        INDEX   { cpqRackCduApolloControllerCduIndex }
        ::= { cpqRackCduApolloControllerTable 1 }

    CpqRackCduApolloControllerEntry ::= SEQUENCE {
        cpqRackCduApolloControllerCduIndex                      INTEGER,
        cpqRackCduApolloControllerFwVersion                     INTEGER,
        cpqRackCduApolloControllerPlanAddress                   INTEGER,
        cpqRackCduApolloControllerPlanStatus                    INTEGER,
        cpqRackCduApolloControllerBmsFacilityWaterValveControl  DisplayString,
        cpqRackCduApolloControllerBmsPumpBypassValveControl     DisplayString,
        cpqRackCduApolloControllerBmsPumpVfdControl             DisplayString,
        cpqRackCduApolloControllerBmsHeartbeat                  INTEGER
    }

    cpqRackCduApolloControllerCduIndex OBJECT-TYPE
        SYNTAX  INTEGER
        ACCESS  read-only
        STATUS  mandatory
        DESCRIPTION
            "A number that uniquely specifies this Cdu in the rack."
        ::= { cpqRackCduApolloControllerEntry 1 }

    cpqRackCduApolloControllerFwVersion OBJECT-TYPE
        SYNTAX  INTEGER
        ACCESS  read-only
        STATUS  mandatory
        DESCRIPTION
            "This Cdu controller FW version."
        ::= { cpqRackCduApolloControllerEntry 2 }

    cpqRackCduApolloControllerPlanAddress OBJECT-TYPE
        SYNTAX  INTEGER
        ACCESS  read-only
        STATUS  mandatory
        DESCRIPTION
            "This Cdu controller PLAN address."
        ::= { cpqRackCduApolloControllerEntry 3 }

    cpqRackCduApolloControllerPlanStatus OBJECT-TYPE
        SYNTAX  INTEGER
        ACCESS  read-only
        STATUS  mandatory
        DESCRIPTION
            "This Cdu controller PLAN status."
        ::= { cpqRackCduApolloControllerEntry 4 }

    cpqRackCduApolloControllerBmsFacilityWaterValveControl OBJECT-TYPE
        SYNTAX  DisplayString (SIZE (0..25))
        ACCESS  read-only
        STATUS  mandatory
        DESCRIPTION
            "This Cdu controller BMS facility water valve control."
        ::= { cpqRackCduApolloControllerEntry 5 }

    cpqRackCduApolloControllerBmsPumpBypassValveControl OBJECT-TYPE
        SYNTAX  DisplayString (SIZE (0..25))
        ACCESS  read-only
        STATUS  mandatory
        DESCRIPTION
            "This Cdu controller BMS pump bypass valve control."
        ::= { cpqRackCduApolloControllerEntry 6 }

    cpqRackCduApolloControllerBmsPumpVfdControl OBJECT-TYPE
        SYNTAX  DisplayString (SIZE (0..25))
        ACCESS  read-only
        STATUS  mandatory
        DESCRIPTION
            "This Cdu controller BMS pump VFD control."
        ::= { cpqRackCduApolloControllerEntry 7 }

    cpqRackCduApolloControllerBmsHeartbeat OBJECT-TYPE
        SYNTAX  INTEGER
        ACCESS  read-only
        STATUS  mandatory
        DESCRIPTION
            "This Cdu controller heartbeat."
        ::= { cpqRackCduApolloControllerEntry 8 }

-- ****************************************************************************
--   Rack Cdu Apollo Facility Water Loop Table
--   ========================================
--
-- The compaq enterprise                 (1.3.6.1.4.1.232)
--      cpqRackInfo Group                (1.3.6.1.4.1.232.22)
--       cpqRackComponent Group          (1.3.6.1.4.1.232.22.2)
--        cpqRackCdu Group               (1.3.6.1.4.1.232.22.2.9)
--         cpqRackCduApolloFacilityWater Table      (1.3.6.1.4.1.232.22.2.9.2)
--
-- ****************************************************************************

    cpqRackCduApolloFacilityWaterTable OBJECT-TYPE
        SYNTAX  SEQUENCE OF CpqRackCduApolloFacilityWaterEntry
        ACCESS  not-accessible
        STATUS  mandatory
        DESCRIPTION
            "A table of rack Cdu controller information."
        ::= { cpqRackCduApolloFacilityWater 1 }

    cpqRackCduApolloFacilityWaterEntry OBJECT-TYPE
        SYNTAX  CpqRackCduApolloFacilityWaterEntry
        ACCESS  not-accessible
        STATUS  mandatory
        DESCRIPTION
            "A rack Cdu controller description."
        INDEX   { cpqRackCduApolloFacilityWaterCduIndex }
        ::= { cpqRackCduApolloFacilityWaterTable 1 }

    CpqRackCduApolloFacilityWaterEntry ::= SEQUENCE {
        cpqRackCduApolloFacilityWaterCduIndex                      INTEGER,
        cpqRackCduApolloFacilityWaterSupplyTemp                    DisplayString,
        cpqRackCduApolloFacilityWaterSupplyHiTempAlarmSp           DisplayString,
        cpqRackCduApolloFacilityWaterSupplyIsoValveState           INTEGER,
        cpqRackCduApolloFacilityWaterReturnTemp                    DisplayString,
        cpqRackCduApolloFacilityWaterReturnHiTempAlarmSp           DisplayString,
        cpqRackCduApolloFacilityWaterReturnIsoValveState           INTEGER,
        cpqRackCduApolloFacilityWaterRegulatingValveOpening        DisplayString,
        cpqRackCduApolloFacilityWaterPressureHexDifferential       DisplayString,
        cpqRackCduApolloFacilityWaterLoDifferentialPressureAlarmSp DisplayString,
        cpqRackCduApolloFacilityWaterPressureInlet                 DisplayString,
        cpqRackCduApolloFacilityWaterPressureOutlet                DisplayString
    }

    cpqRackCduApolloFacilityWaterCduIndex OBJECT-TYPE
        SYNTAX  INTEGER
        ACCESS  read-only
        STATUS  mandatory
        DESCRIPTION
            "A number that uniquely specifies this Cdu in the rack."
        ::= { cpqRackCduApolloFacilityWaterEntry 1 }

    cpqRackCduApolloFacilityWaterSupplyTemp OBJECT-TYPE
        SYNTAX  DisplayString (SIZE (0..25))
        ACCESS  read-only
        STATUS  mandatory
        DESCRIPTION
            "This Cdu facility water inlet temperature."
        ::= { cpqRackCduApolloFacilityWaterEntry 2 }

    cpqRackCduApolloFacilityWaterSupplyHiTempAlarmSp OBJECT-TYPE
        SYNTAX  DisplayString (SIZE (0..25))
        ACCESS  read-only
        STATUS  mandatory
        DESCRIPTION
            "This Cdu high facility inlet temperature alarm set point."
        ::= { cpqRackCduApolloFacilityWaterEntry 3 }

    cpqRackCduApolloFacilityWaterSupplyIsoValveState OBJECT-TYPE
        SYNTAX  INTEGER {
                close(1),         --  Facility isolation valve 1 is closed.   Facility supply.
                open(2)           --  Facility isolation valve 1 is open.   Facility supply.
                }
        ACCESS  read-only
        STATUS  mandatory
        DESCRIPTION
            "This Cdu facility isolation valve 1 status (open/close).  Facility supply."
        ::= { cpqRackCduApolloFacilityWaterEntry 4 }

    cpqRackCduApolloFacilityWaterReturnTemp OBJECT-TYPE
        SYNTAX  DisplayString (SIZE (0..25))
        ACCESS  read-only
        STATUS  mandatory
        DESCRIPTION
            "This Cdu facility outlet temperature."
        ::= { cpqRackCduApolloFacilityWaterEntry 5 }

    cpqRackCduApolloFacilityWaterReturnHiTempAlarmSp OBJECT-TYPE
        SYNTAX  DisplayString (SIZE (0..25))
        ACCESS  read-only
        STATUS  mandatory
        DESCRIPTION
           "This Cdu facility outlet temperature alarm set point."
        ::= { cpqRackCduApolloFacilityWaterEntry 6 }

    cpqRackCduApolloFacilityWaterReturnIsoValveState OBJECT-TYPE
        SYNTAX  INTEGER {
                close(1),         --  Facility isolation valve 2 is closed.   Facility return.
                open(2)           --  Facility isolation valve 2 is open.   Facility return.
                }
        ACCESS  read-only
        STATUS  mandatory
        DESCRIPTION
            "This Cdu facility isolation valve 2 status (open/close).  Facility return."
        ::= { cpqRackCduApolloFacilityWaterEntry 7 }

    cpqRackCduApolloFacilityWaterRegulatingValveOpening OBJECT-TYPE
        SYNTAX  DisplayString (SIZE (0..25))
        ACCESS  read-only
        STATUS  mandatory
        DESCRIPTION
            "This Cdu water regulation valve output (from Carel controller)."
        ::= { cpqRackCduApolloFacilityWaterEntry 8 }

    cpqRackCduApolloFacilityWaterPressureHexDifferential OBJECT-TYPE
        SYNTAX  DisplayString (SIZE (0..25))
        ACCESS  read-only
        STATUS  mandatory
        DESCRIPTION
            "This Cdu facility heat exchanger differential pressure."
        ::= { cpqRackCduApolloFacilityWaterEntry 9 }

    cpqRackCduApolloFacilityWaterLoDifferentialPressureAlarmSp OBJECT-TYPE
        SYNTAX  DisplayString (SIZE (0..25))
        ACCESS  read-only
        STATUS  mandatory
        DESCRIPTION
            "This Cdu low facility heat exchanger differential pressure alarm set point."
        ::= { cpqRackCduApolloFacilityWaterEntry 10 }

    cpqRackCduApolloFacilityWaterPressureInlet OBJECT-TYPE
        SYNTAX  DisplayString (SIZE (0..25))
        ACCESS  read-only
        STATUS  mandatory
        DESCRIPTION
            "This Cdu facility inlet pressure."
        ::= { cpqRackCduApolloFacilityWaterEntry 11 }

    cpqRackCduApolloFacilityWaterPressureOutlet OBJECT-TYPE
        SYNTAX  DisplayString (SIZE (0..25))
        ACCESS  read-only
        STATUS  mandatory
        DESCRIPTION
            "This Cdu facility outlet pressure."
        ::= { cpqRackCduApolloFacilityWaterEntry 12 }


-- ****************************************************************************
--   Rack Cdu Apollo IT Water Loop Table
--   ==================================
--
-- The compaq enterprise                 (1.3.6.1.4.1.232)
--      cpqRackInfo Group                (1.3.6.1.4.1.232.22)
--       cpqRackComponent Group          (1.3.6.1.4.1.232.22.2)
--        cpqRackCdu Group               (1.3.6.1.4.1.232.22.2.9)
--         cpqRackCduApollo Group         (1.3.6.1.4.1.232.22.2.9.1)
--          cpqRackCduA800ItWaterLoop Table   (1.3.6.1.4.1.232.22.2.9.1.3)
--
-- ****************************************************************************

    cpqRackCduApolloItWaterTable OBJECT-TYPE
        SYNTAX  SEQUENCE OF CpqRackCduApolloItWaterEntry
        ACCESS  not-accessible
        STATUS  mandatory
        DESCRIPTION
            "A table of rack Cdu controller information."
        ::= { cpqRackCduApolloItWater 1 }

    cpqRackCduApolloItWaterEntry OBJECT-TYPE
        SYNTAX  CpqRackCduApolloItWaterEntry
        ACCESS  not-accessible
        STATUS  mandatory
        DESCRIPTION
            "A rack Cdu controller description."
        INDEX   { cpqRackCduApolloItWaterCduIndex }
        ::= { cpqRackCduApolloItWaterTable 1 }

    CpqRackCduApolloItWaterEntry ::= SEQUENCE {
        cpqRackCduApolloItWaterCduIndex                               INTEGER,
        cpqRackCduApolloItWaterSupplyTemp                             DisplayString,
        cpqRackCduApolloItWaterSupplyHiDischargeTempSp                DisplayString,
        cpqRackCduApolloItWaterSupplyIsoValveState                    INTEGER,
        cpqRackCduApolloItWaterReturnTemp                             DisplayString,
        cpqRackCduApolloItWaterReturnIsoValveState                    INTEGER,
        cpqRackCduApolloItWaterPumpSpeed                              DisplayString,
        cpqRackCduApolloItWaterPumpPower                              DisplayString,
        cpqRackCduApolloItWaterPumpSupplyTempSp                       DisplayString,
        cpqRackCduApolloItWaterVfdControlLocation                     INTEGER,
        cpqRackCduApolloItWaterVfdCurrent                             INTEGER,
        cpqRackCduApolloItWaterVfdDcVoltage                           INTEGER,
        cpqRackCduApolloItWaterVfdTemperature                         INTEGER,
        cpqRackCduApolloItWaterVfdExternalControlSignal               INTEGER,
        cpqRackCduApolloItWaterVfdFaultWord1                          INTEGER,
        cpqRackCduApolloItWaterVfdFaultWord2                          INTEGER,
        cpqRackCduApolloItWaterVfdFaultWord3                          INTEGER,
        cpqRackCduApolloItWaterVfdFrequency                           INTEGER,
        cpqRackCduApolloItWaterVfdKwhCounter                          INTEGER,
        cpqRackCduApolloItWaterVfdMwhCounter                          INTEGER,
        cpqRackCduApolloItWaterVfdOutputVoltage                       INTEGER,
        cpqRackCduApolloItWaterVfdPowerReading                        INTEGER,
        cpqRackCduApolloItWaterVfdRunTime                             INTEGER,
        cpqRackCduApolloItWaterVfdSpeed                               INTEGER,
        cpqRackCduApolloItWaterVfdTorque                              INTEGER,
        cpqRackCduApolloItWaterMotorNominalCurrent                    INTEGER,
        cpqRackCduApolloItWaterMotorNominalFrequency                  INTEGER,
        cpqRackCduApolloItWaterMotorNominalPower                      INTEGER,
        cpqRackCduApolloItWaterMotorNominalSpeed                      INTEGER,
        cpqRackCduApolloItWaterMotorNominalVoltage                    INTEGER,
        cpqRackCduApolloItWaterMotorModbusStatusWord                  INTEGER,
        cpqRackCduApolloItWaterPressureHexDiffActual                  DisplayString,
        cpqRackCduApolloItWaterPressureDiffPressureSp                 DisplayString,
        cpqRackCduApolloItWaterPressureLoAlarmSp                      DisplayString,
        cpqRackCduApolloItWaterPressureHiAlarmSp                      DisplayString,
        cpqRackCduApolloItWaterPressureHexOutlet                      DisplayString,
        cpqRackCduApolloItWaterPressurePumpDischarge                  DisplayString,
        cpqRackCduApolloItWaterReservoirVacuumPumpOn                  INTEGER,
        cpqRackCduApolloItWaterReservoirVacuumPressureCutInSp         DisplayString,
        cpqRackCduApolloItWaterReservoirVacuumPressureCutOutSp        DisplayString,
        cpqRackCduApolloItWaterReservoirVacuumLockOutOffset           DisplayString,
        cpqRackCduApolloItWaterReservoirVacuumLockedOut               INTEGER,
        cpqRackCduApolloItWaterReservoirPressure                      DisplayString,
        cpqRackCduApolloItWaterReservoirVolume                        DisplayString,
        cpqRackCduApolloItWaterReservoirTankWaterLevel                DisplayString,
        cpqRackCduApolloItWaterReservoirWaterFillOn                   INTEGER,
        cpqRackCduApolloItWaterReservoirAirInletValveStatusOn         INTEGER,
        cpqRackCduApolloItWaterReservoirAirInletValveSolenoidCutInSp  DisplayString,
        cpqRackCduApolloItWaterReservoirAirInletValveSolenoidCutOutSp DisplayString,
        cpqRackCduApolloItWaterReservoirFlow                          INTEGER,
        cpqRackCduApolloItWaterReservoirEnergy                        INTEGER
    }

    cpqRackCduApolloItWaterCduIndex OBJECT-TYPE
        SYNTAX  INTEGER
        ACCESS  read-only
        STATUS  mandatory
        DESCRIPTION
            "A number that uniquely specifies this Cdu in the rack."
        ::= { cpqRackCduApolloItWaterEntry 1 }

    cpqRackCduApolloItWaterSupplyTemp OBJECT-TYPE
        SYNTAX  DisplayString (SIZE (0..25))
        ACCESS  read-only
        STATUS  mandatory
        DESCRIPTION
            "This Cdu IT heat exchanger inlet/supply temperature."
        ::= { cpqRackCduApolloItWaterEntry 2 }

    cpqRackCduApolloItWaterSupplyHiDischargeTempSp OBJECT-TYPE
        SYNTAX  DisplayString (SIZE (0..25))
        ACCESS  read-only
        STATUS  mandatory
        DESCRIPTION
            "This Cdu high IT discharge temperature set point."
        ::= { cpqRackCduApolloItWaterEntry 3 }

    cpqRackCduApolloItWaterSupplyIsoValveState OBJECT-TYPE
        SYNTAX  INTEGER {
                close(1),         --  IT isolation valve 1 is closed.   IT supply.
                open(2)           --  IT isolation valve 1 is open.   IT supply.
                }
        ACCESS  read-only
        STATUS  mandatory
        DESCRIPTION
            "This Cdu IT isolation valve 1 state (open/close).  IT supply."
        ::= { cpqRackCduApolloItWaterEntry 4 }

    cpqRackCduApolloItWaterReturnTemp OBJECT-TYPE
        SYNTAX  DisplayString (SIZE (0..25))
        ACCESS  read-only
        STATUS  mandatory
        DESCRIPTION
            "This Cdu IT heat exchanger discharge/return temperature."
        ::= { cpqRackCduApolloItWaterEntry 5 }

    cpqRackCduApolloItWaterReturnIsoValveState OBJECT-TYPE
        SYNTAX  INTEGER {
                close(1),         --  IT isolation valve 2 is closed.   IT return.
                open(2)           --  IT isolation valve 2 is open.   IT return.
                }

        ACCESS  read-only
        STATUS  mandatory
        DESCRIPTION
            "This Cdu IT isolation valve 2 state (open/close).  IT return."
        ::= { cpqRackCduApolloItWaterEntry 6 }

    cpqRackCduApolloItWaterPumpSpeed OBJECT-TYPE
        SYNTAX  DisplayString (SIZE (0..25))
        ACCESS  read-only
        STATUS  mandatory
        DESCRIPTION
            "This Cdu IT pump VFD output (from Carel controller)."
        ::= { cpqRackCduApolloItWaterEntry 7 }

    cpqRackCduApolloItWaterPumpPower OBJECT-TYPE
        SYNTAX  DisplayString (SIZE (0..25))
        ACCESS  read-only
        STATUS  mandatory
        DESCRIPTION
            "This Cdu IT pump power (calculated)."
        ::= { cpqRackCduApolloItWaterEntry 8 }

    cpqRackCduApolloItWaterPumpSupplyTempSp OBJECT-TYPE
        SYNTAX  DisplayString (SIZE (0..25))
        ACCESS  read-only
        STATUS  mandatory
        DESCRIPTION
            "This Cdu IT pump supply temperature set point."
        ::= { cpqRackCduApolloItWaterEntry 9 }

    cpqRackCduApolloItWaterVfdControlLocation OBJECT-TYPE
        SYNTAX  INTEGER
        ACCESS  read-only
        STATUS  mandatory
        DESCRIPTION
            "This Cdu IT VFD control location"
        ::= { cpqRackCduApolloItWaterEntry 10 }

    cpqRackCduApolloItWaterVfdCurrent OBJECT-TYPE
        SYNTAX  INTEGER
        ACCESS  read-only
        STATUS  mandatory
        DESCRIPTION
            "This Cdu IT VFD current."
        ::= { cpqRackCduApolloItWaterEntry 11 }

    cpqRackCduApolloItWaterVfdDcVoltage OBJECT-TYPE
        SYNTAX  INTEGER
        ACCESS  read-only
        STATUS  mandatory
        DESCRIPTION
            "This Cdu IT VFD DC voltage."
        ::= { cpqRackCduApolloItWaterEntry 12 }

    cpqRackCduApolloItWaterVfdTemperature OBJECT-TYPE
        SYNTAX  INTEGER
        ACCESS  read-only
        STATUS  mandatory
        DESCRIPTION
            "This Cdu IT VFD temperature."
        ::= { cpqRackCduApolloItWaterEntry 13 }

    cpqRackCduApolloItWaterVfdExternalControlSignal OBJECT-TYPE
        SYNTAX  INTEGER
        ACCESS  read-only
        STATUS  mandatory
        DESCRIPTION
            "This Cdu IT VFD external control signal."
        ::= { cpqRackCduApolloItWaterEntry 14 }

    cpqRackCduApolloItWaterVfdFaultWord1 OBJECT-TYPE
        SYNTAX  INTEGER
        ACCESS  read-only
        STATUS  mandatory
        DESCRIPTION
            "This Cdu IT VFD fault word1."
        ::= { cpqRackCduApolloItWaterEntry 15 }

    cpqRackCduApolloItWaterVfdFaultWord2 OBJECT-TYPE
        SYNTAX  INTEGER
        ACCESS  read-only
        STATUS  mandatory
        DESCRIPTION
            "This Cdu  IT VFD fault word2."
        ::= { cpqRackCduApolloItWaterEntry 16 }

    cpqRackCduApolloItWaterVfdFaultWord3 OBJECT-TYPE
        SYNTAX  INTEGER
        ACCESS  read-only
        STATUS  mandatory
        DESCRIPTION
            "This Cdu  IT VFD fault word3."
        ::= { cpqRackCduApolloItWaterEntry 17 }

    cpqRackCduApolloItWaterVfdFrequency OBJECT-TYPE
        SYNTAX  INTEGER
        ACCESS  read-only
        STATUS  mandatory
        DESCRIPTION
            "This Cdu IT VFD frequency."
        ::= { cpqRackCduApolloItWaterEntry 18 }

    cpqRackCduApolloItWaterVfdKwhCounter OBJECT-TYPE
        SYNTAX  INTEGER
        ACCESS  read-only
        STATUS  mandatory
        DESCRIPTION
            "This Cdu IT VFD KWh counter."
        ::= { cpqRackCduApolloItWaterEntry 19 }

    cpqRackCduApolloItWaterVfdMwhCounter OBJECT-TYPE
        SYNTAX  INTEGER
        ACCESS  read-only
        STATUS  mandatory
        DESCRIPTION
            "This Cdu IT VFD MWh counter."
        ::= { cpqRackCduApolloItWaterEntry 20 }

    cpqRackCduApolloItWaterVfdOutputVoltage OBJECT-TYPE
        SYNTAX  INTEGER
        ACCESS  read-only
        STATUS  mandatory
        DESCRIPTION
            "This Cdu IT VFD output voltage."
        ::= { cpqRackCduApolloItWaterEntry 21 }

    cpqRackCduApolloItWaterVfdPowerReading OBJECT-TYPE
        SYNTAX  INTEGER
        ACCESS  read-only
        STATUS  mandatory
        DESCRIPTION
            "This Cdu IT VFD power reading."
        ::= { cpqRackCduApolloItWaterEntry 22 }

    cpqRackCduApolloItWaterVfdRunTime OBJECT-TYPE
        SYNTAX  INTEGER
        ACCESS  read-only
        STATUS  mandatory
        DESCRIPTION
            "This Cdu IT VFD runtime."
        ::= { cpqRackCduApolloItWaterEntry 23 }

    cpqRackCduApolloItWaterVfdSpeed OBJECT-TYPE
        SYNTAX  INTEGER
        ACCESS  read-only
        STATUS  mandatory
        DESCRIPTION
            "This Cdu IT VFD speed."
        ::= { cpqRackCduApolloItWaterEntry 24 }

    cpqRackCduApolloItWaterVfdTorque OBJECT-TYPE
        SYNTAX  INTEGER
        ACCESS  read-only
        STATUS  mandatory
        DESCRIPTION
            "This Cdu IT VFD torque."
        ::= { cpqRackCduApolloItWaterEntry 25 }

    cpqRackCduApolloItWaterMotorNominalCurrent OBJECT-TYPE
        SYNTAX  INTEGER
        ACCESS  read-only
        STATUS  mandatory
        DESCRIPTION
            "This Cdu IT motor nominal current."
        ::= { cpqRackCduApolloItWaterEntry 26 }

    cpqRackCduApolloItWaterMotorNominalFrequency OBJECT-TYPE
        SYNTAX  INTEGER
        ACCESS  read-only
        STATUS  mandatory
        DESCRIPTION
            "This Cdu IT motor nominal frequency."
        ::= { cpqRackCduApolloItWaterEntry 27 }

    cpqRackCduApolloItWaterMotorNominalPower OBJECT-TYPE
        SYNTAX  INTEGER
        ACCESS  read-only
        STATUS  mandatory
        DESCRIPTION
            "This Cdu IT motor nominal power."
        ::= { cpqRackCduApolloItWaterEntry 28 }

    cpqRackCduApolloItWaterMotorNominalSpeed OBJECT-TYPE
        SYNTAX  INTEGER
        ACCESS  read-only
        STATUS  mandatory
        DESCRIPTION
            "This Cdu IT motor nominal speed."
        ::= { cpqRackCduApolloItWaterEntry 29 }

    cpqRackCduApolloItWaterMotorNominalVoltage OBJECT-TYPE
        SYNTAX  INTEGER
        ACCESS  read-only
        STATUS  mandatory
        DESCRIPTION
            "This Cdu IT motor nominal voltage."
        ::= { cpqRackCduApolloItWaterEntry 30 }

    cpqRackCduApolloItWaterMotorModbusStatusWord OBJECT-TYPE
        SYNTAX  INTEGER
        ACCESS  read-only
        STATUS  mandatory
        DESCRIPTION
            "This Cdu IT motor modbus status word."
        ::= { cpqRackCduApolloItWaterEntry 31 }

    cpqRackCduApolloItWaterPressureHexDiffActual OBJECT-TYPE
        SYNTAX  DisplayString (SIZE (0..25))
        ACCESS  read-only
        STATUS  mandatory
        DESCRIPTION
            "This Cdu IT heat exchanger differential pressure actual."
        ::= { cpqRackCduApolloItWaterEntry 32 }

    cpqRackCduApolloItWaterPressureDiffPressureSp OBJECT-TYPE
        SYNTAX  DisplayString (SIZE (0..25))
        ACCESS  read-only
        STATUS  mandatory
        DESCRIPTION
            "This Cdu IT heat exchanger differential pressure setpoint."
        ::= { cpqRackCduApolloItWaterEntry 33 }

    cpqRackCduApolloItWaterPressureLoAlarmSp OBJECT-TYPE
        SYNTAX  DisplayString (SIZE (0..25))
        ACCESS  read-only
        STATUS  mandatory
        DESCRIPTION
            "This Cdu IT pressure low alarm setpoint."
        ::= { cpqRackCduApolloItWaterEntry 34 }

    cpqRackCduApolloItWaterPressureHiAlarmSp OBJECT-TYPE
        SYNTAX  DisplayString (SIZE (0..25))
        ACCESS  read-only
        STATUS  mandatory
        DESCRIPTION
            "This Cdu IT pressure high alarm setpoint."
        ::= { cpqRackCduApolloItWaterEntry 35 }

    cpqRackCduApolloItWaterPressureHexOutlet OBJECT-TYPE
        SYNTAX  DisplayString (SIZE (0..25))
        ACCESS  read-only
        STATUS  mandatory
        DESCRIPTION
            "This Cdu IT heat exchanger pressure outlet."
        ::= { cpqRackCduApolloItWaterEntry 36 }

    cpqRackCduApolloItWaterPressurePumpDischarge OBJECT-TYPE
        SYNTAX  DisplayString (SIZE (0..25))
        ACCESS  read-only
        STATUS  mandatory
        DESCRIPTION
            "This Cdu IT pump discharge."
        ::= { cpqRackCduApolloItWaterEntry 37 }

    cpqRackCduApolloItWaterReservoirVacuumPumpOn OBJECT-TYPE
        SYNTAX  INTEGER
        ACCESS  read-only
        STATUS  mandatory
        DESCRIPTION
            "This Cdu IT rerservoir vacuum pump on."
        ::= { cpqRackCduApolloItWaterEntry 38 }

    cpqRackCduApolloItWaterReservoirVacuumPressureCutInSp OBJECT-TYPE
        SYNTAX  DisplayString (SIZE (0..25))
        ACCESS  read-only
        STATUS  mandatory
        DESCRIPTION
            "This Cdu IT reservoir vacuum pressure cut in setpoint."
        ::= { cpqRackCduApolloItWaterEntry 39 }

    cpqRackCduApolloItWaterReservoirVacuumPressureCutOutSp OBJECT-TYPE
        SYNTAX  DisplayString (SIZE (0..25))
        ACCESS  read-only
        STATUS  mandatory
        DESCRIPTION
            "This Cdu IT reservoir vacuum pressure cut out setpoint."
        ::= { cpqRackCduApolloItWaterEntry 40 }

    cpqRackCduApolloItWaterReservoirVacuumLockOutOffset OBJECT-TYPE
        SYNTAX  DisplayString (SIZE (0..25))
        ACCESS  read-only
        STATUS  mandatory
        DESCRIPTION
            "This Cdu IT reservoir vacuum lock out offset."
        ::= { cpqRackCduApolloItWaterEntry 41 }

    cpqRackCduApolloItWaterReservoirVacuumLockedOut OBJECT-TYPE
        SYNTAX  INTEGER
        ACCESS  read-only
        STATUS  mandatory
        DESCRIPTION
            "This Cdu IT reservoir vacuum locked out."
        ::= { cpqRackCduApolloItWaterEntry 42 }

    cpqRackCduApolloItWaterReservoirPressure OBJECT-TYPE
        SYNTAX  DisplayString (SIZE (0..25))
        ACCESS  read-only
        STATUS  mandatory
        DESCRIPTION
            "This Cdu IT reservoir pressure."
        ::= { cpqRackCduApolloItWaterEntry 43 }

    cpqRackCduApolloItWaterReservoirVolume OBJECT-TYPE
        SYNTAX  DisplayString (SIZE (0..25))
        ACCESS  read-only
        STATUS  mandatory
        DESCRIPTION
            "This Cdu IT reservoir volume."
        ::= { cpqRackCduApolloItWaterEntry 44 }

    cpqRackCduApolloItWaterReservoirTankWaterLevel OBJECT-TYPE
        SYNTAX  DisplayString (SIZE (0..25))
        ACCESS  read-only
        STATUS  mandatory
        DESCRIPTION
            "This Cdu IT reservoir tank water level."
        ::= { cpqRackCduApolloItWaterEntry 45 }

    cpqRackCduApolloItWaterReservoirWaterFillOn OBJECT-TYPE
        SYNTAX  INTEGER
        ACCESS  read-only
        STATUS  mandatory
        DESCRIPTION
            "This Cdu IT reservoir water fill ON."
        ::= { cpqRackCduApolloItWaterEntry 46 }

    cpqRackCduApolloItWaterReservoirAirInletValveStatusOn OBJECT-TYPE
        SYNTAX  INTEGER
        ACCESS  read-only
        STATUS  mandatory
        DESCRIPTION
            "This Cdu IT reservoir air inlet valve status ON."
        ::= { cpqRackCduApolloItWaterEntry 47 }

    cpqRackCduApolloItWaterReservoirAirInletValveSolenoidCutInSp OBJECT-TYPE
        SYNTAX  DisplayString (SIZE (0..25))
        ACCESS  read-only
        STATUS  mandatory
        DESCRIPTION
            "This Cdu IT reservoir air inlet valve solenoid cut in setpoint."
        ::= { cpqRackCduApolloItWaterEntry 48 }

    cpqRackCduApolloItWaterReservoirAirInletValveSolenoidCutOutSp OBJECT-TYPE
        SYNTAX  DisplayString (SIZE (0..25))
        ACCESS  read-only
        STATUS  mandatory
        DESCRIPTION
            "This Cdu IT reservoir air inlet valve solenoid cut out setpoint."
        ::= { cpqRackCduApolloItWaterEntry 49 }

    cpqRackCduApolloItWaterReservoirFlow OBJECT-TYPE
        SYNTAX  INTEGER
        ACCESS  read-only
        STATUS  mandatory
        DESCRIPTION
            "This Cdu IT reservoir flow."
        ::= { cpqRackCduApolloItWaterEntry 50 }

    cpqRackCduApolloItWaterReservoirEnergy OBJECT-TYPE
        SYNTAX  INTEGER
        ACCESS  read-only
        STATUS  mandatory
        DESCRIPTION
            "This Cdu IT reservoir energy."
        ::= { cpqRackCduApolloItWaterEntry 51 }

-- ****************************************************************************
--   Rack System Object Identification
--   =================================
--
-- The compaq enterprise                 (1.3.6.1.4.1.232)
--      cpqRackInfo Group                (1.3.6.1.4.1.232.22)
--       cpqRackSysObjID Group           (1.3.6.1.4.1.232.22.3)
--
-- ****************************************************************************

    cpqRackSystemObjectIdentification OBJECT-TYPE
        SYNTAX  DisplayString (SIZE (0..64))
        ACCESS  read-only
        STATUS  mandatory
        DESCRIPTION
            "The hardware identification string.

            The string will reported by the rack firmware."
        ::= { cpqRackSysObjID 1 }

-- ****************************************************************************
--   Rack Event Information
--   =================================
--
-- The compaq enterprise                 (1.3.6.1.4.1.232)
--      cpqRackInfo Group                (1.3.6.1.4.1.232.22)
--       cpqRackEventInfo Group          (1.3.6.1.4.1.232.22.4)
--
-- ****************************************************************************

    cpqRackEventIndicationIdentifier OBJECT-TYPE
        SYNTAX  DisplayString (SIZE (0..25))
        ACCESS  read-only
        STATUS  mandatory
        DESCRIPTION
            "The Event Indication Identifier."
        ::= { cpqRackEventInfo 1 }

    cpqRackEventIndicationTime OBJECT-TYPE
        SYNTAX  DisplayString (SIZE (0..33))
        ACCESS  read-only
        STATUS  optional
        DESCRIPTION
            "The Event Indication Time."
        ::= { cpqRackEventInfo 2 }

    cpqRackEventDescription OBJECT-TYPE
        SYNTAX  OCTET STRING (SIZE (0..1024))
        ACCESS  read-only
        STATUS  optional
        DESCRIPTION
            "The Event Description."
        ::= { cpqRackEventInfo 3 }

    cpqRackEventSummary OBJECT-TYPE
        SYNTAX  DisplayString (SIZE (0..255))
        ACCESS  read-only
        STATUS  optional
        DESCRIPTION
            "Short description of the reason for the event."
        ::= { cpqRackEventInfo 4 }

    cpqRackEventCategory OBJECT-TYPE
        SYNTAX	INTEGER {
                unknown(1),
                other(2),
                processor(3),
                memory(4),
                systemHardware(5),
                supportHardware(6),
                primaryStorageDevice(7),
                secondaryStorageDevice(8),
                otherStorageDevice(9),
                networkDevice(10),
                otherDevice(11),
                ioAdapter(12),
                networkAdapter(13),
                otherAdapter(14),
                processorPower(15),
                memoryPower(16),
                systemPower(17),
                primaryStorageDevicePower(18),
                secondaryStoragePower(19),
                otherStoragePower(20),
                otherPower(21),
                processorCooling(22),
                memoryCooling(23),
                systemCooling(24),
                primaryStorageDeviceCooling(25),
                secondaryStorageDeviceCooling(26),
                otherStorageDeviceCooling(27),
                otherCooling(28),
                systemHWSecurity(29),
                primaryStorageDeviceSecurity(30),
                secondaryStorageDeviceSecurity(31),
                otherStorageDeviceSecurity(32),
                otherHWSecurity(33),
                systemInterconnect(34),
                supportInterconnect(35),
                clusterInterconnect(36),
                storageInterconnect(37),
                networkInterconnect(38),
                otherInterconnect(39),
                os(40),
                systemFirmware(41),
                deviceFirmware(42),
                supportFirmware(43),
                systemFirmwareSecurity(44),
                osSecurity(45),
                softwareApplication(46),
                softwareApplicationSecurity(47),
                nonStopIncident(48)
                }
        ACCESS  read-only
        STATUS  optional
        DESCRIPTION
            "Category for the event.

            This category is intended to be used by the consumer to group events."
        ::= { cpqRackEventInfo 5 }

    cpqRackOtherEventCategory OBJECT-TYPE
        SYNTAX  DisplayString (SIZE (0..64))
        ACCESS  read-only
        STATUS  optional
        DESCRIPTION
            "A string defining other values for EventCategory.

            It is empty unless EventCategory value is other(1)."
        ::= { cpqRackEventInfo 6 }

    cpqRackEventSubCategory OBJECT-TYPE
        SYNTAX  INTEGER
        ACCESS  read-only
        STATUS  optional
        DESCRIPTION
            "Sub-category for the event.

            This sub-category is intended to be used by the consumer in conjunction
            with the EventCategory to provide additional granularity to group events.
            It is expected that additional values will be added that can be used with
            other EventCategory values."
        ::= { cpqRackEventInfo 7 }

    cpqRackOtherEventSubCategory OBJECT-TYPE
        SYNTAX  DisplayString (SIZE (0..64))
        ACCESS  read-only
        STATUS  optional
        DESCRIPTION
            "A string defining other values for EventSubCategory.

            It is empty unless EventSubCategory value is other(1)"
        ::= { cpqRackEventInfo 8 }

    cpqRackEventThreshold OBJECT-TYPE
        SYNTAX  INTEGER
        ACCESS  read-only
        STATUS  optional
        DESCRIPTION
            "Identifies the number of indications that need to occur as part of the
            internal provider throttling configured for this event."
        ::= { cpqRackEventInfo 9 }

    cpqRackEventTimeWin OBJECT-TYPE
        SYNTAX  INTEGER
        ACCESS  read-only
        STATUS  optional
        DESCRIPTION
            "Identifies the time window during which the EventThreshold number of events
            need to occur as part of the internal provider throttling configured for
            this event.

            Time is in minutes. 0 means any amount of time."
        ::= { cpqRackEventInfo 10 }

    cpqRackEventActualThreshold OBJECT-TYPE
        SYNTAX  INTEGER
        ACCESS  read-only
        STATUS  optional
        DESCRIPTION
            "Identifies the number of indications that have occurred to meet the
            internal provider throttling configured for this event."
        ::= { cpqRackEventInfo 11 }

    cpqRackEventActualTimeWin OBJECT-TYPE
        SYNTAX  INTEGER
        ACCESS  read-only
        STATUS  optional
        DESCRIPTION
            "Identifies the time window during which the ActualEventThreshold number
            of events have occurred to meet the internal provider throttling configured
            for this event.

            Time is in minutes. 0 means any amount of time."
        ::= { cpqRackEventInfo 12 }

    cpqRackEventProviderVersion OBJECT-TYPE
        SYNTAX  DisplayString (SIZE (0..31))
        ACCESS  read-only
        STATUS  optional
        DESCRIPTION
            "The version of the provider generating this indication."
        ::= { cpqRackEventInfo 13 }

   cpqRackEventAlertingElementFormat OBJECT-TYPE
        SYNTAX	INTEGER {
                unknown(1),
                other(2),
                cimObjectPath(3)
                }
        ACCESS  read-only
        STATUS  optional
        DESCRIPTION
            "The format of the AlertingManagedElement property is interpretable based
            upon the value of this property.

            Values are defined as:
            1 - unknown. The format is unknown or not meaningfully interpretable by a
            CIM client application.
            2 - other. The format is defined by the value of the OtherAlertingElementFormat
            property.
            3 - cimObjectPath. The format is a CIMObjectPath, specifying an instance in
            the CIM Schema."
        ::= { cpqRackEventInfo 14 }

    cpqRackEventOtherAlertingElementFormat OBJECT-TYPE
        SYNTAX  OCTET STRING ( SIZE (0..256))
        ACCESS  read-only
        STATUS  optional
        DESCRIPTION
            "A string defining other values for AlertingElementFormat.

            It is empty unless cpqRackEventAlertingElementFormat value is other(1)"
        ::= { cpqRackEventInfo 15 }

    cpqRackEventImpactedDomain OBJECT-TYPE
        SYNTAX  INTEGER {
                unknown(1),
                cluster(2),
                complex(3),
                enclosure(4),
                system(5),
                partition(6)
                }
        ACCESS  read-only
        STATUS  optional
        DESCRIPTION
            "ImpactedDomain is an enumerated value indicating the domain this event
            affects."
        ::= { cpqRackEventInfo 16 }

    cpqRackEventComplexName OBJECT-TYPE
        SYNTAX  DisplayString (SIZE (0..64))
        ACCESS  read-only
        STATUS  optional
        DESCRIPTION
            "The name of the complex."
        ::= { cpqRackEventInfo 17 }

    cpqRackEventPartitionId OBJECT-TYPE
        SYNTAX  DisplayString (SIZE (0..12))
        ACCESS  read-only
        STATUS  optional
        DESCRIPTION
            "The Unique Identifier for the Partition.

            The format of the partitionId will be of the form nparId:vparId."
        ::= { cpqRackEventInfo 18 }

    cpqRackEventTriggeringLogIDTable OBJECT-TYPE
        SYNTAX  SEQUENCE OF CpqRackEventTriggeringLogIDEntry
        ACCESS  not-accessible
        STATUS  optional
        DESCRIPTION
            "A table of rack of Low Level LOG IDs."
        ::= { cpqRackEventInfo 19 }

    cpqRackEventTriggeringLogIDEntry OBJECT-TYPE
        SYNTAX  CpqRackEventTriggeringLogIDEntry
        ACCESS  not-accessible
        STATUS  optional
        DESCRIPTION
            "The list of Low level LOG ID which were used to generate this event.

            The format of the value contained in this array is defined using the
            TriggeringLogIDFormat field."
        INDEX { cpqRackEventTriggeringLogID }
        ::= { cpqRackEventTriggeringLogIDTable 1 }

    CpqRackEventTriggeringLogIDEntry ::= SEQUENCE {
        cpqRackEventTriggeringLogID                     OCTET STRING
    }

    cpqRackEventTriggeringLogID OBJECT-TYPE
        SYNTAX OCTET STRING (SIZE (0..256))
        ACCESS read-only
        STATUS optional
        DESCRIPTION
           "A Low Lvevel LOG ID which were used to generate this event."
        ::= {cpqRackEventTriggeringLogIDEntry 1 }


    cpqRackEventTriggeringLogIDFormat OBJECT-TYPE
        SYNTAX  INTEGER {
                unknown(1),
                cimObjectPath(2)
                }
        ACCESS  read-only
        STATUS  optional
        DESCRIPTION
            "The format of the TriggeringLogID property which interpretable based upon
            the value of this property.

            Values are defined as:
            1 - unknown. The format is unknown or not meaningfully interpretable by a
            CIM client application.
            2 - cimObjectPath. The format is a CIMObjectPath, with format specifying an
            instance in the CIM Schema."
        ::= { cpqRackEventInfo 20 }

    cpqRackEventAlertType OBJECT-TYPE
        SYNTAX  INTEGER
        ACCESS  read-only
        STATUS  optional
        DESCRIPTION
            "The event alert type."
        ::= { cpqRackEventInfo 21 }

    cpqRackEventOtherAlertType OBJECT-TYPE
        SYNTAX  DisplayString ( SIZE (0..33))
        ACCESS  read-only
        STATUS  optional
        DESCRIPTION
            "The event other alert type.

            It is empty unless cpqRackEventAlertType value is other."
        ::= { cpqRackEventInfo 22 }

    cpqRackEventProbableCause OBJECT-TYPE
        SYNTAX  INTEGER
        ACCESS  read-only
        STATUS  optional
        DESCRIPTION
            "An enumerated value that describes the probable cause of the error."
        ::= { cpqRackEventInfo 23 }

    cpqRackEventProbableCauseDescription OBJECT-TYPE
        SYNTAX  OCTET STRING ( SIZE (0..1024))
        ACCESS  read-only
        STATUS  optional
        DESCRIPTION
            "A free-form string describing the probable cause of the error."
        ::= { cpqRackEventInfo 24 }

    cpqRackEventPerceivedSeverity OBJECT-TYPE
        SYNTAX  INTEGER
        ACCESS  read-only
        STATUS  optional
        DESCRIPTION
            "An enumerated value that describes the severity of the Indication from
            the point of view of the notifier."
        ::= { cpqRackEventInfo 25 }

    cpqRackEventOtherSeverity OBJECT-TYPE
        SYNTAX	DisplayString ( SIZE (0..64))
        ACCESS  read-only
        STATUS  optional
        DESCRIPTION
            "Other perceived severity.

            It is empty unless cpqRackEventPerceivedSeverity value is other."
        ::= { cpqRackEventInfo 26 }

    cpqRackEventTrending OBJECT-TYPE
        SYNTAX  INTEGER
        ACCESS  read-only
        STATUS  optional
        DESCRIPTION
            "The event trending."
        ::= { cpqRackEventInfo 27 }

    cpqRackEventRecommendedActions OBJECT-TYPE
        SYNTAX  OCTET STRING ( SIZE (0..1024))
        ACCESS  read-only
        STATUS  optional
        DESCRIPTION
            "A free-form string describing recommended actions to take to resolve the error."
        ::= { cpqRackEventInfo 28 }

    cpqRackEventID OBJECT-TYPE
        SYNTAX  DisplayString ( SIZE (0..64))
        ACCESS  read-only
        STATUS  optional
        DESCRIPTION
            "An instrumentation or provider specific value that describes the underlying real-world event
            represented by the indication related to the not-OK status."
        ::= { cpqRackEventInfo 29 }

    cpqRackEventTime OBJECT-TYPE
        SYNTAX  DisplayString ( SIZE (0..33))
        ACCESS  read-only
        STATUS  optional
        DESCRIPTION
            "The event time."
        ::= { cpqRackEventInfo 30 }

    cpqRackEventSystemCreationClassName OBJECT-TYPE
        SYNTAX  DisplayString ( SIZE (0..64))
        ACCESS  read-only
        STATUS  optional
        DESCRIPTION
            "The event system creation class name."
        ::= { cpqRackEventInfo 31 }

    cpqRackEventSystemName OBJECT-TYPE
        SYNTAX  DisplayString ( SIZE (0..64))
        ACCESS  read-only
        STATUS  optional
        DESCRIPTION
            "The event system name."
        ::= { cpqRackEventInfo 32 }

    cpqRackEventProviderName OBJECT-TYPE
        SYNTAX  DisplayString ( SIZE (0..64))
        ACCESS  read-only
        STATUS  optional
        DESCRIPTION
            "The name of the Provider that generated the indication related to the not-OK status."
        ::= { cpqRackEventInfo 33 }



-- ****************************************************************************
--  Rack Information Trap Definitions
--  =================================
--
--  The SNMP trap messages must not be bigger than 484 octets (bytes).
--
--  Trap support in an SNMP agent implementation is optional.  An SNMP
--  agent implementation may support all, some, or none of the traps.
--  If traps are supported, The user should be provided with the option of
--  disabling traps.
-- **************************************************************************

    cpqRackNameChanged TRAP-TYPE
        ENTERPRISE compaq
        VARIABLES  { sysName,
                     cpqHoTrapFlags,
                     cpqRackName,
                     cpqRackUid,
                     cpqRackSerialNum,
                     cpqRackTrapSequenceNum }
        DESCRIPTION
           "Rack name has changed.

            This trap signifies that an agent or utility has changed the name
            of the rack.  Each of the server blades in each of the enclosure
            within the rack will be updated to reflect the new rack name.

            It may take several minutes for the rack name change to be
            propagated throughout the entire rack.

            User Action: None."

        --#TYPE "Rack name changed (22001)"
        --#SUMMARY "The rack name has changed to %s."
        --#ARGUMENTS {2}
        --#SEVERITY INFORMATIONAL
        --#TIMEINDEX 99
        --#STATE OPERATIONAL
        --#SIMPLE_SEVERITY OK
        --#HWSTATUS_CATEGORY OA
        --#LIFECYCLE

        ::= 22001

    cpqRackEnclosureNameChanged TRAP-TYPE
        ENTERPRISE compaq
        VARIABLES  { sysName,
                     cpqHoTrapFlags,
                     cpqRackName,
                     cpqRackUid,
                     cpqRackCommonEnclosureName,
                     cpqRackCommonEnclosureSerialNum,
                     cpqRackCommonEnclosureModel,
                     cpqRackCommonEnclosureSparePartNumber,
                     cpqRackCommonEnclosureTrapSequenceNum }
        DESCRIPTION
           "The enclosure name has changed.

            This trap signifies that an agent or utility has changed the name
            of an enclosure within the rack.  Each of the components
            within the rack will be updated to reflect the new enclosure name.

            It may take several minutes for the enclosure name change to be
            propagated throughout the entire enclosure.

            User Action: None."

        --#TYPE "Enclosure name changed (22002)"
        --#SUMMARY "The enclosure name has changed to %s in rack %s."
        --#ARGUMENTS {4, 2}
        --#SEVERITY INFORMATIONAL
        --#TIMEINDEX 99
        --#STATE OPERATIONAL
        --#SIMPLE_SEVERITY OK
        --#HWSTATUS_CATEGORY OA
        --#LIFECYCLE

        ::= 22002

    cpqRackEnclosureRemoved TRAP-TYPE
        ENTERPRISE compaq
        VARIABLES  { sysName,
                     cpqHoTrapFlags,
                     cpqRackName,
                     cpqRackUid,
                     cpqRackCommonEnclosureName,
                     cpqRackCommonEnclosureModel,
                     cpqRackCommonEnclosureSerialNum,
                     cpqRackCommonEnclosureSparePartNumber,
                     cpqRackCommonEnclosureTrapSequenceNum }
        DESCRIPTION
           "The enclosure has been removed.

            This trap signifies that an enclosure has been removed from
            the rack.

            User Action: None."

        --#TYPE "Enclosure removed (22003)"
        --#SUMMARY "The enclosure %s has been removed from rack %s."
        --#ARGUMENTS {4, 2}
        --#SEVERITY INFORMATIONAL
        --#TIMEINDEX 99
        --#STATE OPERATIONAL
        --#SIMPLE_SEVERITY OK
        --#HWSTATUS_CATEGORY OA
        --#LIFECYCLE

        ::= 22003

    cpqRackEnclosureInserted TRAP-TYPE
        ENTERPRISE compaq
        VARIABLES  { sysName,
                     cpqHoTrapFlags,
                     cpqRackName,
                     cpqRackUid,
                     cpqRackCommonEnclosureName,
                     cpqRackCommonEnclosureModel,
                     cpqRackCommonEnclosureSerialNum,
                     cpqRackCommonEnclosureSparePartNumber,
                     cpqRackCommonEnclosureTrapSequenceNum }
        DESCRIPTION
           "The enclosure has been inserted.

            This trap signifies that an enclosure has been inserted into
            the rack.

            User Action: None."

        --#TYPE "Enclosure inserted (22004)"
        --#SUMMARY "The enclosure %s has been inserted into rack %s."
        --#ARGUMENTS {4, 2}
        --#SEVERITY INFORMATIONAL
        --#TIMEINDEX 99
        --#STATE OPERATIONAL
        --#SIMPLE_SEVERITY OK
        --#HWSTATUS_CATEGORY OA
        --#LIFECYCLE

        ::= 22004

    cpqRackEnclosureTempFailed TRAP-TYPE
        ENTERPRISE compaq
        VARIABLES  { sysName,
                     cpqHoTrapFlags,
                     cpqRackName,
                     cpqRackUid,
                     cpqRackCommonEnclosureName,
                     cpqRackCommonEnclosureSerialNum,
                     cpqRackCommonEnclosureTempLocation,
                     cpqRackCommonEnclosureSparePartNumber,
                     cpqRackCommonEnclosureTrapSequenceNum }
        DESCRIPTION
           "The enclosure temperature status has been set to failed.

            This trap signifies that a enclosure temperature sensor has
            been tripped indicating an overheat condition.

            User Action: Shutdown the enclosure and possibly the rack
            as soon as possible.  Ensure all fans are working properly and
            that air flow in the rack has not been blocked."

        --#TYPE "Enclosure temperature failed (22005)"
        --#SUMMARY "The temperature sensor %s in enclosure %s in rack %s has been set to failed."
        --#ARGUMENTS {6, 4, 2}
        --#SEVERITY CRITICAL
        --#TIMEINDEX 99
        --#STATE NONOPERATIONAL
        --#SIMPLE_SEVERITY CRITICAL
        --#HWSTATUS_CATEGORY THERMAL
        --#ACTION "Shutdown the enclosure and possibly the rack as soon as possible.  Ensure all fans are working properly and that air flow in the rack has not been blocked."

        ::= 22005

    cpqRackEnclosureTempDegraded TRAP-TYPE
        ENTERPRISE compaq
        VARIABLES  { sysName,
                     cpqHoTrapFlags,
                     cpqRackName,
                     cpqRackUid,
                     cpqRackCommonEnclosureName,
                     cpqRackCommonEnclosureSerialNum,
                     cpqRackCommonEnclosureTempLocation,
                     cpqRackCommonEnclosureSparePartNumber,
                     cpqRackCommonEnclosureTrapSequenceNum }
        DESCRIPTION
           "The enclosure temperature status has been set to degraded.

            This trap signifies that an enclosure temperature sensor has
            been tripped indicating a possible overheat condition.

            User Action: Shutdown the enclosure and possibly the rack
            as soon as possible.  Ensure all fans are working properly and
            that air flow in the rack has not been blocked."

        --#TYPE "Enclosure temperature degraded (22006)"
        --#SUMMARY "The temperature sensor %s in enclosure %s in rack %s has been set to degraded."
        --#ARGUMENTS {6, 4, 2}
        --#SEVERITY MAJOR
        --#TIMEINDEX 99
        --#STATE DEGRADED
        --#SIMPLE_SEVERITY MAJOR
        --#HWSTATUS_CATEGORY THERMAL
        --#ACTION "Shutdown the enclosure and possibly the rack as soon as possible.  Ensure all fans are working properly and that air flow in the rack has not been blocked."

        ::= 22006

    cpqRackEnclosureTempOk TRAP-TYPE
        ENTERPRISE compaq
        VARIABLES  { sysName,
                     cpqHoTrapFlags,
                     cpqRackName,
                     cpqRackUid,
                     cpqRackCommonEnclosureName,
                     cpqRackCommonEnclosureSerialNum,
                     cpqRackCommonEnclosureTempLocation,
                     cpqRackCommonEnclosureSparePartNumber,
                     cpqRackCommonEnclosureTrapSequenceNum }
        DESCRIPTION
           "The enclosure temperature status has been set to ok.

            This trap signifies that an enclosure temperature sensor has
            returned to normal.

            User Action: None."

        --#TYPE "Enclosure temperature ok (22007)"
        --#SUMMARY "The temperature sensor %s in enclosure %s in rack %s has been set to ok."
        --#ARGUMENTS {6, 4, 2}
        --#SEVERITY INFORMATIONAL
        --#TIMEINDEX 99
        --#STATE OPERATIONAL
        --#SIMPLE_SEVERITY OK
        --#HWSTATUS_CATEGORY THERMAL

        ::= 22007

    cpqRackEnclosureFanFailed TRAP-TYPE
        ENTERPRISE compaq
        VARIABLES  { sysName,
                     cpqHoTrapFlags,
                     cpqRackName,
                     cpqRackUid,
                     cpqRackCommonEnclosureName,
                     cpqRackCommonEnclosureSerialNum,
                     cpqRackCommonEnclosureFanLocation,
                     cpqRackCommonEnclosureFanSparePartNumber,
                     cpqRackCommonEnclosureTrapSequenceNum }
        DESCRIPTION
           "The enclosure fan status has been set to failed.

            This trap signifies that an enclosure fan has failed and
            no other fans in the redundant fan group are operating.
            This may result in overheating of the enclosure.

            User Action: Replace the fan as soon as possible."

        --#TYPE "Enclosure fan failed (22008)"
        --#SUMMARY "The fan %s in enclosure %s in rack %s has been set to failed."
        --#ARGUMENTS {6, 4, 2}
        --#SEVERITY CRITICAL
        --#TIMEINDEX 99
        --#STATE NONOPERATIONAL
        --#SIMPLE_SEVERITY CRITICAL
        --#HWSTATUS_CATEGORY THERMAL
        --#ACTION "Replace the failed enclosure fan."

        ::= 22008

    cpqRackEnclosureFanDegraded TRAP-TYPE
        ENTERPRISE compaq
        VARIABLES  { sysName,
                     cpqHoTrapFlags,
                     cpqRackName,
                     cpqRackUid,
                     cpqRackCommonEnclosureName,
                     cpqRackCommonEnclosureSerialNum,
                     cpqRackCommonEnclosureFanLocation,
                     cpqRackCommonEnclosureFanSparePartNumber,
                     cpqRackCommonEnclosureTrapSequenceNum }
        DESCRIPTION
           "The enclosure fan status has been set to degraded.

            This trap signifies that an enclosure fan has failed but
            other fans in the redundant fan group are still operating.
            This may result in overheating of the enclosure.

            User Action: Replace the fan as soon as possible."

        --#TYPE "Enclosure fan degraded (22009)"
        --#SUMMARY "The fan %s in enclosure %s in rack %s has been set to degraded."
        --#ARGUMENTS {6, 4, 2}
        --#SEVERITY MAJOR
        --#TIMEINDEX 99
        --#STATE DEGRADED
        --#SIMPLE_SEVERITY MAJOR
        --#HWSTATUS_CATEGORY THERMAL
        --#ACTION "Replace the failing enclosure fan."

        ::= 22009

    cpqRackEnclosureFanOk TRAP-TYPE
        ENTERPRISE compaq
        VARIABLES  { sysName,
                     cpqHoTrapFlags,
                     cpqRackName,
                     cpqRackUid,
                     cpqRackCommonEnclosureName,
                     cpqRackCommonEnclosureSerialNum,
                     cpqRackCommonEnclosureFanLocation,
                     cpqRackCommonEnclosureFanSparePartNumber,
                     cpqRackCommonEnclosureTrapSequenceNum }
        DESCRIPTION
           "The enclosure fan status has been set to ok.

            This trap signifies that an enclosure fan has returned
            to normal operation.

            User Action: None."

        --#TYPE "Enclosure fan ok (22010)"
        --#SUMMARY "The fan %s in enclosure %s in rack %s has been set to ok."
        --#ARGUMENTS {6, 4, 2}
        --#SEVERITY INFORMATIONAL
        --#TIMEINDEX 99
        --#STATE OPERATIONAL
        --#SIMPLE_SEVERITY OK
        --#HWSTATUS_CATEGORY THERMAL

        ::= 22010


    cpqRackEnclosureFanRemoved TRAP-TYPE
        ENTERPRISE compaq
        VARIABLES  { sysName,
                     cpqHoTrapFlags,
                     cpqRackName,
                     cpqRackUid,
                     cpqRackCommonEnclosureName,
                     cpqRackCommonEnclosureSerialNum,
                     cpqRackCommonEnclosureFanLocation,
                     cpqRackCommonEnclosureFanSparePartNumber,
                     cpqRackCommonEnclosureTrapSequenceNum }
        DESCRIPTION
           "The enclosure fan has been removed.

            User Action: None."

        --#TYPE "Enclosure fan removed (22011)"
        --#SUMMARY "The fan %s in enclosure %s in rack %s has been removed."
        --#ARGUMENTS {6, 4, 2}
        --#SEVERITY MINOR
        --#TIMEINDEX 99
        --#STATE OPERATIONAL
        --#SIMPLE_SEVERITY OK
        --#HWSTATUS_CATEGORY THERMAL
        --#LIFECYCLE

        ::= 22011

    cpqRackEnclosureFanInserted TRAP-TYPE
        ENTERPRISE compaq
        VARIABLES  { sysName,
                     cpqHoTrapFlags,
                     cpqRackName,
                     cpqRackUid,
                     cpqRackCommonEnclosureName,
                     cpqRackCommonEnclosureSerialNum,
                     cpqRackCommonEnclosureFanLocation,
                     cpqRackCommonEnclosureFanSparePartNumber,
                     cpqRackCommonEnclosureTrapSequenceNum }
        DESCRIPTION
           "The enclosure fan has been inserted.

            User Action: None."

        --#TYPE "Enclosure fan inserted (22012)"
        --#SUMMARY "The fan %s in enclosure %s in rack %s has been inserted."
        --#ARGUMENTS {6, 4, 2}
        --#SEVERITY INFORMATIONAL
        --#TIMEINDEX 99
        --#STATE OPERATIONAL
        --#SIMPLE_SEVERITY OK
        --#HWSTATUS_CATEGORY THERMAL
        --#LIFECYCLE

        ::= 22012

    cpqRackPowerSupplyFailed TRAP-TYPE
        ENTERPRISE compaq
        VARIABLES  { sysName,
                     cpqHoTrapFlags,
                     cpqRackName,
                     cpqRackUid,
                     cpqRackPowerSupplyEnclosureName,
                     cpqRackPowerSupplySerialNum,
                     cpqRackPowerSupplyPosition,
                     cpqRackPowerSupplyFWRev,
                     cpqRackPowerSupplySparePartNumber,
                     cpqRackCommonEnclosureSerialNum,
                     cpqRackCommonEnclosureTrapSequenceNum }
        DESCRIPTION
           "The power supply status has been set to failed.

            This trap signifies that a power supply has failed.

            User Action: Replace the power supply as soon as possible."

        --#TYPE "Rack power supply failed (22013)"
        --#SUMMARY "The power supply %s in enclosure %s in rack %s has been set to failed."
        --#ARGUMENTS {6, 4, 2}
        --#SEVERITY CRITICAL
        --#TIMEINDEX 99
        --#STATE NONOPERATIONAL
        --#SIMPLE_SEVERITY CRITICAL
        --#HWSTATUS_CATEGORY POWER
        --#ACTION "Replace the failed power supply."

        ::= 22013

    cpqRackPowerSupplyDegraded TRAP-TYPE
        ENTERPRISE compaq
        VARIABLES  { sysName,
                     cpqHoTrapFlags,
                     cpqRackName,
                     cpqRackUid,
                     cpqRackPowerSupplyEnclosureName,
                     cpqRackPowerSupplySerialNum,
                     cpqRackPowerSupplyPosition,
                     cpqRackPowerSupplyFWRev,
                     cpqRackPowerSupplySparePartNumber,
                     cpqRackCommonEnclosureSerialNum,
                     cpqRackCommonEnclosureTrapSequenceNum }
        DESCRIPTION
           "The power supply status has been set to degraded.

            This trap signifies that a power supply has degraded.

            User Action: Replace the power supply as soon as possible."

        --#TYPE "Rack power supply degraded (22014)"
        --#SUMMARY "The power supply %s in enclosure %s in rack %s has been set to degraded."
        --#ARGUMENTS {6, 4, 2}
        --#SEVERITY MAJOR
        --#TIMEINDEX 99
        --#STATE DEGRADED
        --#SIMPLE_SEVERITY MAJOR
        --#HWSTATUS_CATEGORY POWER
        --#ACTION "Replace the failing power supply."

        ::= 22014

    cpqRackPowerSupplyOk TRAP-TYPE
        ENTERPRISE compaq
        VARIABLES  { sysName,
                     cpqHoTrapFlags,
                     cpqRackName,
                     cpqRackUid,
                     cpqRackPowerSupplyEnclosureName,
                     cpqRackPowerSupplySerialNum,
                     cpqRackPowerSupplyPosition,
                     cpqRackPowerSupplyFWRev,
                     cpqRackPowerSupplySparePartNumber,
                     cpqRackCommonEnclosureSerialNum,
                     cpqRackCommonEnclosureTrapSequenceNum }
        DESCRIPTION
           "The power supply status has been set to ok.

            This trap signifies that a power supply has returned to normal
            operation.

            User Action: None."

        --#TYPE "Rack power supply ok (22015)"
        --#SUMMARY "The power supply %s in enclosure %s in rack %s has been set to ok."
        --#ARGUMENTS {6, 4, 2}
        --#SEVERITY INFORMATIONAL
        --#TIMEINDEX 99
        --#STATE OPERATIONAL
        --#SIMPLE_SEVERITY OK
        --#HWSTATUS_CATEGORY POWER

        ::= 22015

    cpqRackPowerSupplyRemoved TRAP-TYPE
        ENTERPRISE compaq
        VARIABLES  { sysName,
                     cpqHoTrapFlags,
                     cpqRackName,
                     cpqRackUid,
                     cpqRackPowerSupplyEnclosureName,
                     cpqRackPowerSupplySerialNum,
                     cpqRackPowerSupplyPosition,
                     cpqRackPowerSupplyFWRev,
                     cpqRackPowerSupplySparePartNumber,
                     cpqRackCommonEnclosureSerialNum,
                     cpqRackCommonEnclosureTrapSequenceNum }
        DESCRIPTION
           "The power supply has been removed.

            User Action: None."

        --#TYPE "Rack power supply removed (22016)"
        --#SUMMARY "The power supply %s in enclosure %s in rack %s has been removed."
        --#ARGUMENTS {6, 4, 2}
        --#SEVERITY INFORMATIONAL
        --#TIMEINDEX 99
        --#STATE OPERATIONAL
        --#SIMPLE_SEVERITY OK
        --#HWSTATUS_CATEGORY POWER
        --#LIFECYCLE

        ::= 22016

    cpqRackPowerSupplyInserted TRAP-TYPE
        ENTERPRISE compaq
        VARIABLES  { sysName,
                     cpqHoTrapFlags,
                     cpqRackName,
                     cpqRackUid,
                     cpqRackPowerSupplyEnclosureName,
                     cpqRackPowerSupplySerialNum,
                     cpqRackPowerSupplyPosition,
                     cpqRackPowerSupplyFWRev,
                     cpqRackPowerSupplySparePartNumber,
                     cpqRackCommonEnclosureSerialNum,
                     cpqRackCommonEnclosureTrapSequenceNum }
        DESCRIPTION
           "The power supply has been inserted.

            User Action: None."

        --#TYPE "Rack power supply inserted (22017)"
        --#SUMMARY "The power supply %s in enclosure %s in rack %s has been inserted."
        --#ARGUMENTS {6, 4, 2}
        --#SEVERITY INFORMATIONAL
        --#TIMEINDEX 99
        --#STATE OPERATIONAL
        --#SIMPLE_SEVERITY OK
        --#HWSTATUS_CATEGORY POWER
        --#LIFECYCLE

        ::= 22017

    cpqRackPowerSubsystemNotRedundant TRAP-TYPE
        ENTERPRISE compaq
        VARIABLES  { sysName,
                     cpqHoTrapFlags,
                     cpqRackName,
                     cpqRackUid,
                     cpqRackPowerEnclosureName,
                     cpqRackCommonEnclosureSerialNum,
                     cpqRackCommonEnclosureTrapSequenceNum }
        DESCRIPTION
           "The rack power subsystem is no longer in a redundant state.

            User Action: Replace any failed power supplies as soon as possible
            to return the system to a redundant state."

        --#TYPE "Rack power subsystem not redundant (22018)"
        --#SUMMARY "The power subsystem in enclosure %s in rack %s is no longer redundant."
        --#ARGUMENTS {4, 2}
        --#SEVERITY MAJOR
        --#TIMEINDEX 99
        --#STATE DEGRADED
        --#SIMPLE_SEVERITY MAJOR
        --#HWSTATUS_CATEGORY POWER
        --#ACTION "Replace any failed power supplies as soon as possible to return the system to a redundant state."
        --#CLEAR_PRIOR_EVENTS true

        ::= 22018

    cpqRackPowerSubsystemLineVoltageProblem TRAP-TYPE
        ENTERPRISE compaq
        VARIABLES  { sysName,
                     cpqHoTrapFlags,
                     cpqRackName,
                     cpqRackUid,
                     cpqRackPowerSupplyEnclosureName,
                     cpqRackPowerSupplyPosition,
                     cpqRackPowerSupplyFWRev,
                     cpqRackPowerSupplyInputLineStatus,
                     cpqRackPowerSupplySparePartNumber,
                     cpqRackCommonEnclosureSerialNum,
                     cpqRackCommonEnclosureTrapSequenceNum }
        DESCRIPTION
           "The rack power supply detected an input line voltage problem.

            User Action: Check the power input for the power supply or replace
            any failed power supplies as soon as possible."

        --#TYPE "Rack power supply input voltage problem (22019)"
        --#SUMMARY "The rack power supply detected an input line voltage problem in power supply %s, enclosure %s, rack %s."
        --#ARGUMENTS {5, 4, 2}
        --#SEVERITY MAJOR
        --#TIMEINDEX 99
        --#STATE DEGRADED
        --#SIMPLE_SEVERITY MAJOR
        --#HWSTATUS_CATEGORY POWER
        --#ACTION "Check the power input for the power supply or replace any failed power supplies as soon as possible."

        ::= 22019

    cpqRackPowerSubsystemOverloadCondition TRAP-TYPE
        ENTERPRISE compaq
        VARIABLES  { sysName,
                     cpqHoTrapFlags,
                     cpqRackName,
                     cpqRackUid,
                     cpqRackPowerEnclosureName,
                     cpqRackCommonEnclosureSparePartNumber,
                     cpqRackCommonEnclosureSerialNum,
                     cpqRackCommonEnclosureTrapSequenceNum }
        DESCRIPTION
           "The rack power subsystem overload condition.

            User Action: Replace any failed power supplies as soon as possible
            to return the system to a redundant state."

        --#TYPE "Rack power subsystem overload condition (22020)"
        --#SUMMARY "The power subsystem in enclosure %s in rack %s is in an overload condition."
        --#ARGUMENTS {4, 2}
        --#SEVERITY MAJOR
        --#TIMEINDEX 99
        --#STATE DEGRADED
        --#SIMPLE_SEVERITY MAJOR
        --#HWSTATUS_CATEGORY POWER
        --#ACTION "Replace any failed power supplies as soon as possible."
        --#CLEAR_PRIOR_EVENTS true
        ::= 22020

    cpqRackPowerShedAutoShutdown TRAP-TYPE
        ENTERPRISE compaq
        VARIABLES  { sysName,
                     cpqHoTrapFlags,
                     cpqRackName,
                     cpqRackUid,
                     cpqRackServerBladeEnclosureName,
                     cpqRackServerBladePosition,
                     cpqRackServerBladeSparePartNumber,
                     cpqRackCommonEnclosureSerialNum,
                     cpqRackCommonEnclosureTrapSequenceNum }
        DESCRIPTION
           "Server shutdown due to power shedding.

            The server blade was shutdown due to a lack of power.

            User Action: Check power connections or add power supplies."

        --#TYPE "Server shutdown due to power shedding (22021)"
        --#SUMMARY "The server shutdown due to lack of power blade %s, in enclosure %s, in rack %s."
        --#ARGUMENTS {5, 4, 2}
        --#SEVERITY CRITICAL
        --#TIMEINDEX 99
        --#STATE NONOPERATIONAL
        --#SIMPLE_SEVERITY CRITICAL
        --#HWSTATUS_CATEGORY POWER
        --#ACTION "Check the power connections for problems, then add power supplies if necessary."

        ::= 22021

    cpqRackServerPowerOnFailedNotRedundant TRAP-TYPE
        ENTERPRISE compaq
        VARIABLES  { sysName,
                     cpqHoTrapFlags,
                     cpqRackName,
                     cpqRackUid,
                     cpqRackServerBladeEnclosureName,
                     cpqRackServerBladePosition,
                     cpqRackServerBladeSparePartNumber,
                     cpqRackCommonEnclosureSerialNum,
                     cpqRackCommonEnclosureTrapSequenceNum }
        DESCRIPTION
           "Server power on prevented to preserve redundancy.

            There is not enough power to power on the server blade and
            maintain redundancy for the other blades in the enclosure.

            User Action: Check power connections or add power supplies."

        --#TYPE "Server power on prevented to preserve redundancy (22022)"
        --#SUMMARY "Server power on prevented to preserve redundancy in blade %s, in enclosure %s, in rack %s."
        --#ARGUMENTS {5, 4, 2}
        --#SEVERITY CRITICAL
        --#TIMEINDEX 99
        --#STATE NONOPERATIONAL
        --#SIMPLE_SEVERITY CRITICAL
        --#HWSTATUS_CATEGORY POWER
        --#ACTION "Check the power connections for problems, then add power supplies if necessary."

        ::= 22022

    cpqRackServerPowerOnFailedNotEnoughPower TRAP-TYPE
        ENTERPRISE compaq
        VARIABLES  { sysName,
                     cpqHoTrapFlags,
                     cpqRackName,
                     cpqRackUid,
                     cpqRackServerBladeEnclosureName,
                     cpqRackServerBladePosition,
                     cpqRackServerBladeSparePartNumber,
                     cpqRackCommonEnclosureSerialNum,
                     cpqRackCommonEnclosureTrapSequenceNum }
        DESCRIPTION
           "Inadequate power to power on.

            There is not enough power to power on the server blade.

            User Action: Check power connections or add power supplies."

        --#TYPE "Inadequate power to power on (22023)"
        --#SUMMARY "Inadequate power to power on blade %s, in enclosure %s, in rack %s."
        --#ARGUMENTS {5, 4, 2}
        --#SEVERITY CRITICAL
        --#TIMEINDEX 99
        --#STATE NONOPERATIONAL
        --#SIMPLE_SEVERITY CRITICAL
        --#HWSTATUS_CATEGORY DEVICEBAY
        --#ACTION "Check the power connections for problems, then add power supplies if necessary."

        ::= 22023

    cpqRackServerPowerOnFailedEnclosureNotFound TRAP-TYPE
        ENTERPRISE compaq
        VARIABLES  { sysName,
                     cpqHoTrapFlags,
                     cpqRackName,
                     cpqRackUid,
                     cpqRackServerBladeEnclosureName,
                     cpqRackServerBladePosition,
                     cpqRackServerBladeSparePartNumber,
                     cpqRackCommonEnclosureSerialNum,
                     cpqRackCommonEnclosureTrapSequenceNum }
        DESCRIPTION
           "Inadequate power to power on.

            There is not enough power to power on the server blade.  The
            server enclosure micro-controller was not found.

            User Action: Check server enclosure connections or add power supplies."

        --#TYPE "Inadequate power to power on (22024)"
        --#SUMMARY "Inadequate power to power on blade %s, in enclosure %s, in rack %s."
        --#ARGUMENTS {5, 4, 2}
        --#SEVERITY CRITICAL
        --#TIMEINDEX 99
        --#STATE NONOPERATIONAL
        --#SIMPLE_SEVERITY CRITICAL
        --#HWSTATUS_CATEGORY DEVICEBAY
        --#ACTION "Check the server enclosure connections for problems, then add power supplies if necessary."

        ::= 22024

    cpqRackServerPowerOnFailedPowerChassisNotFound TRAP-TYPE
        ENTERPRISE compaq
        VARIABLES  { sysName,
                     cpqHoTrapFlags,
                     cpqRackName,
                     cpqRackUid,
                     cpqRackServerBladeEnclosureName,
                     cpqRackServerBladePosition,
                     cpqRackServerBladeSparePartNumber,
                     cpqRackCommonEnclosureSerialNum,
                     cpqRackCommonEnclosureTrapSequenceNum }
        DESCRIPTION
           "Inadequate power to power on.

            There is not enough power to power on the server blade.  The
            power enclosure micro-controller was not found.

            User Action: Check power enclosure connections or add power supplies."

        --#TYPE "Inadequate power to power on (22025)"
        --#SUMMARY "Inadequate power to power on blade %s, in enclosure %s, in rack %s."
        --#ARGUMENTS {5, 4, 2}
        --#SEVERITY CRITICAL
        --#TIMEINDEX 99
        --#STATE NONOPERATIONAL
        --#SIMPLE_SEVERITY CRITICAL
        --#HWSTATUS_CATEGORY DEVICEBAY
        --#ACTION "Check the power enclosure connections for problems, then add power supplies if necessary."

        ::= 22025

    cpqRackServerPowerOnManualOverride TRAP-TYPE
        ENTERPRISE compaq
        VARIABLES  { sysName,
                     cpqHoTrapFlags,
                     cpqRackName,
                     cpqRackUid,
                     cpqRackServerBladeEnclosureName,
                     cpqRackServerBladePosition,
                     cpqRackServerBladeSparePartNumber,
                     cpqRackCommonEnclosureSerialNum,
                     cpqRackCommonEnclosureTrapSequenceNum }
        DESCRIPTION
           "Server power on via manual override.

            The server blade was powered on by a manual override.

            User Action: None."

        --#TYPE "Server power on via manual override (22026)"
        --#SUMMARY "Server power on via manual override on blade %s, in enclosure %s, in rack %s."
        --#ARGUMENTS {5, 4, 2}
        --#SEVERITY MAJOR
        --#TIMEINDEX 99
        --#STATE DEGRADED
        --#SIMPLE_SEVERITY MAJOR
        --#HWSTATUS_CATEGORY DEVICEBAY

        ::= 22026

    cpqRackFuseOpen TRAP-TYPE
        ENTERPRISE compaq
        VARIABLES  { sysName,
                     cpqHoTrapFlags,
                     cpqRackName,
                     cpqRackUid,
                     cpqRackCommonEnclosureName,
                     cpqRackCommonEnclosureFuseLocation,
                     cpqRackCommonEnclosureSparePartNumber,
                     cpqRackCommonEnclosureSerialNum,
                     cpqRackCommonEnclosureTrapSequenceNum }
        DESCRIPTION
           "Fuse open.

            The fuse has been tripped.

            User Action: Check enclosure and / or blade power connections and
            reset the fuse."

        --#TYPE "Fuse open (22027)"
        --#SUMMARY "Fuse open fuse %s, in enclosure %s, in rack %s."
        --#ARGUMENTS {5, 4, 2}
        --#SEVERITY MAJOR
        --#TIMEINDEX 99
        --#STATE DEGRADED
        --#SIMPLE_SEVERITY MAJOR
        --#HWSTATUS_CATEGORY ENCLOSURE
        --#ACTION "Check the enclosure and blade power connections, then reset the fuse."

        ::= 22027


    cpqRackServerBladeRemoved TRAP-TYPE
        ENTERPRISE compaq
        VARIABLES  { sysName,
                     cpqHoTrapFlags,
                     cpqRackName,
                     cpqRackUid,
                     cpqRackServerBladeEnclosureName,
                     cpqRackServerBladeName,
                     cpqRackServerBladePosition,
                     cpqRackServerBladeSparePartNumber,
                     cpqRackCommonEnclosureSerialNum,
                     cpqRackCommonEnclosureTrapSequenceNum }
        DESCRIPTION
           "Server blade removed.

            The server blade has been removed from the enclosure.

            User Action: None."

        --#TYPE "Server blade removed (22028)"
        --#SUMMARY "Server blade %s removed from position %s, in enclosure %s, in rack %s."
        --#ARGUMENTS {5, 6, 4, 2}
        --#SEVERITY INFORMATIONAL
        --#TIMEINDEX 99
        --#STATE OPERATIONAL
        --#SIMPLE_SEVERITY OK
        --#HWSTATUS_CATEGORY DEVICEBAY
        --#LIFECYCLE

        ::= 22028

    cpqRackServerBladeInserted TRAP-TYPE
        ENTERPRISE compaq
        VARIABLES  { sysName,
                     cpqHoTrapFlags,
                     cpqRackName,
                     cpqRackUid,
                     cpqRackServerBladeEnclosureName,
                     cpqRackServerBladeName,
                     cpqRackServerBladePosition,
                     cpqRackServerBladeSparePartNumber,
                     cpqRackCommonEnclosureSerialNum,
                     cpqRackCommonEnclosureTrapSequenceNum }
        DESCRIPTION
           "Server blade inserted.

            The server blade has been inserted into the enclosure.

            User Action: None."

        --#TYPE "Server blade inserted (22029)"
        --#SUMMARY "Server blade %s inserted into position %s, in enclosure %s, in rack %s."
        --#ARGUMENTS {5, 6, 4, 2}
        --#SEVERITY INFORMATIONAL
        --#TIMEINDEX 99
        --#STATE OPERATIONAL
        --#SIMPLE_SEVERITY OK
        --#HWSTATUS_CATEGORY DEVICEBAY
        --#LIFECYCLE

        ::= 22029

    cpqRackPowerChassisNotLoadBalanced TRAP-TYPE
        ENTERPRISE compaq
        VARIABLES  { sysName,
                     cpqHoTrapFlags,
                     cpqRackName,
                     cpqRackUid,
                     cpqRackCommonEnclosureName,
                     cpqRackCommonEnclosureSerialNum,
                     cpqRackCommonEnclosureSparePartNumber,
                     cpqRackCommonEnclosureTrapSequenceNum }
        DESCRIPTION
           "Power subsystem not load balanced.

            The power subsystem is out of balance for this power enclosure.

            User Action: Check the power enclosure and power supplies.  Replace
            any failed or degraded power supplies.  Add additional power supplies
            if needed."

        --#TYPE "Power subsystem not load balanced (22030)"
        --#SUMMARY "Power subsystem not load balanced in enclosure %s, in rack %s."
        --#ARGUMENTS {4, 2}
        --#SEVERITY MAJOR
        --#TIMEINDEX 99
        --#STATE DEGRADED
        --#SIMPLE_SEVERITY MAJOR
        --#HWSTATUS_CATEGORY POWER
        --#ACTION "Check the power enclosure and power supplies. Replace any failed or degraded power supplies. Add additional power supplies if needed."

        ::= 22030

    cpqRackPowerChassisDcPowerProblem TRAP-TYPE
        ENTERPRISE compaq
        VARIABLES  { sysName,
                     cpqHoTrapFlags,
                     cpqRackName,
                     cpqRackUid,
                     cpqRackCommonEnclosureName,
                     cpqRackCommonEnclosureSerialNum,
                     cpqRackCommonEnclosureSparePartNumber,
                     cpqRackCommonEnclosureTrapSequenceNum }
        DESCRIPTION
           "Power subsystem DC power problem.

            There is a power subsystem DC power problem for this power enclosure.

            User Action: Check the power enclosure and power supplies.  Replace
            any failed or degraded power supplies."

        --#TYPE "Power subsystem DC power problem (22031)"
        --#SUMMARY "Power subsystem DC power problem in enclosure %s, in rack %s."
        --#ARGUMENTS {4, 2}
        --#SEVERITY MAJOR
        --#TIMEINDEX 99
        --#STATE DEGRADED
        --#SIMPLE_SEVERITY MAJOR
        --#HWSTATUS_CATEGORY POWER
        --#ACTION "Check the power enclosure and power supplies. Replace any failed or degraded power supplies."

        ::= 22031

    cpqRackPowerChassisAcFacilityPowerExceeded TRAP-TYPE
        ENTERPRISE compaq
        VARIABLES  { sysName,
                     cpqHoTrapFlags,
                     cpqRackName,
                     cpqRackUid,
                     cpqRackCommonEnclosureName,
                     cpqRackCommonEnclosureSerialNum,
                     cpqRackCommonEnclosureSparePartNumber,
                     cpqRackCommonEnclosureTrapSequenceNum }
        DESCRIPTION
           "Power subsystem AC facility input power exceeded.

            There is a power subsystem Power subsystem AC facility input power
            exceeded for this power enclosure.

            User Action: Check the power enclosure and power supplies.  Replace
            any failed or degraded power supplies."

        --#TYPE "Power subsystem AC facility input power exceeded (22032)"
        --#SUMMARY "Power subsystem AC facility input power exceeded in enclosure %s, in rack %s."
        --#ARGUMENTS {4, 2}
        --#SEVERITY MAJOR
        --#TIMEINDEX 99
        --#STATE DEGRADED
        --#SIMPLE_SEVERITY MAJOR
        --#HWSTATUS_CATEGORY POWER
        --#ACTION "Check the power enclosure and power supplies. Replace any failed or degraded power supplies."

        ::= 22032



    cpqRackPowerUnknownPowerConsumption TRAP-TYPE
        ENTERPRISE compaq
        VARIABLES  { sysName,
                     cpqHoTrapFlags,
                     cpqRackName,
                     cpqRackUid,
                     cpqRackCommonEnclosureSerialNum,
                     cpqRackCommonEnclosureTrapSequenceNum }
        DESCRIPTION
           "Unknown power consumption.

            There is an unknown power consumer drawing power.

            User Action: Check the power enclosure and power supplies.  Replace
            any failed or degraded power supplies."

        --#TYPE "Unknown power consumption (22033)"
        --#SUMMARY "Unknown power consumption in rack %s."
        --#ARGUMENTS {2}
        --#SEVERITY MAJOR
        --#TIMEINDEX 99
        --#STATE DEGRADED
        --#SIMPLE_SEVERITY MAJOR
        --#HWSTATUS_CATEGORY POWER
        --#ACTION "Check the power enclosure and power supplies. Replace any failed or degraded power supplies."

        ::= 22033

    cpqRackPowerChassisLoadBalancingWireMissing TRAP-TYPE
        ENTERPRISE compaq
        VARIABLES  { sysName,
                     cpqHoTrapFlags,
                     cpqRackName,
                     cpqRackUid,
                     cpqRackCommonEnclosureName,
                     cpqRackCommonEnclosureSerialNum,
                     cpqRackCommonEnclosureSparePartNumber,
                     cpqRackCommonEnclosureTrapSequenceNum }
        DESCRIPTION
           "Power subsystem load balancing wire missing.

            The power subsystem load balancing wire missing.

            User Action: Connect the load balancing wire."

        --#TYPE "Power subsystem load balancing wire missing (22034)"
        --#SUMMARY "Power subsystem load balancing wire missing for enclosure %s, in rack %s."
        --#ARGUMENTS {4, 2}
        --#SEVERITY MAJOR
        --#TIMEINDEX 99
        --#STATE DEGRADED
        --#SIMPLE_SEVERITY MAJOR
        --#HWSTATUS_CATEGORY POWER
        --#ACTION "Connect the load balancing wire."

        ::= 22034

    cpqRackPowerChassisTooManyPowerChassis TRAP-TYPE
        ENTERPRISE compaq
        VARIABLES  { sysName,
                     cpqHoTrapFlags,
                     cpqRackName,
                     cpqRackUid,
                     cpqRackCommonEnclosureName,
                     cpqRackCommonEnclosureSerialNum,
                     cpqRackCommonEnclosureTrapSequenceNum }
        DESCRIPTION
           "Power subsystem has too may power enclosures.

            The maximum number of power enclosures has been exceeded.

            User Action: Remove the extra power enclosure."

        --#TYPE "Power subsystem has too may power enclosures (22035)"
        --#SUMMARY "Power subsystem has too may power enclosures %s, in rack %s."
        --#ARGUMENTS {4, 2}
        --#SEVERITY MAJOR
        --#TIMEINDEX 99
        --#STATE DEGRADED
        --#SIMPLE_SEVERITY MAJOR
        --#HWSTATUS_CATEGORY POWER
        --#ACTION "Remove the extra power enclosure."

        ::= 22035

    cpqRackPowerChassisConfigError TRAP-TYPE
        ENTERPRISE compaq
        VARIABLES  { sysName,
                     cpqHoTrapFlags,
                     cpqRackName,
                     cpqRackUid,
                     cpqRackCommonEnclosureName,
                     cpqRackCommonEnclosureSerialNum,
                     cpqRackCommonEnclosureSparePartNumber,
                     cpqRackCommonEnclosureTrapSequenceNum }
        DESCRIPTION
           "Power subsystem improperly configured.

            The power subsystem has been improperly configured.

            User Action: Check the cabling of the power enclosure."

        --#TYPE "Power subsystem improperly configured (22036)"
        --#SUMMARY "Power subsystem has been improperly configured in enclosure %s, in rack %s."
        --#ARGUMENTS {4, 2}
        --#SEVERITY MAJOR
        --#TIMEINDEX 99
        --#STATE DEGRADED
        --#SIMPLE_SEVERITY MAJOR
        --#HWSTATUS_CATEGORY POWER
        --#ACTION "Check the cabling of the power enclosure."

        ::= 22036

    cpqRackEnclosureManagerDegraded TRAP-TYPE
        ENTERPRISE compaq
        VARIABLES  { sysName,
                     cpqHoTrapFlags,
                     cpqRackName,
                     cpqRackUid,
                     cpqRackCommonEnclosureName,
                     cpqRackCommonEnclosureSerialNum,
                     cpqRackCommonEnclosureManagerLocation,
                     cpqRackCommonEnclosureManagerSparePartNumber,
                     cpqRackCommonEnclosureManagerSerialNum,
                     cpqRackCommonEnclosureTrapSequenceNum }
        DESCRIPTION
           "The Onboard Administrator or other management processor status has been set to degraded.

            This trap signifies that either the Onboard Administrator(s) or its component(s) has degraded/failed,
            their firmware versions are mismatched, or one or more management processors is in a non-optimal operating state.

            User Action: For C-Class enclosures, please refer to the Onboard Administrator SYSLOG.
            For all the others please refer to product documentation for possible corrective actions"

        --#TYPE "Enclosure manager degraded (22037)"
        --#SUMMARY "The enclosure %s manager in rack %s has been set to degraded."
        --#ARGUMENTS {4, 2}
        --#SEVERITY MAJOR
        --#TIMEINDEX 99
        --#STATE DEGRADED
        --#SIMPLE_SEVERITY MAJOR
        --#HWSTATUS_CATEGORY OA
        --#ACTION "The following conditions can result in a degraded Onboard Administrator (OA): 1) one OA failed but the second OA is still operating, 2) one or more OAs is in a non-optimal operating state, 3) a firmware revision mismatch occurred between the primary and secondary OAs, or 4) OA RTC battery is low.  To determine what caused the issue, see the OA and check the logs for more  information.    If a firmware mismatch occurred, use the OA UI or CLI (UPDATE IMAGE SYNC command) to resynchronize the firmware on the OAs.   If OA RTC battery  is found to be low, replace battery."


        ::= 22037

    cpqRackEnclosureManagerOk TRAP-TYPE
        ENTERPRISE compaq
        VARIABLES  { sysName,
                     cpqHoTrapFlags,
                     cpqRackName,
                     cpqRackUid,
                     cpqRackCommonEnclosureName,
                     cpqRackCommonEnclosureSerialNum,
                     cpqRackCommonEnclosureManagerLocation,
                     cpqRackCommonEnclosureManagerSparePartNumber,
                     cpqRackCommonEnclosureManagerSerialNum,
                     cpqRackCommonEnclosureTrapSequenceNum }
        DESCRIPTION
           "The Onboard Administrator or other management processor's status has been set to ok.

            This trap signifies that an Onboard Administrator or other management processor has returned
            to normal operation.

            User Action: None."

        --#TYPE "Onboard or management processor ok (22038)"
        --#SUMMARY "The Onboard Administrator or management processor %s in rack %s has been set to ok."
        --#ARGUMENTS {4, 2}
        --#SEVERITY INFORMATIONAL
        --#TIMEINDEX 99
        --#STATE OPERATIONAL
        --#SIMPLE_SEVERITY OK
        --#HWSTATUS_CATEGORY OA

        ::= 22038

    cpqRackEnclosureManagerRemoved TRAP-TYPE
        ENTERPRISE compaq
        VARIABLES  { sysName,
                     cpqHoTrapFlags,
                     cpqRackName,
                     cpqRackUid,
                     cpqRackCommonEnclosureName,
                     cpqRackCommonEnclosureSerialNum,
                     cpqRackCommonEnclosureManagerLocation,
                     cpqRackCommonEnclosureManagerSparePartNumber,
                     cpqRackCommonEnclosureManagerSerialNum,
                     cpqRackCommonEnclosureTrapSequenceNum }
        DESCRIPTION
           "The Onboard Administrator has been removed.

            User Action: None."

        --#TYPE "Onboard Administrator removed (22039)"
        --#SUMMARY "The Onboard Administrator %s in rack %s has been removed."
        --#ARGUMENTS {4, 2}
        --#SEVERITY INFORMATIONAL
        --#TIMEINDEX 99
        --#STATE OPERATIONAL
        --#SIMPLE_SEVERITY OK
        --#HWSTATUS_CATEGORY OA
        --#LIFECYCLE

        ::= 22039

    cpqRackEnclosureManagerInserted TRAP-TYPE
        ENTERPRISE compaq
        VARIABLES  { sysName,
                     cpqHoTrapFlags,
                     cpqRackName,
                     cpqRackUid,
                     cpqRackCommonEnclosureName,
                     cpqRackCommonEnclosureSerialNum,
                     cpqRackCommonEnclosureManagerLocation,
                     cpqRackCommonEnclosureManagerSparePartNumber,
                     cpqRackCommonEnclosureManagerSerialNum,
                     cpqRackCommonEnclosureTrapSequenceNum }
        DESCRIPTION
           "The Onboard Administrator or other management processor has been inserted.

            User Action: None."

        --#TYPE "Onboard Administrator or other management processor inserted (22040)"
        --#SUMMARY "The Onboard Administrator or other management processor %s in rack %s has been inserted."
        --#ARGUMENTS {4, 2}
        --#SEVERITY INFORMATIONAL
        --#TIMEINDEX 99
        --#STATE OPERATIONAL
        --#SIMPLE_SEVERITY OK
        --#HWSTATUS_CATEGORY OA
        --#LIFECYCLE

        ::= 22040

    cpqRackManagerPrimaryRole TRAP-TYPE
        ENTERPRISE compaq
        VARIABLES  { sysName,
                     cpqHoTrapFlags,
                     cpqRackName,
                     cpqRackUid,
                     cpqRackCommonEnclosureName,
                     cpqRackCommonEnclosureSerialNum,
                     cpqRackCommonEnclosureManagerLocation,
                     cpqRackCommonEnclosureManagerSparePartNumber,
                     cpqRackCommonEnclosureManagerSerialNum,
                     cpqRackCommonEnclosureTrapSequenceNum }
        DESCRIPTION
           "The Onboard Administrator or other management processor has taken the role of primary.

            User Action: None."

        --#TYPE "Onboard Administrator or other management processor has taken the role of primary (UID)."
        --#SUMMARY "Onboard Administrator or other management processor has taken the role of primary, in enclosure %s, in rack %s."
        --#ARGUMENTS {4, 2}
        --#SEVERITY MAJOR
        --#TIMEINDEX 99
        --#STATE OPERATIONAL
        --#SIMPLE_SEVERITY MAJOR
        --#HWSTATUS_CATEGORY OA

        ::= 22041

    cpqRackServerBladeEKeyingFailed TRAP-TYPE
        ENTERPRISE compaq
        VARIABLES  { sysName,
                     cpqHoTrapFlags,
                     cpqRackName,
                     cpqRackUid,
                     cpqRackServerBladeEnclosureName,
                     cpqRackServerBladeName,
                     cpqRackServerBladePosition,
                     cpqRackServerBladeSparePartNumber,
                     cpqRackCommonEnclosureSerialNum,
                     cpqRackCommonEnclosureTrapSequenceNum }
        DESCRIPTION
           "The server blade e-keying has failed.

            This trap signifies that a server blade e-keying has failed and
            there is a port mapping problem between a server mezz card
            and the interconnect.

            User Action: Reconfigure server blade mezz cards."

        --#TYPE "Server Blade e-keying failed (22042)"
        --#SUMMARY "Server blade %s e-keying failed in position %s, in enclosure %s, in rack %s."
        --#ARGUMENTS {5, 6, 4, 2}
        --#SEVERITY MAJOR
        --#TIMEINDEX 99
        --#STATE DEGRADED
        --#SIMPLE_SEVERITY MAJOR
        --#HWSTATUS_CATEGORY DEVICEBAY
        --#ACTION "Reconfigure the server blade mezz cards."

        ::= 22042

    cpqRackServerBladeEKeyingOK TRAP-TYPE
        ENTERPRISE compaq
        VARIABLES  { sysName,
                     cpqHoTrapFlags,
                     cpqRackName,
                     cpqRackUid,
                     cpqRackServerBladeEnclosureName,
                     cpqRackServerBladeName,
                     cpqRackServerBladePosition,
                     cpqRackServerBladeSparePartNumber,
                     cpqRackCommonEnclosureSerialNum,
                     cpqRackCommonEnclosureTrapSequenceNum }
        DESCRIPTION
           "The server blade e-keying is ok.

            This trap signifies that a server blade e-keying has returned to
            normal operation.

            User Action: None."

        --#TYPE "Server Blade e-keying ok (22043)"
        --#SUMMARY "Server blade %s e-keying is ok in position %s, in enclosure %s, in rack %s."
        --#ARGUMENTS {5, 6, 4, 2}
        --#SEVERITY INFORMATIONAL
        --#TIMEINDEX 99
        --#STATE OPERATIONAL
        --#SIMPLE_SEVERITY OK
        --#HWSTATUS_CATEGORY DEVICEBAY

        ::= 22043

    cpqRackNetConnectorRemoved TRAP-TYPE
        ENTERPRISE compaq
        VARIABLES  { sysName,
                     cpqHoTrapFlags,
                     cpqRackName,
                     cpqRackUid,
                     cpqRackNetConnectorEnclosureName,
                     cpqRackNetConnectorName,
                     cpqRackNetConnectorLocation,
                     cpqRackNetConnectorSparePartNumber,
                     cpqRackCommonEnclosureSerialNum,
                     cpqRackCommonEnclosureTrapSequenceNum }
        DESCRIPTION
           "Interconnect removed.

            The interconnect has been removed from the enclosure.

            User Action: None."

        --#TYPE "Interconnect removed (22044)"
        --#SUMMARY "Interconnect %s removed from position %s, in enclosure %s, in rack %s."
        --#ARGUMENTS {5, 6, 4, 2}
        --#SEVERITY INFORMATIONAL
        --#TIMEINDEX 99
        --#STATE OPERATIONAL
        --#SIMPLE_SEVERITY OK
        --#HWSTATUS_CATEGORY INTERCONNECTBAY
        --#LIFECYCLE

        ::= 22044

    cpqRackNetConnectorInserted TRAP-TYPE
        ENTERPRISE compaq
        VARIABLES  { sysName,
                     cpqHoTrapFlags,
                     cpqRackName,
                     cpqRackUid,
                     cpqRackNetConnectorEnclosureName,
                     cpqRackNetConnectorName,
                     cpqRackNetConnectorLocation,
                     cpqRackNetConnectorSparePartNumber,
                     cpqRackCommonEnclosureSerialNum,
                     cpqRackCommonEnclosureTrapSequenceNum }
        DESCRIPTION
           "Interconnect inserted.

            The interconnect has been inserted into the enclosure.

            User Action: None."

        --#TYPE "Interconnect inserted (22045)"
        --#SUMMARY "Interconnect %s inserted into position %s, in enclosure %s, in rack %s."
        --#ARGUMENTS {5, 6, 4, 2}
        --#SEVERITY INFORMATIONAL
        --#TIMEINDEX 99
        --#STATE OPERATIONAL
        --#SIMPLE_SEVERITY OK
        --#HWSTATUS_CATEGORY INTERCONNECTBAY
        --#LIFECYCLE

        ::= 22045

    cpqRackNetConnectorFailed TRAP-TYPE
        ENTERPRISE compaq
        VARIABLES  { sysName,
                     cpqHoTrapFlags,
                     cpqRackName,
                     cpqRackUid,
                     cpqRackNetConnectorEnclosureName,
                     cpqRackNetConnectorName,
                     cpqRackNetConnectorLocation,
                     cpqRackNetConnectorSparePartNumber,
                     cpqRackCommonEnclosureSerialNum,
                     cpqRackCommonEnclosureTrapSequenceNum }
        DESCRIPTION
           "The interconnect status has been set to failed.

            This trap signifies that a interconnect has failed.

            User Action: Replace the interconnect as soon as possible."

        --#TYPE "Interconnect failed (22046)"
        --#SUMMARY "Interconnect %s failed in position %s, in enclosure %s, in rack %s."
        --#ARGUMENTS {5, 6, 4, 2}
        --#SEVERITY CRITICAL
        --#TIMEINDEX 99
        --#STATE NONOPERATIONAL
        --#SIMPLE_SEVERITY CRITICAL
        --#HWSTATUS_CATEGORY INTERCONNECTBAY
        --#ACTION "Refer to the OA and the status diagnostics reported for the interconnect."

        ::= 22046

    cpqRackNetConnectorDegraded TRAP-TYPE
        ENTERPRISE compaq
        VARIABLES  { sysName,
                     cpqHoTrapFlags,
                     cpqRackName,
                     cpqRackUid,
                     cpqRackNetConnectorEnclosureName,
                     cpqRackNetConnectorName,
                     cpqRackNetConnectorLocation,
                     cpqRackNetConnectorSparePartNumber,
                     cpqRackCommonEnclosureSerialNum,
                     cpqRackCommonEnclosureTrapSequenceNum }
        DESCRIPTION
           "The interconnect status has been set to degraded.

            This trap signifies that a interconnect has degraded.

            User Action: Refer to the OA and the status diagnostics reported for the interconnect."

        --#TYPE "Interconnect degraded (22047)"
        --#SUMMARY "Interconnect %s degraded in position %s, in enclosure %s, in rack %s."
        --#ARGUMENTS {5, 6, 4, 2}
        --#SEVERITY MAJOR
        --#TIMEINDEX 99
        --#STATE DEGRADED
        --#SIMPLE_SEVERITY MAJOR
        --#HWSTATUS_CATEGORY INTERCONNECTBAY
        --#ACTION "Refer to the OA and the status diagnostics reported for the interconnect."

        ::= 22047

    cpqRackNetConnectorOk TRAP-TYPE
        ENTERPRISE compaq
        VARIABLES  { sysName,
                     cpqHoTrapFlags,
                     cpqRackName,
                     cpqRackUid,
                     cpqRackNetConnectorEnclosureName,
                     cpqRackNetConnectorName,
                     cpqRackNetConnectorLocation,
                     cpqRackNetConnectorSparePartNumber,
                     cpqRackCommonEnclosureSerialNum,
                     cpqRackCommonEnclosureTrapSequenceNum }
        DESCRIPTION
           "The interconnect status has been set to ok.

            This trap signifies that a interconnect has returned to
            normal operation.

            User Action: None."

        --#TYPE "Interconnect ok (22048)"
        --#SUMMARY "Interconnect %s ok in position %s, in enclosure %s, in rack %s."
        --#ARGUMENTS {5, 6, 4, 2}
        --#SEVERITY INFORMATIONAL
        --#TIMEINDEX 99
        --#STATE OPERATIONAL
        --#SIMPLE_SEVERITY OK
        --#HWSTATUS_CATEGORY INTERCONNECTBAY

        ::= 22048

    cpqRackServerBladeToLowPower TRAP-TYPE
        ENTERPRISE compaq
        VARIABLES  { sysName,
                     cpqHoTrapFlags,
                     cpqRackName,
                     cpqRackUid,
                     cpqRackServerBladeEnclosureName,
                     cpqRackServerBladeName,
                     cpqRackServerBladePosition,
                     cpqRackServerBladeSparePartNumber,
                     cpqRackCommonEnclosureSerialNum,
                     cpqRackCommonEnclosureTrapSequenceNum }
        DESCRIPTION
           "The server blade requested to low power.

            User Action: None."

        --#TYPE "Server Blade requested to low power (22049)"
        --#SUMMARY "Server blade %s requested to low power in position %s, in enclosure %s, in rack %s."
        --#ARGUMENTS {5, 6, 4, 2}
        --#SEVERITY MAJOR
        --#TIMEINDEX 99
        --#STATE DEGRADED
        --#SIMPLE_SEVERITY MAJOR
        --#HWSTATUS_CATEGORY DEVICEBAY

        ::= 22049

    cpqRackServerBladeRemoved2 TRAP-TYPE
        ENTERPRISE compaq
        VARIABLES  { sysName,
                     cpqHoTrapFlags,
                     cpqRackName,
                     cpqRackUid,
                     cpqRackServerBladeEnclosureName,
                     cpqRackServerBladeName,
                     cpqRackServerBladePosition,
                     cpqRackServerBladeSparePartNumber,
                     cpqRackCommonEnclosureSerialNum,
                     cpqRackServerBladeSerialNum,
                     cpqRackServerBladeUid,
                     cpqRackCommonEnclosureTrapSequenceNum }
        DESCRIPTION
           "Server blade removed.

            The server blade has been removed from the enclosure.

            User Action: None."

        --#TYPE "Server blade removed (22050)"
        --#SUMMARY "Server blade %s removed from position %s, in enclosure %s, in rack %s."
        --#ARGUMENTS {5, 6, 4, 2}
        --#SEVERITY INFORMATIONAL
        --#TIMEINDEX 99
        --#STATE OPERATIONAL
        --#SIMPLE_SEVERITY OK
        --#HWSTATUS_CATEGORY DEVICEBAY
        --#LIFECYCLE

        ::= 22050

    cpqRackServerBladeInserted2 TRAP-TYPE
        ENTERPRISE compaq
        VARIABLES  { sysName,
                     cpqHoTrapFlags,
                     cpqRackName,
                     cpqRackUid,
                     cpqRackServerBladeEnclosureName,
                     cpqRackServerBladeName,
                     cpqRackServerBladePosition,
                     cpqRackServerBladeSparePartNumber,
                     cpqRackCommonEnclosureSerialNum,
                     cpqRackServerBladeSerialNum,
                     cpqRackServerBladeUid,
                     cpqRackCommonEnclosureTrapSequenceNum }
        DESCRIPTION
           "Server blade inserted.

            The server blade has been inserted into the enclosure.

            User Action: None."

        --#TYPE "Server blade inserted (22051)"
        --#SUMMARY "Server blade %s inserted into position %s, in enclosure %s, in rack %s."
        --#ARGUMENTS {5, 6, 4, 2}
        --#SEVERITY INFORMATIONAL
        --#TIMEINDEX 99
        --#STATE OPERATIONAL
        --#SIMPLE_SEVERITY OK
        --#HWSTATUS_CATEGORY DEVICEBAY
        --#LIFECYCLE

        ::= 22051

    cpqRackServerBladeStatusRepaired TRAP-TYPE
        ENTERPRISE compaq
        VARIABLES  { sysName,
                     cpqHoTrapFlags,
                     cpqRackName,
                     cpqRackUid,
                     cpqRackServerBladeEnclosureName,
                     cpqRackServerBladeName,
                     cpqRackServerBladeProductId,
                     cpqRackServerBladePosition,
                     cpqRackServerBladeSparePartNumber,
                     cpqRackCommonEnclosureSerialNum,
                     cpqRackServerBladeSerialNum,
                     cpqRackServerBladeUid,
                     cpqRackCommonEnclosureTrapSequenceNum }
        DESCRIPTION
           "Server blade repaired.

            The server blade status has changed to OK.

            User Action: None."

        --#TYPE "Server blade repaired (22052)"
        --#SUMMARY "Server blade %s in position %s, in enclosure %s, in rack %s status has changed to OK."
        --#ARGUMENTS {5, 7, 4, 2}
        --#SEVERITY INFORMATIONAL
        --#TIMEINDEX 99
        --#STATE OPERATIONAL
        --#SIMPLE_SEVERITY OK
        --#HWSTATUS_CATEGORY DEVICEBAY

        ::= 22052

cpqRackServerBladeStatusDegraded TRAP-TYPE
        ENTERPRISE compaq
        VARIABLES  { sysName,
                     cpqHoTrapFlags,
                     cpqRackName,
                     cpqRackUid,
                     cpqRackServerBladeEnclosureName,
                     cpqRackServerBladeName,
                     cpqRackServerBladeProductId,
                     cpqRackServerBladePosition,
                     cpqRackServerBladeSparePartNumber,
                     cpqRackCommonEnclosureSerialNum,
                     cpqRackServerBladeSerialNum,
                     cpqRackServerBladeUid,
                     cpqRackServerBladeFaultMajor,
                     cpqRackServerBladeFaultMinor,
                     cpqRackServerBladeFaultDiagnosticString,
                     cpqRackCommonEnclosureTrapSequenceNum }
        DESCRIPTION
           "Server blade health status Degraded.

            The server blade health status has changed to Degraded.

            User Action: Check blade server and enclosure SYSLOG."

        --#TYPE "Server blade health status degraded (22053)"
        --#SUMMARY "Server blade %s in position %s, in enclosure %s, in rack %s health status has changed to degraded.  Reason:  %s."
        --#ARGUMENTS {5, 7, 4, 2, 14}
        --#SEVERITY MAJOR
        --#TIMEINDEX 99
        --#STATE OPERATIONAL
        --#SIMPLE_SEVERITY MAJOR
        --#HWSTATUS_CATEGORY DEVICEBAY
        --#ACTION "Check the blade server and enclosure SYSLOG."

        ::= 22053

cpqRackServerBladeStatusCritical TRAP-TYPE
        ENTERPRISE compaq
        VARIABLES  { sysName,
                     cpqHoTrapFlags,
                     cpqRackName,
                     cpqRackUid,
                     cpqRackServerBladeEnclosureName,
                     cpqRackServerBladeName,
                     cpqRackServerBladeProductId,
                     cpqRackServerBladePosition,
                     cpqRackServerBladeSparePartNumber,
                     cpqRackCommonEnclosureSerialNum,
                     cpqRackServerBladeSerialNum,
                     cpqRackServerBladeUid,
                     cpqRackServerBladeFaultMajor,
                     cpqRackServerBladeFaultMinor,
                     cpqRackServerBladeFaultDiagnosticString,
                     cpqRackCommonEnclosureTrapSequenceNum }
        DESCRIPTION
           "Server blade health status Critical.

            The server blade health status has changed to Critical.

            User Action: Check blade server and enclosure SYSLOG."

        --#TYPE "Server blade health status critical (22054)"
        --#SUMMARY "Server blade %s in position %s, in enclosure %s, in rack %s health status has changed to critical.   Reason:  %s."
        --#ARGUMENTS {5, 7, 4, 2, 14}
        --#SEVERITY CRITICAL
        --#TIMEINDEX 99
        --#STATE OPERATIONAL
        --#SIMPLE_SEVERITY CRITICAL
        --#HWSTATUS_CATEGORY DEVICEBAY
        --#ACTION "Check the blade server and enclosure SYSLOG."

        ::= 22054

cpqRackServerBladeGrpCapTimeout TRAP-TYPE
        ENTERPRISE compaq
        VARIABLES  { sysName,
                     cpqHoTrapFlags,
                     cpqRackName,
                     cpqRackUid,
                     cpqRackServerBladeEnclosureName,
                     cpqRackServerBladeName,
                     cpqRackServerBladePosition,
                     cpqRackServerBladeSparePartNumber,
                     cpqRackCommonEnclosureSerialNum,
                     cpqRackCommonEnclosureTrapSequenceNum }
        DESCRIPTION
           "The server blade is not responding to the group capper.

            The server blade is not responding to capping requests from the enclosure group capper

            User Action: Reset the iLO management processor."

        --#TYPE "Server blade not responding to group capping requests (22055)"
        --#SUMMARY "Server blade %s in position %s, in enclosure %s, in rack %s is not responding to requests from the enclosure group capper."
        --#ARGUMENTS {5, 6, 4, 2}
        --#SEVERITY CRITICAL
        --#TIMEINDEX 99
        --#STATE DEGRADED
        --#SIMPLE_SEVERITY CRITICAL
        --#HWSTATUS_CATEGORY DEVICEBAY
        --#ACTION "Reset the iLO management processor."

        ::= 22055

   cpqRackServerBladeUnexpectedShutdown TRAP-TYPE
        ENTERPRISE compaq
        VARIABLES  { sysName,
                     cpqHoTrapFlags,
                     cpqRackName,
                     cpqRackUid,
                     cpqRackServerBladeEnclosureName,
                     cpqRackServerBladeName,
                     cpqRackServerBladePosition,
                     cpqRackServerBladeSparePartNumber,
                     cpqRackCommonEnclosureSerialNum,
                     cpqRackServerBladeSerialNum,
                     cpqRackServerBladeUid,
                     cpqRackCommonEnclosureTrapSequenceNum }
        DESCRIPTION
           "Server blade shutdown unexpectadly.

            An unexpected shutdown event has occurred for this server blade.

            User Action: Check blade server and enclosure SYSLOG."

        --#TYPE "Server blade unexpected shutdown (22056)"
        --#SUMMARY "Server blade %s in position %s, in enclosure %s, in rack %s has unexpectedly shutdown."
        --#ARGUMENTS {5, 6, 4, 2}
        --#SEVERITY INFORMATIONAL
        --#TIMEINDEX 99
        --#STATE OPERATIONAL
        --#SIMPLE_SEVERITY OK
        --#HWSTATUS_CATEGORY DEVICEBAY
        --#ACTION "Check the blade server and enclosure SYSLOG."

        ::= 22056

   cpqRackServerBladeMangementControllerFirmwareUpdating TRAP-TYPE
        ENTERPRISE compaq
        VARIABLES  { sysName,
                     cpqHoTrapFlags,
                     cpqRackName,
                     cpqRackUid,
                     cpqRackServerBladeEnclosureName,
                     cpqRackServerBladeName,
                     cpqRackServerBladePosition,
                     cpqRackServerBladeSparePartNumber,
                     cpqRackCommonEnclosureSerialNum,
                     cpqRackServerBladeSerialNum,
                     cpqRackServerBladeUid,
                     cpqRackServerBladeManagementDeviceFirmwareFlashingStatus,
                     cpqRackCommonEnclosureTrapSequenceNum }
        DESCRIPTION
           "Server blade's management controller firmware updating.

            This server blade's management controller has started updating it's firmware.

            User Action: None."

        --#TYPE "Server blade management controller firmware update started (22057)"
        --#SUMMARY "Server blade %s in position %s, in enclosure %s, in rack %s has started updating it's management controller firmware."
        --#ARGUMENTS {5, 6, 4, 2}
        --#SEVERITY INFORMATIONAL
        --#TIMEINDEX 99
        --#STATE OPERATIONAL
        --#SIMPLE_SEVERITY OK
        --#HWSTATUS_CATEGORY DEVICEBAY
        --#LIFECYCLE

        ::= 22057

   cpqRackServerBladeMangementControllerFirmwareUpdateComplete TRAP-TYPE
        ENTERPRISE compaq
        VARIABLES  { sysName,
                     cpqHoTrapFlags,
                     cpqRackName,
                     cpqRackUid,
                     cpqRackServerBladeEnclosureName,
                     cpqRackServerBladeName,
                     cpqRackServerBladePosition,
                     cpqRackServerBladeSparePartNumber,
                     cpqRackCommonEnclosureSerialNum,
                     cpqRackServerBladeSerialNum,
                     cpqRackServerBladeUid,
                     cpqRackServerBladeManagementDeviceFirmwareFlashingStatus,
                     cpqRackCommonEnclosureTrapSequenceNum }
        DESCRIPTION
           "Server blade's management controller firmware update has completed.

            This server blade's management controller has finished updating it's firmware.

            User Action: None."

        --#TYPE "Server blade management controller firmware update completed (22058)"
        --#SUMMARY "Server blade %s in position %s, in enclosure %s, in rack %s has finished updating it's management controller firmware."
        --#ARGUMENTS {5, 6, 4, 2}
        --#SEVERITY INFORMATIONAL
        --#TIMEINDEX 99
        --#STATE OPERATIONAL
        --#SIMPLE_SEVERITY OK
        --#HWSTATUS_CATEGORY DEVICEBAY
        --#LIFECYCLE

        ::= 22058

   cpqRackServerBladeSystemBIOSFirmwareUpdating TRAP-TYPE
        ENTERPRISE compaq
        VARIABLES  { sysName,
                     cpqHoTrapFlags,
                     cpqRackName,
                     cpqRackUid,
                     cpqRackServerBladeEnclosureName,
                     cpqRackServerBladeName,
                     cpqRackServerBladePosition,
                     cpqRackServerBladeSparePartNumber,
                     cpqRackCommonEnclosureSerialNum,
                     cpqRackServerBladeSerialNum,
                     cpqRackServerBladeUid,
                     cpqRackServerBladeSystemBIOSFlashingStatus,
                     cpqRackCommonEnclosureTrapSequenceNum }
        DESCRIPTION
           "Server blade's system BIOS firmware updating.

            This server blade's system BIOS has started updating.

            User Action: None."

        --#TYPE "Server blade system BIOS firmware update started (22059)"
        --#SUMMARY "Server blade %s in position %s, in enclosure %s, in rack %s has started updating it's system BIOS firmware."
        --#ARGUMENTS {5, 6, 4, 2}
        --#SEVERITY INFORMATIONAL
        --#TIMEINDEX 99
        --#STATE OPERATIONAL
        --#SIMPLE_SEVERITY OK
        --#HWSTATUS_CATEGORY DEVICEBAY
        --#LIFECYCLE

        ::= 22059

   cpqRackServerBladeSystemBIOSFirmwareUpdateCompleted TRAP-TYPE
        ENTERPRISE compaq
        VARIABLES  { sysName,
                     cpqHoTrapFlags,
                     cpqRackName,
                     cpqRackUid,
                     cpqRackServerBladeEnclosureName,
                     cpqRackServerBladeName,
                     cpqRackServerBladePosition,
                     cpqRackServerBladeSparePartNumber,
                     cpqRackCommonEnclosureSerialNum,
                     cpqRackServerBladeSerialNum,
                     cpqRackServerBladeUid,
                     cpqRackServerBladeSystemBIOSFlashingStatus,
                     cpqRackCommonEnclosureTrapSequenceNum }
        DESCRIPTION
           "Server blade's system BIOS firmware update complete.

            This server blade's system BIOS has completed updating.

            User Action: None."

        --#TYPE "Server blade system BIOS firmware update completed (22060)"
        --#SUMMARY "Server blade %s in position %s, in enclosure %s, in rack %s has completed updating it's system BIOS firmware."
        --#ARGUMENTS {5, 6, 4, 2}
        --#SEVERITY INFORMATIONAL
        --#TIMEINDEX 99
        --#STATE OPERATIONAL
        --#SIMPLE_SEVERITY OK
        --#HWSTATUS_CATEGORY DEVICEBAY
        --#LIFECYCLE

        ::= 22060


   cpqRackServerBladeFrontIOBlankingActive TRAP-TYPE
        ENTERPRISE compaq
        VARIABLES  { sysName,
                     cpqHoTrapFlags,
                     cpqRackName,
                     cpqRackUid,
                     cpqRackServerBladeEnclosureName,
                     cpqRackServerBladeName,
                     cpqRackServerBladePosition,
                     cpqRackServerBladeSparePartNumber,
                     cpqRackCommonEnclosureSerialNum,
                     cpqRackServerBladeSerialNum,
                     cpqRackServerBladeUid,
                     cpqRackServerBladeFrontIOBlankingModeStatus,
                     cpqRackCommonEnclosureTrapSequenceNum }
        DESCRIPTION
           "Server blade has disabled front IO ports.

            Front IO blanking status has changed to active for this server blade.

            User Action: None."

        --#TYPE "Server blade front IO blanking active (22061)"
        --#SUMMARY "Server blade %s in position %s, in enclosure %s, in rack %s has disabled front IO."
        --#ARGUMENTS {5, 6, 4, 2}
        --#SEVERITY INFORMATIONAL
        --#TIMEINDEX 99
        --#STATE OPERATIONAL
        --#SIMPLE_SEVERITY OK
        --#HWSTATUS_CATEGORY DEVICEBAY
	    --#LIFECYCLE

        ::= 22061


   cpqRackServerBladeRemoteFrontIOBlankingInactive TRAP-TYPE
        ENTERPRISE compaq
        VARIABLES  { sysName,
                     cpqHoTrapFlags,
                     cpqRackName,
                     cpqRackUid,
                     cpqRackServerBladeEnclosureName,
                     cpqRackServerBladeName,
                     cpqRackServerBladePosition,
                     cpqRackServerBladeSparePartNumber,
                     cpqRackCommonEnclosureSerialNum,
                     cpqRackServerBladeSerialNum,
                     cpqRackServerBladeUid,
                     cpqRackServerBladeFrontIOBlankingModeStatus,
                     cpqRackCommonEnclosureTrapSequenceNum }
        DESCRIPTION
           "Server blade has front IO blanking mode now inactive.

            Front IO blanking status has changed to inactive for this server blade.

            User Action: None."

        --#TYPE "Server blade front IO blanking inactive (22062)"
        --#SUMMARY "Server blade %s in position %s, in enclosure %s, in rack %s has enabled front IO."
        --#ARGUMENTS {5, 6, 4, 2}
        --#SEVERITY INFORMATIONAL
        --#TIMEINDEX 99
        --#STATE OPERATIONAL
        --#SIMPLE_SEVERITY OK
        --#HWSTATUS_CATEGORY DEVICEBAY
	    --#LIFECYCLE

        ::= 22062

 cpqRackServerBladeDiagnosticAdaptorInserted TRAP-TYPE
        ENTERPRISE compaq
        VARIABLES  { sysName,
                     cpqHoTrapFlags,
                     cpqRackName,
                     cpqRackUid,
                     cpqRackServerBladeEnclosureName,
                     cpqRackServerBladeName,
                     cpqRackServerBladePosition,
                     cpqRackServerBladeSparePartNumber,
                     cpqRackCommonEnclosureSerialNum,
                     cpqRackServerBladeSerialNum,
                     cpqRackServerBladeUid,
                     cpqRackServerBladeDiagnosticAdaptorPresence,
                     cpqRackCommonEnclosureTrapSequenceNum }
        DESCRIPTION
           "Server blade diagnostic adaptor inserted.

            Blade diagnostic adaptor status has changed to inserted for this server blade.

            User Action: None."

        --#TYPE "Server blade diagnostic adaptor inserted (22063)"
        --#SUMMARY "Server blade %s in position %s, in enclosure %s, in rack %s diagnostic adaptor inserted."
        --#ARGUMENTS {5, 6, 4, 2}
        --#SEVERITY INFORMATIONAL
        --#TIMEINDEX 99
        --#STATE OPERATIONAL
        --#SIMPLE_SEVERITY OK
        --#HWSTATUS_CATEGORY DEVICEBAY
	    --#LIFECYCLE

        ::= 22063

 cpqRackServerBladeDiagnosticAdaptorRemoved TRAP-TYPE
        ENTERPRISE compaq
        VARIABLES  { sysName,
                     cpqHoTrapFlags,
                     cpqRackName,
                     cpqRackUid,
                     cpqRackServerBladeEnclosureName,
                     cpqRackServerBladeName,
                     cpqRackServerBladePosition,
                     cpqRackServerBladeSparePartNumber,
                     cpqRackCommonEnclosureSerialNum,
                     cpqRackServerBladeSerialNum,
                     cpqRackServerBladeUid,
                     cpqRackServerBladeDiagnosticAdaptorPresence,
                     cpqRackCommonEnclosureTrapSequenceNum }
        DESCRIPTION
           "Server blade diagnostic adaptor removed.

            Blade diagnostic adaptor status has changed to removed for this server blade.

            User Action: None."

        --#TYPE "Server blade diagnostic adaptor removed (22064)"
        --#SUMMARY "Server blade %s in position %s, in enclosure %s, in rack %s diagnostic adaptor removed."
        --#ARGUMENTS {5, 6, 4, 2}
        --#SEVERITY INFORMATIONAL
        --#TIMEINDEX 99
        --#STATE OPERATIONAL
        --#SIMPLE_SEVERITY OK
        --#HWSTATUS_CATEGORY DEVICEBAY
  	    --#LIFECYCLE

        ::= 22064

 cpqRackServerBladeEnteredPXEBootMode TRAP-TYPE
        ENTERPRISE compaq
        VARIABLES  { sysName,
                     cpqHoTrapFlags,
                     cpqRackName,
                     cpqRackUid,
                     cpqRackServerBladeEnclosureName,
                     cpqRackServerBladeName,
                     cpqRackServerBladePosition,
                     cpqRackServerBladeSparePartNumber,
                     cpqRackCommonEnclosureSerialNum,
                     cpqRackServerBladeSerialNum,
                     cpqRackServerBladeUid,
                     cpqRackServerBladePXEBootModeStatus,
                     cpqRackCommonEnclosureTrapSequenceNum }
        DESCRIPTION
           "Server blade has entered PXE Boot Mode.

            Server blade Pre-Boot-eXecution (PXE) Mode started.

            User Action: None."

        --#TYPE "Server blade has entered PXE Boot Mode (22065)"
        --#SUMMARY "Server blade %s in position %s, in enclosure %s, in rack %s has entered PXE Boot Mode."
        --#ARGUMENTS {5, 6, 4, 2}
        --#SEVERITY INFORMATIONAL
        --#TIMEINDEX 99
        --#STATE OPERATIONAL
        --#SIMPLE_SEVERITY OK
        --#HWSTATUS_CATEGORY DEVICEBAY
        --#LIFECYCLE

        ::= 22065

 cpqRackServerBladeExitedPXEBootMode TRAP-TYPE
        ENTERPRISE compaq
        VARIABLES  { sysName,
                     cpqHoTrapFlags,
                     cpqRackName,
                     cpqRackUid,
                     cpqRackServerBladeEnclosureName,
                     cpqRackServerBladeName,
                     cpqRackServerBladePosition,
                     cpqRackServerBladeSparePartNumber,
                     cpqRackCommonEnclosureSerialNum,
                     cpqRackServerBladeSerialNum,
                     cpqRackServerBladeUid,
                     cpqRackServerBladePXEBootModeStatus,
                     cpqRackCommonEnclosureTrapSequenceNum }
        DESCRIPTION
           "Server blade has exited PXE Boot Mode.

            Server blade Pre-Boot-eXecution (PXE) Mode exited.

            User Action: None."

        --#TYPE "Server blade has exited PXE Boot Mode (22066)"
        --#SUMMARY "Server blade %s in position %s, in enclosure %s, in rack %s has exited PXE Boot Mode."
        --#ARGUMENTS {5, 6, 4, 2}
        --#SEVERITY INFORMATIONAL
        --#TIMEINDEX 99
        --#STATE OPERATIONAL
        --#SIMPLE_SEVERITY OK
        --#HWSTATUS_CATEGORY DEVICEBAY
        --#LIFECYCLE

        ::= 22066


 cpqRackServerBladeWarmReset TRAP-TYPE
        ENTERPRISE compaq
        VARIABLES  { sysName,
                     cpqHoTrapFlags,
                     cpqRackName,
                     cpqRackUid,
                     cpqRackServerBladeEnclosureName,
                     cpqRackServerBladeName,
                     cpqRackServerBladePosition,
                     cpqRackServerBladeSparePartNumber,
                     cpqRackCommonEnclosureSerialNum,
                     cpqRackServerBladeSerialNum,
                     cpqRackServerBladeUid,
                     cpqRackServerBladePOSTStatus,
                     cpqRackCommonEnclosureTrapSequenceNum }
        DESCRIPTION
           "Server blade has been warm reset.

            Server blade has experienced a warm reset.

            User Action: None."

        --#TYPE "Server blade warm reset occurred (22067)"
        --#SUMMARY "Server blade %s in position %s, in enclosure %s, in rack %s has been warm reset."
        --#ARGUMENTS {5, 6, 4, 2}
        --#SEVERITY INFORMATIONAL
        --#TIMEINDEX 99
        --#STATE OPERATIONAL
        --#SIMPLE_SEVERITY OK
        --#HWSTATUS_CATEGORY DEVICEBAY
	    --#LIFECYCLE

        ::= 22067

 cpqRackServerBladePOSTCompleted TRAP-TYPE
        ENTERPRISE compaq
        VARIABLES  { sysName,
                     cpqHoTrapFlags,
                     cpqRackName,
                     cpqRackUid,
                     cpqRackServerBladeEnclosureName,
                     cpqRackServerBladeName,
                     cpqRackServerBladePosition,
                     cpqRackServerBladeSparePartNumber,
                     cpqRackCommonEnclosureSerialNum,
                     cpqRackServerBladeSerialNum,
                     cpqRackServerBladeUid,
                     cpqRackServerBladePOSTStatus,
                     cpqRackCommonEnclosureTrapSequenceNum }
        DESCRIPTION
           "Server blade system BIOS POST complete.

            Server blade has completed system BIOS Power-On-Self-Test (POST).

            User Action: None."

        --#TYPE "Server blade system BIOS POST completed (22068)"
        --#SUMMARY "Server blade %s in position %s, in enclosure %s, in rack %s system BIOS POST completed."
        --#ARGUMENTS {5, 6, 4, 2}
        --#SEVERITY INFORMATIONAL
        --#TIMEINDEX 99
        --#STATE OPERATIONAL
        --#SIMPLE_SEVERITY OK
        --#HWSTATUS_CATEGORY DEVICEBAY
        --#LIFECYCLE

        ::= 22068

         cpqRackServerBladePoweredOn TRAP-TYPE
        ENTERPRISE compaq
        VARIABLES  { sysName,
                     cpqHoTrapFlags,
                     cpqRackName,
                     cpqRackUid,
                     cpqRackServerBladeEnclosureName,
                     cpqRackServerBladeName,
                     cpqRackServerBladePosition,
                     cpqRackServerBladeSparePartNumber,
                     cpqRackCommonEnclosureSerialNum,
                     cpqRackServerBladeSerialNum,
                     cpqRackServerBladeUid,
                     cpqRackServerBladePowered,
                     cpqRackCommonEnclosureTrapSequenceNum }
        DESCRIPTION
           "Server blade has powered on.

            User Action: None."

        --#TYPE "Server blade has powered on (22069)"
        --#SUMMARY "Server blade %s in position %s, in enclosure %s, in rack %s has powered on."
        --#ARGUMENTS {5, 6, 4, 2}
        --#SEVERITY INFORMATIONAL
        --#TIMEINDEX 99
        --#STATE OPERATIONAL
        --#SIMPLE_SEVERITY OK
        --#HWSTATUS_CATEGORY DEVICEBAY
        --#LIFECYCLE

        ::= 22069

         cpqRackServerBladePoweredOff TRAP-TYPE
        ENTERPRISE compaq
        VARIABLES  { sysName,
                     cpqHoTrapFlags,
                     cpqRackName,
                     cpqRackUid,
                     cpqRackServerBladeEnclosureName,
                     cpqRackServerBladeName,
                     cpqRackServerBladePosition,
                     cpqRackServerBladeSparePartNumber,
                     cpqRackCommonEnclosureSerialNum,
                     cpqRackServerBladeSerialNum,
                     cpqRackServerBladeUid,
                     cpqRackServerBladePowered,
                     cpqRackCommonEnclosureTrapSequenceNum }
        DESCRIPTION
           "Server blade has powered off.

            User Action: None."

        --#TYPE "Server blade has powered off (22070)"
        --#SUMMARY "Server blade %s in position %s, in enclosure %s, in rack %s has powered off."
        --#ARGUMENTS {5, 6, 4, 2}
        --#SEVERITY INFORMATIONAL
        --#TIMEINDEX 99
        --#STATE OPERATIONAL
        --#SIMPLE_SEVERITY OK
        --#HWSTATUS_CATEGORY DEVICEBAY
        --#LIFECYCLE

        ::= 22070

    cpqRackInformationalEAETrap TRAP-TYPE
        ENTERPRISE compaq
        VARIABLES  { sysName,
                     cpqHoTrapFlags,
                     cpqRackName,
                     cpqRackUid,
                     cpqRackServerBladeEnclosureName,
                     cpqRackCommonEnclosureTrapSequenceNum,
                     cpqRackLastEAEEvent }

        DESCRIPTION
           "EAE Informational trap"

              --#TYPE "Generic EAE Informational trap"
              --#SUMMARY "%s"
              --#ARGUMENTS {6}
              --#SEVERITY INFORMATIONAL
              --#TIMEINDEX 99
              --#SIMPLE_SEVERITY OK
              --#HWSTATUS_CATEGORY NONE

        ::= 22071

    cpqRackMinorEAETrap TRAP-TYPE
        ENTERPRISE compaq
        VARIABLES  { sysName,
                     cpqHoTrapFlags,
                     cpqRackName,
                     cpqRackUid,
                     cpqRackServerBladeEnclosureName,
                     cpqRackCommonEnclosureTrapSequenceNum,
                     cpqRackLastEAEEvent }

        DESCRIPTION
           "EAE Minor trap"

              --#TYPE "Generic EAE Minor trap"
              --#SUMMARY "%s"
              --#ARGUMENTS {6}
              --#SEVERITY MINOR
              --#TIMEINDEX 99
              --#SIMPLE_SEVERITY MAJOR
              --#HWSTATUS_CATEGORY NONE
        ::= 22072

    cpqRackMajorEAETrap TRAP-TYPE
        ENTERPRISE compaq
        VARIABLES  { sysName,
                     cpqHoTrapFlags,
                     cpqRackName,
                     cpqRackUid,
                     cpqRackServerBladeEnclosureName,
                     cpqRackCommonEnclosureTrapSequenceNum,
                     cpqRackLastEAEEvent }

        DESCRIPTION
           "EAE Major trap"

              --#TYPE "Generic EAE Major trap"
              --#SUMMARY "%s"
              --#ARGUMENTS {6}
              --#SEVERITY MAJOR
              --#TIMEINDEX 99
              --#SIMPLE_SEVERITY MAJOR
              --#HWSTATUS_CATEGORY NONE
        ::= 22073

    cpqRackCriticalEAETrap TRAP-TYPE
        ENTERPRISE compaq
        VARIABLES  { sysName,
                     cpqHoTrapFlags,
                     cpqRackName,
                     cpqRackUid,
                     cpqRackServerBladeEnclosureName,
                     cpqRackCommonEnclosureTrapSequenceNum,
                     cpqRackLastEAEEvent }

        DESCRIPTION
           "EAE Critical trap"

              --#TYPE "Generic EAE Critical trap"
              --#SUMMARY "%s"
              --#ARGUMENTS {6}
              --#SEVERITY CRITICAL
              --#TIMEINDEX 99
              --#SIMPLE_SEVERITY CRITICAL
              --#HWSTATUS_CATEGORY NONE
        ::= 22074

  cpqRackPowerMinorEAETrap TRAP-TYPE
        ENTERPRISE compaq
        VARIABLES  { sysName,
                     cpqHoTrapFlags,
                     cpqRackName,
                     cpqRackUid,
                     cpqRackServerBladeEnclosureName,
                     cpqRackCommonEnclosureTrapSequenceNum,
                     cpqRackLastEAEEvent }

        DESCRIPTION
           "FlexFabric Cmdr Power Subsystem Minor trap.
            User Action: For FlexFabric Cmdr, please refer to product documentation for
            possible corrective actions."

              --#TYPE "Generic Power Subsystem EAE Minor trap"
              --#SUMMARY "%s"
              --#ARGUMENTS {6}
              --#SEVERITY MINOR
              --#TIMEINDEX 99
              --#SIMPLE_SEVERITY MAJOR
              --#HWSTATUS_CATEGORY NONE
        ::= 22075


   cpqRackPowerMajorEAETrap TRAP-TYPE
        ENTERPRISE compaq
        VARIABLES  { sysName,
                     cpqHoTrapFlags,
                     cpqRackName,
                     cpqRackUid,
                     cpqRackServerBladeEnclosureName,
                     cpqRackCommonEnclosureTrapSequenceNum,
                     cpqRackLastEAEEvent }

        DESCRIPTION
           "FlexFabric Cmdr Power Subsystem Major trap.
            User Action: For FlexFabric Cmdr, please refer to product documentation for
            possible corrective actions."

              --#TYPE "Generic Power Subsystem EAE Major trap"
              --#SUMMARY "%s"
              --#ARGUMENTS {6}
              --#SEVERITY MAJOR
              --#TIMEINDEX 99
              --#SIMPLE_SEVERITY MAJOR
              --#HWSTATUS_CATEGORY NONE
        ::= 22076

   cpqRackPowerCriticalEAETrap TRAP-TYPE
        ENTERPRISE compaq
        VARIABLES  { sysName,
                     cpqHoTrapFlags,
                     cpqRackName,
                     cpqRackUid,
                     cpqRackServerBladeEnclosureName,
                     cpqRackCommonEnclosureTrapSequenceNum,
                     cpqRackLastEAEEvent }

        DESCRIPTION
           "FlexFabric Cmdr Power Subsystem Critical trap.
            User Action: For FlexFabric Cmdr, please refer to product documentation for
            possible corrective actions."

              --#TYPE "Generic Power Subsystem EAE Critical trap"
              --#SUMMARY "%s"
              --#ARGUMENTS {6}
              --#SEVERITY CRITICAL
              --#TIMEINDEX 99
              --#SIMPLE_SEVERITY CRITICAL
              --#HWSTATUS_CATEGORY NONE
        ::= 22077

    cpqRackServerBladePartitionChange TRAP-TYPE
        ENTERPRISE compaq
        VARIABLES  { sysName,
                     cpqHoTrapFlags,
                     cpqRackName,
                     cpqRackUid,
                     cpqRackServerBladeEnclosureName,
                     cpqRackServerBladeName,
                     cpqRackServerBladePosition,
                     cpqRackServerBladeSparePartNumber,
                     cpqRackCommonEnclosureSerialNum,
                     cpqRackServerBladeSerialNum,
                     cpqRackServerBladeUid,
                     cpqRackCommonEnclosureTrapSequenceNum }
        DESCRIPTION
           "Server Blade Partition Changed trap.

            The server blade is part of a conjoined blade and its partition has changed.

            User Action: None."

        --#TYPE "Server blade partition changed (22078)"
        --#SUMMARY "Server blade %s in position %s, in enclosure %s, in rack %s partition has changed."
        --#ARGUMENTS {5, 6, 4, 2}
        --#SEVERITY INFORMATIONAL
        --#TIMEINDEX 99
        --#STATE OPERATIONAL
        --#SIMPLE_SEVERITY OK
        --#HWSTATUS_CATEGORY DEVICEBAY
        --#LIFECYCLE

        ::= 22078

    cpqRackInformationalWSMANTrap TRAP-TYPE
        ENTERPRISE compaq
        VARIABLES  { sysName,
                     cpqHoTrapFlags,
                     cpqRackName,
                     cpqRackUid,
                     cpqRackCommonEnclosureName,
                     cpqRackCommonEnclosureTrapSequenceNum,
                     cpqRackLastEAEEvent,
                     cpqRackEventIndicationIdentifier,
                     cpqRackEventIndicationTime,
                     cpqRackEventDescription,
                     cpqRackEventSummary,
                     cpqRackEventCategory,
                     cpqRackOtherEventCategory,
                     cpqRackEventSubCategory,
                     cpqRackOtherEventSubCategory,
                     cpqRackEventThreshold,
                     cpqRackEventTimeWin,
                     cpqRackEventActualThreshold,
                     cpqRackEventActualTimeWin,
                     cpqRackEventProviderVersion,
                     cpqHoOsType,
                     cpqHoVersion,
                     cpqRackNetworkAddresses,
                     cpqRackSerialNum,
                     cpqRackEventAlertingElementFormat,
                     cpqRackEventOtherAlertingElementFormat,
                     cpqRackEventImpactedDomain,
                     cpqRackEventComplexName,
                     cpqRackEventPartitionId,
                     cpqRackEventTriggeringLogID,
                     cpqRackEventTriggeringLogIDFormat,
                     cpqRackHWPartNumber,
                     cpqRackHWFirmwareVersion,
                     cpqRackHWManufacturer,
                     cpqRackHWSerialNumber,
                     cpqRackHWFRUDetails,
                     cpqRackHWDevicePermanentNameFormat,
                     cpqRackHWOtherPermanentNameFormat,
                     cpqRackEventAlertType,
                     cpqRackEventOtherAlertType,
                     cpqRackEventProbableCause,
                     cpqRackEventProbableCauseDescription,
                     cpqRackEventPerceivedSeverity,
                     cpqRackEventOtherSeverity,
                     cpqRackEventTrending,
                     cpqRackEventRecommendedActions,
                     cpqRackEventID,
                     cpqRackEventTime,
                     cpqRackEventSystemCreationClassName,
                     cpqRackEventSystemName,
                     cpqRackEventProviderName }

        DESCRIPTION
           "WSMAN Informational trap"

              --#TYPE "Generic WSMAN Informational trap"
              --#SUMMARY "%s"
              --#ARGUMENTS {6}
              --#SEVERITY INFORMATIONAL
              --#TIMEINDEX 99
              --#SIMPLE_SEVERITY OK
              --#HWSTATUS_CATEGORY NONE

        ::= 22079

    cpqRackMinorWSMANTrap TRAP-TYPE
        ENTERPRISE compaq
        VARIABLES  { sysName,
                     cpqHoTrapFlags,
                     cpqRackName,
                     cpqRackUid,
                     cpqRackCommonEnclosureName,
                     cpqRackCommonEnclosureTrapSequenceNum,
                     cpqRackLastEAEEvent,
                     cpqRackEventIndicationIdentifier,
                     cpqRackEventIndicationTime,
                     cpqRackEventDescription,
                     cpqRackEventSummary,
                     cpqRackEventCategory,
                     cpqRackOtherEventCategory,
                     cpqRackEventSubCategory,
                     cpqRackOtherEventSubCategory,
                     cpqRackEventThreshold,
                     cpqRackEventTimeWin,
                     cpqRackEventActualThreshold,
                     cpqRackEventActualTimeWin,
                     cpqRackEventProviderVersion,
                     cpqHoOsType,
                     cpqHoVersion,
                     cpqRackNetworkAddresses,
                     cpqRackSerialNum,
                     cpqRackEventAlertingElementFormat,
                     cpqRackEventOtherAlertingElementFormat,
                     cpqRackEventImpactedDomain,
                     cpqRackEventComplexName,
                     cpqRackEventPartitionId,
                     cpqRackEventTriggeringLogID,
                     cpqRackEventTriggeringLogIDFormat,
                     cpqRackHWPartNumber,
                     cpqRackHWFirmwareVersion,
                     cpqRackHWManufacturer,
                     cpqRackHWSerialNumber,
                     cpqRackHWFRUDetails,
                     cpqRackHWDevicePermanentNameFormat,
                     cpqRackHWOtherPermanentNameFormat,
                     cpqRackEventAlertType,
                     cpqRackEventOtherAlertType,
                     cpqRackEventProbableCause,
                     cpqRackEventProbableCauseDescription,
                     cpqRackEventPerceivedSeverity,
                     cpqRackEventOtherSeverity,
                     cpqRackEventTrending,
                     cpqRackEventRecommendedActions,
                     cpqRackEventID,
                     cpqRackEventTime,
                     cpqRackEventSystemCreationClassName,
                     cpqRackEventSystemName,
                     cpqRackEventProviderName }

        DESCRIPTION
           "WSMAN Minor trap"

              --#TYPE "Generic WSMAN Minor trap"
              --#SUMMARY "%s"
              --#ARGUMENTS {6}
              --#SEVERITY MINOR
              --#TIMEINDEX 99
              --#SIMPLE_SEVERITY MAJOR
              --#HWSTATUS_CATEGORY NONE
        ::= 22080

    cpqRackMajorWSMANTrap TRAP-TYPE
        ENTERPRISE compaq
        VARIABLES  { sysName,
                     cpqHoTrapFlags,
                     cpqRackName,
                     cpqRackUid,
                     cpqRackCommonEnclosureName,
                     cpqRackCommonEnclosureTrapSequenceNum,
                     cpqRackLastEAEEvent,
                     cpqRackEventIndicationIdentifier,
                     cpqRackEventIndicationTime,
                     cpqRackEventDescription,
                     cpqRackEventSummary,
                     cpqRackEventCategory,
                     cpqRackOtherEventCategory,
                     cpqRackEventSubCategory,
                     cpqRackOtherEventSubCategory,
                     cpqRackEventThreshold,
                     cpqRackEventTimeWin,
                     cpqRackEventActualThreshold,
                     cpqRackEventActualTimeWin,
                     cpqRackEventProviderVersion,
                     cpqHoOsType,
                     cpqHoVersion,
                     cpqRackNetworkAddresses,
                     cpqRackSerialNum,
                     cpqRackEventAlertingElementFormat,
                     cpqRackEventOtherAlertingElementFormat,
                     cpqRackEventImpactedDomain,
                     cpqRackEventComplexName,
                     cpqRackEventPartitionId,
                     cpqRackEventTriggeringLogID,
                     cpqRackEventTriggeringLogIDFormat,
                     cpqRackHWPartNumber,
                     cpqRackHWFirmwareVersion,
                     cpqRackHWManufacturer,
                     cpqRackHWSerialNumber,
                     cpqRackHWFRUDetails,
                     cpqRackHWDevicePermanentNameFormat,
                     cpqRackHWOtherPermanentNameFormat,
                     cpqRackEventAlertType,
                     cpqRackEventOtherAlertType,
                     cpqRackEventProbableCause,
                     cpqRackEventProbableCauseDescription,
                     cpqRackEventPerceivedSeverity,
                     cpqRackEventOtherSeverity,
                     cpqRackEventTrending,
                     cpqRackEventRecommendedActions,
                     cpqRackEventID,
                     cpqRackEventTime,
                     cpqRackEventSystemCreationClassName,
                     cpqRackEventSystemName,
                     cpqRackEventProviderName }

        DESCRIPTION
           "WSMAN Major trap"

              --#TYPE "Generic WSMAN Major trap"
              --#SUMMARY "%s"
              --#ARGUMENTS {6}
              --#SEVERITY MAJOR
              --#TIMEINDEX 99
              --#SIMPLE_SEVERITY MAJOR
              --#HWSTATUS_CATEGORY NONE
        ::= 22081

    cpqRackCriticalWSMANTrap TRAP-TYPE
        ENTERPRISE compaq
        VARIABLES  { sysName,
                     cpqHoTrapFlags,
                     cpqRackName,
                     cpqRackUid,
                     cpqRackCommonEnclosureName,
                     cpqRackCommonEnclosureTrapSequenceNum,
                     cpqRackLastEAEEvent,
                     cpqRackEventIndicationIdentifier,
                     cpqRackEventIndicationTime,
                     cpqRackEventDescription,
                     cpqRackEventSummary,
                     cpqRackEventCategory,
                     cpqRackOtherEventCategory,
                     cpqRackEventSubCategory,
                     cpqRackOtherEventSubCategory,
                     cpqRackEventThreshold,
                     cpqRackEventTimeWin,
                     cpqRackEventActualThreshold,
                     cpqRackEventActualTimeWin,
                     cpqRackEventProviderVersion,
                     cpqHoOsType,
                     cpqHoVersion,
                     cpqRackNetworkAddresses,
                     cpqRackSerialNum,
                     cpqRackEventAlertingElementFormat,
                     cpqRackEventOtherAlertingElementFormat,
                     cpqRackEventImpactedDomain,
                     cpqRackEventComplexName,
                     cpqRackEventPartitionId,
                     cpqRackEventTriggeringLogID,
                     cpqRackEventTriggeringLogIDFormat,
                     cpqRackHWPartNumber,
                     cpqRackHWFirmwareVersion,
                     cpqRackHWManufacturer,
                     cpqRackHWSerialNumber,
                     cpqRackHWFRUDetails,
                     cpqRackHWDevicePermanentNameFormat,
                     cpqRackHWOtherPermanentNameFormat,
                     cpqRackEventAlertType,
                     cpqRackEventOtherAlertType,
                     cpqRackEventProbableCause,
                     cpqRackEventProbableCauseDescription,
                     cpqRackEventPerceivedSeverity,
                     cpqRackEventOtherSeverity,
                     cpqRackEventTrending,
                     cpqRackEventRecommendedActions,
                     cpqRackEventID,
                     cpqRackEventTime,
                     cpqRackEventSystemCreationClassName,
                     cpqRackEventSystemName,
                     cpqRackEventProviderName }

        DESCRIPTION
           "WSMAN Critical trap"

              --#TYPE "Generic WSMAN Critical trap"
              --#SUMMARY "%s"
              --#ARGUMENTS {6}
              --#SEVERITY CRITICAL
              --#TIMEINDEX 99
              --#SIMPLE_SEVERITY CRITICAL
              --#HWSTATUS_CATEGORY NONE
        ::= 22082

    cpqRackEnclosureManagerLinkDown TRAP-TYPE
        ENTERPRISE compaq
        VARIABLES  { sysName,
                     cpqHoTrapFlags,
                     cpqRackName,
                     cpqRackUid,
                     cpqRackCommonEnclosureName,
                     cpqRackCommonEnclosureSerialNum,
                     cpqRackCommonEnclosureManagerLocation,
                     cpqRackCommonEnclosureManagerSparePartNumber,
                     cpqRackCommonEnclosureManagerSerialNum,
                     cpqRackCommonEnclosureTrapSequenceNum }
        DESCRIPTION
           "The Onboard Administrator Network Link is Down.

            The Onboard Administrator firmware has detected the loss of network link.
            User Action: Check network connection and configurations for the Onboard Administrator."

              --#TYPE "Onboard Administrator Link Down (22083)"
              --#SUMMARY "Onboard Administrator Link Down."
              --#ARGUMENTS { }
              --#SEVERITY CRITICAL
              --#TIMEINDEX 99
              --#STATE DEGRADED
              --#SIMPLE_SEVERITY CRITICAL
              --#HWSTATUS_CATEGORY NETWORK
              --#ACTION "Check network connection and configurations for the Onboard Administrator."

        ::= 22083

    cpqRackEnclosureManagerLinkUp TRAP-TYPE
        ENTERPRISE compaq
        VARIABLES  { sysName,
                     cpqHoTrapFlags,
                     cpqRackName,
                     cpqRackUid,
                     cpqRackCommonEnclosureName,
                     cpqRackCommonEnclosureSerialNum,
                     cpqRackCommonEnclosureManagerLocation,
                     cpqRackCommonEnclosureManagerSparePartNumber,
                     cpqRackCommonEnclosureManagerSerialNum,
                     cpqRackCommonEnclosureTrapSequenceNum }
        DESCRIPTION
           "The Onboard Administrator Network Link is Up.

            The Onboard Administrator firmware has detected the presence of network link.
            User Action: None."

              --#TYPE "Onboard Administrator Link Up (22084)"
              --#SUMMARY "Onboard Administrator Link Up."
              --#ARGUMENTS { }
              --#SEVERITY INFORMATIONAL
              --#TIMEINDEX 99
              --#STATE OPERATIONAL
              --#SIMPLE_SEVERITY OK
              --#HWSTATUS_CATEGORY NETWORKK

	::= 22084

    cpqRackErsCommFailure TRAP-TYPE
        ENTERPRISE compaq
        VARIABLES  { sysName,
                     cpqHoTrapFlags,
                     cpqRackName,
                     cpqRackUid,
                     cpqRackCommonEnclosureName,
                     cpqRackCommonEnclosureSerialNum,
                     cpqRackCommonEnclosureSparePartNumber,
                     cpqRackErsTransactionType,
                     cpqRackErsConnectionModel,
                     cpqRackErsFailureCode,
                     cpqRackErsRemoteHost }

        DESCRIPTION
           "The Onboard Administrator to Insight Remote Support or Insight Online communication failed.
            User Action: Please check the connectivity to Insight Remote Support or Insight Online."

              --#TYPE "Onboard Administrator to Insight Remote Support or Insight Online communication failure (22085)"
              --#SUMMARY "Onboard Administrator in enclosure %s, in rack %s to Insight Remote Support or Insight Online communication failed."
              --#ARGUMENTS {4, 2}
              --#SEVERITY MAJOR
              --#TIMEINDEX 99
              --#STATE DEGRADED
              --#SIMPLE_SEVERITY MAJOR
              --#HWSTATUS_CATEGORY REMOTESUPPORT
              --#ACTION "Please check the connectivity to Insight Remote Support or Insight Online."

        ::= 22085

    cpqRackPowerSubsystemOverloadConditionRepaired TRAP-TYPE
        ENTERPRISE compaq
        VARIABLES  { sysName,
                     cpqHoTrapFlags,
                     cpqRackName,
                     cpqRackUid,
                     cpqRackPowerEnclosureName,
                     cpqRackCommonEnclosureSparePartNumber,
                     cpqRackCommonEnclosureSerialNum,
                     cpqRackCommonEnclosureTrapSequenceNum }
        DESCRIPTION
           "The rack power subsystem overload condition repaired."

        --#TYPE "Rack power subsystem overload condition repaired (22086)"
        --#SUMMARY "The power subsystem overload condition in enclosure %s in rack %s is repaired."
        --#ARGUMENTS {4, 2}
        --#SEVERITY INFORMATIONAL
        --#TIMEINDEX 99
        --#STATE OPERATIONAL
        --#SIMPLE_SEVERITY OK
        --#HWSTATUS_CATEGORY POWER

        ::= 22086
    cpqRackPowerSubsystemRedundancyOk TRAP-TYPE
        ENTERPRISE compaq
        VARIABLES  { sysName,
                     cpqHoTrapFlags,
                     cpqRackName,
                     cpqRackUid,
                     cpqRackPowerEnclosureName,
                     cpqRackCommonEnclosureSerialNum,
                     cpqRackCommonEnclosureTrapSequenceNum }
        DESCRIPTION
           "The rack power subsystem is now redundant.

            This trap signifies that the enclosure power subsystem redundancy is now restored.
            User Action : None."

        --#TYPE "Rack power subsystem  of enclosure is now redundant (22087)"
        --#SUMMARY "The power subsystem of enclosure %s in rack %s is now redundant."
        --#ARGUMENTS {4, 2}
        --#SEVERITY INFORMATIONAL
        --#TIMEINDEX 99
        --#STATE OPERATIONAL
        --#SIMPLE_SEVERITY OK
        --#HWSTATUS_CATEGORY POWER
        --#CLEAR_PRIOR_EVENTS true

        ::= 22087

    cpqRackNetConnectorTempDegraded TRAP-TYPE
        ENTERPRISE compaq
        VARIABLES  { sysName,
                     cpqHoTrapFlags,
                     cpqRackName,
                     cpqRackUid,
                     cpqRackNetConnectorEnclosureName,
                     cpqRackNetConnectorName,
                     cpqRackNetConnectorLocation,
                     cpqRackNetConnectorSparePartNumber,
                     cpqRackCommonEnclosureSerialNum,
                     cpqRackCommonEnclosureTrapSequenceNum }
        DESCRIPTION
           "The Interconnect temperature status has been set to degraded.

            This trap signifies that an interconnect temperature sensor has
            been tripped indicating a possible overheat condition.

            User Action: Refer to the OA and the status diagnostics reported for the interconnect."

        --#TYPE "Interconnect temperature degraded (22088)"
        --#SUMMARY "Interconnect temperature  %s degraded in position %s, in enclosure %s, in rack %s."
        --#ARGUMENTS {5, 6, 4, 2}
        --#SEVERITY MAJOR
        --#TIMEINDEX 99
        --#STATE DEGRADED
        --#SIMPLE_SEVERITY MAJOR
        --#HWSTATUS_CATEGORY INTERCONNECTBAY
        --#ACTION "Refer to the OA and the status diagnostics reported for the interconnect."

        ::= 22088

    cpqRackNetConnectorTempOk TRAP-TYPE
        ENTERPRISE compaq
        VARIABLES  { sysName,
                     cpqHoTrapFlags,
                     cpqRackName,
                     cpqRackUid,
                     cpqRackNetConnectorEnclosureName,
                     cpqRackNetConnectorName,
                     cpqRackNetConnectorLocation,
                     cpqRackNetConnectorSparePartNumber,
                     cpqRackCommonEnclosureSerialNum,
                     cpqRackCommonEnclosureTrapSequenceNum }
        DESCRIPTION
           "The  interconnect temperature status has been set to ok.

            This trap signifies that an interconnect temperature sensor has
            returned to normal.

            User Action: None."

        --#TYPE "Interconnect temperature ok (22089)"
        --#SUMMARY "Interconnect temperature %s ok in position %s, in enclosure %s, in rack %s."
        --#ARGUMENTS {5, 6, 4, 2}
        --#SEVERITY INFORMATIONAL
        --#TIMEINDEX 99
        --#STATE OPERATIONAL
        --#SIMPLE_SEVERITY OK
        --#HWSTATUS_CATEGORY INTERCONNECTBAY

        ::= 22089

    cpqRackEnvironmentalLeakDetected TRAP-TYPE
        ENTERPRISE compaq
        VARIABLES { sysName,
                cpqHoTrapFlags,
                cpqRackName,
                cpqRackUid,
                cpqRackThermalControllerLeakDetect1,
                cpqRackThermalControllerLeakDetect2,
                cpqRackThermalControllerLeakDetect3,
                cpqRackThermalControllerLeakDetectFacility,
                cpqRackCommonEnclosureTrapSequenceNum }
        DESCRIPTION
           "A leak was detected by one or more leak detect sensors in the rack"

        --#TYPE "Leak detected by one or more leak sensors in the rack (22090)"
        --#SUMMARY "A leak was detected in the rack"
        --#ARGUMENTS {4, 2}
        --#SEVERITY WARNING
        --#TIMEINDEX 99
        --#STATE OPERATIONAL
        --#SIMPLE_SEVERITY OK
        --#HWSTATUS_CATEGORY ENVIRONMENTAL

        ::= 22090

    cpqRackEnvironmentalDoorState TRAP-TYPE
        ENTERPRISE compaq
        VARIABLES { sysName,
                cpqHoTrapFlags,
                cpqRackName,
                cpqRackUid,
                cpqRackThermalControllerDoorSensorFront,
                cpqRackThermalControllerDoorSensorRear,
                cpqRackThermalControllerDoorControlFront,
                cpqRackThermalControllerDoorControlRear1,
                cpqRackThermalControllerDoorControlRear2,
                cpqRackCommonEnclosureTrapSequenceNum }
        DESCRIPTION
           "A door has been opened or closed in the rack"

        --#TYPE "Door has been opened or closed (22091)"
        --#SUMMARY "A front or rear door on the rack has been opened or closed"
        --#ARGUMENTS {4, 2}
        --#SEVERITY INFORMATIONAL
        --#TIMEINDEX 99
        --#STATE OPERATIONAL
        --#SIMPLE_SEVERITY OK
        --#HWSTATUS_CATEGORY ENVIRONMENTAL

        ::= 22091

    cpqRackEnvironmentalAirTempSensor TRAP-TYPE
        ENTERPRISE compaq
        VARIABLES { sysName,
                cpqHoTrapFlags,
                cpqRackName,
                cpqRackUid,
                cpqRackThermalControllerAirTempSensorFront1,
                cpqRackThermalControllerAirTempSensorFront2,
                cpqRackThermalControllerAirTempSensorFront3,
                cpqRackThermalControllerAirTempSensorFront4,
                cpqRackThermalControllerAirTempSensorRear1,
                cpqRackThermalControllerAirTempSensorRear2,
                cpqRackThermalControllerAirTempSensorRear3,
                cpqRackThermalControllerAirTempSensorRear4,
                cpqRackCommonEnclosureTrapSequenceNum,
				cpqRackEnvironmentalTrapDescription }
        DESCRIPTION
           "Air temperature sensor warning condition"

        --#TYPE "An air temperature sensor has reached a warning condition (22092)"
        --#SUMMARY "An air temperature threshold as reached a warning state"
        --#ARGUMENTS {4, 2}
        --#SEVERITY WARNING
        --#TIMEINDEX 99
        --#STATE OPERATIONAL
        --#SIMPLE_SEVERITY OK
        --#HWSTATUS_CATEGORY ENVIRONMENTAL

        ::= 22092

    cpqRackEnvironmentalControlValveStatus TRAP-TYPE
        ENTERPRISE compaq
        VARIABLES { sysName,
                cpqHoTrapFlags,
                cpqRackName,
                cpqRackUid,
                cpqRackThermalControllerControlValveSupply,
                cpqRackThermalControllerControlValveReturn,
                cpqRackCommonEnclosureTrapSequenceNum,
				cpqRackEnvironmentalTrapDescription }
        DESCRIPTION
           "Water control valve status"

        --#TYPE "Water control valve status (22093)"
        --#SUMMARY "Water control valve state"
        --#ARGUMENTS {4, 2}
        --#SEVERITY INFORMATIONAL
        --#TIMEINDEX 99
        --#STATE OPERATIONAL
        --#SIMPLE_SEVERITY OK
        --#HWSTATUS_CATEGORY ENVIRONMENTAL

        ::= 22093

    cpqRackEnvironmentalWaterTempThresholdExceeded TRAP-TYPE
        ENTERPRISE compaq
        VARIABLES { sysName,
                cpqHoTrapFlags,
                cpqRackName,
                cpqRackUid,
                cpqRackThermalControllerWaterTempSupply,
                cpqRackThermalControllerWaterTempReturn,
                cpqRackCommonEnclosureTrapSequenceNum,
				cpqRackEnvironmentalTrapDescription }
        DESCRIPTION
           "Water Temperature Threshold exceeded"

        --#TYPE "Water Temperature exceeded a threshold (22094)"
        --#SUMMARY "Water temperature threshold exceeded"
        --#ARGUMENTS {4, 2}
        --#SEVERITY WARNING
        --#TIMEINDEX 99
        --#STATE OPERATIONAL
        --#SIMPLE_SEVERITY OK
        --#HWSTATUS_CATEGORY ENVIRONMENTAL

        ::= 22094

    cpqRackEnvironmentalFlowSensorStatus TRAP-TYPE
        ENTERPRISE compaq
        VARIABLES { sysName,
                cpqHoTrapFlags,
                cpqRackName,
                cpqRackUid,
                cpqRackThermalControllerITFlowSensor,
                cpqRackThermalControllerCDUFlowSensor,
                cpqRackCommonEnclosureTrapSequenceNum,
				cpqRackEnvironmentalTrapDescription }
        DESCRIPTION
           "Flow sensor status"

        --#TYPE "Flow sensor status (22095)"
        --#SUMMARY "Flow sensor status"
        --#ARGUMENTS {4, 2}
        --#SEVERITY INFORMATIONAL
        --#TIMEINDEX 99
        --#STATE OPERATIONAL
        --#SIMPLE_SEVERITY OK
        --#HWSTATUS_CATEGORY ENVIRONMENTAL

        ::= 22095

    cpqRackEnvironmentalWaterPressureThresholdExceeded TRAP-TYPE
        ENTERPRISE compaq
        VARIABLES { sysName,
                cpqHoTrapFlags,
                cpqRackName,
                cpqRackUid,
                cpqRackThermalControllerWaterPressureSupply,
                cpqRackThermalControllerWaterPressureReturn,
                cpqRackCommonEnclosureTrapSequenceNum,
				cpqRackEnvironmentalTrapDescription }
        DESCRIPTION
           "Water pressure threshold exceeded"

        --#TYPE "Water pressure threshold exceeded (22096)"
        --#SUMMARY "Water pressure threshold exceeded"
        --#ARGUMENTS {4, 2}
        --#SEVERITY WARNING
        --#TIMEINDEX 99
        --#STATE OPERATIONAL
        --#SIMPLE_SEVERITY OK
        --#HWSTATUS_CATEGORY ENVIRONMENTAL

        ::= 22096

    cpqRackEnvironmentalAutomaticRapidPowerOff TRAP-TYPE
        ENTERPRISE compaq
        VARIABLES { sysName,
                cpqHoTrapFlags,
                cpqRackName,
                cpqRackUid,
                cpqRackCommonEnclosureTrapSequenceNum }
        DESCRIPTION
           "An Automatic Rapid Power Off (ARPO) event occured"

        --#TYPE "Automatic Rapid Power Off (22097)"
        --#SUMMARY "ARPO event"
        --#ARGUMENTS {4, 2}
        --#SEVERITY CRITICAL
        --#TIMEINDEX 99
        --#STATE OPERATIONAL
        --#SIMPLE_SEVERITY OK
        --#HWSTATUS_CATEGORY ENVIRONMENTAL

        ::= 22097

    cpqRackEnvironmentalRopeLeakDetectorEvent TRAP-TYPE
        ENTERPRISE compaq
        VARIABLES { sysName,
                cpqHoTrapFlags,
                cpqRackName,
                cpqRackUid,
                cpqRackThermalControllerChassisRopeSensor1,
                cpqRackThermalControllerChassisRopeSensor2,
                cpqRackThermalControllerChassisRopeSensor3,
                cpqRackThermalControllerChassisRopeSensor4,
                cpqRackCommonEnclosureTrapSequenceNum }
        DESCRIPTION
           "Rope leak detector event"

        --#TYPE "Rope leak detector event occured (22098)"
        --#SUMMARY "Rope leak detector event"
        --#ARGUMENTS {4, 2}
        --#SEVERITY CRITICAL
        --#TIMEINDEX 99
        --#STATE OPERATIONAL
        --#SIMPLE_SEVERITY OK
        --#HWSTATUS_CATEGORY ENVIRONMENTAL

        ::= 22098

    cpqRackEnvironmentalTemperatureThresholdExceeded TRAP-TYPE
        ENTERPRISE compaq
        VARIABLES { sysName,
                cpqHoTrapFlags,
                cpqRackName,
                cpqRackUid,
                cpqRackThermalControllerOnBoardTemp,
                cpqRackCommonEnclosureTrapSequenceNum,
				cpqRackEnvironmentalTrapDescription }
        DESCRIPTION
           "Environmental Controller on board temperature sensor exceeded threshold"

        --#TYPE "Temp sensor exceeded threshold (22099)"
        --#SUMMARY "Temp sensor exceeded threshold"
        --#ARGUMENTS {4, 2}
        --#SEVERITY WARNING
        --#TIMEINDEX 99
        --#STATE OPERATIONAL
        --#SIMPLE_SEVERITY OK
        --#HWSTATUS_CATEGORY ENVIRONMENTAL

        ::= 22099

    cpqRackEnvironmentalHumidityThresholdExceeded TRAP-TYPE
        ENTERPRISE compaq
        VARIABLES { sysName,
                cpqHoTrapFlags,
                cpqRackName,
                cpqRackUid,
                cpqRackThermalControllerOnBoardHumidity,
                cpqRackCommonEnclosureTrapSequenceNum,
				cpqRackEnvironmentalTrapDescription }
        DESCRIPTION
           "Environmental Controller on board temperature sensor exceeded threshold"

        --#TYPE "Humidity sensor exceeded threshold (22100)"
        --#SUMMARY "Humidity sensor exceeded threshold"
        --#ARGUMENTS {4, 2}
        --#SEVERITY WARNING
        --#TIMEINDEX 99
        --#STATE OPERATIONAL
        --#SIMPLE_SEVERITY OK
        --#HWSTATUS_CATEGORY ENVIRONMENTAL

        ::= 22100

    cpqRackEnvironmentalControllerOnBoardBattery TRAP-TYPE
        ENTERPRISE compaq
        VARIABLES { sysName,
                cpqHoTrapFlags,
                cpqRackName,
                cpqRackUid,
                cpqRackThermalControllerBattery,
                cpqRackCommonEnclosureTrapSequenceNum,
				cpqRackEnvironmentalTrapDescription }
        DESCRIPTION
           "Environmental controller on board Battery is low"

        --#TYPE "Environmental controller on board Battery is low (22101)"
        --#SUMMARY "Environmental controller on board battery is low"
        --#ARGUMENTS {4, 2}
        --#SEVERITY WARNING
        --#TIMEINDEX 99
        --#STATE OPERATIONAL
        --#SIMPLE_SEVERITY OK
        --#HWSTATUS_CATEGORY ENVIRONMENTAL

        ::= 22101

    cpqRackEnvironmentalControllerAPMCommunicationFailure TRAP-TYPE
        ENTERPRISE compaq
        VARIABLES { sysName,
                cpqHoTrapFlags,
                cpqRackName,
                cpqRackUid,
                cpqRackThermalControllerAPMCommunications,
                cpqRackCommonEnclosureTrapSequenceNum }
        DESCRIPTION
           "Communcations between Apollo Platform Manager (APM) and the environmental controller failed"

        --#TYPE "Communcations between Apollo Platform Manager (APM) and the environmental controller failed (22102)"
        --#SUMMARY "Communcations between Apollo Platform Manager (APM) and the environmental controller failed"
        --#ARGUMENTS {4, 2}
        --#SEVERITY CRITICAL
        --#TIMEINDEX 99
        --#STATE OPERATIONAL
        --#SIMPLE_SEVERITY OK
        --#HWSTATUS_CATEGORY ENVIRONMENTAL

        ::= 22102

    cpqRackEnvironmentalLeakDetectedCritical TRAP-TYPE
        ENTERPRISE compaq
        VARIABLES { sysName,
                cpqHoTrapFlags,
                cpqRackName,
                cpqRackUid,
                cpqRackThermalControllerLeakDetect1,
                cpqRackThermalControllerLeakDetect2,
                cpqRackThermalControllerLeakDetect3,
                cpqRackThermalControllerLeakDetectFacility,
                cpqRackCommonEnclosureTrapSequenceNum }
        DESCRIPTION
           "A leak was detected by one or more leak detect sensors in the rack"

        --#TYPE "Leak detected by one or more leak sensors in the rack (22103)"
        --#SUMMARY "A leak was detected in the rack"
        --#ARGUMENTS {4, 2}
		--#SEVERITY CRITICAL
        --#TIMEINDEX 99
        --#STATE OPERATIONAL
        --#SIMPLE_SEVERITY OK
        --#HWSTATUS_CATEGORY ENVIRONMENTAL

        ::= 22103

	cpqRackPowerSubsystemReductionModeActivate TRAP-TYPE
        ENTERPRISE compaq
        VARIABLES  { sysName,
                     cpqHoTrapFlags,
                     cpqRackName,
                     cpqRackUid,
                     cpqRackPowerEnclosureName,
                     cpqRackCommonEnclosureSerialNum,
                     cpqRackCommonEnclosureTrapSequenceNum }
        DESCRIPTION
           "All rack power supplies in a bank detected input voltage problem and power reduction mode activated in the enclosure.

            User Action : None."

        --#TYPE "Rack power subsystem server power reduction mode activated (22104)"
        --#SUMMARY "The power subsystem server power reduction mode (E-Break)activated in enclosure %s in rack %s."
        --#ARGUMENTS {4, 2}
        --#SEVERITY MAJOR
        --#TIMEINDEX 99
        --#STATE DEGRADED
        --#SIMPLE_SEVERITY MAJOR
        --#HWSTATUS_CATEGORY POWER
        --#ACTION "Check the power input for the power supply or replace any failed power supplies as soon as possible."

        ::= 22104

    cpqRackPowerSubsystemReductionModeDeactivate TRAP-TYPE
        ENTERPRISE compaq
        VARIABLES  { sysName,
                     cpqHoTrapFlags,
                     cpqRackName,
                     cpqRackUid,
                     cpqRackPowerEnclosureName,
                     cpqRackCommonEnclosureSerialNum,
                     cpqRackCommonEnclosureTrapSequenceNum }
        DESCRIPTION
           "The power reduction mode deactivated in the enclosure.

            User Action : None."

        --#TYPE "Rack power subsystem server power reduction mode deactivated (22105)"
        --#SUMMARY "The power subsystem server power reduction mode (E-Break)activated in enclosure %s in rack %s."
        --#ARGUMENTS {4, 2}
        --#SEVERITY INFORMATIONAL
        --#TIMEINDEX 99
        --#STATE OPERATIONAL
        --#SIMPLE_SEVERITY OK
        --#HWSTATUS_CATEGORY POWER

        ::= 22105
END
