-- ****************************************************************************
--
--                                  SAS Switch
--           Management Information Base for SNMP Network Management
--
--
--      Copyright 1992,2009 Hewlett-Packard Development Company, L.P.
--      Hewlett-Packard Company shall not be liable for technical or
--      editorial errors or omissions contained herein. The information in
--      this document is provided "as is" without warranty of any kind and
--      is subject to change without notice. The warranties for HP products
--      are set forth in the express limited warranty statements
--      accompanying such products. Nothing herein should be construed as
--      constituting an additional warranty.
--
--      Confidential computer software. Valid license from HP required for
--      possession, use or copying. Consistent with FAR 12.211 and 12.212,
--      Commercial Computer Software, Computer Software Documentation, and
--      Technical Data for Commercial Items are licensed to the U.S.
--      Government under vendor's standard commercial license.
--
--      Refer to the READMIB.RDM file for more information about the
--      organization of the information in the Compaq Enterprise.
--
--      The Compaq Enterprise number is 232.
--      The ASN.1 prefix to, and including the Compaq Enterprise is:
--           1.3.6.1.4.1.232
--
-- ****************************************************************************

CPQSASSWITCH-MIB DEFINITIONS ::= BEGIN

    IMPORTS
        compaq                      FROM CPQHOST-MIB
        enterprises                 FROM RFC1155-SMI
        Counter                     FROM RFC1155-SMI
        Gauge                       FROM RFC1155-SMI
        DisplayString               FROM RFC1213-MIB
        OBJECT-TYPE                 FROM RFC-1212
        TRAP-TYPE                   FROM RFC-1215
        sysName                     FROM RFC1213-MIB
        sysLocation                 FROM RFC1213-MIB
        cpqHoTrapFlags              FROM CPQHOST-MIB
        cpqSiProductName            FROM CPQSINFO-MIB
        cpqSiSysProductId           FROM CPQSINFO-MIB
        cpqSiSysSerialNum           FROM CPQSINFO-MIB
        cpqDaPhyDrvStatus           FROM CPQIDA-MIB
        cpqDaPhyDrvCntlrIndex       FROM CPQIDA-MIB
        cpqDaPhyDrvIndex            FROM CPQIDA-MIB
        cpqDaPhyDrvLocationString   FROM CPQIDA-MIB
        cpqDaPhyDrvType             FROM CPQIDA-MIB
        cpqDaPhyDrvModel            FROM CPQIDA-MIB
        cpqDaPhyDrvFWRev            FROM CPQIDA-MIB
        cpqDaPhyDrvSerialNum        FROM CPQIDA-MIB
        cpqDaPhyDrvBoxOnConnector   FROM CPQIDA-MIB
        cpqSsBoxCntlrHwLocation     FROM CPQSTSYS-MIB
        cpqSsBoxCntlrIndex          FROM CPQSTSYS-MIB
        cpqSsBoxBusIndex            FROM CPQSTSYS-MIB
        cpqSsBoxVendor              FROM CPQSTSYS-MIB
        cpqSsBoxModel               FROM CPQSTSYS-MIB
        cpqSsBoxSerialNumber        FROM CPQSTSYS-MIB
        cpqSsBoxCondition           FROM CPQSTSYS-MIB
        cpqSsBoxLocationString      FROM CPQSTSYS-MIB;




--    compaq               OBJECT IDENTIFIER ::= { enterprises 232 }

    cpqSasSwitch           OBJECT IDENTIFIER ::= { compaq 25 }
    cpqSasSwitchMibRev     OBJECT IDENTIFIER ::= { cpqSasSwitch 1 }
    cpqSasSwitchComponent  OBJECT IDENTIFIER ::= { cpqSasSwitch 2 }

    cpqSasSwitchInterface  OBJECT IDENTIFIER ::= { cpqSasSwitchComponent 1 }
    cpqSasSwitchHw         OBJECT IDENTIFIER ::= { cpqSasSwitchComponent 2 }

    cpqSasSwitchOsCommon   OBJECT IDENTIFIER ::= { cpqSasSwitchInterface 4 }

    cpqSasSwitchHwType     OBJECT IDENTIFIER ::= { cpqSasSwitchHw 1 }


-- ****************************************************************************
--   SAS Switch MIB Revision
--  =================================
--
-- The compaq enterprise               (1.3.6.1.4.1.232)
--      cpqSasSwitch Group             (1.3.6.1.4.1.232.25)
--       cpqSasSwitchMibRev Group      (1.3.6.1.4.1.232.25.1)
--
--      An SNMP agent conforming to this document will return a
--      cpqSasSwitchMibRevMajor of one (1) and a cpqSasSwitchMibRevMinor of
--      two (2).
--
--      Implementation of the cpqSasSwitchMibRev group is mandatory for
--      all agents supporting the SAS Switch MIB.
--
--
-- ****************************************************************************

    cpqSasSwitchMibRevMajor OBJECT-TYPE
        SYNTAX  INTEGER (1..65535)
        ACCESS  read-only
        STATUS  mandatory
        DESCRIPTION
            "The Major Revision level.
             A change in the major revision level represents a major change
             in the architecture of the MIB.  A change in the major revision
             level may indicate a significant change in the information
             supported and/or the meaning of the supported information,
             correct interpretation of data may require a MIB document with
             the same major revision level."
        ::= { cpqSasSwitchMibRev 1 }

    cpqSasSwitchMibRevMinor OBJECT-TYPE
        SYNTAX  INTEGER (0..65535)
        ACCESS  read-only
        STATUS  mandatory
        DESCRIPTION
            "The Minor Revision level.
             A change in the minor revision level may represent some minor
             additional support, no changes to any pre-existing information
             has occurred."
        ::= { cpqSasSwitchMibRev 2 }

    cpqSasSwitchMibCondition OBJECT-TYPE
        SYNTAX  INTEGER {
            other(1),
            ok(2),
            degraded(3),
            failed(4)
            }
        ACCESS  read-only
        STATUS  mandatory
        DESCRIPTION
            "The overall condition (status) of the system represented by
            this MIB."
        ::= { cpqSasSwitchMibRev 3 }





    cpqSasSwitchTestTrap  TRAP-TYPE
	ENTERPRISE cpqSasSwitch
	VARIABLES  { cpqSiProductName, cpqSiSysProductId, cpqSiSysSerialNum, sysName, sysLocation  }

	DESCRIPTION
	"SAS Switch Test Trap"

      --#TYPE "Test Trap"
      --#SUMMARY "Test trap recieved from %s, S/N: %s"
      --#ARGUMENTS {0,2}
      --#SEVERITY INFORMATIONAL
      --#TIMEINDEX 99

	::= 1


    cpqSasSwitchHwStatusChangeTrap  TRAP-TYPE
	ENTERPRISE cpqSasSwitch
	VARIABLES  { cpqSiProductName, cpqSiSysProductId, cpqSiSysSerialNum, sysName, sysLocation, cpqSasSwitchHwStatus }

	DESCRIPTION
	"SAS Switch Status change

   The switch has detected a change in the status.
   The new status is defined in cpqSasSwitchHwStatus.
   "

      --#TYPE "SAS Switch Status change"
      --#SUMMARY "Switch Status has changed. Status is now %s"
      --#ARGUMENTS {5}
      --#SEVERITY INFORMATIONAL
      --#TIMEINDEX 99

	::= 101

    cpqSasSwitchHwRedundancyStateChangeTrap  TRAP-TYPE
	ENTERPRISE cpqSasSwitch
	VARIABLES  { cpqSiProductName, cpqSiSysProductId, cpqSiSysSerialNum, sysName, sysLocation, cpqSasSwitchHwRedundancyState }

	DESCRIPTION
	"SAS Switch Redundancy State change.

   The switch has detected a change in the redundancy operation
   mode. The new redundancy state is defined in cpqSasSwitchHwRedundancyState."

      --#TYPE "SAS Switch Redundancy State change"
      --#SUMMARY "Switch Redundancy State has changed. New state is now %s"
      --#ARGUMENTS {5}
      --#SEVERITY INFORMATIONAL
      --#TIMEINDEX 99

	::= 201


    cpqSasSwitchPhysicalDriveAddedTrap  TRAP-TYPE
	ENTERPRISE cpqSasSwitch
   VARIABLES  { sysName, cpqHoTrapFlags, sysLocation,
                   cpqDaPhyDrvCntlrIndex, cpqDaPhyDrvIndex,
                   cpqDaPhyDrvLocationString, cpqDaPhyDrvType,
                   cpqDaPhyDrvModel, cpqDaPhyDrvFWRev, cpqDaPhyDrvSerialNum,
                   cpqDaPhyDrvBoxOnConnector }
	DESCRIPTION
	"SAS switch detected physical drive added to attached enclosure.

   The switch has detected a physical drive has been added to attached storage
   enclosure."

      --#TYPE "Physical Drive Added"
      --#SUMMARY "Physical Drive has been added at location: %s"
      --#ARGUMENTS {5}
      --#SEVERITY INFORMATIONAL
      --#TIMEINDEX 99

	::= 301

    cpqSasSwitchPhysicalDriveRemovedTrap  TRAP-TYPE
	ENTERPRISE cpqSasSwitch
   VARIABLES  { sysName, cpqHoTrapFlags, sysLocation,
                   cpqDaPhyDrvCntlrIndex, cpqDaPhyDrvIndex,
                   cpqDaPhyDrvLocationString, cpqDaPhyDrvType,
                   cpqDaPhyDrvModel, cpqDaPhyDrvFWRev, cpqDaPhyDrvSerialNum,
                   cpqDaPhyDrvBoxOnConnector }
	DESCRIPTION
	"SAS switch detected physical drive removed from attached enclosure.

   The switch has detected a physical drive has been removed from attached storage
   enclosure."

      --#TYPE "Physical Drive Removed"
      --#SUMMARY "Physical Drive has been removed at location: %s"
      --#ARGUMENTS {5}
      --#SEVERITY INFORMATIONAL
      --#TIMEINDEX 99

	::= 302


    cpqSasSwitchStorageEnclosureAddedTrap  TRAP-TYPE
	ENTERPRISE cpqSasSwitch
   VARIABLES  { sysName, cpqHoTrapFlags, cpqSsBoxCntlrHwLocation,
                     cpqSsBoxCntlrIndex, cpqSsBoxBusIndex, cpqSsBoxVendor,
                     cpqSsBoxModel, cpqSsBoxSerialNumber,
                     cpqSsBoxCondition, cpqSsBoxLocationString }
	DESCRIPTION
	"SAS switch detected storage enclosure added.

   The switch has detected a storage enclosure has been added."

      --#TYPE "Storage Enclosure Added"
      --#SUMMARY "Storage Enclosure has been added at location: %s"
      --#ARGUMENTS {9}
      --#SEVERITY INFORMATIONAL
      --#TIMEINDEX 99


	::= 401

    cpqSasSwitchStorageEnclosureRemovedTrap  TRAP-TYPE
	ENTERPRISE cpqSasSwitch
   VARIABLES  { sysName, cpqHoTrapFlags, cpqSsBoxCntlrHwLocation,
                     cpqSsBoxCntlrIndex, cpqSsBoxBusIndex, cpqSsBoxVendor,
                     cpqSsBoxModel, cpqSsBoxSerialNumber,
                     cpqSsBoxCondition, cpqSsBoxLocationString }
	DESCRIPTION
	"SAS switch detected storage enclosure removed.

   The switch has detected a storage enclosure has been removed."

      --#TYPE "Storage Enclosure Removed"
      --#SUMMARY "Storage Enclosure has been removed at location: %s"
      --#ARGUMENTS {9}
      --#SEVERITY INFORMATIONAL
      --#TIMEINDEX 99

	::= 402


-- ****************************************************************************
--    SAS Switch Hardware Group
--    =========================
--
-- The compaq enterprise               (1.3.6.1.4.1.232)
--      cpqSasSwitch Group             (1.3.6.1.4.1.232.25)
--       cpqSasSwitchComponent Group   (1.3.6.1.4.1.232.25.2)
--        cpqSasSwitchHw Group         (1.3.6.1.4.1.232.25.2.2)
--
--      The cpqSasSwitchHw group contains configuration and statistical
--      information about the SAS Switch hardware.
--
--      Implementation of the cpqSasSwitchHw group is mandatory for all
--      agents that support the SAS Switch MIB.
--
-- ****************************************************************************


-- ****************************************************************************
--    SAS Switch Type
--    ===============
--
-- The compaq enterprise               (1.3.6.1.4.1.232)
--      cpqSasSwitch Group             (1.3.6.1.4.1.232.25)
--       cpqSasSwitchComponent Group   (1.3.6.1.4.1.232.25.2)
--        cpqSasSwitchHw Group         (1.3.6.1.4.1.232.25.2.2)
--         cpqSasSwitchHwType          (1.3.6.1.4.1.232.25.2.2.1)
--
--  The cpqSasSwitchHwType contains object identifiers unique to each
--  SAS Switch type.
--
-- ****************************************************************************


--   The SysObjId for the "HP Virtual SAS Manager (VSM) Module" is
--   (1.3.6.1.4.1.232.25.2.2.1.1)
--   cpqSasSwitchTypeVsmm  OBJECT IDENTIFIER ::= { cpqSasSwitchHwType 1 }


-- ****************************************************************************
--    SAS Switch Status
--    ===============
--
-- The compaq enterprise               (1.3.6.1.4.1.232)
--      cpqSasSwitch Group             (1.3.6.1.4.1.232.25)
--       cpqSasSwitchComponent Group   (1.3.6.1.4.1.232.25.2)
--        cpqSasSwitchHw Group         (1.3.6.1.4.1.232.25.2.2)
--         cpqSasSwitchHwStatus        (1.3.6.1.4.1.232.25.2.2.2)
--
--  The cpqSasSwitchHwStatus contains the Status for the SAS Switch
--
-- ****************************************************************************
    cpqSasSwitchHwStatus OBJECT-TYPE
        SYNTAX  INTEGER {
            other(1),
            ok(2),
            degraded(3),
            failed(4)
            }
        ACCESS  read-only
        STATUS  mandatory
        DESCRIPTION
            "The Status of the SAS Switch.

            The switch can be in one of the following states:

            other(1)
              The switch is in a state other than one of those listed
              below.

            ok(2)
              Indicates that the switch is in normal operation mode.
              No user action is necessary.

            degraded(3)
              Indicates that the switch is operating in a degraded
              manner.
              User intervention required.

            failed(4)
              Indicates that the switch is in a failed state and
              is not operating.
              User action is required."
        ::= { cpqSasSwitchHw 2 }

-- ****************************************************************************
--    SAS Switch RedundancyState
--    ===============
--
-- The compaq enterprise               (1.3.6.1.4.1.232)
--      cpqSasSwitch Group             (1.3.6.1.4.1.232.25)
--       cpqSasSwitchComponent Group   (1.3.6.1.4.1.232.25.2)
--        cpqSasSwitchHw Group         (1.3.6.1.4.1.232.25.2.2)
--         cpqSasSwitchHwRedundancyState (1.3.6.1.4.1.232.25.2.2.2)
--
--  The cpqSasSwitchHwStatus contains the Status for the SAS Switch
--
-- ****************************************************************************
    cpqSasSwitchHwRedundancyState OBJECT-TYPE
        SYNTAX  INTEGER {
            other(1),
            active(2),
            standby(3),
            notConfigured(4),
            notRedundant(5),
            degraded(6),
            mismatch(7)
            }
        ACCESS  read-only
        STATUS  mandatory
        DESCRIPTION
            "The Redundancy State for the SAS Switch.

            The switch can be in one of the following redundant states:

            other(1)
              The switch is in a state other than one of those listed
              below.

            active(2)
              Indicates that the switch is acting in a redundant
              configuration and the switch is operating in the active
              state.
              No user action is necessary.

            standby(3)
              Indicates that the switch is acting in a redundant
              configuration and the switch is operating in the standby
              state.
              No user action is necessary.

            notConfigured(4)
              Indicates that the switch is in a non redundant
              configuration and the switch not configured correctly
              since the switch has been moved from a different location.
              User action is required.

            notRedundant(5)
              Indicates that the switch is operating is a non redundant
              configuration.
              No user action is necessary.

            degraded(6)
              Indicates that the switch cannot communicate with its
              partner switch.
              User action is necessary.

            mismatch(7)
              Indicates that there is a mismatch in firmware versions
              or zoning configurations between the redundant switches.
              User action is necessary to upgrade firmware or select
              desired zoning configuration by forcing appropriate
              switch to active state."
        ::= { cpqSasSwitchHw 3 }

END
