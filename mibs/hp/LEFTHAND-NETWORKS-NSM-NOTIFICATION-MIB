-- ****************************************************************************
-- LEFTHAND-NETWORKS-NSM-NOTIFICATION-MIB
-- Management Information Base for SNMP Network Management
--
-- This MIB provides notification (trap) information for a storage node.

-- This MIB must be loaded after:
--                                LEFTHAND-NETWORKS-GLOBAL-REG-MIB.mib
--                                LEFTHAND-NETWORKS-NSM-MIB.mib
--
-- The LeftHand Networks Enterprise number is 9804.
-- The ASN.1 prefix to, and including the LeftHand Networks Enterprise is:
--     1.3.6.1.4.1.9804
-- ****************************************************************************
-- Copyright 2009,2010 Hewlett-Packard Development Company, L.P.
-- Copyright 2008,2009 LeftHand Networks, Inc.
-- All Rights Reserved.
--
-- Hewlett-Packard Company shall not be liable for technical or
-- editorial errors or omissions contained herein. The information in
-- this document is provided "as is" without warranty of any kind and
-- is subject to change without notice. The warranties for HP products
-- are set forth in the express limited warranty statements
-- accompanying such products. Nothing herein should be construed as
-- constituting an additional warranty.
--
-- Confidential computer software. Valid license from HP required for
-- possession, use or copying. Consistent with FAR 12.211 and 12.212,
-- Commercial Computer Software, Computer Software Documentation, and
-- Technical Data for Commercial Items are licensed to the U.S.
-- Government under vendor's standard commercial license.
-- ****************************************************************************

LEFTHAND-NETWORKS-NSM-NOTIFICATION-MIB DEFINITIONS ::= BEGIN

IMPORTS
	MODULE-IDENTITY, OBJECT-IDENTITY, OBJECT-TYPE, NOTIFICATION-TYPE, Integer32, Unsigned32, Gauge32
		FROM SNMPv2-SMI
	OBJECT-GROUP, NOTIFICATION-GROUP, MODULE-COMPLIANCE
		FROM SNMPv2-CONF
	TEXTUAL-CONVENTION, DisplayString, DateAndTime, TruthValue
		FROM SNMPv2-TC
	lhnModules, lhnNsm
		FROM LEFTHAND-NETWORKS-GLOBAL-REG-MIB
	lhnNsmNotification, lhnNsmEvents, lhnNsmOldNotification, lhnNsmOldEvents
		FROM LEFTHAND-NETWORKS-NSM-MIB;

-- lhnNsm is imported but never used, this will create a smilint warning
-- however, it's necessary for some MIB compilers

--
-- Module definition and a brief description of this mib.
--
lhnNsmNotificationModule MODULE-IDENTITY
    LAST-UPDATED        "201311220000Z"
    ORGANIZATION        "Hewlett Packard Company, StorageWorks Division"
    CONTACT-INFO        "Product Support
                         Product URL: www.hp.com/go/p4000
                         Support URL: www.itrc.hp.com
                         Product Phone: www.hp.com/go/contact
                                        1-800-786-7967 (US only)
                         Support Phone: www.hp.com/go/contact
                                        1-800-334-5144 (US only)"
    DESCRIPTION         "HP Storage P4000 Notifications:
                         Traps(v1) and Informs(v2c)"

    REVISION            "201311220000Z"
    DESCRIPTION         "SAN/iQ 7.0, SAN/iQ 8.0, SAN/iQ 8.1, SAN/iQ 8.5, SAN/iQ 9.0, SAN/iQ 9.5, SAN/iQ 10.0, SAN/iQ 10.5, SAN/iQ 11.0, SAN/iQ 11.5
						Added:
							lhnWearState
							lhnWearDays
							lhnWearPercent"

    REVISION            "201306250000Z"
    DESCRIPTION         "SAN/iQ 7.0, SAN/iQ 8.0, SAN/iQ 8.1, SAN/iQ 8.5, SAN/iQ 9.0, SAN/iQ 9.5, SAN/iQ 10.0, SAN/iQ 10.5, SAN/iQ 11.0"

    REVISION            "201210120000Z"
    DESCRIPTION         "SAN/iQ 7.0, SAN/iQ 8.0, SAN/iQ 8.1, SAN/iQ 8.5, SAN/iQ 9.0, SAN/iQ 9.5, SAN/iQ 10.0, SAN/iQ 10.5
						Added:
							lhnWarrantyPartNumber
							lhnWarrantySerialNumber
							lhnWarrantyLicenseNumber"
    REVISION            "201209180000Z"
    DESCRIPTION         "SAN/iQ 7.0, SAN/iQ 8.0, SAN/iQ 8.1, SAN/iQ 8.5, SAN/iQ 9.0, SAN/iQ 9.5, SAN/iQ 10.0, SAN/iQ 10.5
							Changed Bbu to Bps"
    REVISION            "201209040000Z"
    DESCRIPTION         "SAN/iQ 7.0, SAN/iQ 8.0, SAN/iQ 8.1, SAN/iQ 8.5, SAN/iQ 9.0, SAN/iQ 9.5, SAN/iQ 10.0"

    REVISION            "201106210000Z"
    DESCRIPTION         "SAN/iQ 7.0, SAN/iQ 8.0, SAN/iQ 8.1, SAN/iQ 8.5, SAN/iQ 9.0, SAN/iQ 9.5"

    REVISION            "201009070000Z"
    DESCRIPTION         "SAN/iQ 7.0, SAN/iQ 8.0, SAN/iQ 8.1, SAN/iQ 8.5, SAN/iQ 9.0
						Prefixed object names with 'lhn' or 'Lhn' to prevent namespace collisions in some SNMP clients.
						Added Notifications:
							lhnNsmNotificationSnapshotSchedule
							lhnNsmNotificationManager
							lhnNsmNotificationVirtualManager
							lhnNsmNotificationFailoverManager
							lhnNsmNotificationConfiguration
							lhnNsmNotificationResource
							lhnNsmNotificationService
							lhnNsmNotificationMountPoint
							lhnNsmNotificationPartition
						Added:
							diskSpeed
							licenseState
							utilizationState
							latencyState
							serverVIPAddress
							serverVIPState
							replicationState
							snapshotState
							snapshotSchedState"

    REVISION            "201007190000Z"
    DESCRIPTION         "SAN/iQ 7.0, SAN/iQ 8.0, SAN/iQ 8.1, SAN/iQ 8.5 with patch 10076
						Added Notifications:
						Added Objects:
							lhnDiskSpeed
							lhnLicenseState
							lhnUtilizationState
							lhnLatencyState
							lhnServerVIPAddress
							lhnServerVIPAddress
							lhnServerVIPState
							lhnReplicationState
							lhnSnapshotState
							lhnSnapshotSchedState
						Renamed some objects to have a consistent use of 'Status' and 'State'.
						Redeclared lhnNsmDevices and lhnNsmEvents for increased client compatability."

    REVISION            "200911200000Z"
    DESCRIPTION         "SAN/iQ 7.0, SAN/iQ 8.0, SAN/iQ 8.1, SAN/iQ 8.5
						Added Notifications:
							lhnNsmNotificationGeneric
							lhnNsmNotificationBackplane
							lhnNsmNotificationController
							lhnNsmNotificationRAID
							lhnNsmNotificationDisk
							lhnNsmNotificationBootDevice
							lhnNsmNotificationFan
							lhnNsmNotificationTemperature
							lhnNsmNotificationPowerSupply
							lhnNsmNotificationVoltage
							lhnNsmNotificationNetwork
							lhnNsmNotificationMemory
							lhnNsmNotificationCPU
							lhnNsmNotificationLogging
							lhnNsmNotificationManagementGroup
							lhnNsmNotificationRemoteManagementGroup
							lhnNsmNotificationCluster
							lhnNsmNotificationStorageServer
							lhnNsmNotificationRemoteCopy
							lhnNsmNotificationVolume
							lhnNsmNotificationSnapshot
						Obsoleted Notifications:
							userNotification
						Added Objects:
							lhnNotificationOldMessageCount
							lhnNotificationMessage
							lhnNotificationTime
							lhnNotificationMessageCount
							lhnMessage
							lhnMessageTime
							lhnEventID
							lhnSeverity
							lhnHostname
							lhnPrimaryIP
							lhnMac
							lhnSerialNumber
							lhnModelName
							lhnProductName
							lhnProductID
							lhnHpim
							lhnSoftwareVersion
							lhnManagementGroupVersion
							lhnManagementGroupSerialNumber
							lhnManagementGroup
							lhnCluster
							lhnSite
							lhnComponentName
							lhnSystemName
							lhnLogicalName
							lhnComponentState
							lhnComponentModel
							lhnComponentSerialNumber
							lhnComponentFirmwareVersion
							lhnComponentHardwareVersion
							lhnDriverVersion
							lhnBiosVersion
							lhnRaidConfiguration
							lhnDiskInterface
							lhnDiskCapacity
							lhnRaidState
							lhnParityInitStatus
							lhnHealthState
							lhnBpsState
							lhnCacheState
							lhnLinkState
							lhnVipState
							lhnMaintenanceMode
							lhnMinFanSpeed
							lhnFanSpeed
							lhnHighTemperatureLimit
							lhnTemperatureState
							lhnTemperature
							lhnHighVoltageLimit
							lhnLowVoltageLimit
							lhnVoltage
							lhnUtilization
							lhnLatency
							lhnMemoryUtilization
							lhnMemoryConfig
							lhnCpuUtilization
							lhnCpuConfig
						Obsoleted Objects
							notificationMessageCount
							notificationMessage
							notificationTime"

    REVISION            "200903100000Z"
    DESCRIPTION         "SAN/iQ 7.0, SAN/iQ 8.0, SAN/iQ 8.1"

    REVISION            "200801240000Z"
    DESCRIPTION         "SAN/iQ 7.0, SAN/iQ 8.0
                        Updated object names to use current product branding.
                        Added conformance and compliance objects.
                        Updated the MIB for increased client compatability."

	::= { lhnModules 15 }

-- lhnNsmDevices and lhnNsmEvents are redefined(duplicated) in this MIB to
-- increase compatability with some SNMP clients

lhnNsmDevices OBJECT-IDENTITY
    STATUS              current
    DESCRIPTION         "sub-tree for NSM devices"
    ::= { lhnNsm 1 }

lhnNsmEvents OBJECT-IDENTITY
    STATUS              current
    DESCRIPTION         "sub-tree for NSM events"
    ::= { lhnNsmDevices 0 }

--******************************************************************************
--
-- Conformance
--
--******************************************************************************

lhnNsmNotificationModuleConformance OBJECT IDENTIFIER
	::= { lhnNsmNotificationModule 1 }

lhnNsmNotificationModuleCompliances OBJECT IDENTIFIER
	::= { lhnNsmNotificationModuleConformance 1 }

lhnNsmNotificationModuleGroups OBJECT IDENTIFIER
	::= { lhnNsmNotificationModuleConformance 2 }

lefthandNetworksNsmNotificationMibCompliance MODULE-COMPLIANCE
	STATUS current
	DESCRIPTION "The compliance statement."
	MODULE
	MANDATORY-GROUPS {
			lefthandNetworksNsmNotificationGroup,
			lefthandNetworksNsmNotificationMibAllNotifications
		}
	::= { lhnNsmNotificationModuleCompliances 1 }

lefthandNetworksNsmNotificationGroup OBJECT-GROUP
    OBJECTS {
					lhnNotificationOldMessageCount,
					lhnNotificationMessage,
					lhnNotificationTime,
                    lhnNotificationMessageCount,
                    lhnMessage,
                    lhnMessageTime,
                    lhnEventID,
                    lhnSeverity,
                    lhnHostname,
                    lhnPrimaryIP,
                    lhnMac,
                    lhnSerialNumber,
                    lhnModelName,
                    lhnProductName,
                    lhnProductID,
                    lhnHpim,
                    lhnSoftwareVersion,
                    lhnManagementGroupVersion,
                    lhnManagementGroupSerialNumber,
                    lhnManagementGroup,
                    lhnCluster,
                    lhnSite,
					lhnComponentName,
					lhnSystemName,
					lhnLogicalName,
					lhnComponentState,
					lhnComponentModel,
					lhnComponentSerialNumber,
					lhnComponentFirmwareVersion,
					lhnComponentHardwareVersion,
					lhnDriverVersion,
					lhnBiosVersion,
					lhnRaidConfiguration,
					lhnDiskInterface,
					lhnDiskCapacity,
                    lhnRaidState,
					lhnParityInitStatus,
					lhnHealthState,
					lhnBpsState,
					lhnCacheState,
					lhnLinkState,
					lhnVipState,
					lhnMaintenanceMode,
					lhnMinFanSpeed,
					lhnFanSpeed,
					lhnHighTemperatureLimit,
					lhnTemperatureState,
					lhnTemperature,
					lhnHighVoltageLimit,
					lhnLowVoltageLimit,
					lhnVoltage,
					lhnUtilization,
					lhnLatency,
					lhnMemoryUtilization,
					lhnMemoryConfig,
					lhnCpuUtilization,
					lhnCpuConfig,
					lhnDiskSpeed,
					lhnLicenseState,
					lhnUtilizationState,
					lhnLatencyState,
					lhnServerVIPAddress,
					lhnServerVIPState,
					lhnReplicationState,
					lhnSnapshotState,
					lhnSnapshotSchedState,
					lhnWarrantyPartNumber,
					lhnWarrantySerialNumber,
					lhnWarrantyLicenseNumber,
					lhnWearState,
					lhnWearDays,
					lhnWearPercent
            }
    STATUS              current
    DESCRIPTION         "The default group for all NSM Notification objects."
    ::= { lhnNsmNotificationModuleGroups 1 }

lefthandNetworksNsmNotificationMibAllNotifications NOTIFICATION-GROUP
    NOTIFICATIONS       {
                            lhnUserNotification,
                            lhnNsmNotificationGeneric,
							lhnNsmNotificationBackplane,
							lhnNsmNotificationController,
							lhnNsmNotificationRAID,
							lhnNsmNotificationDisk,
							lhnNsmNotificationBootDevice,
							lhnNsmNotificationFan,
							lhnNsmNotificationTemperature,
							lhnNsmNotificationPowerSupply,
							lhnNsmNotificationVoltage,
							lhnNsmNotificationNetwork,
							lhnNsmNotificationMemory,
							lhnNsmNotificationCPU,
							lhnNsmNotificationLogging,
							lhnNsmNotificationManagementGroup,
							lhnNsmNotificationRemoteManagementGroup,
							lhnNsmNotificationCluster,
							lhnNsmNotificationStorageServer,
							lhnNsmNotificationRemoteCopy,
							lhnNsmNotificationVolume,
							lhnNsmNotificationSnapshot,
							lhnNsmNotificationSnapshotSchedule,
							lhnNsmNotificationManager,
							lhnNsmNotificationVirtualManager,
							lhnNsmNotificationFailoverManager,
							lhnNsmNotificationConfiguration,
							lhnNsmNotificationResource,
							lhnNsmNotificationService,
							lhnNsmNotificationMountPoint,
							lhnNsmNotificationPartition
                        }
    STATUS              current
    DESCRIPTION         "The default group for all NSM Notification objects."
    ::= { lhnNsmNotificationModuleGroups 2 }

--******************************************************************************
--
-- Notification Objects
--
--******************************************************************************

--******************************************************************************
-- In SAN/iQ 8.1 and earlier all notifications were SNMP v2c notifications
-- from a single OID:
--                      LEFTHAND-NETWORKS-NSM-NOTIFICATION-MIB::userNotification
--                      .1.3.6.1.4.1.9804.3.1.1.3.1
--
-- In SAN/iQ 8.5 and later notifications can be sent as SNMP v1 traps or
-- SNMP v2 notifications and use multiple OIDs defined in this MIB.
--******************************************************************************

lhnNotificationMessageCount OBJECT-TYPE
    SYNTAX              Integer32
    MAX-ACCESS          read-only
    STATUS              current
    DESCRIPTION         "The number of notification messages available in the history."
    ::= { lhnNsmNotification 1 }

lhnNotificationMessageTable OBJECT-TYPE
    SYNTAX              SEQUENCE OF LhnNotificationMessageEntry
    MAX-ACCESS          not-accessible
    STATUS              current
    DESCRIPTION         "A table of the last 100 notifications for the NSM.
                        The number of entries is given by lhnNotificationMessageCount."
    ::= { lhnNsmNotification 2 }

    lhnNotificationMessageEntry OBJECT-TYPE
        SYNTAX              LhnNotificationMessageEntry
        MAX-ACCESS          not-accessible
        STATUS              current
        DESCRIPTION         "A row of notification message information.
							The information contained in each row is dependant on the trap type
							and the event that caused the trap.  Not all LhnNotificationMessageEntry
							objects will have values."
        INDEX               {
                                lhnNotificationMessageIndex
                            }
        ::= { lhnNotificationMessageTable 1 }

    LhnNotificationMessageEntry ::= SEQUENCE {
        lhnNotificationMessageIndex Unsigned32,
        lhnMessage							DisplayString,
        lhnMessageTime						DateAndTime,
        lhnEventID							DisplayString,
        lhnSeverity							INTEGER,
        lhnHostname							DisplayString,
        lhnPrimaryIP						DisplayString,
        lhnMac								DisplayString,
        lhnSerialNumber						DisplayString,
        lhnModelName						DisplayString,
        lhnProductName						DisplayString,
        lhnProductID						DisplayString,
        lhnHpim								TruthValue,
        lhnSoftwareVersion					DisplayString,
        lhnManagementGroupVersion			DisplayString,
        lhnManagementGroupSerialNumber		DisplayString,
        lhnManagementGroup					DisplayString,
        lhnCluster							DisplayString,
        lhnSite								DisplayString,
		lhnComponentName					DisplayString,
		lhnSystemName						DisplayString,
		lhnLogicalName						DisplayString,
		lhnComponentState					DisplayString,
		lhnComponentModel					DisplayString,
		lhnComponentSerialNumber			DisplayString,
		lhnComponentFirmwareVersion			DisplayString,
		lhnComponentHardwareVersion			DisplayString,
		lhnDriverVersion					DisplayString,
		lhnBiosVersion						DisplayString,
		lhnRaidConfiguration				DisplayString,
		lhnDiskInterface					DisplayString,
		lhnDiskCapacity						Integer32,
        lhnRaidState						DisplayString,
		lhnParityInitStatus					DisplayString,
		lhnHealthState						DisplayString,
		lhnBpsState							DisplayString,
		lhnCacheState						DisplayString,
		lhnLinkState						DisplayString,
		lhnVipState							DisplayString,
		lhnMaintenanceMode					DisplayString,
		lhnMinFanSpeed						Integer32,
		lhnFanSpeed							Gauge32,
		lhnHighTemperatureLimit				Integer32,
		lhnTemperatureState					DisplayString,
		lhnTemperature						Gauge32,
		lhnHighVoltageLimit					Integer32,
		lhnLowVoltageLimit					Integer32,
		lhnVoltage							Gauge32,
		lhnUtilization						Gauge32,
		lhnLatency							Gauge32,
		lhnMemoryUtilization				Gauge32,
		lhnMemoryConfig						Integer32,
		lhnCpuUtilization					Gauge32,
		lhnCpuConfig						Integer32,
		lhnDiskSpeed						DisplayString,
		lhnLicenseState						DisplayString,
		lhnUtilizationState					DisplayString,
		lhnLatencyState						DisplayString,
		lhnServerVIPAddress					DisplayString,
		lhnServerVIPState					DisplayString,
		lhnReplicationState					DisplayString,
		lhnSnapshotState					DisplayString,
		lhnSnapshotSchedState				DisplayString,
		lhnWarrantyPartNumber				DisplayString,
		lhnWarrantySerialNumber				DisplayString,
		lhnWarrantyLicenseNumber			DisplayString,
		lhnWearState						DisplayString,
		lhnWearDays							Integer32,
		lhnWearPercent						Gauge32
}

    lhnNotificationMessageIndex OBJECT-TYPE
        SYNTAX              Unsigned32
        MAX-ACCESS          not-accessible
        STATUS              current
        DESCRIPTION         "The index for the lhnNotificationMessageTable table."
        ::= { lhnNotificationMessageEntry 1 }

    lhnMessage OBJECT-TYPE
        SYNTAX              DisplayString
        MAX-ACCESS          read-only
        STATUS              current
        DESCRIPTION         "The notification message."
        ::= { lhnNotificationMessageEntry 2 }

    lhnMessageTime OBJECT-TYPE
        SYNTAX              DateAndTime
        MAX-ACCESS          read-only
        STATUS              current
        DESCRIPTION         "The time the notification was sent."
        ::= { lhnNotificationMessageEntry 3 }

    lhnEventID OBJECT-TYPE
        SYNTAX              DisplayString
        MAX-ACCESS          read-only
        STATUS              current
        DESCRIPTION         "The event ID in symbolic format."
        ::= { lhnNotificationMessageEntry 4 }

    lhnSeverity OBJECT-TYPE
        SYNTAX              INTEGER { critical(0), warning(1), info(2) }
        MAX-ACCESS          read-only
        STATUS              current
        DESCRIPTION         "The event severity."
        ::= { lhnNotificationMessageEntry 5 }

    lhnHostname OBJECT-TYPE
        SYNTAX              DisplayString
        MAX-ACCESS          read-only
        STATUS              current
        DESCRIPTION         "The NSM hostname."
        ::= { lhnNotificationMessageEntry 6 }

    lhnPrimaryIP OBJECT-TYPE
        SYNTAX              DisplayString
        MAX-ACCESS          read-only
        STATUS              current
        DESCRIPTION         "The primary IP address."
        ::= { lhnNotificationMessageEntry 7 }

    lhnMac OBJECT-TYPE
        SYNTAX              DisplayString
        MAX-ACCESS          read-only
        STATUS              current
        DESCRIPTION         "The MAC address of the primary IP address."
        ::= { lhnNotificationMessageEntry 8 }

    lhnSerialNumber OBJECT-TYPE
        SYNTAX              DisplayString
        MAX-ACCESS          read-only
        STATUS              current
        DESCRIPTION         "The chassis serial number."
        ::= { lhnNotificationMessageEntry 9 }

    lhnModelName OBJECT-TYPE
        SYNTAX              DisplayString
        MAX-ACCESS          read-only
        STATUS              current
        DESCRIPTION         "The system model name."
        ::= { lhnNotificationMessageEntry 10 }

    lhnProductName OBJECT-TYPE
        SYNTAX              DisplayString
        MAX-ACCESS          read-only
        STATUS              current
        DESCRIPTION         "The OEM product name."
        ::= { lhnNotificationMessageEntry 11 }

    lhnProductID OBJECT-TYPE
        SYNTAX              DisplayString
        MAX-ACCESS          read-only
        STATUS              current
        DESCRIPTION         "The OEM product ID."
        ::= { lhnNotificationMessageEntry 12 }

    lhnHpim OBJECT-TYPE
        SYNTAX              TruthValue
        MAX-ACCESS          read-only
        STATUS              current
        DESCRIPTION         "HP Insight Manager SNMP agent installed on NSM"
        ::= { lhnNotificationMessageEntry 13 }

    lhnSoftwareVersion OBJECT-TYPE
        SYNTAX              DisplayString
        MAX-ACCESS          read-only
        STATUS              current
        DESCRIPTION         "The SAN/iQ software version"
        ::= { lhnNotificationMessageEntry 14 }

    lhnManagementGroupVersion OBJECT-TYPE
        SYNTAX              DisplayString
        MAX-ACCESS          read-only
        STATUS              current
        DESCRIPTION         "The management group version."
        ::= { lhnNotificationMessageEntry 15 }

    lhnManagementGroupSerialNumber OBJECT-TYPE
        SYNTAX              DisplayString
        MAX-ACCESS          read-only
        STATUS              current
        DESCRIPTION         "The management group serial number."
        ::= { lhnNotificationMessageEntry 16 }

    lhnManagementGroup OBJECT-TYPE
        SYNTAX              DisplayString
        MAX-ACCESS          read-only
        STATUS              current
        DESCRIPTION         "The management group name."
        ::= { lhnNotificationMessageEntry 17 }

    lhnCluster OBJECT-TYPE
        SYNTAX              DisplayString
        MAX-ACCESS          read-only
        STATUS              current
        DESCRIPTION         "The cluster name."
        ::= { lhnNotificationMessageEntry 18 }

    lhnSite OBJECT-TYPE
        SYNTAX              DisplayString
        MAX-ACCESS          read-only
        STATUS              current
        DESCRIPTION         "The site the cluster is in."
        ::= { lhnNotificationMessageEntry 19 }

    lhnComponentName OBJECT-TYPE
        SYNTAX              DisplayString
        MAX-ACCESS          read-only
        STATUS              current
        DESCRIPTION         "The component name."
        ::= { lhnNotificationMessageEntry 20 }

    lhnSystemName OBJECT-TYPE
        SYNTAX              DisplayString
        MAX-ACCESS          read-only
        STATUS              current
        DESCRIPTION         "The system hostname."
        ::= { lhnNotificationMessageEntry 21 }

    lhnLogicalName OBJECT-TYPE
        SYNTAX              DisplayString
        MAX-ACCESS          read-only
        STATUS              current
        DESCRIPTION         "The logical name for the component."
        ::= { lhnNotificationMessageEntry 22 }

    lhnComponentState OBJECT-TYPE
        SYNTAX              DisplayString
        MAX-ACCESS          read-only
        STATUS              current
        DESCRIPTION         "The component state."
        ::= { lhnNotificationMessageEntry 23 }

    lhnComponentModel OBJECT-TYPE
        SYNTAX              DisplayString
        MAX-ACCESS          read-only
        STATUS              current
        DESCRIPTION         "The component model."
        ::= { lhnNotificationMessageEntry 24 }

    lhnComponentSerialNumber OBJECT-TYPE
        SYNTAX              DisplayString
        MAX-ACCESS          read-only
        STATUS              current
        DESCRIPTION         "The component serial number."
        ::= { lhnNotificationMessageEntry 25 }

    lhnComponentFirmwareVersion OBJECT-TYPE
        SYNTAX              DisplayString
        MAX-ACCESS          read-only
        STATUS              current
        DESCRIPTION         "The component firmware version."
        ::= { lhnNotificationMessageEntry 26 }

    lhnComponentHardwareVersion OBJECT-TYPE
        SYNTAX              DisplayString
        MAX-ACCESS          read-only
        STATUS              current
        DESCRIPTION         "The component hardware version."
        ::= { lhnNotificationMessageEntry 27 }

    lhnDriverVersion OBJECT-TYPE
        SYNTAX              DisplayString
        MAX-ACCESS          read-only
        STATUS              current
        DESCRIPTION         "The driver version."
        ::= { lhnNotificationMessageEntry 28 }

    lhnBiosVersion OBJECT-TYPE
        SYNTAX              DisplayString
        MAX-ACCESS          read-only
        STATUS              current
        DESCRIPTION         "The BIOS version."
        ::= { lhnNotificationMessageEntry 29 }

    lhnRaidConfiguration OBJECT-TYPE
        SYNTAX              DisplayString
        MAX-ACCESS          read-only
        STATUS              current
        DESCRIPTION         "The RAID configuration."
        ::= { lhnNotificationMessageEntry 30 }

    lhnDiskInterface OBJECT-TYPE
        SYNTAX              DisplayString
        MAX-ACCESS          read-only
        STATUS              current
        DESCRIPTION         "The disk interface type."
        ::= { lhnNotificationMessageEntry 31 }

    lhnDiskCapacity OBJECT-TYPE
        SYNTAX              Integer32
		UNITS				"MB"
        MAX-ACCESS          read-only
        STATUS              current
        DESCRIPTION         "The disk capacity."
        ::= { lhnNotificationMessageEntry 32 }

    lhnRaidState OBJECT-TYPE
        SYNTAX              DisplayString
        MAX-ACCESS          read-only
        STATUS              current
        DESCRIPTION         "The RAID state."
        ::= { lhnNotificationMessageEntry 33 }

    lhnParityInitStatus OBJECT-TYPE
        SYNTAX              DisplayString
        MAX-ACCESS          read-only
        STATUS              current
        DESCRIPTION         "The RAID Parity Initialization status."
        ::= { lhnNotificationMessageEntry 34 }

    lhnHealthState OBJECT-TYPE
        SYNTAX              DisplayString
        MAX-ACCESS          read-only
        STATUS              current
        DESCRIPTION         "The disk health state."
        ::= { lhnNotificationMessageEntry 35 }

    lhnBpsState OBJECT-TYPE
        SYNTAX              DisplayString
        MAX-ACCESS          read-only
        STATUS              current
        DESCRIPTION         "The BPS state."
        ::= { lhnNotificationMessageEntry 36 }

    lhnCacheState OBJECT-TYPE
        SYNTAX              DisplayString
        MAX-ACCESS          read-only
        STATUS              current
        DESCRIPTION         "The cache state."
        ::= { lhnNotificationMessageEntry 37 }

    lhnLinkState OBJECT-TYPE
        SYNTAX              DisplayString
        MAX-ACCESS          read-only
        STATUS              current
        DESCRIPTION         "The link state."
        ::= { lhnNotificationMessageEntry 38 }

    lhnVipState OBJECT-TYPE
        SYNTAX              DisplayString
        MAX-ACCESS          read-only
        STATUS              current
        DESCRIPTION         "The cluster VIP state."
        ::= { lhnNotificationMessageEntry 39 }

    lhnMaintenanceMode OBJECT-TYPE
        SYNTAX              DisplayString
        MAX-ACCESS          read-only
        STATUS              current
        DESCRIPTION         "The management group maintenance mode."
        ::= { lhnNotificationMessageEntry 40 }

    lhnMinFanSpeed OBJECT-TYPE
        SYNTAX              Integer32
		UNITS               "RPM"
        MAX-ACCESS          read-only
        STATUS              current
        DESCRIPTION         "The minimal fan speed."
        ::= { lhnNotificationMessageEntry 41 }

    lhnFanSpeed OBJECT-TYPE
        SYNTAX              Gauge32
		UNITS               "RPM"
        MAX-ACCESS          read-only
        STATUS              current
        DESCRIPTION         "The fan speed."
        ::= { lhnNotificationMessageEntry 42 }

    lhnHighTemperatureLimit OBJECT-TYPE
        SYNTAX              Integer32
		UNITS               "Celsius"
        MAX-ACCESS          read-only
        STATUS              current
        DESCRIPTION         "The high temperature limit."
        ::= { lhnNotificationMessageEntry 43 }

    lhnTemperatureState OBJECT-TYPE
        SYNTAX              DisplayString
        MAX-ACCESS          read-only
        STATUS              current
        DESCRIPTION         "The component temperature state."
        ::= { lhnNotificationMessageEntry 44 }

    lhnTemperature OBJECT-TYPE
        SYNTAX              Gauge32
		UNITS               "Celsius"
        MAX-ACCESS          read-only
        STATUS              current
        DESCRIPTION         "The component temperature."
        ::= { lhnNotificationMessageEntry 45 }

    lhnHighVoltageLimit OBJECT-TYPE
        SYNTAX              Integer32
		UNITS				"Volts"
        MAX-ACCESS          read-only
        STATUS              current
        DESCRIPTION         "The high voltage limit."
        ::= { lhnNotificationMessageEntry 46 }

    lhnLowVoltageLimit OBJECT-TYPE
        SYNTAX              Integer32
		UNITS				"Volts"
        MAX-ACCESS          read-only
        STATUS              current
        DESCRIPTION         "The low voltage limit."
        ::= { lhnNotificationMessageEntry 47 }

    lhnVoltage OBJECT-TYPE
        SYNTAX              Gauge32
		UNITS				"Volts"
        MAX-ACCESS          read-only
        STATUS              current
        DESCRIPTION         "The voltage."
        ::= { lhnNotificationMessageEntry 48 }

    lhnUtilization OBJECT-TYPE
        SYNTAX              Gauge32
		UNITS				"%"
        MAX-ACCESS          read-only
        STATUS              current
        DESCRIPTION         "The resource utilization."
        ::= { lhnNotificationMessageEntry 49 }

    lhnLatency OBJECT-TYPE
		SYNTAX				Gauge32
		UNITS				"ms"
        MAX-ACCESS          read-only
        STATUS              current
        DESCRIPTION         "The storage server latency."
        ::= { lhnNotificationMessageEntry 50 }

    lhnMemoryUtilization OBJECT-TYPE
        SYNTAX              Gauge32
		UNITS				"%"
        MAX-ACCESS          read-only
        STATUS              current
        DESCRIPTION         "The memory utilization."
        ::= { lhnNotificationMessageEntry 51 }

    lhnMemoryConfig OBJECT-TYPE
        SYNTAX              Integer32
		UNITS				"MB"
        MAX-ACCESS          read-only
        STATUS              current
        DESCRIPTION         "The system memory configuration."
        ::= { lhnNotificationMessageEntry 52 }

    lhnCpuUtilization OBJECT-TYPE
        SYNTAX              Gauge32
		UNITS				"%"
        MAX-ACCESS          read-only
        STATUS              current
        DESCRIPTION         "The CPU utilization."
        ::= { lhnNotificationMessageEntry 53 }

    lhnCpuConfig OBJECT-TYPE
        SYNTAX              Integer32
		UNITS				"cores"
        MAX-ACCESS          read-only
        STATUS              current
        DESCRIPTION         "The number of CPU cores."
        ::= { lhnNotificationMessageEntry 54 }

    lhnDiskSpeed OBJECT-TYPE
        SYNTAX              DisplayString
        MAX-ACCESS          read-only
        STATUS              current
        DESCRIPTION         "The disk interface speed."
        ::= { lhnNotificationMessageEntry 55 }

    lhnLicenseState OBJECT-TYPE
        SYNTAX              DisplayString
        MAX-ACCESS          read-only
        STATUS              current
        DESCRIPTION         "The feature license state."
        ::= { lhnNotificationMessageEntry 56 }

    lhnUtilizationState OBJECT-TYPE
        SYNTAX              DisplayString
        MAX-ACCESS          read-only
        STATUS              current
        DESCRIPTION         "The utilization state."
        ::= { lhnNotificationMessageEntry 57 }

    lhnLatencyState OBJECT-TYPE
        SYNTAX              DisplayString
        MAX-ACCESS          read-only
        STATUS              current
        DESCRIPTION         "The storage server latency state."
        ::= { lhnNotificationMessageEntry 58 }

    lhnServerVIPAddress OBJECT-TYPE
        SYNTAX              DisplayString
        MAX-ACCESS          read-only
        STATUS              current
        DESCRIPTION         "The VIP address."
        ::= { lhnNotificationMessageEntry 59 }

    lhnServerVIPState OBJECT-TYPE
        SYNTAX              DisplayString
        MAX-ACCESS          read-only
        STATUS              current
        DESCRIPTION         "The VIP state."
        ::= { lhnNotificationMessageEntry 60 }

    lhnReplicationState OBJECT-TYPE
        SYNTAX              DisplayString
        MAX-ACCESS          read-only
        STATUS              current
        DESCRIPTION         "The volume/snapshot replication state."
        ::= { lhnNotificationMessageEntry 61 }

    lhnSnapshotState OBJECT-TYPE
        SYNTAX              DisplayString
        MAX-ACCESS          read-only
        STATUS              current
        DESCRIPTION         "The snapshot state."
        ::= { lhnNotificationMessageEntry 62 }

    lhnSnapshotSchedState OBJECT-TYPE
        SYNTAX              DisplayString
        MAX-ACCESS          read-only
        STATUS              current
        DESCRIPTION         "The snapshot schedule state."
        ::= { lhnNotificationMessageEntry 63 }

    lhnWarrantyPartNumber OBJECT-TYPE
        SYNTAX              DisplayString
        MAX-ACCESS          read-only
        STATUS              current
        DESCRIPTION         "The warranty part number."
        ::= { lhnNotificationMessageEntry 64 }

    lhnWarrantySerialNumber OBJECT-TYPE
        SYNTAX              DisplayString
        MAX-ACCESS          read-only
        STATUS              current
        DESCRIPTION         "The warranty Serial number."
        ::= { lhnNotificationMessageEntry 65 }

    lhnWarrantyLicenseNumber OBJECT-TYPE
        SYNTAX              DisplayString
        MAX-ACCESS          read-only
        STATUS              current
        DESCRIPTION         "The warranty License number."
        ::= { lhnNotificationMessageEntry 66 }

    lhnWearState OBJECT-TYPE
        SYNTAX              DisplayString
        MAX-ACCESS          read-only
        STATUS              current
        DESCRIPTION         "The SSD Wear State."
        ::= { lhnNotificationMessageEntry 67 }

    lhnWearDays OBJECT-TYPE
        SYNTAX              Integer32
        MAX-ACCESS          read-only
        STATUS              current
        DESCRIPTION         "The SSD Wear Days Remaining."
        ::= { lhnNotificationMessageEntry 68 }

    lhnWearPercent OBJECT-TYPE
        SYNTAX              Gauge32
		UNITS				"%"
        MAX-ACCESS          read-only
        STATUS              current
        DESCRIPTION         "The SSD Wear Percentage Remaining."
        ::= { lhnNotificationMessageEntry 69 }

--******************************************************************************
--
-- Current Notifications
--
--******************************************************************************

lhnNsmNotificationGeneric NOTIFICATION-TYPE
	OBJECTS {
					lhnMessage,
					lhnMessageTime,
					lhnEventID,
					lhnSeverity,
					lhnHostname,
					lhnPrimaryIP,
					lhnMac,
					lhnSerialNumber,
					lhnModelName,
					lhnProductName,
					lhnProductID,
					lhnHpim,
					lhnSoftwareVersion,
					lhnManagementGroupVersion,
					lhnManagementGroupSerialNumber,
					lhnManagementGroup,
					lhnCluster,
					lhnSite,
					lhnWarrantyPartNumber,
					lhnWarrantySerialNumber,
					lhnWarrantyLicenseNumber
			}
	STATUS              current
	DESCRIPTION         "A generic system event was generated.
						The user chose to be notified of this condition
						via SNMP. A table of messages exists which stores
						all the notifications issued. This trap will
						contain the OID referring to the corresponding
						message stored in this table.
						Added in SAN/iQ 8.5"
	::= { lhnNsmEvents 1 }

lhnNsmNotificationBackplane NOTIFICATION-TYPE
	OBJECTS {
					lhnMessage,
					lhnMessageTime,
					lhnEventID,
					lhnSeverity,
					lhnHostname,
					lhnPrimaryIP,
					lhnMac,
					lhnSerialNumber,
					lhnModelName,
					lhnProductName,
					lhnProductID,
					lhnHpim,
					lhnSoftwareVersion,
					lhnManagementGroupVersion,
					lhnManagementGroupSerialNumber,
					lhnManagementGroup,
					lhnCluster,
					lhnSite,
					lhnComponentName,
					lhnComponentState,
					lhnComponentSerialNumber,
					lhnComponentFirmwareVersion,
					lhnWarrantyPartNumber,
					lhnWarrantySerialNumber,
					lhnWarrantyLicenseNumber
			}
	STATUS              current
	DESCRIPTION         "An event for the system backplane was generated.
						The user chose to be notified of this condition
						via SNMP. A table of messages exists which stores
						all the notifications issued. This trap will
						contain the OID referring to the corresponding
						message stored in this table.
						Added in SAN/iQ 8.5"
	::= { lhnNsmEvents 2 }

lhnNsmNotificationController NOTIFICATION-TYPE
	OBJECTS {
					lhnMessage,
					lhnMessageTime,
					lhnEventID,
					lhnSeverity,
					lhnHostname,
					lhnPrimaryIP,
					lhnMac,
					lhnSerialNumber,
					lhnModelName,
					lhnProductName,
					lhnProductID,
					lhnHpim,
					lhnSoftwareVersion,
					lhnManagementGroupVersion,
					lhnManagementGroupSerialNumber,
					lhnManagementGroup,
					lhnCluster,
					lhnSite,
					lhnComponentName,
					lhnComponentState,
					lhnComponentModel,
					lhnComponentSerialNumber,
					lhnComponentHardwareVersion,
					lhnComponentFirmwareVersion,
					lhnDriverVersion,
					lhnBiosVersion,
					lhnCacheState,
					lhnBpsState,
					lhnWarrantyPartNumber,
					lhnWarrantySerialNumber,
					lhnWarrantyLicenseNumber
			}
	STATUS              current
	DESCRIPTION         "An event for the RAID controller was generated.
						The user chose to be notified of this condition
						via SNMP. A table of messages exists which stores
						all the notifications issued. This trap will
						contain the OID referring to the corresponding
						message stored in this table.
						Added in SAN/iQ 8.5"
	::= { lhnNsmEvents 3 }

lhnNsmNotificationRAID NOTIFICATION-TYPE
	OBJECTS {
					lhnMessage,
					lhnMessageTime,
					lhnEventID,
					lhnSeverity,
					lhnHostname,
					lhnPrimaryIP,
					lhnMac,
					lhnSerialNumber,
					lhnModelName,
					lhnProductName,
					lhnProductID,
					lhnHpim,
					lhnSoftwareVersion,
					lhnManagementGroupVersion,
					lhnManagementGroupSerialNumber,
					lhnManagementGroup,
					lhnCluster,
					lhnSite,
					lhnComponentState,
					lhnRaidConfiguration,
					lhnParityInitStatus,
					lhnWarrantyPartNumber,
					lhnWarrantySerialNumber,
					lhnWarrantyLicenseNumber
			}
	STATUS              current
	DESCRIPTION         "An event for the system RAID was generated.
						The user chose to be notified of this condition
						via SNMP. A table of messages exists which stores
						all the notifications issued. This trap will
						contain the OID referring to the corresponding
						message stored in this table.
						Added in SAN/iQ 8.5"
	::= { lhnNsmEvents 4 }

lhnNsmNotificationDisk NOTIFICATION-TYPE
	OBJECTS {
					lhnMessage,
					lhnMessageTime,
					lhnEventID,
					lhnSeverity,
					lhnHostname,
					lhnPrimaryIP,
					lhnMac,
					lhnSerialNumber,
					lhnModelName,
					lhnProductName,
					lhnProductID,
					lhnHpim,
					lhnSoftwareVersion,
					lhnManagementGroupVersion,
					lhnManagementGroupSerialNumber,
					lhnManagementGroup,
					lhnCluster,
					lhnSite,
					lhnComponentName,
					lhnComponentState,
					lhnComponentModel,
					lhnComponentSerialNumber,
					lhnComponentFirmwareVersion,
					lhnDiskInterface,
					lhnDiskCapacity,
					lhnHealthState,
					lhnTemperatureState,
					lhnTemperature,
					lhnDiskSpeed,
					lhnWarrantyPartNumber,
					lhnWarrantySerialNumber,
					lhnWarrantyLicenseNumber,
					lhnWearState,
					lhnWearDays,
					lhnWearPercent
			}
	STATUS              current
	DESCRIPTION         "An event for a disk was generated.
						The user chose to be notified of this condition
						via SNMP. A table of messages exists which stores
						all the notifications issued. This trap will
						contain the OID referring to the corresponding
						message stored in this table.
						Added in SAN/iQ 8.5"
	::= { lhnNsmEvents 5 }

lhnNsmNotificationBootDevice NOTIFICATION-TYPE
	OBJECTS {
					lhnMessage,
					lhnMessageTime,
					lhnEventID,
					lhnSeverity,
					lhnHostname,
					lhnPrimaryIP,
					lhnMac,
					lhnSerialNumber,
					lhnModelName,
					lhnProductName,
					lhnProductID,
					lhnHpim,
					lhnSoftwareVersion,
					lhnManagementGroupVersion,
					lhnManagementGroupSerialNumber,
					lhnManagementGroup,
					lhnCluster,
					lhnSite,
					lhnComponentName,
					lhnComponentState,
					lhnWarrantyPartNumber,
					lhnWarrantySerialNumber,
					lhnWarrantyLicenseNumber
			}
	STATUS              current
	DESCRIPTION         "An event for a boot device was generated.
						The user chose to be notified of this condition
						via SNMP. A table of messages exists which stores
						all the notifications issued. This trap will
						contain the OID referring to the corresponding
						message stored in this table.
						Added in SAN/iQ 8.5"
	::= { lhnNsmEvents 6 }

lhnNsmNotificationFan NOTIFICATION-TYPE
	OBJECTS {
					lhnMessage,
					lhnMessageTime,
					lhnEventID,
					lhnSeverity,
					lhnHostname,
					lhnPrimaryIP,
					lhnMac,
					lhnSerialNumber,
					lhnModelName,
					lhnProductName,
					lhnProductID,
					lhnHpim,
					lhnSoftwareVersion,
					lhnManagementGroupVersion,
					lhnManagementGroupSerialNumber,
					lhnManagementGroup,
					lhnCluster,
					lhnSite,
					lhnComponentName,
					lhnComponentState,
					lhnMinFanSpeed,
					lhnFanSpeed,
					lhnWarrantyPartNumber,
					lhnWarrantySerialNumber,
					lhnWarrantyLicenseNumber
			}
	STATUS              current
	DESCRIPTION         "An event for a fan was generated.
						The user chose to be notified of this condition
						via SNMP. A table of messages exists which stores
						all the notifications issued. This trap will
						contain the OID referring to the corresponding
						message stored in this table.
						Added in SAN/iQ 8.5"
	::= { lhnNsmEvents 7 }

lhnNsmNotificationTemperature NOTIFICATION-TYPE
	OBJECTS {
					lhnMessage,
					lhnMessageTime,
					lhnEventID,
					lhnSeverity,
					lhnHostname,
					lhnPrimaryIP,
					lhnMac,
					lhnSerialNumber,
					lhnModelName,
					lhnProductName,
					lhnProductID,
					lhnHpim,
					lhnSoftwareVersion,
					lhnManagementGroupVersion,
					lhnManagementGroupSerialNumber,
					lhnManagementGroup,
					lhnCluster,
					lhnSite,
					lhnComponentName,
					lhnComponentState,
					lhnHighTemperatureLimit,
					lhnTemperature,
					lhnWarrantyPartNumber,
					lhnWarrantySerialNumber,
					lhnWarrantyLicenseNumber
			}
	STATUS              current
	DESCRIPTION         "An event for a temperature sensor was generated.
						The user chose to be notified of this condition
						via SNMP. A table of messages exists which stores
						all the notifications issued. This trap will
						contain the OID referring to the corresponding
						message stored in this table.
						Added in SAN/iQ 8.5"
	::= { lhnNsmEvents 8 }

lhnNsmNotificationPowerSupply NOTIFICATION-TYPE
	OBJECTS {
					lhnMessage,
					lhnMessageTime,
					lhnEventID,
					lhnSeverity,
					lhnHostname,
					lhnPrimaryIP,
					lhnMac,
					lhnSerialNumber,
					lhnModelName,
					lhnProductName,
					lhnProductID,
					lhnHpim,
					lhnSoftwareVersion,
					lhnManagementGroupVersion,
					lhnManagementGroupSerialNumber,
					lhnManagementGroup,
					lhnCluster,
					lhnSite,
					lhnComponentName,
					lhnComponentState,
					lhnWarrantyPartNumber,
					lhnWarrantySerialNumber,
					lhnWarrantyLicenseNumber
			}
	STATUS              current
	DESCRIPTION         "An event for a power supply was generated.
						The user chose to be notified of this condition
						via SNMP. A table of messages exists which stores
						all the notifications issued. This trap will
						contain the OID referring to the corresponding
						message stored in this table.
						Added in SAN/iQ 8.5"
	::= { lhnNsmEvents 9 }

lhnNsmNotificationVoltage NOTIFICATION-TYPE
	OBJECTS {
					lhnMessage,
					lhnMessageTime,
					lhnEventID,
					lhnSeverity,
					lhnHostname,
					lhnPrimaryIP,
					lhnMac,
					lhnSerialNumber,
					lhnModelName,
					lhnProductName,
					lhnProductID,
					lhnHpim,
					lhnSoftwareVersion,
					lhnManagementGroupVersion,
					lhnManagementGroupSerialNumber,
					lhnManagementGroup,
					lhnCluster,
					lhnSite,
					lhnComponentName,
					lhnComponentState,
					lhnHighVoltageLimit,
					lhnLowVoltageLimit,
					lhnVoltage,
					lhnWarrantyPartNumber,
					lhnWarrantySerialNumber,
					lhnWarrantyLicenseNumber
			}
	STATUS              current
	DESCRIPTION         "An event for a voltage sensor was generated.
						The user chose to be notified of this condition
						via SNMP. A table of messages exists which stores
						all the notifications issued. This trap will
						contain the OID referring to the corresponding
						message stored in this table.
						Added in SAN/iQ 8.5"
	::= { lhnNsmEvents 10 }

lhnNsmNotificationNetwork NOTIFICATION-TYPE
	OBJECTS {
					lhnMessage,
					lhnMessageTime,
					lhnEventID,
					lhnSeverity,
					lhnHostname,
					lhnPrimaryIP,
					lhnMac,
					lhnSerialNumber,
					lhnModelName,
					lhnProductName,
					lhnProductID,
					lhnHpim,
					lhnSoftwareVersion,
					lhnManagementGroupVersion,
					lhnManagementGroupSerialNumber,
					lhnManagementGroup,
					lhnCluster,
					lhnSite,
					lhnSystemName,
					lhnLogicalName,
					lhnLinkState,
					lhnWarrantyPartNumber,
					lhnWarrantySerialNumber,
					lhnWarrantyLicenseNumber
			}
	STATUS              current
	DESCRIPTION         "An event for the network was generated.
						The user chose to be notified of this condition
						via SNMP. A table of messages exists which stores
						all the notifications issued. This trap will
						contain the OID referring to the corresponding
						message stored in this table.
						Added in SAN/iQ 8.5"
	::= { lhnNsmEvents 11 }

lhnNsmNotificationMemory NOTIFICATION-TYPE
	OBJECTS {
					lhnMessage,
					lhnMessageTime,
					lhnEventID,
					lhnSeverity,
					lhnHostname,
					lhnPrimaryIP,
					lhnMac,
					lhnSerialNumber,
					lhnModelName,
					lhnProductName,
					lhnProductID,
					lhnHpim,
					lhnSoftwareVersion,
					lhnManagementGroupVersion,
					lhnManagementGroupSerialNumber,
					lhnManagementGroup,
					lhnCluster,
					lhnSite,
					lhnMemoryConfig,
					lhnMemoryUtilization,
					lhnWarrantyPartNumber,
					lhnWarrantySerialNumber,
					lhnWarrantyLicenseNumber
			}
	STATUS              current
	DESCRIPTION         "An event for the system memory was generated.
						The user chose to be notified of this condition
						via SNMP. A table of messages exists which stores
						all the notifications issued. This trap will
						contain the OID referring to the corresponding
						message stored in this table.
						Added in SAN/iQ 8.5"
	::= { lhnNsmEvents 12 }

lhnNsmNotificationCPU NOTIFICATION-TYPE
	OBJECTS {
					lhnMessage,
					lhnMessageTime,
					lhnEventID,
					lhnSeverity,
					lhnHostname,
					lhnPrimaryIP,
					lhnMac,
					lhnSerialNumber,
					lhnModelName,
					lhnProductName,
					lhnProductID,
					lhnHpim,
					lhnSoftwareVersion,
					lhnManagementGroupVersion,
					lhnManagementGroupSerialNumber,
					lhnManagementGroup,
					lhnCluster,
					lhnSite,
					lhnCpuConfig,
					lhnCpuUtilization,
					lhnWarrantyPartNumber,
					lhnWarrantySerialNumber,
					lhnWarrantyLicenseNumber
			}
	STATUS              current
	DESCRIPTION         "An event for the CPU was generated.
						The user chose to be notified of this condition
						via SNMP. A table of messages exists which stores
						all the notifications issued. This trap will
						contain the OID referring to the corresponding
						message stored in this table.
						Added in SAN/iQ 8.5"
	::= { lhnNsmEvents 13 }

lhnNsmNotificationLogging NOTIFICATION-TYPE
	OBJECTS {
					lhnMessage,
					lhnMessageTime,
					lhnEventID,
					lhnSeverity,
					lhnHostname,
					lhnPrimaryIP,
					lhnMac,
					lhnSerialNumber,
					lhnModelName,
					lhnProductName,
					lhnProductID,
					lhnHpim,
					lhnSoftwareVersion,
					lhnManagementGroupVersion,
					lhnManagementGroupSerialNumber,
					lhnManagementGroup,
					lhnCluster,
					lhnSite,
					lhnUtilization
			}
	STATUS              current
	DESCRIPTION         "An event for the log partition was generated.
						The user chose to be notified of this condition
						via SNMP. A table of messages exists which stores
						all the notifications issued. This trap will
						contain the OID referring to the corresponding
						message stored in this table.
						Added in SAN/iQ 8.5"
	::= { lhnNsmEvents 14 }

lhnNsmNotificationManagementGroup NOTIFICATION-TYPE
	OBJECTS {
					lhnMessage,
					lhnMessageTime,
					lhnEventID,
					lhnSeverity,
					lhnHostname,
					lhnPrimaryIP,
					lhnMac,
					lhnSerialNumber,
					lhnModelName,
					lhnProductName,
					lhnProductID,
					lhnHpim,
					lhnSoftwareVersion,
					lhnManagementGroupVersion,
					lhnManagementGroupSerialNumber,
					lhnManagementGroup,
					lhnCluster,
					lhnSite,
					lhnComponentName,
					lhnMaintenanceMode,
					lhnLicenseState
			}
	STATUS              current
	DESCRIPTION         "An event for the management group was generated.
						The user chose to be notified of this condition
						via SNMP. A table of messages exists which stores
						all the notifications issued. This trap will
						contain the OID referring to the corresponding
						message stored in this table.
						Added in SAN/iQ 8.5"
	::= { lhnNsmEvents 15 }

lhnNsmNotificationRemoteManagementGroup NOTIFICATION-TYPE
	OBJECTS {
					lhnMessage,
					lhnMessageTime,
					lhnEventID,
					lhnSeverity,
					lhnHostname,
					lhnPrimaryIP,
					lhnMac,
					lhnSerialNumber,
					lhnModelName,
					lhnProductName,
					lhnProductID,
					lhnHpim,
					lhnSoftwareVersion,
					lhnManagementGroupVersion,
					lhnManagementGroupSerialNumber,
					lhnManagementGroup,
					lhnCluster,
					lhnSite,
					lhnComponentName,
					lhnComponentState
			}
	STATUS              current
	DESCRIPTION         "An event for a remote management group was generated.
						The user chose to be notified of this condition
						via SNMP. A table of messages exists which stores
						all the notifications issued. This trap will
						contain the OID referring to the corresponding
						message stored in this table.
						Added in SAN/iQ 8.5"
	::= { lhnNsmEvents 16 }

lhnNsmNotificationCluster NOTIFICATION-TYPE
	OBJECTS {
					lhnMessage,
					lhnMessageTime,
					lhnEventID,
					lhnSeverity,
					lhnHostname,
					lhnPrimaryIP,
					lhnMac,
					lhnSerialNumber,
					lhnModelName,
					lhnProductName,
					lhnProductID,
					lhnHpim,
					lhnSoftwareVersion,
					lhnManagementGroupVersion,
					lhnManagementGroupSerialNumber,
					lhnManagementGroup,
					lhnCluster,
					lhnSite,
					lhnUtilization,
					lhnVipState,
					lhnUtilizationState
			}
	STATUS              current
	DESCRIPTION         "An event for the cluster was generated.
						The user chose to be notified of this condition
						via SNMP. A table of messages exists which stores
						all the notifications issued. This trap will
						contain the OID referring to the corresponding
						message stored in this table.
						Added in SAN/iQ 8.5"
	::= { lhnNsmEvents 17 }

lhnNsmNotificationStorageServer NOTIFICATION-TYPE
	OBJECTS {
					lhnMessage,
					lhnMessageTime,
					lhnEventID,
					lhnSeverity,
					lhnHostname,
					lhnPrimaryIP,
					lhnMac,
					lhnSerialNumber,
					lhnModelName,
					lhnProductName,
					lhnProductID,
					lhnHpim,
					lhnSoftwareVersion,
					lhnManagementGroupVersion,
					lhnManagementGroupSerialNumber,
					lhnManagementGroup,
					lhnCluster,
					lhnSite,
					lhnComponentName,
					lhnComponentState,
					lhnLatency,
					lhnLatencyState,
					lhnServerVIPAddress,
					lhnServerVIPState
			}
	STATUS              current
	DESCRIPTION         "An event for the storage server was generated.
						The user chose to be notified of this condition
						via SNMP. A table of messages exists which stores
						all the notifications issued. This trap will
						contain the OID referring to the corresponding
						message stored in this table.
						Added in SAN/iQ 8.5"
	::= { lhnNsmEvents 18 }

lhnNsmNotificationRemoteCopy NOTIFICATION-TYPE
	OBJECTS {
					lhnMessage,
					lhnMessageTime,
					lhnEventID,
					lhnSeverity,
					lhnHostname,
					lhnPrimaryIP,
					lhnMac,
					lhnSerialNumber,
					lhnModelName,
					lhnProductName,
					lhnProductID,
					lhnHpim,
					lhnSoftwareVersion,
					lhnManagementGroupVersion,
					lhnManagementGroupSerialNumber,
					lhnManagementGroup,
					lhnCluster,
					lhnSite,
					lhnComponentName,
					lhnComponentState,
					lhnReplicationState
			}
	STATUS              current
	DESCRIPTION         "An event for a remote copy operation was generated.
						The user chose to be notified of this condition
						via SNMP. A table of messages exists which stores
						all the notifications issued. This trap will
						contain the OID referring to the corresponding
						message stored in this table.
						Added in SAN/iQ 8.5"
	::= { lhnNsmEvents 19 }

lhnNsmNotificationVolume NOTIFICATION-TYPE
	OBJECTS {
					lhnMessage,
					lhnMessageTime,
					lhnEventID,
					lhnSeverity,
					lhnHostname,
					lhnPrimaryIP,
					lhnMac,
					lhnSerialNumber,
					lhnModelName,
					lhnProductName,
					lhnProductID,
					lhnHpim,
					lhnSoftwareVersion,
					lhnManagementGroupVersion,
					lhnManagementGroupSerialNumber,
					lhnManagementGroup,
					lhnCluster,
					lhnSite,
					lhnComponentName,
					lhnComponentState
			}
	STATUS              current
	DESCRIPTION         "An event for a volume was generated.
						The user chose to be notified of this condition
						via SNMP. A table of messages exists which stores
						all the notifications issued. This trap will
						contain the OID referring to the corresponding
						message stored in this table.
						Added in SAN/iQ 8.5"
	::= { lhnNsmEvents 20 }

lhnNsmNotificationSnapshot NOTIFICATION-TYPE
	OBJECTS {
					lhnMessage,
					lhnMessageTime,
					lhnEventID,
					lhnSeverity,
					lhnHostname,
					lhnPrimaryIP,
					lhnMac,
					lhnSerialNumber,
					lhnModelName,
					lhnProductName,
					lhnProductID,
					lhnHpim,
					lhnSoftwareVersion,
					lhnManagementGroupVersion,
					lhnManagementGroupSerialNumber,
					lhnManagementGroup,
					lhnCluster,
					lhnSite,
					lhnComponentName,
					lhnComponentState,
					lhnSnapshotState
			}
	STATUS              current
	DESCRIPTION         "An event for a snapshot was generated.
						The user chose to be notified of this condition
						via SNMP. A table of messages exists which stores
						all the notifications issued. This trap will
						contain the OID referring to the corresponding
						message stored in this table.
						Added in SAN/iQ 8.5"
	::= { lhnNsmEvents 21 }

lhnNsmNotificationSnapshotSchedule NOTIFICATION-TYPE
	OBJECTS {
					lhnMessage,
					lhnMessageTime,
					lhnEventID,
					lhnSeverity,
					lhnHostname,
					lhnPrimaryIP,
					lhnMac,
					lhnSerialNumber,
					lhnModelName,
					lhnProductName,
					lhnProductID,
					lhnHpim,
					lhnSoftwareVersion,
					lhnManagementGroupVersion,
					lhnManagementGroupSerialNumber,
					lhnManagementGroup,
					lhnCluster,
					lhnSite,
					lhnComponentName,
					lhnComponentState,
					lhnSnapshotSchedState
			}
	STATUS              current
	DESCRIPTION         "An event for a snapshot schedule was generated.
						The user chose to be notified of this condition
						via SNMP. A table of messages exists which stores
						all the notifications issued. This trap will
						contain the OID referring to the corresponding
						message stored in this table.
						Added in SAN/iQ 9.0"
	::= { lhnNsmEvents 22 }

lhnNsmNotificationManager NOTIFICATION-TYPE
	OBJECTS {
					lhnMessage,
					lhnMessageTime,
					lhnEventID,
					lhnSeverity,
					lhnHostname,
					lhnPrimaryIP,
					lhnMac,
					lhnSerialNumber,
					lhnModelName,
					lhnProductName,
					lhnProductID,
					lhnHpim,
					lhnSoftwareVersion,
					lhnManagementGroupVersion,
					lhnManagementGroupSerialNumber,
					lhnManagementGroup,
					lhnCluster,
					lhnSite,
					lhnComponentName,
					lhnComponentState
			}
	STATUS              current
	DESCRIPTION         "An event for a manager was generated.
						The user chose to be notified of this condition
						via SNMP. A table of messages exists which stores
						all the notifications issued. This trap will
						contain the OID referring to the corresponding
						message stored in this table.
						Added in SAN/iQ 9.0"
	::= { lhnNsmEvents 23 }

lhnNsmNotificationVirtualManager NOTIFICATION-TYPE
	OBJECTS {
					lhnMessage,
					lhnMessageTime,
					lhnEventID,
					lhnSeverity,
					lhnHostname,
					lhnPrimaryIP,
					lhnMac,
					lhnSerialNumber,
					lhnModelName,
					lhnProductName,
					lhnProductID,
					lhnHpim,
					lhnSoftwareVersion,
					lhnManagementGroupVersion,
					lhnManagementGroupSerialNumber,
					lhnManagementGroup,
					lhnCluster,
					lhnSite,
					lhnComponentName,
					lhnComponentState
			}
	STATUS              current
	DESCRIPTION         "An event for a virtual manager was generated.
						The user chose to be notified of this condition
						via SNMP. A table of messages exists which stores
						all the notifications issued. This trap will
						contain the OID referring to the corresponding
						message stored in this table.
						Added in SAN/iQ 9.0"
	::= { lhnNsmEvents 24 }

lhnNsmNotificationFailoverManager NOTIFICATION-TYPE
	OBJECTS {
					lhnMessage,
					lhnMessageTime,
					lhnEventID,
					lhnSeverity,
					lhnHostname,
					lhnPrimaryIP,
					lhnMac,
					lhnSerialNumber,
					lhnModelName,
					lhnProductName,
					lhnProductID,
					lhnHpim,
					lhnSoftwareVersion,
					lhnManagementGroupVersion,
					lhnManagementGroupSerialNumber,
					lhnManagementGroup,
					lhnCluster,
					lhnSite,
					lhnComponentName,
					lhnComponentState
			}
	STATUS              current
	DESCRIPTION         "An event for a failover manager was generated.
						The user chose to be notified of this condition
						via SNMP. A table of messages exists which stores
						all the notifications issued. This trap will
						contain the OID referring to the corresponding
						message stored in this table.
						Added in SAN/iQ 9.0"
	::= { lhnNsmEvents 25 }

lhnNsmNotificationConfiguration NOTIFICATION-TYPE
	OBJECTS {
					lhnMessage,
					lhnMessageTime,
					lhnEventID,
					lhnSeverity,
					lhnHostname,
					lhnPrimaryIP,
					lhnMac,
					lhnSerialNumber,
					lhnModelName,
					lhnProductName,
					lhnProductID,
					lhnHpim,
					lhnSoftwareVersion,
					lhnManagementGroupVersion,
					lhnManagementGroupSerialNumber,
					lhnManagementGroup,
					lhnCluster,
					lhnSite
			}
	STATUS              current
	DESCRIPTION         "An event for system configuration was generated.
						The user chose to be notified of this condition
						via SNMP. A table of messages exists which stores
						all the notifications issued. This trap will
						contain the OID referring to the corresponding
						message stored in this table.
						Added in SAN/iQ 9.0"
	::= { lhnNsmEvents 26 }

lhnNsmNotificationResource NOTIFICATION-TYPE
	OBJECTS {
					lhnMessage,
					lhnMessageTime,
					lhnEventID,
					lhnSeverity,
					lhnHostname,
					lhnPrimaryIP,
					lhnMac,
					lhnSerialNumber,
					lhnModelName,
					lhnProductName,
					lhnProductID,
					lhnHpim,
					lhnSoftwareVersion,
					lhnManagementGroupVersion,
					lhnManagementGroupSerialNumber,
					lhnManagementGroup,
					lhnCluster,
					lhnSite
			}
	STATUS              current
	DESCRIPTION         "An event for a system resource was generated.
						The user chose to be notified of this condition
						via SNMP. A table of messages exists which stores
						all the notifications issued. This trap will
						contain the OID referring to the corresponding
						message stored in this table.
						Added in SAN/iQ 9.0"
	::= { lhnNsmEvents 27 }

lhnNsmNotificationService NOTIFICATION-TYPE
	OBJECTS {
					lhnMessage,
					lhnMessageTime,
					lhnEventID,
					lhnSeverity,
					lhnHostname,
					lhnPrimaryIP,
					lhnMac,
					lhnSerialNumber,
					lhnModelName,
					lhnProductName,
					lhnProductID,
					lhnHpim,
					lhnSoftwareVersion,
					lhnManagementGroupVersion,
					lhnManagementGroupSerialNumber,
					lhnManagementGroup,
					lhnCluster,
					lhnSite
			}
	STATUS              current
	DESCRIPTION         "An event for a system service was generated.
						The user chose to be notified of this condition
						via SNMP. A table of messages exists which stores
						all the notifications issued. This trap will
						contain the OID referring to the corresponding
						message stored in this table.
						Added in SAN/iQ 9.0"
	::= { lhnNsmEvents 28 }

lhnNsmNotificationMountPoint NOTIFICATION-TYPE
	OBJECTS {
					lhnMessage,
					lhnMessageTime,
					lhnEventID,
					lhnSeverity,
					lhnHostname,
					lhnPrimaryIP,
					lhnMac,
					lhnSerialNumber,
					lhnModelName,
					lhnProductName,
					lhnProductID,
					lhnHpim,
					lhnSoftwareVersion,
					lhnManagementGroupVersion,
					lhnManagementGroupSerialNumber,
					lhnManagementGroup,
					lhnCluster,
					lhnSite
			}
	STATUS              current
	DESCRIPTION         "An event for a mount point was generated.
						The user chose to be notified of this condition
						via SNMP. A table of messages exists which stores
						all the notifications issued. This trap will
						contain the OID referring to the corresponding
						message stored in this table.
						Added in SAN/iQ 9.0"
	::= { lhnNsmEvents 29 }

lhnNsmNotificationPartition NOTIFICATION-TYPE
	OBJECTS {
					lhnMessage,
					lhnMessageTime,
					lhnEventID,
					lhnSeverity,
					lhnHostname,
					lhnPrimaryIP,
					lhnMac,
					lhnSerialNumber,
					lhnModelName,
					lhnProductName,
					lhnProductID,
					lhnHpim,
					lhnSoftwareVersion,
					lhnManagementGroupVersion,
					lhnManagementGroupSerialNumber,
					lhnManagementGroup,
					lhnCluster,
					lhnSite
			}
	STATUS              current
	DESCRIPTION         "An event for a partition was generated.
						The user chose to be notified of this condition
						via SNMP. A table of messages exists which stores
						all the notifications issued. This trap will
						contain the OID referring to the corresponding
						message stored in this table.
						Added in SAN/iQ 9.0"
	::= { lhnNsmEvents 30 }

--******************************************************************************
--
-- Obsolete Notifications
--
--******************************************************************************

lhnNotificationOldMessageCount OBJECT-TYPE
    SYNTAX              Integer32
    MAX-ACCESS          read-only
    STATUS              current
    DESCRIPTION         "number of notification messages
						Used by SAN/iQ 8.1 and earlier.
						Obsolete in SAN/iQ 8.5.
						Marked as current to increase compatability with some SNMP clients."
    ::= { lhnNsmOldNotification 1 }

lhnNotificationOldMessageTable OBJECT-TYPE
    SYNTAX              SEQUENCE OF LhnNotificationOldMessageEntry
    MAX-ACCESS          not-accessible
    STATUS              current
    DESCRIPTION         "A table of notification messages for the NSM.
                        The number of entries is given by notificationMessageCount.
						Used by SAN/iQ 8.1 and earlier.
						Obsolete in SAN/iQ 8.5.
						Marked as current to increase compatability with some SNMP clients."
    ::= { lhnNsmOldNotification 2 }

    lhnNotificationOldMessageEntry OBJECT-TYPE
        SYNTAX              LhnNotificationOldMessageEntry
        MAX-ACCESS          not-accessible
        STATUS              current
        DESCRIPTION         "row of notification message parameters
							Used by SAN/iQ 8.1 and earlier.
							Obsolete in SAN/iQ 8.5.
							Marked as current to increase compatability with some SNMP clients."
        INDEX               {
                                lhnNotificationIndex
                            }
        ::= { lhnNotificationOldMessageTable 1 }

    LhnNotificationOldMessageEntry ::= SEQUENCE {
        lhnNotificationIndex
            Unsigned32,
        lhnNotificationMessage
            DisplayString,
        lhnNotificationTime
            DateAndTime
    }

    lhnNotificationIndex OBJECT-TYPE
        SYNTAX              Unsigned32
        MAX-ACCESS          not-accessible
        STATUS              current
        DESCRIPTION         "notification message index
							Used by SAN/iQ 8.1 and earlier.
							Obsolete in SAN/iQ 8.5.
							Marked as current to increase compatability with some SNMP clients."
        ::= { lhnNotificationOldMessageEntry 1 }

    lhnNotificationMessage OBJECT-TYPE
        SYNTAX              DisplayString
        MAX-ACCESS          read-only
        STATUS              current
        DESCRIPTION         "notification message contents
							Used by SAN/iQ 8.1 and earlier.
							Obsolete in SAN/iQ 8.5.
							Marked as current to increase compatability with some SNMP clients."
        ::= { lhnNotificationOldMessageEntry 2 }

    lhnNotificationTime OBJECT-TYPE
        SYNTAX              DateAndTime
        MAX-ACCESS          read-only
        STATUS              current
        DESCRIPTION         "time notification occurred
							Used by SAN/iQ 8.1 and earlier.
							Obsolete in SAN/iQ 8.5.
							Marked as current to increase compatability with some SNMP clients."
        ::= { lhnNotificationOldMessageEntry 3 }

lhnUserNotification NOTIFICATION-TYPE
	OBJECTS {
					lhnNotificationMessage,
					lhnNotificationTime
			}
	STATUS              current
	DESCRIPTION         "A system event was generated.
						The user chose to be notified of this condition
						via SNMP. A table of messages exists which stores
						all the notifications issued. This trap will
						contain the OID referring to the corresponding
						message stored in this table.
						Used by SAN/iQ 8.1 and earlier.
						Obsolete in SAN/iQ 8.5.
						Marked as current to increase compatability with some SNMP clients."
	::= { lhnNsmOldEvents 1 }

END

-- END: some MIB compilers require a CR/LF after the END statement --
