-- =====================================================================
-- Copyright (c) 2010-2013 Hewlett-Packard Development Company, L.P.
--
-- Description: Timerange MIB Definition
-- Reference:
-- Version: V1.3
-- History:
--   V1.0 Yang Hongjie,2003-04-11,Initial Version
--   v1.1 modify follow node define:
--        hpnicfTrngPeriodicDayOfWeek,hpnicfTrngCreateRowStatus
--        hpnicfTimerangeAbsolueRowStatus,hpnicfTimerangePeriodicRowStatus
--   V1.2 2004-10-12 updated by gaolong
--        Change DESCRIPTION syntax format of hpnicfTRNG and hpnicfTrngCreateTimerangeTable.
--        Change hpnicfTrngPeriodicDayofWeek to hpnicfTrngPeriodicDayOfWeek. This is
--        a word error.
--   V1.3 2005-2-5 updated by zhangjie
--        Correct word error for 'wednesday'.
--      Adjust the file format
-- =====================================================================
HPN-ICF-TRNG-MIB DEFINITIONS ::= BEGIN

        IMPORTS
            hpnicfRhw
                FROM HPN-ICF-OID-MIB
            OBJECT-GROUP, MODULE-COMPLIANCE
                FROM SNMPv2-CONF
            Integer32, OBJECT-TYPE, MODULE-IDENTITY
                FROM SNMPv2-SMI
            TruthValue, DateAndTime, RowStatus
                FROM SNMPv2-TC;


        hpnicfTRNG MODULE-IDENTITY
            LAST-UPDATED "200304110000Z"        -- April 11, 2003 at 00:00 GMT
            ORGANIZATION
                ""
            CONTACT-INFO
                ""
            DESCRIPTION
                "The HPN-ICF-TRNG-MIB contains objects to
                Configure the system absolute and periodic time-range."
            REVISION "200304110000Z"        -- April 11, 2003 at 00:00 GMT
            DESCRIPTION
                "200304110000Z, --The initial revision of this MIB module."
            ::= { hpnicfRhw 13 }


--
-- Node definitions
--

        hpnicfTRNGMibObjects OBJECT IDENTIFIER ::= { hpnicfTRNG 1 }


        hpnicfTrngCreateTimerangeTable OBJECT-TYPE
            SYNTAX SEQUENCE OF HpnicfTrngCreateTimerangeEntry
            MAX-ACCESS not-accessible
            STATUS current
            DESCRIPTION
                              "Creat TimeRange."
            ::= { hpnicfTRNGMibObjects 1 }


        hpnicfTrngCreateTimerangeEntry OBJECT-TYPE
            SYNTAX HpnicfTrngCreateTimerangeEntry
            MAX-ACCESS not-accessible
            STATUS current
            DESCRIPTION
                "Define the entry of hpnicfTrngCreateTimerangeTable"
            INDEX { hpnicfTrngIndex }
            ::= { hpnicfTrngCreateTimerangeTable 1 }


        HpnicfTrngCreateTimerangeEntry ::=
            SEQUENCE {
                hpnicfTrngIndex
                    Integer32,
                hpnicfTrngName
                    OCTET STRING,
                hpnicfTrngValidFlag
                    TruthValue,
                hpnicfTrngCreateRowStatus
                    RowStatus
             }

        hpnicfTrngIndex OBJECT-TYPE
            SYNTAX Integer32 (1..256)
            MAX-ACCESS not-accessible
            STATUS current
            DESCRIPTION
                "TimeRange's index"
            ::= { hpnicfTrngCreateTimerangeEntry 1 }


        hpnicfTrngName OBJECT-TYPE
            SYNTAX OCTET STRING (SIZE (1..32))
            MAX-ACCESS read-create
            STATUS current
            DESCRIPTION
                "TimeRange's name"
            ::= { hpnicfTrngCreateTimerangeEntry 2 }


        hpnicfTrngValidFlag OBJECT-TYPE
            SYNTAX TruthValue
            MAX-ACCESS read-only
            STATUS current
            DESCRIPTION
                "Valid or Invalid flag"
            ::= { hpnicfTrngCreateTimerangeEntry 3 }


        hpnicfTrngCreateRowStatus OBJECT-TYPE
            SYNTAX RowStatus
            MAX-ACCESS read-create
            STATUS current
            DESCRIPTION
                "The status of this conceptual row.Now only realize CreateAndGo and Destroy and Active."
            ::= { hpnicfTrngCreateTimerangeEntry 4 }


        hpnicfTrngAbsoluteTable OBJECT-TYPE
            SYNTAX SEQUENCE OF HpnicfTrngAbsoluteEntry
            MAX-ACCESS not-accessible
            STATUS current
            DESCRIPTION
                "Creat absoluteness time item of the TimeRange"
            ::= { hpnicfTRNGMibObjects 2 }


        hpnicfTrngAbsoluteEntry OBJECT-TYPE
            SYNTAX HpnicfTrngAbsoluteEntry
            MAX-ACCESS not-accessible
            STATUS current
            DESCRIPTION
                "Define the entry of hpnicfTrngAbsoluteTable"
            INDEX { hpnicfTrngAbsoluteNameIndex, hpnicfTrngAbsoluteSubIndex }
            ::= { hpnicfTrngAbsoluteTable 1 }


        HpnicfTrngAbsoluteEntry ::=
            SEQUENCE {
                hpnicfTrngAbsoluteNameIndex
                    Integer32,
                hpnicfTrngAbsoluteSubIndex
                    Integer32,
                hpnicfTimerangeAbsoluteStartTime
                    DateAndTime,
                hpnicfTimerangeAbsoluteEndTime
                    DateAndTime,
                hpnicfTimerangeAbsolueRowStatus
                    RowStatus
             }

        hpnicfTrngAbsoluteNameIndex OBJECT-TYPE
            SYNTAX Integer32 (1..256)
            MAX-ACCESS not-accessible
            STATUS current
            DESCRIPTION
                "TimeRange's index"
            ::= { hpnicfTrngAbsoluteEntry 1 }


        hpnicfTrngAbsoluteSubIndex OBJECT-TYPE
            SYNTAX Integer32 (1..12)
            MAX-ACCESS not-accessible
            STATUS current
            DESCRIPTION
                "SubItem's index"
            ::= { hpnicfTrngAbsoluteEntry 2 }


        hpnicfTimerangeAbsoluteStartTime OBJECT-TYPE
            SYNTAX DateAndTime
            MAX-ACCESS read-create
            STATUS current
            DESCRIPTION
                "Start point of the timerange.The format defined like 'YYYY-MM-DD,hh:mm:0.0'."
            ::= { hpnicfTrngAbsoluteEntry 3 }


        hpnicfTimerangeAbsoluteEndTime OBJECT-TYPE
            SYNTAX DateAndTime
            MAX-ACCESS read-create
            STATUS current
            DESCRIPTION
                "End point of the timerange.The format defined like 'YYYY-MM-DD,hh:mm:0.0'."
            ::= { hpnicfTrngAbsoluteEntry 4 }


        hpnicfTimerangeAbsolueRowStatus OBJECT-TYPE
            SYNTAX RowStatus
            MAX-ACCESS read-create
            STATUS current
            DESCRIPTION
                "The status of this conceptual row. Now only realize CreateAndGo and Destroy and Active."
            ::= { hpnicfTrngAbsoluteEntry 5 }


        hpnicfTrngPeriodicTable OBJECT-TYPE
            SYNTAX SEQUENCE OF HpnicfTrngPeriodicEntry
            MAX-ACCESS not-accessible
            STATUS current
            DESCRIPTION
                "Creat periodic time item of the TimeRange"
            ::= { hpnicfTRNGMibObjects 3 }


        hpnicfTrngPeriodicEntry OBJECT-TYPE
            SYNTAX HpnicfTrngPeriodicEntry
            MAX-ACCESS not-accessible
            STATUS current
            DESCRIPTION
                "Define the index of hpnicfTrngPeriodicTable"
            INDEX { hpnicfTrngPeriodicNameIndex, hpnicfTrngPeriodicSubIndex }
            ::= { hpnicfTrngPeriodicTable 1 }


        HpnicfTrngPeriodicEntry ::=
            SEQUENCE {
                hpnicfTrngPeriodicNameIndex
                    Integer32,
                hpnicfTrngPeriodicSubIndex
                    Integer32,
                hpnicfTrngPeriodicDayOfWeek
                    BITS,
                hpnicfTimerangePeriodicStartTime
                    DateAndTime,
                hpnicfTimerangePeriodicEndTime
                    DateAndTime,
                hpnicfTimerangePeriodicRowStatus
                    RowStatus
             }

        hpnicfTrngPeriodicNameIndex OBJECT-TYPE
            SYNTAX Integer32 (1..256)
            MAX-ACCESS not-accessible
            STATUS current
            DESCRIPTION
                "TimeRange's index"
            ::= { hpnicfTrngPeriodicEntry 1 }


        hpnicfTrngPeriodicSubIndex OBJECT-TYPE
            SYNTAX Integer32 (1..32)
            MAX-ACCESS not-accessible
            STATUS current
            DESCRIPTION
                "SubItem's index"
            ::= { hpnicfTrngPeriodicEntry 2 }


        hpnicfTrngPeriodicDayOfWeek OBJECT-TYPE
            SYNTAX BITS {
                                      sunday(0),
                                      monday(1),
                                      tuesday(2),
                                      wednesday(3),
                                      thursday(4),
                                      friday(5),
                                      saturday(6)
                                      }
            MAX-ACCESS read-create
            STATUS current
            DESCRIPTION
                "The day of week. This is a bit-map of possible conditions.
                The various bit positions are:
                |0        |sunday                    |
                |1        |monday                 |
                |2        |tuesday                |
                |3        |wednesday              |
                |4        |thursday               |
                |5        |friday                 |
                |6        |saturday               |
                "
            ::= { hpnicfTrngPeriodicEntry 3 }


        hpnicfTimerangePeriodicStartTime OBJECT-TYPE
            SYNTAX DateAndTime
            MAX-ACCESS read-create
            STATUS current
            DESCRIPTION
                "Start point of this timerange,The format defined like 'hh:mm:0,0'."
            ::= { hpnicfTrngPeriodicEntry 4 }


        hpnicfTimerangePeriodicEndTime OBJECT-TYPE
            SYNTAX DateAndTime
            MAX-ACCESS read-create
            STATUS current
            DESCRIPTION
                "End point of this timerange. The format definedlike 'hh:mm:0,0'."
            ::= { hpnicfTrngPeriodicEntry 5 }


        hpnicfTimerangePeriodicRowStatus OBJECT-TYPE
            SYNTAX RowStatus
            MAX-ACCESS read-create
            STATUS current
            DESCRIPTION
                "The status of this conceptual row, Now only realize CreateAndGo and Destroy and Active."
            ::= { hpnicfTrngPeriodicEntry 6 }

        hpnicfTRNGMibConformance OBJECT IDENTIFIER ::= { hpnicfTRNG 3 }


        hpnicfTRNGMibCompliances OBJECT IDENTIFIER ::= { hpnicfTRNGMibConformance 1 }


        hpnicfTRNGMibCompliance MODULE-COMPLIANCE
            STATUS current
            DESCRIPTION
                "The compliance statement for entities which
                implement the Time-range MIB."
            MODULE -- this module
                MANDATORY-GROUPS { hpnicfTRNGGroup }
                OBJECT hpnicfTrngCreateRowStatus
                    SYNTAX INTEGER
                    DESCRIPTION
                        "Now only realize CreateAndGo and Destroy and Active."
                OBJECT hpnicfTimerangeAbsolueRowStatus
                    SYNTAX INTEGER
                    DESCRIPTION
                        "Now only realize CreateAndGo and Destroy and Active."
                OBJECT hpnicfTimerangePeriodicRowStatus
                    SYNTAX INTEGER
                    DESCRIPTION
                        "Now only realize CreateAndGo and Destroy and Active."
            ::= { hpnicfTRNGMibCompliances 1 }


        hpnicfTRNGMibGroups OBJECT IDENTIFIER ::= { hpnicfTRNGMibConformance 2 }


        hpnicfTRNGGroup OBJECT-GROUP
            OBJECTS { hpnicfTrngName, hpnicfTrngValidFlag, hpnicfTrngCreateRowStatus, hpnicfTimerangeAbsoluteStartTime, hpnicfTimerangeAbsoluteEndTime,
                hpnicfTimerangeAbsolueRowStatus, hpnicfTrngPeriodicDayOfWeek, hpnicfTimerangePeriodicStartTime, hpnicfTimerangePeriodicEndTime, hpnicfTimerangePeriodicRowStatus
                 }
            STATUS current
            DESCRIPTION
                "A collection of objects providing mandatory time-range information."
            ::= { hpnicfTRNGMibGroups 1 }



    END
