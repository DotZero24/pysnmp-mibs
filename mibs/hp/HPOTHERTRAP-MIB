HPOTHERTRAP-MIB DEFINITIONS ::= BEGIN

IMPORTS
enterprises    FROM RFC1155-SMI
TRAP-TYPE      FROM RFC-1215;

--
hp                          OBJECT IDENTIFIER ::= { enterprises 11 }
adaptec                     OBJECT IDENTIFIER ::= { enterprises 795 }
nm                          OBJECT IDENTIFIER ::= { hp 2 }
hpnsa                       OBJECT IDENTIFIER ::= { nm 23 }
hpnsaECC                    OBJECT IDENTIFIER ::= { hpnsa 6 }
hpnsaRemoteAssist           OBJECT IDENTIFIER ::= { hpnsa 8 }
adaptecNm                   OBJECT IDENTIFIER ::= { adaptec 4 }
adaptecNmScsiStatus         OBJECT IDENTIFIER ::= { adaptecNm 1 }
hpnr                        OBJECT IDENTIFIER ::= { enterprises 16 }
hpNetRAID                   OBJECT IDENTIFIER ::= { hpnr 1 }
hpNetRaidMib                OBJECT IDENTIFIER ::= { hpNetRAID 1 }
raidTraps                   OBJECT IDENTIFIER ::= { hpNetRaidMib 200 }
storagemanagement           OBJECT IDENTIFIER ::= { adaptec 2 }
raidproducts                OBJECT IDENTIFIER ::= { adaptec 10 }
aac                         OBJECT IDENTIFIER ::= { raidproducts 1 }
aac-hpn                     OBJECT IDENTIFIER ::= { aac 50 }
adaptecRaid                 OBJECT IDENTIFIER ::= { adaptec 3 }
cyclone                     OBJECT IDENTIFIER ::= { storagemanagement 5 }
cycTraps                    OBJECT IDENTIFIER ::= { cyclone 9000 }
symbios                     OBJECT IDENTIFIER ::= { enterprises 1123}
coloradosprings             OBJECT IDENTIFIER ::= { symbios 3}
scsi                        OBJECT IDENTIFIER ::= { coloradosprings 1}
symc8xx                     OBJECT IDENTIFIER ::= { scsi 2}
symTrap                     OBJECT IDENTIFIER ::= { symc8xx 2}
eMylex1                     OBJECT IDENTIFIER ::= {enterprises 1608}
eMylex2                     OBJECT IDENTIFIER ::= {eMylex1 1}
eMylex3                     OBJECT IDENTIFIER ::= {eMylex2 1}
eMylex4                     OBJECT IDENTIFIER ::= {eMylex3 1}
eMylex5                     OBJECT IDENTIFIER ::= {eMylex4 9}
eMylexRaidEventInformation  OBJECT IDENTIFIER ::= {eMylex5 1}
dmtfStd                     OBJECT IDENTIFIER ::= {eMylexRaidEventInformation 1}
dmtfComponents              OBJECT IDENTIFIER ::= {dmtfStd 1}
dmtfGroups                  OBJECT IDENTIFIER ::= {dmtfComponents 1}

adaptecSCSI1 TRAP-TYPE
  ENTERPRISE adaptecNmScsiStatus
  DESCRIPTION
  "Device Database has been corrupted."
 --#TYPE "Corrupt Devices File"
 --#SUMMARY "Corrupt Devices File"
 --#ARGUMENTS {}
 --#SEVERITY CRITICAL
 --#TIMEINDEX 100
 --#HELP "SCSI-FLT.hlp"
 --#HELPTAG  6
 --#STATE OPERATIONAL
 --FIXED STRING : NOT PRESENT
 --CUSTOM STRING : NOT PRESENT
 --SEVERITY :
::= 8193

adaptecSCSI2 TRAP-TYPE
  ENTERPRISE adaptecNmScsiStatus
  DESCRIPTION
  "Device Database has been corrupted."
 --#TYPE "Corrupt Devices File"
 --#SUMMARY "Device Database has been corrupted."
 --#ARGUMENTS {}
 --#SEVERITY CRITICAL
 --#TIMEINDEX 100
 --#HELP "SCSI-FLT.hlp"
 --#HELPTAG  6
 --#STATE OPERATIONAL
 --FIXED STRING : NOT PRESENT
 --CUSTOM STRING : NOT PRESENT
 --SEVERITY :
::= 18193

adaptecSCSI3 TRAP-TYPE
  ENTERPRISE adaptecNmScsiStatus
  DESCRIPTION
  "SCSI Status agent was unloaded from a NetWare Server."
 --#TYPE "SCSI fault agent unloaded"
 --#SUMMARY "SCSI fault agent unloaded"
 --#ARGUMENTS {}
 --#SEVERITY INFORMATIONAL
 --#TIMEINDEX 100
 --#HELP "SCSI-FLT.hlp"
 --#HELPTAG  7
 --#STATE OPERATIONAL
 --FIXED STRING : NOT PRESENT
 --CUSTOM STRING : NOT PRESENT
 --SEVERITY :
::= 8194

adaptecSCSI4 TRAP-TYPE
  ENTERPRISE adaptecNmScsiStatus
  DESCRIPTION
  "SCSI Status agent was unloaded from a NetWare Server."
 --#TYPE "SCSI fault agent unloaded"
 --#SUMMARY "SCSI Status agent was unloaded from a NetWare Server."
 --#ARGUMENTS {}
 --#SEVERITY INFORMATIONAL
 --#TIMEINDEX 100
 --#HELP "SCSI-FLT.hlp"
 --#HELPTAG  7
 --#STATE OPERATIONAL
 --FIXED STRING : NOT PRESENT
 --CUSTOM STRING : NOT PRESENT
 --SEVERITY :
::= 18194

adaptecSCSI5 TRAP-TYPE
  ENTERPRISE adaptecNmScsiStatus
  DESCRIPTION
  "One of the SCSI HBAs can no longer be detected by the SCSI Status agent."
 --#TYPE "Host Adapter failed"
 --#SUMMARY "Host Adapter Failed"
 --#ARGUMENTS {}
 --#SEVERITY CRITICAL
 --#TIMEINDEX 100
 --#HELP "SCSI-FLT.hlp"
 --#HELPTAG  9
 --#STATE OPERATIONAL
 --FIXED STRING : NOT PRESENT
 --CUSTOM STRING : NOT PRESENT
 --SEVERITY :
::= 8196

adaptecSCSI6 TRAP-TYPE
  ENTERPRISE adaptecNmScsiStatus
  DESCRIPTION
  "One of the SCSI HBAs can no longer be detected by the SCSI Status agent."
 --#TYPE "Host Adapter failed"
 --#SUMMARY "One of the SCSI HBAs can no longer be detected by the SCSI Status agent."
 --#ARGUMENTS {}
 --#SEVERITY CRITICAL
 --#TIMEINDEX 100
 --#HELP "SCSI-FLT.hlp"
 --#HELPTAG  9
 --#STATE OPERATIONAL
 --FIXED STRING : NOT PRESENT
 --CUSTOM STRING : NOT PRESENT
 --SEVERITY :
::= 18196

adaptecSCSI7 TRAP-TYPE
  ENTERPRISE adaptecNmScsiStatus
  DESCRIPTION
  "A Host Adapter which has failed, has become accessible again."
 --#TYPE "Host Adapter recovered"
 --#SUMMARY "Host Adapter Recovered"
 --#ARGUMENTS {}
 --#SEVERITY INFORMATIONAL
 --#TIMEINDEX 100
 --#HELP "SCSI-FLT.hlp"
 --#HELPTAG  10
 --#STATE OPERATIONAL
 --FIXED STRING : NOT PRESENT
 --CUSTOM STRING : NOT PRESENT
 --SEVERITY :
::= 8197

adaptecSCSI8 TRAP-TYPE
  ENTERPRISE adaptecNmScsiStatus
  DESCRIPTION
  "A Host Adapter which has failed, has become accessible again."
 --#TYPE "Host Adapter recovered"
 --#SUMMARY "A Host Adapter which has failed, has become accessible again."
 --#ARGUMENTS {}
 --#SEVERITY INFORMATIONAL
 --#TIMEINDEX 100
 --#HELP "SCSI-FLT.hlp"
 --#HELPTAG  10
 --#STATE OPERATIONAL
 --FIXED STRING : NOT PRESENT
 --CUSTOM STRING : NOT PRESENT
 --SEVERITY :
::= 18197

adaptecSCSI9 TRAP-TYPE
  ENTERPRISE adaptecNmScsiStatus
  DESCRIPTION
  "A new SCSI Host Bus Adapter has been discovered or device database has been cleared."
 --#TYPE "Host Adapter Discovered"
 --#SUMMARY "Host Adapter Discovered"
 --#ARGUMENTS {}
 --#SEVERITY INFORMATIONAL
 --#TIMEINDEX 100
 --#HELP "SCSI-FLT.hlp"
 --#HELPTAG  8
 --#STATE OPERATIONAL
 --FIXED STRING : NOT PRESENT
 --CUSTOM STRING : NOT PRESENT
 --SEVERITY :
::= 8198

adaptecSCSI10 TRAP-TYPE
  ENTERPRISE adaptecNmScsiStatus
  DESCRIPTION
  "A new SCSI Host Bus Adapter has been discovered or device database has been cleared."
 --#TYPE "Host Adapter Discovered"
 --#SUMMARY "A new SCSI Host Bus Adapter has been discovered or device database has been cleared"
 --#ARGUMENTS {}
 --#SEVERITY INFORMATIONAL
 --#TIMEINDEX 100
 --#HELP "SCSI-FLT.hlp"
 --#HELPTAG  8
 --#STATE OPERATIONAL
 --FIXED STRING : NOT PRESENT
 --CUSTOM STRING : NOT PRESENT
 --SEVERITY :
::= 18198

adaptecSCSI11 TRAP-TYPE
  ENTERPRISE adaptecNmScsiStatus
  DESCRIPTION
  "One of the SCSI devices installed on the server can no longer be detected by the SCSI Status agent."
 --#TYPE "Device Failed"
 --#SUMMARY "Device Failed"
 --#ARGUMENTS {}
 --#SEVERITY CRITICAL
 --#TIMEINDEX 100
 --#HELP "SCSI-FLT.hlp"
 --#HELPTAG  14
 --#STATE OPERATIONAL
 --FIXED STRING : NOT PRESENT
 --CUSTOM STRING : NOT PRESENT
 --SEVERITY :
::= 8199

adaptecSCSI12 TRAP-TYPE
  ENTERPRISE adaptecNmScsiStatus
  DESCRIPTION
  "One of the SCSI devices installed on the server can no longer be detected by the SCSI Status agent."
 --#TYPE "Device Failed"
 --#SUMMARY "One of the SCSI devices installed on the server can no longer be detected by the SCSI Status agent."
 --#ARGUMENTS {}
 --#SEVERITY CRITICAL
 --#TIMEINDEX 100
 --#HELP "SCSI-FLT.hlp"
 --#HELPTAG  14
 --#STATE OPERATIONAL
 --FIXED STRING : NOT PRESENT
 --CUSTOM STRING : NOT PRESENT
 --SEVERITY :
::= 18199

adaptecSCSI13 TRAP-TYPE
  ENTERPRISE adaptecNmScsiStatus
  DESCRIPTION
  "A SCSI device which has failed, has become accessible again."
 --#TYPE "Device recovered"
 --#SUMMARY "Device Recovered"
 --#ARGUMENTS {}
 --#SEVERITY INFORMATIONAL
 --#TIMEINDEX 100
 --#HELP "SCSI-FLT.hlp"
 --#HELPTAG  15
 --#STATE OPERATIONAL
 --FIXED STRING : NOT PRESENT
 --CUSTOM STRING : NOT PRESENT
 --SEVERITY :
::= 8200

adaptecSCSI14 TRAP-TYPE
  ENTERPRISE adaptecNmScsiStatus
  DESCRIPTION
  "A SCSI device which has failed, has become accessible again."
 --#TYPE "Device recovered"
 --#SUMMARY "A SCSI device which has failed, has become accessible again."
 --#ARGUMENTS {}
 --#SEVERITY INFORMATIONAL
 --#TIMEINDEX 100
 --#HELP "SCSI-FLT.hlp"
 --#HELPTAG  15
 --#STATE OPERATIONAL
 --FIXED STRING : NOT PRESENT
 --CUSTOM STRING : NOT PRESENT
 --SEVERITY :
::= 18200

adaptecSCSI15 TRAP-TYPE
  ENTERPRISE adaptecNmScsiStatus
  DESCRIPTION
  "A new SCSI device has been discovered."
 --#TYPE "Device discovered"
 --#SUMMARY "Device Discovered"
 --#ARGUMENTS {}
 --#SEVERITY INFORMATIONAL
 --#TIMEINDEX 100
 --#HELP "SCSI-FLT.hlp"
 --#HELPTAG  13
 --#STATE OPERATIONAL
 --FIXED STRING : NOT PRESENT
 --CUSTOM STRING : NOT PRESENT
 --SEVERITY :
::= 8201

adaptecSCSI16 TRAP-TYPE
  ENTERPRISE adaptecNmScsiStatus
  DESCRIPTION
  "A new SCSI device has been discovered."
 --#TYPE "Device discovered"
 --#SUMMARY "A new SCSI device has been discovered."
 --#ARGUMENTS {}
 --#SEVERITY INFORMATIONAL
 --#TIMEINDEX 100
 --#HELP "SCSI-FLT.hlp"
 --#HELPTAG  13
 --#STATE OPERATIONAL
 --FIXED STRING : NOT PRESENT
 --CUSTOM STRING : NOT PRESENT
 --SEVERITY :
::= 18201

adaptecSCSI17 TRAP-TYPE
  ENTERPRISE adaptecNmScsiStatus
  DESCRIPTION
  "The SCSI Status agent detected that the Host Bus Adapter has been changed."
 --#TYPE "Host Adapter changed"
 --#SUMMARY "Host Adapter Changed"
 --#ARGUMENTS {}
 --#SEVERITY INFORMATIONAL
 --#TIMEINDEX 100
 --#HELP "SCSI-FLT.hlp"
 --#HELPTAG  11
 --#STATE OPERATIONAL
 --FIXED STRING : NOT PRESENT
 --CUSTOM STRING : NOT PRESENT
 --SEVERITY :
::= 8205

adaptecSCSI18 TRAP-TYPE
  ENTERPRISE adaptecNmScsiStatus
  DESCRIPTION
  "The SCSI Status agent detected that the Host Bus Adapter has been changed."
 --#TYPE "Host Adapter changed"
 --#SUMMARY "The SCSI Status agent detected that the Host Bus Adapter has been changed."
 --#ARGUMENTS {}
 --#SEVERITY INFORMATIONAL
 --#TIMEINDEX 100
 --#HELP "SCSI-FLT.hlp"
 --#HELPTAG  11
 --#STATE OPERATIONAL
 --FIXED STRING : NOT PRESENT
 --CUSTOM STRING : NOT PRESENT
 --SEVERITY :
::= 18205

adaptecSCSI19 TRAP-TYPE
  ENTERPRISE adaptecNmScsiStatus
  DESCRIPTION
  "The SCSI Status agent sent a request to an HBA and the request never completed."
 --#TYPE "Host Adapter Timeout"
 --#SUMMARY "Host Adapter Timeout"
 --#ARGUMENTS {}
 --#SEVERITY CRITICAL
 --#TIMEINDEX 100
 --#HELP "SCSI-FLT.hlp"
 --#HELPTAG  12
 --#STATE OPERATIONAL
 --FIXED STRING : NOT PRESENT
 --CUSTOM STRING : NOT PRESENT
 --SEVERITY :
::= 8208

adaptecSCSI20 TRAP-TYPE
  ENTERPRISE adaptecNmScsiStatus
  DESCRIPTION
  "The SCSI Status agent sent a request to an HBA and the request never completed."
 --#TYPE "Host Adapter Timeout"
 --#SUMMARY "The SCSI Status agent sent a request to an HBA and the request never completed."
 --#ARGUMENTS {}
 --#SEVERITY CRITICAL
 --#TIMEINDEX 100
 --#HELP "SCSI-FLT.hlp"
 --#HELPTAG  12
 --#STATE OPERATIONAL
 --FIXED STRING : NOT PRESENT
 --CUSTOM STRING : NOT PRESENT
 --SEVERITY :
::= 18208

adaptecSCSI21 TRAP-TYPE
  ENTERPRISE adaptecNmScsiStatus
  DESCRIPTION
  "The SCSI Status agent detected that a SCSI device installed on the server has been changed."
 --#TYPE "Device Changed"
 --#SUMMARY "Device Changed"
 --#ARGUMENTS {}
 --#SEVERITY INFORMATIONAL
 --#TIMEINDEX 100
 --#HELP "SCSI-FLT.hlp"
 --#HELPTAG  16
 --#STATE OPERATIONAL
 --FIXED STRING : NOT PRESENT
 --CUSTOM STRING : NOT PRESENT
 --SEVERITY :
::= 8206

adaptecSCSI22 TRAP-TYPE
  ENTERPRISE adaptecNmScsiStatus
  DESCRIPTION
  "The SCSI Status agent detected that a SCSI device installed on the server has been changed."
 --#TYPE "Device Changed"
 --#SUMMARY "The SCSI Status agent detected that a SCSI device installed on the server has been changed."
 --#ARGUMENTS {}
 --#SEVERITY INFORMATIONAL
 --#TIMEINDEX 100
 --#HELP "SCSI-FLT.hlp"
 --#HELPTAG  16
 --#STATE OPERATIONAL
 --FIXED STRING : NOT PRESENT
 --CUSTOM STRING : NOT PRESENT
 --SEVERITY :
::= 18206

adaptecSCSI23 TRAP-TYPE
  ENTERPRISE adaptecNmScsiStatus
  DESCRIPTION
  "The SCSI Status agent sent a request to a SCSI device and the request never completed."
 --#TYPE "Device timeout"
 --#SUMMARY "Device Timeout"
 --#ARGUMENTS {}
 --#SEVERITY CRITICAL
 --#TIMEINDEX 100
 --#HELP "SCSI-FLT.hlp"
 --#HELPTAG  17
 --#STATE OPERATIONAL
 --FIXED STRING : NOT PRESENT
 --CUSTOM STRING : NOT PRESENT
 --SEVERITY :
::= 8209

adaptecSCSI24 TRAP-TYPE
  ENTERPRISE adaptecNmScsiStatus
  DESCRIPTION
  "The SCSI Status agent sent a request to a SCSI device and the request never completed."
 --#TYPE "Device timeout"
 --#SUMMARY "The SCSI Status agent sent a request to a SCSI device and the request never completed."
 --#ARGUMENTS {}
 --#SEVERITY CRITICAL
 --#TIMEINDEX 100
 --#HELP "SCSI-FLT.hlp"
 --#HELPTAG  17
 --#STATE OPERATIONAL
 --FIXED STRING : NOT PRESENT
 --CUSTOM STRING : NOT PRESENT
 --SEVERITY :
::= 18209

aSR1 TRAP-TYPE
  ENTERPRISE hpnsa
  DESCRIPTION
  "Server has been restarted after the system watchdog timer has timed out due to NOS being hung"
 --#TYPE "Automatic Server Restart hard reset"
 --#SUMMARY "Automatic Server Restart: hard reset after NOS hang"
 --#ARGUMENTS {}
 --#SEVERITY INFORMATIONAL
 --#TIMEINDEX 100
 --#HELP "NSATrap.hlp"
 --#HELPTAG  2057
 --#STATE OPERATIONAL
 --FIXED STRING : NOT PRESENT
 --CUSTOM STRING : NOT PRESENT
 --SEVERITY :
::= 20752

aSR2 TRAP-TYPE
  ENTERPRISE hpnsa
  DESCRIPTION
  "OS Watchdog Shutdown"
 --#TYPE "OS Watchdog Shutdown"
 --#SUMMARY "OS Watchdog Shutdown"
 --#ARGUMENTS {}
 --#SEVERITY CRITICAL
 --#TIMEINDEX 100
 --#HELP "NSATRAP.HLP"
 --#HELPTAG  1021
 --#STATE OPERATIONAL
 --FIXED STRING : NOT PRESENT
 --CUSTOM STRING : NOT PRESENT
 --SEVERITY :
::= 20753

aSR3 TRAP-TYPE
  ENTERPRISE hpnsa
  DESCRIPTION
  "OS Watchdog poweroff"
 --#TYPE "OS Watchdog poweroff"
 --#SUMMARY "OS Watchdog poweroff"
 --#ARGUMENTS {}
 --#SEVERITY CRITICAL
 --#TIMEINDEX 100
 --#HELP "NSATRAP.HLP"
 --#HELPTAG  1023
 --#STATE OPERATIONAL
 --FIXED STRING : NOT PRESENT
 --CUSTOM STRING : NOT PRESENT
 --SEVERITY :
::= 20754

aSR4 TRAP-TYPE
  ENTERPRISE hpnsa
  DESCRIPTION
  "Server has been restarted after the system watchdog timer has timed out due to NOS being hung"
 --#TYPE "Automatic Server Restart: hard reset after NOS hang"
 --#SUMMARY "Automatic Server Restart: hard reset after NOS hang"
 --#ARGUMENTS {}
 --#SEVERITY INFORMATIONAL
 --#TIMEINDEX 100
 --#HELP "NSATrap.hlp"
 --#HELPTAG  2057
 --#STATE OPERATIONAL
 --FIXED STRING : NOT PRESENT
 --CUSTOM STRING : NOT PRESENT
 --SEVERITY :
::= 220752

aSR5 TRAP-TYPE
  ENTERPRISE hpnsa
  DESCRIPTION
  "Server has not been restarted after the system watchdog timer has timed out due to NOS being hung"
 --#TYPE "NOS hang, automatic server restart disabled"
 --#SUMMARY "NOS hang, automatic server restart disabled"
 --#ARGUMENTS {}
 --#SEVERITY INFORMATIONAL
 --#TIMEINDEX 100
 --#HELP "NSATrap.hlp"
 --#HELPTAG  1027
 --#STATE OPERATIONAL
 --FIXED STRING : NOT PRESENT
 --CUSTOM STRING : NOT PRESENT
 --SEVERITY :
::= 320752

aSR6 TRAP-TYPE
  ENTERPRISE hpnsa
  DESCRIPTION
  "Server has been powered down after the system watchdog timer has timed out due to NOS being hung"
 --#TYPE "Automatic Server Restart: power down after NOS hang"
 --#SUMMARY "Automatic Server Restart: power down after NOS hang"
 --#ARGUMENTS {}
 --#SEVERITY INFORMATIONAL
 --#TIMEINDEX 100
 --#HELP "NSATrap.hlp"
 --#HELPTAG  1001
 --#STATE OPERATIONAL
 --FIXED STRING : NOT PRESENT
 --CUSTOM STRING : NOT PRESENT
 --SEVERITY :
::= 420752

aSR7 TRAP-TYPE
  ENTERPRISE hpnsa
  DESCRIPTION
  "Server has been power cycled after the system watchdog timer has timed out due to NOS being hung"
 --#TYPE "Automatic Server Restart: power cycle after NOS hang"
 --#SUMMARY "Automatic Server Restart: power cycle after NOS hang"
 --#ARGUMENTS {}
 --#SEVERITY INFORMATIONAL
 --#TIMEINDEX 100
 --#HELP "NSATrap.hlp"
 --#HELPTAG  1002
 --#STATE OPERATIONAL
 --FIXED STRING : NOT PRESENT
 --CUSTOM STRING : NOT PRESENT
 --SEVERITY :
::= 520752

aSR8 TRAP-TYPE
  ENTERPRISE hpnsa
  DESCRIPTION
  "The System has been reset by the microcontroller firmware because watchdog timer expired."
 --#TYPE "Microcontroller Reset"
 --#SUMMARY "Microcontroller Reset"
 --#ARGUMENTS {}
 --#SEVERITY CRITICAL
 --#TIMEINDEX 100
 --#HELP "eightway.hlp"
 --#HELPTAG  9
 --#STATE OPERATIONAL
 --FIXED STRING : NOT PRESENT
 --CUSTOM STRING : NOT PRESENT
 --SEVERITY :
::= 22624

fibreChannel5 TRAP-TYPE
  ENTERPRISE hpnsa
  DESCRIPTION
  "The Fibre Channel Adapter is Online"
 --#TYPE "The Fibre Channel Adapter is Online"
 --#SUMMARY "The Fibre Channel Host Bus Adapter # %d is Online. Port: %s, PortWNN: %s"
 --#ARGUMENTS {0,1,2}
 --#SEVERITY INFORMATIONAL
 --#TIMEINDEX 100
 --#HELP "IPFsys.hlp"
 --#HELPTAG  1005
 --#STATE OPERATIONAL
 --FIXED STRING : NOT PRESENT
 --CUSTOM STRING : NOT PRESENT
 --SEVERITY :
::= 20759

fibreChannel6 TRAP-TYPE
  ENTERPRISE hpnsa
  DESCRIPTION
  "The Fibre Channel Adapter is Offline"
 --#TYPE "The Fibre Channel Adapter is Offline"
 --#SUMMARY "The Fibre Channel Host Bus Adapter # %d is Offline. Port: %s, PortWNN: %s"
 --#ARGUMENTS {0,1,2}
 --#SEVERITY CRITICAL
 --#TIMEINDEX 100
 --#HELP "IPFsys.hlp"
 --#HELPTAG  1006
 --#STATE OPERATIONAL
 --FIXED STRING : NOT PRESENT
 --CUSTOM STRING : NOT PRESENT
 --SEVERITY :
::= 20760

hPDiskSystem1 TRAP-TYPE
  ENTERPRISE hpnsa
  DESCRIPTION
  "The Defect List Threshold has been exceeded."
 --#TYPE "Exceeded Defect List Threshold"
 --#SUMMARY "Exceeded Defect List Threshold"
 --#ARGUMENTS {}
 --#SEVERITY MAJOR
 --#TIMEINDEX 100
 --#HELP "DISKS.hlp"
 --#HELPTAG  1
 --#STATE OPERATIONAL
 --FIXED STRING : NOT PRESENT
 --CUSTOM STRING : NOT PRESENT
 --SEVERITY :
::= 8210

hPECCMemory10 TRAP-TYPE
  ENTERPRISE hpnsa
  DESCRIPTION
  "System memory size reduced due to error in memory slot"
 --#TYPE "System memory size reduced due to error in memory slot"
 --#SUMMARY "System memory size reduced due to error in memory slot %d"
 --#ARGUMENTS {0}
 --#SEVERITY MAJOR
 --#TIMEINDEX 100
 --#HELP "NSATrap.hlp"
 --#HELPTAG  2058
 --#STATE OPERATIONAL
 --FIXED STRING : NOT PRESENT
 --CUSTOM STRING : NOT PRESENT
 --SEVERITY :
::= 220592

hPECCMemory2 TRAP-TYPE
  ENTERPRISE hpnsaECC
  DESCRIPTION
  "A single-bit error has been corrected in one of the memory modules."
 --#TYPE "Single-bit memory error corrected in a memory slot"
 --#SUMMARY "Single-bit error corrected in memory slot %d on bank/board %d"
 --#ARGUMENTS {0,1}
 --#SEVERITY INFORMATIONAL
 --#TIMEINDEX 100
 --#HELP "NSATrap.hlp"
 --#HELPTAG  2059
 --#STATE OPERATIONAL
 --FIXED STRING : NOT PRESENT
 --CUSTOM STRING : NOT PRESENT
 --SEVERITY :
::= 24353

hPECCMemory3 TRAP-TYPE
  ENTERPRISE hpnsaECC
  DESCRIPTION
  "Predictive failure in a memory module"
 --#TYPE "Predictive failure in a memory module"
 --#SUMMARY "Predictive failure in memory slot %d on bank/board %d"
 --#ARGUMENTS {0,1}
 --#SEVERITY MAJOR
 --#TIMEINDEX 100
 --#HELP "NSATRAP.HLP"
 --#HELPTAG  1013
 --#STATE OPERATIONAL
 --FIXED STRING : NOT PRESENT
 --CUSTOM STRING : NOT PRESENT
 --SEVERITY :
::= 24354


hPECCMemory7 TRAP-TYPE
  ENTERPRISE hpnsaECC
  DESCRIPTION
  "A Multiple-bit error has occurred in one of the memory modules"
 --#TYPE "Multiple-bit memory error has occurred"
 --#SUMMARY "A multiple bit memory error in slot %d, bank/board %d occurred"
 --#ARGUMENTS {0,1}
 --#SEVERITY CRITICAL
 --#TIMEINDEX 100
 --#HELP "NSATrap.hlp"
 --#HELPTAG  2060
 --#STATE OPERATIONAL
 --FIXED STRING : NOT PRESENT
 --CUSTOM STRING : NOT PRESENT
 --SEVERITY :
::= 24357

hPECCMemory9 TRAP-TYPE
  ENTERPRISE hpnsaECC
  DESCRIPTION
  "Single-bit repeated error"
 --#TYPE "Single-bit repeated error"
 --#SUMMARY "Single-bit repeated error in memory slot %d"
 --#ARGUMENTS {0}
 --#SEVERITY INFORMATIONAL
 --#TIMEINDEX 100
 --#HELP "nsatrap.hlp"
 --#HELPTAG  1034
 --#STATE OPERATIONAL
 --FIXED STRING : NOT PRESENT
 --CUSTOM STRING : NOT PRESENT
 --SEVERITY :
::= 24359

hPECCMemory11 TRAP-TYPE
  ENTERPRISE hpnsaECC
  DESCRIPTION
  "ECC error corrected in memory module"
 --#TYPE "ECC error corrected in memory module"
 --#SUMMARY "ECC error corrected in memory module [%s]."
 --#ARGUMENTS {0}
 --#SEVERITY INFORMATIONAL
 --#TIMEINDEX 100
 --#HELP "nsatrap.hlp"
 --#HELPTAG  2059
 --#STATE OPERATIONAL
 --FIXED STRING : NOT PRESENT
 --CUSTOM STRING : NOT PRESENT
 --SEVERITY :
::= 4360

hPECCMemory12 TRAP-TYPE
  ENTERPRISE hpnsaECC
  DESCRIPTION
  "Uncorrectable multi-bit ECC error has occurred in memory module"
 --#TYPE "Uncorrectable multi-bit ECC error has occurred in memory module"
 --#SUMMARY "Uncorrectable multi-bit ECC error has occurred in memory module [%s]"
 --#ARGUMENTS {0}
 --#SEVERITY CRITICAL
 --#TIMEINDEX 100
 --#HELP "nsatrap.hlp"
 --#HELPTAG  2060
 --#STATE OPERATIONAL
 --FIXED STRING : NOT PRESENT
 --CUSTOM STRING : NOT PRESENT
 --SEVERITY :
::= 4361

hPECCMemory13 TRAP-TYPE
  ENTERPRISE hpnsaECC
  DESCRIPTION
  "Repeated ECC error corrected in memory module"
 --#TYPE "Repeated ECC error corrected in memory module"
 --#SUMMARY "Repeated ECC error corrected in memory module [%s]"
 --#ARGUMENTS {0}
 --#SEVERITY INFORMATIONAL
 --#TIMEINDEX 100
 --#HELP "nsatrap.hlp"
 --#HELPTAG  1034
 --#STATE OPERATIONAL
 --FIXED STRING : NOT PRESENT
 --CUSTOM STRING : NOT PRESENT
 --SEVERITY :
::= 4363

hPECCMemory14 TRAP-TYPE
  ENTERPRISE hpnsaECC
  DESCRIPTION
  "ECC memory module is operating outside of acceptable margins"
 --#TYPE "ECC memory module is operating outside of acceptable margins"
 --#SUMMARY "ECC memory module [%s] is operating outside of acceptable margins"
 --#ARGUMENTS {0}
 --#SEVERITY MAJOR
 --#TIMEINDEX 100
 --#HELP "nsatrap.hlp"
 --#HELPTAG  1013
 --#STATE OPERATIONAL
 --FIXED STRING : NOT PRESENT
 --CUSTOM STRING : NOT PRESENT
 --SEVERITY :
::= 4364

hPECCMemory15 TRAP-TYPE
  ENTERPRISE hpnsaECC
  DESCRIPTION
  "Memory Mirroring switched to Slave Set"
 --#TYPE "Memory Mirroring switched to Slave Set"
 --#SUMMARY "Memory Mirroring switched to Slave Set"
 --#ARGUMENTS {}
 --#SEVERITY MAJOR
 --#TIMEINDEX 100
 --#HELP "nsatrap.hlp"
 --#HELPTAG  1041
 --#STATE OPERATIONAL
 --FIXED STRING : NOT PRESENT
 --CUSTOM STRING : NOT PRESENT
 --SEVERITY :
::= 4365

hPECCMemory16 TRAP-TYPE
  ENTERPRISE hpnsaECC
  DESCRIPTION
  "Faulty row switched to Hot Spare row"
 --#TYPE "Faulty row switched to Hot Spare row"
 --#SUMMARY "Faulty row switched to Hot Spare row"
 --#ARGUMENTS {}
 --#SEVERITY MAJOR
 --#TIMEINDEX 100
 --#HELP "nsatrap.hlp"
 --#HELPTAG  1042
 --#STATE OPERATIONAL
 --FIXED STRING : NOT PRESENT
 --CUSTOM STRING : NOT PRESENT
 --SEVERITY :
::= 4366

hPRaid1 TRAP-TYPE
  ENTERPRISE hpnsa
  DESCRIPTION
  "HPDA Controller: Cache Error"
 --#TYPE "HPDA Controller: Cache Error"
 --#SUMMARY "HPDA Controller: Cache Error"
 --#ARGUMENTS {}
 --#SEVERITY CRITICAL
 --#TIMEINDEX 100
 --#HELP "HPDA.hlp"
 --#HELPTAG  601
 --#STATE OPERATIONAL
 --FIXED STRING : NOT PRESENT
 --CUSTOM STRING : NOT PRESENT
 --SEVERITY :
::= 8609

hPRaid2 TRAP-TYPE
  ENTERPRISE hpnsa
  DESCRIPTION
  "HPDA Controller: Cache Error"
 --#TYPE "HPDA Controller: Cache Error"
 --#SUMMARY "HPDA Controller: Adapter-%d Cache Error"
 --#ARGUMENTS {0}
 --#SEVERITY CRITICAL
 --#TIMEINDEX 100
 --#HELP "HPDA.hlp"
 --#HELPTAG  601
 --#STATE OPERATIONAL
 --FIXED STRING : NOT PRESENT
 --CUSTOM STRING : NOT PRESENT
 --SEVERITY :
::= 28609

hPRaid3 TRAP-TYPE
  ENTERPRISE hpnsa
  DESCRIPTION
  "HPDA Logical Drive: Critical"
 --#TYPE "HPDA Logical Drive: Critical"
 --#SUMMARY "HPDA Logical Drive: Critical"
 --#ARGUMENTS {}
 --#SEVERITY MAJOR
 --#TIMEINDEX 100
 --#HELP "HPDA.hlp"
 --#HELPTAG  602
 --#STATE OPERATIONAL
 --FIXED STRING : NOT PRESENT
 --CUSTOM STRING : NOT PRESENT
 --SEVERITY :
::= 8625

hPRaid4 TRAP-TYPE
  ENTERPRISE hpnsa
  DESCRIPTION
  "HPDA Logical Drive Not Available"
 --#TYPE "HPDA Logical Drive Not Available"
 --#SUMMARY "HPDA Logical Drive: Not Available"
 --#ARGUMENTS {}
 --#SEVERITY CRITICAL
 --#TIMEINDEX 100
 --#HELP "HPDA.hlp"
 --#HELPTAG  603
 --#STATE OPERATIONAL
 --FIXED STRING : NOT PRESENT
 --CUSTOM STRING : NOT PRESENT
 --SEVERITY :
::= 8626

hPRaid5 TRAP-TYPE
  ENTERPRISE hpnsa
  DESCRIPTION
  "HPDA Hot Spare:Failed"
 --#TYPE "HPDA Hot Spare Failed"
 --#SUMMARY "HPDA Hot Spare: Failed"
 --#ARGUMENTS {}
 --#SEVERITY MAJOR
 --#TIMEINDEX 100
 --#HELP "HPDA.hlp"
 --#HELPTAG  604
 --#STATE OPERATIONAL
 --FIXED STRING : NOT PRESENT
 --CUSTOM STRING : NOT PRESENT
 --SEVERITY :
::= 8641

hPRaid6 TRAP-TYPE
  ENTERPRISE hpnsa
  DESCRIPTION
  "HPDA Hot Spare:Failed"
 --#TYPE "HPDA Hot Spare Failed"
 --#SUMMARY "HPDA Hot Spare: Adapter-%d, Channel-%d, TargetID-%d Failed."
 --#ARGUMENTS {0,1,2}
 --#SEVERITY MAJOR
 --#TIMEINDEX 100
 --#HELP "HPDA.hlp"
 --#HELPTAG  604
 --#STATE OPERATIONAL
 --FIXED STRING : NOT PRESENT
 --CUSTOM STRING : NOT PRESENT
 --SEVERITY :
::= 28641

hPRaid7 TRAP-TYPE
  ENTERPRISE hpnsa
  DESCRIPTION
  "HPDA Hot Spare Succeeded"
 --#TYPE "HPDA Hot Spare Succeeded"
 --#SUMMARY "HPDA Hot Spare: Succeeded"
 --#ARGUMENTS {}
 --#SEVERITY INFORMATIONAL
 --#TIMEINDEX 100
 --#HELP "HPDA.hlp"
 --#HELPTAG  605
 --#STATE OPERATIONAL
 --FIXED STRING : NOT PRESENT
 --CUSTOM STRING : NOT PRESENT
 --SEVERITY :
::= 8642

hPRaid8 TRAP-TYPE
  ENTERPRISE hpnsa
  DESCRIPTION
  "HPDA Hard Disk Failed"
 --#TYPE "HPDA Hard Disk Failed"
 --#SUMMARY "HPDA Hard Disk: Failed"
 --#ARGUMENTS {}
 --#SEVERITY MAJOR
 --#TIMEINDEX 100
 --#HELP "HPDA.hlp"
 --#HELPTAG  606
 --#STATE OPERATIONAL
 --FIXED STRING : NOT PRESENT
 --CUSTOM STRING : NOT PRESENT
 --SEVERITY :
::= 8657

hPRaid9 TRAP-TYPE
  ENTERPRISE hpnsa
  DESCRIPTION
  "HPDA Hard Disk Failed"
 --#TYPE "HPDA Hard Disk Failed"
 --#SUMMARY "HPDA Hard Disk: Adapter-%d, Channel-%d, TargetID-%d Failed."
 --#ARGUMENTS {0, 1, 2}
 --#SEVERITY MAJOR
 --#TIMEINDEX 100
 --#HELP "HPDA.hlp"
 --#HELPTAG  606
 --#STATE OPERATIONAL
 --FIXED STRING : NOT PRESENT
 --CUSTOM STRING : NOT PRESENT
 --SEVERITY :
::= 28657

hPRaid10 TRAP-TYPE
  ENTERPRISE hpnsa
  DESCRIPTION
  "HPDA Threshold Exceeded: Parity"
 --#TYPE "HPDA Threshold Exceeded: Parity"
 --#SUMMARY "HPDA Threshold Exceeded: Parity"
 --#ARGUMENTS {}
 --#SEVERITY MAJOR
 --#TIMEINDEX 100
 --#HELP "HPDA.hlp"
 --#HELPTAG  607
 --#STATE OPERATIONAL
 --FIXED STRING : NOT PRESENT
 --CUSTOM STRING : NOT PRESENT
 --SEVERITY :
::= 8673

hPRaid11 TRAP-TYPE
  ENTERPRISE hpnsa
  DESCRIPTION
  "HPDA Threshold Exceeded: Parity"
 --#TYPE "HPDA Threshold Exceeded: Parity"
 --#SUMMARY "HPDA:Parity Threshold Exceeded, Adapter-%d, Channel-%d, TargetID-%d."
 --#ARGUMENTS {0, 1, 2}
 --#SEVERITY MAJOR
 --#TIMEINDEX 100
 --#HELP "HPDA.hlp"
 --#HELPTAG  607
 --#STATE OPERATIONAL
 --FIXED STRING : NOT PRESENT
 --CUSTOM STRING : NOT PRESENT
 --SEVERITY :
::= 28673

hPRaid12 TRAP-TYPE
  ENTERPRISE hpnsa
  DESCRIPTION
  "HPDA Threshold Exceeded: Soft Errors"
 --#TYPE "HPDA Threshold Exceeded: Soft Errors"
 --#SUMMARY "HPDA Threshold Exceeded: Soft Errors"
 --#ARGUMENTS {}
 --#SEVERITY MAJOR
 --#TIMEINDEX 100
 --#HELP "HPDA.hlp"
 --#HELPTAG  608
 --#STATE OPERATIONAL
 --FIXED STRING : NOT PRESENT
 --CUSTOM STRING : NOT PRESENT
 --SEVERITY :
::= 8674

hPRaid13 TRAP-TYPE
  ENTERPRISE hpnsa
  DESCRIPTION
  "HPDA Threshold Exceeded: Soft Errors"
 --#TYPE "HPDA Threshold Exceeded: Soft Errors"
 --#SUMMARY "HPDA: Soft Error Threshold Exceeded, Adapter-%d, Channel-%d, TargetID-%d."
 --#ARGUMENTS {0, 1, 2}
 --#SEVERITY MAJOR
 --#TIMEINDEX 100
 --#HELP "HPDA.hlp"
 --#HELPTAG  608
 --#STATE OPERATIONAL
 --FIXED STRING : NOT PRESENT
 --CUSTOM STRING : NOT PRESENT
 --SEVERITY :
::= 28674

hPRaid14 TRAP-TYPE
  ENTERPRISE hpnsa
  DESCRIPTION
  "HPDA Threshold Exceeded: Hardware Errors"
 --#TYPE "HPDA Threshold Exceeded: Hardware Errors"
 --#SUMMARY "HPDA Threshold Exceeded: Hardware Errors"
 --#ARGUMENTS {}
 --#SEVERITY MAJOR
 --#TIMEINDEX 100
 --#HELP "HPDA.hlp"
 --#HELPTAG  609
 --#STATE OPERATIONAL
 --FIXED STRING : NOT PRESENT
 --CUSTOM STRING : NOT PRESENT
 --SEVERITY :
::= 8675

hPRaid15 TRAP-TYPE
  ENTERPRISE hpnsa
  DESCRIPTION
  "HPDA Threshold Exceeded: Hardware Errors"
 --#TYPE "HPDA Threshold Exceeded: Hardware Errors"
 --#SUMMARY "HPDA: Hardware Error Threshold Exceeded, Adapter-%d, Channel-%d, TargetID-%d."
 --#ARGUMENTS {0, 1, 2}
 --#SEVERITY MAJOR
 --#TIMEINDEX 100
 --#HELP "HPDA.hlp"
 --#HELPTAG  609
 --#STATE OPERATIONAL
 --FIXED STRING : NOT PRESENT
 --CUSTOM STRING : NOT PRESENT
 --SEVERITY :
::= 28675

hPRaid16 TRAP-TYPE
  ENTERPRISE hpnsa
  DESCRIPTION
  "HPDA Threshold Exceeded: Miscellaneous Errors"
 --#TYPE "HPDA Threshold Exceeded: Miscellaneous Errors"
 --#SUMMARY "HPDA Threshold Exceeded:Miscellaneous Errors"
 --#ARGUMENTS {}
 --#SEVERITY MAJOR
 --#TIMEINDEX 100
 --#HELP "HPDA.hlp"
 --#HELPTAG  610
 --#STATE OPERATIONAL
 --FIXED STRING : NOT PRESENT
 --CUSTOM STRING : NOT PRESENT
 --SEVERITY :
::= 8676

hPRaid17 TRAP-TYPE
  ENTERPRISE hpnsa
  DESCRIPTION
  "HPDA Threshold Exceeded: Miscellaneous Errors"
 --#TYPE "HPDA Threshold Exceeded: Miscellaneous Errors"
 --#SUMMARY "HPDA: Miscellaneous Error Threshold Exceeded, Adapter-%d, Channel-%d, TargetID-%d."
 --#ARGUMENTS {0,1,2}
 --#SEVERITY MAJOR
 --#TIMEINDEX 100
 --#HELP "HPDA.hlp"
 --#HELPTAG  610
 --#STATE OPERATIONAL
 --FIXED STRING : NOT PRESENT
 --CUSTOM STRING : NOT PRESENT
 --SEVERITY :
::= 28676

hPRaid18 TRAP-TYPE
  ENTERPRISE hpnsa
  DESCRIPTION
  "HPDA Controller: NVRAM Age"
 --#TYPE "HPDA Controller: NVRAM Age"
 --#SUMMARY "HPDA Controller: NVRAM Age"
 --#ARGUMENTS {}
 --#SEVERITY INFORMATIONAL
 --#TIMEINDEX 100
 --#HELP "HPDA.hlp"
 --#HELPTAG  611
 --#STATE OPERATIONAL
 --FIXED STRING : NOT PRESENT
 --CUSTOM STRING : NOT PRESENT
 --SEVERITY :
::= 8677

hPRaid19 TRAP-TYPE
  ENTERPRISE hpnsa
  DESCRIPTION
  "HPDA Controller: NVRAM Age"
 --#TYPE "HPDA Controller: NVRAM Age"
 --#SUMMARY "HPDA Controller: Adapter-%d NVRAM Age."
 --#ARGUMENTS {0}
 --#SEVERITY INFORMATIONAL
 --#TIMEINDEX 100
 --#HELP "HPDA.hlp"
 --#HELPTAG  611
 --#STATE OPERATIONAL
 --FIXED STRING : NOT PRESENT
 --CUSTOM STRING : NOT PRESENT
 --SEVERITY :
::= 28677

hPChassis1 TRAP-TYPE
  ENTERPRISE hpnsa
  DESCRIPTION
  "The chassis has been opened."
 --#TYPE "Chassis Intrusion"
 --#SUMMARY "The chassis has been opened."
 --#ARGUMENTS {}
 --#SEVERITY MAJOR
 --#TIMEINDEX 100
 --#HELP "era.hlp"
 --#HELPTAG  9
 --#STATE OPERATIONAL
 --FIXED STRING : NOT PRESENT
 --CUSTOM STRING : NOT PRESENT
 --SEVERITY :
::= 25019

hPChassis2 TRAP-TYPE
  ENTERPRISE hpnsa
  DESCRIPTION
  "I/O area open"
 --#TYPE "I/O area open"
 --#SUMMARY "I/O area open"
 --#ARGUMENTS {}
 --#SEVERITY MAJOR
 --#TIMEINDEX 100
 --#HELP "era.hlp"
 --#HELPTAG  14
 --#STATE OPERATIONAL
 --FIXED STRING : NOT PRESENT
 --CUSTOM STRING : NOT PRESENT
 --SEVERITY :
::= 25020

hPChassis3 TRAP-TYPE
  ENTERPRISE hpnsa
  DESCRIPTION
  "Processor area open"
 --#TYPE "Processor area open"
 --#SUMMARY "Processor area open"
 --#ARGUMENTS {}
 --#SEVERITY MAJOR
 --#TIMEINDEX 100
 --#HELP "era.hlp"
 --#HELPTAG  15
 --#STATE OPERATIONAL
 --FIXED STRING : NOT PRESENT
 --CUSTOM STRING : NOT PRESENT
 --SEVERITY :
::= 25021

hPEnvironment1 TRAP-TYPE
  ENTERPRISE hpnsa
  DESCRIPTION
  "One of the voltage sensors crossed its lower non-critical threshold."
 --#TYPE "Voltage Warning"
 --#SUMMARY "Voltage sensor %s crossed the lower non-critical threshold."
 --#ARGUMENTS {0}
 --#SEVERITY MAJOR
 --#TIMEINDEX 100
 --#HELP "RA.HLP"
 --#HELPTAG  7
 --#STATE OPERATIONAL
 --FIXED STRING : NOT PRESENT
 --CUSTOM STRING : NOT PRESENT
 --SEVERITY :
::= 25000

hPEnvironment2 TRAP-TYPE
  ENTERPRISE hpnsa
  DESCRIPTION
  "One of the voltage sensors crossed its lower critical threshold."
 --#TYPE "Voltage Emergency"
 --#SUMMARY "Voltage sensor %s crossed the lower critical threshold."
 --#ARGUMENTS {0}
 --#SEVERITY CRITICAL
 --#TIMEINDEX 100
 --#HELP "RA.HLP"
 --#HELPTAG  7
 --#STATE OPERATIONAL
 --FIXED STRING : NOT PRESENT
 --CUSTOM STRING : NOT PRESENT
 --SEVERITY :
::= 25001

hPEnvironment3 TRAP-TYPE
  ENTERPRISE hpnsa
  DESCRIPTION
  "One of the voltage sensors crossed its lower non-recoverable threshold."
 --#TYPE "Voltage Emergency"
 --#SUMMARY "Voltage sensor %s crossed the lower non-recoverable threshold."
 --#ARGUMENTS {0}
 --#SEVERITY CRITICAL
 --#TIMEINDEX 100
 --#HELP "ERA.HLP"
 --#HELPTAG  2
 --#STATE OPERATIONAL
 --FIXED STRING : NOT PRESENT
 --CUSTOM STRING : NOT PRESENT
 --SEVERITY :
::= 25002

hPEnvironment4 TRAP-TYPE
  ENTERPRISE hpnsa
  DESCRIPTION
  "One of the voltage sensors crossed its upper non-critical threshold."
 --#TYPE "Voltage Warning"
 --#SUMMARY "Voltage sensor %s crossed the upper non-critical threshold."
 --#ARGUMENTS {0}
 --#SEVERITY MAJOR
 --#TIMEINDEX 100
 --#HELP "RA.HLP"
 --#HELPTAG  7
 --#STATE OPERATIONAL
 --FIXED STRING : NOT PRESENT
 --CUSTOM STRING : NOT PRESENT
 --SEVERITY :
::= 25003

hPEnvironment5 TRAP-TYPE
  ENTERPRISE hpnsa
  DESCRIPTION
  "One of the voltage sensors crossed its upper critical threshold."
 --#TYPE "Voltage Emergency"
 --#SUMMARY "Voltage sensor %s crossed the upper critical threshold."
 --#ARGUMENTS {0}
 --#SEVERITY CRITICAL
 --#TIMEINDEX 100
 --#HELP "RA.HLP"
 --#HELPTAG  7
 --#STATE OPERATIONAL
 --FIXED STRING : NOT PRESENT
 --CUSTOM STRING : NOT PRESENT
 --SEVERITY :
::= 25004

hPEnvironment6 TRAP-TYPE
  ENTERPRISE hpnsa
  DESCRIPTION
  "One of the voltage sensors crossed its upper non-recoverable threshold."
 --#TYPE "Voltage Emergency"
 --#SUMMARY "Voltage sensor %s crossed the upper non-recoverable threshold."
 --#ARGUMENTS {0}
 --#SEVERITY CRITICAL
 --#TIMEINDEX 100
 --#HELP "RA.HLP"
 --#HELPTAG  7
 --#STATE OPERATIONAL
 --FIXED STRING : NOT PRESENT
 --CUSTOM STRING : NOT PRESENT
 --SEVERITY :
::= 25005

hPEnvironment7 TRAP-TYPE
  ENTERPRISE hpnsa
  DESCRIPTION
  "Voltage Regulating Module (VRM) on the indicated processor module had failed."
 --#TYPE "Voltage Regulating Module (VRM) failed"
 --#SUMMARY "Voltage Regulating Module (VRM) failed on processor %d"
 --#ARGUMENTS {0}
 --#SEVERITY CRITICAL
 --#TIMEINDEX 100
 --#HELP "eightway.hlp"
 --#HELPTAG  20
 --#STATE OPERATIONAL
 --FIXED STRING : NOT PRESENT
 --CUSTOM STRING : NOT PRESENT
 --SEVERITY :
::= 22801

hPFan1 TRAP-TYPE
  ENTERPRISE hpnsa
  DESCRIPTION
  "One of the fan sensors crossed its lower non-critical threshold."
 --#TYPE "Fan Warning"
 --#SUMMARY "Fan sensor %s crossed the lower non-critical threshold."
 --#ARGUMENTS {0}
 --#SEVERITY MAJOR
 --#TIMEINDEX 100
 --#HELP "ERA.HLP"
 --#HELPTAG  7
 --#STATE OPERATIONAL
 --FIXED STRING : NOT PRESENT
 --CUSTOM STRING : NOT PRESENT
 --SEVERITY :
::= 25013

hPFan2 TRAP-TYPE
  ENTERPRISE hpnsa
  DESCRIPTION
  "One of the fan sensors crossed its lower critical threshold."
 --#TYPE "Fan Emergency"
 --#SUMMARY "Fan sensor %s crossed the lower critical threshold."
 --#ARGUMENTS {0}
 --#SEVERITY CRITICAL
 --#TIMEINDEX 100
 --#HELP "ERA.HLP"
 --#HELPTAG  8
 --#STATE OPERATIONAL
 --FIXED STRING : NOT PRESENT
 --CUSTOM STRING : NOT PRESENT
 --SEVERITY :
::= 25014

hPFan3 TRAP-TYPE
  ENTERPRISE hpnsa
  DESCRIPTION
  "One of the fan sensors crossed its lower non-recoverable threshold."
 --#TYPE "Fan Emergency"
 --#SUMMARY "Fan sensor %s crossed the lower non-recoverable threshold."
 --#ARGUMENTS {0}
 --#SEVERITY CRITICAL
 --#TIMEINDEX 100
 --#HELP "ERA.HLP"
 --#HELPTAG  8
 --#STATE OPERATIONAL
 --FIXED STRING : NOT PRESENT
 --CUSTOM STRING : NOT PRESENT
 --SEVERITY :
::= 25015

hPFan4 TRAP-TYPE
  ENTERPRISE hpnsa
  DESCRIPTION
  "One of the fan sensors crossed its upper non-critical threshold."
 --#TYPE "Fan Warning"
 --#SUMMARY "Fan sensor %s crossed the upper non-critical threshold."
 --#ARGUMENTS {0}
 --#SEVERITY MAJOR
 --#TIMEINDEX 100
 --#HELP "ERA.HLP"
 --#HELPTAG  7
 --#STATE OPERATIONAL
 --FIXED STRING : NOT PRESENT
 --CUSTOM STRING : NOT PRESENT
 --SEVERITY :
::= 25016

hPFan5 TRAP-TYPE
  ENTERPRISE hpnsa
  DESCRIPTION
  "One of the fan sensors crossed its upper critical threshold."
 --#TYPE "Fan Emergency"
 --#SUMMARY "Fan sensor %s crossed the upper critical threshold."
 --#ARGUMENTS {0}
 --#SEVERITY CRITICAL
 --#TIMEINDEX 100
 --#HELP "ERA.HLP"
 --#HELPTAG  8
 --#STATE OPERATIONAL
 --FIXED STRING : NOT PRESENT
 --CUSTOM STRING : NOT PRESENT
 --SEVERITY :
::= 25017

hPFan6 TRAP-TYPE
  ENTERPRISE hpnsa
  DESCRIPTION
  "One of the fan sensors crossed its upper non-recoverable threshold."
 --#TYPE "Fan Emergency"
 --#SUMMARY "Fan sensor %s crossed the upper non-recoverable threshold."
 --#ARGUMENTS {0}
 --#SEVERITY CRITICAL
 --#TIMEINDEX 100
 --#HELP "ERA.HLP"
 --#HELPTAG  8
 --#STATE OPERATIONAL
 --FIXED STRING : NOT PRESENT
 --CUSTOM STRING : NOT PRESENT
 --SEVERITY :
::= 25018

hPFan7 TRAP-TYPE
  ENTERPRISE hpnsa
  DESCRIPTION
  "One of the fans in the Processor/PCI fan tray stopped."
 --#TYPE "Processor/PCI fan Tray error"
 --#SUMMARY "Processor/PCI fan Tray error"
 --#ARGUMENTS {}
 --#SEVERITY CRITICAL
 --#TIMEINDEX 100
 --#HELP "eightway.hlp"
 --#HELPTAG  6
 --#STATE OPERATIONAL
 --FIXED STRING : NOT PRESENT
 --CUSTOM STRING : NOT PRESENT
 --SEVERITY :
::= 22576

hPFan8 TRAP-TYPE
  ENTERPRISE hpnsa
  DESCRIPTION
  "Two or more of the fans in the Processor/PCI Fan Tray have stopped or have been removed."
 --#TYPE "Processor/PCI Fan Tray failure"
 --#SUMMARY "Processor/PCI Fan Tray failure"
 --#ARGUMENTS {}
 --#SEVERITY CRITICAL
 --#TIMEINDEX 100
 --#HELP "eightway.hlp"
 --#HELPTAG  7
 --#STATE OPERATIONAL
 --FIXED STRING : NOT PRESENT
 --CUSTOM STRING : NOT PRESENT
 --SEVERITY :
::= 22593

hPFan9 TRAP-TYPE
  ENTERPRISE hpnsa
  DESCRIPTION
  "Fan problem in Processor/PCI Fan Tray has been corrected."
 --#TYPE "Processor/PCI Fan Fan Restored"
 --#SUMMARY "Processor/PCI Fan Restored"
 --#ARGUMENTS {}
 --#SEVERITY INFORMATIONAL
 --#TIMEINDEX 100
 --#HELP "eightway.hlp"
 --#HELPTAG  8
 --#STATE OPERATIONAL
 --FIXED STRING : NOT PRESENT
 --CUSTOM STRING : NOT PRESENT
 --SEVERITY :
::= 22608

hPFan10 TRAP-TYPE
  ENTERPRISE hpnsa
  DESCRIPTION
  "One of the fans in the Memory Fan Tray stopped."
 --#TYPE "Memory Fan Error"
 --#SUMMARY "Memory Fan Error"
 --#ARGUMENTS {}
 --#SEVERITY CRITICAL
 --#TIMEINDEX 100
 --#HELP "eightway.hlp"
 --#HELPTAG  10
 --#STATE OPERATIONAL
 --FIXED STRING : NOT PRESENT
 --CUSTOM STRING : NOT PRESENT
 --SEVERITY :
::= 22640

hPFan11 TRAP-TYPE
  ENTERPRISE hpnsa
  DESCRIPTION
  "Two or more of the fans in the Memory Fan Tray have stopped or been removed."
 --#TYPE "Memory Fan Failure"
 --#SUMMARY "Memory Fan Failure"
 --#ARGUMENTS {}
 --#SEVERITY CRITICAL
 --#TIMEINDEX 100
 --#HELP "eightway.hlp"
 --#HELPTAG  11
 --#STATE OPERATIONAL
 --FIXED STRING : NOT PRESENT
 --CUSTOM STRING : NOT PRESENT
 --SEVERITY :
::= 22657

hPFan12 TRAP-TYPE
  ENTERPRISE hpnsa
  DESCRIPTION
  "Fan problem in the Memory Fan Tray has been corrected."
 --#TYPE "Memory Fan Restored"
 --#SUMMARY "Memory Fan Restored"
 --#ARGUMENTS {}
 --#SEVERITY INFORMATIONAL
 --#TIMEINDEX 100
 --#HELP "eightway.hlp"
 --#HELPTAG  12
 --#STATE OPERATIONAL
 --FIXED STRING : NOT PRESENT
 --CUSTOM STRING : NOT PRESENT
 --SEVERITY :
::= 22672

hPFan13 TRAP-TYPE
  ENTERPRISE hpnsa
  DESCRIPTION
  "A system fan module error has occurred"
 --#TYPE "Fan Warning"
 --#SUMMARY "A system fan module error has occurred"
 --#ARGUMENTS {0}
 --#SEVERITY MAJOR
 --#TIMEINDEX 100
 --#HELP "ERA.HLP"
 --#HELPTAG  7
 --#STATE OPERATIONAL
 --FIXED STRING : NOT PRESENT
 --CUSTOM STRING : NOT PRESENT
 --SEVERITY :
::= 25025

hPFan14 TRAP-TYPE
  ENTERPRISE hpnsa
  DESCRIPTION
  "A system fan module error has occurred"
 --#TYPE "Fan Emergency"
 --#SUMMARY "A system fan module error has occurred"
 --#ARGUMENTS {0}
 --#SEVERITY CRITICAL
 --#TIMEINDEX 100
 --#HELP "ERA.HLP"
 --#HELPTAG  8
 --#STATE OPERATIONAL
 --FIXED STRING : NOT PRESENT
 --CUSTOM STRING : NOT PRESENT
 --SEVERITY :
::= 25026

hPFan15 TRAP-TYPE
  ENTERPRISE hpnsa
  DESCRIPTION
  "Fan module failure"
 --#TYPE "Fan module failure"
 --#SUMMARY "Fan module failure"
 --#ARGUMENTS {0}
 --#SEVERITY MAJOR
 --#TIMEINDEX 100
 --#HELP "ERA.HLP"
 --#HELPTAG  7
 --#STATE OPERATIONAL
 --FIXED STRING : NOT PRESENT
 --CUSTOM STRING : NOT PRESENT
 --SEVERITY :
::= 25027

hPFan16 TRAP-TYPE
  ENTERPRISE hpnsa
  DESCRIPTION
  "Fan module failure"
 --#TYPE "Fan module failure"
 --#SUMMARY "Fan module failure"
 --#ARGUMENTS {0}
 --#SEVERITY CRITICAL
 --#TIMEINDEX 100
 --#HELP "ERA.HLP"
 --#HELPTAG  8
 --#STATE OPERATIONAL
 --FIXED STRING : NOT PRESENT
 --CUSTOM STRING : NOT PRESENT
 --SEVERITY :
::= 25028

hPFWUpdate1 TRAP-TYPE
  ENTERPRISE hpnsa
  DESCRIPTION
  "Front Panel Controller firmware updated"
 --#TYPE "Front Panel Controller firmware updated"
 --#SUMMARY "Front Panel Controller firmware updated."
 --#ARGUMENTS {}
 --#SEVERITY INFORMATIONAL
 --#TIMEINDEX 100
 --#HELP "era.hlp"
 --#HELPTAG  10
 --#STATE OPERATIONAL
 --FIXED STRING : NOT PRESENT
 --CUSTOM STRING : NOT PRESENT
 --SEVERITY :
::= 101

hPFWUpdate2 TRAP-TYPE
  ENTERPRISE hpnsa
  DESCRIPTION
  "Primary Hot Swap Cage Controller firmware updated"
 --#TYPE "Primary Hot Swap Cage Controller firmware updated"
 --#SUMMARY "Primary Hot Swap Cage Controller firmware updated"
 --#ARGUMENTS {}
 --#SEVERITY INFORMATIONAL
 --#TIMEINDEX 100
 --#HELP "era.hlp"
 --#HELPTAG  11
 --#STATE OPERATIONAL
 --FIXED STRING : NOT PRESENT
 --CUSTOM STRING : NOT PRESENT
 --SEVERITY :
::= 102

hPFWUpdate3 TRAP-TYPE
  ENTERPRISE hpnsa
  DESCRIPTION
  "Secondary Hot Swap Cage Controller firmware updated"
 --#TYPE "Secondary Hot Swap Cage Controller firmware updated"
 --#SUMMARY "Secondary Hot Swap Cage Controller firmware updated"
 --#ARGUMENTS {}
 --#SEVERITY INFORMATIONAL
 --#TIMEINDEX 100
 --#HELP "era.hlp"
 --#HELPTAG  12
 --#STATE OPERATIONAL
 --FIXED STRING : NOT PRESENT
 --CUSTOM STRING : NOT PRESENT
 --SEVERITY :
::= 103

hPFWUpdate4 TRAP-TYPE
  ENTERPRISE hpnsa
  DESCRIPTION
  "NetServer Management Controller firmware updated"
 --#TYPE "NetServer Management Controller firmware updated"
 --#SUMMARY "NetServer Management Controller firmware updated"
 --#ARGUMENTS {}
 --#SEVERITY INFORMATIONAL
 --#TIMEINDEX 100
 --#HELP "era.hlp"
 --#HELPTAG  13
 --#STATE OPERATIONAL
 --FIXED STRING : NOT PRESENT
 --CUSTOM STRING : NOT PRESENT
 --SEVERITY :
::= 104

hPFWUpdate5 TRAP-TYPE
  ENTERPRISE hpnsa
  DESCRIPTION
  "CPU Management Controller firmware updated"
 --#TYPE "CPU Management Controller firmware updated"
 --#SUMMARY "CPU Management Controller firmware updated"
 --#ARGUMENTS {}
 --#SEVERITY INFORMATIONAL
 --#TIMEINDEX 100
 --#HELP "nsatrap.hlp"
 --#HELPTAG  1038
 --#STATE OPERATIONAL
 --FIXED STRING : NOT PRESENT
 --CUSTOM STRING : NOT PRESENT
 --SEVERITY :
::= 105

hPTemperature1 TRAP-TYPE
  ENTERPRISE hpnsa
  DESCRIPTION
  "One of the temperature sensors crossed its lower non-critical threshold."
 --#TYPE "Temperature warning"
 --#SUMMARY "Temperature sensor %s crossed the lower non-critical threshold."
 --#ARGUMENTS {0}
 --#SEVERITY MAJOR
 --#TIMEINDEX 100
 --#HELP "ERA.HLP"
 --#HELPTAG  5
 --#STATE OPERATIONAL
 --FIXED STRING : NOT PRESENT
 --CUSTOM STRING : NOT PRESENT
 --SEVERITY :
::= 25007

hPTemperature2 TRAP-TYPE
  ENTERPRISE hpnsa
  DESCRIPTION
  "One of the temperature sensors crossed its lower critical threshold."
 --#TYPE "Temperature Emergency"
 --#SUMMARY "Temperature sensor %s crossed the lower critical threshold."
 --#ARGUMENTS {0}
 --#SEVERITY CRITICAL
 --#TIMEINDEX 100
 --#HELP "ERA.HLP"
 --#HELPTAG  6
 --#STATE OPERATIONAL
 --FIXED STRING : NOT PRESENT
 --CUSTOM STRING : NOT PRESENT
 --SEVERITY :
::= 25008

hPTemperature3 TRAP-TYPE
  ENTERPRISE hpnsa
  DESCRIPTION
  "One of the temperature sensors crossed its lower non-recoverable threshold."
 --#TYPE "Temperature Emergency"
 --#SUMMARY "Temperature sensor %s crossed the lower non-recoverable threshold."
 --#ARGUMENTS {0}
 --#SEVERITY CRITICAL
 --#TIMEINDEX 100
 --#HELP "ERA.HLP"
 --#HELPTAG  6
 --#STATE OPERATIONAL
 --FIXED STRING : NOT PRESENT
 --CUSTOM STRING : NOT PRESENT
 --SEVERITY :
::= 25009

hPTemperature4 TRAP-TYPE
  ENTERPRISE hpnsa
  DESCRIPTION
  "One of the temperature sensors crossed its upper non-critical threshold."
 --#TYPE "Temperature warning"
 --#SUMMARY "Temperature sensor %s crossed the upper non-critical threshold."
 --#ARGUMENTS {0}
 --#SEVERITY MAJOR
 --#TIMEINDEX 100
 --#HELP "era.hlp"
 --#HELPTAG  5
 --#STATE OPERATIONAL
 --FIXED STRING : NOT PRESENT
 --CUSTOM STRING : NOT PRESENT
 --SEVERITY :
::= 25010

hPTemperature5 TRAP-TYPE
  ENTERPRISE hpnsa
  DESCRIPTION
  "One of the temperature sensors crossed its upper critical threshold."
 --#TYPE "Temperature Emergency"
 --#SUMMARY "Temperature sensor %s crossed the upper critical threshold."
 --#ARGUMENTS {0}
 --#SEVERITY CRITICAL
 --#TIMEINDEX 100
 --#HELP "era.hlp"
 --#HELPTAG  6
 --#STATE OPERATIONAL
 --FIXED STRING : NOT PRESENT
 --CUSTOM STRING : NOT PRESENT
 --SEVERITY :
::= 25011

hPTemperature6 TRAP-TYPE
  ENTERPRISE hpnsa
  DESCRIPTION
  "One of the temperature sensors crossed its upper non-recoverable threshold."
 --#TYPE "Temperature Emergency"
 --#SUMMARY "Temperature sensor %s crossed the upper non-recoverable threshold."
 --#ARGUMENTS {0}
 --#SEVERITY CRITICAL
 --#TIMEINDEX 100
 --#HELP "ERA.HLP"
 --#HELPTAG  6
 --#STATE OPERATIONAL
 --FIXED STRING : NOT PRESENT
 --CUSTOM STRING : NOT PRESENT
 --SEVERITY :
::= 25012

networkCard1 TRAP-TYPE
  ENTERPRISE hpnsa
  DESCRIPTION
  "The total number of packets with receive errors has exceeded the threshold."
 --#TYPE "Received Errors exceeded threshold"
 --#SUMMARY "Received Errors exceeded threshold"
 --#ARGUMENTS {}
 --#SEVERITY MAJOR
 --#TIMEINDEX 100
 --#HELP "NIC.hlp"
 --#HELPTAG  200
 --#STATE OPERATIONAL
 --FIXED STRING : NOT PRESENT
 --CUSTOM STRING : NOT PRESENT
 --SEVERITY :
::= 16385

networkCard2 TRAP-TYPE
  ENTERPRISE hpnsa
  DESCRIPTION
  "The total number of packets with receive errors has exceeded the threshold."
 --#TYPE "Received Errors exceeded threshold"
 --#SUMMARY "NIC adapter %d received errors exceeded relative threshold: current value is %d."
 --#ARGUMENTS {0,1}
 --#SEVERITY MAJOR
 --#TIMEINDEX 100
 --#HELP "NIC.hlp"
 --#HELPTAG  200
 --#STATE OPERATIONAL
 --FIXED STRING : NOT PRESENT
 --CUSTOM STRING : NOT PRESENT
 --SEVERITY :
::= 116385

networkCard3 TRAP-TYPE
  ENTERPRISE hpnsa
  DESCRIPTION
  "The total number of packets with receive errors has exceeded the threshold."
 --#TYPE "Received Errors exceeded threshold"
 --#SUMMARY "NIC adapter %d received errors exceeded absolute threshold: current value is %d."
 --#ARGUMENTS {0,1}
 --#SEVERITY MAJOR
 --#TIMEINDEX 100
 --#HELP "NIC.hlp"
 --#HELPTAG  200
 --#STATE OPERATIONAL
 --FIXED STRING : NOT PRESENT
 --CUSTOM STRING : NOT PRESENT
 --SEVERITY :
::= 216385

networkCard4 TRAP-TYPE
  ENTERPRISE hpnsa
  DESCRIPTION
  "The total number of packets with receive errors has exceeded the threshold."
 --#TYPE "Received Errors exceeded threshold"
 --#SUMMARY "NIC adapter %d received errors exceeded delta threshold: current value is %d."
 --#ARGUMENTS {0,1}
 --#SEVERITY MAJOR
 --#TIMEINDEX 100
 --#HELP "NIC.hlp"
 --#HELPTAG  200
 --#STATE OPERATIONAL
 --FIXED STRING : NOT PRESENT
 --CUSTOM STRING : NOT PRESENT
 --SEVERITY :
::= 316385

networkCard5 TRAP-TYPE
  ENTERPRISE hpnsa
  DESCRIPTION
  "The total number of packets with transmit errors has exceeded the threshold."
 --#TYPE "Transmit Error exceeded threshold"
 --#SUMMARY "Transmit Errors exceeded threshold"
 --#ARGUMENTS {}
 --#SEVERITY MAJOR
 --#TIMEINDEX 100
 --#HELP "NIC.hlp"
 --#HELPTAG  201
 --#STATE OPERATIONAL
 --FIXED STRING : NOT PRESENT
 --CUSTOM STRING : NOT PRESENT
 --SEVERITY :
::= 16386

networkCard6 TRAP-TYPE
  ENTERPRISE hpnsa
  DESCRIPTION
  "The total number of packets with transmit errors has exceeded the threshold."
 --#TYPE "Transmit Error exceeded threshold"
 --#SUMMARY "NIC adapter %d transmit errors exceeded relative threshold: current value is %d."
 --#ARGUMENTS {0,1}
 --#SEVERITY MAJOR
 --#TIMEINDEX 100
 --#HELP "NIC.hlp"
 --#HELPTAG  201
 --#STATE OPERATIONAL
 --FIXED STRING : NOT PRESENT
 --CUSTOM STRING : NOT PRESENT
 --SEVERITY :
::= 116386

networkCard7 TRAP-TYPE
  ENTERPRISE hpnsa
  DESCRIPTION
  "The total number of packets with transmit errors has exceeded the threshold."
 --#TYPE "Transmit Error exceeded threshold"
 --#SUMMARY "NIC adapter %d transmit errors exceeded absolute threshold: current value is %d."
 --#ARGUMENTS {0,1}
 --#SEVERITY MAJOR
 --#TIMEINDEX 100
 --#HELP "NIC.hlp"
 --#HELPTAG  201
 --#STATE OPERATIONAL
 --FIXED STRING : NOT PRESENT
 --CUSTOM STRING : NOT PRESENT
 --SEVERITY :
::= 216386

networkCard8 TRAP-TYPE
  ENTERPRISE hpnsa
  DESCRIPTION
  "The total number of packets with transmit errors has exceeded the threshold."
 --#TYPE "Transmit Error exceeded threshold"
 --#SUMMARY "NIC adapter %d transmit errors exceeded delta threshold: current value is %d."
 --#ARGUMENTS {0,1}
 --#SEVERITY MAJOR
 --#TIMEINDEX 100
 --#HELP "NIC.hlp"
 --#HELPTAG  201
 --#STATE OPERATIONAL
 --FIXED STRING : NOT PRESENT
 --CUSTOM STRING : NOT PRESENT
 --SEVERITY :
::= 316386

networkCard9 TRAP-TYPE
  ENTERPRISE hpnsa
  DESCRIPTION
  "The total number of LAN Adapter reset errors has exceeded the threshold."
 --#TYPE "Adapter Reset Errors exceeded threshold"
 --#SUMMARY "Adapter Reset Errors exceeded threshold"
 --#ARGUMENTS {}
 --#SEVERITY CRITICAL
 --#TIMEINDEX 100
 --#HELP "NIC.hlp"
 --#HELPTAG  202
 --#STATE OPERATIONAL
 --FIXED STRING : NOT PRESENT
 --CUSTOM STRING : NOT PRESENT
 --SEVERITY :
::= 16387

networkCard10 TRAP-TYPE
  ENTERPRISE hpnsa
  DESCRIPTION
  "The total number of LAN Adapter reset errors has exceeded the threshold."
 --#TYPE "Adapter Reset Errors exceeded threshold"
 --#SUMMARY "NIC adapter %d adapter reset errors exceeded relative threshold: current value is %d."
 --#ARGUMENTS {0,1}
 --#SEVERITY CRITICAL
 --#TIMEINDEX 100
 --#HELP "NIC.hlp"
 --#HELPTAG  202
 --#STATE OPERATIONAL
 --FIXED STRING : NOT PRESENT
 --CUSTOM STRING : NOT PRESENT
 --SEVERITY :
::= 116387

networkCard11 TRAP-TYPE
  ENTERPRISE hpnsa
  DESCRIPTION
  "The total number of LAN Adapter reset errors has exceeded the threshold."
 --#TYPE "Adapter Reset Errors exceeded threshold"
 --#SUMMARY "NIC adapter %d adapter reset errors exceeded absolute threshold: current value is %d."
 --#ARGUMENTS {0,1}
 --#SEVERITY CRITICAL
 --#TIMEINDEX 100
 --#HELP "NIC.hlp"
 --#HELPTAG  202
 --#STATE OPERATIONAL
 --FIXED STRING : NOT PRESENT
 --CUSTOM STRING : NOT PRESENT
 --SEVERITY :
::= 216387

networkCard12 TRAP-TYPE
  ENTERPRISE hpnsa
  DESCRIPTION
  "The total number of LAN Adapter reset errors has exceeded the threshold."
 --#TYPE "Adapter Reset Errors exceeded threshold"
 --#SUMMARY "NIC adapter %d adapter reset errors exceeded delta threshold: current value is %d."
 --#ARGUMENTS {0,1}
 --#SEVERITY CRITICAL
 --#TIMEINDEX 100
 --#HELP "NIC.hlp"
 --#HELPTAG  202
 --#STATE OPERATIONAL
 --FIXED STRING : NOT PRESENT
 --CUSTOM STRING : NOT PRESENT
 --SEVERITY :
::= 316387

networkCard13 TRAP-TYPE
  ENTERPRISE hpnsa
  DESCRIPTION
  "The total number of alignment and CRC errors has exceeded the threshold."
 --#TYPE "Alignment Errors exceeded threshold"
 --#SUMMARY "Alignment Errors exceeded threshold"
 --#ARGUMENTS {}
 --#SEVERITY MAJOR
 --#TIMEINDEX 100
 --#HELP "NIC.hlp"
 --#HELPTAG  203
 --#STATE OPERATIONAL
 --FIXED STRING : NOT PRESENT
 --CUSTOM STRING : NOT PRESENT
 --SEVERITY :
::= 16388

networkCard14 TRAP-TYPE
  ENTERPRISE hpnsa
  DESCRIPTION
  "The total number of alignment and CRC errors has exceeded the threshold."
 --#TYPE "Alignment Errors exceeded threshold"
 --#SUMMARY "NIC adapter %d alignment errors exceeded relative threshold: current value is %d."
 --#ARGUMENTS {0,1}
 --#SEVERITY MAJOR
 --#TIMEINDEX 100
 --#HELP "NIC.hlp"
 --#HELPTAG  203
 --#STATE OPERATIONAL
 --FIXED STRING : NOT PRESENT
 --CUSTOM STRING : NOT PRESENT
 --SEVERITY :
::= 116388

networkCard15 TRAP-TYPE
  ENTERPRISE hpnsa
  DESCRIPTION
  "The total number of alignment and CRC errors has exceeded the threshold."
 --#TYPE "Alignment Errors exceeded threshold"
 --#SUMMARY "NIC adapter %d alignment errors exceeded absolute threshold: current value is %d."
 --#ARGUMENTS {0,1}
 --#SEVERITY MAJOR
 --#TIMEINDEX 100
 --#HELP "NIC.hlp"
 --#HELPTAG  203
 --#STATE OPERATIONAL
 --FIXED STRING : NOT PRESENT
 --CUSTOM STRING : NOT PRESENT
 --SEVERITY :
::= 216388

networkCard16 TRAP-TYPE
  ENTERPRISE hpnsa
  DESCRIPTION
  "The total number of alignment and CRC errors has exceeded the threshold."
 --#TYPE "Alignment Errors exceeded threshold"
 --#SUMMARY "NIC adapter %d alignment errors exceeded delta threshold: current value is %d."
 --#ARGUMENTS {0,1}
 --#SEVERITY MAJOR
 --#TIMEINDEX 100
 --#HELP "NIC.hlp"
 --#HELPTAG  203
 --#STATE OPERATIONAL
 --FIXED STRING : NOT PRESENT
 --CUSTOM STRING : NOT PRESENT
 --SEVERITY :
::= 316388

networkCard17 TRAP-TYPE
  ENTERPRISE hpnsa
  DESCRIPTION
  "The total number of giant frame packets has exceeded the threshold."
 --#TYPE "Giant Frame Errors exceeded threshold"
 --#SUMMARY "GiantFrame Errors exceeded threshold"
 --#ARGUMENTS {}
 --#SEVERITY MAJOR
 --#TIMEINDEX 100
 --#HELP "NIC.hlp"
 --#HELPTAG  204
 --#STATE OPERATIONAL
 --FIXED STRING : NOT PRESENT
 --CUSTOM STRING : NOT PRESENT
 --SEVERITY :
::= 16389

networkCard18 TRAP-TYPE
  ENTERPRISE hpnsa
  DESCRIPTION
  "The total number of giant frame packets has exceeded the threshold."
 --#TYPE "Giant Frame Errors exceeded threshold"
 --#SUMMARY "NIC adapter %d giant frame errors exceeded relative threshold: current value is %d."
 --#ARGUMENTS {0,1}
 --#SEVERITY MAJOR
 --#TIMEINDEX 100
 --#HELP "NIC.hlp"
 --#HELPTAG  204
 --#STATE OPERATIONAL
 --FIXED STRING : NOT PRESENT
 --CUSTOM STRING : NOT PRESENT
 --SEVERITY :
::= 116389

networkCard19 TRAP-TYPE
  ENTERPRISE hpnsa
  DESCRIPTION
  "The total number of giant frame packets has exceeded the threshold."
 --#TYPE "Giant Frame Errors exceeded threshold"
 --#SUMMARY "NIC adapter %d giant frame errors exceeded absolute threshold: current value is %d."
 --#ARGUMENTS {0,1}
 --#SEVERITY MAJOR
 --#TIMEINDEX 100
 --#HELP "NIC.hlp"
 --#HELPTAG  204
 --#STATE OPERATIONAL
 --FIXED STRING : NOT PRESENT
 --CUSTOM STRING : NOT PRESENT
 --SEVERITY :
::= 216389

networkCard20 TRAP-TYPE
  ENTERPRISE hpnsa
  DESCRIPTION
  "The total number of giant frame packets has exceeded the threshold."
 --#TYPE "Giant Frame Errors exceeded threshold"
 --#SUMMARY "NIC adapter %d giant frame errors exceeded delta threshold: current value is %d."
 --#ARGUMENTS {0,1}
 --#SEVERITY MAJOR
 --#TIMEINDEX 100
 --#HELP "NIC.hlp"
 --#HELPTAG  204
 --#STATE OPERATIONAL
 --FIXED STRING : NOT PRESENT
 --CUSTOM STRING : NOT PRESENT
 --SEVERITY :
::= 316389

networkCard21 TRAP-TYPE
  ENTERPRISE hpnsa
  DESCRIPTION
  "The total number of packets with length less than the required minimum length has exceeded the threshold."
 --#TYPE "Hardware Mismatch Errors exceeded threshold"
 --#SUMMARY "Hardware Mismatch Errors exceeded threshold"
 --#ARGUMENTS {}
 --#SEVERITY MAJOR
 --#TIMEINDEX 100
 --#HELP "NIC.hlp"
 --#HELPTAG  205
 --#STATE OPERATIONAL
 --FIXED STRING : NOT PRESENT
 --CUSTOM STRING : NOT PRESENT
 --SEVERITY :
::= 16390

networkCard22 TRAP-TYPE
  ENTERPRISE hpnsa
  DESCRIPTION
  "The total number of packets with length less than the required minimum length has exceeded the threshold."
 --#TYPE "Hardware Mismatch Errors exceeded threshold"
 --#SUMMARY "NIC adapter %d, packet length error count pass threshold of %d."
 --#ARGUMENTS {0,1}
 --#SEVERITY MAJOR
 --#TIMEINDEX 100
 --#HELP "NIC.hlp"
 --#HELPTAG  205
 --#STATE OPERATIONAL
 --FIXED STRING : NOT PRESENT
 --CUSTOM STRING : NOT PRESENT
 --SEVERITY :
::= 116390

networkCard23 TRAP-TYPE
  ENTERPRISE hpnsa
  DESCRIPTION
  "The total number of packets with length less than the required minimum length has exceeded the threshold."
 --#TYPE "Hardware Mismatch Errors exceeded threshold"
 --#SUMMARY "NIC adapter %d, packet length error count pass threshold of %d."
 --#ARGUMENTS {0,1}
 --#SEVERITY MAJOR
 --#TIMEINDEX 100
 --#HELP "NIC.hlp"
 --#HELPTAG  205
 --#STATE OPERATIONAL
 --FIXED STRING : NOT PRESENT
 --CUSTOM STRING : NOT PRESENT
 --SEVERITY :
::= 216390

networkCard24 TRAP-TYPE
  ENTERPRISE hpnsa
  DESCRIPTION
  "The total number of packets with length less than the required minimum length has exceeded the threshold."
 --#TYPE "Hardware Mismatch Errors exceeded threshold"
 --#SUMMARY "NIC adapter %d, packet length error count pass threshold of %d."
 --#ARGUMENTS {0,1}
 --#SEVERITY MAJOR
 --#TIMEINDEX 100
 --#HELP "NIC.hlp"
 --#HELPTAG  205
 --#STATE OPERATIONAL
 --FIXED STRING : NOT PRESENT
 --CUSTOM STRING : NOT PRESENT
 --SEVERITY :
::= 316390

networkCard25 TRAP-TYPE
  ENTERPRISE hpnsa
  DESCRIPTION
  "The total number of late collision errors has exceeded the threshold (the network is too large)."
 --#TYPE "Late Collision Errors exceeded threshold"
 --#SUMMARY "Late Collision Errors exceeded threshold"
 --#ARGUMENTS {}
 --#SEVERITY MAJOR
 --#TIMEINDEX 100
 --#HELP "NIC.hlp"
 --#HELPTAG  206
 --#STATE OPERATIONAL
 --FIXED STRING : NOT PRESENT
 --CUSTOM STRING : NOT PRESENT
 --SEVERITY :
::= 16391

networkCard26 TRAP-TYPE
  ENTERPRISE hpnsa
  DESCRIPTION
  "The total number of late collision errors has exceeded the threshold (the network is too large)."
 --#TYPE "Late Collision Errors exceeded threshold"
 --#SUMMARY "NIC adapter %d late collisions errors exceeded relative threshold: current value is %d."
 --#ARGUMENTS {0,1}
 --#SEVERITY MAJOR
 --#TIMEINDEX 100
 --#HELP "NIC.hlp"
 --#HELPTAG  206
 --#STATE OPERATIONAL
 --FIXED STRING : NOT PRESENT
 --CUSTOM STRING : NOT PRESENT
 --SEVERITY :
::= 116391

networkCard27 TRAP-TYPE
  ENTERPRISE hpnsa
  DESCRIPTION
  "The total number of late collision errors has exceeded the threshold (the network is too large)."
 --#TYPE "Late Collision Errors exceeded threshold"
 --#SUMMARY "NIC adapter %d late collisions errors exceeded absolute threshold: current value is %d."
 --#ARGUMENTS {0,1}
 --#SEVERITY MAJOR
 --#TIMEINDEX 100
 --#HELP "NIC.hlp"
 --#HELPTAG  206
 --#STATE OPERATIONAL
 --FIXED STRING : NOT PRESENT
 --CUSTOM STRING : NOT PRESENT
 --SEVERITY :
::= 216391

networkCard28 TRAP-TYPE
  ENTERPRISE hpnsa
  DESCRIPTION
  "The total number of late collision errors has exceeded the threshold (the network is too large)."
 --#TYPE "Late Collision Errors exceeded threshold"
 --#SUMMARY "NIC adapter %d late collisions errors exceeded delta threshold: current value is %d."
 --#ARGUMENTS {0,1}
 --#SEVERITY MAJOR
 --#TIMEINDEX 100
 --#HELP "NIC.hlp"
 --#HELPTAG  206
 --#STATE OPERATIONAL
 --FIXED STRING : NOT PRESENT
 --CUSTOM STRING : NOT PRESENT
 --SEVERITY :
::= 316391

networkCard29 TRAP-TYPE
  ENTERPRISE hpnsa
  DESCRIPTION
  "The total number of colliding packets has exceeded the threshold (the network is too busy)."
 --#TYPE "Excessive Collision Errors exceeded threshold"
 --#SUMMARY "Excessive Collision Errors exceeded threshold"
 --#ARGUMENTS {}
 --#SEVERITY MAJOR
 --#TIMEINDEX 100
 --#HELP "NIC.hlp"
 --#HELPTAG  207
 --#STATE OPERATIONAL
 --FIXED STRING : NOT PRESENT
 --CUSTOM STRING : NOT PRESENT
 --SEVERITY :
::= 16392

networkCard30 TRAP-TYPE
  ENTERPRISE hpnsa
  DESCRIPTION
  "The total number of colliding packets has exceeded the threshold (the network is too busy)."
 --#TYPE "Excessive Collision Errors exceeded threshold"
 --#SUMMARY "NIC adapter %d excessive collision errors exceeded threshold of %d."
 --#ARGUMENTS {0,1}
 --#SEVERITY MAJOR
 --#TIMEINDEX 100
 --#HELP "NIC.hlp"
 --#HELPTAG  207
 --#STATE OPERATIONAL
 --FIXED STRING : NOT PRESENT
 --CUSTOM STRING : NOT PRESENT
 --SEVERITY :
::= 116392

networkCard31 TRAP-TYPE
  ENTERPRISE hpnsa
  DESCRIPTION
  "The total number of colliding packets has exceeded the threshold (the network is too busy)."
 --#TYPE "Excessive Collision Errors exceeded threshold"
 --#SUMMARY "NIC adapter %d excessive collision errors exceeded threshold of %d."
 --#ARGUMENTS {0,1}
 --#SEVERITY MAJOR
 --#TIMEINDEX 100
 --#HELP "NIC.hlp"
 --#HELPTAG  207
 --#STATE OPERATIONAL
 --FIXED STRING : NOT PRESENT
 --CUSTOM STRING : NOT PRESENT
 --SEVERITY :
::= 216392

networkCard32 TRAP-TYPE
  ENTERPRISE hpnsa
  DESCRIPTION
  "The total number of colliding packets has exceeded the threshold (the network is too busy)."
 --#TYPE "Excessive Collision Errors exceeded threshold"
 --#SUMMARY "NIC adapter %d excessive collision errors exceeded threshold of %d."
 --#ARGUMENTS {0,1}
 --#SEVERITY MAJOR
 --#TIMEINDEX 100
 --#HELP "NIC.hlp"
 --#HELPTAG  207
 --#STATE OPERATIONAL
 --FIXED STRING : NOT PRESENT
 --CUSTOM STRING : NOT PRESENT
 --SEVERITY :
::= 316392

networkCard33 TRAP-TYPE
  ENTERPRISE hpnsa
  DESCRIPTION
  "The total number of carrier sense errors has exceeded the threshold."
 --#TYPE "Carrier Sense Errors exceeded threshold"
 --#SUMMARY "Carrier Sense Errors exceeded threshold"
 --#ARGUMENTS {}
 --#SEVERITY MAJOR
 --#TIMEINDEX 100
 --#HELP "NIC.hlp"
 --#HELPTAG  208
 --#STATE OPERATIONAL
 --FIXED STRING : NOT PRESENT
 --CUSTOM STRING : NOT PRESENT
 --SEVERITY :
::= 16393

networkCard34 TRAP-TYPE
  ENTERPRISE hpnsa
  DESCRIPTION
  "The total number of carrier sense errors has exceeded the threshold."
 --#TYPE "Carrier Sense Errors exceeded threshold"
 --#SUMMARY "NIC adapter %d carrier sense error exceeded relative threshold: current value is %d."
 --#ARGUMENTS {0,1}
 --#SEVERITY MAJOR
 --#TIMEINDEX 100
 --#HELP "NIC.hlp"
 --#HELPTAG  208
 --#STATE OPERATIONAL
 --FIXED STRING : NOT PRESENT
 --CUSTOM STRING : NOT PRESENT
 --SEVERITY :
::= 116393

networkCard35 TRAP-TYPE
  ENTERPRISE hpnsa
  DESCRIPTION
  "The total number of carrier sense errors has exceeded the threshold."
 --#TYPE "Carrier Sense Errors exceeded threshold"
 --#SUMMARY "NIC adapter %d carrier sense error exceeded absolute threshold: current value is %d."
 --#ARGUMENTS {0,1}
 --#SEVERITY MAJOR
 --#TIMEINDEX 100
 --#HELP "NIC.hlp"
 --#HELPTAG  208
 --#STATE OPERATIONAL
 --FIXED STRING : NOT PRESENT
 --CUSTOM STRING : NOT PRESENT
 --SEVERITY :
::= 216393

networkCard36 TRAP-TYPE
  ENTERPRISE hpnsa
  DESCRIPTION
  "The total number of carrier sense errors has exceeded the threshold."
 --#TYPE "Carrier Sense Errors exceeded threshold"
 --#SUMMARY "NIC adapter %d carrier sense error exceeded delta threshold: current value is %d."
 --#ARGUMENTS {0,1}
 --#SEVERITY MAJOR
 --#TIMEINDEX 100
 --#HELP "NIC.hlp"
 --#HELPTAG  208
 --#STATE OPERATIONAL
 --FIXED STRING : NOT PRESENT
 --CUSTOM STRING : NOT PRESENT
 --SEVERITY :
::= 316393

networkCard37 TRAP-TYPE
  ENTERPRISE hpnsa
  DESCRIPTION
  "The total number of adapter deferrals has exceeded the threshold (the network is forever busy)."
 --#TYPE "Deferral Errors exceeded threshold"
 --#SUMMARY "Deferral Errors exceeded threshold"
 --#ARGUMENTS {}
 --#SEVERITY MAJOR
 --#TIMEINDEX 100
 --#HELP "NIC.hlp"
 --#HELPTAG  209
 --#STATE OPERATIONAL
 --FIXED STRING : NOT PRESENT
 --CUSTOM STRING : NOT PRESENT
 --SEVERITY :
::= 16394

networkCard38 TRAP-TYPE
  ENTERPRISE hpnsa
  DESCRIPTION
  "The total number of adapter deferrals has exceeded the threshold (the network is forever busy)."
 --#TYPE "Deferral Errors exceeded threshold"
 --#SUMMARY "NIC adapter %d deferral error exceeded relative threshold: current value is %d."
 --#ARGUMENTS {0,1}
 --#SEVERITY MAJOR
 --#TIMEINDEX 100
 --#HELP "NIC.hlp"
 --#HELPTAG  209
 --#STATE OPERATIONAL
 --FIXED STRING : NOT PRESENT
 --CUSTOM STRING : NOT PRESENT
 --SEVERITY :
::= 116394

networkCard39 TRAP-TYPE
  ENTERPRISE hpnsa
  DESCRIPTION
  "The total number of adapter deferrals has exceeded the threshold (the network is forever busy)."
 --#TYPE "Deferral Errors exceeded threshold"
 --#SUMMARY "NIC adapter %d deferral error exceeded absolute threshold: current value is %d."
 --#ARGUMENTS {0,1}
 --#SEVERITY MAJOR
 --#TIMEINDEX 100
 --#HELP "NIC.hlp"
 --#HELPTAG  209
 --#STATE OPERATIONAL
 --FIXED STRING : NOT PRESENT
 --CUSTOM STRING : NOT PRESENT
 --SEVERITY :
::= 216394

networkCard40 TRAP-TYPE
  ENTERPRISE hpnsa
  DESCRIPTION
  "The total number of adapter deferrals has exceeded the threshold (the network is forever busy)."
 --#TYPE "Deferral Errors exceeded threshold"
 --#SUMMARY "NIC adapter %d deferral error exceeded delta threshold: current value is %d."
 --#ARGUMENTS {0,1}
 --#SEVERITY MAJOR
 --#TIMEINDEX 100
 --#HELP "NIC.hlp"
 --#HELPTAG  209
 --#STATE OPERATIONAL
 --FIXED STRING : NOT PRESENT
 --CUSTOM STRING : NOT PRESENT
 --SEVERITY :
::= 316394

networkCard41 TRAP-TYPE
  ENTERPRISE hpnsa
  DESCRIPTION
  "The total number of No ECB errors (LAN adapter is out of receive buffers) errors has exceeded the threshold."
 --#TYPE "No ECB Errors exceeded threshold"
 --#SUMMARY "No ECB Errors exceeded threshold"
 --#ARGUMENTS {}
 --#SEVERITY MAJOR
 --#TIMEINDEX 100
 --#HELP "NIC.hlp"
 --#HELPTAG  210
 --#STATE OPERATIONAL
 --FIXED STRING : NOT PRESENT
 --CUSTOM STRING : NOT PRESENT
 --SEVERITY :
::= 16395

networkCard42 TRAP-TYPE
  ENTERPRISE hpnsa
  DESCRIPTION
  "The total number of No ECB errors (LAN adapter is out of receive buffers) errors has exceeded the threshold."
 --#TYPE "No ECB Errors exceeded threshold"
 --#SUMMARY "NIC adapter %d no ECB errors exceeded relative threshold: current value is %d."
 --#ARGUMENTS {0,1}
 --#SEVERITY MAJOR
 --#TIMEINDEX 100
 --#HELP "NIC.hlp"
 --#HELPTAG  210
 --#STATE OPERATIONAL
 --FIXED STRING : NOT PRESENT
 --CUSTOM STRING : NOT PRESENT
 --SEVERITY :
::= 116395

networkCard43 TRAP-TYPE
  ENTERPRISE hpnsa
  DESCRIPTION
  "The total number of No ECB errors (LAN adapter is out of receive buffers) errors has exceeded the threshold."
 --#TYPE "No ECB Errors exceeded threshold"
 --#SUMMARY "NIC adapter %d no ECB errors exceeded  absolute threshold: current value is %d."
 --#ARGUMENTS {0,1}
 --#SEVERITY MAJOR
 --#TIMEINDEX 100
 --#HELP "NIC.hlp"
 --#HELPTAG  210
 --#STATE OPERATIONAL
 --FIXED STRING : NOT PRESENT
 --CUSTOM STRING : NOT PRESENT
 --SEVERITY :
::= 216395

networkCard44 TRAP-TYPE
  ENTERPRISE hpnsa
  DESCRIPTION
  "The total number of No ECB errors (LAN adapter is out of receive buffers) errors has exceeded the threshold."
 --#TYPE "No ECB Errors exceeded threshold"
 --#SUMMARY "NIC adapter %d no ECB errors exceeded delta threshold: current value is %d."
 --#ARGUMENTS {0,1}
 --#SEVERITY MAJOR
 --#TIMEINDEX 100
 --#HELP "NIC.hlp"
 --#HELPTAG  210
 --#STATE OPERATIONAL
 --FIXED STRING : NOT PRESENT
 --CUSTOM STRING : NOT PRESENT
 --SEVERITY :
::= 316395

networkCard45 TRAP-TYPE
  ENTERPRISE hpnsa
  DESCRIPTION
  "The total number of Receive Overflow errors has exceeded the threshold."
 --#TYPE "Rx Overflow errors exceeded threshold"
 --#SUMMARY "Rx Overflow errors exceeded threshold"
 --#ARGUMENTS {}
 --#SEVERITY CRITICAL
 --#TIMEINDEX 100
 --#HELP "NIC.hlp"
 --#HELPTAG  211
 --#STATE OPERATIONAL
 --FIXED STRING : NOT PRESENT
 --CUSTOM STRING : NOT PRESENT
 --SEVERITY :
::= 16396

networkCard46 TRAP-TYPE
  ENTERPRISE hpnsa
  DESCRIPTION
  "The total number of Receive Overflow errors has exceeded the threshold."
 --#TYPE "Rx Overflow errors exceeded threshold"
 --#SUMMARY "NIC adapter %d Rx overflow errrors exceeded relative threshold: current value is %d."
 --#ARGUMENTS {0,1}
 --#SEVERITY CRITICAL
 --#TIMEINDEX 100
 --#HELP "NIC.hlp"
 --#HELPTAG  211
 --#STATE OPERATIONAL
 --FIXED STRING : NOT PRESENT
 --CUSTOM STRING : NOT PRESENT
 --SEVERITY :
::= 116396

networkCard47 TRAP-TYPE
  ENTERPRISE hpnsa
  DESCRIPTION
  "The total number of Receive Overflow errors has exceeded the threshold."
 --#TYPE "Rx Overflow errors exceeded threshold"
 --#SUMMARY "NIC adapter %d Rx overflow errrors exceeded absolute threshold: current value is %d."
 --#ARGUMENTS {0,1}
 --#SEVERITY CRITICAL
 --#TIMEINDEX 100
 --#HELP "NIC.hlp"
 --#HELPTAG  211
 --#STATE OPERATIONAL
 --FIXED STRING : NOT PRESENT
 --CUSTOM STRING : NOT PRESENT
 --SEVERITY :
::= 216396

networkCard48 TRAP-TYPE
  ENTERPRISE hpnsa
  DESCRIPTION
  "The total number of Receive Overflow errors has exceeded the threshold."
 --#TYPE "Rx Overflow errors exceeded threshold"
 --#SUMMARY "NIC adapter %d Rx overflow errrors exceeded delta threshold: current value is %d."
 --#ARGUMENTS {0,1}
 --#SEVERITY CRITICAL
 --#TIMEINDEX 100
 --#HELP "NIC.hlp"
 --#HELPTAG  211
 --#STATE OPERATIONAL
 --FIXED STRING : NOT PRESENT
 --CUSTOM STRING : NOT PRESENT
 --SEVERITY :
::= 316396

networkCard49 TRAP-TYPE
  ENTERPRISE hpnsa
  DESCRIPTION
  "LAN adapter utilization count has exceeded the threshold."
 --#TYPE "Utilization count exceeded threshold"
 --#SUMMARY "Utilization count exceeded threshold"
 --#ARGUMENTS {}
 --#SEVERITY INFORMATIONAL
 --#TIMEINDEX 100
 --#HELP "NIC.hlp"
 --#HELPTAG  212
 --#STATE OPERATIONAL
 --FIXED STRING : NOT PRESENT
 --CUSTOM STRING : NOT PRESENT
 --SEVERITY :
::= 16397

networkCard50 TRAP-TYPE
  ENTERPRISE hpnsa
  DESCRIPTION
  "LAN adapter utilization count has exceeded the threshold."
 --#TYPE "Utilization count exceeded threshold"
 --#SUMMARY "NIC adapter %d utilization count exceeded relative threshold: current value is %d."
 --#ARGUMENTS {0,1}
 --#SEVERITY INFORMATIONAL
 --#TIMEINDEX 100
 --#HELP "NIC.hlp"
 --#HELPTAG  212
 --#STATE OPERATIONAL
 --FIXED STRING : NOT PRESENT
 --CUSTOM STRING : NOT PRESENT
 --SEVERITY :
::= 116397

networkCard51 TRAP-TYPE
  ENTERPRISE hpnsa
  DESCRIPTION
  "LAN adapter utilization count has exceeded the threshold."
 --#TYPE "Utilization count exceeded threshold"
 --#SUMMARY "NIC adapter %d utilization count exceeded absolute threshold: current value is %d."
 --#ARGUMENTS {0,1}
 --#SEVERITY INFORMATIONAL
 --#TIMEINDEX 100
 --#HELP "NIC.hlp"
 --#HELPTAG  212
 --#STATE OPERATIONAL
 --FIXED STRING : NOT PRESENT
 --CUSTOM STRING : NOT PRESENT
 --SEVERITY :
::= 216397

networkCard52 TRAP-TYPE
  ENTERPRISE hpnsa
  DESCRIPTION
  "LAN adapter utilization count has exceeded the threshold."
 --#TYPE "Utilization count exceeded threshold"
 --#SUMMARY "NIC adapter %d utilization count exceeded delta threshold: current value is %d."
 --#ARGUMENTS {0,1}
 --#SEVERITY INFORMATIONAL
 --#TIMEINDEX 100
 --#HELP "NIC.hlp"
 --#HELPTAG  212
 --#STATE OPERATIONAL
 --FIXED STRING : NOT PRESENT
 --CUSTOM STRING : NOT PRESENT
 --SEVERITY :
::= 316397

networkCard53 TRAP-TYPE
  ENTERPRISE hpnsa
  DESCRIPTION
  "The LAN adapter which the alarms were configured for, has been replaced by another type of LAN adapter."
 --#TYPE "Adapter Mismatch"
 --#SUMMARY "Adapter Mismatch"
 --#ARGUMENTS {}
 --#SEVERITY MAJOR
 --#TIMEINDEX 100
 --#HELP "NIC.hlp"
 --#HELPTAG  213
 --#STATE OPERATIONAL
 --FIXED STRING : NOT PRESENT
 --CUSTOM STRING : NOT PRESENT
 --SEVERITY :
::= 16398

networkCard54 TRAP-TYPE
  ENTERPRISE hpnsa
  DESCRIPTION
  "The LAN adapter which the alarms were configured for, has been replaced by another type of LAN adapter."
 --#TYPE "Adapter Mismatch"
 --#SUMMARY "NIC adapter %d adapter mismatch."
 --#ARGUMENTS {0}
 --#SEVERITY MAJOR
 --#TIMEINDEX 100
 --#HELP "NIC.hlp"
 --#HELPTAG  213
 --#STATE OPERATIONAL
 --FIXED STRING : NOT PRESENT
 --CUSTOM STRING : NOT PRESENT
 --SEVERITY :
::= 116398

networkCard55 TRAP-TYPE
  ENTERPRISE hpnsa
  DESCRIPTION
  "There possibly is a dataflow problem with your HP LAN adapter."
 --#TYPE "Adapter Tx FIFO Underrun errors"
 --#SUMMARY "Adapter Tx FIFO Underrun errors"
 --#ARGUMENTS {}
 --#SEVERITY MAJOR
 --#TIMEINDEX 100
 --#HELP "NIC.hlp"
 --#HELPTAG  214
 --#STATE OPERATIONAL
 --FIXED STRING : NOT PRESENT
 --CUSTOM STRING : NOT PRESENT
 --SEVERITY :
::= 16399

networkCard56 TRAP-TYPE
  ENTERPRISE hpnsa
  DESCRIPTION
  "The HP LAN adapter driver did not receive a transmit complete interrupt."
 --#TYPE "Adapter Tx Timed Out error"
 --#SUMMARY "Adapter Tx Timed Out errors"
 --#ARGUMENTS {}
 --#SEVERITY MAJOR
 --#TIMEINDEX 100
 --#HELP "NIC.hlp"
 --#HELPTAG  215
 --#STATE OPERATIONAL
 --FIXED STRING : NOT PRESENT
 --CUSTOM STRING : NOT PRESENT
 --SEVERITY :
::= 16400

networkCard57 TRAP-TYPE
  ENTERPRISE hpnsa
  DESCRIPTION
  "There possibly is a dataflow problem with your HP LAN adapter."
 --#TYPE "Adapter Rx FIFO Overrun errors"
 --#SUMMARY "Adapter Rx Fifo Overrun errors"
 --#ARGUMENTS {}
 --#SEVERITY MAJOR
 --#TIMEINDEX 100
 --#HELP "NIC.hlp"
 --#HELPTAG  216
 --#STATE OPERATIONAL
 --FIXED STRING : NOT PRESENT
 --CUSTOM STRING : NOT PRESENT
 --SEVERITY :
::= 16401

networkCard58 TRAP-TYPE
  ENTERPRISE hpnsa
  DESCRIPTION
  "There is a dataflow problem with your HP LAN adapter - receive interrupts are being generated, but no receive packets are being present."
 --#TYPE "Adapter Rx False Interrupt errors"
 --#SUMMARY "Adapter Rx False Interrupt errors"
 --#ARGUMENTS {}
 --#SEVERITY INFORMATIONAL
 --#TIMEINDEX 100
 --#HELP "NIC.hlp"
 --#HELPTAG  217
 --#STATE OPERATIONAL
 --FIXED STRING : NOT PRESENT
 --CUSTOM STRING : NOT PRESENT
 --SEVERITY :
::= 16402

networkCard59 TRAP-TYPE
  ENTERPRISE hpnsa
  DESCRIPTION
  "There possibly is a problem with your HP LAN adapter - it generates too many buffer pointer errors."
 --#TYPE "Adapter Rx Paging errors"
 --#SUMMARY "Adapter Rx Paging errors"
 --#ARGUMENTS {}
 --#SEVERITY MAJOR
 --#TIMEINDEX 100
 --#HELP "NIC.hlp"
 --#HELPTAG  218
 --#STATE OPERATIONAL
 --FIXED STRING : NOT PRESENT
 --CUSTOM STRING : NOT PRESENT
 --SEVERITY :
::= 16403

networkCard60 TRAP-TYPE
  ENTERPRISE hpnsa
  DESCRIPTION
  "There possibly is a problem with your HP LAN adapter - DMA timed out while transmitting or receiving a packet."
 --#TYPE "Adapter DMA Timed Out errors"
 --#SUMMARY "Adapter DMA Timed Out errors"
 --#ARGUMENTS {}
 --#SEVERITY MAJOR
 --#TIMEINDEX 100
 --#HELP "NIC.hlp"
 --#HELPTAG  219
 --#STATE OPERATIONAL
 --FIXED STRING : NOT PRESENT
 --CUSTOM STRING : NOT PRESENT
 --SEVERITY :
::= 16404

networkCard61 TRAP-TYPE
  ENTERPRISE hpnsa
  DESCRIPTION
  "The HP LAN adapter is transmitting faster than the media can handle."
 --#TYPE "Adapter Tx No Resources errors"
 --#SUMMARY "Adapter Tx No Resources errors"
 --#ARGUMENTS {}
 --#SEVERITY INFORMATIONAL
 --#TIMEINDEX 100
 --#HELP "NIC.hlp"
 --#HELPTAG  220
 --#STATE OPERATIONAL
 --FIXED STRING : NOT PRESENT
 --CUSTOM STRING : NOT PRESENT
 --SEVERITY :
::= 16405

networkCard62 TRAP-TYPE
  ENTERPRISE hpnsa
  DESCRIPTION
  "The number of buffer fragments has exceeded the maximum number allowed by the network protocol in your HP LAN adapter."
 --#TYPE "Adapter Tx Excessive Frags errors"
 --#SUMMARY "Adapter Tx Excessive Frags errors"
 --#ARGUMENTS {}
 --#SEVERITY MAJOR
 --#TIMEINDEX 100
 --#HELP "NIC.hlp"
 --#HELPTAG  221
 --#STATE OPERATIONAL
 --FIXED STRING : NOT PRESENT
 --CUSTOM STRING : NOT PRESENT
 --SEVERITY :
::= 16406

networkCard63 TRAP-TYPE
  ENTERPRISE hpnsa
  DESCRIPTION
  "The total number of errors due to requests of an ECB being denied has exceeded the threshold."
 --#TYPE "Adapter Rx Low Errors"
 --#SUMMARY "Adapter Rx Low errors"
 --#ARGUMENTS {}
 --#SEVERITY INFORMATIONAL
 --#TIMEINDEX 100
 --#HELP "NIC.hlp"
 --#HELPTAG  222
 --#STATE OPERATIONAL
 --FIXED STRING : NOT PRESENT
 --CUSTOM STRING : NOT PRESENT
 --SEVERITY :
::= 16407

networkCard64 TRAP-TYPE
  ENTERPRISE hpnsa
  DESCRIPTION
  "There possibly is a problem with your HP LAN adapter running in bus master mode."
 --#TYPE "Adapter Rx Empty errors"
 --#SUMMARY "Adapter Rx Empty errors"
 --#ARGUMENTS {}
 --#SEVERITY MAJOR
 --#TIMEINDEX 100
 --#HELP "NIC.hlp"
 --#HELPTAG  223
 --#STATE OPERATIONAL
 --FIXED STRING : NOT PRESENT
 --CUSTOM STRING : NOT PRESENT
 --SEVERITY :
::= 16408

networkCard65 TRAP-TYPE
  ENTERPRISE hpnsa
  DESCRIPTION
  "The active NIC in a redundant group has failed.  The standby NIC has taken over."
 --#TYPE "NIC Redundancy Group Failover"
 --#SUMMARY "The active NIC in a redundant group has failed.  The standby NIC has taken over."
 --#ARGUMENTS {}
 --#SEVERITY MAJOR
 --#TIMEINDEX 100
 --#HELP "NIC.hlp"
 --#HELPTAG  224
 --#STATE OPERATIONAL
 --FIXED STRING : NOT PRESENT
 --CUSTOM STRING : NOT PRESENT
 --SEVERITY :
::= 16418

networkCard66 TRAP-TYPE
  ENTERPRISE hpnsa
  DESCRIPTION
  "The active NIC in a redundant group has failed.  The standby NIC has taken over."
 --#TYPE "NIC Redundancy Group Failover"
 --#SUMMARY "The active NIC %d in redundant group %d has failed. The standby NIC %d has taken over."
 --#ARGUMENTS {0,1,2}
 --#SEVERITY MAJOR
 --#TIMEINDEX 100
 --#HELP "NIC.hlp"
 --#HELPTAG  224
 --#STATE OPERATIONAL
 --FIXED STRING : NOT PRESENT
 --CUSTOM STRING : NOT PRESENT
 --SEVERITY :
::= 116418

networkCard67 TRAP-TYPE
  ENTERPRISE hpnsa
  DESCRIPTION
  "A previously failed NIC in a redundant group has become operational."
 --#TYPE "NIC Redundant Group Recovery"
 --#SUMMARY "A previously failed NIC in a redundant group has become operational."
 --#ARGUMENTS {}
 --#SEVERITY INFORMATIONAL
 --#TIMEINDEX 100
 --#HELP "NIC.hlp"
 --#HELPTAG  225
 --#STATE OPERATIONAL
 --FIXED STRING : NOT PRESENT
 --CUSTOM STRING : NOT PRESENT
 --SEVERITY :
::= 16419

networkCard68 TRAP-TYPE
  ENTERPRISE hpnsa
  DESCRIPTION
  "A previously failed NIC in a redundant group has become operational."
 --#TYPE "NIC Redundant Group Recovery"
 --#SUMMARY "A previously failed NIC %d in redundant group %d has become operational."
 --#ARGUMENTS {0,1}
 --#SEVERITY INFORMATIONAL
 --#TIMEINDEX 100
 --#HELP "NIC.hlp"
 --#HELPTAG  225
 --#STATE OPERATIONAL
 --FIXED STRING : NOT PRESENT
 --CUSTOM STRING : NOT PRESENT
 --SEVERITY :
::= 116419

networkCard69 TRAP-TYPE
  ENTERPRISE hpnsa
  DESCRIPTION
  "The standby NIC in a redundant group has failed."
 --#TYPE "NIC Redundant Group Standby Failure"
 --#SUMMARY "The standby NIC in a redundant group has failed."
 --#ARGUMENTS {}
 --#SEVERITY MAJOR
 --#TIMEINDEX 100
 --#HELP "NIC.hlp"
 --#HELPTAG  226
 --#STATE OPERATIONAL
 --FIXED STRING : NOT PRESENT
 --CUSTOM STRING : NOT PRESENT
 --SEVERITY :
::= 16420

networkCard70 TRAP-TYPE
  ENTERPRISE hpnsa
  DESCRIPTION
  "The standby NIC in a redundant group has failed."
 --#TYPE "NIC Redundant Group Standby Failure"
 --#SUMMARY "The standby NIC %d in redundant group %d has failed."
 --#ARGUMENTS {0,1}
 --#SEVERITY MAJOR
 --#TIMEINDEX 100
 --#HELP "NIC.hlp"
 --#HELPTAG  226
 --#STATE OPERATIONAL
 --FIXED STRING : NOT PRESENT
 --CUSTOM STRING : NOT PRESENT
 --SEVERITY :
::= 116420

networkCard71 TRAP-TYPE
  ENTERPRISE hpnsa
  DESCRIPTION
  "All NICs (active and standby) in a redundant group have failed."
 --#TYPE "NIC Redundant Group Failure"
 --#SUMMARY "All NICs (active and standby) in a redundant group"
 --#ARGUMENTS {}
 --#SEVERITY CRITICAL
 --#TIMEINDEX 100
 --#HELP "NIC.hlp"
 --#HELPTAG  227
 --#STATE OPERATIONAL
 --FIXED STRING : NOT PRESENT
 --CUSTOM STRING : NOT PRESENT
 --SEVERITY :
::= 16421

networkCard72 TRAP-TYPE
  ENTERPRISE hpnsa
  DESCRIPTION
  "All NICs (active and standby) in a redundant group have failed."
 --#TYPE "NIC Redundant Group Failure"
 --#SUMMARY "All NICs (active and standby) in redundant group %d have failed."
 --#ARGUMENTS {0}
 --#SEVERITY CRITICAL
 --#TIMEINDEX 100
 --#HELP "NIC.hlp"
 --#HELPTAG  227
 --#STATE OPERATIONAL
 --FIXED STRING : NOT PRESENT
 --CUSTOM STRING : NOT PRESENT
 --SEVERITY :
::= 116421

rAASR1 TRAP-TYPE
  ENTERPRISE hpnsaRemoteAssist
  DESCRIPTION
  "ASR has stopped notifying the HP Remote Assistant Card that the system is running correctly (the server probably hung or crashed)."
 --#TYPE "Warning NOS hang (ASR)"
 --#SUMMARY "Warning NOS hang (ASR)"
 --#ARGUMENTS {}
 --#SEVERITY INFORMATIONAL
 --#TIMEINDEX 100
 --#HELP "RA.hlp"
 --#HELPTAG  12
 --#STATE OPERATIONAL
 --FIXED STRING : NOT PRESENT
 --CUSTOM STRING : NOT PRESENT
 --SEVERITY :
::= 501

rAASR2 TRAP-TYPE
  ENTERPRISE hpnsaRemoteAssist
  DESCRIPTION
  "The HP Remote Assistant card has restarted the server due to the NOS being hung."
 --#TYPE "Server Restart after NOS hang (ASR)"
 --#SUMMARY "Server Restart after NOS hang (ASR)"
 --#ARGUMENTS {}
 --#SEVERITY INFORMATIONAL
 --#TIMEINDEX 100
 --#HELP "RA.hlp"
 --#HELPTAG  13
 --#STATE OPERATIONAL
 --FIXED STRING : NOT PRESENT
 --CUSTOM STRING : NOT PRESENT
 --SEVERITY :
::= 502

rAASR3 TRAP-TYPE
  ENTERPRISE hpnsaRemoteAssist
  DESCRIPTION
  "The Automatic Server Restart software has been enabled by the Remote Assistant ASR timer."
 --#TYPE "ASR Timer Enabled"
 --#SUMMARY "ASR Timer Enabled"
 --#ARGUMENTS {}
 --#SEVERITY INFORMATIONAL
 --#TIMEINDEX 100
 --#HELP "RA.hlp"
 --#HELPTAG  24
 --#STATE OPERATIONAL
 --FIXED STRING : NOT PRESENT
 --CUSTOM STRING : NOT PRESENT
 --SEVERITY :
::= 503

rAASR4 TRAP-TYPE
  ENTERPRISE hpnsaRemoteAssist
  DESCRIPTION
  "The HP Remote Assistant Automatic Server Restart timer has been disabled."
 --#TYPE "ASR Timer Disabled"
 --#SUMMARY "ASR Timer Disabled"
 --#ARGUMENTS {}
 --#SEVERITY INFORMATIONAL
 --#TIMEINDEX 100
 --#HELP "RA.hlp"
 --#HELPTAG  25
 --#STATE OPERATIONAL
 --FIXED STRING : NOT PRESENT
 --CUSTOM STRING : NOT PRESENT
 --SEVERITY :
::= 504

rABusUsage1 TRAP-TYPE
  ENTERPRISE hpnsaRemoteAssist
  DESCRIPTION
  "The 5-minute average EISA bus utilization has exceeded the configured threshold."
 --#TYPE "Bus Utilization"
 --#SUMMARY "Bus Utilization"
 --#ARGUMENTS {}
 --#SEVERITY MAJOR
 --#TIMEINDEX 100
 --#HELP "RA.hlp"
 --#HELPTAG  14
 --#STATE OPERATIONAL
 --FIXED STRING : NOT PRESENT
 --CUSTOM STRING : NOT PRESENT
 --SEVERITY :
::= 800

rAOther1 TRAP-TYPE
  ENTERPRISE hpnsaRemoteAssist
  DESCRIPTION
  "An administrator has logged in to the HP Remote Assistant Card."
 --#TYPE "Successful Login"
 --#SUMMARY "Successful Login"
 --#ARGUMENTS {}
 --#SEVERITY INFORMATIONAL
 --#TIMEINDEX 100
 --#HELP "RA.hlp"
 --#HELPTAG  15
 --#STATE OPERATIONAL
 --FIXED STRING : NOT PRESENT
 --CUSTOM STRING : NOT PRESENT
 --SEVERITY :
::= 401

rAOther2 TRAP-TYPE
  ENTERPRISE hpnsaRemoteAssist
  DESCRIPTION
  "A remote user has logged in to the HP RA or Remote Control card."
 --#TYPE "Remote management user login"
 --#SUMMARY "Remote management user %d login"
 --#ARGUMENTS {0}
 --#SEVERITY INFORMATIONAL
 --#TIMEINDEX 100
 --#HELP "RA.hlp"
 --#HELPTAG  15
 --#STATE OPERATIONAL
 --FIXED STRING : NOT PRESENT
 --CUSTOM STRING : NOT PRESENT
 --SEVERITY :
::= 2401

rAOther3 TRAP-TYPE
  ENTERPRISE hpnsaRemoteAssist
  DESCRIPTION
  "An unauthorized user has made 3 or more unsuccessful attempts to log in to the HP Remote Assistant Card within a 5-minute period of time."
 --#TYPE "Illegal Login"
 --#SUMMARY "Illegal Login"
 --#ARGUMENTS {}
 --#SEVERITY MAJOR
 --#TIMEINDEX 100
 --#HELP "RA.hlp"
 --#HELPTAG  16
 --#STATE OPERATIONAL
 --FIXED STRING : NOT PRESENT
 --CUSTOM STRING : NOT PRESENT
 --SEVERITY :
::= 402

rAOther4 TRAP-TYPE
  ENTERPRISE hpnsaRemoteAssist
  DESCRIPTION
  "An unauthorized user has made 3 or more unsuccessful attempts to log in to the HP RA or Remote Control card."
 --#TYPE "Failed remote management login attempt"
 --#SUMMARY "%d failed remote management logins"
 --#ARGUMENTS {0}
 --#SEVERITY MAJOR
 --#TIMEINDEX 100
 --#HELP "RA.hlp"
 --#HELPTAG  16
 --#STATE OPERATIONAL
 --FIXED STRING : NOT PRESENT
 --CUSTOM STRING : NOT PRESENT
 --SEVERITY :
::= 2402

rAOther5 TRAP-TYPE
  ENTERPRISE hpnsaRemoteAssist
  DESCRIPTION
  "The HP Remote Assistant Card's battery charging circuit is bad."
 --#TYPE "Low Battery Charge"
 --#SUMMARY "Low Battery Charge"
 --#ARGUMENTS {}
 --#SEVERITY INFORMATIONAL
 --#TIMEINDEX 100
 --#HELP "RA.hlp"
 --#HELPTAG  17
 --#STATE OPERATIONAL
 --FIXED STRING : NOT PRESENT
 --CUSTOM STRING : NOT PRESENT
 --SEVERITY :
::= 403

rAOther6 TRAP-TYPE
  ENTERPRISE hpnsaRemoteAssist
  DESCRIPTION
  "The HP Remote Assistant Card has been shut down."
 --#TYPE "Board shut down"
 --#SUMMARY "Board has shut down"
 --#ARGUMENTS {}
 --#SEVERITY INFORMATIONAL
 --#TIMEINDEX 100
 --#HELP "RA.hlp"
 --#HELPTAG  18
 --#STATE OPERATIONAL
 --FIXED STRING : NOT PRESENT
 --CUSTOM STRING : NOT PRESENT
 --SEVERITY :
::= 404

rAOther7 TRAP-TYPE
  ENTERPRISE hpnsaRemoteAssist
  DESCRIPTION
  "An administrator has executed a remote <Ctrl-Alt-Del> on the server via the HP Remote Assistant Card."
 --#TYPE "Remote Initiates <Ctrl-Alt-Del>"
 --#SUMMARY "Remote Initiated <Ctrl-Alt-Del>"
 --#ARGUMENTS {}
 --#SEVERITY INFORMATIONAL
 --#TIMEINDEX 100
 --#HELP "RA.hlp"
 --#HELPTAG  19
 --#STATE OPERATIONAL
 --FIXED STRING : NOT PRESENT
 --CUSTOM STRING : NOT PRESENT
 --SEVERITY :
::= 601

rAOther8 TRAP-TYPE
  ENTERPRISE hpnsaRemoteAssist
  DESCRIPTION
  "An administrator has executed a remote <Ctrl-Alt-Del> on the server via the HP RA or Remote Control card."
 --#TYPE "Remote-initiated <Ctrl-Alt-Del>"
 --#SUMMARY "Remote-initiated <Ctrl-Alt-Del>"
 --#ARGUMENTS {}
 --#SEVERITY INFORMATIONAL
 --#TIMEINDEX 100
 --#HELP "RA.hlp"
 --#HELPTAG  19
 --#STATE OPERATIONAL
 --FIXED STRING : NOT PRESENT
 --CUSTOM STRING : NOT PRESENT
 --SEVERITY :
::= 2601

rAOther9 TRAP-TYPE
  ENTERPRISE hpnsaRemoteAssist
  DESCRIPTION
  "An administrator has executed a remote power cycle on the server via the HP Remote Assistant Card."
 --#TYPE "Remote Initiated Reset or Power Cycle"
 --#SUMMARY "Remote Initiated Reset or Power Cycle"
 --#ARGUMENTS {}
 --#SEVERITY INFORMATIONAL
 --#TIMEINDEX 100
 --#HELP "RA.hlp"
 --#HELPTAG  20
 --#STATE OPERATIONAL
 --FIXED STRING : NOT PRESENT
 --CUSTOM STRING : NOT PRESENT
 --SEVERITY :
::= 602

rAOther10 TRAP-TYPE
  ENTERPRISE hpnsaRemoteAssist
  DESCRIPTION
  "A remote user has executed a remote power cycle on the server via the HP RA or Remote Control."
 --#TYPE "Remote-initiated power cycle"
 --#SUMMARY "Remote-initiated power cycle"
 --#ARGUMENTS {}
 --#SEVERITY INFORMATIONAL
 --#TIMEINDEX 100
 --#HELP "RA.hlp"
 --#HELPTAG  20
 --#STATE OPERATIONAL
 --FIXED STRING : NOT PRESENT
 --CUSTOM STRING : NOT PRESENT
 --SEVERITY :
::= 1602

rAOther11 TRAP-TYPE
  ENTERPRISE hpnsaRemoteAssist
  DESCRIPTION
  "A remote user has executed a remote hard reset on the server via the HP RA or Remote Control."
 --#TYPE "Remote-initiated reset"
 --#SUMMARY "Remote initiated reset"
 --#ARGUMENTS {}
 --#SEVERITY INFORMATIONAL
 --#TIMEINDEX 100
 --#HELP "RA.hlp"
 --#HELPTAG  20
 --#STATE OPERATIONAL
 --FIXED STRING : NOT PRESENT
 --CUSTOM STRING : NOT PRESENT
 --SEVERITY :
::= 3602

rAOther12 TRAP-TYPE
  ENTERPRISE hpnsaRemoteAssist
  DESCRIPTION
  "An administrator has executed a remote power down of the server via the HP Remote Assistant Card."
 --#TYPE "Remote Initiated Power Down"
 --#SUMMARY "Remote Initiated Power Down"
 --#ARGUMENTS {}
 --#SEVERITY INFORMATIONAL
 --#TIMEINDEX 100
 --#HELP "RA.hlp"
 --#HELPTAG  21
 --#STATE OPERATIONAL
 --FIXED STRING : NOT PRESENT
 --CUSTOM STRING : NOT PRESENT
 --SEVERITY :
::= 603

rAOther13 TRAP-TYPE
  ENTERPRISE hpnsaRemoteAssist
  DESCRIPTION
  "A remote user has executed a remote power down of the server via the HP RA or Remote Control card."
 --#TYPE "Remote-initiated power down"
 --#SUMMARY "Remote-initiated power down"
 --#ARGUMENTS {}
 --#SEVERITY INFORMATIONAL
 --#TIMEINDEX 100
 --#HELP "RA.hlp"
 --#HELPTAG  21
 --#STATE OPERATIONAL
 --FIXED STRING : NOT PRESENT
 --CUSTOM STRING : NOT PRESENT
 --SEVERITY :
::= 1603

rAOther14 TRAP-TYPE
  ENTERPRISE hpnsaRemoteAssist
  DESCRIPTION
  "A remote user has executed a remote power up of the server via the HP RA or Remote Control card."
 --#TYPE "Remote-initiated power up"
 --#SUMMARY "Remote-initiated power up"
 --#ARGUMENTS {}
 --#SEVERITY INFORMATIONAL
 --#TIMEINDEX 100
 --#HELP "RA.hlp"
 --#HELPTAG  40
 --#STATE OPERATIONAL
 --FIXED STRING : NOT PRESENT
 --CUSTOM STRING : NOT PRESENT
 --SEVERITY :
::= 3603

rAOther15 TRAP-TYPE
  ENTERPRISE hpnsaRemoteAssist
  DESCRIPTION
  "Automatic power shutdown due to critical condition."
 --#TYPE "Automatic power shutdown due to critical condition"
 --#SUMMARY "Automatic power shutdown due to critical condition."
 --#ARGUMENTS {}
 --#SEVERITY CRITICAL
 --#TIMEINDEX 100
 --#HELP "RA.hlp"
 --#HELPTAG  41
 --#STATE OPERATIONAL
 --FIXED STRING : NOT PRESENT
 --CUSTOM STRING : NOT PRESENT
 --SEVERITY :
::= 4603

rAOther16 TRAP-TYPE
  ENTERPRISE hpnsaRemoteAssist
  DESCRIPTION
  "Front panel power down."
 --#TYPE "Front panel power down"
 --#SUMMARY "Front panel power down"
 --#ARGUMENTS {}
 --#SEVERITY INFORMATIONAL
 --#TIMEINDEX 100
 --#HELP "RA.hlp"
 --#HELPTAG  42
 --#STATE OPERATIONAL
 --FIXED STRING : NOT PRESENT
 --CUSTOM STRING : NOT PRESENT
 --SEVERITY :
::= 5603

rAOther17 TRAP-TYPE
  ENTERPRISE hpnsaRemoteAssist
  DESCRIPTION
  "A remote user has executed a remote graceful shutdown of the server via the HP RA or Remote Control card."
 --#TYPE "Remote-initiated graceful shutdown of NOS"
 --#SUMMARY "Remote-initiated graceful shutdown of NOS by remote management user %d."
 --#ARGUMENTS {0}
 --#SEVERITY INFORMATIONAL
 --#TIMEINDEX 100
 --#HELP "RA.hlp"
 --#HELPTAG  44
 --#STATE OPERATIONAL
 --FIXED STRING : NOT PRESENT
 --CUSTOM STRING : NOT PRESENT
 --SEVERITY :
::= 2604

rAOther18 TRAP-TYPE
  ENTERPRISE hpnsaRemoteAssist
  DESCRIPTION
  "The server's BIOS has successfully initialized the HP Remote Assistant Card during the boot process."
 --#TYPE "Server BIOS Initialization"
 --#SUMMARY "Server BIOS Initialization"
 --#ARGUMENTS {}
 --#SEVERITY INFORMATIONAL
 --#TIMEINDEX 100
 --#HELP "RA.hlp"
 --#HELPTAG  22
 --#STATE OPERATIONAL
 --FIXED STRING : NOT PRESENT
 --CUSTOM STRING : NOT PRESENT
 --SEVERITY :
::= 701

rAOther19 TRAP-TYPE
  ENTERPRISE hpnsaRemoteAssist
  DESCRIPTION
  "An administrator has executed Test Page from the HP Remote Assistant Configuration Utility."
 --#TYPE "Test notification"
 --#SUMMARY "Test Notification"
 --#ARGUMENTS {}
 --#SEVERITY INFORMATIONAL
 --#TIMEINDEX 100
 --#HELP "RA.hlp"
 --#HELPTAG  23
 --#STATE OPERATIONAL
 --FIXED STRING : NOT PRESENT
 --CUSTOM STRING : NOT PRESENT
 --SEVERITY :
::= 900

rAOther20 TRAP-TYPE
  ENTERPRISE hpnsaRemoteAssist
  DESCRIPTION
  "A remote user disconnected from the HP RA or Remote Control card."
 --#TYPE "Remote management user logout"
 --#SUMMARY "Remote management user %d logout"
 --#ARGUMENTS {0}
 --#SEVERITY INFORMATIONAL
 --#TIMEINDEX 100
 --#HELP "RA.hlp"
 --#HELPTAG  26
 --#STATE OPERATIONAL
 --FIXED STRING : NOT PRESENT
 --CUSTOM STRING : NOT PRESENT
 --SEVERITY :
::= 405

rAOther21 TRAP-TYPE
  ENTERPRISE hpnsaRemoteAssist
  DESCRIPTION
  "An administrator has been automatically disconnected from the HP Remote Assistant board. The administrator was inactive for more than five minutes."
 --#TYPE "Administrator Autologout"
 --#SUMMARY "Administrator Autologout"
 --#ARGUMENTS {}
 --#SEVERITY INFORMATIONAL
 --#TIMEINDEX 100
 --#HELP "RA.hlp"
 --#HELPTAG  27
 --#STATE OPERATIONAL
 --FIXED STRING : NOT PRESENT
 --CUSTOM STRING : NOT PRESENT
 --SEVERITY :
::= 406

rAOther22 TRAP-TYPE
  ENTERPRISE hpnsaRemoteAssist
  DESCRIPTION
  "A remote user has been automatically disconnected from the HP RA or Remote Control card, because of inactivity."
 --#TYPE "Remote management user auto-logout"
 --#SUMMARY "Remote management user %d auto-logout"
 --#ARGUMENTS {0}
 --#SEVERITY INFORMATIONAL
 --#TIMEINDEX 100
 --#HELP "RA.hlp"
 --#HELPTAG  27
 --#STATE OPERATIONAL
 --FIXED STRING : NOT PRESENT
 --CUSTOM STRING : NOT PRESENT
 --SEVERITY :
::= 2406

rAOther23 TRAP-TYPE
  ENTERPRISE hpnsaRemoteAssist
  DESCRIPTION
  "An administrator has been prematurely disconnected from the Remote Assistant board."
 --#TYPE "Administrator Connection Lost"
 --#SUMMARY "Administrator Connection Lost"
 --#ARGUMENTS {}
 --#SEVERITY MAJOR
 --#TIMEINDEX 100
 --#HELP "RA.hlp"
 --#HELPTAG  28
 --#STATE OPERATIONAL
 --FIXED STRING : NOT PRESENT
 --CUSTOM STRING : NOT PRESENT
 --SEVERITY :
::= 407

rAOther24 TRAP-TYPE
  ENTERPRISE hpnsaRemoteAssist
  DESCRIPTION
  "A remote user has been prematurely disconnected from the HP RA or Remote Control card."
 --#TYPE "Remote management user connection lost"
 --#SUMMARY "Remote management user %d connection lost"
 --#ARGUMENTS {0}
 --#SEVERITY INFORMATIONAL
 --#TIMEINDEX 100
 --#HELP "RA.hlp"
 --#HELPTAG  28
 --#STATE OPERATIONAL
 --FIXED STRING : NOT PRESENT
 --CUSTOM STRING : NOT PRESENT
 --SEVERITY :
::= 2407

rAOther25 TRAP-TYPE
  ENTERPRISE hpnsaRemoteAssist
  DESCRIPTION
  "An administrator failed to connect to the HP Remote Assistant board on a dialback"
 --#TYPE "Administrator Dialback Failed"
 --#SUMMARY "Administrator Dialback Failed"
 --#ARGUMENTS {}
 --#SEVERITY MAJOR
 --#TIMEINDEX 100
 --#HELP "RA.hlp"
 --#HELPTAG  29
 --#STATE OPERATIONAL
 --FIXED STRING : NOT PRESENT
 --CUSTOM STRING : NOT PRESENT
 --SEVERITY :
::= 408

rAOther26 TRAP-TYPE
  ENTERPRISE hpnsaRemoteAssist
  DESCRIPTION
  "A remote user failed to connect to the HP RA or Remote Control on a dialback"
 --#TYPE "Remote management user dialback failed"
 --#SUMMARY "Remote management user %d dialback has failed"
 --#ARGUMENTS {0}
 --#SEVERITY INFORMATIONAL
 --#TIMEINDEX 100
 --#HELP "RA.hlp"
 --#HELPTAG  29
 --#STATE OPERATIONAL
 --FIXED STRING : NOT PRESENT
 --CUSTOM STRING : NOT PRESENT
 --SEVERITY :
::= 2408

rAOther27 TRAP-TYPE
  ENTERPRISE hpnsaRemoteAssist
  DESCRIPTION
  "Integrated RA configuration reset to defaults"
 --#TYPE "Integrated RA configuration reset to defaults"
 --#SUMMARY "Integrated RA configuration reset to defaults"
 --#ARGUMENTS {}
 --#SEVERITY MAJOR
 --#TIMEINDEX 100
 --#HELP "RA.hlp"
 --#HELPTAG  43
 --#STATE OPERATIONAL
 --FIXED STRING : NOT PRESENT
 --CUSTOM STRING : NOT PRESENT
 --SEVERITY :
::= 3408

rAOther28 TRAP-TYPE
  ENTERPRISE hpnsaRemoteAssist
  DESCRIPTION
  "TopTools Remote Control card configuration was corrupted and has been restored to default settings."
 --#TYPE "Remote Control Card configuration reset to defaults"
 --#SUMMARY "Remote Control Card configuration reset to defaults"
 --#ARGUMENTS {}
 --#SEVERITY MAJOR
 --#TIMEINDEX 100
 --#HELP "RA.hlp"
 --#HELPTAG  43
 --#STATE OPERATIONAL
 --FIXED STRING : NOT PRESENT
 --CUSTOM STRING : NOT PRESENT
 --SEVERITY :
::= 4408

rAOther29 TRAP-TYPE
  ENTERPRISE hpnsaRemoteAssist
  DESCRIPTION
  "The HP Remote Assistant modem was unable to connect to the TAP paging service modem."
 --#TYPE "TAP No Connect"
 --#SUMMARY "TAP No Connect"
 --#ARGUMENTS {}
 --#SEVERITY INFORMATIONAL
 --#TIMEINDEX 100
 --#HELP "RA.hlp"
 --#HELPTAG  30
 --#STATE OPERATIONAL
 --FIXED STRING : NOT PRESENT
 --CUSTOM STRING : NOT PRESENT
 --SEVERITY :
::= 901

rAOther30 TRAP-TYPE
  ENTERPRISE hpnsaRemoteAssist
  DESCRIPTION
  "The HP RA or Remote Control modem was unable to connect to the TAP paging service modem."
 --#TYPE "Remote management page: No Connection"
 --#SUMMARY "Remote management TAP: No Connection"
 --#ARGUMENTS {}
 --#SEVERITY INFORMATIONAL
 --#TIMEINDEX 100
 --#HELP "RA.hlp"
 --#HELPTAG  30
 --#STATE OPERATIONAL
 --FIXED STRING : NOT PRESENT
 --CUSTOM STRING : NOT PRESENT
 --SEVERITY :
::= 2901

rAOther31 TRAP-TYPE
  ENTERPRISE hpnsaRemoteAssist
  DESCRIPTION
  "HP Remote Assistant was unable to connect with the TAP paging service."
 --#TYPE "TAP Parameter 1 Error"
 --#SUMMARY "TAP Parameter 1 Error"
 --#ARGUMENTS {}
 --#SEVERITY INFORMATIONAL
 --#TIMEINDEX 100
 --#HELP "RA.hlp"
 --#HELPTAG  31
 --#STATE OPERATIONAL
 --FIXED STRING : NOT PRESENT
 --CUSTOM STRING : NOT PRESENT
 --SEVERITY :
::= 902

rAOther32 TRAP-TYPE
  ENTERPRISE hpnsaRemoteAssist
  DESCRIPTION
  "HP Remote Assistant was unable to log on to the TAP paging service."
 --#TYPE "TAP Parameter : 2 Error"
 --#SUMMARY "TAP Parameter 2 Error"
 --#ARGUMENTS {}
 --#SEVERITY INFORMATIONAL
 --#TIMEINDEX 100
 --#HELP "RA.hlp"
 --#HELPTAG  32
 --#STATE OPERATIONAL
 --FIXED STRING : NOT PRESENT
 --CUSTOM STRING : NOT PRESENT
 --SEVERITY :
::= 903

rAOther33 TRAP-TYPE
  ENTERPRISE hpnsaRemoteAssist
  DESCRIPTION
  "The HP RA or Remote Control was unable to connect to the TAP paging service."
 --#TYPE "Remote management TAP page: No ID= prompt"
 --#SUMMARY "Remote management TAP page: No ID= prompt"
 --#ARGUMENTS {}
 --#SEVERITY INFORMATIONAL
 --#TIMEINDEX 100
 --#HELP "RA.hlp"
 --#HELPTAG  31
 --#STATE OPERATIONAL
 --FIXED STRING : NOT PRESENT
 --CUSTOM STRING : NOT PRESENT
 --SEVERITY :
::= 2902

rAOther34 TRAP-TYPE
  ENTERPRISE hpnsaRemoteAssist
  DESCRIPTION
  "The HP RA or Remote Control was unable to log on to the TAP paging service."
 --#TYPE "Remote management TAP page: No message go-ahead"
 --#SUMMARY "Remote management TAP page: No message go-ahead"
 --#ARGUMENTS {}
 --#SEVERITY INFORMATIONAL
 --#TIMEINDEX 100
 --#HELP "RA.hlp"
 --#HELPTAG  32
 --#STATE OPERATIONAL
 --FIXED STRING : NOT PRESENT
 --CUSTOM STRING : NOT PRESENT
 --SEVERITY :
::= 2903

rAOther35 TRAP-TYPE
  ENTERPRISE hpnsaRemoteAssist
  DESCRIPTION
  "The HP Remote Assistant pager message was rejected"
 --#TYPE "TAP Parameter 3 Error"
 --#SUMMARY "TAP parameter Error"
 --#ARGUMENTS {}
 --#SEVERITY INFORMATIONAL
 --#TIMEINDEX 100
 --#HELP "RA.hlp"
 --#HELPTAG  33
 --#STATE OPERATIONAL
 --FIXED STRING : NOT PRESENT
 --CUSTOM STRING : NOT PRESENT
 --SEVERITY :
::= 904

rAOther36 TRAP-TYPE
  ENTERPRISE hpnsaRemoteAssist
  DESCRIPTION
  "The HP RA or Remote Control pager message was rejected by the TAP paging service."
 --#TYPE "Remote management TAP page: Message not accepted"
 --#SUMMARY "Remote management TAP page: Message not accepted"
 --#ARGUMENTS {}
 --#SEVERITY INFORMATIONAL
 --#TIMEINDEX 100
 --#HELP "RA.hlp"
 --#HELPTAG  33
 --#STATE OPERATIONAL
 --FIXED STRING : NOT PRESENT
 --CUSTOM STRING : NOT PRESENT
 --SEVERITY :
::= 2904

rAOther37 TRAP-TYPE
  ENTERPRISE hpnsaRemoteAssist
  DESCRIPTION
  "The HP RA or Remote Control email notification message was not sent correctly."
 --#TYPE "Remote management user Email notification failed"
 --#SUMMARY "Remote management user %d Email notification failed"
 --#ARGUMENTS {0}
 --#SEVERITY MAJOR
 --#TIMEINDEX 100
 --#HELP "RA.hlp"
 --#HELPTAG  52
 --#STATE OPERATIONAL
 --FIXED STRING : NOT PRESENT
 --CUSTOM STRING : NOT PRESENT
 --SEVERITY :
::= 2905

rAOther38 TRAP-TYPE
  ENTERPRISE hpnsaRemoteAssist
  DESCRIPTION
  "A modem error has been detected on the remote management card."
 --#TYPE "Remote management modem error."
 --#SUMMARY "Remote management user %d page: Modem error"
 --#ARGUMENTS {0}
 --#SEVERITY INFORMATIONAL
 --#TIMEINDEX 100
 --#HELP "RA.hlp"
 --#HELPTAG  45
 --#STATE OPERATIONAL
 --FIXED STRING : NOT PRESENT
 --CUSTOM STRING : NOT PRESENT
 --SEVERITY :
::= 2906

rAOther39 TRAP-TYPE
  ENTERPRISE hpnsaRemoteAssist
  DESCRIPTION
  "TopTools Remote Control Card memory test started"
 --#TYPE "Remote Control Card memory test started"
 --#SUMMARY "Remote Control Card memory test started"
 --#ARGUMENTS {}
 --#SEVERITY INFORMATIONAL
 --#TIMEINDEX 100
 --#HELP "RA.hlp"
 --#HELPTAG  46
 --#STATE OPERATIONAL
 --FIXED STRING : NOT PRESENT
 --CUSTOM STRING : NOT PRESENT
 --SEVERITY :
::= 2907

rAOther40 TRAP-TYPE
  ENTERPRISE hpnsaRemoteAssist
  DESCRIPTION
  "TopTools Remote Control Card memory test completed"
 --#TYPE "Remote Control Card memory test completed"
 --#SUMMARY "Remote Control Card memory test completed"
 --#ARGUMENTS {}
 --#SEVERITY INFORMATIONAL
 --#TIMEINDEX 100
 --#HELP "RA.hlp"
 --#HELPTAG  53
 --#STATE OPERATIONAL
 --FIXED STRING : NOT PRESENT
 --CUSTOM STRING : NOT PRESENT
 --SEVERITY :
::= 2908

rAOther41 TRAP-TYPE
  ENTERPRISE hpnsaRemoteAssist
  DESCRIPTION
  "TopTools Remote Control Card memory test stopped by user"
 --#TYPE "Remote Control Card memory test stopped by user"
 --#SUMMARY "Remote Control Card memory test stopped by user"
 --#ARGUMENTS {}
 --#SEVERITY INFORMATIONAL
 --#TIMEINDEX 100
 --#HELP "RA.hlp"
 --#HELPTAG  54
 --#STATE OPERATIONAL
 --FIXED STRING : NOT PRESENT
 --CUSTOM STRING : NOT PRESENT
 --SEVERITY :
::= 2909

rAOther42 TRAP-TYPE
  ENTERPRISE hpnsaRemoteAssist
  DESCRIPTION
  "TopTools Remote Control Card memory test error"
 --#TYPE "Remote Control Card memory test error"
 --#SUMMARY "Remote Control Card memory test halted, error: %s"
 --#ARGUMENTS {0}
 --#SEVERITY MAJOR
 --#TIMEINDEX 100
 --#HELP "RA.hlp"
 --#HELPTAG  55
 --#STATE OPERATIONAL
 --FIXED STRING : NOT PRESENT
 --CUSTOM STRING : NOT PRESENT
 --SEVERITY :
::= 2910

rAOther43 TRAP-TYPE
  ENTERPRISE hpnsaRemoteAssist
  DESCRIPTION
  "TopTools Remote Control Card started"
 --#TYPE "Remote Control Card started"
 --#SUMMARY "Remote Control Card started"
 --#ARGUMENTS {}
 --#SEVERITY INFORMATIONAL
 --#TIMEINDEX 100
 --#HELP "RA.hlp"
 --#HELPTAG  47
 --#STATE OPERATIONAL
 --FIXED STRING : NOT PRESENT
 --CUSTOM STRING : NOT PRESENT
 --SEVERITY :
::= 2911

rAOther44 TRAP-TYPE
  ENTERPRISE hpnsaRemoteAssist
  DESCRIPTION
  "TopTools Remote Control Card detects a serious internal error that prevents normal operation of the card"
 --#TYPE "Remote Control Card internal error"
 --#SUMMARY "Remote Control Card internal error"
 --#ARGUMENTS {}
 --#SEVERITY MAJOR
 --#TIMEINDEX 100
 --#HELP "RA.hlp"
 --#HELPTAG  48
 --#STATE OPERATIONAL
 --FIXED STRING : NOT PRESENT
 --CUSTOM STRING : NOT PRESENT
 --SEVERITY :
::= 2912

rAOther45 TRAP-TYPE
  ENTERPRISE hpnsaRemoteAssist
  DESCRIPTION
  "The firmware on the TopTools Remote Control has been updated"
 --#TYPE "Remote Control Card firmware updated"
 --#SUMMARY "Remote Control Card firmware updated"
 --#ARGUMENTS {}
 --#SEVERITY INFORMATIONAL
 --#TIMEINDEX 100
 --#HELP "RA.hlp"
 --#HELPTAG  49
 --#STATE OPERATIONAL
 --FIXED STRING : NOT PRESENT
 --CUSTOM STRING : NOT PRESENT
 --SEVERITY :
::= 2913

rAOther46 TRAP-TYPE
  ENTERPRISE hpnsaRemoteAssist
  DESCRIPTION
  "The TopTools Remote Control backup battery has discharged to a level where it will not be able to power the card"
 --#TYPE "Remote Control Card battery low"
 --#SUMMARY "Remote Control Card battery low"
 --#ARGUMENTS {}
 --#SEVERITY MAJOR
 --#TIMEINDEX 100
 --#HELP "RA.hlp"
 --#HELPTAG  50
 --#STATE OPERATIONAL
 --FIXED STRING : NOT PRESENT
 --CUSTOM STRING : NOT PRESENT
 --SEVERITY :
::= 2914

rAOther47 TRAP-TYPE
  ENTERPRISE hpnsaRemoteAssist
  DESCRIPTION
  "The battery on the TopTools Remote Control card is disconnected"
 --#TYPE "Remote Control Card battery disconnected"
 --#SUMMARY "Remote Control Card battery disconnected"
 --#ARGUMENTS {}
 --#SEVERITY MAJOR
 --#TIMEINDEX 100
 --#HELP "RA.hlp"
 --#HELPTAG  51
 --#STATE OPERATIONAL
 --FIXED STRING : NOT PRESENT
 --CUSTOM STRING : NOT PRESENT
 --SEVERITY :
::= 2915

rAOther48 TRAP-TYPE
  ENTERPRISE hpnsaRemoteAssist
  DESCRIPTION
  "Remote Control Card: DHCP has assigned a new IP address"
 --#TYPE "Remote Control Card: DHCP has assigned a new IP address"
 --#SUMMARY "Remote Control Card: DHCP has assigned a new IP address"
 --#ARGUMENTS {}
 --#SEVERITY MAJOR
 --#TIMEINDEX 100
 --#HELP "RA.hlp"
 --#HELPTAG  56
 --#STATE OPERATIONAL
 --FIXED STRING : NOT PRESENT
 --CUSTOM STRING : NOT PRESENT
 --SEVERITY :
::= 2916

rATemp1 TRAP-TYPE
  ENTERPRISE hpnsaRemoteAssist
  DESCRIPTION
  "The server temperature measured on the HP Remote Assistant Card has exceeded the configured warning threshold."
 --#TYPE "Temperature Warning"
 --#SUMMARY "Temperature Warning"
 --#ARGUMENTS {}
 --#SEVERITY MAJOR
 --#TIMEINDEX 100
 --#HELP "RA.hlp"
 --#HELPTAG  9
 --#STATE OPERATIONAL
 --FIXED STRING : NOT PRESENT
 --CUSTOM STRING : NOT PRESENT
 --SEVERITY :
::= 211

rATemp2 TRAP-TYPE
  ENTERPRISE hpnsaRemoteAssist
  DESCRIPTION
  "The server temperature measured on the HP Remote Assistant Card has exceeded the configured threshold and the server has been automatically shut down."
 --#TYPE "Temperature Graceful Shutdown"
 --#SUMMARY "Temperature Graceful Shutdown"
 --#ARGUMENTS {}
 --#SEVERITY INFORMATIONAL
 --#TIMEINDEX 100
 --#HELP "RA.hlp"
 --#HELPTAG  10
 --#STATE OPERATIONAL
 --FIXED STRING : NOT PRESENT
 --CUSTOM STRING : NOT PRESENT
 --SEVERITY :
::= 221

rATemp3 TRAP-TYPE
  ENTERPRISE hpnsaRemoteAssist
  DESCRIPTION
  "The server temperature or voltage levels measured by the remote management hardware has exceeded the configured threshold. The server has been automatically shut down."
 --#TYPE "Automatic graceful shutdown of NOS"
 --#SUMMARY "Automatic graceful shutdown of NOS"
 --#ARGUMENTS {}
 --#SEVERITY MAJOR
 --#TIMEINDEX 100
 --#HELP "RA.hlp"
 --#HELPTAG  10
 --#STATE OPERATIONAL
 --FIXED STRING : NOT PRESENT
 --CUSTOM STRING : NOT PRESENT
 --SEVERITY :
::= 2221

rATemp4 TRAP-TYPE
  ENTERPRISE hpnsaRemoteAssist
  DESCRIPTION
  "The server temperature measured on the HP Remote Assistant Card has exceeded the configured Graceful Shutdown threshold value by 5 degrees C and the server has been automatically shut down."
 --#TYPE "Temperature Critical"
 --#SUMMARY "Temperature Critical"
 --#ARGUMENTS {}
 --#SEVERITY INFORMATIONAL
 --#TIMEINDEX 100
 --#HELP "RA.hlp"
 --#HELPTAG  11
 --#STATE OPERATIONAL
 --FIXED STRING : NOT PRESENT
 --CUSTOM STRING : NOT PRESENT
 --SEVERITY :
::= 231

rAVoltage1 TRAP-TYPE
  ENTERPRISE hpnsaRemoteAssist
  DESCRIPTION
  "The server has lost the power completely."
 --#TYPE "Server power failure"
 --#SUMMARY "Server Power Failure"
 --#ARGUMENTS {}
 --#SEVERITY INFORMATIONAL
 --#TIMEINDEX 100
 --#HELP "RA.hlp"
 --#HELPTAG  8
 --#STATE OPERATIONAL
 --FIXED STRING : NOT PRESENT
 --CUSTOM STRING : NOT PRESENT
 --SEVERITY :
::= 109

rAVoltage2 TRAP-TYPE
  ENTERPRISE hpnsaRemoteAssist
  DESCRIPTION
  "Voltage measured in the server has gone outside of -12V Upper Threshold."
 --#TYPE "-12V Upper Threshold upper threshold warning"
 --#SUMMARY "-12V Upper Threshold Warning"
 --#ARGUMENTS {}
 --#SEVERITY CRITICAL
 --#TIMEINDEX 100
 --#HELP "RA.hlp"
 --#HELPTAG  7
 --#STATE OPERATIONAL
 --FIXED STRING : NOT PRESENT
 --CUSTOM STRING : NOT PRESENT
 --SEVERITY :
::= 111

rAVoltage3 TRAP-TYPE
  ENTERPRISE hpnsaRemoteAssist
  DESCRIPTION
  "Voltage measured in the server has gone outside of +3.3V Upper Threshold."
 --#TYPE "+3.3 Upper Threshold Warning"
 --#SUMMARY "+3.3 Upper Threshold Warning"
 --#ARGUMENTS {}
 --#SEVERITY CRITICAL
 --#TIMEINDEX 100
 --#HELP "RA.hlp"
 --#HELPTAG  7
 --#STATE OPERATIONAL
 --FIXED STRING : NOT PRESENT
 --CUSTOM STRING : NOT PRESENT
 --SEVERITY :
::= 113

rAVoltage4 TRAP-TYPE
  ENTERPRISE hpnsaRemoteAssist
  DESCRIPTION
  "Voltage measured in the server has gone outside of +5V Upper Threshold."
 --#TYPE "+5V Upper Threshold Warning"
 --#SUMMARY "+5V Upper Threshold Warning"
 --#ARGUMENTS {}
 --#SEVERITY CRITICAL
 --#TIMEINDEX 100
 --#HELP "RA.hlp"
 --#HELPTAG  7
 --#STATE OPERATIONAL
 --FIXED STRING : NOT PRESENT
 --CUSTOM STRING : NOT PRESENT
 --SEVERITY :
::= 114

rAVoltage5 TRAP-TYPE
  ENTERPRISE hpnsaRemoteAssist
  DESCRIPTION
  "Voltage measured in the server has gone outside of +12V Upper Threshold."
 --#TYPE "+12V Upper Threshold Warning"
 --#SUMMARY "+12V Upper Threshold Warning"
 --#ARGUMENTS {}
 --#SEVERITY CRITICAL
 --#TIMEINDEX 100
 --#HELP "RA.hlp"
 --#HELPTAG  7
 --#STATE OPERATIONAL
 --FIXED STRING : NOT PRESENT
 --CUSTOM STRING : NOT PRESENT
 --SEVERITY :
::= 115

rAVoltage6 TRAP-TYPE
  ENTERPRISE hpnsaRemoteAssist
  DESCRIPTION
  "Voltage measured in the server has gone outside of -12V Lower Threshold."
 --#TYPE "-12V Lower Threshold Warning"
 --#SUMMARY "-12V Lower Threshold Warning"
 --#ARGUMENTS {}
 --#SEVERITY CRITICAL
 --#TIMEINDEX 100
 --#HELP "RA.hlp"
 --#HELPTAG  7
 --#STATE OPERATIONAL
 --FIXED STRING : NOT PRESENT
 --CUSTOM STRING : NOT PRESENT
 --SEVERITY :
::= 121

rAVoltage7 TRAP-TYPE
  ENTERPRISE hpnsaRemoteAssist
  DESCRIPTION
  "Voltage measured in the server has gone outside of +3.3V Lower Threshold."
 --#TYPE "+3.3V Lower Threshold Warning"
 --#SUMMARY "+3.3 Lower Threshold Warning"
 --#ARGUMENTS {}
 --#SEVERITY CRITICAL
 --#TIMEINDEX 100
 --#HELP "RA.hlp"
 --#HELPTAG  7
 --#STATE OPERATIONAL
 --FIXED STRING : NOT PRESENT
 --CUSTOM STRING : NOT PRESENT
 --SEVERITY :
::= 123

rAVoltage8 TRAP-TYPE
  ENTERPRISE hpnsaRemoteAssist
  DESCRIPTION
  "Voltage measured in the server has gone outside of +5V Lower Threshold."
 --#TYPE "+5V Lower Threshold Warning"
 --#SUMMARY "+5V Lower Threshold Warning"
 --#ARGUMENTS {}
 --#SEVERITY CRITICAL
 --#TIMEINDEX 100
 --#HELP "RA.hlp"
 --#HELPTAG  7
 --#STATE OPERATIONAL
 --FIXED STRING : NOT PRESENT
 --CUSTOM STRING : NOT PRESENT
 --SEVERITY :
::= 124

rAVoltage9 TRAP-TYPE
  ENTERPRISE hpnsaRemoteAssist
  DESCRIPTION
  "Voltage measured in the server has gone outside of +12V Lower Threshold."
 --#TYPE "+12V Lower Threshold Warning"
 --#SUMMARY "+12V Lower Threshold Warning"
 --#ARGUMENTS {}
 --#SEVERITY CRITICAL
 --#TIMEINDEX 100
 --#HELP "RA.hlp"
 --#HELPTAG  7
 --#STATE OPERATIONAL
 --FIXED STRING : NOT PRESENT
 --CUSTOM STRING : NOT PRESENT
 --SEVERITY :
::= 125

rAVoltage10 TRAP-TYPE
  ENTERPRISE hpnsaRemoteAssist
  DESCRIPTION
  "The HP Remote Assistant Card's battery charging circuit is bad."
 --#TYPE "Battery Lower Threshold Warning"
 --#SUMMARY "Battery Lower Threshold Warning"
 --#ARGUMENTS {}
 --#SEVERITY MAJOR
 --#TIMEINDEX 100
 --#HELP "RA.hlp"
 --#HELPTAG  17
 --#STATE OPERATIONAL
 --FIXED STRING : NOT PRESENT
 --CUSTOM STRING : NOT PRESENT
 --SEVERITY :
::= 122

redundantPower1 TRAP-TYPE
  ENTERPRISE hpnsa
  DESCRIPTION
  "The Redundant Power Supply module is not operating properly, but there is no power supply module hardware failure."
 --#TYPE "PSU: Abnormal environmental condition occurred"
 --#SUMMARY "PSU:  Abnormal Environmental Condition Occurred"
 --#ARGUMENTS {}
 --#SEVERITY CRITICAL
 --#TIMEINDEX 100
 --#HELP "Power.hlp"
 --#HELPTAG  2069
 --#STATE OPERATIONAL
 --FIXED STRING : NOT PRESENT
 --CUSTOM STRING : NOT PRESENT
 --SEVERITY :
::= 9101

redundantPower2 TRAP-TYPE
  ENTERPRISE hpnsa
  DESCRIPTION
  "Indicates a failure with the AC power source that is connected to one of the redundant power supply units."
 --#TYPE "PSU: AC power source failure"
 --#SUMMARY "PSU:  AC Power Source Failure"
 --#ARGUMENTS {}
 --#SEVERITY CRITICAL
 --#TIMEINDEX 100
 --#HELP "Power.hlp"
 --#HELPTAG  2070
 --#STATE OPERATIONAL
 --FIXED STRING : NOT PRESENT
 --CUSTOM STRING : NOT PRESENT
 --SEVERITY :
::= 9103

redundantPower3 TRAP-TYPE
  ENTERPRISE hpnsa
  DESCRIPTION
  "Indicates a failure with the AC power source that is connected to one of the redundant power supply units."
 --#TYPE "PSU: AC power source failure"
 --#SUMMARY "PSU:  Unit %d AC Power Source Failure"
 --#ARGUMENTS {0}
 --#SEVERITY CRITICAL
 --#TIMEINDEX 100
 --#HELP "Power.hlp"
 --#HELPTAG  2070
 --#STATE OPERATIONAL
 --FIXED STRING : NOT PRESENT
 --CUSTOM STRING : NOT PRESENT
 --SEVERITY :
::= 209103

redundantPower4 TRAP-TYPE
  ENTERPRISE hpnsa
  DESCRIPTION
  "Indicates that one of the redundant power supply modules is not in normal operating condition."
 --#TYPE "PSU: Failure detected"
 --#SUMMARY "PSU:  Power Supply Unit Failure Detected"
 --#ARGUMENTS {}
 --#SEVERITY CRITICAL
 --#TIMEINDEX 100
 --#HELP "Power.hlp"
 --#HELPTAG  2073
 --#STATE OPERATIONAL
 --FIXED STRING : NOT PRESENT
 --CUSTOM STRING : NOT PRESENT
 --SEVERITY :
::= 9105

redundantPower5 TRAP-TYPE
  ENTERPRISE hpnsa
  DESCRIPTION
  "Indicates that one of the redundant power supply modules is in over temperature protection mode."
 --#TYPE "PSU: Protection temperature exceeded, DC shutdown"
 --#SUMMARY "PSU:  Protection Temperature Exceeded, DC Output Shutdown"
 --#ARGUMENTS {}
 --#SEVERITY CRITICAL
 --#TIMEINDEX 100
 --#HELP "Power.hlp"
 --#HELPTAG  2071
 --#STATE OPERATIONAL
 --FIXED STRING : NOT PRESENT
 --CUSTOM STRING : NOT PRESENT
 --SEVERITY :
::= 9106

redundantPower6 TRAP-TYPE
  ENTERPRISE hpnsa
  DESCRIPTION
  "Indicates that one of the redundant power supply modules is in over temperature protection mode."
 --#TYPE "PSU: Protection temperature exceeded, DC shutdown"
 --#SUMMARY "PSU:  Unit %d Protection Temperature Exceeded, DC Output Shutdown"
 --#ARGUMENTS {0}
 --#SEVERITY CRITICAL
 --#TIMEINDEX 100
 --#HELP "Power.hlp"
 --#HELPTAG  2071
 --#STATE OPERATIONAL
 --FIXED STRING : NOT PRESENT
 --CUSTOM STRING : NOT PRESENT
 --SEVERITY :
::= 209106

redundantPower7 TRAP-TYPE
  ENTERPRISE hpnsa
  DESCRIPTION
  "Indicates that one of the redundant power supply modules has been physically removed from the HP NetServer Power Supply Subsystem."
 --#TYPE "PSU: Removed"
 --#SUMMARY "PSU:  Removed"
 --#ARGUMENTS {}
 --#SEVERITY INFORMATIONAL
 --#TIMEINDEX 100
 --#HELP "Power.hlp"
 --#HELPTAG  2074
 --#STATE OPERATIONAL
 --FIXED STRING : NOT PRESENT
 --CUSTOM STRING : NOT PRESENT
 --SEVERITY :
::= 9107

redundantPower8 TRAP-TYPE
  ENTERPRISE hpnsa
  DESCRIPTION
  "Indicates that one of the redundant power supply modules has been physically inserted into the HP NetServer Power Supply Subsystem."
 --#TYPE "PSU: Inserted"
 --#SUMMARY "PSU:  Inserted"
 --#ARGUMENTS {}
 --#SEVERITY INFORMATIONAL
 --#TIMEINDEX 100
 --#HELP "Power.hlp"
 --#HELPTAG  2075
 --#STATE OPERATIONAL
 --FIXED STRING : NOT PRESENT
 --CUSTOM STRING : NOT PRESENT
 --SEVERITY :
::= 9108

redundantPower9 TRAP-TYPE
  ENTERPRISE hpnsa
  DESCRIPTION
  "Indicates that one of the redundant power supply modules in the HP NetServer has recovered from an over temperature protection mode."
 --#TYPE "PSU: Protection temperature normal, power restored"
 --#SUMMARY "PSU:  Protection Temperature Normal, Power Restored"
 --#ARGUMENTS {}
 --#SEVERITY INFORMATIONAL
 --#TIMEINDEX 100
 --#HELP "Power.hlp"
 --#HELPTAG  2072
 --#STATE OPERATIONAL
 --FIXED STRING : NOT PRESENT
 --CUSTOM STRING : NOT PRESENT
 --SEVERITY :
::= 9109

redundantPower10 TRAP-TYPE
  ENTERPRISE hpnsa
  DESCRIPTION
  "Indicates that one of the redundant power supply modules in the HP NetServer has recovered from an over temperature protection mode."
 --#TYPE "PSU: Protection temperature normal, power restored"
 --#SUMMARY "PSU:  Unit %d Protection Temperature Normal, Power Restored"
 --#ARGUMENTS {0}
 --#SEVERITY INFORMATIONAL
 --#TIMEINDEX 100
 --#HELP "Power.hlp"
 --#HELPTAG  2072
 --#STATE OPERATIONAL
 --FIXED STRING : NOT PRESENT
 --CUSTOM STRING : NOT PRESENT
 --SEVERITY :
::= 209109

redundantPower11 TRAP-TYPE
  ENTERPRISE hpnsa
  DESCRIPTION
  "Indicates that one of the redundant power supply modules in the HP NetServer has exceeded the warning temperature level."
 --#TYPE "PSS: Warning temperature exceeded"
 --#SUMMARY "PSS:  Warning Temperature Exceeded"
 --#ARGUMENTS {}
 --#SEVERITY MAJOR
 --#TIMEINDEX 100
 --#HELP "Power.hlp"
 --#HELPTAG  2076
 --#STATE OPERATIONAL
 --FIXED STRING : NOT PRESENT
 --CUSTOM STRING : NOT PRESENT
 --SEVERITY :
::= 9110

redundantPower12 TRAP-TYPE
  ENTERPRISE hpnsa
  DESCRIPTION
  "Indicates that one of the redundant power supply modules in the HP NetServer has exceeded the warning temperature level."
 --#TYPE "PSS: Warning temperature exceeded"
 --#SUMMARY "PSS:  Unit %d Warning Temperature Exceeded"
 --#ARGUMENTS {0}
 --#SEVERITY MAJOR
 --#TIMEINDEX 100
 --#HELP "Power.hlp"
 --#HELPTAG  2076
 --#STATE OPERATIONAL
 --FIXED STRING : NOT PRESENT
 --CUSTOM STRING : NOT PRESENT
 --SEVERITY :
::= 209110

redundantPower13 TRAP-TYPE
  ENTERPRISE hpnsa
  DESCRIPTION
  "Indicates that one of the redundant power supply modules in the HP NetServer has exceeded the emergency temperature level."
 --#TYPE "PSS: Emergency temperature exceeded"
 --#SUMMARY "PSS:  Emergency Temperature Exceeded"
 --#ARGUMENTS {}
 --#SEVERITY CRITICAL
 --#TIMEINDEX 100
 --#HELP "Power.hlp"
 --#HELPTAG  2077
 --#STATE OPERATIONAL
 --FIXED STRING : NOT PRESENT
 --CUSTOM STRING : NOT PRESENT
 --SEVERITY :
::= 9111

redundantPower14 TRAP-TYPE
  ENTERPRISE hpnsa
  DESCRIPTION
  "Power System failure A/C Lost"
 --#TYPE "Power System failure A/C Lost"
 --#SUMMARY "Power System failure A/C Lost"
 --#ARGUMENTS {}
 --#SEVERITY CRITICAL
 --#TIMEINDEX 100
 --#HELP "NSATRAP.HLP"
 --#HELPTAG  1026
 --#STATE OPERATIONAL
 --FIXED STRING : NOT PRESENT
 --CUSTOM STRING : NOT PRESENT
 --SEVERITY :
::= 9112

redundantPower15 TRAP-TYPE
  ENTERPRISE hpnsa
  DESCRIPTION
  "The Power Supply Subsystem has fewer than the required number of Power Supply Units installed for normal operation or is having problems powering up or down."
 --#TYPE "Not enough Power Supply Units detected."
 --#SUMMARY "Not enough Power Supply Units detected, trouble powering up or down."
 --#ARGUMENTS {}
 --#SEVERITY CRITICAL
 --#TIMEINDEX 100
 --#HELP "Power.hlp"
 --#HELPTAG  2081
 --#STATE OPERATIONAL
 --FIXED STRING : NOT PRESENT
 --CUSTOM STRING : NOT PRESENT
 --SEVERITY :
::= 9113

redundantPower16 TRAP-TYPE
  ENTERPRISE hpnsa
  DESCRIPTION
  "Temperature alert on designated Power Supply."
 --#TYPE "Power Supply Over Temperature"
 --#SUMMARY "Power Supply Over Temperature"
 --#ARGUMENTS {}
 --#SEVERITY CRITICAL
 --#TIMEINDEX 100
 --#HELP "eightway.hlp"
 --#HELPTAG  14
 --#STATE OPERATIONAL
 --FIXED STRING : NOT PRESENT
 --CUSTOM STRING : NOT PRESENT
 --SEVERITY :
::= 22705

redundantPower17 TRAP-TYPE
  ENTERPRISE hpnsa
  DESCRIPTION
  "Temperature alert on designated Power Supply."
 --#TYPE "Power Supply Over Temperature"
 --#SUMMARY "Power Supply %d Over Temperature"
 --#ARGUMENTS {0}
 --#SEVERITY CRITICAL
 --#TIMEINDEX 100
 --#HELP "eightway.hlp"
 --#HELPTAG  14
 --#STATE OPERATIONAL
 --FIXED STRING : NOT PRESENT
 --CUSTOM STRING : NOT PRESENT
 --SEVERITY :
::= 222705

redundantPower18 TRAP-TYPE
  ENTERPRISE hpnsa
  DESCRIPTION
  "Fan failure on designated Power Supply."
 --#TYPE "Power Supply Fan Failed"
 --#SUMMARY "Power Supply Fan Failed"
 --#ARGUMENTS {}
 --#SEVERITY CRITICAL
 --#TIMEINDEX 100
 --#HELP "eightway.hlp"
 --#HELPTAG  14
 --#STATE OPERATIONAL
 --FIXED STRING : NOT PRESENT
 --CUSTOM STRING : NOT PRESENT
 --SEVERITY :
::= 22706

redundantPower19 TRAP-TYPE
  ENTERPRISE hpnsa
  DESCRIPTION
  "Fan failure on designated Power Supply."
 --#TYPE "Power Supply Fan Failed"
 --#SUMMARY "Power Supply %d Fan Failed"
 --#ARGUMENTS {0}
 --#SEVERITY CRITICAL
 --#TIMEINDEX 100
 --#HELP "eightway.hlp"
 --#HELPTAG  14
 --#STATE OPERATIONAL
 --FIXED STRING : NOT PRESENT
 --CUSTOM STRING : NOT PRESENT
 --SEVERITY :
::= 222706

redundantPower20 TRAP-TYPE
  ENTERPRISE hpnsa
  DESCRIPTION
  "Voltage error on designated Power Supply."
 --#TYPE "Power Supply Voltage supply bad"
 --#SUMMARY "Power Supply Voltage supply bad"
 --#ARGUMENTS {}
 --#SEVERITY CRITICAL
 --#TIMEINDEX 100
 --#HELP "eightway.hlp"
 --#HELPTAG  14
 --#STATE OPERATIONAL
 --FIXED STRING : NOT PRESENT
 --CUSTOM STRING : NOT PRESENT
 --SEVERITY :
::= 22707

redundantPower21 TRAP-TYPE
  ENTERPRISE hpnsa
  DESCRIPTION
  "Fan speed-up on designated Power Supply."
 --#TYPE "Power Supply Fan speed up"
 --#SUMMARY "Power Supply fan speed up"
 --#ARGUMENTS {}
 --#SEVERITY MAJOR
 --#TIMEINDEX 100
 --#HELP "eightway.hlp"
 --#HELPTAG  14
 --#STATE OPERATIONAL
 --FIXED STRING : NOT PRESENT
 --CUSTOM STRING : NOT PRESENT
 --SEVERITY :
::= 22708

redundantPower22 TRAP-TYPE
  ENTERPRISE hpnsa
  DESCRIPTION
  "Fan speed-up on designated Power Supply."
 --#TYPE "Power Supply Fan speed up"
 --#SUMMARY "Power Supply %d fan speed up"
 --#ARGUMENTS {0}
 --#SEVERITY MAJOR
 --#TIMEINDEX 100
 --#HELP "eightway.hlp"
 --#HELPTAG  14
 --#STATE OPERATIONAL
 --FIXED STRING : NOT PRESENT
 --CUSTOM STRING : NOT PRESENT
 --SEVERITY :
::= 222708

redundantPower23 TRAP-TYPE
  ENTERPRISE hpnsa
  DESCRIPTION
  "A power supply's 3.3 volt supply has gone bad"
 --#TYPE "Power Supply 3.3 volts bad"
 --#SUMMARY "Power Supply %d: 3.3 volts bad"
 --#ARGUMENTS {0}
 --#SEVERITY CRITICAL
 --#TIMEINDEX 100
 --#HELP "ra.hlp"
 --#HELPTAG  7
 --#STATE OPERATIONAL
 --FIXED STRING : NOT PRESENT
 --CUSTOM STRING : NOT PRESENT
 --SEVERITY :
::= 22709

redundantPower24 TRAP-TYPE
  ENTERPRISE hpnsa
  DESCRIPTION
  "A power supply's 5 volt supply has gone bad"
 --#TYPE "Power Supply 5 volts bad"
 --#SUMMARY "Power Supply %d: 5 volts bad"
 --#ARGUMENTS {0}
 --#SEVERITY CRITICAL
 --#TIMEINDEX 100
 --#HELP "ra.hlp"
 --#HELPTAG  7
 --#STATE OPERATIONAL
 --FIXED STRING : NOT PRESENT
 --CUSTOM STRING : NOT PRESENT
 --SEVERITY :
::= 22710

redundantPower25 TRAP-TYPE
  ENTERPRISE hpnsa
  DESCRIPTION
  "A power supply's 12 volt supply has gone bad"
 --#TYPE "Power Supply 12 volts bad"
 --#SUMMARY "Power Supply %d: 12 volts bad"
 --#ARGUMENTS {0}
 --#SEVERITY CRITICAL
 --#TIMEINDEX 100
 --#HELP "ra.hlp"
 --#HELPTAG  7
 --#STATE OPERATIONAL
 --FIXED STRING : NOT PRESENT
 --CUSTOM STRING : NOT PRESENT
 --SEVERITY :
::= 22711

redundantPower26 TRAP-TYPE
  ENTERPRISE hpnsa
  DESCRIPTION
  "A power supply's -12 volt supply has gone bad"
 --#TYPE "Power Supply -12 volts bad"
 --#SUMMARY "Power Supply %d: -12 volts bad"
 --#ARGUMENTS {0}
 --#SEVERITY CRITICAL
 --#TIMEINDEX 100
 --#HELP "ra.hlp"
 --#HELPTAG  7
 --#STATE OPERATIONAL
 --FIXED STRING : NOT PRESENT
 --CUSTOM STRING : NOT PRESENT
 --SEVERITY :
::= 22712

redundantPower27 TRAP-TYPE
  ENTERPRISE hpnsa
  DESCRIPTION
  "Indicated Power Supply has been removed or is not connected properly."
 --#TYPE "Power Supply Removed"
 --#SUMMARY "Power Supply Removed"
 --#ARGUMENTS {}
 --#SEVERITY MAJOR
 --#TIMEINDEX 100
 --#HELP "eightway.hlp"
 --#HELPTAG  15
 --#STATE OPERATIONAL
 --FIXED STRING : NOT PRESENT
 --CUSTOM STRING : NOT PRESENT
 --SEVERITY :
::= 22720

redundantPower28 TRAP-TYPE
  ENTERPRISE hpnsa
  DESCRIPTION
  "The indicated Power Supply has been inserted."
 --#TYPE "Power Supply Inserted"
 --#SUMMARY "Power Supply Inserted"
 --#ARGUMENTS {}
 --#SEVERITY INFORMATIONAL
 --#TIMEINDEX 100
 --#HELP "eightway.hlp"
 --#HELPTAG  16
 --#STATE OPERATIONAL
 --FIXED STRING : NOT PRESENT
 --CUSTOM STRING : NOT PRESENT
 --SEVERITY :
::= 22736

redundantPower29 TRAP-TYPE
  ENTERPRISE hpnsa
  DESCRIPTION
  "Indicated Power Supply has been removed."
 --#TYPE "Power Supply Removed"
 --#SUMMARY "Power Supply %d Removed"
 --#ARGUMENTS {0}
 --#SEVERITY MAJOR
 --#TIMEINDEX 100
 --#HELP "Power.hlp"
 --#HELPTAG  2074
 --#STATE OPERATIONAL
 --FIXED STRING : NOT PRESENT
 --CUSTOM STRING : NOT PRESENT
 --SEVERITY :
::= 29101

redundantPower30 TRAP-TYPE
  ENTERPRISE hpnsa
  DESCRIPTION
  "The indicated Power Supply has been inserted."
 --#TYPE "Power Supply Inserted"
 --#SUMMARY "Power Supply %d Inserted."
 --#ARGUMENTS {0}
 --#SEVERITY INFORMATIONAL
 --#TIMEINDEX 100
 --#HELP "Power.hlp"
 --#HELPTAG  2075
 --#STATE OPERATIONAL
 --FIXED STRING : NOT PRESENT
 --CUSTOM STRING : NOT PRESENT
 --SEVERITY :
::= 29102

redundantPower31 TRAP-TYPE
  ENTERPRISE hpnsa
  DESCRIPTION
  "The indicated Power Supply Unit power has failed."
 --#TYPE "Power Supply Unit power has failed."
 --#SUMMARY "Power failed in power supply module %d"
 --#ARGUMENTS {0, 1}
 --#SEVERITY MAJOR
 --#TIMEINDEX 100
 --#HELP "Power.hlp"
 --#HELPTAG  2078
 --#STATE OPERATIONAL
 --FIXED STRING : NOT PRESENT
 --CUSTOM STRING : NOT PRESENT
 --SEVERITY :
::= 29103

redundantPower32 TRAP-TYPE
  ENTERPRISE hpnsa
  DESCRIPTION
  "Predictive failure/alert in power supply"
 --#TYPE "Predictive failure/alert in power supply"
 --#SUMMARY "Predictive failure/alert in sensor %d, power supply unit %d"
 --#ARGUMENTS {0, 1}
 --#SEVERITY MAJOR
 --#TIMEINDEX 100
 --#HELP "power.HLP"
 --#HELPTAG  2083
 --#STATE OPERATIONAL
 --FIXED STRING : NOT PRESENT
 --CUSTOM STRING : NOT PRESENT
 --SEVERITY :
::= 29109

redundantPower33 TRAP-TYPE
  ENTERPRISE hpnsa
  DESCRIPTION
  "Power supply subsystem redundancy gained."
 --#TYPE "Power supply subsystem redundancy gained."
 --#SUMMARY "Power supply subsystem redundancy gained."
 --#ARGUMENTS {}
 --#SEVERITY INFORMATIONAL
 --#TIMEINDEX 100
 --#HELP "Power.hlp"
 --#HELPTAG  2079
 --#STATE OPERATIONAL
 --FIXED STRING : NOT PRESENT
 --CUSTOM STRING : NOT PRESENT
 --SEVERITY :
::= 29104

redundantPower34 TRAP-TYPE
  ENTERPRISE hpnsa
  DESCRIPTION
  "Power supply sunsystem redundancy lost."
 --#TYPE "Power supply sunsystem redundancy lost."
 --#SUMMARY "Power supply subsystem redundancy lost."
 --#ARGUMENTS {}
 --#SEVERITY MAJOR
 --#TIMEINDEX 100
 --#HELP "Power.hlp"
 --#HELPTAG  2080
 --#STATE OPERATIONAL
 --FIXED STRING : NOT PRESENT
 --CUSTOM STRING : NOT PRESENT
 --SEVERITY :
::= 29105

redundantPower35 TRAP-TYPE
  ENTERPRISE hpnsa
  DESCRIPTION
  "The server Power Supply Subsystem has fewer than the required number of Power Supply Units installed for normal operation."
 --#TYPE "PSS: Not enough Power Supply Units detected."
 --#SUMMARY "PSS: Not enough Power Supply Units detected."
 --#ARGUMENTS {}
 --#SEVERITY CRITICAL
 --#TIMEINDEX 100
 --#HELP "Power.hlp"
 --#HELPTAG  2081
 --#STATE OPERATIONAL
 --FIXED STRING : NOT PRESENT
 --CUSTOM STRING : NOT PRESENT
 --SEVERITY :
::= 29106

redundantPower36 TRAP-TYPE
  ENTERPRISE hpnsa
  DESCRIPTION
  "The server Power Supply Subsystem has fewer than the required number of Power Supply Units installed for normal operation."
 --#TYPE "PSS: Not enough Power Supply Units detected."
 --#SUMMARY "PSS: Not enough Power Supply Units detected."
 --#ARGUMENTS {}
 --#SEVERITY CRITICAL
 --#TIMEINDEX 100
 --#HELP "Power.hlp"
 --#HELPTAG  2081
 --#STATE OPERATIONAL
 --FIXED STRING : NOT PRESENT
 --CUSTOM STRING : NOT PRESENT
 --SEVERITY :
::= 29107

redundantPower37 TRAP-TYPE
  ENTERPRISE hpnsa
  DESCRIPTION
  "Power Supply Subsystem soft failure"
 --#TYPE "Power Supply Subsystem soft failure"
 --#SUMMARY "Power Supply Subsystem soft failure"
 --#ARGUMENTS {}
 --#SEVERITY CRITICAL
 --#TIMEINDEX 100
 --#HELP "power.hlp"
 --#HELPTAG  2084
 --#STATE OPERATIONAL
 --FIXED STRING : NOT PRESENT
 --CUSTOM STRING : NOT PRESENT
 --SEVERITY :
::= 9114


sCSISmart22 TRAP-TYPE
  ENTERPRISE cyclone
  DESCRIPTION
  "Aspi: initializing"
 --#TYPE "Aspi: initializing"
 --#SUMMARY "ScsiSMART: ASPI model portion is initializing."
 --#ARGUMENTS {}
 --#SEVERITY INFORMATIONAL
 --#TIMEINDEX 100
 --#HELP "SCSI.hlp"
 --#HELPTAG  126
 --#STATE OPERATIONAL
 --FIXED STRING : NOT PRESENT
 --CUSTOM STRING : NOT PRESENT
 --SEVERITY :
::= 126

storageCap1 TRAP-TYPE
  ENTERPRISE hpnsa
  DESCRIPTION
  "Volume Storage Capacity has exceeded the warning threshold level."
 --#TYPE "Capacity warning level"
 --#SUMMARY "Capacity warning level"
 --#ARGUMENTS {}
 --#SEVERITY MAJOR
 --#TIMEINDEX 100
 --#HELP "NSATrap.hlp"
 --#HELPTAG  500
 --#STATE OPERATIONAL
 --FIXED STRING : NOT PRESENT
 --CUSTOM STRING : NOT PRESENT
 --SEVERITY :
::= 4096

storageCap2 TRAP-TYPE
  ENTERPRISE hpnsa
  DESCRIPTION
  "Volume Storage Capacity has exceeded the warning threshold level."
 --#TYPE "Capacity warning level"
 --#SUMMARY "Volume capacity %d percent exceeded warning threshold %d percent on %s."
 --#ARGUMENTS {0,1,2}
 --#SEVERITY MAJOR
 --#TIMEINDEX 100
 --#HELP "NSATrap.hlp"
 --#HELPTAG  500
 --#STATE OPERATIONAL
 --FIXED STRING : NOT PRESENT
 --CUSTOM STRING : NOT PRESENT
 --SEVERITY :
::= 24096

storageCap3 TRAP-TYPE
  ENTERPRISE hpnsa
  DESCRIPTION
  "Volume Storage Capacity has exceeded the minor threshold level."
 --#TYPE "Capacity minor level"
 --#SUMMARY "Capacity minor level"
 --#ARGUMENTS {}
 --#SEVERITY MAJOR
 --#TIMEINDEX 100
 --#HELP "NSATrap.hlp"
 --#HELPTAG  501
 --#STATE OPERATIONAL
 --FIXED STRING : NOT PRESENT
 --CUSTOM STRING : NOT PRESENT
 --SEVERITY :
::= 4097

storageCap4 TRAP-TYPE
  ENTERPRISE hpnsa
  DESCRIPTION
  "Volume Storage Capacity has exceeded the minor threshold level."
 --#TYPE "Capacity minor level"
 --#SUMMARY "Volume capacity %d percent exceeded minor threshold %d percent on %s."
 --#ARGUMENTS {0,1,2}
 --#SEVERITY MAJOR
 --#TIMEINDEX 100
 --#HELP "NSATrap.hlp"
 --#HELPTAG  501
 --#STATE OPERATIONAL
 --FIXED STRING : NOT PRESENT
 --CUSTOM STRING : NOT PRESENT
 --SEVERITY :
::= 24097

storageCap5 TRAP-TYPE
  ENTERPRISE hpnsa
  DESCRIPTION
  "Volume Storage Capacity has exceeded the major threshold level."
 --#TYPE "Capacity major level"
 --#SUMMARY "Capacity major level"
 --#ARGUMENTS {}
 --#SEVERITY CRITICAL
 --#TIMEINDEX 100
 --#HELP "NSATrap.hlp"
 --#HELPTAG  502
 --#STATE OPERATIONAL
 --FIXED STRING : NOT PRESENT
 --CUSTOM STRING : NOT PRESENT
 --SEVERITY :
::= 4098

storageCap6 TRAP-TYPE
  ENTERPRISE hpnsa
  DESCRIPTION
  "Volume Storage Capacity has exceeded the major threshold level."
 --#TYPE "Capacity major level"
 --#SUMMARY "Volume capacity %d percent exceeded major threshold %d percent on %s."
 --#ARGUMENTS {0,1,2}
 --#SEVERITY CRITICAL
 --#TIMEINDEX 100
 --#HELP "NSATrap.hlp"
 --#HELPTAG  502
 --#STATE OPERATIONAL
 --FIXED STRING : NOT PRESENT
 --CUSTOM STRING : NOT PRESENT
 --SEVERITY :
::= 24098

systemHW1 TRAP-TYPE
  ENTERPRISE hpnsa
  DESCRIPTION
  "Post Error has occurred."
 --#TYPE "POST error"
 --#SUMMARY "POST error"
 --#ARGUMENTS {}
 --#SEVERITY MAJOR
 --#TIMEINDEX 100
 --#HELP "NSATrap.hlp"
 --#HELPTAG  2038
 --#STATE OPERATIONAL
 --FIXED STRING : NOT PRESENT
 --CUSTOM STRING : NOT PRESENT
 --SEVERITY :
::= 4356

systemHW2 TRAP-TYPE
  ENTERPRISE hpnsa
  DESCRIPTION
  "Post Error has occurred."
 --#TYPE "POST error"
 --#SUMMARY "POST error on boot:%d."
 --#ARGUMENTS {0}
 --#SEVERITY MAJOR
 --#TIMEINDEX 100
 --#HELP "NSATrap.hlp"
 --#HELPTAG  2038
 --#STATE OPERATIONAL
 --FIXED STRING : NOT PRESENT
 --CUSTOM STRING : NOT PRESENT
 --SEVERITY :
::= 24356

systemHW3 TRAP-TYPE
  ENTERPRISE hpnsa
  DESCRIPTION
  "Post Error has occurred."
 --#TYPE "POST error"
 --#SUMMARY "POST error on boot:%d."
 --#ARGUMENTS {0}
 --#SEVERITY MAJOR
 --#TIMEINDEX 100
 --#HELP "NSATrap.hlp"
 --#HELPTAG  2038
 --#STATE OPERATIONAL
 --FIXED STRING : NOT PRESENT
 --CUSTOM STRING : NOT PRESENT
 --SEVERITY :
::= 24358

systemHW4 TRAP-TYPE
  ENTERPRISE hpnsa
  DESCRIPTION
  "System boot (POST Complete)."
 --#TYPE "POST Complete"
 --#SUMMARY "System boot (POST Complete)."
 --#ARGUMENTS {}
 --#SEVERITY INFORMATIONAL
 --#TIMEINDEX 100
 --#HELP "NSATrap.hlp"
 --#HELPTAG  1028
 --#STATE OPERATIONAL
 --FIXED STRING : NOT PRESENT
 --CUSTOM STRING : NOT PRESENT
 --SEVERITY :
::= 34356

systemHW5 TRAP-TYPE
  ENTERPRISE hpnsa
  DESCRIPTION
  "Netserver Management Controller started"
 --#TYPE "Netserver Management Controller started"
 --#SUMMARY "Netserver Management Controller started"
 --#ARGUMENTS {}
 --#SEVERITY INFORMATIONAL
 --#TIMEINDEX 100
 --#HELP "NSATrap.hlp"
 --#HELPTAG  2038
 --#STATE OPERATIONAL
 --FIXED STRING : NOT PRESENT
 --CUSTOM STRING : NOT PRESENT
 --SEVERITY :
::= 34357

systemHW6 TRAP-TYPE
  ENTERPRISE hpnsa
  DESCRIPTION
  "Parity error has been detected in parity memory"
 --#TYPE "Parity error"
 --#SUMMARY "Parity error"
 --#ARGUMENTS {}
 --#SEVERITY CRITICAL
 --#TIMEINDEX 100
 --#HELP "NSATrap.hlp"
 --#HELPTAG  2042
 --#STATE OPERATIONAL
 --FIXED STRING : NOT PRESENT
 --CUSTOM STRING : NOT PRESENT
 --SEVERITY :
::= 20528

systemHW7 TRAP-TYPE
  ENTERPRISE hpnsa
  DESCRIPTION
  "IPMB Protocol Error"
 --#TYPE "IPMB Protocol Error"
 --#SUMMARY "IPMB Protocol Error"
 --#ARGUMENTS {}
 --#SEVERITY CRITICAL
 --#TIMEINDEX 100
 --#HELP "NSATRAP.HLP"
 --#HELPTAG  1024
 --#STATE OPERATIONAL
 --FIXED STRING : NOT PRESENT
 --CUSTOM STRING : NOT PRESENT
 --SEVERITY :
::= 20545

systemHW7s TRAP-TYPE
  ENTERPRISE hpnsa
  DESCRIPTION
  "VRM failure"
 --#TYPE "VRM failure"
 --#SUMMARY "VRM failure"
 --#ARGUMENTS {0}
 --#SEVERITY CRITICAL
 --#TIMEINDEX 100
 --#HELP "RA.HLP"
 --#HELPTAG  7
 --#STATE OPERATIONAL
 --FIXED STRING : NOT PRESENT
 --CUSTOM STRING : NOT PRESENT
 --SEVERITY :
::= 25006

systemHW8 TRAP-TYPE
  ENTERPRISE hpnsa
  DESCRIPTION
  "One of the bus masters caused a bus timeout"
 --#TYPE "Bus timeout"
 --#SUMMARY "Bus timeout"
 --#ARGUMENTS {}
 --#SEVERITY CRITICAL
 --#TIMEINDEX 100
 --#HELP "NSATrap.hlp"
 --#HELPTAG  2044
 --#STATE OPERATIONAL
 --FIXED STRING : NOT PRESENT
 --CUSTOM STRING : NOT PRESENT
 --SEVERITY :
::= 20544

systemHW9 TRAP-TYPE
  ENTERPRISE hpnsa
  DESCRIPTION
  "I/0 channel check activated by device in EISA slot caused an error"
 --#TYPE "I/O channel check"
 --#SUMMARY "I/O channel check"
 --#ARGUMENTS {}
 --#SEVERITY CRITICAL
 --#TIMEINDEX 100
 --#HELP "NSATrap.hlp"
 --#HELPTAG  2045
 --#STATE OPERATIONAL
 --FIXED STRING : NOT PRESENT
 --CUSTOM STRING : NOT PRESENT
 --SEVERITY :
::= 20560

systemHW10 TRAP-TYPE
  ENTERPRISE hpnsa
  DESCRIPTION
  "Voltage utilization warning"
 --#TYPE "Voltage utilization warning"
 --#SUMMARY "%s Voltage utilization warning"
 --#ARGUMENTS {0}
 --#SEVERITY MAJOR
 --#TIMEINDEX 100
 --#HELP "power.hlp"
 --#HELPTAG  2087
 --#STATE OPERATIONAL
 --FIXED STRING : NOT PRESENT
 --CUSTOM STRING : NOT PRESENT
 --SEVERITY :
::= 20740

systemHW10s TRAP-TYPE
  ENTERPRISE hpnsa
  DESCRIPTION
  "I/0 channel check activated by device in EISA slot caused an error"
 --#TYPE "I/O channel check"
 --#SUMMARY "I/O channel check occured."
 --#ARGUMENTS {}
 --#SEVERITY CRITICAL
 --#TIMEINDEX 100
 --#HELP "NSATrap.hlp"
 --#HELPTAG  2045
 --#STATE OPERATIONAL
 --FIXED STRING : NOT PRESENT
 --CUSTOM STRING : NOT PRESENT
 --SEVERITY :
::= 220560

systemHW11 TRAP-TYPE
  ENTERPRISE hpnsa
  DESCRIPTION
  "Software NMI has been generated"
 --#TYPE "Software NMI"
 --#SUMMARY "Software NMI"
 --#ARGUMENTS {}
 --#SEVERITY CRITICAL
 --#TIMEINDEX 100
 --#HELP "NSATrap.hlp"
 --#HELPTAG  2046
 --#STATE OPERATIONAL
 --FIXED STRING : NOT PRESENT
 --CUSTOM STRING : NOT PRESENT
 --SEVERITY :
::= 20576

systemHW11s TRAP-TYPE
  ENTERPRISE hpnsa
  DESCRIPTION
  "Voltage utilization error"
 --#TYPE "Voltage utilization error"
 --#SUMMARY "%s Voltage utilization error"
 --#ARGUMENTS {0}
 --#SEVERITY CRITICAL
 --#TIMEINDEX 100
 --#HELP "power.hlp"
 --#HELPTAG  2088
 --#STATE OPERATIONAL
 --FIXED STRING : NOT PRESENT
 --CUSTOM STRING : NOT PRESENT
 --SEVERITY :
::= 20741

systemHW12 TRAP-TYPE
  ENTERPRISE hpnsa
  DESCRIPTION
  "Uncorrectable Bus Error"
 --#TYPE "Uncorrectable Bus Error"
 --#SUMMARY "Uncorrectable Bus Error:DataByte2=%d DataByte3=%d"
 --#ARGUMENTS {0,1}
 --#SEVERITY CRITICAL
 --#TIMEINDEX 100
 --#HELP "NSATRAP.HLP"
 --#HELPTAG  1025
 --#STATE OPERATIONAL
 --FIXED STRING : NOT PRESENT
 --CUSTOM STRING : NOT PRESENT
 --SEVERITY :
::= 20577

systemHW13 TRAP-TYPE
  ENTERPRISE hpnsa
  DESCRIPTION
  "Memory size has been adjusted during the Power-On-Self-Test during the last boot"
 --#TYPE "Memory resize"
 --#SUMMARY "memory resize"
 --#ARGUMENTS {}
 --#SEVERITY MAJOR
 --#TIMEINDEX 100
 --#HELP "NSATrap.hlp"
 --#HELPTAG  2058
 --#STATE OPERATIONAL
 --FIXED STRING : NOT PRESENT
 --CUSTOM STRING : NOT PRESENT
 --SEVERITY :
::= 20592

systemHW14 TRAP-TYPE
  ENTERPRISE hpnsa
  DESCRIPTION
  "Parity error has occurred on a transfer to/from a device on one of the PCI buses"
 --#TYPE "PCI bus error"
 --#SUMMARY "PCI bus error"
 --#ARGUMENTS {}
 --#SEVERITY CRITICAL
 --#TIMEINDEX 100
 --#HELP "NSATrap.hlp"
 --#HELPTAG  2047
 --#STATE OPERATIONAL
 --FIXED STRING : NOT PRESENT
 --CUSTOM STRING : NOT PRESENT
 --SEVERITY :
::= 20624

systemHW15 TRAP-TYPE
  ENTERPRISE hpnsa
  DESCRIPTION
  "Parity error has occurred on a transfer to or from a device on one of the PCI buses"
 --#TYPE "PCI bus error"
 --#SUMMARY "Parity error has occurred on a transfer to or from a device on one of the PCI buses"
 --#ARGUMENTS {}
 --#SEVERITY CRITICAL
 --#TIMEINDEX 100
 --#HELP "NSATrap.hlp"
 --#HELPTAG  2047
 --#STATE OPERATIONAL
 --FIXED STRING : NOT PRESENT
 --CUSTOM STRING : NOT PRESENT
 --SEVERITY :
::= 220624

systemHW16 TRAP-TYPE
  ENTERPRISE hpnsa
  DESCRIPTION
  "System error has occurred in the PCI subsystem"
 --#TYPE "PCI system error"
 --#SUMMARY "PCI system error"
 --#ARGUMENTS {}
 --#SEVERITY CRITICAL
 --#TIMEINDEX 100
 --#HELP "NSATrap.hlp"
 --#HELPTAG  2048
 --#STATE OPERATIONAL
 --FIXED STRING : NOT PRESENT
 --CUSTOM STRING : NOT PRESENT
 --SEVERITY :
::= 20640

systemHW17 TRAP-TYPE
  ENTERPRISE hpnsa
  DESCRIPTION
  "System error has occurred in the PCI subsystem"
 --#TYPE "PCI system error"
 --#SUMMARY "System error has occurred in the PCI subsystem"
 --#ARGUMENTS {}
 --#SEVERITY CRITICAL
 --#TIMEINDEX 100
 --#HELP "NSATrap.hlp"
 --#HELPTAG  2048
 --#STATE OPERATIONAL
 --FIXED STRING : NOT PRESENT
 --CUSTOM STRING : NOT PRESENT
 --SEVERITY :
::= 220640

systemHW18 TRAP-TYPE
  ENTERPRISE hpnsa
  DESCRIPTION
  "An uncorrectable Processor problem was detected."
 --#TYPE "Processor problem"
 --#SUMMARY "Processor problem"
 --#ARGUMENTS {}
 --#SEVERITY CRITICAL
 --#TIMEINDEX 100
 --#HELP "NSATRAP.HLP"
 --#HELPTAG  1009
 --#STATE OPERATIONAL
 --FIXED STRING : NOT PRESENT
 --CUSTOM STRING : NOT PRESENT
 --SEVERITY :
::= 20657

systemHW19 TRAP-TYPE
  ENTERPRISE hpnsa
  DESCRIPTION
  "Processor (#) Disabled"
 --#TYPE "Processor failure"
 --#SUMMARY "Processor ID %s Disabled"
 --#ARGUMENTS {0}
 --#SEVERITY CRITICAL
 --#TIMEINDEX 100
 --#HELP "NSATrap.hlp"
 --#HELPTAG  1012
 --#STATE OPERATIONAL
 --FIXED STRING : NOT PRESENT
 --CUSTOM STRING : NOT PRESENT
 --SEVERITY :
::= 20658

systemHW20 TRAP-TYPE
  ENTERPRISE hpnsa
  DESCRIPTION
  "Processor or Terminator Card  Not Detected"
 --#TYPE "Processor failure"
 --#SUMMARY "Processor failure"
 --#ARGUMENTS {}
 --#SEVERITY CRITICAL
 --#TIMEINDEX 100
 --#HELP "NSATRAP.HLP"
 --#HELPTAG  1006
 --#STATE OPERATIONAL
 --FIXED STRING : NOT PRESENT
 --CUSTOM STRING : NOT PRESENT
 --SEVERITY :
::= 20660

systemHW21 TRAP-TYPE
  ENTERPRISE hpnsa
  DESCRIPTION
  "Processor or Terminator (#) not detected"
 --#TYPE "Processor or Terminator not detected"
 --#SUMMARY "Processor or Terminator with ID %s not detected"
 --#ARGUMENTS {0}
 --#SEVERITY CRITICAL
 --#TIMEINDEX 100
 --#HELP "NSATRAP.HLP"
 --#HELPTAG  1006
 --#STATE OPERATIONAL
 --FIXED STRING : NOT PRESENT
 --CUSTOM STRING : NOT PRESENT
 --SEVERITY :
::= 20656

systemHW22 TRAP-TYPE
  ENTERPRISE hpnsa
  DESCRIPTION
  "Processor Internal Error"
 --#TYPE "Processor failure"
 --#SUMMARY "Processor Internal Error"
 --#ARGUMENTS {}
 --#SEVERITY CRITICAL
 --#TIMEINDEX 100
 --#HELP "NSATRAP.HLP"
 --#HELPTAG  1009
 --#STATE OPERATIONAL
 --FIXED STRING : NOT PRESENT
 --CUSTOM STRING : NOT PRESENT
 --SEVERITY :
::= 20661

systemHW23 TRAP-TYPE
  ENTERPRISE hpnsa
  DESCRIPTION
  "Processor Thermal Trip Failure"
 --#TYPE "Processor failure"
 --#SUMMARY "Processor Thermal Trip Failure"
 --#ARGUMENTS {}
 --#SEVERITY CRITICAL
 --#TIMEINDEX 100
 --#HELP "NSATRAP.HLP"
 --#HELPTAG  1008
 --#STATE OPERATIONAL
 --FIXED STRING : NOT PRESENT
 --CUSTOM STRING : NOT PRESENT
 --SEVERITY :
::= 20662

systemHW24 TRAP-TYPE
  ENTERPRISE hpnsa
  DESCRIPTION
  "Processor failed internal self test"
 --#TYPE "Processor failure"
 --#SUMMARY "Processor failed internal self test"
 --#ARGUMENTS {}
 --#SEVERITY CRITICAL
 --#TIMEINDEX 100
 --#HELP "NSATRAP.HLP"
 --#HELPTAG  1007
 --#STATE OPERATIONAL
 --FIXED STRING : NOT PRESENT
 --CUSTOM STRING : NOT PRESENT
 --SEVERITY :
::= 20663

systemHW25 TRAP-TYPE
  ENTERPRISE hpnsa
  DESCRIPTION
  "Processor hung during POST"
 --#TYPE "Processor failure"
 --#SUMMARY "Processor hung during POST"
 --#ARGUMENTS {}
 --#SEVERITY CRITICAL
 --#TIMEINDEX 100
 --#HELP "NSATRAP.HLP"
 --#HELPTAG  1007
 --#STATE OPERATIONAL
 --FIXED STRING : NOT PRESENT
 --CUSTOM STRING : NOT PRESENT
 --SEVERITY :
::= 20664

systemHW26 TRAP-TYPE
  ENTERPRISE hpnsa
  DESCRIPTION
  "Processor startup/initialization failed"
 --#TYPE "Processor startup/initialization failed"
 --#SUMMARY "Processor startup/initialization failed"
 --#ARGUMENTS {}
 --#SEVERITY CRITICAL
 --#TIMEINDEX 100
 --#HELP "NSATRAP.HLP"
 --#HELPTAG  1007
 --#STATE OPERATIONAL
 --FIXED STRING : NOT PRESENT
 --CUSTOM STRING : NOT PRESENT
 --SEVERITY :
::= 20665

systemHW27 TRAP-TYPE
  ENTERPRISE hpnsa
  DESCRIPTION
  "Multiple Fan Failure"
 --#TYPE "Fan failure"
 --#SUMMARY "Multiple Fan Failure"
 --#ARGUMENTS {}
 --#SEVERITY CRITICAL
 --#TIMEINDEX 100
 --#HELP "NSATRAP.HLP"
 --#HELPTAG  1010
 --#STATE OPERATIONAL
 --FIXED STRING : NOT PRESENT
 --CUSTOM STRING : NOT PRESENT
 --SEVERITY :
::= 20670

systemHW28 TRAP-TYPE
  ENTERPRISE hpnsa
  DESCRIPTION
  "Timeout of failsafe timer has occurred"
 --#TYPE "Failsafe timer timeout"
 --#SUMMARY "Failsafe timer timeout"
 --#ARGUMENTS {}
 --#SEVERITY CRITICAL
 --#TIMEINDEX 100
 --#HELP "NSATrap.hlp"
 --#HELPTAG  2050
 --#STATE OPERATIONAL
 --FIXED STRING : NOT PRESENT
 --CUSTOM STRING : NOT PRESENT
 --SEVERITY :
::= 20672

systemHW29 TRAP-TYPE
  ENTERPRISE hpnsa
  DESCRIPTION
  "Error logging for a specific error has been disabled due to too many errors of that kind in a short time period"
 --#TYPE "Too many errors of this type"
 --#SUMMARY "Too many errors of this type"
 --#ARGUMENTS {}
 --#SEVERITY INFORMATIONAL
 --#TIMEINDEX 100
 --#HELP "NSATrap.hlp"
 --#HELPTAG  2052
 --#STATE OPERATIONAL
 --FIXED STRING : NOT PRESENT
 --CUSTOM STRING : NOT PRESENT
 --SEVERITY :
::= 20704

systemHW30 TRAP-TYPE
  ENTERPRISE hpnsa
  DESCRIPTION
  "EISA Configuration Utility has altered system configuration"
 --#TYPE "System configuration altered"
 --#SUMMARY "System configuration altered"
 --#ARGUMENTS {}
 --#SEVERITY INFORMATIONAL
 --#TIMEINDEX 100
 --#HELP "NSATrap.hlp"
 --#HELPTAG  2051
 --#STATE OPERATIONAL
 --FIXED STRING : NOT PRESENT
 --CUSTOM STRING : NOT PRESENT
 --SEVERITY :
::= 20800

systemHW31 TRAP-TYPE
  ENTERPRISE hpnsa
  DESCRIPTION
  "Configuration Utility has altered system configuration"
 --#TYPE "System configuration altered"
 --#SUMMARY "System configuration altered."
 --#ARGUMENTS {}
 --#SEVERITY INFORMATIONAL
 --#TIMEINDEX 100
 --#HELP "NSATrap.hlp"
 --#HELPTAG  2051
 --#STATE OPERATIONAL
 --FIXED STRING : NOT PRESENT
 --CUSTOM STRING : NOT PRESENT
 --SEVERITY :
::= 220800

systemHW32 TRAP-TYPE
  ENTERPRISE hpnsa
  DESCRIPTION
  "Power connection failure in one of the devices in the hot swap cage"
 --#TYPE "Hot swap: Power failure"
 --#SUMMARY "Hot swap disks: Power connection failure"
 --#ARGUMENTS {}
 --#SEVERITY CRITICAL
 --#TIMEINDEX 100
 --#HELP "DISKS.hlp"
 --#HELPTAG  2053
 --#STATE OPERATIONAL
 --FIXED STRING : NOT PRESENT
 --CUSTOM STRING : NOT PRESENT
 --SEVERITY :
::= 24453

systemHW33 TRAP-TYPE
  ENTERPRISE hpnsa
  DESCRIPTION
  "system Voltage failure"
 --#TYPE "system Voltage failure"
 --#SUMMARY "System Voltage failure: error code %d"
 --#ARGUMENTS {0}
 --#SEVERITY MAJOR
 --#TIMEINDEX 100
 --#HELP "Disks.hlp"
 --#HELPTAG  2073
 --#STATE OPERATIONAL
 --FIXED STRING : NOT PRESENT
 --CUSTOM STRING : NOT PRESENT
 --SEVERITY :
::= 54453

systemHW34 TRAP-TYPE
  ENTERPRISE hpnsa
  DESCRIPTION
  "A device has been removed from the hot swap cage"
 --#TYPE "Hot swap: Device removed"
 --#SUMMARY "Hot swap disks: Device removed"
 --#ARGUMENTS {}
 --#SEVERITY CRITICAL
 --#TIMEINDEX 100
 --#HELP "DISKS.hlp"
 --#HELPTAG  2054
 --#STATE OPERATIONAL
 --FIXED STRING : NOT PRESENT
 --CUSTOM STRING : NOT PRESENT
 --SEVERITY :
::= 24454

systemHW35 TRAP-TYPE
  ENTERPRISE hpnsa
  DESCRIPTION
  "A device has been inserted into the hot swap cage"
 --#TYPE "Hot swap: Device inserted"
 --#SUMMARY "Hot swap disks: Device inserted"
 --#ARGUMENTS {}
 --#SEVERITY INFORMATIONAL
 --#TIMEINDEX 100
 --#HELP "DISKS.hlp"
 --#HELPTAG  2055
 --#STATE OPERATIONAL
 --FIXED STRING : NOT PRESENT
 --CUSTOM STRING : NOT PRESENT
 --SEVERITY :
::= 24455

systemHW36 TRAP-TYPE
  ENTERPRISE hpnsa
  DESCRIPTION
  "A SCSI cable has been removed from the hot swap cage."
 --#TYPE "Hot swap: SCSI cable removed"
 --#SUMMARY "Hot Swap Cage: A SCSI Cable has been removed from cage %d."
 --#ARGUMENTS {0}
 --#SEVERITY MAJOR
 --#TIMEINDEX 100
 --#HELP "Disks.hlp"
 --#HELPTAG  2069
 --#STATE OPERATIONAL
 --FIXED STRING : NOT PRESENT
 --CUSTOM STRING : NOT PRESENT
 --SEVERITY :
::= 54454

systemHW37 TRAP-TYPE
  ENTERPRISE hpnsa
  DESCRIPTION
  "A SCSI cable was attached to hot swap cage."
 --#TYPE "Hot swap: SCSI cable attached"
 --#SUMMARY "Hot Swap Cage : A SCSI cable has been attached in cage %d."
 --#ARGUMENTS {0}
 --#SEVERITY INFORMATIONAL
 --#TIMEINDEX 100
 --#HELP "Disks.hlp"
 --#HELPTAG  2070
 --#STATE OPERATIONAL
 --FIXED STRING : NOT PRESENT
 --CUSTOM STRING : NOT PRESENT
 --SEVERITY :
::= 54455

systemHW38 TRAP-TYPE
  ENTERPRISE hpnsa
  DESCRIPTION
  "A SCSI terminator has been removed from the hot swap cage."
 --#TYPE "Hot swap: SCSI terminator removed"
 --#SUMMARY "Hot Swap Cage : SCSI terminator has been removed from cage %d."
 --#ARGUMENTS {0}
 --#SEVERITY MAJOR
 --#TIMEINDEX 100
 --#HELP "Disks.hlp"
 --#HELPTAG  2071
 --#STATE OPERATIONAL
 --FIXED STRING : NOT PRESENT
 --CUSTOM STRING : NOT PRESENT
 --SEVERITY :
::= 54456

systemHW39 TRAP-TYPE
  ENTERPRISE hpnsa
  DESCRIPTION
  "A SCSI terminator has been attached in the hot swap cage."
 --#TYPE "Hot swap: SCSI terminator attached"
 --#SUMMARY "Hot Swap Cage : A SCSI terminator has been attached in cage %d."
 --#ARGUMENTS {0}
 --#SEVERITY INFORMATIONAL
 --#TIMEINDEX 100
 --#HELP "Disks.hlp"
 --#HELPTAG  2072
 --#STATE OPERATIONAL
 --FIXED STRING : NOT PRESENT
 --CUSTOM STRING : NOT PRESENT
 --SEVERITY :
::= 54457

systemHW40 TRAP-TYPE
  ENTERPRISE hpnsa
  DESCRIPTION
  "Power connection failure in one of the devices in the hot swap cage"
 --#TYPE "Hot Swap Cage: Power failure"
 --#SUMMARY "Hot Swap Cage : Device %d: Power connection failure!"
 --#ARGUMENTS {0}
 --#SEVERITY CRITICAL
 --#TIMEINDEX 100
 --#HELP "DISKS.hlp"
 --#HELPTAG  2053
 --#STATE OPERATIONAL
 --FIXED STRING : NOT PRESENT
 --CUSTOM STRING : NOT PRESENT
 --SEVERITY :
::= 224453

systemHW41 TRAP-TYPE
  ENTERPRISE hpnsa
  DESCRIPTION
  "A device has been removed from the hot swap cage"
 --#TYPE "Hot swap: Device removed"
 --#SUMMARY "Hot Swap Cage : Device %d: Removed."
 --#ARGUMENTS {0}
 --#SEVERITY CRITICAL
 --#TIMEINDEX 100
 --#HELP "DISKS.HLP"
 --#HELPTAG  2054
 --#STATE OPERATIONAL
 --FIXED STRING : NOT PRESENT
 --CUSTOM STRING : NOT PRESENT
 --SEVERITY :
::= 224454

systemHW42 TRAP-TYPE
  ENTERPRISE hpnsa
  DESCRIPTION
  "A device has been inserted into the hot swap cage"
 --#TYPE "Hot swap: Device inserted"
 --#SUMMARY "Hot Swap Cage : Device %d: Inserted."
 --#ARGUMENTS {0}
 --#SEVERITY INFORMATIONAL
 --#TIMEINDEX 100
 --#HELP "DISKS.HLP"
 --#HELPTAG  2055
 --#STATE OPERATIONAL
 --FIXED STRING : NOT PRESENT
 --CUSTOM STRING : NOT PRESENT
 --SEVERITY :
::= 224455

systemHW43 TRAP-TYPE
  ENTERPRISE hpnsa
  DESCRIPTION
  "An event of warning severity has occurred in the system. For example, chassis door has been opened"
 --#TYPE "System Warning limit exceeded"
 --#SUMMARY "System warning limit exceeded"
 --#ARGUMENTS {}
 --#SEVERITY MAJOR
 --#TIMEINDEX 100
 --#HELP "NSATrap.hlp"
 --#HELPTAG  2065
 --#STATE OPERATIONAL
 --FIXED STRING : NOT PRESENT
 --CUSTOM STRING : NOT PRESENT
 --SEVERITY :
::= 20736

systemHW44 TRAP-TYPE
  ENTERPRISE hpnsa
  DESCRIPTION
  "An event of critical severity has occurred in the system. For example, both system fans have failed"
 --#TYPE "System critical limit exceeded"
 --#SUMMARY "System critical limit exceeded"
 --#ARGUMENTS {}
 --#SEVERITY CRITICAL
 --#TIMEINDEX 100
 --#HELP "NSATrap.hlp"
 --#HELPTAG  2065
 --#STATE OPERATIONAL
 --FIXED STRING : NOT PRESENT
 --CUSTOM STRING : NOT PRESENT
 --SEVERITY :
::= 20737

systemHW45 TRAP-TYPE
  ENTERPRISE hpnsa
  DESCRIPTION
  "Event log is getting full."
 --#TYPE "Event log getting full."
 --#SUMMARY "Event log %d percent full."
 --#ARGUMENTS {0}
 --#SEVERITY INFORMATIONAL
 --#TIMEINDEX 100
 --#HELP "NSATrap.hlp"
 --#HELPTAG  1
 --#STATE OPERATIONAL
 --FIXED STRING : NOT PRESENT
 --CUSTOM STRING : NOT PRESENT
 --SEVERITY :
::= 24456

systemHW46 TRAP-TYPE
  ENTERPRISE hpnsa
  DESCRIPTION
  "Event log cleared"
 --#TYPE "Event log cleared"
 --#SUMMARY "Event log cleared"
 --#ARGUMENTS {}
 --#SEVERITY INFORMATIONAL
 --#TIMEINDEX 100
 --#HELP "NSATrap.hlp"
 --#HELPTAG  1003
 --#STATE OPERATIONAL
 --FIXED STRING : NOT PRESENT
 --CUSTOM STRING : NOT PRESENT
 --SEVERITY :
::= 34456

systemHW47 TRAP-TYPE
  ENTERPRISE hpnsa
  DESCRIPTION
  "SDR area cleared"
 --#TYPE "SDR area cleared"
 --#SUMMARY "SDR area cleared."
 --#ARGUMENTS {}
 --#SEVERITY INFORMATIONAL
 --#TIMEINDEX 100
 --#HELP "NSATrap.hlp"
 --#HELPTAG  1004
 --#STATE OPERATIONAL
 --FIXED STRING : NOT PRESENT
 --CUSTOM STRING : NOT PRESENT
 --SEVERITY :
::= 44456

systemHW48 TRAP-TYPE
  ENTERPRISE hpnsa
  DESCRIPTION
  "The hardware eventlog has been cleared."
 --#TYPE "Event Log cleared"
 --#SUMMARY "Event Log cleared"
 --#ARGUMENTS {}
 --#SEVERITY INFORMATIONAL
 --#TIMEINDEX 100
 --#HELP "eightway.hlp"
 --#HELPTAG  1
 --#STATE OPERATIONAL
 --FIXED STRING : NOT PRESENT
 --CUSTOM STRING : NOT PRESENT
 --SEVERITY :
::= 20832

systemHW49 TRAP-TYPE
  ENTERPRISE hpnsa
  DESCRIPTION
  "An unrecognized HW log event was detected."
 --#TYPE "An unrecognized HW log event was detected."
 --#SUMMARY "An unrecognized HW log event was detected."
 --#ARGUMENTS {}
 --#SEVERITY INFORMATIONAL
 --#TIMEINDEX 100
 --#HELP "NSATRAP.HLP"
 --#HELPTAG  1005
 --#STATE OPERATIONAL
 --FIXED STRING : NOT PRESENT
 --CUSTOM STRING : NOT PRESENT
 --SEVERITY :
::= 20833

systemHW50 TRAP-TYPE
  ENTERPRISE hpnsa
  DESCRIPTION
  "The system has been rebooted."
 --#TYPE "System Reboot"
 --#SUMMARY "System Reboot"
 --#ARGUMENTS {}
 --#SEVERITY INFORMATIONAL
 --#TIMEINDEX 100
 --#HELP "eightway.hlp"
 --#HELPTAG  2
 --#STATE OPERATIONAL
 --FIXED STRING : NOT PRESENT
 --CUSTOM STRING : NOT PRESENT
 --SEVERITY :
::= 20848

systemHW51 TRAP-TYPE
  ENTERPRISE hpnsa
  DESCRIPTION
  "The Processor in the indicated slot has been disabled by the BIOS."
 --#TYPE "Processor Disabled"
 --#SUMMARY "Processor Disabled"
 --#ARGUMENTS {}
 --#SEVERITY CRITICAL
 --#TIMEINDEX 100
 --#HELP "eightway.hlp"
 --#HELPTAG  3
 --#STATE OPERATIONAL
 --FIXED STRING : NOT PRESENT
 --CUSTOM STRING : NOT PRESENT
 --SEVERITY :
::= 22528

systemHW52 TRAP-TYPE
  ENTERPRISE hpnsa
  DESCRIPTION
  "A user has halted the system with the NMI switch on the front panel."
 --#TYPE "Front Panel System Halt"
 --#SUMMARY "Front Panel System Halt"
 --#ARGUMENTS {}
 --#SEVERITY INFORMATIONAL
 --#TIMEINDEX 100
 --#HELP "eightway.hlp"
 --#HELPTAG  5
 --#STATE OPERATIONAL
 --FIXED STRING : NOT PRESENT
 --CUSTOM STRING : NOT PRESENT
 --SEVERITY :
::= 22651

systemHW53 TRAP-TYPE
  ENTERPRISE hpnsa
  DESCRIPTION
  "Previously disabled Processor has been reinstalled."
 --#TYPE "Processor Reinstalled"
 --#SUMMARY "Processor Reinstalled"
 --#ARGUMENTS {}
 --#SEVERITY INFORMATIONAL
 --#TIMEINDEX 100
 --#HELP "eightway.hlp"
 --#HELPTAG  13
 --#STATE OPERATIONAL
 --FIXED STRING : NOT PRESENT
 --CUSTOM STRING : NOT PRESENT
 --SEVERITY :
::= 22688

systemHW54 TRAP-TYPE
  ENTERPRISE hpnsa
  DESCRIPTION
  "The system has been reset because Control Board detected a critical error."
 --#TYPE "Control Board System reset"
 --#SUMMARY "Control Board System reset"
 --#ARGUMENTS {}
 --#SEVERITY CRITICAL
 --#TIMEINDEX 100
 --#HELP "eightway.hlp"
 --#HELPTAG  17
 --#STATE OPERATIONAL
 --FIXED STRING : NOT PRESENT
 --CUSTOM STRING : NOT PRESENT
 --SEVERITY :
::= 22752

systemHW55 TRAP-TYPE
  ENTERPRISE hpnsa
  DESCRIPTION
  "The system has been power-cycled because Control Board detected a critical error."
 --#TYPE "Control Board System power-cycle"
 --#SUMMARY "Control Board System power-cycle"
 --#ARGUMENTS {}
 --#SEVERITY CRITICAL
 --#TIMEINDEX 100
 --#HELP "eightway.hlp"
 --#HELPTAG  18
 --#STATE OPERATIONAL
 --FIXED STRING : NOT PRESENT
 --CUSTOM STRING : NOT PRESENT
 --SEVERITY :
::= 22768

systemHW56 TRAP-TYPE
  ENTERPRISE hpnsa
  DESCRIPTION
  "The Processor Card is missing or not properly terminated in indicated processor module."
 --#TYPE "Processor Card Missing or not terminated"
 --#SUMMARY "Processor Card Missing or not terminated"
 --#ARGUMENTS {}
 --#SEVERITY MAJOR
 --#TIMEINDEX 100
 --#HELP "eightway.hlp"
 --#HELPTAG  19
 --#STATE OPERATIONAL
 --FIXED STRING : NOT PRESENT
 --CUSTOM STRING : NOT PRESENT
 --SEVERITY :
::= 22785

systemHW57 TRAP-TYPE
  ENTERPRISE hpnsa
  DESCRIPTION
  "A single or multiple ECC Error has been detected on the P6 bus."
 --#TYPE "ECC Error on P6 Bus"
 --#SUMMARY "ECC Error on P6 Bus"
 --#ARGUMENTS {}
 --#SEVERITY MAJOR
 --#TIMEINDEX 100
 --#HELP "eightway.hlp"
 --#HELPTAG  4
 --#STATE OPERATIONAL
 --FIXED STRING : NOT PRESENT
 --CUSTOM STRING : NOT PRESENT
 --SEVERITY :
::= 22544

systemHW58 TRAP-TYPE
  ENTERPRISE hpnsa
  DESCRIPTION
  "Front Panel Button Violation"
 --#TYPE "Violation"
 --#SUMMARY "Front Panel Button Violation"
 --#ARGUMENTS {}
 --#SEVERITY INFORMATIONAL
 --#TIMEINDEX 100
 --#HELP "NSATRAP.HLP"
 --#HELPTAG  1011
 --#STATE OPERATIONAL
 --FIXED STRING : NOT PRESENT
 --CUSTOM STRING : NOT PRESENT
 --SEVERITY :
::= 20680

systemHW59 TRAP-TYPE
  ENTERPRISE hpnsa
  DESCRIPTION
  "The CPU processor module is currently functioning properly, but it is no longer operating within acceptable margins"
 --#TYPE "CPU Processor module is operating outside of acceptable margins"
 --#SUMMARY "Processor number %d is operating outside of acceptable margins."
 --#ARGUMENTS {0}
 --#SEVERITY MAJOR
 --#TIMEINDEX 100
 --#HELP "NSATRAP.HLP"
 --#HELPTAG  1014
 --#STATE OPERATIONAL
 --FIXED STRING : NOT PRESENT
 --CUSTOM STRING : NOT PRESENT
 --SEVERITY :
::= 20659

systemHW60 TRAP-TYPE
  ENTERPRISE hpnsa
  DESCRIPTION
  "PCI Hot Plug fault deasserted"
 --#TYPE "PCI Hot Plug fault"
 --#SUMMARY "PCI Hot Plug fault deasserted"
 --#ARGUMENTS {}
 --#SEVERITY INFORMATIONAL
 --#TIMEINDEX 100
 --#HELP "NSATRAP.HLP"
 --#HELPTAG  1015
 --#STATE OPERATIONAL
 --FIXED STRING : NOT PRESENT
 --CUSTOM STRING : NOT PRESENT
 --SEVERITY :
::= 20666

systemHW61 TRAP-TYPE
  ENTERPRISE hpnsa
  DESCRIPTION
  "PCI Hot Plug Powered On"
 --#TYPE "PCI Hot Plug powered on"
 --#SUMMARY "PCI Hot Plug Powered On"
 --#ARGUMENTS {}
 --#SEVERITY INFORMATIONAL
 --#TIMEINDEX 100
 --#HELP "NSATRAP.HLP"
 --#HELPTAG  1017
 --#STATE OPERATIONAL
 --FIXED STRING : NOT PRESENT
 --CUSTOM STRING : NOT PRESENT
 --SEVERITY :
::= 20667

systemHW62 TRAP-TYPE
  ENTERPRISE hpnsa
  DESCRIPTION
  "PCI Hot Plug fault asserted"
 --#TYPE "PCI Hot Plug fault asserted"
 --#SUMMARY "PCI Hot Plug fault asserted"
 --#ARGUMENTS {}
 --#SEVERITY CRITICAL
 --#TIMEINDEX 100
 --#HELP "NSATRAP.HLP"
 --#HELPTAG  1016
 --#STATE OPERATIONAL
 --FIXED STRING : NOT PRESENT
 --CUSTOM STRING : NOT PRESENT
 --SEVERITY :
::= 20668

systemHW63 TRAP-TYPE
  ENTERPRISE hpnsa
  DESCRIPTION
  "PCI Hot Plug Powered off"
 --#TYPE "PCI Hot Plug powered off"
 --#SUMMARY "PCI Hot Plug Powered off"
 --#ARGUMENTS {}
 --#SEVERITY INFORMATIONAL
 --#TIMEINDEX 100
 --#HELP "NSATRAP.HLP"
 --#HELPTAG  1018
 --#STATE OPERATIONAL
 --FIXED STRING : NOT PRESENT
 --CUSTOM STRING : NOT PRESENT
 --SEVERITY :
::= 20669

systemHW64 TRAP-TYPE
  ENTERPRISE hpnsa
  DESCRIPTION
  "Cache Protocol and Parity error"
 --#TYPE "Cache Protocol and Parity error"
 --#SUMMARY "Cache Protocol and Parity error: %d."
 --#ARGUMENTS {0}
 --#SEVERITY CRITICAL
 --#TIMEINDEX 100
 --#HELP "NSATRAP.HLP"
 --#HELPTAG  1029
 --#STATE OPERATIONAL
 --FIXED STRING : NOT PRESENT
 --CUSTOM STRING : NOT PRESENT
 --SEVERITY :
::= 20578

systemHW65 TRAP-TYPE
  ENTERPRISE hpnsa
  DESCRIPTION
  "Correctable data error"
 --#TYPE "Correctable data error"
 --#SUMMARY "Correctable data error."
 --#ARGUMENTS {}
 --#SEVERITY INFORMATIONAL
 --#TIMEINDEX 100
 --#HELP "NSATRAP.HLP"
 --#HELPTAG  1030
 --#STATE OPERATIONAL
 --FIXED STRING : NOT PRESENT
 --CUSTOM STRING : NOT PRESENT
 --SEVERITY :
::= 20579

systemHW67 TRAP-TYPE
  ENTERPRISE hpnsa
  DESCRIPTION
  "A SCSI cable has been removed from the hot swap cage."
 --#TYPE "Hot Swap Cage: SCSI cable removed"
 --#SUMMARY "Hot Swap Cage %d: %s has been removed"
 --#ARGUMENTS {0,1}
 --#SEVERITY MAJOR
 --#TIMEINDEX 100
 --#HELP "Disks.hlp"
 --#HELPTAG  2069
 --#STATE OPERATIONAL
 --FIXED STRING : NOT PRESENT
 --CUSTOM STRING : NOT PRESENT
 --SEVERITY :
::= 254454

systemHW68 TRAP-TYPE
  ENTERPRISE hpnsa
  DESCRIPTION
  "A SCSI cable was attached to the hot swap cage."
 --#TYPE "Hot Swap Cage: SCSI cable attached"
 --#SUMMARY "Hot Swap Cage %d: %s has been attached"
 --#ARGUMENTS {0,1}
 --#SEVERITY INFORMATIONAL
 --#TIMEINDEX 100
 --#HELP "Disks.hlp"
 --#HELPTAG  2070
 --#STATE OPERATIONAL
 --FIXED STRING : NOT PRESENT
 --CUSTOM STRING : NOT PRESENT
 --SEVERITY :
::= 254455

systemHW69 TRAP-TYPE
  ENTERPRISE hpnsa
  DESCRIPTION
  "A SCSI terminator has been removed from the hot swap cage."
 --#TYPE "Hot Swap Cage: SCSI terminator removed"
 --#SUMMARY "Hot Swap Cage %d: %s has been removed"
 --#ARGUMENTS {0,1}
 --#SEVERITY MAJOR
 --#TIMEINDEX 100
 --#HELP "Disks.hlp"
 --#HELPTAG  2071
 --#STATE OPERATIONAL
 --FIXED STRING : NOT PRESENT
 --CUSTOM STRING : NOT PRESENT
 --SEVERITY :
::= 254456

systemHW70 TRAP-TYPE
  ENTERPRISE hpnsa
  DESCRIPTION
  "A SCSI terminator has been attached in the hot swap cage."
 --#TYPE "Hot Swap Cage: SCSI terminator attached"
 --#SUMMARY "Hot Swap Cage %d: %s has been attached"
 --#ARGUMENTS {0,1}
 --#SEVERITY INFORMATIONAL
 --#TIMEINDEX 100
 --#HELP "Disks.hlp"
 --#HELPTAG  2072
 --#STATE OPERATIONAL
 --FIXED STRING : NOT PRESENT
 --CUSTOM STRING : NOT PRESENT
 --SEVERITY :
::= 254457

systemHW71 TRAP-TYPE
  ENTERPRISE hpnsa
  DESCRIPTION
  "A drive has been removed from the hot swap cage"
 --#TYPE "Hot Swap Cage: Device removed"
 --#SUMMARY "Hot Swap Cage %d: Drive removed from slot %d"
 --#ARGUMENTS {0,1}
 --#SEVERITY CRITICAL
 --#TIMEINDEX 100
 --#HELP "DISKS.HLP"
 --#HELPTAG  2054
 --#STATE OPERATIONAL
 --FIXED STRING : NOT PRESENT
 --CUSTOM STRING : NOT PRESENT
 --SEVERITY :
::= 324454

systemHW72 TRAP-TYPE
  ENTERPRISE hpnsa
  DESCRIPTION
  "A drive has been inserted into the hot swap cage"
 --#TYPE "Hot Swap Cage: Device inserted"
 --#SUMMARY "Hot Swap Cage %d: Drive inserted into slot %d"
 --#ARGUMENTS {0,1}
 --#SEVERITY INFORMATIONAL
 --#TIMEINDEX 100
 --#HELP "DISKS.HLP"
 --#HELPTAG  2055
 --#STATE OPERATIONAL
 --FIXED STRING : NOT PRESENT
 --CUSTOM STRING : NOT PRESENT
 --SEVERITY :
::= 324455

systemHW73 TRAP-TYPE
  ENTERPRISE hpnsa
  DESCRIPTION
  "NOS memory dump initiated"
 --#TYPE "NOS memory dump initiated"
 --#SUMMARY "NOS memory dump initiated"
 --#ARGUMENTS {}
 --#SEVERITY CRITICAL
 --#TIMEINDEX 100
 --#HELP "nsatrap.hlp"
 --#HELPTAG  1033
 --#STATE OPERATIONAL
 --FIXED STRING : NOT PRESENT
 --CUSTOM STRING : NOT PRESENT
 --SEVERITY :
::= 20546

systemHW74 TRAP-TYPE
  ENTERPRISE hpnsa
  DESCRIPTION
  "SCSI Duplex Board has been removed"
 --#TYPE "SCSI Duplex Board has been removed"
 --#SUMMARY "%s has been removed from Cage %d"
 --#ARGUMENTS {0,1}
 --#SEVERITY MAJOR
 --#TIMEINDEX 100
 --#HELP "disks.hlp"
 --#HELPTAG  2074
 --#STATE OPERATIONAL
 --FIXED STRING : NOT PRESENT
 --CUSTOM STRING : NOT PRESENT
 --SEVERITY :
::= 54460

systemHW75 TRAP-TYPE
  ENTERPRISE hpnsa
  DESCRIPTION
  "SCSI Duplex Board has been inserted"
 --#TYPE "SCSI Duplex Board has been inserted"
 --#SUMMARY "%s has been inserted in Cage %d"
 --#ARGUMENTS {0,1}
 --#SEVERITY INFORMATIONAL
 --#TIMEINDEX 100
 --#HELP "disks.hlp"
 --#HELPTAG  2075
 --#STATE OPERATIONAL
 --FIXED STRING : NOT PRESENT
 --CUSTOM STRING : NOT PRESENT
 --SEVERITY :
::= 54461

systemHW76 TRAP-TYPE
  ENTERPRISE hpnsa
  DESCRIPTION
  "Normal ACPI server shutdown"
 --#TYPE "Normal ACPI server shutdown"
 --#SUMMARY "Normal ACPI server shutdown"
 --#ARGUMENTS {}
 --#SEVERITY INFORMATIONAL
 --#TIMEINDEX 100
 --#HELP "power.hlp"
 --#HELPTAG  2085
 --#STATE OPERATIONAL
 --FIXED STRING : NOT PRESENT
 --CUSTOM STRING : NOT PRESENT
 --SEVERITY :
::= 54465

systemHW77 TRAP-TYPE
  ENTERPRISE hpnsa
  DESCRIPTION
  "ACPI hardware failure"
 --#TYPE "ACPI hardware failure"
 --#SUMMARY "ACPI hardware failure"
 --#ARGUMENTS {}
 --#SEVERITY MAJOR
 --#TIMEINDEX 100
 --#HELP "power.hlp"
 --#HELPTAG  2086
 --#STATE OPERATIONAL
 --FIXED STRING : NOT PRESENT
 --CUSTOM STRING : NOT PRESENT
 --SEVERITY :
::= 54466

systemHW78 TRAP-TYPE
  ENTERPRISE hpnsa
  DESCRIPTION
  "SCSI Bus Type has changed"
 --#TYPE "Hot Swap Cage: SCSI Bus type has changed"
 --#SUMMARY "Hot Swap Cage %d: %s"
 --#ARGUMENTS {0,1}
 --#SEVERITY MAJOR
 --#TIMEINDEX 100
 --#HELP "disks.hlp"
 --#HELPTAG  2076
 --#STATE OPERATIONAL
 --FIXED STRING : NOT PRESENT
 --CUSTOM STRING : NOT PRESENT
 --SEVERITY :
::= 54464

systemHW79 TRAP-TYPE
  ENTERPRISE hpnsa
  DESCRIPTION
  "Configuration error in a processor slot"
 --#TYPE "Configuration error for a processor slot"
 --#SUMMARY "Configuration error in %s slot"
 --#ARGUMENTS {0}
 --#SEVERITY CRITICAL
 --#TIMEINDEX 100
 --#HELP "nsatrap.hlp"
 --#HELPTAG  1037
 --#STATE OPERATIONAL
 --FIXED STRING : NOT PRESENT
 --CUSTOM STRING : NOT PRESENT
 --SEVERITY :
::= 20671

systemHW80 TRAP-TYPE
  ENTERPRISE hpnsa
  DESCRIPTION
  "Battery cycles have gone beyond the upper non-critical range"
 --#TYPE "The battery cycles have gone beyond the upper non-critical range"
 --#SUMMARY "Battery Cycles Sensor %s has gone beyond the upper non-critical range"
 --#ARGUMENTS {0}
 --#SEVERITY MAJOR
 --#TIMEINDEX 100
 --#HELP "nsatrap.hlp"
 --#HELPTAG  1035
 --#STATE OPERATIONAL
 --FIXED STRING : NOT PRESENT
 --CUSTOM STRING : NOT PRESENT
 --SEVERITY :
::= 25022

systemHW80s TRAP-TYPE
  ENTERPRISE hpnsa
  DESCRIPTION
  "CPU internal error"
 --#TYPE "CPU internal error"
 --#SUMMARY "CPU internal error"
 --#ARGUMENTS {0}
 --#SEVERITY CRITICAL
 --#TIMEINDEX 100
 --#HELP "nsatrap.hlp"
 --#HELPTAG  1009
 --#STATE OPERATIONAL
 --FIXED STRING : NOT PRESENT
 --CUSTOM STRING : NOT PRESENT
 --SEVERITY :
::= 20675

systemHW81 TRAP-TYPE
  ENTERPRISE hpnsa
  DESCRIPTION
  "Battery cycles have gone beyond the upper critical range"
 --#TYPE "The battery cycles have gone beyond the upper critical range"
 --#SUMMARY "Battery Cycles Sensor %s has gone beyond the upper critical range"
 --#ARGUMENTS {0}
 --#SEVERITY CRITICAL
 --#TIMEINDEX 100
 --#HELP "nsatrap.hlp"
 --#HELPTAG  1035
 --#STATE OPERATIONAL
 --FIXED STRING : NOT PRESENT
 --CUSTOM STRING : NOT PRESENT
 --SEVERITY :
::= 25023

systemHW81s TRAP-TYPE
  ENTERPRISE hpnsa
  DESCRIPTION
  "CPU thermal trip"
 --#TYPE "CPU thermal trip"
 --#SUMMARY "CPU thermal trip"
 --#ARGUMENTS {0}
 --#SEVERITY CRITICAL
 --#TIMEINDEX 100
 --#HELP "nsatrap.hlp"
 --#HELPTAG  1008
 --#STATE OPERATIONAL
 --FIXED STRING : NOT PRESENT
 --CUSTOM STRING : NOT PRESENT
 --SEVERITY :
::= 20673

systemHW82 TRAP-TYPE
  ENTERPRISE hpnsa
  DESCRIPTION
  "Battery cycles have gone beyond the upper non-recoverable range"
 --#TYPE "The battery cycles have gone beyond the upper non-recoverable range"
 --#SUMMARY "Battery Cycles Sensor %s has gone beyond the upper non-recoverable range"
 --#ARGUMENTS {0}
 --#SEVERITY CRITICAL
 --#TIMEINDEX 100
 --#HELP "nsatrap.hlp"
 --#HELPTAG  1035
 --#STATE OPERATIONAL
 --FIXED STRING : NOT PRESENT
 --CUSTOM STRING : NOT PRESENT
 --SEVERITY :
::= 25024

systemHW82s TRAP-TYPE
  ENTERPRISE hpnsa
  DESCRIPTION
  "CPU hot warning"
 --#TYPE "CPU hot warning"
 --#SUMMARY "CPU hot warning"
 --#ARGUMENTS {0}
 --#SEVERITY MAJOR
 --#TIMEINDEX 100
 --#HELP "era.hlp"
 --#HELPTAG  17
 --#STATE OPERATIONAL
 --FIXED STRING : NOT PRESENT
 --CUSTOM STRING : NOT PRESENT
 --SEVERITY :
::= 20674

systemHW83 TRAP-TYPE
  ENTERPRISE hpnsa
  DESCRIPTION
  "CPU mismatch"
 --#TYPE "CPU mismatch"
 --#SUMMARY "CPU mismatch"
 --#ARGUMENTS {}
 --#SEVERITY CRITICAL
 --#TIMEINDEX 100
 --#HELP "nsatrap.hlp"
 --#HELPTAG  1037
 --#STATE OPERATIONAL
 --FIXED STRING : NOT PRESENT
 --CUSTOM STRING : NOT PRESENT
 --SEVERITY :
::= 20676

systemHW83s TRAP-TYPE
  ENTERPRISE hpnsa
  DESCRIPTION
  "FRU internal use area cleared"
 --#TYPE "FRU internal use area cleared"
 --#SUMMARY "FRU internal use area cleared"
 --#ARGUMENTS {}
 --#SEVERITY INFORMATIONAL
 --#TIMEINDEX 100
 --#HELP "NSATrap.hlp"
 --#HELPTAG  1039
 --#STATE OPERATIONAL
 --FIXED STRING : NOT PRESENT
 --CUSTOM STRING : NOT PRESENT
 --SEVERITY :
::= 44457

systemHW84 TRAP-TYPE
  ENTERPRISE hpnsa
  DESCRIPTION
  "Unrecoverable chipset error has occurred in system board ."
 --#TYPE "Uncorrectable chipset error"
 --#SUMMARY "Uncorrectable chipset error"
 --#ARGUMENTS {0,1}
 --#SEVERITY CRITICAL
 --#TIMEINDEX 100
 --#HELP "NSATrap.hlp"
 --#HELPTAG  1040
 --#STATE OPERATIONAL
 --FIXED STRING : NOT PRESENT
 --CUSTOM STRING : NOT PRESENT
 --SEVERITY :
::= 25780

systemHW100 TRAP-TYPE
  ENTERPRISE hpnsa
  DESCRIPTION
  "SMART predictive failure detected"
 --#TYPE "SMART predictive failure detected"
 --#SUMMARY "SMART predictive failure detected: host adapter %d, Target ID %d and LUN %d vendor %s product %s sense info %d"
 --#ARGUMENTS {0,1,2,3,4,5}
 --#SEVERITY MAJOR
 --#TIMEINDEX 100
 --#HELP "netraid.hlp"
 --#HELPTAG  217
 --#STATE OPERATIONAL
 --FIXED STRING : NOT PRESENT
 --CUSTOM STRING : NOT PRESENT
 --SEVERITY :
::= 53001

systemFW1 TRAP-TYPE
  ENTERPRISE hpnsa
  DESCRIPTION
  "Generic trap for Critical or Fatal type E0 event from system firmware"
 --#TYPE "Generic trap for Critical or Fatal type E0 event from system firmware"
 --#SUMMARY "Generic trap for Critical or Fatal type E0 event from system firmware"
 --#ARGUMENTS {}
 --#SEVERITY CRITICAL
 --#TIMEINDEX 100
 --#HELP "IPFsys.hlp"
 --#HELPTAG  1003
 --#STATE OPERATIONAL
 --FIXED STRING : NOT PRESENT
 --CUSTOM STRING : NOT PRESENT
 --SEVERITY :
::= 20758

systemFW2 TRAP-TYPE
  ENTERPRISE hpnsa
  DESCRIPTION
  "System Firmware Boot Start"
 --#TYPE "System Firmware Boot Start"
 --#SUMMARY "System Firmware Boot Start"
 --#ARGUMENTS {}
 --#SEVERITY INFORMATIONAL
 --#TIMEINDEX 100
 --#HELP "IPFsys.hlp"
 --#HELPTAG  1001
 --#STATE OPERATIONAL
 --FIXED STRING : NOT PRESENT
 --CUSTOM STRING : NOT PRESENT
 --SEVERITY :
::= 20756

systemFW3 TRAP-TYPE
  ENTERPRISE hpnsa
  DESCRIPTION
  "OS Boot Complete"
 --#TYPE "OS Boot Complete"
 --#SUMMARY "OS Boot Complete"
 --#ARGUMENTS {}
 --#SEVERITY INFORMATIONAL
 --#TIMEINDEX 100
 --#HELP "IPFsys.hlp"
 --#HELPTAG  1002
 --#STATE OPERATIONAL
 --FIXED STRING : NOT PRESENT
 --CUSTOM STRING : NOT PRESENT
 --SEVERITY :
::= 20755

systemFW4 TRAP-TYPE
  ENTERPRISE hpnsa
  DESCRIPTION
  "Machine Check Initiated"
 --#TYPE "Machine Check Initiated"
 --#SUMMARY "Machine Check Initiated"
 --#ARGUMENTS {}
 --#SEVERITY CRITICAL
 --#TIMEINDEX 100
 --#HELP "IPFsys.hlp"
 --#HELPTAG  1004
 --#STATE OPERATIONAL
 --FIXED STRING : NOT PRESENT
 --CUSTOM STRING : NOT PRESENT
 --SEVERITY :
::= 20757

temperature1 TRAP-TYPE
  ENTERPRISE hpnsa
  DESCRIPTION
  "Server temperature monitor cannot read temperature data."
 --#TYPE "Temperature Monitor error"
 --#SUMMARY "Temp. monitor error"
 --#ARGUMENTS {}
 --#SEVERITY CRITICAL
 --#TIMEINDEX 100
 --#HELP "NSATrap.hlp"
 --#HELPTAG  2039
 --#STATE OPERATIONAL
 --FIXED STRING : NOT PRESENT
 --CUSTOM STRING : NOT PRESENT
 --SEVERITY :
::= 12288

temperature2 TRAP-TYPE
  ENTERPRISE hpnsa
  DESCRIPTION
  "Server temperature has exceeded the warning temperature threshold."
 --#TYPE "Temperature warning"
 --#SUMMARY "Temperature warning"
 --#ARGUMENTS {}
 --#SEVERITY MAJOR
 --#TIMEINDEX 100
 --#HELP "ERA.HLP"
 --#HELPTAG  5
 --#STATE OPERATIONAL
 --FIXED STRING : NOT PRESENT
 --CUSTOM STRING : NOT PRESENT
 --SEVERITY :
::= 12289

temperature3 TRAP-TYPE
  ENTERPRISE hpnsa
  DESCRIPTION
  "Server temperature has exceeded the emergency temperature threshold."
 --#TYPE "Temperature Emergency"
 --#SUMMARY "Temperature emergency"
 --#ARGUMENTS {}
 --#SEVERITY CRITICAL
 --#TIMEINDEX 100
 --#HELP "ERA.HLP"
 --#HELPTAG  6
 --#STATE OPERATIONAL
 --FIXED STRING : NOT PRESENT
 --CUSTOM STRING : NOT PRESENT
 --SEVERITY :
::= 12290

temperature4 TRAP-TYPE
  ENTERPRISE hpnsa
  DESCRIPTION
  "Hot Swap Cage : Temperature monitor error occurred"
 --#TYPE "Hot Swap: Temperature monitor error"
 --#SUMMARY "Hot swap:  Temperature monitor error"
 --#ARGUMENTS {}
 --#SEVERITY CRITICAL
 --#TIMEINDEX 100
 --#HELP "Disks.hlp"
 --#HELPTAG  2066
 --#STATE OPERATIONAL
 --FIXED STRING : NOT PRESENT
 --CUSTOM STRING : NOT PRESENT
 --SEVERITY :
::= 24449

temperature5 TRAP-TYPE
  ENTERPRISE hpnsa
  DESCRIPTION
  "Hot Swap Cage : Warning temperature exceeded"
 --#TYPE "Hot Swap: Temperature warning"
 --#SUMMARY "Hot swap:  Temperature warning"
 --#ARGUMENTS {}
 --#SEVERITY MAJOR
 --#TIMEINDEX 100
 --#HELP "Disks.hlp"
 --#HELPTAG  2067
 --#STATE OPERATIONAL
 --FIXED STRING : NOT PRESENT
 --CUSTOM STRING : NOT PRESENT
 --SEVERITY :
::= 24451

temperature6 TRAP-TYPE
  ENTERPRISE hpnsa
  DESCRIPTION
  "Hot Swap Cage : Emergency temperature exceeded!"
 --#TYPE "Hot Swap: Temperature emergency"
 --#SUMMARY "Hot swap:  Temperature emergency"
 --#ARGUMENTS {}
 --#SEVERITY CRITICAL
 --#TIMEINDEX 100
 --#HELP "Disks.hlp"
 --#HELPTAG  2068
 --#STATE OPERATIONAL
 --FIXED STRING : NOT PRESENT
 --CUSTOM STRING : NOT PRESENT
 --SEVERITY :
::= 24452

temperature7 TRAP-TYPE
  ENTERPRISE hpnsa
  DESCRIPTION
  "Hot Swap Cage : Temperature monitor error occurred"
 --#TYPE "Hot Swap Cage: Temperature monitor error"
 --#SUMMARY "Hot swap: Temperature monitor error;"
 --#ARGUMENTS {}
 --#SEVERITY CRITICAL
 --#TIMEINDEX 100
 --#HELP "Disks.hlp"
 --#HELPTAG  2066
 --#STATE OPERATIONAL
 --FIXED STRING : NOT PRESENT
 --CUSTOM STRING : NOT PRESENT
 --SEVERITY :
::= 224449

temperature8 TRAP-TYPE
  ENTERPRISE hpnsa
  DESCRIPTION
  "Hot Swap Cage : Warning temperature exceeded"
 --#TYPE "Hot Swap Cage: Temperature warning"
 --#SUMMARY "Hot swap:  Temperature warning;"
 --#ARGUMENTS {}
 --#SEVERITY MAJOR
 --#TIMEINDEX 100
 --#HELP "Disks.hlp"
 --#HELPTAG  2067
 --#STATE OPERATIONAL
 --FIXED STRING : NOT PRESENT
 --CUSTOM STRING : NOT PRESENT
 --SEVERITY :
::= 224451

temperature9 TRAP-TYPE
  ENTERPRISE hpnsa
  DESCRIPTION
  "Hot Swap Cage : Emergency temperature exceeded!"
 --#TYPE "Hot Swap Cage: Temperature emergency"
 --#SUMMARY "Hot swap:  Temperature emergency"
 --#ARGUMENTS {}
 --#SEVERITY CRITICAL
 --#TIMEINDEX 100
 --#HELP "Disks.hlp"
 --#HELPTAG  2068
 --#STATE OPERATIONAL
 --FIXED STRING : NOT PRESENT
 --CUSTOM STRING : NOT PRESENT
 --SEVERITY :
::= 224452

voltage1 TRAP-TYPE
  ENTERPRISE hpnsa
  DESCRIPTION
  "Warning voltage threshold on one of the system voltage channels has been exceeded. Voltage channels are +12V, +5V, -12V, +3.3V to PCI, +3.3V to Processor"
 --#TYPE "Voltage Warning"
 --#SUMMARY "Voltage warning"
 --#ARGUMENTS {}
 --#SEVERITY MAJOR
 --#TIMEINDEX 100
 --#HELP "NSATrap.hlp"
 --#HELPTAG  2063
 --#STATE OPERATIONAL
 --FIXED STRING : NOT PRESENT
 --CUSTOM STRING : NOT PRESENT
 --SEVERITY :
::= 20739

voltage2 TRAP-TYPE
  ENTERPRISE hpnsa
  DESCRIPTION
  "Fatal voltage threshold on one of the system voltage sensors has been exceeded. Voltage sensors are +12V, +5V, -12V, +3.3V to PCI, +3.3V to Processor"
 --#TYPE "Voltage Emergency"
 --#SUMMARY "Voltage emergency"
 --#ARGUMENTS {}
 --#SEVERITY CRITICAL
 --#TIMEINDEX 100
 --#HELP "NSATrap.hlp"
 --#HELPTAG  2064
 --#STATE OPERATIONAL
 --FIXED STRING : NOT PRESENT
 --CUSTOM STRING : NOT PRESENT
 --SEVERITY :
::= 20738



END
