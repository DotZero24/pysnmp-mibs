LEFTHAND-NETWORKS-NUS-COMMON-INFO-MIB DEFINITIONS ::= BEGIN

-- A Comment!

-- IMPORTS: Include definitions from other mibs here, which is always
-- the first item in a MIB file.
IMPORTS
	MODULE-IDENTITY, OBJECT-TYPE, IpAddress,
	Counter64, Counter32                       FROM SNMPv2-SMI
	RowStatus, TruthValue                      FROM SNMPv2-TC
	lhnModules                                 FROM LEFTHAND-NETWORKS-GLOBAL-REG
	lhnNusCommonInfo                           FROM LEFTHAND-NETWORKS-NUS-COMMON-MIB;


--
-- A brief description and update information about this mib.
--
lhnNusCommonInfoModule MODULE-IDENTITY
    LAST-UPDATED "0106010000Z"
	 ORGANIZATION "LeftHand Networks, Inc."
    CONTACT-INFO "
                  Author:     Jose Faria
                              LeftHand Networks
                  postal:     1688 Conestoga St.
                              Boulder, CO 80301
                              USA
                  email:      jfaria@lefthandnetworks.com
                  phone:      +1 303 449-4100
                 "
    DESCRIPTION  "info items for NSM"
    ::= { lhnModules 4 }

-- *********************************************************************************
--
-- Information Objects
--
-- *********************************************************************************

--
--  Identification
--

infoSerialNumber OBJECT-TYPE
    SYNTAX      OCTET STRING
    MAX-ACCESS  read-only
    STATUS      current
    DESCRIPTION "serial number of the NSM"
    ::= { lhnNusCommonInfo 1 }

infoModel OBJECT-TYPE
    SYNTAX      OCTET STRING
    MAX-ACCESS  read-only
    STATUS      current
    DESCRIPTION "model of the NSM"
    ::= { lhnNusCommonInfo 2 }

infoSoftwareVersion OBJECT-TYPE
    SYNTAX      OCTET STRING
    MAX-ACCESS  read-only
    STATUS      current
    DESCRIPTION "software version of the NSM"
    ::= { lhnNusCommonInfo 3 }

infoDSPFirmwareVersion OBJECT-TYPE
    SYNTAX      OCTET STRING
    MAX-ACCESS  read-only
    STATUS      current
    DESCRIPTION "DSP firmware version of the NSM"
    ::= { lhnNusCommonInfo 4 }


--
-- Status objects
--

infoMotherboardTemperature OBJECT-TYPE
    SYNTAX         INTEGER
    UNITS          "Celsius"
    MAX-ACCESS     read-only
    STATUS         current
    DESCRIPTION    "motherboard temperature"
    ::= { lhnNusCommonInfo 5 }

infoCPUTemperature OBJECT-TYPE
    SYNTAX         INTEGER
    UNITS          "Celsius"
    MAX-ACCESS     read-only
    STATUS         current
    DESCRIPTION    "CPU temperature"
    ::= { lhnNusCommonInfo 6 }


infoCPUFanSpeed OBJECT-TYPE
    SYNTAX         INTEGER
    UNITS          "RPM"
    MAX-ACCESS     read-only
    STATUS         current
    DESCRIPTION    "CPU fan speed"
    ::= { lhnNusCommonInfo 7 }

--
-- Power Supplies
--

infoPowerSupplyCount OBJECT-TYPE
    SYNTAX         INTEGER
    MAX-ACCESS     read-only
    STATUS         current
    DESCRIPTION    "Number of power supplies"
    ::= { lhnNusCommonInfo 8 }

infoPowerSupplyTable OBJECT-TYPE
    SYNTAX      SEQUENCE OF InfoPowerSupplyEntry
    MAX-ACCESS  not-accessible
    STATUS      current
    DESCRIPTION
    "A table of power supplies in the system.
     The number of entries is given by infoPowerSupplyCount."
    ::= { lhnNusCommonInfo 9 }


infoPowerSupplyEntry OBJECT-TYPE
    SYNTAX      InfoPowerSupplyEntry
    MAX-ACCESS  not-accessible
    STATUS      current
    DESCRIPTION "A row of power supply parameters"
    INDEX { infoPowerSupplyIndex }
    ::= { infoPowerSupplyTable 1 }

InfoPowerSupplyEntry ::= SEQUENCE
{
   infoPowerSupplyIndex           INTEGER,
   infoPowerSupplyStatus          INTEGER
}


infoPowerSupplyIndex OBJECT-TYPE
    SYNTAX         INTEGER
    MAX-ACCESS     read-only
    STATUS         current
    DESCRIPTION    "index for a power supply"
    ::= { infoPowerSupplyEntry 1 }

infoPowerSupplyStatus OBJECT-TYPE
    SYNTAX      INTEGER { active(1), inactive(2), marginal(3) }
    MAX-ACCESS  read-only
    STATUS      current
    DESCRIPTION "power supply status"
    ::= { infoPowerSupplyEntry 2 }

--
-- SFDS Cards
--

infoSFDSCount OBJECT-TYPE
    SYNTAX         INTEGER
    MAX-ACCESS     read-only
    STATUS         current
    DESCRIPTION    "Number of SFDS cards"
    ::= { lhnNusCommonInfo 10 }

infoSFDSTable OBJECT-TYPE
    SYNTAX      SEQUENCE OF InfoSFDSEntry
    MAX-ACCESS  not-accessible
    STATUS      current
    DESCRIPTION
    "A table of SFDS cards in the system.
     The number of entries is given by infoSFDSCount."
    ::= { lhnNusCommonInfo 11 }


infoSFDSEntry OBJECT-TYPE
    SYNTAX      InfoSFDSEntry
    MAX-ACCESS  not-accessible
    STATUS      current
    DESCRIPTION "A row of SFDS parameters"
    INDEX { infoSFDSIndex }
    ::= { infoSFDSTable 1 }

InfoSFDSEntry ::= SEQUENCE
{
   infoSFDSIndex            INTEGER,
   infoSFDSHardwareVersion  OCTET STRING,
   infoSFDSFirmwareVersion  OCTET STRING,
   infoSFDSDriverVersion    OCTET STRING,
   infoSFDSMemorySize       INTEGER,
   infoSFDSStatus           OCTET STRING
}


infoSFDSIndex OBJECT-TYPE
    SYNTAX         INTEGER
    MAX-ACCESS     read-only
    STATUS         current
    DESCRIPTION    "index for an SFDS card"
    ::= { infoSFDSEntry 1 }

infoSFDSHardwareVersion OBJECT-TYPE
    SYNTAX      OCTET STRING
    MAX-ACCESS  read-only
    STATUS      current
    DESCRIPTION "SFDS card hardware version"
    ::= { infoSFDSEntry 2 }

infoSFDSFirmwareVersion OBJECT-TYPE
    SYNTAX      OCTET STRING
    MAX-ACCESS  read-only
    STATUS      current
    DESCRIPTION "SFDS card firmware version"
    ::= { infoSFDSEntry 3 }

infoSFDSDriverVersion OBJECT-TYPE
    SYNTAX      OCTET STRING
    MAX-ACCESS  read-only
    STATUS      current
    DESCRIPTION "SFDS card driver version"
    ::= { infoSFDSEntry 4 }

infoSFDSMemorySize OBJECT-TYPE
    SYNTAX         Counter32
    UNITS          "KBytes"
    MAX-ACCESS     read-only
    STATUS         current
    DESCRIPTION    "Memory Size of SFDS Card"
    ::= { infoSFDSEntry 5 }


infoSFDSStatus OBJECT-TYPE
    SYNTAX      OCTET STRING
    MAX-ACCESS  read-only
    STATUS      current
    DESCRIPTION "SFDS card status"
    ::= { infoSFDSEntry 6 }

--
-- Drive Interface Cards for 2U (will not be displayed if not 2U)
--

infoDriveCardCount OBJECT-TYPE
    SYNTAX         INTEGER
    MAX-ACCESS     read-only
    STATUS         current
    DESCRIPTION    "Number of drive interface cards"
    ::= { lhnNusCommonInfo 12 }

infoDriveCardTable OBJECT-TYPE
    SYNTAX      SEQUENCE OF InfoDriveCardEntry
    MAX-ACCESS  not-accessible
    STATUS      current
    DESCRIPTION
    "A table of drive interface cards in the system.
     The number of entries is given by infoDriveCardCount."
    ::= { lhnNusCommonInfo 13 }


infoDriveCardEntry OBJECT-TYPE
    SYNTAX      InfoDriveCardEntry
    MAX-ACCESS  not-accessible
    STATUS      current
    DESCRIPTION "A row of drive card parameters"
    INDEX { infoDriveCardIndex }
    ::= { infoDriveCardTable 1 }

InfoDriveCardEntry ::= SEQUENCE
{
   infoDriveCardIndex            INTEGER,
   infoDriveCardModel            OCTET STRING,
   infoDriveCardBiosVersion      OCTET STRING,
   infoDriveCardFirmwareVersion  OCTET STRING
}

infoDriveCardIndex OBJECT-TYPE
    SYNTAX         INTEGER
    MAX-ACCESS     read-only
    STATUS         current
    DESCRIPTION    "index for a drive card"
    ::= { infoDriveCardEntry 1 }

infoDriveCardModel OBJECT-TYPE
    SYNTAX      OCTET STRING
    MAX-ACCESS  read-only
    STATUS      current
    DESCRIPTION "Drive Interface Card Model"
    ::= { infoDriveCardEntry 2 }

infoDriveCardBiosVersion OBJECT-TYPE
    SYNTAX      OCTET STRING
    MAX-ACCESS  read-only
    STATUS      current
    DESCRIPTION "Drive Interface Card BIOS Version"
    ::= { infoDriveCardEntry 3 }

infoDriveCardFirmwareVersion OBJECT-TYPE
    SYNTAX      OCTET STRING
    MAX-ACCESS  read-only
    STATUS      current
    DESCRIPTION "Drive Interface Card Firmware Version"
    ::= { infoDriveCardEntry 4 }

END
