HP-httpManageable-MIB DEFINITIONS ::= BEGIN

  IMPORTS
     OBJECT-TYPE, MODULE-IDENTITY, NOTIFICATION-TYPE,
     enterprises
       FROM SNMPv2-SMI
     TEXTUAL-CONVENTION
       FROM SNMPv2-TC
     OBJECT-GROUP, NOTIFICATION-GROUP, MODULE-COMPLIANCE
       FROM SNMPv2-CONF;

  hpHttpMgMod MODULE-IDENTITY
    LAST-UPDATED "9706260000Z"
    ORGANIZATION "Hewlett-Packard Web-based Management Working Group"
    CONTACT-INFO
    "WG E-mail: webmgmt@sysman.hpl.hp.com
         Chair: Brian Harrison
        Postal: Hewlett-Packard
                10500 Ridgeview Court
                Cupertino  CA 95014  USA
           Tel: +1-408-343-5661
           Fax: +1-408-343-6537
        E-mail: brian_harrison@hp.com"

    DESCRIPTION
      "Management information for HTTP manageable devices.
       This MIB gives SNMP systems information on how to
       manage a device using HTTP."
    REVISION     "9706260000Z"
    DESCRIPTION  "Incorporated NetCitizen definitions"
    REVISION     "9606120000Z"
    DESCRIPTION  "Initial Version"

              ::= { hpWebMgmt 1 }

  hp        OBJECT IDENTIFIER ::= { enterprises 11 }
  nm        OBJECT IDENTIFIER ::= { hp 2 }
  hpWebMgmt OBJECT IDENTIFIER ::= { nm 36 }

     -- textual conventions

     Utf8String ::= TEXTUAL-CONVENTION
         DISPLAY-HINT "255a"
         STATUS  current
         DESCRIPTION
              "To facilitate internationalization, this TC
               represents information taken from the ISO/IEC IS
               10646-1 character set, encoded as an octet string
               using the UTF-8 character encoding scheme described
               in RFC 2044 [10].  For strings in 7-bit US-ASCII,
               there is no impact since the UTF-8 representation is
               identical to the US-ASCII encoding."
         SYNTAX  OCTET STRING (SIZE (0..255))


    hpHttpMgTraps         OBJECT IDENTIFIER ::= { hpHttpMgMod 0 }
    hpHttpMgObjects       OBJECT IDENTIFIER ::= { hpHttpMgMod 1 }
    hpHttpMgGroups        OBJECT IDENTIFIER ::= { hpHttpMgMod 2 }
    hpHttpMgCompliances   OBJECT IDENTIFIER ::= { hpHttpMgMod 3 }

    -- MIB Objects
    -- Default attributes for managing via HTTP
    hpHttpMgDefaults      OBJECT IDENTIFIER ::= { hpHttpMgObjects 1 }

    hpHttpMgDefaultURL    OBJECT-TYPE
        SYNTAX      Utf8String
        MAX-ACCESS  read-write
        STATUS      current
        DESCRIPTION
            "A Uniform Resource Locator (URL), as defined in RFC1738,
             for the default management information for this device.
             This URL is typically used by a HTTP browser to display
             management information for this device.  This default
             page should contain links to any other management
             pages for this device."
        ::= { hpHttpMgDefaults 1}

    -- Additional HP NetCitizen attributes

    hpHttpMgNetCitizen    OBJECT IDENTIFIER ::= { hpHttpMgObjects 2 }

    hpHttpMgMgmtSrvrURL OBJECT-TYPE
        SYNTAX          Utf8String
        MAX-ACCESS      read-write
        STATUS          current
        DESCRIPTION     "URL of management server for this device.  "
        ::= { hpHttpMgNetCitizen 1}

    hpHttpMgID OBJECT-TYPE
        SYNTAX          Utf8String
        MAX-ACCESS      read-only
        STATUS          current
        DESCRIPTION     "Unique identifier for this entity.  This ID
                        must not change even if network address or
                        removable cards are changed. For devices with
                        fixed MAC addresses this may be the same as
                        ifPhysAddress; for devices with fixed serial
                        numbers this may be the same as
                        hpHttpMgSerialNumber."
        ::= { hpHttpMgNetCitizen 2}

    hpHttpMgHealth OBJECT-TYPE
        SYNTAX          INTEGER {
                                unknown(1),
                                information(2),
                                ok(3),
                                warning(4),
                                critical(5),
                                nonrecoverable(6)
                                }
        MAX-ACCESS      read-only
        STATUS          current
        DESCRIPTION     "Operating status of this entity."
        ::= { hpHttpMgNetCitizen 3}

    hpHttpMgManufacturer OBJECT-TYPE
        SYNTAX          Utf8String
        MAX-ACCESS      read-only
        STATUS          current
        DESCRIPTION     "Manufacturer of the hardware for this entity
                         e.g. 'Hewlett-Packard'."
        ::= { hpHttpMgNetCitizen 4}

    hpHttpMgProduct OBJECT-TYPE
        SYNTAX          Utf8String (SIZE(0..32))
        MAX-ACCESS      read-only
        STATUS          current
        DESCRIPTION     "Manufacturer's product number for this entity,
                         e.g. 'D1234A'."
        ::= { hpHttpMgNetCitizen 5}

    hpHttpMgVersion OBJECT-TYPE
        SYNTAX          Utf8String (SIZE(0..32))
        MAX-ACCESS      read-only
        STATUS          current
        DESCRIPTION     "Version number of this entity, e.g. 'A.00.01'.
                         Where several version numbers are available,
                         this represents the software version."
        ::= { hpHttpMgNetCitizen 6}

    hpHttpMgHWVersion OBJECT-TYPE
        SYNTAX          Utf8String (SIZE(0..32))
        MAX-ACCESS      read-only
        STATUS          current
        DESCRIPTION     "Version number of the hardware for this entity,
                         e.g. 'A.00.01'."
        ::= { hpHttpMgNetCitizen 7}

    hpHttpMgROMVersion OBJECT-TYPE
        SYNTAX          Utf8String (SIZE(0..32))
        MAX-ACCESS      read-only
        STATUS          current
        DESCRIPTION     "Version number of ROM for this entity, e.g.
                        'A.00.01'."
        ::= { hpHttpMgNetCitizen 8}

    hpHttpMgSerialNumber OBJECT-TYPE
        SYNTAX          Utf8String (SIZE(0..32))
        MAX-ACCESS      read-write
        STATUS          current
        DESCRIPTION     "Serial number of entity.  It is recommended
                        that this be factory set and read only; if not
                        factory set, should initially be blank."
        ::= { hpHttpMgNetCitizen 9}

    hpHttpMgAssetNumber OBJECT-TYPE
        SYNTAX          Utf8String (SIZE(0..32))
        MAX-ACCESS      read-write
        STATUS          current
        DESCRIPTION     "Asset number of entity.  This is not normally
                        modified once set."
        ::= { hpHttpMgNetCitizen 10}

    hpHttpMgPhone OBJECT-TYPE
        SYNTAX          Utf8String (SIZE(0..32))
        MAX-ACCESS      read-write
        STATUS          current
        DESCRIPTION     "Phone number of contact person for this
                        entity."
        ::= { hpHttpMgNetCitizen 11}


    -- Trap Definitions

    hpHttpMgHealthTrap NOTIFICATION-TYPE
        OBJECTS         { hpHttpMgHealth }
        STATUS          current
        DESCRIPTION     "Sent whenever hpHttpMgHealth changes state."
        ::= { hpHttpMgTraps 1 }

    hpHttpMgShutdown NOTIFICATION-TYPE
        STATUS          current
        DESCRIPTION     "Sent when the agent is about to shut down."
        ::= { hpHttpMgTraps 2 }


    -- Compliance statements

    hpHttpMgMinCompliance MODULE-COMPLIANCE
        STATUS  current
        DESCRIPTION
            "The compliance statement for SNMP entities which
             are http manageable."

        MODULE  -- this module
        MANDATORY-GROUPS { hpHttpMgDefaultGroup }

        ::= { hpHttpMgCompliances 1 }

    hpHttpMgBasicNetCitizenCompliance MODULE-COMPLIANCE
            STATUS current
                DESCRIPTION
                    " The compliance statement for SNMP entities which
                      meet basic NetCitizen crieria"
                MODULE -- this module
                MANDATORY-GROUPS { hpHttpMgDefaultGroup,
                                   hpHttpMgBasicNetCitizenGroup,
                                   hpHttpMgBasicNetCitizenTrapGroup }
                ::= { hpHttpMgCompliances 2 }


    -- Units of conformance

    hpHttpMgDefaultGroup OBJECT-GROUP
        OBJECTS { hpHttpMgDefaultURL }
        STATUS current
        DESCRIPTION
            "The objects providing information applicable to all
             http manageable systems"
              ::= { hpHttpMgGroups 1 }

    hpHttpMgBasicNetCitizenGroup OBJECT-GROUP
        OBJECTS {   hpHttpMgMgmtSrvrURL,
                    hpHttpMgID,
                    hpHttpMgHealth,
                    hpHttpMgManufacturer,
                    hpHttpMgProduct,
                    hpHttpMgVersion }
        STATUS current
        DESCRIPTION
            "Additional HP NetCitizen objects"
              ::= { hpHttpMgGroups 2 }

    hpHttpMgBasicNetCitizenTrapGroup NOTIFICATION-GROUP
        NOTIFICATIONS { hpHttpMgHealthTrap }
        STATUS current
        DESCRIPTION
            "HP NetCitizen notifications"
              ::= { hpHttpMgGroups 3 }

    hpHttpMgExtendedNetCitizenGroup OBJECT-GROUP
        OBJECTS {   hpHttpMgHWVersion,
                    hpHttpMgROMVersion,
                    hpHttpMgSerialNumber,
                    hpHttpMgAssetNumber,
                    hpHttpMgPhone }
        STATUS current
        DESCRIPTION
            "Additional HP NetCitizen objects"
              ::= { hpHttpMgGroups 4 }

    hpHttpMgExtendedNetCitizenTrapGroup NOTIFICATION-GROUP
        NOTIFICATIONS { hpHttpMgShutdown }
        STATUS current
        DESCRIPTION
            "HP NetCitizen notifications"
              ::= { hpHttpMgGroups 5 }

  END
