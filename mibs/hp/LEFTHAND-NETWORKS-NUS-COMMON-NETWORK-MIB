LEFTHAND-NETWORKS-NUS-COMMON-NETWORK-MIB DEFINITIONS ::= BEGIN

-- IMPORTS: Include definitions from other mibs here, which is always
-- the first item in a MIB file.
IMPORTS
 	MODULE-IDENTITY, OBJECT-TYPE, IpAddress    FROM SNMPv2-SMI
	RowStatus, TruthValue                      FROM SNMPv2-TC
	lhnModules                                 FROM LEFTHAND-NETWORKS-GLOBAL-REG
	lhnNusCommonNetwork                        FROM LEFTHAND-NETWORKS-NUS-COMMON-MIB;

--
-- A brief description and update information about this mib.
--
lhnNusCommonNetworkModule MODULE-IDENTITY
    LAST-UPDATED "0106010000Z"
	 ORGANIZATION "LeftHand Networks, Inc."
    CONTACT-INFO "
                  Author:     Jose Faria
                              LeftHand Networks
                  postal:     1688 Conestoga St.
                              Boulder, CO 80301
                              USA
                  email:      jfaria@lefthandnetworks.com
                  phone:      +1 303 449-4100
                 "
    DESCRIPTION  "network items for NSM Devices"
    ::= { lhnModules 5 }

-- *********************************************************************************
--
-- Network Module Objects
--
-- *********************************************************************************

networkDeviceCount OBJECT-TYPE
    SYNTAX      INTEGER
    MAX-ACCESS  read-only
    STATUS      current
    DESCRIPTION "number of network devices"
    ::= { lhnNusCommonNetwork 1 }

networkDeviceTable OBJECT-TYPE
    SYNTAX      SEQUENCE OF NetworkDeviceEntry
    MAX-ACCESS  not-accessible
    STATUS      current
    DESCRIPTION
	"A table of network setup parameters for the NSM.
	 The number of entries is given by networkDeviceCount."
    ::= { lhnNusCommonNetwork 2 }

NetworkDeviceEntry ::= SEQUENCE
{
   networkDeviceIndex          INTEGER,
   networkDeviceName           OCTET STRING,
   networkDeviceIpAddress      IpAddress,
   networkDeviceMask           IpAddress,
   networkDeviceDefaultGateway IpAddress,
   networkDeviceMode           INTEGER,
   networkDeviceStatus         OCTET STRING
}

networkDeviceEntry OBJECT-TYPE
    SYNTAX      NetworkDeviceEntry
    MAX-ACCESS  not-accessible
    STATUS      current
    DESCRIPTION
	"A row of network setup parameters for the NSM."
    INDEX { networkIndex }
    ::= { networkDeviceTable 1 }

networkDeviceIndex OBJECT-TYPE
    SYNTAX      INTEGER
    MAX-ACCESS  read-only
    STATUS      current
    DESCRIPTION
	"network device index"
    ::= { networkDeviceEntry 1 }

networkDeviceName OBJECT-TYPE
    SYNTAX      OCTET STRING
    MAX-ACCESS  read-only
    STATUS      current
    DESCRIPTION "network device name"
    ::= { networkDeviceEntry 6 }

networkDeviceIpAddress OBJECT-TYPE
    SYNTAX      IpAddress
    MAX-ACCESS  read-write
    STATUS      current
    DESCRIPTION
	"IP address"
    ::= { networkDeviceEntry 7 }

networkDeviceMask OBJECT-TYPE
    SYNTAX      IpAddress
    MAX-ACCESS  read-write
    STATUS      current
    DESCRIPTION
	"network mask"
    ::= { networkDeviceEntry 8 }

networkDeviceDefaultGateway OBJECT-TYPE
    SYNTAX      IpAddress
    MAX-ACCESS  read-write
    STATUS      current
    DESCRIPTION
	"network default gateway"
    ::= { networkDeviceEntry 9 }

networkDeviceMode OBJECT-TYPE
   SYNTAX      INTEGER { disabled(1), auto(2), static(3), slave(4) }
   MAX-ACCESS  read-write
   STATUS      current
   DESCRIPTION "network device mode"
   ::= { networkDeviceEntry 10 }

networkDeviceStatus OBJECT-TYPE
    SYNTAX      OCTET STRING
    MAX-ACCESS  read-only
    STATUS      current
    DESCRIPTION "network device status"
    ::= { networkDeviceEntry 11 }

END
