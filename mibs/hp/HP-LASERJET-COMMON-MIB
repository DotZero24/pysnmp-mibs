-- THIS MIB CREATED TO REDUCE DUPLICATION BETWEEN HP LASERJET MIBS
--
--  Notes:
--
--  1) Objects containing a string which are defined in this MIB use the
--     first two bytes to hold the symbol set used to encode the string.
--     The Roman-8 symbol set has a hex encoding of 0x0115.  Other
--     symbol sets are listed in the PCL 5 Comparison Guide in table
--     C-1 Symbol Set Values.
--
HP-LASERJET-COMMON-MIB DEFINITIONS ::= BEGIN

IMPORTS
   enterprises               FROM SNMPv2-SMI
   DisplayString             FROM SNMPv2-TC;

hp  MODULE-IDENTITY
    LAST-UPDATED "202005180000Z" --May 17, 2020 00:00 GMT
    ORGANIZATION "Hewlett-Packard Company"
    CONTACT-INFO "Customer Care Center"
    DESCRIPTION  "Objects used in HP JetDirect Print Servers"

    REVISION "202005180000Z"
    DESCRIPTION  "Copied multiple Oids from FUTURESMART-MIB."

    ::= { enterprises 11 }


-- hp OBJECT IDENTIFIER ::= { enterprises 11 }
nm OBJECT IDENTIFIER ::= { hp 2 }
hpsystem OBJECT IDENTIFIER ::= { nm 3 }
net-peripheral OBJECT IDENTIFIER ::= { hpsystem 9 }
netdm OBJECT IDENTIFIER ::= { net-peripheral 4 }
dm OBJECT IDENTIFIER ::= { netdm 2 }

device                                 OBJECT IDENTIFIER ::=  { dm 1 }
device-system                          OBJECT IDENTIFIER ::=  { device 1 }

settings-system                        OBJECT IDENTIFIER ::=  { device-system 1 }
status-system                          OBJECT IDENTIFIER ::=  { device-system 2 }

test                                   OBJECT IDENTIFIER ::=  { device-system 5 }

job                                    OBJECT IDENTIFIER ::=  { device-system 6 }

job-info                               OBJECT IDENTIFIER ::=  { job 5 }
job-info-accounting                    OBJECT IDENTIFIER ::=  { job-info 28 }
processing-subsystem                   OBJECT IDENTIFIER ::=  { device 3 }
pml                                    OBJECT IDENTIFIER ::=  { processing-subsystem 4 }
accounting                             OBJECT IDENTIFIER ::=  { device-system 16 }

printer-accounting                     OBJECT IDENTIFIER ::=  { accounting 1 }
printed-media-usage                    OBJECT IDENTIFIER ::=  { printer-accounting 1 }
printer-color-accounting               OBJECT IDENTIFIER ::=  { accounting 3 }
printed-media-color-usage              OBJECT IDENTIFIER ::=  { printer-color-accounting 1 }
printed-modes-accounting               OBJECT IDENTIFIER ::=  { accounting 4 }
printed-modes-usage                    OBJECT IDENTIFIER ::=  { printed-modes-accounting 1 }
source-tray-accounting                 OBJECT IDENTIFIER ::=  { accounting 5 }
source-tray-usage                      OBJECT IDENTIFIER ::=  { source-tray-accounting 1 }
destination-bin-accounting             OBJECT IDENTIFIER ::=  { accounting 6 }
destination-bin-usage                  OBJECT IDENTIFIER ::=  { destination-bin-accounting 1 }
destination-subsystem                  OBJECT IDENTIFIER ::=  { device 4 }
print-engine                           OBJECT IDENTIFIER ::=  { destination-subsystem 1 }
print-media                            OBJECT IDENTIFIER ::=  { print-engine 8 }
media-size                             OBJECT IDENTIFIER ::=  { print-media 5 }
background-message                     OBJECT IDENTIFIER ::=  { status-system 37 }
background-message1                    OBJECT IDENTIFIER ::=  { background-message 1 }
background-message2                    OBJECT IDENTIFIER ::=  { background-message 2 }
control-panel-display                  OBJECT IDENTIFIER ::=  { status-system 65 }

id                                     OBJECT IDENTIFIER ::=  { device-system 3 }

interface                              OBJECT IDENTIFIER ::=  { device-system 4 }
at                                     OBJECT IDENTIFIER ::=  { interface 2 }
at1                                    OBJECT IDENTIFIER ::=  { at 1 }
imaging                                OBJECT IDENTIFIER ::=  { print-engine 6 }
simm                                   OBJECT IDENTIFIER ::=  { interface 1 }
simm1                                  OBJECT IDENTIFIER ::=  { simm 1 }
simm1-bank                             OBJECT IDENTIFIER ::=  { simm1 6 }
simm1-bank1                            OBJECT IDENTIFIER ::=  { simm1-bank 1 }
simm1-bank2                            OBJECT IDENTIFIER ::=  { simm1-bank 2 }
simm2                                  OBJECT IDENTIFIER ::=  { simm 2 }
simm2-bank                             OBJECT IDENTIFIER ::=  { simm2 6 }
simm2-bank1                            OBJECT IDENTIFIER ::=  { simm2-bank 1 }
simm2-bank2                            OBJECT IDENTIFIER ::=  { simm2-bank 2 }
simm3-bank                             OBJECT IDENTIFIER ::=  { simm3 6 }
simm3-bank1                            OBJECT IDENTIFIER ::=  { simm3-bank 1 }
simm3-bank2                            OBJECT IDENTIFIER ::=  { simm3-bank 2 }
simm3                                  OBJECT IDENTIFIER ::=  { simm 3 }
simm4                                  OBJECT IDENTIFIER ::=  { simm 4 }
simm5                                  OBJECT IDENTIFIER ::=  { simm 5 }
simm6                                  OBJECT IDENTIFIER ::=  { simm 6 }
simm7                                  OBJECT IDENTIFIER ::=  { simm 7 }
simm8                                  OBJECT IDENTIFIER ::=  { simm 8 }

settings-job                           OBJECT IDENTIFIER ::=  { job 1 }
operating-system                       OBJECT IDENTIFIER ::=  { device-system 19 }
phd                                    OBJECT IDENTIFIER ::=  { interface 5 }
phd1                                   OBJECT IDENTIFIER ::=  { phd 1 }
phd2                                   OBJECT IDENTIFIER ::=  { phd 2 }
phd3                                   OBJECT IDENTIFIER ::=  { phd 3 }
phd4                                   OBJECT IDENTIFIER ::=  { phd 4 }
phd5                                   OBJECT IDENTIFIER ::=  { phd 5 }
phd6                                   OBJECT IDENTIFIER ::=  { phd 6 }

pdl                                    OBJECT IDENTIFIER ::=  { processing-subsystem 3 }
settings-pdl                           OBJECT IDENTIFIER ::=  { pdl 1 }
status-pdl                             OBJECT IDENTIFIER ::=  { pdl 2 }
menus                                  OBJECT IDENTIFIER ::=  { print-engine 13 }
errorlog                               OBJECT IDENTIFIER ::=  { device-system 11 }
error1                                 OBJECT IDENTIFIER ::=  { errorlog 1 }
error2                                 OBJECT IDENTIFIER ::=  { errorlog 2 }
error3                                 OBJECT IDENTIFIER ::=  { errorlog 3 }
error4                                 OBJECT IDENTIFIER ::=  { errorlog 4 }
error5                                 OBJECT IDENTIFIER ::=  { errorlog 5 }
error6                                 OBJECT IDENTIFIER ::=  { errorlog 6 }
error7                                 OBJECT IDENTIFIER ::=  { errorlog 7 }
error8                                 OBJECT IDENTIFIER ::=  { errorlog 8 }
error9                                 OBJECT IDENTIFIER ::=  { errorlog 9 }
error10                                OBJECT IDENTIFIER ::=  { errorlog 10 }
error11                                OBJECT IDENTIFIER ::=  { errorlog 11 }
error12                                OBJECT IDENTIFIER ::=  { errorlog 12 }
error13                                OBJECT IDENTIFIER ::=  { errorlog 13 }
error14                                OBJECT IDENTIFIER ::=  { errorlog 14 }
error15                                OBJECT IDENTIFIER ::=  { errorlog 15 }
error16                                OBJECT IDENTIFIER ::=  { errorlog 16 }
error17                                OBJECT IDENTIFIER ::=  { errorlog 17 }
error18                                OBJECT IDENTIFIER ::=  { errorlog 18 }
error19                                OBJECT IDENTIFIER ::=  { errorlog 19 }
error20                                OBJECT IDENTIFIER ::=  { errorlog 20 }
error21                                OBJECT IDENTIFIER ::=  { errorlog 21 }
error22                                OBJECT IDENTIFIER ::=  { errorlog 22 }
error23                                OBJECT IDENTIFIER ::=  { errorlog 23 }
error24                                OBJECT IDENTIFIER ::=  { errorlog 24 }
error25                                OBJECT IDENTIFIER ::=  { errorlog 25 }
error26                                OBJECT IDENTIFIER ::=  { errorlog 26 }
error27                                OBJECT IDENTIFIER ::=  { errorlog 27 }
error28                                OBJECT IDENTIFIER ::=  { errorlog 28 }
error29                                OBJECT IDENTIFIER ::=  { errorlog 29 }
error30                                OBJECT IDENTIFIER ::=  { errorlog 30 }
error31                                OBJECT IDENTIFIER ::=  { errorlog 31 }
error32                                OBJECT IDENTIFIER ::=  { errorlog 32 }
error33                                OBJECT IDENTIFIER ::=  { errorlog 33 }
error34                                OBJECT IDENTIFIER ::=  { errorlog 34 }
error35                                OBJECT IDENTIFIER ::=  { errorlog 35 }
error36                                OBJECT IDENTIFIER ::=  { errorlog 36 }
error37                                OBJECT IDENTIFIER ::=  { errorlog 37 }
error38                                OBJECT IDENTIFIER ::=  { errorlog 38 }
error39                                OBJECT IDENTIFIER ::=  { errorlog 39 }
error40                                OBJECT IDENTIFIER ::=  { errorlog 40 }
error41                                OBJECT IDENTIFIER ::=  { errorlog 41 }
error42                                OBJECT IDENTIFIER ::=  { errorlog 42 }
error43                                OBJECT IDENTIFIER ::=  { errorlog 43 }
error44                                OBJECT IDENTIFIER ::=  { errorlog 44 }
error45                                OBJECT IDENTIFIER ::=  { errorlog 45 }
error46                                OBJECT IDENTIFIER ::=  { errorlog 46 }
error47                                OBJECT IDENTIFIER ::=  { errorlog 47 }
error48                                OBJECT IDENTIFIER ::=  { errorlog 48 }
error49                                OBJECT IDENTIFIER ::=  { errorlog 49 }
error50                                OBJECT IDENTIFIER ::=  { errorlog 50 }
error51                                OBJECT IDENTIFIER ::=  { errorlog 51 }
error52                                OBJECT IDENTIFIER ::=  { errorlog 52 }
error53                                OBJECT IDENTIFIER ::=  { errorlog 53 }
error54                                OBJECT IDENTIFIER ::=  { errorlog 54 }
error55                                OBJECT IDENTIFIER ::=  { errorlog 55 }
error56                                OBJECT IDENTIFIER ::=  { errorlog 56 }
error57                                OBJECT IDENTIFIER ::=  { errorlog 57 }
error58                                OBJECT IDENTIFIER ::=  { errorlog 58 }
error59                                OBJECT IDENTIFIER ::=  { errorlog 59 }
error60                                OBJECT IDENTIFIER ::=  { errorlog 60 }
error61                                OBJECT IDENTIFIER ::=  { errorlog 61 }
error62                                OBJECT IDENTIFIER ::=  { errorlog 62 }
error63                                OBJECT IDENTIFIER ::=  { errorlog 63 }
error64                                OBJECT IDENTIFIER ::=  { errorlog 64 }
error65                                OBJECT IDENTIFIER ::=  { errorlog 65 }
error66                                OBJECT IDENTIFIER ::=  { errorlog 66 }
error67                                OBJECT IDENTIFIER ::=  { errorlog 67 }
error68                                OBJECT IDENTIFIER ::=  { errorlog 68 }
error69                                OBJECT IDENTIFIER ::=  { errorlog 69 }
error70                                OBJECT IDENTIFIER ::=  { errorlog 70 }
error71                                OBJECT IDENTIFIER ::=  { errorlog 71 }
error72                                OBJECT IDENTIFIER ::=  { errorlog 72 }
error73                                OBJECT IDENTIFIER ::=  { errorlog 73 }
error74                                OBJECT IDENTIFIER ::=  { errorlog 74 }
error75                                OBJECT IDENTIFIER ::=  { errorlog 75 }
error76                                OBJECT IDENTIFIER ::=  { errorlog 76 }
error77                                OBJECT IDENTIFIER ::=  { errorlog 77 }
error78                                OBJECT IDENTIFIER ::=  { errorlog 78 }
error79                                OBJECT IDENTIFIER ::=  { errorlog 79 }
error80                                OBJECT IDENTIFIER ::=  { errorlog 80 }
error81                                OBJECT IDENTIFIER ::=  { errorlog 81 }
error82                                OBJECT IDENTIFIER ::=  { errorlog 82 }
error83                                OBJECT IDENTIFIER ::=  { errorlog 83 }
error84                                OBJECT IDENTIFIER ::=  { errorlog 84 }
error85                                OBJECT IDENTIFIER ::=  { errorlog 85 }
error86                                OBJECT IDENTIFIER ::=  { errorlog 86 }
error87                                OBJECT IDENTIFIER ::=  { errorlog 87 }
error88                                OBJECT IDENTIFIER ::=  { errorlog 88 }
error89                                OBJECT IDENTIFIER ::=  { errorlog 89 }
error90                                OBJECT IDENTIFIER ::=  { errorlog 90 }

channel                                OBJECT IDENTIFIER ::=  { device 6 }
channelTable                           OBJECT IDENTIFIER ::=  { channel 3 }
channelEntry                           OBJECT IDENTIFIER ::=  { channelTable 1 }
display                                OBJECT IDENTIFIER ::=  { status-system 20 }
display-status                         OBJECT IDENTIFIER ::=  { display 1 }
status-message                         OBJECT IDENTIFIER ::=  { display 2 }
status-message1                        OBJECT IDENTIFIER ::=  { status-message 1 }
web-server                             OBJECT IDENTIFIER ::=  { interface 6 }
settings-web-server                    OBJECT IDENTIFIER ::=  { web-server 1 }
pdl-postscript                         OBJECT IDENTIFIER ::=  { pdl 4 }
webserver-proc-sub                     OBJECT IDENTIFIER ::=  { processing-subsystem 9 }
settings-webserver                     OBJECT IDENTIFIER ::=  { webserver-proc-sub 1 }
settings-prt-eng                       OBJECT IDENTIFIER ::=  { print-engine 1 }
intray                                 OBJECT IDENTIFIER ::=  { print-engine 3 }
settings-intray                        OBJECT IDENTIFIER ::=  { intray 1 }
status-intray                          OBJECT IDENTIFIER ::=  { intray 2 }
ph                                     OBJECT IDENTIFIER ::=  { print-engine 7 }
settings-ph                            OBJECT IDENTIFIER ::=  { ph 1 }
pdl-pcl                                OBJECT IDENTIFIER ::=  { pdl 3 }
pdl-esc-p                              OBJECT IDENTIFIER ::=  { pdl 5 }
pdl-pdf                                OBJECT IDENTIFIER ::=  { pdl 15 }
pdl-pclxl                              OBJECT IDENTIFIER ::=  { pdl 16 }
active-print-jobs                      OBJECT IDENTIFIER ::=  { job 2 }
job-being-parsed                       OBJECT IDENTIFIER ::=  { active-print-jobs 1 }
job-info-attribute                     OBJECT IDENTIFIER ::=  { job-info 23 }
fax-job-control                        OBJECT IDENTIFIER ::=  { job 3 }
settings-fax-job                       OBJECT IDENTIFIER ::=  { fax-job-control 1 }
status-fax-job                         OBJECT IDENTIFIER ::=  { fax-job-control 2 }
faxjob                                 OBJECT IDENTIFIER ::=  { fax-job-control 3 }
faxjob-rx-status                       OBJECT IDENTIFIER ::=  { faxjob 1 }
faxjob-tx-status                       OBJECT IDENTIFIER ::=  { faxjob 3 }
faxjob-tx-error                        OBJECT IDENTIFIER ::=  { faxjob 4 }
faxjob-tx-current-page                 OBJECT IDENTIFIER ::=  { faxjob 5 }
faxjob-rx-current-page                 OBJECT IDENTIFIER ::=  { faxjob 6 }
faxjob-rx-duration                     OBJECT IDENTIFIER ::=  { faxjob 7 }
faxjob-tx-duration                     OBJECT IDENTIFIER ::=  { faxjob 8 }
fax-activity-log                       OBJECT IDENTIFIER ::=  { job 4 }
settings-faxlog                        OBJECT IDENTIFIER ::=  { fax-activity-log 1 }
settings-fax-proc-sub                  OBJECT IDENTIFIER ::=  { fax-proc-sub 1 }
status-fax-proc-sub                    OBJECT IDENTIFIER ::=  { fax-proc-sub 2 }
fax-forwarding                         OBJECT IDENTIFIER ::=  { fax-proc-sub 3 }
fax-receive                            OBJECT IDENTIFIER ::=  { source-subsystem 3 }
settings-fax-receive                   OBJECT IDENTIFIER ::=  { fax-receive 1 }
status-fax-receive                     OBJECT IDENTIFIER ::=  { fax-receive 2 }
held-job                               OBJECT IDENTIFIER ::=  { job 7 }
held-job-info                          OBJECT IDENTIFIER ::=  { held-job 1 }
held-job-control                       OBJECT IDENTIFIER ::=  { held-job 2 }
photo-job                              OBJECT IDENTIFIER ::=  { job 8 }
settings-photo-job                     OBJECT IDENTIFIER ::=  { photo-job 3 }

source-subsystem                       OBJECT IDENTIFIER ::=  { device 2 }
spooler                                OBJECT IDENTIFIER ::=  { source-subsystem 4 }
settings-spooler                       OBJECT IDENTIFIER ::=  { spooler 1 }
pjl                                    OBJECT IDENTIFIER ::=  { processing-subsystem 5 }
mio                                    OBJECT IDENTIFIER ::=  { interface 3 }
mio1                                   OBJECT IDENTIFIER ::=  { mio 1 }
mio2                                   OBJECT IDENTIFIER ::=  { mio 2 }
mio3                                   OBJECT IDENTIFIER ::=  { mio 3 }
mio4                                   OBJECT IDENTIFIER ::=  { mio 4 }
usb-interface                          OBJECT IDENTIFIER ::=  { interface 9 }
usb                                    OBJECT IDENTIFIER ::=  { usb-interface 2 }
io                                     OBJECT IDENTIFIER ::=  { source-subsystem 1 }
settings-io                            OBJECT IDENTIFIER ::=  { io 1 }
status-io                              OBJECT IDENTIFIER ::=  { io 2 }
ports                                  OBJECT IDENTIFIER ::=  { io 3 }
port1                                  OBJECT IDENTIFIER ::=  { ports 1 }
parallel                               OBJECT IDENTIFIER ::=  { port1 1 }
foreign-interface                      OBJECT IDENTIFIER   ::= { interface 8 }
fax-send                               OBJECT IDENTIFIER ::=  { destination-subsystem 2 }
settings-fax-send                      OBJECT IDENTIFIER ::=  { fax-send 1 }
status-fax-send                        OBJECT IDENTIFIER ::=  { fax-send 2 }
transmit-fax                           OBJECT IDENTIFIER ::=  { fax-send 5 }
phone                                  OBJECT IDENTIFIER ::=  { device-system 9 }
dial                                   OBJECT IDENTIFIER ::=  { phone 1 }
dial-all-lines                         OBJECT IDENTIFIER ::=  { dial 1 }
answer                                 OBJECT IDENTIFIER ::=  { phone 2 }
answer-all-lines                       OBJECT IDENTIFIER ::=  { answer 1 }
fax-proc-sub                           OBJECT IDENTIFIER ::=  { processing-subsystem 7 }


tables                                 OBJECT IDENTIFIER ::=  { device 7 }
channel-table                          OBJECT IDENTIFIER ::=  { tables 2 }
channel-entry                          OBJECT IDENTIFIER ::=  { channel-table 1 }
remote-procedure-call                  OBJECT IDENTIFIER ::=  { device-system 13 }

settings-rpc                           OBJECT IDENTIFIER ::=  { remote-procedure-call 1 }
status-rpc                             OBJECT IDENTIFIER ::=  { remote-procedure-call 2 }
rpc-services                           OBJECT IDENTIFIER ::=  { remote-procedure-call 3 }
file-system                            OBJECT IDENTIFIER ::=  { device-system 10 }

settings-file-system                   OBJECT IDENTIFIER ::=  { file-system 1 }
status-file-system                     OBJECT IDENTIFIER ::=  { file-system 2 }
file-systems                           OBJECT IDENTIFIER ::=  { file-system 3 }
file-system1                           OBJECT IDENTIFIER ::=  { file-systems 1 }
file-system2                           OBJECT IDENTIFIER ::=  { file-systems 2 }
file-system3                           OBJECT IDENTIFIER ::=  { file-systems 3 }
file-system4                           OBJECT IDENTIFIER ::=  { file-systems 4 }
resource-manager                       OBJECT IDENTIFIER ::=  { device-system 12 }

mass-storage-resources                 OBJECT IDENTIFIER ::=  { resource-manager 3 }
mass-storage-block-driver              OBJECT IDENTIFIER ::=  { device-system 15 }

settings-mass-storage-bd               OBJECT IDENTIFIER ::=  { mass-storage-block-driver 1 }
status-mass-storage-bd                 OBJECT IDENTIFIER ::=  { mass-storage-block-driver 2 }
mass-storage-block-drivers             OBJECT IDENTIFIER ::=  { mass-storage-block-driver 3 }
mass-storage-bd2                       OBJECT IDENTIFIER ::=  { mass-storage-block-drivers 2 }
settings-msbd2                         OBJECT IDENTIFIER ::=  { mass-storage-bd2 1 }

settings-print-media                   OBJECT IDENTIFIER ::=  { print-media 1 }
media-info                             OBJECT IDENTIFIER ::=  { print-media 3 }
media1                                 OBJECT IDENTIFIER ::=  { media-info 1 }
media2                                 OBJECT IDENTIFIER ::=  { media-info 2 }
media3                                 OBJECT IDENTIFIER ::=  { media-info 3 }
media4                                 OBJECT IDENTIFIER ::=  { media-info 4 }
media5                                 OBJECT IDENTIFIER ::=  { media-info 5 }
media6                                 OBJECT IDENTIFIER ::=  { media-info 6 }
media7                                 OBJECT IDENTIFIER ::=  { media-info 7 }
media8                                 OBJECT IDENTIFIER ::=  { media-info 8 }
media9                                 OBJECT IDENTIFIER ::=  { media-info 9 }
media10                                OBJECT IDENTIFIER ::=  { media-info 10 }
media11                                OBJECT IDENTIFIER ::=  { media-info 11 }
media12                                OBJECT IDENTIFIER ::=  { media-info 12 }
media13                                OBJECT IDENTIFIER ::=  { media-info 13 }
media14                                OBJECT IDENTIFIER ::=  { media-info 14 }
media15                                OBJECT IDENTIFIER ::=  { media-info 15 }
media16                                OBJECT IDENTIFIER ::=  { media-info 16 }
media17                                OBJECT IDENTIFIER ::=  { media-info 17 }
media18                                OBJECT IDENTIFIER ::=  { media-info 18 }
media19                                OBJECT IDENTIFIER ::=  { media-info 19 }
media20                                OBJECT IDENTIFIER ::=  { media-info 20 }
media21                                OBJECT IDENTIFIER ::=  { media-info 21 }
media22                                OBJECT IDENTIFIER ::=  { media-info 22 }
media23                                OBJECT IDENTIFIER ::=  { media-info 23 }
media24                                OBJECT IDENTIFIER ::=  { media-info 24 }
media25                                OBJECT IDENTIFIER ::=  { media-info 25 }
media26                                OBJECT IDENTIFIER ::=  { media-info 26 }
media27                                OBJECT IDENTIFIER ::=  { media-info 27 }
media28                                OBJECT IDENTIFIER ::=  { media-info 28 }
media29                                OBJECT IDENTIFIER ::=  { media-info 29 }
media30                                OBJECT IDENTIFIER ::=  { media-info 30 }
media31                                OBJECT IDENTIFIER ::=  { media-info 31 }
media32                                OBJECT IDENTIFIER ::=  { media-info 32 }
media33                                OBJECT IDENTIFIER ::=  { media-info 33 }
media34                                OBJECT IDENTIFIER ::=  { media-info 34 }
media35                                OBJECT IDENTIFIER ::=  { media-info 35 }
media36                                OBJECT IDENTIFIER ::=  { media-info 36 }
media37                                OBJECT IDENTIFIER ::=  { media-info 37 }
media38                                OBJECT IDENTIFIER ::=  { media-info 38 }
media-types                            OBJECT IDENTIFIER ::=  { print-media 8 }
media-sizes                            OBJECT IDENTIFIER ::=  { print-engine 15 }
device-configure                       OBJECT IDENTIFIER ::=  { settings-system 32 }
marking-agent-density                  OBJECT IDENTIFIER ::=  { settings-prt-eng 9 }
status-prt-eng                         OBJECT IDENTIFIER ::=  { print-engine 2 }
printer-calibration-dhalf              OBJECT IDENTIFIER ::=  { status-prt-eng 37 }
printer-cal-dhalf-data                 OBJECT IDENTIFIER ::=  { printer-calibration-dhalf 3 }
printer-cal-grayaxis                   OBJECT IDENTIFIER ::=  { printer-calibration-dhalf 6 }
printer-cal-grayaxis-data              OBJECT IDENTIFIER ::=  { printer-calibration-dhalf 7 }
printer-calibration-cpr                OBJECT IDENTIFIER ::=  { status-prt-eng 38 }
intrays                                OBJECT IDENTIFIER ::=  { intray 3 }
intray1                                OBJECT IDENTIFIER ::=  { intrays 1 }
intray2                                OBJECT IDENTIFIER ::=  { intrays 2 }
intray3                                OBJECT IDENTIFIER ::=  { intrays 3 }
intray4                                OBJECT IDENTIFIER ::=  { intrays 4 }
intray5                                OBJECT IDENTIFIER ::=  { intrays 5 }
intray6                                OBJECT IDENTIFIER ::=  { intrays 6 }
intray7                                OBJECT IDENTIFIER ::=  { intrays 7 }
outbin                                 OBJECT IDENTIFIER ::=  { print-engine 4 }
settings-outbin                        OBJECT IDENTIFIER ::=  { outbin 1 }
outbins                                OBJECT IDENTIFIER ::=  { outbin 3 }
outbin1                                OBJECT IDENTIFIER ::=  { outbins 1 }
outbin2                                OBJECT IDENTIFIER ::=  { outbins 2 }
outbin3                                OBJECT IDENTIFIER ::=  { outbins 3 }
outbin4                                OBJECT IDENTIFIER ::=  { outbins 4 }
outbin5                                OBJECT IDENTIFIER ::=  { outbins 5 }
outbin6                                OBJECT IDENTIFIER ::=  { outbins 6 }
outbin7                                OBJECT IDENTIFIER ::=  { outbins 7 }
outbin8                                OBJECT IDENTIFIER ::=  { outbins 8 }
outbin9                                OBJECT IDENTIFIER ::=  { outbins 9 }
outbin10                               OBJECT IDENTIFIER ::=  { outbins 10 }
outbin11                               OBJECT IDENTIFIER ::=  { outbins 11 }
marking-agent                          OBJECT IDENTIFIER ::=  { print-engine 5 }
settings-marking-agent                 OBJECT IDENTIFIER ::=  { marking-agent 1 }
ph-devices                             OBJECT IDENTIFIER ::=  { ph 3 }
ph2                                    OBJECT IDENTIFIER ::=  { ph-devices 2 }
ph3                                    OBJECT IDENTIFIER ::=  { ph-devices 3 }
ph4                                    OBJECT IDENTIFIER ::=  { ph-devices 4 }
ph5                                    OBJECT IDENTIFIER ::=  { ph-devices 5 }
ph6                                    OBJECT IDENTIFIER ::=  { ph-devices 6 }
media-modes                            OBJECT IDENTIFIER ::=  { print-media 4 }
media-mode-details                     OBJECT IDENTIFIER ::=  { print-media 6 }
media-mode1                            OBJECT IDENTIFIER ::=  { media-mode-details 1 }
media-mode2                            OBJECT IDENTIFIER ::=  { media-mode-details 2 }
media-mode3                            OBJECT IDENTIFIER ::=  { media-mode-details 3 }
media-mode4                            OBJECT IDENTIFIER ::=  { media-mode-details 4 }
media-mode5                            OBJECT IDENTIFIER ::=  { media-mode-details 5 }
media-counts                           OBJECT IDENTIFIER ::=  { print-media 7 }
consumables                            OBJECT IDENTIFIER ::=  { print-engine 10 }
consumables-1                          OBJECT IDENTIFIER ::=  { consumables 1 }
consumable-status                      OBJECT IDENTIFIER ::=  { consumables-1 1 }
consumable-string                      OBJECT IDENTIFIER ::=  { consumables 8 }
consumables-status                     OBJECT IDENTIFIER ::=  { consumables 5 }
consumables-life                       OBJECT IDENTIFIER ::=  { consumables-status 1 }
print-meter                            OBJECT IDENTIFIER ::=  { print-engine 11 }
printer-average                        OBJECT IDENTIFIER ::=  { print-meter 1 }
jetsend-proc-sub                       OBJECT IDENTIFIER ::=  { processing-subsystem 8 }
settings-jetsend                       OBJECT IDENTIFIER ::=  { jetsend-proc-sub 1 }
jetsend-contact                        OBJECT IDENTIFIER ::=  { jetsend-proc-sub 3 }
settings-jetsend-contact               OBJECT IDENTIFIER ::=  { jetsend-contact 1 }
mount                                  OBJECT IDENTIFIER ::=  { rpc-services 1 }
settings-mount                         OBJECT IDENTIFIER ::=  { mount 1 }
nfs-server                             OBJECT IDENTIFIER ::=  { rpc-services 2 }
settings-nfs-server                    OBJECT IDENTIFIER ::=  { nfs-server 1 }
status-nfs-server                      OBJECT IDENTIFIER ::=  { nfs-server 2 }
rpc-bind                               OBJECT IDENTIFIER ::=  { rpc-services 3 }
settings-rpc-bind                      OBJECT IDENTIFIER ::=  { rpc-bind 1 }
status-rpc-bind                        OBJECT IDENTIFIER ::=  { rpc-bind 2 }
xport-interface                        OBJECT IDENTIFIER ::=  { device-system 14 }
status-xip                             OBJECT IDENTIFIER ::=  { xport-interface 2 }
firmware-download                      OBJECT IDENTIFIER ::=  { device-system 18 }

upgradable-devices                     OBJECT IDENTIFIER ::=  { device-system 20 }


warninglog                             OBJECT IDENTIFIER   ::= { device-system 22 }

warning1                 OBJECT IDENTIFIER   ::= { warninglog 1 }
warning2                 OBJECT IDENTIFIER   ::= { warninglog 2 }
warning3                 OBJECT IDENTIFIER   ::= { warninglog 3 }
warning4                 OBJECT IDENTIFIER   ::= { warninglog 4 }
warning5                 OBJECT IDENTIFIER   ::= { warninglog 5 }
warning6                 OBJECT IDENTIFIER   ::= { warninglog 6 }
warning7                 OBJECT IDENTIFIER   ::= { warninglog 7 }
warning8                 OBJECT IDENTIFIER   ::= { warninglog 8 }
warning9                 OBJECT IDENTIFIER   ::= { warninglog 9 }
warning10                OBJECT IDENTIFIER   ::= { warninglog 10 }
warning11                OBJECT IDENTIFIER   ::= { warninglog 11 }
warning12                OBJECT IDENTIFIER   ::= { warninglog 12 }
warning13                OBJECT IDENTIFIER   ::= { warninglog 13 }
warning14                OBJECT IDENTIFIER   ::= { warninglog 14 }
warning15                OBJECT IDENTIFIER   ::= { warninglog 15 }
warning16                OBJECT IDENTIFIER   ::= { warninglog 16 }
warning17                OBJECT IDENTIFIER   ::= { warninglog 17 }
warning18                OBJECT IDENTIFIER   ::= { warninglog 18 }
warning19                OBJECT IDENTIFIER   ::= { warninglog 19 }
warning20                OBJECT IDENTIFIER   ::= { warninglog 20 }
warning21                OBJECT IDENTIFIER   ::= { warninglog 21 }
warning22                OBJECT IDENTIFIER   ::= { warninglog 22 }
warning23                OBJECT IDENTIFIER   ::= { warninglog 23 }
warning24                OBJECT IDENTIFIER   ::= { warninglog 24 }
warning25                OBJECT IDENTIFIER   ::= { warninglog 25 }
warning26                OBJECT IDENTIFIER   ::= { warninglog 26 }
warning27                OBJECT IDENTIFIER   ::= { warninglog 27 }
warning28                OBJECT IDENTIFIER   ::= { warninglog 28 }
warning29                OBJECT IDENTIFIER   ::= { warninglog 29 }
warning30                OBJECT IDENTIFIER   ::= { warninglog 30 }
warning31                OBJECT IDENTIFIER   ::= { warninglog 31 }
warning32                OBJECT IDENTIFIER   ::= { warninglog 32 }
warning33                OBJECT IDENTIFIER   ::= { warninglog 33 }
warning34                OBJECT IDENTIFIER   ::= { warninglog 34 }
warning35                OBJECT IDENTIFIER   ::= { warninglog 35 }
warning36                OBJECT IDENTIFIER   ::= { warninglog 36 }
warning37                OBJECT IDENTIFIER   ::= { warninglog 37 }
warning38                OBJECT IDENTIFIER   ::= { warninglog 38 }
warning39                OBJECT IDENTIFIER   ::= { warninglog 39 }
warning40                OBJECT IDENTIFIER   ::= { warninglog 40 }
warning41                OBJECT IDENTIFIER   ::= { warninglog 41 }
warning42                OBJECT IDENTIFIER   ::= { warninglog 42 }
warning43                OBJECT IDENTIFIER   ::= { warninglog 43 }
warning44                OBJECT IDENTIFIER   ::= { warninglog 44 }
warning45                OBJECT IDENTIFIER   ::= { warninglog 45 }
warning46                OBJECT IDENTIFIER   ::= { warninglog 46 }
warning47                OBJECT IDENTIFIER   ::= { warninglog 47 }
warning48                OBJECT IDENTIFIER   ::= { warninglog 48 }
warning49                OBJECT IDENTIFIER   ::= { warninglog 49 }
warning50                OBJECT IDENTIFIER   ::= { warninglog 50 }
security                 OBJECT IDENTIFIER   ::= { device-system 23 }
settings-security        OBJECT IDENTIFIER   ::= { security 1 }
scanner                                OBJECT IDENTIFIER ::=  { source-subsystem 2 }
settings-scanner                       OBJECT IDENTIFIER ::=  { scanner 1 }
status-scanner                         OBJECT IDENTIFIER ::=  { scanner 2 }
scan-calibration                       OBJECT IDENTIFIER ::=  { settings-scanner 32 }
print-meter-usage                      OBJECT IDENTIFIER ::=  { printer-accounting 14 }
scanner-accounting                     OBJECT IDENTIFIER ::=  { accounting 2 }
scanned-media-usage                    OBJECT IDENTIFIER ::=  { scanner-accounting 1 }
settings-system2       		       OBJECT IDENTIFIER ::=  { device-system 25 }

printmib                               OBJECT IDENTIFIER ::=  { dm 2 }

prtGeneral                             OBJECT IDENTIFIER ::=  { printmib 5 }
prtGeneralTable                        OBJECT IDENTIFIER ::=  { prtGeneral 1 }
prtGeneralEntry                        OBJECT IDENTIFIER ::=  { prtGeneralTable 1 }

prtCover                               OBJECT IDENTIFIER ::=  { printmib 6 }
prtCoverTable                          OBJECT IDENTIFIER ::=  { prtCover 1 }
prtCoverEntry                          OBJECT IDENTIFIER ::=  { prtCoverTable 1 }
prtMarkerSupplies                      OBJECT IDENTIFIER ::=  { printmib 11 }
prtMarkerSuppliesTable                 OBJECT IDENTIFIER ::=  { prtMarkerSupplies 1 }
prtMarkerSuppliesEntry                 OBJECT IDENTIFIER ::=  { prtMarkerSuppliesTable 1 }

prtLocalization                        OBJECT IDENTIFIER ::=  { printmib 7 }
prtLocalizationTable                   OBJECT IDENTIFIER ::=  { prtLocalization 1 }
prtLocalizationEntry                   OBJECT IDENTIFIER ::=  { prtLocalizationTable 1 }
prtStorageRefTable                     OBJECT IDENTIFIER ::=  { prtGeneral 2 }
prtStorageRefEntry                     OBJECT IDENTIFIER ::=  { prtStorageRefTable 1 }
prtDeviceRefTable                      OBJECT IDENTIFIER ::=  { prtGeneral 3 }
prtDeviceRefEntry                      OBJECT IDENTIFIER ::=  { prtDeviceRefTable 1 }

prtInput                               OBJECT IDENTIFIER ::=  { printmib 8 }
prtInputTable                          OBJECT IDENTIFIER ::=  { prtInput 2 }
prtInputEntry                          OBJECT IDENTIFIER ::=  { prtInputTable 1 }

prtOutput                              OBJECT IDENTIFIER ::=  { printmib 9 }
prtOutputTable                         OBJECT IDENTIFIER ::=  { prtOutput 2 }
prtOutputEntry                         OBJECT IDENTIFIER ::=  { prtOutputTable 1 }

prtMarker                              OBJECT IDENTIFIER ::=  { printmib 10 }
prtMarkerTable                         OBJECT IDENTIFIER ::=  { prtMarker 2 }
prtMarkerEntry                         OBJECT IDENTIFIER ::=  { prtMarkerTable 1 }

prtMarkerColorant                      OBJECT IDENTIFIER ::=  { printmib 12 }
prtMarkerColorantTable                 OBJECT IDENTIFIER ::=  { prtMarkerColorant 1 }
prtMarkerColorantEntry                 OBJECT IDENTIFIER ::=  { prtMarkerColorantTable 1 }

prtMediaPath                           OBJECT IDENTIFIER ::=  { printmib 13 }
prtMediaPathTable                      OBJECT IDENTIFIER ::=  { prtMediaPath 4 }
prtMediaPathEntry                      OBJECT IDENTIFIER ::=  { prtMediaPathTable 1 }

prtChannel                             OBJECT IDENTIFIER ::=  { printmib 14 }
prtChannelTable                        OBJECT IDENTIFIER ::=  { prtChannel 1 }
prtChannelEntry                        OBJECT IDENTIFIER ::=  { prtChannelTable 1 }

prtInterpreter                         OBJECT IDENTIFIER ::=  { printmib 15 }
prtInterpreterTable                    OBJECT IDENTIFIER ::=  { prtInterpreter 1 }
prtInterpreterEntry                    OBJECT IDENTIFIER ::=  { prtInterpreterTable 1 }

prtConsoleDisplayBuffer                OBJECT IDENTIFIER ::=  { printmib 16 }
prtConsoleDisplayBufferTable           OBJECT IDENTIFIER ::=  { prtConsoleDisplayBuffer 5 }
prtConsoleDisplayBufferEntry           OBJECT IDENTIFIER ::=  { prtConsoleDisplayBufferTable 1 }

prtConsoleLights                       OBJECT IDENTIFIER ::=  { printmib 17 }
prtConsoleLightTable                   OBJECT IDENTIFIER ::=  { prtConsoleLights 6 }
prtConsoleLightEntry                   OBJECT IDENTIFIER ::=  { prtConsoleLightTable 1 }
prtAlert                               OBJECT IDENTIFIER ::=  { printmib 18 }
prtAlertTable                          OBJECT IDENTIFIER ::=  { prtAlert 1 }
prtAlertEntry                          OBJECT IDENTIFIER ::=  { prtAlertTable 1 }

hrm                                    OBJECT IDENTIFIER ::=  { dm 3 }

hrStorage                              OBJECT IDENTIFIER ::=  { hrm 2 }
hrStorageTable                         OBJECT IDENTIFIER ::=  { hrStorage 3 }
hrStorageEntry                         OBJECT IDENTIFIER ::=  { hrStorageTable 1 }

hrDevice                               OBJECT IDENTIFIER ::=  { hrm 3 }
hrDeviceTable                          OBJECT IDENTIFIER ::=  { hrDevice 2 }
hrDeviceEntry                          OBJECT IDENTIFIER ::=  { hrDeviceTable 1 }
hrPrinterTable                         OBJECT IDENTIFIER ::=  { hrDevice 5 }
hrPrinterEntry                         OBJECT IDENTIFIER ::=  { hrPrinterTable 1 }
hrDiskStorageTable                     OBJECT IDENTIFIER ::=  { hrDevice 6 }
hrDiskStorageEntry                     OBJECT IDENTIFIER ::=  { hrDiskStorageTable 1 }
hrPartitionTable                       OBJECT IDENTIFIER ::=  { hrDevice 7 }
hrPartitionEntry                       OBJECT IDENTIFIER ::=  { hrPartitionTable 1 }
hrFSTable                              OBJECT IDENTIFIER ::=  { hrDevice 8 }
hrFSEntry                              OBJECT IDENTIFIER ::=  { hrFSTable 1 }

net-printer                            OBJECT IDENTIFIER ::=  { net-peripheral 1 }
generalDeviceStatus                    OBJECT IDENTIFIER ::=  { net-printer 1 }
netPrinterType                         OBJECT IDENTIFIER ::=  { net-printer 2 }
gdStatusEntry                          OBJECT IDENTIFIER ::=  { generalDeviceStatus 2 }


localization-language OBJECT-TYPE
    SYNTAX  INTEGER {
		   eEnglish(1),
		   eFrench(2),
		   eGerman(3),
		   eSpanish(4),
		   eItalian(5),
		   eSwedish(6),
		   eDanish(7),
		   eNorwegian(8),
		   eDutch(9),
		   eFinnish(10),
		   eJapanese(11),
		   ePortuguese(12),
		   ePolish(13),
		   eTurkish(14)
		   }
    MAX-ACCESS read-only
    STATUS  current
    DESCRIPTION
                "Localization language used by the device for device
                generated PML strings, control panel messages, and text
                contained in any of the printer generated printed pages.
                The order is the same order that is defined in MIO.
                Since the MIO values start at zero, one has been added
                to each value."
::= { status-system 1 }

not-ready-printer OBJECT-TYPE
    SYNTAX  OCTET STRING
    MAX-ACCESS read-only
    STATUS  current
    DESCRIPTION
                "Indicates if any of the sub-systems in the printer are
                not ready.  A sub-system is not ready if the sub-system
                is unable to perform its function until some sort of
                intervention occurs.  If there are no items in the NOT-
                READY-PRINTER collection (i.e. no bits are set), then
                all printer sub- systems are ready.  Each sub-system has
                a sub-system specific not ready object.  If a sub-system
                specific not ready object contains any items, then the
                associated item will be in the NOT-READY collection."
::= { status-system 2 }


not-ready-controller OBJECT-TYPE
    SYNTAX  OCTET STRING
    MAX-ACCESS read-only
    STATUS  current
    DESCRIPTION
                "Indicates if the hardware controller sub-system in the
                device is not ready.  If there are no items in the
                collection (i.e. no bits are set), then the hardware
                controller sub-system is ready.  If there is an item
                present, then the item indicates what is causing the
                hardware controller sub-system to be not ready.  If the
                cControllerFailure item is in the collection, then a
                hardware error was detected on the main controller PC
                board, sometimes called the formatter or the logic
                broad.  Example controller hardware errors include DRAM
                controller failure, clock failure, memory parity error,
                and ROM CRC error.  The cFirmwareFailure item is in the
                collection if a firmware/software error was detected.
                Device specific detailed error information can be
                retrieved from the error log objects, if the device
                supports those objects.  The POS will list which device
                failures cause each item to be included in the
                collection.
                Additional information:
                A controller failure occurrence will set the
               	cControllerFailure bit (bit 1). The controller
               	failures are: 62.X Service, 63 Service, 65 Service,
               	67 Service, 68 Service, and 68 Error.
               	A SIMM failure occurrence will set the cSIMMFailure
               	bit (bit 2).  The SIMM failures are 61.X Service,
               	53-XY-ZZ Error, and 72 Service.
               	A DISK failure occurrence will set the cATFailure
               	bit (bit 3).  The DISK failure is FS DISK FAILURE."
::= { status-system 3 }


not-idle OBJECT-TYPE
    SYNTAX  OCTET STRING
    MAX-ACCESS read-only
    STATUS  current
    DESCRIPTION
                "Indicates if any of the sub-systems in the device are
                not idle.  The I/O source sub-system is considered not
                idle if there is unprocessed PDL data in the device.
                The PDL processing sub-system is considered not idle if
                the device is processing a print job.  The print engine
                destination sub-system is considered not idle if media
                is moving (i.e. the device is printing).  [other text
                here describing what causes the other sub-systems to be
                considered not idle]."
::= { status-system 4 }

on-off-line OBJECT-TYPE
    SYNTAX  INTEGER {
		   eOnline(1),
		   eOffline(2),
		   eOfflineAtEndOfJob(3)
		   }
    MAX-ACCESS read-write
    STATUS  current
    DESCRIPTION
                "To bring the PDL processing sub-system on or off line.
                If the device is a printer, then the printer does not
                process print job data when the printer is off line.
                PML communication persists.
                Additional information:
                When the printer is in the Offline state,
                printing will stop as soon as possible (no more sheets
                of media are pulled from input trays).  The I/O
                is taken offline also.

                Setting to eOnline has the following affect:
                Printer will immediately go to or remain in the Online
                state; <noError> status is returned.
                If the printer's current state
                is Offline with a pending error condition that
                prevents the printer from going to the Online
                state, the printer will remain in the Offline state;
                <genErr> status is returned

                Setting to eOffline has the following affect:
                Printer will immediately go to or remain in the
                Offline state; <noError> status is returned.
                If pages are being printed, those pages will complete
                with the printer in the Offline state.

                Setting to eOfflineAtEndOfJob has the following
                affect:
                If not in a job or already in the Offline state, the
                printer will immediately go to or remain in the
                Offline state; <noError> status is returned.
                If in a job and the current state is Online, the
                printer will remain in the Online state, with the
                value of this object as eOfflineAtEndOfJob, until the
                end of the job; <noError> status is returned. At the end of
                the job, the printer goes to the Offline state and the
                value of this object becomes eOffline.
                Setting this object to eOffline or eOnline before the
                end of the job causes the action for that value to be
                taken immediately."
::= { status-system 5 }


continue OBJECT-TYPE
    SYNTAX  INTEGER {
		   eInitiateAction(1)
		   }
    MAX-ACCESS read-write
    STATUS  current
    DESCRIPTION
                "A device can support a class of errors called
                continuable errors.  When a continuable error is
                encountered, the device requires a continue event to
                occur before the device will continue operation.  One
                continue event is setting the CONTINUE object to
                eInitiateAction.  Devices can support other continue
                events, like auto-continue.  A continue event causes the
                continuable error to be acknowledged, thus allowing the
                device to continue.  Each device needs to list the
                continuable errors.  If the device doesn't currently
                have an unacknowledged continuable error, the response
                will contain <genErr>.
                Additional information:
                See the CLEARABLE-WARNING and AUTO-CONTINUE objects for the
                errors that this object will clear."
::= { status-system 6 }

auto-continue OBJECT-TYPE
    SYNTAX  INTEGER {
		   eOff(1),
		   eOn(2)
		   }
    MAX-ACCESS read-write
    STATUS  current
    DESCRIPTION
                "Indicates if the device will automatically continue
                after encountering a continuable error.  If AUTO-
                CONTINUE is set to eOn, the device will automatically
                generate continue event to acknowledge continuable
                errors.  If AUTO-CONTINUE is set to eOff, then some
                other continue event will have to acknowledge the
                continuable error.
                Additional information:
                If this is set to eOn the device displays an
                error message and goes offline for ten seconds.  After ten seconds the
                printer automatically returns to the online state.

                If this is set to eOff then the device displays an error message and
                goes offline.  It remains offline until the operator presses the GO key or
                until the CONTINUE object is set.

                If the printer is not idle, the new value may not take effect
                until a job boundary is reached. If a get is done on this object before
                the job boundary is reached, the value last set will be returned."
::= { status-system 7 }


install-date OBJECT-TYPE
    SYNTAX      DisplayString
    MAX-ACCESS read-write
    STATUS      current
       DESCRIPTION "Identifies the date that the device was installed. The format
		of the string is 'YYYYMMDDHHmmZ'. Where:
		    YYYY is the year.
		    MM is the month (1-12).
		    DD is the day (1-31).
		    HH is the hour of the day (0-23).
		    mm are the minutes (0-59).
		    'Z' designates Greenwich Mean Time; if 'Z' not specified,
			value is local time.
		Device POS must specify the conditions for setting this
		object.
                Additional information:
                Identifies the date that the device was installed. The
                format of the string is 'YYYYMMDDHHmmZ'. Where:
                YYYY is the year.
                MM is the month (1-12).
                DD is the day (1-31).
                HH is the hour of the day (0-23).
                mm are the minutes (0-59).
                'Z' designates Greenwich Mean Time; if 'Z' not specified,
                value is local time.

                On Products without a real-time clock this
                object has the inital value of 'INVALID'.  While in
                the invalid state the object may written to.  Once the
                initial install date has been written a new intall date
                can not be written without resetting the object to 'INVALID'.

                The behavior on products with real-time clocks is different.
                The object is set to the initial real-time clock value, usually
                this is '199000300000'.  Manufacturing sets the real-time
                clock to the correct date and sets the INSTALL-DATE to 'INVALID'.
                Then when the customer turns on the printer for the first time
                the install date is reset."
::= { status-system 8 }

user-nvram-reset OBJECT-TYPE
    SYNTAX  INTEGER {
		   eTrue(1)
		   }
    MAX-ACCESS read-write
    STATUS  current
    DESCRIPTION
                "Setting to eTrue causes all user NVRAM settings to
                factory default settings.  May also perform POWER-ON-
                RESET functionality thus loosing print job data.  The
                POS will list which objects are effected by a user NVRAM
                reset.  Some items are NVRAM settings, but not user
                controllable, so this action may not cause all of NVRAM
                to be reset.  Some examples of NVRAM settings that may
                not be affected are page count, internally used pen
                information, line configuration information, etc.
                Additional information:
                Setting to eTrue returns the NVRAM items listed
           	below to their factory default values.  Performs
                the same function as the 'MENU RESET' function
                supported by the control panel except when printer
               	is in Offline state, setting this OID to eTrue will
               	not take the printer to the Online state.
                DEFAULT-COPIES
                DEFAULT-MEDIA-SIZE
                DEFAULT-ORIENTATION
                DEFAULT-LINES-PER-PAGE
                DEFAULT-MANUAL-FEED
                DEFAULT-RET
                DEFAULT-PRINT-QUALITY
                PCL-DEFAULT-FONT-SOURCE
                PCL-DEFAULT-FONT-NUMBER
                PCL-DEFAULT-FONT-HEIGHT
                PCL-DEFAULT-FONT-WIDTH
                PCL-DEFAULT-SYMBOL-SET
                DEFAULT-VERTICAL-BLACK-RESOLUTION
                DEFAULT-HORIZONTAL-BLACK-RESOLUTION
                DEFAULT-PDL
                CONTEXT-SENSITIVE-PDL-SELECTION
                ENERGY-STAR
                IO-TIMEOUT
                DEFAULT-PAGE-PROTECT
                POSTSCRIPT-JAM-RECOVERY (PostScript installed)
               	POSTSCRIPT-PRINT-ERRORS (PostScript installed)"
::= { status-system 12 }

total-ram-size OBJECT-TYPE
    SYNTAX  INTEGER
    MAX-ACCESS read-only
    STATUS  current
    DESCRIPTION
                "Identifies total amount of RAM, in bytes, available to
                the controller for general computing."
::= { status-system 21 }

status-printer OBJECT-TYPE
    SYNTAX  OCTET STRING
    MAX-ACCESS read-only
    STATUS  current
    DESCRIPTION
                "Indicates if any of the sub-systems in the device in a
                warning condition.  A warning condition exists if the
                sub-system is useable, but not at its highest state of
                functionality."
::= { status-system 22 }

status-controller OBJECT-TYPE
    SYNTAX  OCTET STRING
    MAX-ACCESS read-only
    STATUS  current
    DESCRIPTION
                "Indicates if the hardware controller sub-system in a
                warning condition."
::= { status-system 23 }


display-column-size OBJECT-TYPE
    SYNTAX  INTEGER
    MAX-ACCESS read-only
    STATUS  current
    DESCRIPTION
                "Indicates the number of characters displayable on each
                row of the printer's display."
::= { display-status 1 }


display-number-of-rows OBJECT-TYPE
    SYNTAX  INTEGER
    MAX-ACCESS read-only
    STATUS  current
    DESCRIPTION
                "Indicates the number of rows displayable on the
                printer's display."
::= { display-status 2 }


show-address OBJECT-TYPE
    SYNTAX      INTEGER {
                          eAuto(3),
                          eOff(1)
		   }
    MAX-ACCESS read-write
    STATUS      current
       DESCRIPTION "If this object is set to eAuto, and the device has an IP
		address, the IP address of the device will be shown with the
		READY message. If this object is set to eOff, the IP address
		will not be shown."
::= { display-status 3 }


status-msg-line1-part1 OBJECT-TYPE
    SYNTAX  DisplayString
    MAX-ACCESS read-only
    STATUS  current
    DESCRIPTION
                "First part of the first line of the printer's status
                message.
                Additional information:
                In the Offline state, device only returns
               	00 OFFLINE and not the actual content of control panel
                display."
::= { status-message1 1 }


background-status-msg-line1-part1 OBJECT-TYPE
    SYNTAX  DisplayString (SIZE(0..16))
    MAX-ACCESS read-write
    STATUS  current
    DESCRIPTION
                "The string displayed on the device's front panel in
                place of the printer's built-in background status
                string.  An example built-in background status string is
                '00 READY'.
                Additional information:
                The display size for the LaserJet 4050 Series printers is 2 X 16.
                The value of this object and the current value of
                BACKGROUND-STATUS-MSG-LINE2-PART1 are displayed
                together on the 2-line display, but they must
                be set independently.  If line 2 has been set, and the
                next message to be displayed only requires line 1,
                BACKGROUND-STATUS-MSG-LINE2-PART1 must be set to the
                null string to clear it.
                This object allows a message to be displayed when
                it is the highest priority message. Setting this
                object does not guarantee the message will be
                displayed; and reading it returns the value last
                written, not the currently displayed message (use
                prtConsoleDisplayBufferText to read the
                display).
                The priority assigned for displaying this message
                is one lower than the READY message.  In other words,
                the only message that can be replaced by these
                objects is the READY message.
                To clear the message, write a null string to both
                this object and BACKGROUND-STATUS-MSG-LINE2-PART1."
::= { background-message1 1 }


background-status-msg-line2-part1 OBJECT-TYPE
    SYNTAX  DisplayString (SIZE(0..16))
    MAX-ACCESS read-write
    STATUS  current
    DESCRIPTION
                "The string displayed on the device's front panel in
                place of the printer's built-in background status
                string.  An example built-in background status string is
                '00 READY'.
                Additional information:
                See BACKGROUND-STATUS-MSG-LINE1-PART1"
::= { background-message2 1 }

error-log-clear OBJECT-TYPE
    SYNTAX  INTEGER {
		   eClearErrorLog(1)
		   }
    MAX-ACCESS read-write
    STATUS  current
    DESCRIPTION
                "Setting this object clears all the entries in the error
                log sub-tree.
                Additional information:
                Setting this object removes all errors that have been
                stored in the printer's non-volatile memory."
::= { status-system 38 }


localization-languages-supported OBJECT-TYPE
    SYNTAX  DisplayString
    MAX-ACCESS read-only
    STATUS  current
    DESCRIPTION
                "The list of languages supported by the device. The
                languages are primarily, but not limited to, two
                character codes from ISO 639, each separated by a comma
                character.
                Additional information:
                This string will always be in the Roman-8 character
                set.  See prtLocalizationLanguage for details about each language value."
::= { status-system 52 }


localization-countries-supported OBJECT-TYPE
    SYNTAX  DisplayString
    MAX-ACCESS read-only
    STATUS  current
    DESCRIPTION
                "The list of countries supported by the device. The
                countries are primarily, but not limited to, two
                character codes from ISO 3166, each separated by a comma
                character.
                Additional information:
                This string will always be in the Roman-8 character
                set.  See prtLocalizationCountry for details about each country value."
::= { status-system 53 }


control-panel-button-press OBJECT-TYPE
    SYNTAX  INTEGER {
		   eGoButton(1),
		   eMenuPlusButton(2),
		   eMenuMinusButton(3),
		   eItemPlusButton(4),
		   eItemMinusButton(5),
		   eValuePlusButton(6),
		   eValueMinusButton(7),
		   eSelectButton(8),
		   eCancelJobButton(9)
		   }
    MAX-ACCESS read-write
    STATUS  current
    DESCRIPTION
                "Writing this object simulates pressing a button on the
                control panel."
::= { status-system 60 }


model-number OBJECT-TYPE
    SYNTAX  DisplayString
    MAX-ACCESS read-only
    STATUS  current
    DESCRIPTION
                "Identifies the device model number as listed in the HP
                corporate price list (e.g.  C2121A for DeskJet 500C).
                The string is as specific as possible.  Products should
                note in POS if the model number on the CPL changes but
                the device reports the previous model number.  If the
                model number changes based on the installed options, the
                POS should indicate if only the base model number is
                returned, or if the device senses the installed options
                and returns the correct model number.  If possible,
                encode the model number in a symbol set (like Roman-8)
                that matches the ASCII character set and limit the
                characters used to ASCII characters.
                Additional information:
                The value of this object does not change based on
                the installed options."
::= { id 1 }

model-name OBJECT-TYPE
        SYNTAX  DisplayString (SIZE(1..32))
        MAX-ACCESS read-only
        STATUS  current
        DESCRIPTION
        "Identifies the device model name (e.g. ''DeskJet 1200C''). The
        string is as specific as possible. Capitalization and spacing
        should match family naming conventions. Products should note in
        POS if the model name on the HP corporate price list changes
        but the device reports the previous device name. If the model
        name changes based on the installed options, the POS should
        indicate if only the base model name is returned, or if the
        device senses the installed options and returns the correct
        model name. If possible, encode the model name in a symbol set
        (like Roman-8) that matches the ASCII character set and limit
        the characters used to ASCII characters."
::= { id 2 }

serial-number OBJECT-TYPE
    SYNTAX  DisplayString (SIZE(0..10))
    MAX-ACCESS read-only
    STATUS  current
    DESCRIPTION
                "Identifies the serial number for the device.  If the
                SERIAL-NUMBER object is set by the user, then setting
                the object does not need to be protected.  If the
                SERIAL-NUMBER object is set at the factory, then the
                SERVICE-PASSWORD object must be set correctly before the
                SERIAL-NUMBER object is writable.  If this is a writable
                object, the POS should indicate the maximum supported
                string length.  If possible, encode the serial number in
                a symbol set (like Roman-8) that matches the ASCII
                character set and limit the characters used to ASCII
                characters.
                Additional information:
                This value IS AFFECTED BY NVRAM resets, it is set to the
                default value of XXXXXXXXXX, when a NVRAM init is done."
::= { id 3 }


fw-rom-datecode OBJECT-TYPE
    SYNTAX  DisplayString
    MAX-ACCESS read-only
    STATUS  current
    DESCRIPTION
                "Identifies the base system firmware date code.  The date
                code will be encoded in the yyyymmdd format.  There may
                be several versions of the base system firmware.  The
                date code associated with the version of the base system
                firmware that is being used is reported.  There may be
                other date code objects for other specific modules such
                as fonts, localization modules, etc.; these other
                datecode objects are device specific."
::= { id 5 }

fw-rom-revision OBJECT-TYPE
        SYNTAX  DisplayString
        MAX-ACCESS read-only
        STATUS  current
        DESCRIPTION
        "This identifies the system code firmware ROM revision code. The
        format for a revision is major_revision.minor_revision. There
        may be other ROM revision code objects for other specific ROMs
        such as font ROMs, localization ROMs, etc; these other ROM
        revision code objects are device specific."
::= { id 6 }

fax-local-phone-num OBJECT-TYPE
    SYNTAX      OCTET STRING
    MAX-ACCESS read-write
    STATUS      current
       DESCRIPTION "CCITT sender's station id (ex. 08-396-4122)."
::= { id 8 }


fax-station-name OBJECT-TYPE
    SYNTAX      DisplayString
    MAX-ACCESS read-write
    STATUS      current
       DESCRIPTION "name for the fax device (ex. HP R&D)."
::= { id 9 }


device-name OBJECT-TYPE
    SYNTAX  DisplayString (SIZE(0..32))
    MAX-ACCESS read-write
    STATUS  current
    DESCRIPTION
                "User defined device name.  The POS should indicate the
                maximum supported string length.  If the user entered
                string is too long, the device will store as much as
                possible and will return the <noError>.

                Additional information:
                The maximum supported string length is 32
                characters.  If the user entered string is too long,
                the device will store the first 32 characters and will
                return the <noError> status."
::= { id 10 }

device-location OBJECT-TYPE
    SYNTAX  DisplayString
    MAX-ACCESS read-write
    STATUS  current
    DESCRIPTION
                "User defined device location.  The POS should indicate
                the maximum supported string length.  If the user
                entered string is too long, the device will store as
                much as possible and will return the <noError>.

                Additional information:
                The maximum supported string length is 16
                characters.  If the user entered string is too long,
                the device will store the first 16 characters and will
                return the <noError> status."
::= { id 11 }


asset-number OBJECT-TYPE
    SYNTAX  DisplayString
    MAX-ACCESS read-write
    STATUS  current
    DESCRIPTION
                "User defined asset number.  The POS should indicate the
                maximum supported string length.  If the user entered
                string is too long, the device will store as much as
                possible and will return the <noError>.

                Additional information:
                The maximum supported string length is 8
                characters.  If the user entered string is too long,
                the device will store the first 8 characters and will
                return the <noError> status."
::= { id 12 }

system-contact OBJECT-TYPE
    SYNTAX  DisplayString
    MAX-ACCESS read-write
    STATUS  current
    DESCRIPTION
                "User defined string containing the name of the person or
                group that is responsible for the device.  The POS
                should indicate the maximum supported string length.  If
                the user entered string is too long, the device will
                store as much as possible and will return the
                <noError>.
                Additional information:
                User defined system contact.  The maximum
                supported string length is 16 characters.  If the user
                entered string is too long, the device will store as
                much as possible and will return the
                <noError> status."
::= { id 13 }

fax-line-interface-unit-id OBJECT-TYPE
    SYNTAX      INTEGER(0..8)
    MAX-ACCESS read-only
    STATUS      current
       DESCRIPTION "The fax device line interface unit (LIU) identifier. The LIU
		number identifies the telephone system electrical
		characteristics supported by this device.
                Additional information:
                In this LaserJet MFP this value is stored in 3 bits on the
                LIU."
::= { id 18 }


at1-model-number OBJECT-TYPE
    SYNTAX  DisplayString
    MAX-ACCESS read-only
    STATUS  current
    DESCRIPTION
                "Identifies the AT model number.  If the disk was
                manufactured by HP, then the model number is the one
                listed in the HP corporate price list.  If possible,
                encode the model number in a symbol set (like Roman-8)
                that matches the ASCII character set and limit the
                characters used to ASCII characters.
                Additional information:
                The model number is obtained from the disk
                using the IDE (Intelligent Drive Electronics)
               	Identify command.  This objects is only supported
               	if a disk is installed.  Returns
               	<noSuchName> status if attempting
               	to perform a Get on this OID with no disk installed.
               	Returns <noSuchName>
               	status if attempting to perform a Set, EnableTrap, or
               	DisableTrap on this OID with no disk installed."
::= { at1 1 }


at1-model-name OBJECT-TYPE
    SYNTAX  DisplayString
    MAX-ACCESS read-only
    STATUS  current
    DESCRIPTION
                "Returns product information identifying the AT storage
                device.  Example: C3014A
                Additional information:
                The product information is obtained from the
               	disk using the IDE (Intelligent Drive Electronics)
               	Identify command.  This objects is only supported
               	if a disk is installed.  Returns
               	<noSuchName> status if attempting
               	to perform a Get on this OID with no disk installed.
               	Returns <noSuchName>
                status if attempting to perform a Set, EnableTrap, or
               	DisableTrap on this OID with no disk installed."
::= { at1 2 }


at1-manufacturing-info OBJECT-TYPE
    SYNTAX  DisplayString
    MAX-ACCESS read-only
    STATUS  current
    DESCRIPTION
                "Returns information describing the manufacture of this
                particular AT.  May include serial number and firmware
                revision.
                Additional information:
                Returns the model number, serial number, and
              	firmware revision of the installed disk.  This
                information is obtained from the disk using the
                IDE (Intelligent Drive Electronics) Identify
                command.  Example:  HP C3014A JP932412W9 K2A4A059.
               	This objects is only supported if a disk is installed.
               	Returns <noSuchName> status if
               	attempting to perform a Get on this OID with no disk
                installed.
               	Returns <noSuchName>
               	status if attempting to perform a Set, EnableTrap, or
               	DisableTrap on this OID with no disk installed."
::= { at1 3 }


at1-type OBJECT-TYPE
    SYNTAX  INTEGER {
		   eEmpty(1),
		   eDiskDrive(8)
		   }
    MAX-ACCESS read-only
    STATUS  current
    DESCRIPTION
                "Returns an indication of the type of option installed in
                this particular AT interface.  See SIMM1-TYPE for an
                explanation of the enumerations.
                Additional information:
                eEmpty means the device did not detect any AT.
                eDiskDrive means the AT contains a disk drive."
::= { at1 4 }


at1-capacity OBJECT-TYPE
    SYNTAX  INTEGER
    MAX-ACCESS read-only
    STATUS  current
    DESCRIPTION
                "Returns an indication of the capacity of the installed
                option.  See SIMM1-CAPACITY for an explanation of the
                meaning of the value of this object.
                Additional information:
                This object contains the size, in bytes, of
               	the installed disk option.  This objects is only
               	supported if a disk is installed.
               	Returns <noSuchName> status if
               	attempting to perform a Get on this OID with no disk
               	installed.
               	Returns <noSuchName>
               	status if attempting to perform a Set, EnableTrap, or
               	DisableTrap on this OID with no disk installed."
::= { at1 5 }


simm1-type OBJECT-TYPE
    SYNTAX  INTEGER {
		   eEmpty(1),
		   eUnknown(2),
		   eUnSupported(3),
		   eReadOnlyMemory(4),
		   eVolatileRandomAccessMemory(5),
		   eFlashMemory(7),
		   eRamRom(9)
		   }
    MAX-ACCESS read-only
    STATUS  current
    DESCRIPTION
                "Returns an indication of the type of option installed in
                SIMM slot 1.
                  eEmpty means the device did not detect any option
                installed in the interface slot.
                  eUnknown means the device doesn't recognize the
                installed option.
                  eUnSupported means the device recognizes the installed
                option, but does not support the option.
                  eReadOnlyMemory means the installed option contains
                ROM Ics.
                  eVolatileRandomAccessMemory means the installed option
                contains RAM ICs that loose data when the power is
                turned off.
                  eNonVolatileRandomAccessMemory means that the
                installed option contains RAM ICs that do not loose data
                when the power is turned off.
                  eFlashMemory means that the installed option contains
                a type of non-volatile RAM that needs to be erased
                before it can be written.
                  eDiskDrive means the installed option contains a disk
                drive.  eRamRom means the installed option contains both
                volatile random access memory and read only memory.
                  eInputPHD means the installed option is an input paper
                handling device.
                  eOutputPHD means the installed option is an output
                paper handling device.
                  eIOCard means the installed option is an I/O card.
                Additional information:
                This object is used for describing DIMMs instead
                of SIMMs on LaserJet 4050 Series. eRamRom is used to denote LaserJet 4050 Series's combo simm."
::= { simm1 4 }


simm1-capacity OBJECT-TYPE
    SYNTAX  INTEGER
    MAX-ACCESS read-only
    STATUS  current
    DESCRIPTION
                "Returns an indication of the capacity of the SIMM
                installed in SIMM slot 1.  The capacity is dependent on
                the type of option, as indicated by the SIMM1-TYPE
                object.  This object has no meaning if the installed
                option type is eUnknown or eReadOnlyMemory.  This object
                contains the size, in bytes, if the installed option
                type is eVolatileRandomAccessMemory,
                eNonVolatileRandomAccessMemory, eFlashMemory, or
                eDiskDrive.  If the type of the installed option is
                eRamRom, this object contains the size, in bytes, of the
                random access memory.  If the type of the installed
                option is eInputPHD, the capacity indicates the number
                of input trays supported by the installed option.  If
                the type of the installed option is eOutputPHD, the
                capacity indicates the number of output bins supported
                by the installed option.  If the type of the installed
                option is eIOCard, the capacity indicates the number of
                logical I/O ports supported by the I/O card.
                Additional information:
                Returns an indication of the capacity of the
                installed option in bytes.  This object is not
                supported unless the SIMM1-TYPE type is
                eVolatileRandomAccessMemory, eRamRom, or eFlashMemory.
                For eRamRom only the size of the Ram portion of the SIMM
                is returned."
::= { simm1 5 }


simm2-type OBJECT-TYPE
    SYNTAX  INTEGER {
		   eEmpty(1),
		   eUnknown(2),
		   eUnSupported(3),
		   eReadOnlyMemory(4),
		   eVolatileRandomAccessMemory(5),
		   eFlashMemory(7),
		   eRamRom(9)
		   }
    MAX-ACCESS read-only
    STATUS  current
    DESCRIPTION
                "Returns an indication of the type of option installed in
                SIMM slot 2.  See SIMM1-TYPE for a description.
                Additional information:
                This object is used for describing DIMMs instead
                of SIMMs on LaserJet 4050 Series. eRamRom is used to denote LaserJet 4050 Series's combo simm."
::= { simm2 4 }


simm2-capacity OBJECT-TYPE
    SYNTAX  INTEGER
    MAX-ACCESS read-only
    STATUS  current
    DESCRIPTION
                "Returns an indication of the capacity of the SIMM
                installed in SIMM slot 2.  See SIMM1-CAPACITY for a
                description.
                Additional information:
                This object is used for describing DIMMs instead
                of SIMMs on LaserJet 4050 Series. Returns an indication of the capacity of the
                installed option in bytes.  This object is not
                supported unless the SIMM2-TYPE type is
                eVolatileRandomAccessMemory, eRamRom, or eFlashMemory.
                For eRamRom only the size of the Ram portion of the
                SIMM is returned."
::= { simm2 5 }


simm3-type OBJECT-TYPE
    SYNTAX  INTEGER {
		   eEmpty(1),
		   eUnknown(2),
		   eUnSupported(3),
		   eReadOnlyMemory(4),
		   eVolatileRandomAccessMemory(5),
		   eFlashMemory(7),
		   eRamRom(9)
		   }
    MAX-ACCESS read-only
    STATUS  current
    DESCRIPTION
                "Returns an indication of the type of option installed in
                SIMM slot 3.  See SIMM1-TYPE for a description."
::= { simm3 4 }


simm3-capacity OBJECT-TYPE
    SYNTAX  INTEGER
    MAX-ACCESS read-only
    STATUS  current
    DESCRIPTION
                "Returns an indication of the capacity of the SIMM
                installed in SIMM slot 3.  See SIMM1-CAPACITY for a
                description.
                Additional information:
                This object is used for describing DIMMs instead
                of SIMMs on LaserJet 4050 Series. Returns an indication of the capacity of the
                installed option in bytes.  This object is not
                supported unless the SIMM3-TYPE type is
                eVolatileRandomAccessMemory, eRamRom, or eFlashMemory.
                For eRamRom only the size of the Ram portion of the
                simm is returned."
::= { simm3 5 }

simm4-type OBJECT-TYPE
    SYNTAX  INTEGER {
		   eEmpty(1),
		   eUnknown(2),
		   eUnSupported(3),
		   eReadOnlyMemory(4),
		   eVolatileRandomAccessMemory(5)
		   }
    MAX-ACCESS read-only
    STATUS  current
    DESCRIPTION
                "Returns an indication of the type of option installed in
                SIMM slot 4.  See SIMM1-TYPE for a description."
::= { simm4 4 }


simm4-capacity OBJECT-TYPE
    SYNTAX  INTEGER
    MAX-ACCESS read-only
    STATUS  current
    DESCRIPTION
                "Returns an indication of the capacity of the SIMM
                installed in SIMM slot 4.  See SIMM1-CAPACITY for a
                description.
                Additional information:
                Returns an indication of the capacity of the
                installed option in bytes.  This object is not
                supported unless the SIMM4-TYPE type is
                eVolatileRandomAccessMemory."
::= { simm4 5 }

simm5-type OBJECT-TYPE
    SYNTAX  INTEGER {
		   eEmpty(1),
		   eUnknown(2),
		   eUnSupported(3),
		   eReadOnlyMemory(4),
		   eVolatileRandomAccessMemory(5)
		   }
    MAX-ACCESS read-only
    STATUS  current
    DESCRIPTION
                "Returns an indication of the type of option installed in
                SIMM slot 5.  See SIMM1-TYPE for a description."
::= { simm5 4 }


simm5-capacity OBJECT-TYPE
    SYNTAX  INTEGER
    MAX-ACCESS read-only
    STATUS  current
    DESCRIPTION
                "Returns an indication of the capacity of the SIMM
                installed in SIMM slot 5.  See SIMM1-CAPACITY for a
                description.
                Additional information:
                Returns an indication of the capacity of the
                installed option in bytes.  This object is not
                supported unless the SIMM5-TYPE type is
                eVolatileRandomAccessMemory."
::= { simm5 5 }


simm6-type OBJECT-TYPE
    SYNTAX  INTEGER {
		   eEmpty(1),
		   eUnknown(2),
		   eUnSupported(3),
		   eReadOnlyMemory(4),
		   eVolatileRandomAccessMemory(5)
		   }
    MAX-ACCESS read-only
    STATUS  current
    DESCRIPTION
                "Returns an indication of the type of option installed in
                SIMM slot 6.  See SIMM1-TYPE for a description."
::= { simm6 4 }


simm6-capacity OBJECT-TYPE
    SYNTAX  INTEGER
    MAX-ACCESS read-only
    STATUS  current
    DESCRIPTION
                "Returns an indication of the capacity of the SIMM
                installed in SIMM slot 6.  See SIMM1-CAPACITY for a
                description.
                Additional information:
                Returns an indication of the capacity of the
                installed option in bytes.  This object is not
                supported unless the SIMM6-TYPE type is
                eVolatileRandomAccessMemory."
::= { simm6 5 }


simm7-type OBJECT-TYPE
    SYNTAX  INTEGER {
		   eEmpty(1),
		   eUnknown(2),
		   eUnSupported(3),
		   eReadOnlyMemory(4),
		   eVolatileRandomAccessMemory(5)
		   }
    MAX-ACCESS read-only
    STATUS  current
    DESCRIPTION
                "Returns an indication of the type of option installed in
                SIMM slot 7.  See SIMM1-TYPE for a description."
::= { simm7 4 }


simm7-capacity OBJECT-TYPE
    SYNTAX  INTEGER
    MAX-ACCESS read-only
    STATUS  current
    DESCRIPTION
                "Returns an indication of the capacity of the SIMM
                installed in SIMM slot 7.  See SIMM1-CAPACITY for a
                description.
                Additional information:
                Returns an indication of the capacity of the
                installed option in bytes.  This object is not
                supported unless the SIMM7-TYPE type is
                eVolatileRandomAccessMemory."
::= { simm7 5 }


simm8-type OBJECT-TYPE
    SYNTAX  INTEGER {
		   eEmpty(1),
		   eUnknown(2),
		   eUnSupported(3),
		   eReadOnlyMemory(4),
		   eVolatileRandomAccessMemory(5)
		   }
    MAX-ACCESS read-only
    STATUS  current
    DESCRIPTION
                "Returns an indication of the type of option installed in
                SIMM slot 8.  See SIMM1-TYPE for a description."
::= { simm8 4 }


simm8-capacity OBJECT-TYPE
    SYNTAX  INTEGER
    MAX-ACCESS read-only
    STATUS  current
    DESCRIPTION
                "Returns an indication of the capacity of the SIMM
                installed in SIMM slot 8.  See SIMM1-CAPACITY for a
                description.
                Additional information:
                Returns an indication of the capacity of the
                installed option in bytes.  This object is not
                supported unless the SIMM8-TYPE type is
                eVolatileRandomAccessMemory."
::= { simm8 5 }


usb-product-id OBJECT-TYPE
    SYNTAX      INTEGER
    MAX-ACCESS read-only
    STATUS      current
       DESCRIPTION "Returns the Product ID of a connected USB device as defined in
		the Standard Device Descriptor of the Universal Serial Bus
		Specification Version 2.0. The value will be in the range
		0..65535."
::= { usb 5 }


self-test OBJECT-TYPE
    SYNTAX  INTEGER {
		   eNotInASelfTest(1),
		   eNonDestructiveSelfTest(4)
		   }
    MAX-ACCESS read-write
    STATUS  current
    DESCRIPTION
                "Writing this object allows a device self test to be
                started.  Reading this object provides an indication
                what self-test is currently executing, if any.  Actual
                self-test operation is device specific.  A self test may
                not be allowed at any arbitrary time.  If the device
                supports the requested self test, but can not start the
                execution of the self test when requested, the device
                will respond with <genErr>.  If
                a non-destructive self test is being started, the device
                will generate a response before the self test is
                completed.
                RECOMMENDATION:  If the device is ready (i.e. the NOT-
                READY-PRINTER object does not contain any items, except
                maybe being off-line) and is idle (i.e. the NOT-IDLE
                object does not contain any items), this request should
                always succeed.  This provides a mechanism for driver
                writers to always determine if the action will succeed
                or not.
                Additional information:
                The eNonDestructiveSelfTest performs limited
                testing on the printer and its attached paper handling
                devices. After the self-test is complete a
                configuration page is printed. The recommended
                way to cause a configuration page to be printed is to
                use the PRINT-INTERNAL-PAGE object.

                Setting this object to eNonDestructiveSelfTest results in a status of <noError>
                and a value of eNonDestructiveSelfTest being returned.
                If the printer is not idle (whether printing an external job or printing
                an internal page), this action will be delayed until the next job boundary.

                See the PRINT-INTERNAL-PAGE object for more details."
::= { test 1 }


print-internal-page OBJECT-TYPE
    SYNTAX  INTEGER {
		   eNotPrintingAnInternalPage(1),
		   ePrintingAnUnknownInternalPage(2),
		   eDeviceDemoPage1ConfigurationPage(3),
		   eDeviceDemoPage5ErrorLog(7),
		   eDeviceDemoPage6FileSystemDirectoryListing(8),
		   eDeviceDemoPage7MenuMap(9),
		   eDeviceUsagePage(10),
		   ePCLFontList1(350),
		   ePSFontList(450)
		   }
    MAX-ACCESS read-write
    STATUS  current
    DESCRIPTION
                "Writing this object to a value other than
                eNotPrintingAnInternalPage causes the device to attempt
                to print an internally generated page.  Reading this
                object provides an indication what internally generated
                page is currently being printed, if any.  The actual
                page is device specific.  Some devices may support
                continuously printing an internally generated page.
                Setting this object to eNotPrintingAnInternalPage
                terminates continuously printing internally generated
                pages.  An internally generated page may not be allowed
                to be printed at any arbitrary time; under what
                conditions it will succeed or fail is device specific.
                If the device supports the requested page, but can not
                start printing the page when requested, the device will
                respond with <genErr>.
                RECOMMENDATION:  If the device is ready (i.e. the NOT-
                READY-PRINTER object does not contain any items, except
                maybe being off-line) and is idle (i.e. the NOT-IDLE
                object does not contain any items), this request should
                always succeed.  This provides a mechanism for driver
                writers to always determine if the action will succeed
                or not.
                Additional information:
                Previous products used
                ePCLDemoPage1ConfigurationPage(300) for the
                Configuration or Self Test page.  This product uses
                eDeviceDemoPage1ConfigurationPage(3).

                LaserJet 4050 Series does not support continuously printing a demo page.

                When this object is set to a valid value, the status returned is <noError>
                and the value returned is ePrintingAnUnknownInternalPage.  If the printer
                is idle, the page will be printed immediately.  If the printer is
                currently printing another job, the internal page requested will not print
                until that job is finished.

                Setting this object to a valid value causes the
                desired page to be formatted and put in the printer's
                print queue.  While the page is being formatted a get on this object will
                return the value ePrintingAnUnknownInternalPage.  Once the page (or pages)
                is finished being formatted, this object returns a value of
                eNotPrintingAnInternalPage, even though the page may not have finished
                being printed.

                Setting this object multiple times will queue up the requests, but only
                a limited number will be queued.  Once the queue is full, additional
                requests will be ignored."
::= { test 2 }


clearable-warning OBJECT-TYPE
    SYNTAX  INTEGER {
		   eOn(2),
		   eJob(3)
		   }
    MAX-ACCESS read-write
    STATUS  current
    DESCRIPTION
                "Returns or controls how the device will track clearable
                warnings.  A clearable warning indicates a transient
                event in the device.  The device will continue after the
                transient event occurs.  If CLEARABLE-WARNING is eOff,
                the device does not track clearable warnings.  If
                CLEARABLE-WARNING is eOn, all clearable warnings will be
                tracked until cleared (acknowledged).  If CLEARABLE-
                WARNING is eJob, a clearable warning generated due to an
                event that occurs because of the print job being
                processed will be automatically cleared when the device
                has finished processing the job.  Example clearable
                warning events include the device altering resolution or
                page protection due to memory constraints.  The POS will
                document what transient events are treated as clearable
                warnings.
                Additional information:
                If set to eOn, the warning is displayed until the GO key
                is pressed or the CONTINUE object is set.

                If set to eJob, the warning is displayed until the end of the job in which
                it was generated."
::= { settings-job 1 }


cancel-job OBJECT-TYPE
    SYNTAX  INTEGER(0..32767)
    MAX-ACCESS read-write
    STATUS  current
    DESCRIPTION
                "Cancels the print job whose ID matches the value written
                to the CANCEL-JOB object.  The host first learns the job
                ID using the CURRENT-JOB-PARSING-ID command.  If the
                printer has completely processed the job, the printer
                responds with <badValue>.  If the
                value of the CURRENT-JOB-PARSING-ID is smaller than the
                value written to the CANCEL-JOB object, then the printer
                responds with <badValue>.  When
                read, returns the value of the last job ID what was
                canceled, or -1 to indicate no job has been canceled.
                Additional information:
                If the value written matches the ID of a job that is
                currently being canceled (for any reason),
                the printer responds with <noError>.
                LaserJet 4050 Series uses job ID's in the range of 0..32767.
                Because the ID number can wrap to zero,
                CURRENT-JOB-PARSING-ID may be smaller than the value
                written to this object; when this occurs, no error
                will result as long as the ID is for a currently
                processing job.  This object is write only, so the
                comment in the general description stating the
                job ID or -1 will be returned on a read does not
                apply."
::= { settings-job 2 }


faxjob-action OBJECT-TYPE
    SYNTAX  INTEGER {
		   ePrintFaxToPrinter(1),
		   eDeleteFaxFromMemory(3)
		   }
    MAX-ACCESS read-write
    STATUS  current
    DESCRIPTION
                "Permits host to specify an action to be applied with a
                particular fax."
::= { settings-fax-job 1 }


faxjob-action-id OBJECT-TYPE
    SYNTAX  INTEGER
    MAX-ACCESS read-write
    STATUS  current
    DESCRIPTION
                "Contains the fax job identification of the fax to be
                acted upon by the action specified by the object FAXJOB-
                ACTION."
::= { settings-fax-job 2 }


faxjob-tx-type OBJECT-TYPE
    SYNTAX  INTEGER {
		   eSrcHostOnly(2),
		   eSrcScannerOnly(5),
		   eSrcHostToMemoryOnly(9)
		   }
    MAX-ACCESS read-write
    STATUS  current
    DESCRIPTION
                "Indicates sources of the fax image for transmission.
                Also specifies the temporal order of the data sources.
                  eSrcHostOnly - The fax document images will be wholly
                downloaded from the host.
                  eSrcScannerOnly - The fax document images originate
                wholly from the device scanner/ADF subsystem.
                  eSrcHostThenScanner - The fax document is composed of
                images downloaded from the host and pages from the
                scanner/ADF subsystem.  The host downloaded pages will
                be faxed first, followed by the pages in the
                scanner/ADF.
                  eSrcScannerThenHost - The fax document is composed of
                pages in the scanner/ADF and the images downloaded from
                the host.  The document in the ADF is faxed first,
                followed by the pages downloaded from the host.
                wSrcHostThenMemory - The fax document is composed of
                pages downloaded from the host and images already stored
                within the device.  The fax transmission will contain
                the host downloaded pages followed by the images in the
                device memory.
                  eSrcHostToMemoryOnly - Permits fax images to be
                downloaded into device memory for later use with
                eSrcHostThenMemory.
                Additional information:
                GECKO NOTE:  eSrcHostToMemoryOnly is included for
                development and testing only.  eSrcHostToMemoryOnly will
                not be an allowed value for this object in the released
                product."
::= { settings-fax-job 3 }


faxjob-print-duplex-mode-select OBJECT-TYPE
    SYNTAX      INTEGER {
                          eDuplexerDisabled(1),
                          eDuplexerEnabled(2)
		   }
    MAX-ACCESS read-write
    STATUS      current
       DESCRIPTION "Allows the host to enable or disable duplex printing on a
		device for the next fax job.
                Additional information:
                Allows the host to enable or disable duplex printing on a
                device for the next fax job."
::= { settings-fax-job 5 }


faxjob-download-id OBJECT-TYPE
    SYNTAX  INTEGER
    MAX-ACCESS read-only
    STATUS  current
    DESCRIPTION
                "Contains the device assigned job identification for the
                current fax downloading job.  The job ID is
                monotonically increasing number.  The job ID may be
                reset to zero or may roll over to zero after reaching
                some maximum.  The maximum value before the rollover
                should be stated in the POS.
                Additional information:
                The maximum value before this object rolls over
                to 0 is 2,147,483,648.  Behavior of this object once
                the value rolls over to 0 is not specified."
::= { status-fax-job 1 }


faxjob-rx-id OBJECT-TYPE
    SYNTAX  INTEGER
    MAX-ACCESS read-only
    STATUS  current
    DESCRIPTION
                "Contains the device assigned job identification for the
                currently fax reception job.  The job ID is
                monotonically increasing number.  The job ID may be
                reset to zero or may roll over to zero after reaching
                some maximum.  The maximum value before the rollover
                should be stated in the POS.
                Additional information:
                The maximum value before this object rolls over
                to 0 is 2,147,483,648.  Behavior of this object once
                the value rolls over to 0 is not specified."
::= { status-fax-job 2 }


faxjob-tx-id OBJECT-TYPE
    SYNTAX  INTEGER
    MAX-ACCESS read-only
    STATUS  current
    DESCRIPTION
                "Contains the device assigned job identification for the
                current fax transmission job.  The job ID is
                monotonically increasing number.  The job ID may be
                reset to zero or may roll over to zero after reaching
                some maximum.  The maximum value before the rollover
                should be stated in the POS.
                Additional information:
                The maximum value before this object rolls over
                to 0 is 2,147,483,648.  Behavior of this object once
                the value rolls over to 0 is not specified."
::= { status-fax-job 3 }


faxjob-upload-id OBJECT-TYPE
    SYNTAX  INTEGER
    MAX-ACCESS read-only
    STATUS  current
    DESCRIPTION
                "Contains the device assigned job identification for the
                current fax upload job.  The job ID is monotonically
                increasing number.  The job ID may be reset to zero or
                may roll over to zero after reaching some maximum.  The
                maximum value before the rollover should be stated in
                the POS.
                Additional information:
                The maximum value before this object rolls over
                to 0 is 2,147,483,648.  Behavior of this object once
                the value rolls over to 0 is not specified."
::= { status-fax-job 4 }


faxjob-rx-status-1 OBJECT-TYPE
    SYNTAX  INTEGER {
		   eFaxRxIdle(1),
		   eFaxRxRinging(2),
		   eFaxRxAnswering(3),
		   eFaxRxReceiving(4)
		   }
    MAX-ACCESS read-only
    STATUS  current
    DESCRIPTION
                "Status of receiving fax session 1."
::= { faxjob-rx-status 1 }


faxjob-tx-status-1 OBJECT-TYPE
    SYNTAX  INTEGER {
		   eFaxTxIdle(1),
		   eFaxTxDialing(2),
		   eFaxTxConnecting(3),
		   eFaxTxTransmitting(4)
		   }
    MAX-ACCESS read-only
    STATUS  current
    DESCRIPTION
                "Status of sending fax session 1."
::= { faxjob-tx-status 1 }


faxjob-tx-error-1 OBJECT-TYPE
    SYNTAX  INTEGER
    MAX-ACCESS read-only
    STATUS  current
    DESCRIPTION
                "Error status of the fax reception session 1.
                Additional information:
                Error status of the fax transmission session 1."
::= { faxjob-tx-error 1 }


faxjob-tx-current-page-1 OBJECT-TYPE
    SYNTAX  INTEGER
    MAX-ACCESS read-only
    STATUS  current
    DESCRIPTION
                "The page number of the fax page currently being
                transmitted via send fax session 1.  Starts with page
                number 1."
::= { faxjob-tx-current-page 1 }


faxjob-rx-current-page-1 OBJECT-TYPE
    SYNTAX  INTEGER
    MAX-ACCESS read-only
    STATUS  current
    DESCRIPTION
                "The page number of the fax page currently being received
                via fax reception session 1.  Starts with page number
                1."
::= { faxjob-rx-current-page 1 }


faxjob-rx-duration-1 OBJECT-TYPE
    SYNTAX  INTEGER
    MAX-ACCESS read-only
    STATUS  current
    DESCRIPTION
                "Represent the number of seconds of phone-connect time
                for a fax reception session 1."
::= { faxjob-rx-duration 1 }


faxjob-tx-duration-1 OBJECT-TYPE
    SYNTAX  INTEGER
    MAX-ACCESS read-only
    STATUS  current
    DESCRIPTION
                "Represent the number of seconds of phone-connect time
                for send fax session 1."
::= { faxjob-tx-duration 1 }


fax-log-action OBJECT-TYPE
    SYNTAX  INTEGER {
		   eIdle(1),
		   eClear(2),
		   ePrintLatest(3),
		   ePrintAll(4)
		   }
    MAX-ACCESS read-write
    STATUS  current
    DESCRIPTION
                "Provides applications with the ability to clear or print
                the fax transaction log.
                  eIdle        - no action is occurring on the fax log.
                  eClear       - clear the fax log.
                  ePrintLatest - print the latest entry in the fax log.
                  ePrintAll    - print all the entries in the fax log.
                When this object is set to a non-eIdle value by an
                application, the given action starts.  When the action
                is complete, this object is changed back to eIdle by the
                device.  A host's request to write this object will be
                rejected when the object is not eIdle.  When eIdle, the
                host may set the object to any value (including eIdle)."
::= { settings-faxlog 1 }


fax-log-reporting OBJECT-TYPE
    SYNTAX  INTEGER {
		   eNever(1),
		   eErrorOnly(2),
		   eSendOnly(3)
		   }
    MAX-ACCESS read-write
    STATUS  current
    DESCRIPTION
                "Specifies when fax transaction logs are to be printed."
::= { settings-faxlog 2 }


fax-dial-mode OBJECT-TYPE
    SYNTAX  INTEGER {
		   eToneDial(1),
		   ePulseDial(2)
		   }
    MAX-ACCESS read-write
    STATUS  current
    DESCRIPTION
                "Device should use DTMF dialing if eToneDial, pulse dial
                if ePulseDial."
::= { dial-all-lines 1 }


device-redial OBJECT-TYPE
    SYNTAX  OCTET STRING
    MAX-ACCESS read-write
    STATUS  current
    DESCRIPTION
                "Device to permit redial upon detecting certain error
                conditions."
::= { dial-all-lines 2 }


fax-answer-mode OBJECT-TYPE
    SYNTAX  INTEGER {
		   eManualAnswer(1),
		   eFaxAnswer(2)
		   }
    MAX-ACCESS read-write
    STATUS  current
    DESCRIPTION
                "Sets the answering-priority when using a shared voice
                line.
                  eManualAnswer - Device will not automatically answer
                the phone.  User must answer and push START button.
                  eFaxAnswer - Device should assume call is fax, send
                CED immediately upon answering.
                  eTadAnswer - (Telephone Answering Device Mode) Device
                allows downstream TAD to answer but device will
                eavesdrop for fax CNG signal.  If a CNG detected, cut
                off the downstream device, send CED.  Do nothing if CNG
                not detected."
::= { answer-all-lines 1 }


fax-num-rings-pickup OBJECT-TYPE
    SYNTAX  INTEGER(1..6)
    MAX-ACCESS read-write
    STATUS  current
    DESCRIPTION
                "Number of rings before the fax device answers the phone
                if FAX-ANSWER-MODE is not set to MANUAL-MODE."
::= { answer-all-lines 2 }


device-ring-type-pickup OBJECT-TYPE
    SYNTAX  OCTET STRING
    MAX-ACCESS read-write
    STATUS  current
    DESCRIPTION
                "Device to answer the incoming call based on detecting
                the the specified type of telephone ring."
::= { answer-all-lines 3 }


fax-receive-stamping-enable OBJECT-TYPE
    SYNTAX  INTEGER {
		   eDisabled(1),
		   eEnabled(2)
		   }
    MAX-ACCESS read-write
    STATUS  current
    DESCRIPTION
                "Controls whether or not incoming pages of a fax will be
                stamped upon receipt.  Content of the stamp is device-
                specific but may include such information as date,
                time, fax station name, and page number.  When this
                object is set to eEnabled each page of an incoming fax
                is stamped by the device.  When this object is set to
                eDisabled incoming fax pages are not stamped.
                Additional information:
                When this object is set to eEnabled each page of an
                incoming fax is stamped with the date, time, fax station
                name, and page number.  When this object is set to
                eDisabled incoming fax pages are not stamped.
                //
                The received fax page will be scaled down 0.03% to
                accomodate the header. No header will be printed on
                page 2 of paginated output."
::= { settings-fax-receive 1 }


not-ready-fax-receive OBJECT-TYPE
    SYNTAX  OCTET STRING
    MAX-ACCESS read-only
    STATUS  current
    DESCRIPTION
                "Indicates if the receiving fax sub-system in the device
                is not ready.  If there are no items in the collection
                (i.e. no bits are set), then the receiving fax sub-
                system is ready.  If there is an item present, then the
                item indicates what is causing the receiving fax sub-
                system to be not ready."
::= { status-fax-receive 1 }


fax-rxscale OBJECT-TYPE
    SYNTAX  INTEGER
    MAX-ACCESS read-write
    STATUS  current
    DESCRIPTION
                "Received faxes are to be printed at a reduced scale
                percentage.  Value of 0 indicates auto-scaled printing
                based on the length of the received fax image and the
                length of the paper."
::= { settings-fax-proc-sub 1 }


fax-noise-volume OBJECT-TYPE
    SYNTAX  INTEGER(0..200)
    MAX-ACCESS read-write
    STATUS  current
    DESCRIPTION
                "Range is 0..100, where 0 = quietest possible, and 100 =
                loudest possible.  A device shall divide this value into
                ranges corresponding to the possible volumes.
                Additional information:
                For HP Laserjet 3200 the range is 0..200, where 0=off (silent),
                96=soft, 160=medium, and 200=loud.

                For HP Laserjet 3200 this object refers to the line monitor
                noise volume. The decimal values above correspond
                		to the hex values the object gets set to."
::= { settings-fax-proc-sub 3 }


fax-download OBJECT-TYPE
    SYNTAX  INTEGER {
		   eFaxDownloadIdle(1),
		   eFaxDownloadStart(2),
		   eFaxDownloadActive(3),
		   eFaxDownloadAborted(4),
		   eFaxDownloadDone(5)
		   }
    MAX-ACCESS read-write
    STATUS  current
    DESCRIPTION
                "Note:  Changed enumeration values in a non-backwards
                manner in version 4.7.  Handshake mechanism between host
                and device to initiate and coordinate the download of
                fax image data to be transmitted by the device fax
                modem.  This object serves both as an indicator of fax
                download activity as well as a trigger for the host to
                alter fax download progress.  This object has been
                redefined to track only the download acpect of the fax
                transmission.
                  eFaxDownloadIdle - indicates no fax download activity
                is occurring.  Device powers up in this state but will
                otherwise never transition to this state of its own
                accord.  Host setting to eFaxDownloadIdle while object
                is in eFaxDownloadActive will cause download activity to
                be prematurely terminated.  Host setting to this state
                resets the handshake mechanism to permit a another fax
                download activity to be initiated.
                  eFaxDownloadStart - indicates the host requests to
                commence a download session for sending a fax.  This
                state is host settable only from eFaxDownloadIdle.
                Device will never transition to this state of its own
                accord.
                  eFaxDownloadActive - indicates a fax download is
                occurring.  This state is not host settable.  Device
                will transition to this state from eFaxDownloadStart as
                a positive response for host to commence download of fax
                data.  This state is not host settable.  The object
                FAXJOB-DOWNLOAD-ID now contains the job ID to be used to
                track the progress of this fax job.
                  eFaxDownloadAborted - indicates the fax download
                activity has been prematurely terminated by the device
                due to some error.  Object FAX-DOWNLOAD-ERROR contains
                the error reason for the premature session termination.
                This state is device settable from eFaxDownloadStart or
                eFaxDownloadActive.  This state is not host settable.
                If modem transmission of fax data has started for this
                download, the fax session will also be aborted.
                eFaxDownloadDone - indicates the fax download activity
                has reached a successful termination in that the device
                has accepted all the download data from the host.  This
                state is only settable by the device from
                eFaxDownloadActive.  This state is not host settable.
                This state does not indicate the progress of the modem
                transmission of the downloaded fax data.  Host should
                transition from this state to eFaxDownloadIdle in order
                to reset the handshake mechanism for subsequent
                download."
::= { settings-fax-proc-sub 6 }


fax-silent-detection OBJECT-TYPE
    SYNTAX  INTEGER {
		   eDisabled(1),
		   eEnabled(2)
		   }
    MAX-ACCESS read-write
    STATUS  current
    DESCRIPTION
                "When enabled, this object causes the FAX machine to
                assume that the caller is a FAX even though the line has
                remained silent for a time (i.e., no CNG detected).
                When disabled, a CNG is required of the caller."
::= { settings-fax-proc-sub 7 }


fax-ring-enable OBJECT-TYPE
    SYNTAX  INTEGER {
		   eDisabled(1),
		   eEnabled(2)
		   }
    MAX-ACCESS read-write
    STATUS  current
    DESCRIPTION
                "When the phone line rings, this object determines
                whether an audible ring shall be emitted."
::= { settings-fax-proc-sub 8 }


fax-country OBJECT-TYPE
    SYNTAX  INTEGER {
		   eChina(6),
		   eMexicoAndLatinAmerica(13),
		   eCanadaFrench(14),
		   eUnitedStatesAndCanadaEnglish(15),
		   eNewZealand(19),
		   eIsrael(21),
		   eAustralia(23),
		   eMalaysia(27),
		   eHongKong(29),
		   eSingapore(30),
		   eUnitedKingdom(31),
		   eAustria(34),
		   eNetherlands(35),
		   eSwitzerlandFrench(37),
		   eGermany(39),
		   eDenmark(40),
		   eSweden(41),
		   eNorway(43),
		   eIreland(44),
		   eBelgium(45),
		   eFinland(46),
		   eFrance(47),
		   eItaly(51),
		   eSpain(55),
		   ePoland(56),
		   eHungary(62),
		   eUkraine(63),
		   eRussia(64)
		   }
    MAX-ACCESS read-write
    STATUS  current
    DESCRIPTION
                "Note:  Non-backwards compatible change make in version
                4.7.  Returns which country the telephone-electronics
                (LIU) is configured for.

                If this object is implemented with an access of read-write
                the device POS will specify what occurs when this object
                is written.
                Additional information:
                GECKO NOTE:  Is enumeration 37 (eSwitzerlandFrench)
                the correct setting for Switzerland?  The mib also
                provides the following options:
                eSwitzerland(36)
                eSwitzerlandGerman(36)
                eSwitzerlandItalian(38)"
::= { settings-fax-proc-sub 9 }


fax-tx-phone-number OBJECT-TYPE
    SYNTAX  DisplayString
    MAX-ACCESS read-write
    STATUS  current
    DESCRIPTION
                "Phone number about to be dialed."
::= { settings-fax-proc-sub 10 }


fax-redial-time OBJECT-TYPE
    SYNTAX  INTEGER
    MAX-ACCESS read-only
    STATUS  current
    DESCRIPTION
                "Number of seconds one must wait between the current
                redial (set by FAX-WHICH-REDIAL) and any prior dialing."
::= { settings-fax-proc-sub 14 }


fax-pstn-access-code OBJECT-TYPE
    SYNTAX  DisplayString
    MAX-ACCESS read-write
    STATUS  current
    DESCRIPTION
                "The code used within a PBX to get access to an outside
                PSTN line.  Typically this is ''9''."
::= { settings-fax-proc-sub 18 }


fax-rx-disposition OBJECT-TYPE
    SYNTAX  INTEGER {
		   ePrintOnly(1),
		   eUploadOnly(2),
		   eUploadElsePrint(4),
		   eForwardElsePrint(6)
		   }
    MAX-ACCESS read-write
    STATUS  current
    DESCRIPTION
                "Indicates what is to be done with the incoming fax
                call.
                  ePrintOnly - New fax arrivals only go to the printer.
                If printer becomes unavailable, the fax is stored in
                device memory until the printer becomes available.  If
                device memory becomes full, no subsequent calls will be
                answered.  If power is cycled on the device, the user
                must be informed of any lost faxes.  If faxes are saved
                in non-volatile memory, then they will be printed upon
                successful power-up.
                  eUploadOnly - New fax can only be uploaded to the
                host.  If host becomes unavailable, the fax is stored in
                device memory until host becomes available again to
                upload.  If device memory becomes full, no subsequent
                calls will be answered.  If power is cycled on the
                device, the user must be informed of any lost faxes.  If
                faxes are saved in non-volatile device memory, the host
                must be informed of a need to upload saved faxes upon
                successful power up.
                  eUploadAndPrint - Received faxes are to be printed and
                also uploaded to the host.  The fax is stored in device
                memory until it has been printed and uploaded.  If
                device memory becomes full, no subsequent calls will be
                answered.  If power is cycled on the device, the user
                must be informed of any lost faxes.  If faxes were saved
                into non-volatile memory, then faxes must be printed and
                uploaded before erasure from device memory.
                  eUploadElsePrint - Received faxes are to be uploaded
                if host is available, otherwise the fax is printed.
                During an upload, if the host becomes unavailable, the
                remainder of the fax is printed.  Once the host is
                detected to be unavailable, the object will transition
                to ePrintOnly.  Refer to fax reception behavior for
                ePrintOnly.
                  ePrintElseUpload - Received faxes are to be printed.
                If printer is unavailable, the fax will be uploaded.  If
                printer becomes unavailable while the fax is being
                received, the remainder unprinted pages of the fax will
                be uploaded.  If host then becomes unavailable, this
                object will transition to ePrintOnly.  Remainder pages
                of the fax being uploaded will be stored in device
                memory, to be printed when printer becomes available.
                If device memory becomes full, no subsequent calls will
                be answered.  If power is cycled on the device, the user
                must be informed of any lost faxes.
                  eForwardElsePrint - Received faxes are to be forwarded
                to another fax station.  If remote number does not
                answer, fax is printed.  If remote number is busy on
                multiple redial attempts, the fax is printed.  If device
                memory becomes full before fax reception is complete,
                the fax is printed.  If printer becomes unavailable, the
                fax is stored in device memory and then printed when
                printer becomes available again.  "
::= { settings-fax-proc-sub 19 }


fax-error-correction-mode OBJECT-TYPE
    SYNTAX  INTEGER {
		   eDisabled(1),
		   eEnabled(2)
		   }
    MAX-ACCESS read-write
    STATUS  current
    DESCRIPTION
                "Indicates whether the device is configured to send
               and receive faxes in error correction mode (ECM).
               This object controls both receiving and transmitting
               in ECM. A value of eDisabled means ECM is off and the
               device will not advertise the ability to do ECM during
               negotiation with other fax machines. A value of eEnabled
               means ECM is on and the device will advertise its ability
               to do ECM.

               Changing this setting may or may not take affect on the
               immediate page or ensuing pages of the document
               currently being sent."
::= { settings-fax-proc-sub 21 }


fax-report-transmission OBJECT-TYPE
    SYNTAX  INTEGER {
		   eNone(1),
		   ePrintReport(2),
		   ePrintReportOnSend(3),
		   ePrintReportOnError(4),
		   ePrintReportOnSendError(5),
		   ePrintReportOnReceiveError(6)
		   }
    MAX-ACCESS read-write
    STATUS  current
    DESCRIPTION
                "Provides a host application with the ability to
               print a fax transmission report.  The supported
               enumerations are:
               eNone - no transmission report printed
               ePrintReport - transmission report always printed
               ePrintReportOnSend - transmission report printed on
               send only
               ePrintReportOnError - transmission report printed on
               error only
               ePrintReportOnSendError - transmission report printed
               on send error only
               ePrintReportOnReceiveError - transmission report
               printed on receive error only."
::= { settings-fax-proc-sub 22 }


fax-report-activity-log OBJECT-TYPE
    SYNTAX  INTEGER {
		   eNever(1),
		   eThreshold(2)
		   }
    MAX-ACCESS read-write
    STATUS  current
    DESCRIPTION
                "Specifies when a report of fax transactions is to be
               printed.

               eNever - to never print a transaction report.
               eThreshold - to automatically print a transaction
               report every N transactions.

               The POS for each product shall specify the value of N.

               FAX-REPORT-TRANSMISSION also prints a transaction report,
               but for only a given fax, not a log of fax activities.
               May not be settable if the fax machine is not idle.

               The log is cleared after each printing caused by this
               object."
::= { settings-fax-proc-sub 23 }


fax-dial-tone-detection OBJECT-TYPE
    SYNTAX  INTEGER {
		   eDisabled(1),
		   eEnabled(2)
		   }
    MAX-ACCESS read-write
    STATUS  current
    DESCRIPTION
                "Determines whether the fax machine waits for a dial tone
               before dialing a fax number. eEnabled - causes the fax
               machine to wait until a dial tone is recognized before
               attempting to dial a fax number. eDisabled - causes the
               fax machine to dial without waiting to recognize a dial
               tone."
::= { settings-fax-proc-sub 24 }


fax-alarm-volume OBJECT-TYPE
    SYNTAX  INTEGER(0..3)
    MAX-ACCESS read-write
    STATUS  current
    DESCRIPTION
                "Range is 0..100, where 0 = quietest possible, and
               100 = loudest possible. A device shall divide this value
               into ranges corresponding to the possible volumes and
               document these settings and their meanings in the product
               POS.
                Additional information:
                For HP Laserjet 3200 the range is 0..3, where 0=off (silent),
                1=soft, 2=medium, and 3=loud."
::= { settings-fax-proc-sub 25 }


fax-beep-volume OBJECT-TYPE
    SYNTAX  INTEGER(0..3)
    MAX-ACCESS read-write
    STATUS  current
    DESCRIPTION
                "Range is 0..100, where 0 = quietest possible, and
               100 = loudest possible. A device shall divide this value
               into ranges corresponding to the possible volumes and
               document these settings and their meanings in the product
               POS.
                Additional information:
                For HP Laserjet 3200 the range is 0..3, where 0=off (silent),
                1=soft, 2=medium, and 3=loud."
::= { settings-fax-proc-sub 26 }


fax-ring-volume OBJECT-TYPE
    SYNTAX  INTEGER(0..3)
    MAX-ACCESS read-write
    STATUS  current
    DESCRIPTION
                "Range is 0..100, where 0 = quietest possible, and
               100 = loudest possible. A device shall divide this value
               into ranges corresponding to the possible volumes and
               document these settings and their meanings in the product
               POS.
                Additional information:
                For HP Laserjet 3200 the range is 0..3, where 0=off (silent),
                1=soft, 2=medium, and 3=loud."
::= { settings-fax-proc-sub 27 }


fax-master-host OBJECT-TYPE
    SYNTAX  DisplayString
    MAX-ACCESS read-write
    STATUS  current
    DESCRIPTION
                "Identifies the hostname of the master host to which
               the device is connected."
::= { settings-fax-proc-sub 28 }


fax-thumbnail-enable OBJECT-TYPE
    SYNTAX  INTEGER {
		   eDisabled(1),
		   eEnabled(2)
		   }
    MAX-ACCESS read-write
    STATUS  current
    DESCRIPTION
                "Controls whether or not a thumbnail reprint of the
                first page of a fax shall be included on the
                fax call report.  When set to eEnabled a thumbnail shall
                be included on the report.  When set to eDisabled there
                shall be not be a thumbnail on the fax call report.
                Additional information:
                Controls whether or not a thumbnail reprint of the
                first page of a fax shall be included on the
                fax call report.  When set to eEnabled a thumbnail shall
                be included on the report.  When set to eDisabled there
                shall be not be a thumbnail on the fax call report."
::= { settings-fax-proc-sub 29 }


fax-phone-pickup-enable OBJECT-TYPE
    SYNTAX  INTEGER {
		   eDisabled(1),
		   eEnabled(2)
		   }
    MAX-ACCESS read-write
    STATUS  current
    DESCRIPTION
                "This object is included to handle the situation where a
               fax machine and a telephone share the same phone line.

               If a call picked up at the phone turns out to be a fax
               call, the user may initiate a fax receive via the fax
               machine front panel (with, say, a button press).  When
               this object is set to eEnabled and a fax call is answered
               at the phone, the user has the option of initiating the
               fax receive in the usual way at the fax front panel or by
               entering a (product-specific) key sequence on the telephone
               keypad (e.g. '***').  The device POS must indicate what
               the key sequence is for a particular product.

               When this object is set to eDisabled and a fax call is
               answered at the phone, the user may only initiate the fax
               receive by taking the product-specific action (such as a
               button press) at the fax machine front panel.

               It is necessary to be able to turn this feature off (i.e.
               set it to eDisabled) because the key sequence of a
               particular fax device may interfere with other devices
               connected to the phone line (e.g. an answering machine).
                Additional information:
                On HP Laserjet 3200, the key sequence to initiate a fax from the
                phone keypad is '***'."
::= { settings-fax-proc-sub 30 }


fax-adf-scan-count OBJECT-TYPE
    SYNTAX      INTEGER
    MAX-ACCESS read-write
    STATUS      current
       DESCRIPTION "This object tracks the page count for the pages scanned for
		faxing from the ADF. In order to write this object
		SERVICE-PASSWORD must be set correctly.
                Additional information:
                This object tracks the page count for the pages scanned for faxing
                from the ADF. In order to write this object SERVICE-PASSWORD must be
                set correctly."
::= { settings-fax-proc-sub 31 }


fax-print-page-count OBJECT-TYPE
    SYNTAX      INTEGER
    MAX-ACCESS read-write
    STATUS      current
       DESCRIPTION "This object tracks the page count for the pages sent to the
		print engine for fax jobs. In order to write this object
		SERVICE-PASSWORD must be set correctly.
                Additional information:
                This object tracks the page count for the pages sent to the print
                engine for fax jobs. In order to write this object SERVICE-PASSWORD
                must be set correctly."
::= { settings-fax-proc-sub 32 }


fax-download-page-count OBJECT-TYPE
    SYNTAX      INTEGER
    MAX-ACCESS read-write
    STATUS      current
       DESCRIPTION "This object tracks the page count for the pages downloaded to
		the peripheral for fax jobs. In order to write this object
		SERVICE-PASSWORD must be set correctly.
                Additional information:
                This object tracks the page count for the pages downloaded to the
                peripheral for fax jobs. In order to write this object SERVICE-PASSWORD
                must be set correctly."
::= { settings-fax-proc-sub 33 }


fax-upload-page-count OBJECT-TYPE
    SYNTAX      INTEGER
    MAX-ACCESS read-write
    STATUS      current
       DESCRIPTION "This object tracks the page count for the pages uploaded from
		the peripheral for fax jobs. In order to write this object
		SERVICE-PASSWORD must be set correctly.
                Additional information:
                This object tracks the page count for the pages uploaded from the
                peripheral for fax jobs. In order to write this object SERVICE-PASSWORD
                must be set correctly."
::= { settings-fax-proc-sub 34 }


fax-flatbed-scan-count OBJECT-TYPE
    SYNTAX      INTEGER
    MAX-ACCESS read-write
    STATUS      current
       DESCRIPTION "This object tracks the page count for the pages scanned for
		faxing from the flatbed. In order to write this object the
		SERVICE-PASSWORD must be set.
                Additional information:
                This object tracks the page count for the pages scanned
                for faxing from the flatbed.  In order to write this
                object the SERVICE-PASSWORD must be set."
::= { settings-fax-proc-sub 36 }


default-fax-glass-size OBJECT-TYPE
    SYNTAX      INTEGER {
                          eUSLetter(2),
                          eUSLegal(3),
                          eISOandJISA4(26)
		   }
    MAX-ACCESS read-write
    STATUS      current
       DESCRIPTION "Indicates the default fax glass size.
                Additional information:
                Indicates the default fax glass size."
::= { settings-fax-proc-sub 37 }


fax-cold-reset-fax-glass-size OBJECT-TYPE
    SYNTAX      INTEGER {
                          eUSLetter(2),
                          eUSLegal(3),
                          eISOandJISA4(26)
		   }
    MAX-ACCESS read-write
    STATUS      current
       DESCRIPTION "Returns or sets the fax glass size that is used as the
		DEFAULT-FAX-GLASS-SIZE when a cold reset occurs.
                Additional information:
                Returns or sets the fax glass size that is used as the
                DEFAULT-FAX-GLASS-SIZE when a cold reset occurs."
::= { settings-fax-proc-sub 38 }


fax-upload OBJECT-TYPE
    SYNTAX  INTEGER {
		   eFaxUploadIdle(1),
		   eFaxUploadStart(2),
		   eFaxUploadActive(3),
		   eFaxUploadAborted(4),
		   eFaxUploadDone(5),
		   eFaxUploadNeeded(6)
		   }
    MAX-ACCESS read-write
    STATUS  current
    DESCRIPTION
                "Note: The enumeration values for this object where
                changed in a non-backwards compatible manner in version
                4.7.  Handshake mechanism between host and device to
                notify and coordinate the transfer of fax image data
                received by the device fax modem.  This object serves
                both as an indicator of fax upload activity as well as a
                trigger for the host to alter fax upload progress.
                Handshake mechanism between host and device to initiate
                scan operation and coordinate the transfer of scanned
                image data to the host.  This object serves both as an
                indicator of scan upload activity as well as a trigger
                for the host to alter scan upload progress.
                  eFaxUploadIdle - indicates no fax upload activity is
                is occurring.  Device powers up in this state but will
                otherwise never transition to this state of its own
                accord.  Host setting to eFaxUploadIdle while object is
                in eFaxUploadActive will cause download activity to be
                prematurely terminated.  Host setting to this state
                resets the handshake mechanism to permit another fax
                upload activity to be initiated.
                  eFaxUploadStart - indicates the host requests to
                commence an upload session for a received fax.  This
                state is host settable only from eFaxUploadIdle.  Device
                will never transition to this state of its own accord.
                  eFaxUploadActive - indicates a fax upload is
                occurring.  This state is not host settable.  Device
                will transition to this state from eFaxUploadStart as a
                positive response for host to commence upload of fax
                data.  The object FAXJOB-UPLOAD-ID now contains the job
                ID.
                  eFaxUploadAborted - indicates the fax upload activity
                has been prematurely terminated by the device due to
                some error.  Object FAX-UPLOAD-ERROR contains the error
                reason for the premature session termination.  This
                state is device settable from eFaxUploadStart,
                eFaxUploadActive or eFaxUploadNeeded.  This state is not
                host settable.
                  eFaxUploadDone - indicates the fax upload activity has
                reached a successful termination in that the device has
                transmitted all the upload data to the host.  This state
                is only settable by the device from eFaxUploadActive.
                This state is not host settable.  Host should transition
                from this state to eFaxUploadIdle in order to reset the
                handshake mechanism for subsequent upload session.
                  eFaxUploadNeeded - indicates device has received fax
                modem data available for host upload.  This state is not
                host settable.  This state is device settable from
                eFaxUploadIdle.  Host should respond by setting to
                eFaxUploadStart to initiate upload session.  Should host
                fail to respond by the time fax reception is complete or
                device has exhausted local memory storage, device shall
                transition object from eFaxUploadNeeded to
                eFaxUploadAborted.  The POS should state the recourse
                behavior associated with the received fax."
::= { status-fax-proc-sub 1 }


fax-min-rings-pickup OBJECT-TYPE
    SYNTAX  INTEGER(1..1)
    MAX-ACCESS read-only
    STATUS  current
    DESCRIPTION
                "Indicates the minimum legal rings before pickup.
                Additional information:
                GECKO NOTE:  Do all countries on the HP Laserjet 3200 list allow a
                minimum of 1?  If not, object syntax must be amended."
::= { status-fax-proc-sub 2 }


fax-max-rings-pickup OBJECT-TYPE
    SYNTAX  INTEGER(1..10)
    MAX-ACCESS read-only
    STATUS  current
    DESCRIPTION
                "Indicates the maximum legal rings before pickup."
::= { status-fax-proc-sub 3 }


fax-max-redials OBJECT-TYPE
    SYNTAX  INTEGER
    MAX-ACCESS read-only
    STATUS  current
    DESCRIPTION
                "Maximum number of allowed redials."
::= { status-fax-proc-sub 4 }


fax-additional-wait OBJECT-TYPE
    SYNTAX  INTEGER
    MAX-ACCESS read-only
    STATUS  current
    DESCRIPTION
                "Number of additional seconds to wait before beginning a
                FAX-DOWNLOAD."
::= { status-fax-proc-sub 5 }


fax-download-error OBJECT-TYPE
    SYNTAX  INTEGER
    MAX-ACCESS read-only
    STATUS  current
    DESCRIPTION
                "Error status of the fax download session.
                Additional information:
                GECKO NOTE:  What error conditions will be reported by
                this object?  Provide a map for the meaning of each
                valid value here."
::= { status-fax-proc-sub 6 }


fax-upload-error OBJECT-TYPE
    SYNTAX  INTEGER
    MAX-ACCESS read-only
    STATUS  current
    DESCRIPTION
                "Error status of the fax upload session.
                Additional information:
                GECKO NOTE:  What error conditions will be reported by
                this object?  Provide a map for the meaning of each
                valid value here.  Does this functionality stay?  If not,
                this object is superfluous."
::= { status-fax-proc-sub 7 }


fax-firmware-revision OBJECT-TYPE
    SYNTAX  DisplayString (SIZE(8))
    MAX-ACCESS read-only
    STATUS  current
    DESCRIPTION
                "This object identifies the fax firmware ROM revision
               code. The format is device specific and shall be
               specified in the device POS.
                Additional information:
                This object identifies the fax firmware ROM revision
                code.  For HP Laserjet 3200, the format for this object is a date
                in the form YYYYMMDD."
::= { status-fax-proc-sub 8 }


fax-forwarding-phone-num OBJECT-TYPE
    SYNTAX  DisplayString
    MAX-ACCESS read-write
    STATUS  current
    DESCRIPTION
                "Phone number digits of the remote fax station where
                arrived faxes are to be forwarded."
::= { fax-forwarding 3 }


fax-resolution OBJECT-TYPE
    SYNTAX  OCTET STRING (SIZE(1..64))
    MAX-ACCESS read-write
    STATUS  current
    DESCRIPTION
                "struct {
                  unsigned_32bit x_res; /* 1st four bytes; big endian */
                  unsigned_32bit y_res; /* 2nd four bytes; big endian */
                }
                Sets the send fax resolution.  The x and y resolutions
                in this object are in fixed-point with 16 bits of
                fraction, and 16 bits of integer, and are in dots per
                inch.  X is horizontal; Y is vertical.
                Examples of computing x_res and y_res:
                   300 dots/inch:round(300 * 65536) = 19660800
                   16 dots/mm:   round(16 * 25.4 * 65536) = 26633830.
                If the device does not support the given combination,
                then it'll select the nearest supported values in a
                device-dependent manner (documented in the POS).
                Additional information:
                HP Laserjet 3200 supports 4 fax resolutions.  As far as the
                end-user is concerned these resolutions are:  standard,
                fine, superfine, and photo.  Photo is not really a
                resolution--see more below.  Standard is the default.
                Resolutions map as follows (values are given in dots per
                inch (dpi) horizontal X vertical (x X y)):  standard(203
                X 98), fine(203 X 196), superfine(300 X 300), and
                photo(300 X 300).

                Supported resolutions in hex notation (dpi, x X y) are:
                standard(00cb0000 X 00620000), fine(00cb0000 X 00c4000),
                superfine(012C0000 X 012C0000), and photo(012C0000 X
                012C0000).

                The device ignores attempts to set invalid resolutions.

                Photo is not a resolution, but photo setting depends on
                whether half-toning is on or off.  In the case of HP Laserjet 3200
                photo setting doesn't actually change the bits going out
                the modem -- still one bit per pixel so photo and
                superfine are the same.

                NOTE:  The last 16 bits of the horizontal and vertical
                settings are ignored.  Only the first 16 bits of the
                horizontal and vertical resolution setting are used."
::= { settings-fax-send 1 }


fax-contrast OBJECT-TYPE
    SYNTAX  INTEGER(-127..127)
    MAX-ACCESS read-write
    STATUS  current
    DESCRIPTION
                "Behaves as SCL's 'Set Scanner Contrast Level' command
                which is used for setting the sending fax contrast
                level.  Range is 0..100.
                Additional information:
                Behaves as COPIER-CONTRAST and SCANNER-CONTRAST.
                Contrast values can range from -127 to +127, for a total
                of 255 contrast values.  Within that range, HP Laserjet 3200
                supports 11 values.  They are:  -125, -100, -75, -50,
                -25, 0, 25, 50, 75, 100, 125.  The default contrast level is 0
                (normal).  A positive value results in a larger
                difference, and a negative value results in a smaller
                difference.

                HP Laserjet 3200 snaps unsupported values toward zero as follows:
                <=-125 snaps to -125
                >-125 and <=-100 snaps to -100
                >-100 and <=-75 snaps to -75
                >-75 and <=-50 snaps to -50
                >-50 and <=-25 snaps to -25
                >-25 and <25 snaps to 0
                >=25 and <50 snaps to 25
                >=50 and <75 snaps to 50
                >=75 and <100 snaps to 75
                >=100 and <125 snaps to 100
                >=125 snaps to 125"
::= { settings-fax-send 2 }


fax-pixel-data-type OBJECT-TYPE
    SYNTAX  INTEGER {
		   eBiLevelThesholded(1),
		   eBiLevelHalfToned(2)
		   }
    MAX-ACCESS read-write
    STATUS  current
    DESCRIPTION
                "Sets the scanning method used when sending a fax.
                 eBiLevelThesholded - One bit per pixel, using
                                      simple thresholding of greyscale
                                      scan data.
                 eBiLevelHalfToned  - One bit per pixel, using some kind
                                      of half-toning technique (such as
                                      dithering or error-diffusion) to
                                      approximate greyscale scan data."
::= { settings-fax-send 3 }


not-ready-fax-send OBJECT-TYPE
    SYNTAX  OCTET STRING
    MAX-ACCESS read-only
    STATUS  current
    DESCRIPTION
                "Indicates if the sending fax sub-system in the device is
                not ready.  If there are no items in the collection
                (i.e. no bits are set), then the sending fax sub-system
                is ready.  If there is an item present, then the item
                indicates what is causing the sending fax sub-system to
                be not ready."
::= { status-fax-send 1 }


fax-allow-redials OBJECT-TYPE
    SYNTAX  INTEGER {
		   eFalse(1),
		   eTrue(2)
		   }
    MAX-ACCESS read-write
    STATUS  current
    DESCRIPTION
                "When eTrue, the FAX machine can redial a phone number if
                the prior call failed for some reason.  When eFalse,
                such redialing will not occur."
::= { transmit-fax 3 }

error1-time-stamp OBJECT-TYPE
    SYNTAX  INTEGER
    MAX-ACCESS read-only
    STATUS  current
    DESCRIPTION
                "Contains some sort of time stamp indicating when error 1
                occurred.  Example time stamps include the actual time
                the error occurred (in seconds since Jan. 1, 1970), and
                the total engine page count.  The device POS documents
                the meaning of the time stamp.
                Additional information:
                This item contains the engine
                page count when the error occurred.

                If there is currently no error entry for this object, a '0' will be returned.
                Note that '0' may also be returned when there is a valid error, but a current
                page count was unavailable.  If ERROR1-CODE object also returns '0', then
                an error has not yet been logged for this object.

                See ERROR1-CODE for an explanation of the order used for storing errors."
::= { error1 1 }


error1-code OBJECT-TYPE
    SYNTAX  INTEGER
    MAX-ACCESS read-only
    STATUS  current
    DESCRIPTION
                "Contains a device specific error code.  Each device POS
                should list what errors are logged to the error log and
                the meaning of each supported error code value.
                Additional information:
                Returns a device specific error code.
                If the error code returned is '0', then the printer has not yet logged an
                error for this object.
                When the maximum number of errors is reached (30 on LaserJet 4050 Series printers), and
                a new error occurs, the error in ERROR1-CODE will be replaced by the
                one in ERROR2-CODE, and so on until the last error object will be given
                the value of the new error.

                The error number is returned in the upper 16 bits.
                If it is 68, 69, 79, or 80, then the sub code is returned in the lower
                16 bits (eg. 68 001C, where the subcode is already a hexadecimal value).
                If the error number is any other number, then the 1st sub code (XX)
                will be in bits 15-8 and the 2nd sub code (YY) will be in bits 7-0 (eg.
                55.04.02) where XX=04 and YY=02).

                Example: If the error is 68 001A, then the value returned will be 4456474.
                To break it down: 4456474 = 0x0044001A
                The upper 16 bits: 0x0044 = 68
                The lower 16 bits: 0x001A = 001A
                Which is the error: 68 001A

                Example: If the error is 55.04.241, then the error code will be 3605745.
                To break it down: 3605745 = 0x003704F1
                The upper 16 bits: 0x0037 = 55
                The upper byte of the lower 16 bits: 0x04 = 04
                The lower byte of the lower 16 bits: 0xF1 = 241
                Which is the error: 55.04.241"
::= { error1 2 }


error2-time-stamp OBJECT-TYPE
    SYNTAX  INTEGER
    MAX-ACCESS read-only
    STATUS  current
    DESCRIPTION
                "Contains some sort of time stamp indicating when error 2
                occurred.  Example time stamps include the actual time
                the error occurred (in seconds since Jan. 1, 1970), and
                the total engine page count.  The device POS documents
                the meaning of the time stamp.
                Additional information:
                See ERROR1-TIME-STAMP."
::= { error2 1 }


error2-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error2 2 }


error3-time-stamp OBJECT-TYPE
    SYNTAX  INTEGER
    MAX-ACCESS read-only
    STATUS  current
    DESCRIPTION
                "Contains some sort of time stamp indicating when error 3
                occurred.  Example time stamps include the actual time
                the error occurred (in seconds since Jan. 1, 1970), and
                the total engine page count.  The device POS documents
                the meaning of the time stamp.
                Additional information:
                See ERROR1-TIME-STAMP."
::= { error3 1 }


error3-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error3 2 }


error4-time-stamp OBJECT-TYPE
    SYNTAX  INTEGER
    MAX-ACCESS read-only
    STATUS  current
    DESCRIPTION
                "Contains some sort of time stamp indicating when error 4
                occurred.  Example time stamps include the actual time
                the error occurred (in seconds since Jan. 1, 1970), and
                the total engine page count.  The device POS documents
                the meaning of the time stamp.
                Additional information:
                See ERROR1-TIME-STAMP."
::= { error4 1 }


error4-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error4 2 }


error5-time-stamp OBJECT-TYPE
    SYNTAX  INTEGER
    MAX-ACCESS read-only
    STATUS  current
    DESCRIPTION
                "Contains some sort of time stamp indicating when error 5
                occurred.  Example time stamps include the actual time
                the error occurred (in seconds since Jan. 1, 1970), and
                the total engine page count.  The device POS documents
                the meaning of the time stamp.
                Additional information:
                See ERROR1-TIME-STAMP."
::= { error5 1 }


error5-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error5 2 }


error6-time-stamp OBJECT-TYPE
    SYNTAX  INTEGER
    MAX-ACCESS read-only
    STATUS  current
    DESCRIPTION
                "Contains some sort of time stamp indicating when error 6
                occurred.  Example time stamps include the actual time
                the error occurred (in seconds since Jan. 1, 1970), and
                the total engine page count.  The device POS documents
                the meaning of the time stamp.
                Additional information:
                See ERROR1-TIME-STAMP."
::= { error6 1 }


error6-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error6 2 }


error7-time-stamp OBJECT-TYPE
    SYNTAX  INTEGER
    MAX-ACCESS read-only
    STATUS  current
    DESCRIPTION
                "Contains some sort of time stamp indicating when error 7
                occurred.  Example time stamps include the actual time
                the error occurred (in seconds since Jan. 1, 1970), and
                the total engine page count.  The device POS documents
                the meaning of the time stamp.
                Additional information:
                See ERROR1-TIME-STAMP."
::= { error7 1 }


error7-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error7 2 }


error8-time-stamp OBJECT-TYPE
    SYNTAX  INTEGER
    MAX-ACCESS read-only
    STATUS  current
    DESCRIPTION
                "Contains some sort of time stamp indicating when error 8
                occurred.  Example time stamps include the actual time
                the error occurred (in seconds since Jan. 1, 1970), and
                the total engine page count.  The device POS documents
                the meaning of the time stamp.
                Additional information:
                See ERROR1-TIME-STAMP."
::= { error8 1 }


error8-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error8 2 }


error9-time-stamp OBJECT-TYPE
    SYNTAX  INTEGER
    MAX-ACCESS read-only
    STATUS  current
    DESCRIPTION
                "Contains some sort of time stamp indicating when error 9
                occurred.  Example time stamps include the actual time
                the error occurred (in seconds since Jan. 1, 1970), and
                the total engine page count.  The device POS documents
                the meaning of the time stamp.
                Additional information:
                See ERROR1-TIME-STAMP."
::= { error9 1 }


error9-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error9 2 }


error10-time-stamp OBJECT-TYPE
    SYNTAX  INTEGER
    MAX-ACCESS read-only
    STATUS  current
    DESCRIPTION
                "Contains some sort of time stamp indicating when error
                10 occurred.  Example time stamps include the actual
                time the error occurred (in seconds since Jan. 1, 1970),
                and the total engine page count.  The device POS
                documents the meaning of the time stamp.
                Additional information:
                See ERROR1-TIME-STAMP."
::= { error10 1 }


error10-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error10 2 }


error11-time-stamp OBJECT-TYPE
    SYNTAX  INTEGER
    MAX-ACCESS read-only
    STATUS  current
    DESCRIPTION
                "Contains some sort of time stamp indicating when error
                11 occurred.  Example time stamps include the actual
                time the error occurred (in seconds since Jan. 1, 1970),
                and the total engine page count.  The device POS
                documents the meaning of the time stamp.
                Additional information:
                See ERROR1-TIME-STAMP."
::= { error11 1 }


error11-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error11 2 }


error12-time-stamp OBJECT-TYPE
    SYNTAX  INTEGER
    MAX-ACCESS read-only
    STATUS  current
    DESCRIPTION
                "Contains some sort of time stamp indicating when error
                12 occurred.  Example time stamps include the actual
                time the error occurred (in seconds since Jan. 1, 1970),
                and the total engine page count.  The device POS
                documents the meaning of the time stamp.
                Additional information:
                See ERROR1-TIME-STAMP."
::= { error12 1 }


error12-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error12 2 }


error13-time-stamp OBJECT-TYPE
    SYNTAX  INTEGER
    MAX-ACCESS read-only
    STATUS  current
    DESCRIPTION
                "Contains some sort of time stamp indicating when error
                13 occurred.  Example time stamps include the actual
                time the error occurred (in seconds since Jan. 1, 1970),
                and the total engine page count.  The device POS
                documents the meaning of the time stamp.
                Additional information:
                See ERROR1-TIME-STAMP."
::= { error13 1 }


error13-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error13 2 }


error14-time-stamp OBJECT-TYPE
    SYNTAX  INTEGER
    MAX-ACCESS read-only
    STATUS  current
    DESCRIPTION
                "Contains some sort of time stamp indicating when error
                14 occurred.  Example time stamps include the actual
                time the error occurred (in seconds since Jan. 1, 1970),
                and the total engine page count.  The device POS
                documents the meaning of the time stamp.
                Additional information:
                See ERROR1-TIME-STAMP."
::= { error14 1 }


error14-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error14 2 }


error15-time-stamp OBJECT-TYPE
    SYNTAX  INTEGER
    MAX-ACCESS read-only
    STATUS  current
    DESCRIPTION
                "Contains some sort of time stamp indicating when error
                15 occurred.  Example time stamps include the actual
                time the error occurred (in seconds since Jan. 1, 1970),
                and the total engine page count.  The device POS
                documents the meaning of the time stamp.
                Additional information:
                See ERROR1-TIME-STAMP."
::= { error15 1 }


error15-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error15 2 }


error16-time-stamp OBJECT-TYPE
    SYNTAX  INTEGER
    MAX-ACCESS read-only
    STATUS  current
    DESCRIPTION
                "Contains some sort of time stamp indicating when error
                16 occurred.  Example time stamps include the actual
                time the error occurred (in seconds since Jan. 1, 1970),
                and the total engine page count.  The device POS
                documents the meaning of the time stamp.
                Additional information:
                See ERROR1-TIME-STAMP."
::= { error16 1 }


error16-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error16 2 }


error17-time-stamp OBJECT-TYPE
    SYNTAX  INTEGER
    MAX-ACCESS read-only
    STATUS  current
    DESCRIPTION
                "Contains some sort of time stamp indicating when error
                17 occurred.  Example time stamps include the actual
                time the error occurred (in seconds since Jan. 1, 1970),
                and the total engine page count.  The device POS
                documents the meaning of the time stamp.
                Additional information:
                See ERROR1-TIME-STAMP."
::= { error17 1 }


error17-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error17 2 }


error18-time-stamp OBJECT-TYPE
    SYNTAX  INTEGER
    MAX-ACCESS read-only
    STATUS  current
    DESCRIPTION
                "Contains some sort of time stamp indicating when error
                18 occurred.  Example time stamps include the actual
                time the error occurred (in seconds since Jan. 1, 1970),
                and the total engine page count.  The device POS
                documents the meaning of the time stamp.
                Additional information:
                See ERROR1-TIME-STAMP."
::= { error18 1 }


error18-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error18 2 }


error19-time-stamp OBJECT-TYPE
    SYNTAX  INTEGER
    MAX-ACCESS read-only
    STATUS  current
    DESCRIPTION
                "Contains some sort of time stamp indicating when error
                19 occurred.  Example time stamps include the actual
                time the error occurred (in seconds since Jan. 1, 1970),
                and the total engine page count.  The device POS
                documents the meaning of the time stamp.
                Additional information:
                See ERROR1-TIME-STAMP."
::= { error19 1 }


error19-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error19 2 }


error20-time-stamp OBJECT-TYPE
    SYNTAX  INTEGER
    MAX-ACCESS read-only
    STATUS  current
    DESCRIPTION
                "Contains some sort of time stamp indicating when error
                20 occurred.  Example time stamps include the actual
                time the error occurred (in seconds since Jan. 1, 1970),
                and the total engine page count.  The device POS
                documents the meaning of the time stamp.
                Additional information:
                See ERROR1-TIME-STAMP."
::= { error20 1 }


error20-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error20 2 }


error21-time-stamp OBJECT-TYPE
    SYNTAX  INTEGER
    MAX-ACCESS read-only
    STATUS  current
    DESCRIPTION
                "Contains some sort of time stamp indicating when error
                21 occurred.  Example time stamps include the actual
                time the error occurred (in seconds since Jan. 1, 1970),
                and the total engine page count.  The device POS
                documents the meaning of the time stamp.
                Additional information:
                See ERROR1-TIME-STAMP."
::= { error21 1 }


error21-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error21 2 }


error22-time-stamp OBJECT-TYPE
    SYNTAX  INTEGER
    MAX-ACCESS read-only
    STATUS  current
    DESCRIPTION
                "Contains some sort of time stamp indicating when error
                22 occurred.  Example time stamps include the actual
                time the error occurred (in seconds since Jan. 1, 1970),
                and the total engine page count.  The device POS
                documents the meaning of the time stamp.
                Additional information:
                See ERROR1-TIME-STAMP."
::= { error22 1 }


error22-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error22 2 }


error23-time-stamp OBJECT-TYPE
    SYNTAX  INTEGER
    MAX-ACCESS read-only
    STATUS  current
    DESCRIPTION
                "Contains some sort of time stamp indicating when error
                23 occurred.  Example time stamps include the actual
                time the error occurred (in seconds since Jan. 1, 1970),
                and the total engine page count.  The device POS
                documents the meaning of the time stamp.
                Additional information:
                See ERROR1-TIME-STAMP."
::= { error23 1 }


error23-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error23 2 }


error24-time-stamp OBJECT-TYPE
    SYNTAX  INTEGER
    MAX-ACCESS read-only
    STATUS  current
    DESCRIPTION
                "Contains some sort of time stamp indicating when error
                24 occurred.  Example time stamps include the actual
                time the error occurred (in seconds since Jan. 1, 1970),
                and the total engine page count.  The device POS
                documents the meaning of the time stamp.
                Additional information:
                See ERROR1-TIME-STAMP."
::= { error24 1 }


error24-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error24 2 }


error25-time-stamp OBJECT-TYPE
    SYNTAX  INTEGER
    MAX-ACCESS read-only
    STATUS  current
    DESCRIPTION
                "Contains some sort of time stamp indicating when error
                25 occurred.  Example time stamps include the actual
                time the error occurred (in seconds since Jan. 1, 1970),
                and the total engine page count.  The device POS
                documents the meaning of the time stamp.
                Additional information:
                See ERROR1-TIME-STAMP."
::= { error25 1 }


error25-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error25 2 }


error26-time-stamp OBJECT-TYPE
    SYNTAX  INTEGER
    MAX-ACCESS read-only
    STATUS  current
    DESCRIPTION
                "Contains some sort of time stamp indicating when error
                26 occurred.  Example time stamps include the actual
                time the error occurred (in seconds since Jan. 1, 1970),
                and the total engine page count.  The device POS
                documents the meaning of the time stamp.
                Additional information:
                See ERROR1-TIME-STAMP."
::= { error26 1 }


error26-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error26 2 }


error27-time-stamp OBJECT-TYPE
    SYNTAX  INTEGER
    MAX-ACCESS read-only
    STATUS  current
    DESCRIPTION
                "Contains some sort of time stamp indicating when error
                27 occurred.  Example time stamps include the actual
                time the error occurred (in seconds since Jan. 1, 1970),
                and the total engine page count.  The device POS
                documents the meaning of the time stamp.
                Additional information:
                See ERROR1-TIME-STAMP."
::= { error27 1 }


error27-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error27 2 }


error28-time-stamp OBJECT-TYPE
    SYNTAX  INTEGER
    MAX-ACCESS read-only
    STATUS  current
    DESCRIPTION
                "Contains some sort of time stamp indicating when error
                28 occurred.  Example time stamps include the actual
                time the error occurred (in seconds since Jan. 1, 1970),
                and the total engine page count.  The device POS
                documents the meaning of the time stamp.
                Additional information:
                See ERROR1-TIME-STAMP."
::= { error28 1 }


error28-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error28 2 }


error29-time-stamp OBJECT-TYPE
    SYNTAX  INTEGER
    MAX-ACCESS read-only
    STATUS  current
    DESCRIPTION
                "Contains some sort of time stamp indicating when error
                29 occurred.  Example time stamps include the actual
                time the error occurred (in seconds since Jan. 1, 1970),
                and the total engine page count.  The device POS
                documents the meaning of the time stamp.
                Additional information:
                See ERROR1-TIME-STAMP."
::= { error29 1 }


error29-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error29 2 }


error30-time-stamp OBJECT-TYPE
    SYNTAX  INTEGER
    MAX-ACCESS read-only
    STATUS  current
    DESCRIPTION
                "Contains some sort of time stamp indicating when error
                30 occurred.  Example time stamps include the actual
                time the error occurred (in seconds since Jan. 1, 1970),
                and the total engine page count.  The device POS
                documents the meaning of the time stamp.
                Additional information:
                See ERROR1-TIME-STAMP."
::= { error30 1 }


error30-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error30 2 }

error31-time-stamp OBJECT-TYPE
    SYNTAX  INTEGER
    MAX-ACCESS read-only
    STATUS  current
    DESCRIPTION
                "Contains some sort of time stamp indicating when error
                31 occurred.  Example time stamps include the actual
                time the error occurred (in seconds since Jan. 1, 1970),
                and the total engine page count.  The device POS
                documents the meaning of the time stamp.
                Additional information:
                See ERROR1-TIME-STAMP."
::= { error31 1 }


error31-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error31 2 }

error32-time-stamp OBJECT-TYPE
    SYNTAX  INTEGER
    MAX-ACCESS read-only
    STATUS  current
    DESCRIPTION
                "Contains a time stamp indicating when error
                32 occurred.  Example time stamps include the actual
                time the error occurred (in seconds since Jan. 1, 1970),
                and the total engine page count.  The device POS
                documents the meaning of the time stamp.
                Additional information:
                See ERROR1-TIME-STAMP."
::= { error32 1 }


error32-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error32 2 }


error33-time-stamp OBJECT-TYPE
    SYNTAX  INTEGER
    MAX-ACCESS read-only
    STATUS  current
    DESCRIPTION
                "Contains a time stamp indicating when error
                33 occurred.  Example time stamps include the actual
                time the error occurred (in seconds since Jan. 1, 1970),
                and the total engine page count.  The device POS
                documents the meaning of the time stamp.
                Additional information:
                See ERROR1-TIME-STAMP."
::= { error33 1 }


error33-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error33 2 }


error34-time-stamp OBJECT-TYPE
    SYNTAX  INTEGER
    MAX-ACCESS read-only
    STATUS  current
    DESCRIPTION
                "Contains a time stamp indicating when error
                34 occurred.  Example time stamps include the actual
                time the error occurred (in seconds since Jan. 1, 1970),
                and the total engine page count.  The device POS
                documents the meaning of the time stamp.
                Additional information:
                See ERROR1-TIME-STAMP."
::= { error34 1 }


error34-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error34 2 }


error35-time-stamp OBJECT-TYPE
    SYNTAX  INTEGER
    MAX-ACCESS read-only
    STATUS  current
    DESCRIPTION
                "Contains a time stamp indicating when error
                35 occurred.  Example time stamps include the actual
                time the error occurred (in seconds since Jan. 1, 1970),
                and the total engine page count.  The device POS
                documents the meaning of the time stamp.
                Additional information:
                See ERROR1-TIME-STAMP."
::= { error35 1 }


error35-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error35 2 }


error36-time-stamp OBJECT-TYPE
    SYNTAX  INTEGER
    MAX-ACCESS read-only
    STATUS  current
    DESCRIPTION
                "Contains a time stamp indicating when error
                36 occurred.  Example time stamps include the actual
                time the error occurred (in seconds since Jan. 1, 1970),
                and the total engine page count.  The device POS
                documents the meaning of the time stamp.
                Additional information:
                See ERROR1-TIME-STAMP."
::= { error36 1 }


error36-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error36 2 }


error37-time-stamp OBJECT-TYPE
    SYNTAX  INTEGER
    MAX-ACCESS read-only
    STATUS  current
    DESCRIPTION
                "Contains a time stamp indicating when error
                37 occurred.  Example time stamps include the actual
                time the error occurred (in seconds since Jan. 1, 1970),
                and the total engine page count.  The device POS
                documents the meaning of the time stamp.
                Additional information:
                See ERROR1-TIME-STAMP."
::= { error37 1 }


error37-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error37 2 }


error38-time-stamp OBJECT-TYPE
    SYNTAX  INTEGER
    MAX-ACCESS read-only
    STATUS  current
    DESCRIPTION
                "Contains a time stamp indicating when error
                38 occurred.  Example time stamps include the actual
                time the error occurred (in seconds since Jan. 1, 1970),
                and the total engine page count.  The device POS
                documents the meaning of the time stamp.
                Additional information:
                See ERROR1-TIME-STAMP."
::= { error38 1 }


error38-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error38 2 }


error39-time-stamp OBJECT-TYPE
    SYNTAX  INTEGER
    MAX-ACCESS read-only
    STATUS  current
    DESCRIPTION
                "Contains a time stamp indicating when error
                39 occurred.  Example time stamps include the actual
                time the error occurred (in seconds since Jan. 1, 1970),
                and the total engine page count.  The device POS
                documents the meaning of the time stamp.
                Additional information:
                See ERROR1-TIME-STAMP."
::= { error39 1 }


error39-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error39 2 }


error40-time-stamp OBJECT-TYPE
    SYNTAX  INTEGER
    MAX-ACCESS read-only
    STATUS  current
    DESCRIPTION
                "Contains a time stamp indicating when error
                40 occurred.  Example time stamps include the actual
                time the error occurred (in seconds since Jan. 1, 1970),
                and the total engine page count.  The device POS
                documents the meaning of the time stamp.
                Additional information:
                See ERROR1-TIME-STAMP."
::= { error40 1 }


error40-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error40 2 }


error41-time-stamp OBJECT-TYPE
    SYNTAX  INTEGER
    MAX-ACCESS read-only
    STATUS  current
    DESCRIPTION
                "Contains a time stamp indicating when error
                41 occurred.  Example time stamps include the actual
                time the error occurred (in seconds since Jan. 1, 1970),
                and the total engine page count.  The device POS
                documents the meaning of the time stamp.
                Additional information:
                See ERROR1-TIME-STAMP."
::= { error41 1 }


error41-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error41 2 }


error42-time-stamp OBJECT-TYPE
    SYNTAX  INTEGER
    MAX-ACCESS read-only
    STATUS  current
    DESCRIPTION
                "Contains a time stamp indicating when error
                42 occurred.  Example time stamps include the actual
                time the error occurred (in seconds since Jan. 1, 1970),
                and the total engine page count.  The device POS
                documents the meaning of the time stamp.
                Additional information:
                See ERROR1-TIME-STAMP."
::= { error42 1 }


error42-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error42 2 }


error43-time-stamp OBJECT-TYPE
    SYNTAX  INTEGER
    MAX-ACCESS read-only
    STATUS  current
    DESCRIPTION
                "Contains a time stamp indicating when error
                43 occurred.  Example time stamps include the actual
                time the error occurred (in seconds since Jan. 1, 1970),
                and the total engine page count.  The device POS
                documents the meaning of the time stamp.
                Additional information:
                See ERROR1-TIME-STAMP."
::= { error43 1 }


error43-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error43 2 }


error44-time-stamp OBJECT-TYPE
    SYNTAX  INTEGER
    MAX-ACCESS read-only
    STATUS  current
    DESCRIPTION
                "Contains a time stamp indicating when error
                44 occurred.  Example time stamps include the actual
                time the error occurred (in seconds since Jan. 1, 1970),
                and the total engine page count.  The device POS
                documents the meaning of the time stamp.
                Additional information:
                See ERROR1-TIME-STAMP."
::= { error44 1 }


error44-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error44 2 }


error45-time-stamp OBJECT-TYPE
    SYNTAX  INTEGER
    MAX-ACCESS read-only
    STATUS  current
    DESCRIPTION
                "Contains a time stamp indicating when error
                45 occurred.  Example time stamps include the actual
                time the error occurred (in seconds since Jan. 1, 1970),
                and the total engine page count.  The device POS
                documents the meaning of the time stamp.
                Additional information:
                See ERROR1-TIME-STAMP."
::= { error45 1 }


error45-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error45 2 }


error46-time-stamp OBJECT-TYPE
    SYNTAX  INTEGER
    MAX-ACCESS read-only
    STATUS  current
    DESCRIPTION
                "Contains a time stamp indicating when error
                46 occurred.  Example time stamps include the actual
                time the error occurred (in seconds since Jan. 1, 1970),
                and the total engine page count.  The device POS
                documents the meaning of the time stamp.
                Additional information:
                See ERROR1-TIME-STAMP."
::= { error46 1 }


error46-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error46 2 }


error47-time-stamp OBJECT-TYPE
    SYNTAX  INTEGER
    MAX-ACCESS read-only
    STATUS  current
    DESCRIPTION
                "Contains a time stamp indicating when error
                47 occurred.  Example time stamps include the actual
                time the error occurred (in seconds since Jan. 1, 1970),
                and the total engine page count.  The device POS
                documents the meaning of the time stamp.
                Additional information:
                See ERROR1-TIME-STAMP."
::= { error47 1 }


error47-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error47 2 }


error48-time-stamp OBJECT-TYPE
    SYNTAX  INTEGER
    MAX-ACCESS read-only
    STATUS  current
    DESCRIPTION
                "Contains a time stamp indicating when error
                48 occurred.  Example time stamps include the actual
                time the error occurred (in seconds since Jan. 1, 1970),
                and the total engine page count.  The device POS
                documents the meaning of the time stamp.
                Additional information:
                See ERROR1-TIME-STAMP."
::= { error48 1 }


error48-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error48 2 }


error49-time-stamp OBJECT-TYPE
    SYNTAX  INTEGER
    MAX-ACCESS read-only
    STATUS  current
    DESCRIPTION
                "Contains a time stamp indicating when error
                49 occurred.  Example time stamps include the actual
                time the error occurred (in seconds since Jan. 1, 1970),
                and the total engine page count.  The device POS
                documents the meaning of the time stamp.
                Additional information:
                See ERROR1-TIME-STAMP."
::= { error49 1 }


error49-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error49 2 }


error50-time-stamp OBJECT-TYPE
    SYNTAX  INTEGER
    MAX-ACCESS read-only
    STATUS  current
    DESCRIPTION
                "Contains a time stamp indicating when error
                50 occurred.  Example time stamps include the actual
                time the error occurred (in seconds since Jan. 1, 1970),
                and the total engine page count.  The device POS
                documents the meaning of the time stamp.
                Additional information:
                See ERROR1-TIME-STAMP."
::= { error50 1 }


error50-code OBJECT-TYPE
    SYNTAX  INTEGER
    MAX-ACCESS read-only
    STATUS  current
    DESCRIPTION
                "Contains a device specific error code.  Each device POS
                should list what errors are logged to the error log and
                the meaning of each supported error code value.
                Additional information:
                See ERROR1-CODE."
::= { error50 2 }

io-timeout OBJECT-TYPE
    SYNTAX  INTEGER(5..300)
    MAX-ACCESS read-write
    STATUS  current
    DESCRIPTION
                "The amount of time, in seconds, to wait for more print
                job data to be received before an I/O timeout occurs.
                The I/O channel being timed is the I/O channel that
                received the data associated with the current print job.
                If an I/O timeout occurs, the PDL processing sub-system
                assumes all the data associated with the current print
                job has been received, and processes the end of job in
                an PDL specific manner.  The POS specifies the supported
                values.
                Additional information:
                If an I/O timeout occurs,the PDL processing
                sub-system will consider it an end of job condition only
                if there is data from another I/O subsystem waiting to be
                processed.
                The supported values are 5 to 300 seconds.
                Setting to a value outside the supported range returns
                <noError> status and the
                value will be snapped to the nearest supported
                value."
::= { settings-io 1 }


io-switch OBJECT-TYPE
    SYNTAX  INTEGER {
		   eYes(1)
		   }
    MAX-ACCESS read-only
    STATUS  current
    DESCRIPTION
                "Indicates if the device will switch between I/O channels
                when a job boundary is encountered and print job data is
                available on another I/O channel."
::= { settings-io 2 }


io-buffering OBJECT-TYPE
    SYNTAX  INTEGER {
		   eOff(1),
		   eOn(2),
		   eAuto(3)
		   }
    MAX-ACCESS read-write
    STATUS  current
    DESCRIPTION
                "Returns or controls the manner in which the device
                performs I/O data buffering.  I/O data buffering allows
                additional print job data to be buffered by the I/O sub-
                system in an effort to allow the computer sending the
                data to perform other tasks and to keep the PDL
                processing sub-system busy.  eOff, I/O buffering is
                disabled.  When eOn, I/O buffering is enabled and the
                IO-BUFFER-SIZE object controls the amount of memory set
                aside for I/O buffer.  When eAuto, I/O buffering is
                enabled and the I/O buffer size is determined
                automatically by the device and the IO-BUFFER-SIZE
                object is not used.
                Additional information:
                In a PCL-only printer, all values may be set at any time.

                When there is less than 4M of memory installed, setting this object to eOn
                or eAuto will cause <badValue> to be returned.
                At exactly 4M of memory, eOn is not a valid setting.  At more than 4M
                of memory any setting is valid, subject to the conditions listed in the
                interactions below."
::= { settings-io 5 }


io-buffer-size OBJECT-TYPE
    SYNTAX  INTEGER
    MAX-ACCESS read-write
    STATUS  current
    DESCRIPTION
                "Returns or configures the amount of memory, in bytes,
                dedicated to I/O print job data buffering.  Attempting
                to set to an unsupported value causes the device to use
                the closest supported value.  Each device POS should
                document the list of supported values.
                Additional information:
                In LaserJet 4050 Series the minimum supported value is 10K bytes
                (10240).
                The maximum supported value is dependent on total memory installed
                and the amount of memory currently being used by other memory
                consumers.  Use the MAXIMUM-IO-BUFFERING-MEMORY object to determine
                this value.

                The following rules determine legal values for this object:
                1) Sizes less than 10K bytes will snap to 10K bytes.
                2) Sizes between 10K and 100K bytes will be rounded to the nearest 10K.
                3) Sizes between 100K bytes and the maximum value allowed will round to
                the nearest 100K bytes.

                If the value had to be snapped or rounded, <noError>
                will be returned along with the actual value that was written.

                Attempting to set this object when IO-BUFFERING is eOff will cause a status
                of <genErr> to be returned.  When IO-BUFFERING is
                eOff, reading this object will return a value of zero."
::= { settings-io 6 }


maximum-io-buffering-memory OBJECT-TYPE
    SYNTAX  INTEGER
    MAX-ACCESS read-only
    STATUS  current
    DESCRIPTION
                "This object's name is misleading.  Returns the maximum
                amount of additional memory, in bytes, that can be
                dedicated to buffering print job data."
::= { settings-io 7 }

not-ready-source-io OBJECT-TYPE
    SYNTAX  OCTET STRING
    MAX-ACCESS read-only
    STATUS  current
    DESCRIPTION
                "Indicates if the I/O sub-system in the device is not
                ready.  If there are no items in the collection (i.e. no
                bits are set), then the I/O sub-system is ready.  If
                there is an item present, then the item indicates what
                is causing the I/O sub-system to be not ready.  If the
                I/O sub-system is not ready due to a soft error, the
                soft error is considered to be an auto-continuable
                error, thus it can be acknowledged by setting the
                CONTINUE object to eTrue."
::= { status-io 1 }


status-source-io OBJECT-TYPE
    SYNTAX  OCTET STRING
    MAX-ACCESS read-only
    STATUS  current
    DESCRIPTION
                "Indicates if the I/O sub-system in a warning condition."
::= { status-io 2 }

parallel-speed OBJECT-TYPE
    SYNTAX  INTEGER {
		   eSlow(1),
		   eFast(2)
		   }
    MAX-ACCESS read-write
    STATUS  current
    DESCRIPTION
                "Returns or changes the maximum parallel I/O port speed.
                An eSlow setting causes a 10 us busy pulse per received
                byte of data.  An eFast setting causes a 1.5 us busy
                pulse per received byte of data.  In rare cases, setting
                this value to eFast can cause the parallel port to no
                longer transfer data reliably."
::= { parallel 4 }


parallel-bidirectionality OBJECT-TYPE
    SYNTAX  INTEGER {
		   eUnidirectional(1),
		   eBidirectional(2)
		   }
    MAX-ACCESS read-write
    STATUS  current
    DESCRIPTION
                "Returns or changes whether the parallel I/O port
                supports bidirectional communication."
::= { parallel 5 }


port1-parallel-speed OBJECT-TYPE
    SYNTAX  INTEGER {
		   eSlow(1),
		   eFast(2)
		   }
    MAX-ACCESS read-write
    STATUS  current
    DESCRIPTION
                "Returns or changes the maximum parallel I/O port speed,
                for port 1.  This object is only supported if this port
                is a parallel port.  An eSlow setting causes a 10 us
                busy pulse per received byte of data.  An eFast setting
                causes a 1.5 us busy pulse per received byte of data.
                In rare cases, setting this value to eFast can cause the
                parallel port to no longer transfer data reliably."
::= { port1 4 }


port1-parallel-bidirectionality OBJECT-TYPE
    SYNTAX  INTEGER {
		   eUnidirectional(1),
		   eBidirectional(2)
		   }
    MAX-ACCESS read-write
    STATUS  current
    DESCRIPTION
                "Returns or changes whether the parallel I/O port
                supports bidirectional communication for port 1.  This
                object is only supported if this port is a parallel
                port.
                Additional information:
                A get on this object returns the current mode
                for the parallel port. Setting this object specifies whether or not
                bidirectional communications will be allowed."
::= { port1 5 }

default-orientation OBJECT-TYPE
    SYNTAX  INTEGER {
		   ePortrait(1),
		   eLandscape(2)
		   }
    MAX-ACCESS read-write
    STATUS  current
    DESCRIPTION
                "Returns or changes the default orientation.  The list of
                supported values should be documented in the device
                POS."
::= { settings-pdl 2 }


default-copies OBJECT-TYPE
    SYNTAX  INTEGER(1..999)
    MAX-ACCESS read-write
    STATUS  current
    DESCRIPTION
                "Returns or changes default copies.  Default copies is
                the default values used by the PDL to control the number
                of copies of each page in the print job that are
                printed.  The print job can override this value.  The
                list of supported values should be documented in the
                device POS.
                Additional information:
                 The supported values are 1 through 999.
                Setting to an unsupported value causes the printer to substitute in a snap
                value and to return <noError> status.
                The snaps are as follows:
                <1 snaps to 1
                >999 snaps to 999"
::= { settings-pdl 4 }


form-feed OBJECT-TYPE
    SYNTAX  INTEGER {
		   eInitiateAction(1)
		   }
    MAX-ACCESS read-write
    STATUS  current
    DESCRIPTION
                "Instructs the PDL processing sub-system to finishing
                processing the current page of the current job.  Form
                feed is also known as close page or eject page.  If the
                PDL processing sub-system is in a FORM-FEED-NEEDED
                state, this causes the device to flush or finish
                processing the current page of the current job.  If the
                device is not in the FORM-FEED-NEEDED state, an
                <genErr> will occur."
::= { settings-pdl 5 }


resource-saving OBJECT-TYPE
    SYNTAX  INTEGER {
		   eOff(1),
		   eOn(2),
		   eAuto(3)
		   }
    MAX-ACCESS read-write
    STATUS  current
    DESCRIPTION
                "Returns or changes PDL resource saving.  Resource saving
                stores a PDL's permanent soft resources, like fonts,
                even when another PDL is active.  Resource saving is
                also called environment saving.  When eOff, resource
                saving is disabled.  When ON, resource saving is enabled
                and memory is set aside for each PDL based on that PDL's
                resource saving memory size object, to store that PDL's
                permanent soft resources.  When eAuto, resource saving
                is enabled and memory space for each installed PDL is
                determined automatically.  The device POS should
                document what values are legal when only one PDL is
                installed.
                Additional information:
                When PCL (including PCL/XL) is the only PDL
                installed in LaserJet 4050 Series, eOn is not a legal value.  Attempting to set this object to
                eOn with a PCL-only printer will result in a status of
                <badValue> being returned.

                When Postscript is installed and less than 8 Megabytes of RAM are present,
                resource saving is not available.  The only valid value for this object
                is eOff.  Attempting to set this object to eOn or eAuto will cause
                <badValue> to be returned.

                When Postscript and 8 Megabytes or more of RAM are installed, all values
                are valid, provided I/O Buffering, Mopying, or Ram Disk have not consumed
                the needed memory.

                This object is only supported if Postscript is resident in the printer."
::= { settings-pdl 6 }


maximum-resource-saving-memory OBJECT-TYPE
    SYNTAX  INTEGER
    MAX-ACCESS read-only
    STATUS  current
    DESCRIPTION
                "This object's name is misleading.  This object returns
                the maximum amount of additional memory, in bytes, that
                can be dedicated to holding PDL permanent soft
                resources.
                Additional information:
                NOTE:  The values listed below have not been verified
                on LaserJet 4050 Series.  The following numbers assume that IO-BUFFERING=eOff;
                if IO-BUFFERING<>eOff, the following numbers will be reduced by the value of
                IO-BUFFER-SIZE.

                Memory for resource saving is allocated in increments of 102400 bytes.
                Therefore, for each 1M (1048576 bytes) of memory added to the printer, 102400
                bytes are made available to resource saving (and I/O buffering) and 24576
                bytes are retained until an additional 102400 byte block can be made
                available. The value reported by this object is always rounded down to the
                nearest multiple of 102400.

                For a PCL-only printer, the value of this object is zero (all resource saving
                memory is dedicated to PCL).

                If PostScript is installed without a duplex unit, the value of this object is
                as follows:
                Zero if <7M memory is installed.
                1048576 if 7M memory is installed and RESOURCE-SAVING=eOff.
                1048576 if 7M memory is installed and RESOURCE-SAVING=eOn (note that this
                value will be reduced by the amount of memory allocated to
                PCL-RESOURCE-SAVING-MEMORY-SIZE and POSTSCRIPT-RESOURCE-SAVING-MEMORY-SIZE).
                819200 if 7M memory is installed and RESOURCE-SAVING=eAuto.
                When RESOURCE-SAVING=eAuto, 819200 bytes of each 1M over 7M memory installed
                are allocated to PCL and PostScript (409600 each) with the remaining bytes
                added to this object.
                When RESOURCE-SAVING=eOn or eOff, all bytes over 13M memory installed are
                added to this object.

                If PostScript is installed with a duplex unit, the value of this object is as
                follows:
                Zero if <13M memory is installed.
                1048576 if 13M memory is installed and RESOURCE-SAVING=eOff.
                1048576 if 13M memory is installed and RESOURCE-SAVING=eOn (note that this
                value will be reduced by the amount of memory allocated to
                PCL-RESOURCE-SAVING-MEMORY-SIZE and POSTSCRIPT-RESOURCE-SAVING-MEMORY-SIZE).
                1048576 if 13M memory is installed and RESOURCE-SAVING=eAuto.
                When RESOURCE-SAVING=eAuto, 810200 bytes of each 1M over 13M memory installed
                are allocated to PCL and PostScript (409600 each) with the remaining bytes
                added to this object.
                When RESOURCE-SAVING=eOn or eOff, all bytes over 13M memory installed are
                added to this object.

                The above listed values returned by this object will be reduced by the amount
                of memory added to PCL-RESOURCE-SAVING-MEMORY-SIZE and
                POSTSCRIPT-RESOURCE-SAVING-MEMORY-SIZE when RESOURCE-SAVING=eOn."
::= { settings-pdl 7 }


default-vertical-black-resolution OBJECT-TYPE
    SYNTAX  INTEGER
    MAX-ACCESS read-write
    STATUS  current
    DESCRIPTION
                "Returns or changes the value of the default vertical
                black resolution.  The units are dots per inch.
                Additional information:
                In LaserJet 4050 Series changing this OID also causes
                DEFAULT- HORIZONTAL-BLACK RESOLUTION to change.
                DEFAULT- HORIZONTAL-BLACK-RESOLUTION and
                DEFAULT-VERTICAL-BLACK-RESOLUTION must always be the
                same.  The supported values are 300 and 600
                for LaserJet 8100 Series and LaserJet 8000 Series, and 300, 600, and 1200 for LaserJet 5000 Series
                and LaserJet 4000 Series.
                Setting to an unsupported value causes the printer
                to substitute in a snap value and
                to return <noError> status.
                The snap values are as follow:
                LaserJet 5000 Series and LaserJet 4000 Series:
                n < 450 snaps to 300
                450 >= n < 900 snaps to 600
                n >= 900 snaps to 1200
                LaserJet 8100 Series and LaserJet 8000 Series:
                n < 450 snaps to 300
                n >= 450 snaps to 600 "
::= { settings-pdl 8 }


default-horizontal-black-resolution OBJECT-TYPE
    SYNTAX  INTEGER
    MAX-ACCESS read-write
    STATUS  current
    DESCRIPTION
                "Returns or changes the value of the default horizontal
                black resolution.  The units are dots per inch.
                Additional information:
                In LaserJet 4050 Series changing this object also causes
                DEFAULT-VERTICAL-BLACK RESOLUTION to change.
                DEFAULT-HORIZONTAL-BLACK-RESOLUTION and
                DEFAULT-VERTICAL-BLACK-RESOLUTION must always be the
                same.  The supported values are 300 and 600
                for LaserJet 8100 Series and LaserJet 8000 Series, and 300, 600, and 1200 for LaserJet 5000 Series
                and LaserJet 4000 Series.
                Setting to an unsupported value causes the printer
                to substitute in a snap value and to
                return <noError> status.
                The snap values are as follow:
                LaserJet 5000 Series and LaserJet 4000 Series:
                n < 450 snaps to 300
                450 >= n < 900 snaps to 600
                n >= 900 snaps to 1200
                LaserJet 8100 Series and LaserJet 8000 Series:
                n < 450 snaps to 300
                n >= 450 snaps to 600 "
::= { settings-pdl 9 }


default-page-protect OBJECT-TYPE
    SYNTAX  INTEGER {
		   eOn(2),
		   eAuto(3)
		   }
    MAX-ACCESS read-write
    STATUS  current
    DESCRIPTION
                "Returns or changes the default page protection behavior.
                If eOff, the device does not reserve memory for holding
                the entire raster form of a processed page.  If eOn,
                then memory is reserved.  If eAuto, the device
                determines the amount of memory to reserve.
                Additional information:
                Setting to eOn causes MET to be more conservative, but
                it will not allocate memory to hold an entire
                rasterized page."
::= { settings-pdl 10 }


default-lines-per-page OBJECT-TYPE
    SYNTAX  INTEGER
    MAX-ACCESS read-write
    STATUS  current
    DESCRIPTION
                "Returns or changes the default number of lines per page.
                The POS indicates the supported values.  An unsupported
                value causes the printer to use the closest supported
                value, causing the printer to return the
                <noError>.
                Additional information:
                The supported values in LaserJet 4050 Series are 5 to 128.
                Setting to an unsupported value causes the
                the printer to substitute in a snap value and to return
                <noError>
                status.
                The snap values are as follow:
                <5 snaps to 5
                >128 snaps to 128"
::= { settings-pdl 11 }


default-vmi OBJECT-TYPE
    SYNTAX  INTEGER
    MAX-ACCESS read-write
    STATUS  current
    DESCRIPTION
                "Returns or changes the default vertical motion index.
                The unit of measure for VMI is centipoints per line.
                The POS indicates the supported values.  An unsupported
                value causes the printer to use the closest supported
                value, causing the printer to return
                <noError>."
::= { settings-pdl 12 }

default-media-size OBJECT-TYPE
    SYNTAX  INTEGER {
		   eUSExecutive(1),
		   eUSLetter(2),
		   eUSLegal(3),
		   eROC16K(17),
		   eJISExecutive(18),
		   eISOandJISA5(25),
		   eISOandJISA4(26),
		   eMonarch(80),
		   eCommercial10(81),
		   eInternationalDL(90),
		   eInternationalC5(91),
		   eInternationalB5(100),
		   eCustom(101)
		   }
    MAX-ACCESS read-write
    STATUS  current
    DESCRIPTION
                "This indicates the default media size.  A write of an
                unsupported value causes an <badValue>.
  Complete list of supported media sizes along
                with their dimensions are listed in the ''Media Size
                Table'' near the end of this document."
::= { settings-pdl 13 }


cold-reset-media-size OBJECT-TYPE
    SYNTAX  INTEGER {
		   eUSLetter(2),
		   eISOandJISA4(26)
		   }
    MAX-ACCESS read-write
    STATUS  current
    DESCRIPTION
                "Returns or sets the media size that is used as the
                DEFAULT-MEDIA-SIZE when a cold reset occurs."
::= { settings-pdl 19 }

default-media-name OBJECT-TYPE
    SYNTAX  DisplayString
    MAX-ACCESS read-write
    STATUS  current
    DESCRIPTION
                "Returns or sets the media name that is used until the
                media name is changed by a print job command.
                Additional information:
                This string must be one of the MEDIAn-NAME
                objects. The value of this object is saved across
                		            a power cycle."
::= { settings-pdl 22 }

reprint OBJECT-TYPE
    SYNTAX  INTEGER {
		   eOff(1),
		   eOn(2),
		   eAuto(3)
		   }
    MAX-ACCESS read-write
    STATUS  current
    DESCRIPTION
                "Returns or changes the reprint (jam recovery) setting.
                If eOn, then the device will reprint pages jammed pages.
                If eOff, the device will not attempt to reprint jammed
                pages.  If eAuto, a device dependent algorithm (which
                should be documented in the POS) will be used to
                determine if the page gets reprinted.  This object
                controls all PDLs, unless a specific PDL supports its
                own reprint control mechanism.  To date, only PostScript
                has a PDL reprint control mechanism.
                Additional information:
                Setting this object when the printer is not
                idle, may cause a status of <noError> to be returned, but
                the new value will not take effect until a job boundary
                is reached.  If a get is done on object before the job
                boundary is reached, the value last set will be
                returned.

                When the value is set to eOff, pages will not be stored
                in the printer, and in the event of a paper jam, will
                have to be reprinted.  When the value is set to eOn,
                pages will be stored until delivery, therefore, in the
                event of a paper jam, the page will be reprinted.

                When the value is set to eAuto, the printer will behave
                as though it is eOff when there is less than seven
                megabytes of memory installed in the printer.  When
                additional memory is installed, to total at least seven
                megabytes of RAM, the setting of eAuto will behave as
                though it was set to eOn."
::= { settings-pdl 36 }

wide-a4 OBJECT-TYPE
    SYNTAX  INTEGER {
		   eOff(1),
		   eOn(2)
		   }
    MAX-ACCESS read-write
    STATUS  current
    DESCRIPTION
                "Returns or changes the wide A4 logical page size
                setting.  If eOn, then the margins/printable area of A4
                paper will be changed to allow 80 10-pitch characters to
                be printed on a single line.  If eOff then the industry
                standard A4 logical page size is used."
::= { settings-pdl 37 }

dark-courier OBJECT-TYPE
    SYNTAX  INTEGER {
		   eOff(1),
		   eOn(2)
		   }
    MAX-ACCESS read-write
    STATUS  current
    DESCRIPTION
                "Returns or changes the dark Courier setting.  If eOn,
                then the Courier font used will approximate the same
                darkness as the LaserJet III printer.  If eOff, then the
                Courier font used will approximate the same darkness as
                the LaserJet 4 printer."
::= { settings-pdl 38 }

default-bits-per-pixel OBJECT-TYPE
    SYNTAX  INTEGER
    MAX-ACCESS read-write
    STATUS  current
    DESCRIPTION
                "Controls the number of levels used (per pixel) when
                printing grayscale or color images."
::= { settings-pdl 39 }

pcl-datecode OBJECT-TYPE
    SYNTAX  DisplayString
    MAX-ACCESS read-only
    STATUS  current
    DESCRIPTION
                "This indicates the PCL firmware date code in yyyymmdd
                format."
::= { pdl-pcl 1 }

pcl-resource-saving-memory-size OBJECT-TYPE
    SYNTAX  INTEGER
    MAX-ACCESS read-write
    STATUS  current
    DESCRIPTION
                "Returns or changes the amount of resource saving memory
                set aside to hold permanent soft PCL resources.
                Additional information:
                The value returned by this object is the amount of
                Resource Saving memory currently dedicated to PCL.

                For a PCL-only printer, the value of this object is zero. All memory is
                dedicated to PCL, but it is not shown as such.

                If Postscript is installed, the default value of this object is as follows:
                0 if RESOURCE-SAVING = eOff.
                0 if less than 8 Megabytes of RAM is in the printer.
                400K bytes if RAM >= 8 Megabytes and RESOURCE-SAVING = eOn.
                400K bytes if RAM = 8 Megabytes and RESOURCE-SAVING = eAuto, plus 100K bytes
                for each Megabyte of RAM over 8 Megabytes.

                If RESOURCE-SAVING=eOn, this object can be used to set the amount of Resource
                Saving memory currently dedicated to PCL. The range of values supported by
                this object are:
                0 bytes (which disables resource saving for PCL)
                400K bytes through (400K bytes + MAXIMUM-RESOURCE-SAVING-MEMORY) in
                increments of 100K bytes.
                If a value is received that is greater than 0 and less than 400K bytes,
                it will be snapped to 400K bytes and a status of
                <noError> returned.
                If an unsupported value greater than 400K bytes is received,
                it will be snapped down to the nearest 100K value
                and a status of <noError> returned.

                Attempting to set this object when RESOURCE-SAVING is eAuto or eOff will
                cause a status of <genErr> to be returned."
::= { pdl-pcl 2 }

pcl-name OBJECT-TYPE
    SYNTAX  DisplayString
    MAX-ACCESS read-only
    STATUS  current
    DESCRIPTION
                "Contains the name of the PDL.  For PCL, the name is
                `PCL'."
::= { pdl-pcl 3 }

pcl-version OBJECT-TYPE
    SYNTAX  DisplayString
    MAX-ACCESS read-only
    STATUS  current
    DESCRIPTION
                "Contains the PDL version."
::= { pdl-pcl 4 }


pcl-total-page-count OBJECT-TYPE
    SYNTAX  INTEGER
    MAX-ACCESS read-only
    STATUS  current
    DESCRIPTION
                "Total number of PCL pages printed by the device.
                Additional information:
                In LaserJet 4050 Series the PCL page count is kept in
                NVRAM, and the NVRAM value is updated at least every
                10 pages.  NOTE: The value returned by this object will
                be incremented every page but if power is lost between
                NVRAM updates, up to 9 pages of the page count may be
                lost.  The page count counter will be reset to zero
                after 16,777,215 (2^24-1) pages.
                The page count is incremented when a sheet of media is pulled from an input
                tray. A duplex printed sheet will cause this counter to be incremented by
                two."
::= { pdl-pcl 5 }

pcl-default-symbol-set OBJECT-TYPE
    SYNTAX  INTEGER {
		   eISO60DanishNorwegian(4),
		   eISO15Italian(9),
		   eISO88591Latin1ECMA94(14),
		   eISO11SwedishforNames(19),
		   eISO6ASCII(21),
		   eISO4UnitedKingdom(37),
		   eISO69French(38),
		   eISO21German(39),
		   eLegal(53),
		   eISO88592Latin2ECMA94(78),
		   eISO17Spanish(83),
		   ePSMath(173),
		   eISO88599Latin5ECMA128(174),
		   eWindows31Latin5(180),
		   eMicrosoftPublishing(202),
		   eVenturaMath(205),
		   eDeskTop(234),
		   eMath8(269),
		   eRoman8(277),
		   eWindows31Latin2(293),
		   ePC8Turkish(308),
		   eWindows30Latin1(309),
		   ePSText(330),
		   ePC8CodePage437(341),
		   ePC8DNDanishNorwegian(373),
		   ePC850Multilingual(405),
		   eVenturaInternational(426),
		   eVenturaUS(458),
		   ePiFont(501),
		   ePC852Latin2(565),
		   eWindows31J(619),
		   eWindows31Latin1(629)
		   }
    MAX-ACCESS read-write
    STATUS  current
    DESCRIPTION
                "Returns or changes the default PCL symbol set.  The
                enumeration values match the values supported by the PCL
                Symbol Set Code escape sequence, <ESC>*c#R.  The binary
                representation of the enumerated value is also matches
                the PML <SymbolSetValue>.
                Additional information:
                The eWindows31J enumeration is only supported
                if a Japanese font SIMM is installed."
::= { pdl-pcl 11 }


pcl-default-font-height OBJECT-TYPE
    SYNTAX  INTEGER
    MAX-ACCESS read-write
    STATUS  current
    DESCRIPTION
                "Returns or changes the default PCL height.  Height is an
                approximate measure of the body of the type in
                centipoints.  A centipoint is 1/7200 inch.  Height
                applies only to proportional fonts.  Point size, in
                points, can be converted to font height, in centipoints,
                by multiplying the point size by 100.  The POS indicates
                the supported values.  An unsupported value causes the
                printer to use the closest supported value, causing the
                printer to return <noError>.
                ''Closest'' means the smallest absolute difference.
                Additional information:
                Supported values range from 400 to 99975, in
                increments of 25 units.
                Setting to an unsupported value causes the
                printer to substitute in a snap value and to
                return <noError> status.
                The snap values are as follow:
                <=400 snaps to 400
                >=99975 snaps to 99975
                Unsupported values in the range 400 to 99975 snap
                DOWN to the previous supported value
                (i.e 25293 snaps to 25275 or 75038 snaps to 75025)."
::= { pdl-pcl 13 }


pcl-default-font-source OBJECT-TYPE
    SYNTAX  INTEGER {
		   eInternal(1),
		   ePermanentSoft(2),
		   eRomSimm1(10),
		   eRomSimm2(11),
		   eRomSimm3(12),
           eRomSimm4(13),
           eRomSimm5(14),
           eUsb1(15),
           eUsb2(16),
           eUsb3(17),
           eUsb4(18)
		   }
    MAX-ACCESS read-write
    STATUS  current
    DESCRIPTION
                "Returns or changes the value of the default font source
                variable in NVRAM."
::= { pdl-pcl 14 }


pcl-default-font-number OBJECT-TYPE
    SYNTAX  INTEGER(0..255)
    MAX-ACCESS read-write
    STATUS  current
    DESCRIPTION
                "Returns or changes the value of the default font number
                variable in NVRAM.  Writing an unsupported value causes
                the printer to generate an
                <badValue>.
                Additional information:
                Valid numbers or 0 - 255, but only font numbers that are
                included in the PCL FONT LIST are selectable."
::= { pdl-pcl 15 }


pcl-default-font-width OBJECT-TYPE
    SYNTAX  INTEGER
    MAX-ACCESS read-write
    STATUS  current
    DESCRIPTION
                "Returns or changes the default PCL font width.  Width is
                expressed as the width of a character in centipoints.  A
                centipoint is 1/7200 inch.  Width applies only to fixed
                space fonts.  Pitch, in character per inch, can be
                converted to font width, in centipoints, by dividing
                7200 by the pitch.  The POS indicates the supported
                values.  An unsupported value causes the printer to use
                the closest supported value, causing the printer to
                return <noError>.  ''Closest''
                means the smallest absolute difference.
                Additional information:
                Setting to an unsupported value causes the
                printer to substitue in a snap value (listed below)
                and return <noError> status.
                The snap values for pitch are as follow:
                <=44 snaps to 44
                >=9999 snaps to 9999"
::= { pdl-pcl 16 }

postscript-datecode OBJECT-TYPE
    SYNTAX  DisplayString
    MAX-ACCESS read-only
    STATUS  current
    DESCRIPTION
                "This indicates the PostScript firmware datecode in
                yyyymmdd format.
                Additional information:
                This object is only supported if PostScript
                option is installed.
               	Returns <noSuchName> status if
               	attempting to perform a Get on this OID with no
               	PostScript option installed.
               	Returns <noSuchName>
               	status if attempting to perform a Set, EnableTrap, or
               	DisableTrap on this OID with no PostScript option
               	installed."
::= { pdl-postscript 1 }


postscript-resource-saving-memory-size OBJECT-TYPE
    SYNTAX  INTEGER
    MAX-ACCESS read-write
    STATUS  current
    DESCRIPTION
                "Returns or changes the amount of resource saving memory
                set aside to hold permanent soft PostScript resources.
                Additional information:
                The value returned by this object is the amount of
                Resource Saving memory currently dedicated to Postscript.

                If Postscript is installed, the default value of this object is as follows:
                0 if RESOURCE-SAVING = eOff.
                0 if less than 8 Megabytes of RAM is in the printer.
                400K bytes if RAM >= 8 Megabytes and RESOURCE-SAVING = eOn.
                400K bytes if RAM = 8 Megabytes and RESOURCE-SAVING = eAuto, plus 100K bytes
                for each Megabyte of RAM over 8 Megabytes.

                If RESOURCE-SAVING=eOn, this object can be used to set the amount of Resource
                Saving memory currently dedicated to PCL. The range of values supported by
                this object are:
                0 bytes (which disables resource saving for Postscript)
                400K bytes through (400K bytes + MAXIMUM-RESOURCE-SAVING-MEMORY) in
                increments of 100K bytes.
                If a value is received that is greater than 0 and less than 400K bytes,
                it will be snapped to 400K bytes and a status of
                <noError> returned.
                If an unsupported value greater than 400K bytes is received,
                it will be snapped down to the nearest 100K value
                and a status of <noError> returned.

                Attempting to set this object when RESOURCE-SAVING is eAuto or eOff will
                cause a status of <genErr> to be returned."
::= { pdl-postscript 2 }

postscript-name OBJECT-TYPE
    SYNTAX  DisplayString
    MAX-ACCESS read-only
    STATUS  current
    DESCRIPTION
                "Contains the name of the PDL.  For PostScript, the name
                is `PostScript'.
                Additional information:
                This object is only supported if PostScript
                option is installed.
                Returns <noSuchName> status if
               	attempting to perform a Get on this OID with no
               	PostScript option installed.
               	Returns an <noSuchName>
               	status if attempting to perform a Set, EnableTrap, or
               	DisableTrap on this OID with no PostScript option
               	installed."
::= { pdl-postscript 3 }

postscript-version OBJECT-TYPE
    SYNTAX  DisplayString
    MAX-ACCESS read-only
    STATUS  current
    DESCRIPTION
                "Contains the PDL version.
                Additional information:
                This object is only supported if PostScript
               	option is installed.
               	Returns <noSuchName> status if
               	attempting to perform a Get on this OID with no
               	PostScript option installed.
               	Returns an <noSuchName>
               	status if attempting to perform a Set, EnableTrap, or
               	DisableTrap on this OID with no PostScript option
               	installed."
::= { pdl-postscript 4 }

postscript-total-page-count OBJECT-TYPE
    SYNTAX  INTEGER
    MAX-ACCESS read-only
    STATUS  current
    DESCRIPTION
                "Total number of PostScript pages printed by the device.
                Additional information:
                This object is only supported if the PostScript
                option is installed.
                In LaserJet 4050 Series the count is kept in NVRAM, and the
                NVRAM value is updated at least every 10
                sheets.  NOTE: The value returned by this object will
                be incremented every sheet but if power is lost between
                NVRAM updates up to 9 sheets of the count may be
                lost.  The counter will be reset to zero
                after 16,777,215 (2^24-1) pages. "
::= { pdl-postscript 5 }


postscript-print-errors OBJECT-TYPE
    SYNTAX  INTEGER {
		   eOff(1),
		   eOn(2)
		   }
    MAX-ACCESS read-write
    STATUS  current
    DESCRIPTION
                "Returns or changes the value of the print PostScript
                errors setting.  If eOn, PostScript prints an error page
                showing the error encountered and the stack at the time
                of the error.
                Additional information:
                This object is only supported if the PostScript
                option is installed."
::= { pdl-postscript 11 }

postscript-jam-recovery OBJECT-TYPE
    SYNTAX  INTEGER {
		   eOff(1),
		   eOn(2)
		   }
    MAX-ACCESS read-write
    STATUS  current
    DESCRIPTION
                "Returns or changes the PostScript jam recovery setting.
                If eOn, then the device will reprint PostScript pages,
                if those pages jam.
                Additional information:
                This object is only supported if PostScript
                option is installed."
::= { pdl-postscript 12 }

-- 1.3.6.1.4.1.11.2.3.9.4.2.1.3.3.4.14
postscript-defer-media   OBJECT-TYPE
    SYNTAX          INTEGER {
                              eDisabled(1),
                             eEnabled(2)
                    }
    MAX-ACCESS read-write
    STATUS            current
    DESCRIPTION " This object will be used to enable or disable the use of the
    Adobe Postscript Paper Handling Model in the printer firmware.
    By default it is enabled which means that PostScript will
    always defer the media selection to HP Paper Handling Model"
::= { pdl-postscript 14 }

-- 1.3.6.1.4.1.11.2.3.9.4.2.1.3.3.15.1
pdf-version   OBJECT-TYPE
    SYNTAX          OCTET STRING
    MAX-ACCESS read-only
    STATUS            current
    DESCRIPTION " Contains version of PDF that is supported on the device"
::= { pdl-pdf 1 }

-- 1.3.6.1.4.1.11.2.3.9.4.2.1.3.3.15.2
pdf-total-page-count   OBJECT-TYPE
    SYNTAX          INTEGER
    MAX-ACCESS read-only
    STATUS            current
    DESCRIPTION " Total number of PDF pages printed by the device"
::= { pdl-pdf 2 }

-- 1.3.6.1.4.1.11.2.3.9.4.2.1.3.3.15.3
pdf-enabled   OBJECT-TYPE
    SYNTAX          INTEGER {
                              ePDFNotEnabled(1),
                             ePDFEnabled(2)
                    }
    MAX-ACCESS read-only
    STATUS            current
    DESCRIPTION " Used to tell whether the device supports PDF"
::= { pdl-pdf 3 }

-- 1.3.6.1.4.1.11.2.3.9.4.2.1.3.3.15.4
pdf-print-errors   OBJECT-TYPE
    SYNTAX          INTEGER {
                              eOff(1),
                             eOn(2)
                    }
    MAX-ACCESS read-write
    STATUS            current
    DESCRIPTION " Returns or changes the value of the print PDF errors setting.
    If eOn, PDF prints an error page showing the error encountered
    and the stack at the time of the error"
::= { pdl-pdf 4 }

pclxl-total-page-count OBJECT-TYPE
    SYNTAX      INTEGER
    MAX-ACCESS read-write
    STATUS      current
       DESCRIPTION "Total number of PCLXL pages printed by the device."
::= { pdl-pclxl 1 }

esc-p-datecode OBJECT-TYPE
    SYNTAX  DisplayString
    MAX-ACCESS read-only
    STATUS  current
    DESCRIPTION
                "This indicates the ESC-P PDL datecode.  The datecode
                format is yyyymmdd.
                Additional information:
                This object is only supported if ESC-P option is
               	installed.
               	Returns an <noSuchName> status if
               	attempting to perform a Get on this OID with no ESC-P
               	option installed.
               	Returns <noSuchName>
               	status if attempting to perform a Set, EnableTrap, or
               	DisableTrap on this OID with no ESC-P option
               	installed."
::= { pdl-esc-p 1 }


esc-p-name OBJECT-TYPE
    SYNTAX  DisplayString
    MAX-ACCESS read-only
    STATUS  current
    DESCRIPTION
                "Contains the name of the PDL.  For ESC-P, the name is
                `ESC-P'.
                Additional information:
                This object is only supported if ESC-P option is
                installed.
               	Returns an <noSuchName> status if
               	attempting to perform a Get on this OID with no ESC-P
               	option installed.
               	Returns <noSuchName>
               	status if attempting to perform a Set, EnableTrap, or
               	DisableTrap on this OID with no ESC-P option
               	installed."
::= { pdl-esc-p 3 }


esc-p-version OBJECT-TYPE
    SYNTAX  DisplayString
    MAX-ACCESS read-only
    STATUS  current
    DESCRIPTION
                "Contains the PDL version.
                Additional information:
                This object is only supported if ESC-P option is
                installed.
               	Returns an <noSuchName> status if
               	attempting to perform a Get on this OID with no ESC-P
               	option installed.
               	Returns <noSuchName>
               	status if attempting to perform a Set, EnableTrap, or
               	DisableTrap on this OID with no ESC-P option
               	installed."
::= { pdl-esc-p 4 }


pjl-password OBJECT-TYPE
    SYNTAX  INTEGER
    MAX-ACCESS read-only
    STATUS  current
    DESCRIPTION
                "Returns PJL password, if the password is not set (zero).
                If the password is set, then attempting to retrieve the
                password causes an <genErr> to occur
                and will return the <NullValue>."
::= { pjl 1 }

-- 1.3.6.1.4.1.11.2.3.9.4.2.1.4.1.8.8.1
media-number-of-type-supported   OBJECT-TYPE
    SYNTAX          INTEGER
    MAX-ACCESS read-only
    STATUS            current
    DESCRIPTION " Indicates the maximum number of supported media types"
::= { media-types 1 }

-- 1.3.6.1.4.1.11.2.3.9.4.2.1.4.1.15.1.
media-size-supported-driver-n-string   OBJECT-TYPE
    SYNTAX          OCTET STRING
    MAX-ACCESS read-only
    STATUS            current
    DESCRIPTION " Returns the Driver (PJL) string used to specigy a media size,
    for each media size that is supported by a product. PML walk of
    1.4.1.15.1 will return the driver (PJL) name string for each
    media size supported by a product. PML Get of 1.4.1.15.1.X will
    return the driver (PJL) name string of the media size whose PML
    ID maps to X (if it is supported)"
::= { media-sizes 1 }

-- 1.3.6.1.4.1.11.2.3.9.4.2.1.1.4.8.2
fih-extra-pulses-feature   OBJECT-TYPE
    SYNTAX          INTEGER {
                              eDisable(1),
                             eEnable(2)
                    }
    MAX-ACCESS read-write
    STATUS            current
    DESCRIPTION " This object allows one to get/set the setting of the FIH EXTRA
    PULSES FEATURE item. This either turns the feature on or off
    based on customer requirement"
::= { foreign-interface 2 }

print-density OBJECT-TYPE
    SYNTAX  INTEGER(1..5)
    MAX-ACCESS read-write
    STATUS  current
    DESCRIPTION
                "Returns or sets the print density setting.  Print
                density is the instantaneous amount of marking agent
                applied to the paper while printing.  A value of zero
                has the lowest print density, yielding a lighter page.
                A value of 10 has the highest print density, yielding a
                darker page.  Each POS should document what values in
                the 0 to 10 range are supported.
                Additional information:
                When this value is written, the page pipeline
                will be flushed (all pages being printed are completed, no
                new ones are started), the new density setting is set and
                printing resumes.  The acutal change in print density may be
                gradual over several pages.
                The supported values are 1 through 5.  Setting to an
                unsupported value causes the printer to substitue in a
                a snap value and to return <noError>
                status.  The snap values are as follows:
                <1 snaps to 1
                >5 snaps to 5."
::= { settings-prt-eng 5 }


transfer-setting OBJECT-TYPE
    SYNTAX  INTEGER(100..200)
    MAX-ACCESS read-write
    STATUS  current
    DESCRIPTION
                "When set the object will cause the transfer setting of the
               device to be changed to the nearest appropriate value. When
               the object is read it will return the current transfer
               setting. Each engine will have different supported values.
               The object should snap to the nearest supported value.
               Different products could use this value in different ways.
               Typically, this value would be a voltage on an EP system,
               but could be a pressure level on an inkjet.
                Additional information:
                This setting is a voltage adjustment in the LaserJet
                2200.  Any value >= 150 snaps to 200."
::= { settings-prt-eng 8 }


separation-setting OBJECT-TYPE
    SYNTAX  INTEGER(100..200)
    MAX-ACCESS read-write
    STATUS  current
    DESCRIPTION
                "When set this object will cause the separation setting of
               the device to be changed to the nearest appropriate value.
               When the object is read it will return the current separation
               setting.  Each engine will have different supported values.
               The object should snap to the nearest supported value.
               Different products could use this value in different ways.
               Typically, this value would be a voltage in an EP system,
               but could be some other parameter on an inkjet.  The device
               POS will specify supported values, any snap behavior and
               will detail the product specific meaning of
               'device separation'.
                Additional information:
                This object changes the charge so the media does not
                curl too much causing the media to jam under the cartridge.
                Any value >= 150 snaps to 200."
::= { settings-prt-eng 13 }

not-ready-destination-print-engine OBJECT-TYPE
    SYNTAX  OCTET STRING
    MAX-ACCESS read-only
    STATUS  current
    DESCRIPTION
                "Indicates if the print engine sub-system in the device
                is not ready.  If there are no items in the collection
                (i.e. no bits are set), then the print engine sub-
                system is ready.  If there is an item present, then the
                item indicates what is causing the print engine sub-
                system to be not ready.  cDoorOpen is in the collection
                if one or more access panels are open.  If the device
                contains more than one access panel, then NOT-READY-
                PRINT-ENGINE-DOOR indicates which access panel(s) are
                open.  cInternalMediaJam is in the collection if one or
                more pieces of media are jammed inside the device.  If
                the media is jammed at an input tray, cTrayMediaJam is
                in the collection, and if the device has more than one
                input tray, then NOT-READY-MEDIA-JAM-AT-TRAY indicates
                which tray has a media jam.  If the media is jammed at
                an output bin, cBinMediaJam is in the collection, and if
                the device has more than one output bin, then NOT-READY-
                MEDIA-JAM-AT-BIN indicates which bin has a media jam.
                cRequestedMediaUnavailable is in the collection if the
                current print job requires media that is not available.
                cTrayEmpty is in the collection if the current print job
                requires media from an input tray that is empty.  If the
                device has more than one input tray, then NOT-READY-
                TRAY-EMPTY indicates which tray is empty.
                cOutputBinFull is in the collection if an output bin is
                full.  If the device has more than one output bin, then
                NOT-READY-BIN-FULL indicates which bin is full.
                cManualFeedMedia is in the collection if the device is
                waiting for media to manually be fed.
                cMarkingAgentMissing is in the collection if a marking
                agent (toner cartridge, ink pen, etc.) is missing.  If
                the device has more than one marking agent, then NOT-
                READY-MARKING-AGENT-MISSING indicates which marking
                agent is missing.  cMarkingAgentOut is in the collection
                if the device is not ready due to one or more marking
                agents being low or out.  If the device has more than
                one marking agent, then NOT-READY-MARKING-AGENT-LOW-OR-
                OUT indicates which marking agent is low or out.
                cIncorrectMarkingAgent is in the collection if the
                device detects that an incorrect marking agent is
                installed.  If the device has more than one marking
                agent, then NOT-READY-INCORRECT-MARKING-AGENT indicates
                which marking agent location is loaded with the wrong
                type of marking agent.  cTrayMissing is in the
                collection if the device is not ready because one or
                more trays are not installed.  If the device has more
                than one input tray, then NOT-READY-TRAY-MISSING
                indicates which tray is missing.  cDeviceSpecific is in
                the collection if one or more items are in either NOT-
                READY-LASER-PRINT-ENGINE or NOT-READY-DESTINATION-
                INKJET-PRINT-ENGINE-NOT-READY.  cMediaPickMisfeed is in
                the collection if the print engine detects the tray is
                not empty, but can not pick up a sheet of media from
                that tray.  cMarkingAgentFailure indicates there is a
                failure with a marking agent and it may need to be
                replaced.  If the device supports more than one marking
                agent, then the NOT-READY-MARKING-AGENT-FAILURE object
                indicates all the marking agents that have failed.  The
                POS will indicate the marking agent failure recovery
                process, if any."
::= { status-prt-eng 1 }

override-media-name OBJECT-TYPE
    SYNTAX  DisplayString
    MAX-ACCESS read-write
    STATUS  current
    DESCRIPTION
                "Sets a string identifying the media name that is to be
                used in place of the currently requested media.  The
                substitution will continue until another media is
                selected.  If set to a named media that is not currently
                available the requested media is not overridden.
                Additional information:
                When a request is received to print on a size and
                type of media that is not currently available, this
                		      object contains the desired media name as set by the
                		      print job. This object should be set to a media name
                		      that is currently available in the printer.   If a
                		      paper mount request is not pending, attempting to get
                		      or set this object will cause
                		      <noSuchName> to be returned.
                		      Setting this object to a string other than one of the
                		      MEDIAn-NAME objects (MEDIA-NAMES-AVAILABLE is applied)
                		      will cause a status of <badValue>
                		      to be returned."
::= { settings-prt-eng 2 }

not-ready-laser-print-engine OBJECT-TYPE
    SYNTAX  OCTET STRING
    MAX-ACCESS read-only
    STATUS  current
    DESCRIPTION
                "Indicates if the laser print engine sub-system in the
                device is not ready.  If there are no items in the
                collection (i.e. no bits are set), then the laser print
                engine sub-system is ready.  If there is an item
                present, then the item indicates what is causing the
                laser print engine sub-system to be not ready."
::= { status-prt-eng 3 }

total-engine-page-count OBJECT-TYPE
    SYNTAX  INTEGER
    MAX-ACCESS read-write
    STATUS  current
    DESCRIPTION
                "Total number of pages printed by the device.  POS
                indicates if the total engine page count is kept in
                NVRAM, and the maximum supported value before the page
                count rolls over to zero.
                Additional information:
                This object is stored in NVRAM.  The maximum value of
                this count is 1000000 before it rolls over to zero."
::= { status-prt-eng 5 }


total-mono-page-count OBJECT-TYPE
    SYNTAX      INTEGER
    MAX-ACCESS read-write
    STATUS      current
       DESCRIPTION "Total number of black pages printed by the device.
                Additional information:
                Total number of mono pages printed by the device."
::= { status-prt-eng 6 }

total-color-page-count OBJECT-TYPE
    SYNTAX  INTEGER(0..4294967296)
    MAX-ACCESS read-only
    STATUS  current
    DESCRIPTION
                "Total number of color pages printed by the device.
                Additional information:
                Any page with one or more color pixels is counted as
                		a color page. Pages that only contain black marks are not
                		counted by this object.
                		The counter will roll over to zero after 4,294,967,296 pages.
                		Each side of a duplexed sheet of media will be counted
                		independently based on the criteria listed above."
::= { status-prt-eng 7 }

status-destination-print-engine OBJECT-TYPE
    SYNTAX  OCTET STRING
    MAX-ACCESS read-only
    STATUS  current
    DESCRIPTION
                "Indicates if part of the print engine sub-system is not
                functional, but the non-functional component(s) are not
                currently required to print."
::= { status-prt-eng 8 }

duplex-page-count OBJECT-TYPE
    SYNTAX  INTEGER
    MAX-ACCESS read-only
    STATUS  current
    DESCRIPTION
                "Total number of sheets of media that have been duplex
                printed.  A sheet is counted if it travels through the
                duplex page path, regardless of whether or not marks are
                made on the page.  The POS will indicate if the value is
                kept in NVRAM.
                Additional information:
                In LaserJet 4050 Series the count is kept in
                NVRAM however the NVRAM value is only updated every 10
                sheets.  NOTE: The value returned by this object will be
                incremented every sheet but if power is lost between
                NVRAM updates up to 9 sheets of the count may be
                lost.  The counter will be reset to zero
                after 16,777,215 (2^24-1) pages. "
::= { status-prt-eng 22 }

print-engine-revision OBJECT-TYPE
    SYNTAX  DisplayString (SIZE(1..16))
    MAX-ACCESS read-only
    STATUS  current
    DESCRIPTION
                "Print engine revision string.
                Additional information:
                The symbol set for this string is Roman-8. Converts
                engine revision number to a string and returns it."
::= { status-prt-eng 26 }

print-engine-jam-count OBJECT-TYPE
    SYNTAX  INTEGER
    MAX-ACCESS read-write
    STATUS  current
    DESCRIPTION
                "Total number of pages jammed in the print engine's life
               time. The POS indicates if the total jam count is kept in
               NVRAM and the maximum supported value before the jam count
               rolls over to zero.
                Additional information:
                This object is stored in NVRAM. The maximum value of
                this count is 65000 before it rolls over to zero."
::= { status-prt-eng 34 }


print-engine-mispick-count OBJECT-TYPE
    SYNTAX  INTEGER
    MAX-ACCESS read-write
    STATUS  current
    DESCRIPTION
                "Total number of pages mispicked in the print engine's life
               time. The POS indicates if the total mispick count is kept in
               NVRAM and the maximum supported value before the mispick count
               rolls over to zero.
                Additional information:
                This object is stored in NVRAM. The maximum value of
                this count is 65000 before it rolls over to zero."
::= { status-prt-eng 35 }


default-manual-feed OBJECT-TYPE
    SYNTAX  INTEGER {
		   eOff(1),
		   eOn(2)
		   }
    MAX-ACCESS read-write
    STATUS  current
    DESCRIPTION
                "Returns or changes the default manual feed value used by
                the PDLs."
::= { settings-intray 4 }

mp-tray OBJECT-TYPE
    SYNTAX  INTEGER {
		   eCassette(2),
		   eFirst(3)
		   }
    MAX-ACCESS read-write
    STATUS  current
    DESCRIPTION
                "Returns or changes the value of the multi-purpose (MP)
                tray configuration variable.  The MP tray can be
                configured to operate as an additional input tray
                (eCassette), a manual feed slot (eManual), or in a
                manner compatible with the LaserJet III manual feed slot
                (eFirst).  If configured for eFirst, if media is present
                in the MP tray, that media is used (assuming the size
                matches and the print job didn't specify another tray)
                until the MP tray is empty.
                Additional information:
                The MP tray can be configured for use either as a paper
                cassette or as a priority manual feed tray.  When the tray is configured as a manual feed tray, unsolicited status messages are not generated when there is no
                paper in the tray.  LaserJet 4050 Series will pull media from TRAY 1 only if there is
                a sheet present and it matches the needed size and type."
::= { settings-intray 5 }

tray-lock OBJECT-TYPE
    SYNTAX  OCTET STRING
    MAX-ACCESS read-write
    STATUS  current
    DESCRIPTION
                "Returns or changes the list of locked input trays.  The
                printer only pulls media from a locked input tray when
                the input tray is specifically requested by the print
                job.
                Additional information:
                The HP LaserJet 2100 Series will pull paper from a
                locked tray if that tray is specifically requested or if
                the user presses the Go button on a paper mount override
                and there is no paper available in an unlocked tray.

                There must always be at least one unlocked tray.  When
                no optional lower cassette is installed and one tray is
                locked, an attempt to lock the other tray will result in
                the first tray unlocking.  When the optional cassette is
                installed and two trays are locked, an attempt to lock
                the third will fail with a return status of
                <badValue> and a return value
                containing the collection of previously locked trays."
::= { settings-intray 6 }


custom-paper-dim-unit OBJECT-TYPE
    SYNTAX  INTEGER {
		   eTenThousandthsOfInches(3),
		   eMicrometers(4)
		   }
    MAX-ACCESS read-write
    STATUS  current
    DESCRIPTION
                "The units of measure used to specify the width and
                height of the printer's custom paper.  The unit of
                measure of eTenThousandthsOfInches is 0.0001 inches.
                Additional information:
                The only valid values for this object are
                eTenThousandthsOfInches (3), and eMicrometers (4).  The
                data for this object is stored in NVRAM."
::= { settings-intray 7 }

custom-paper-feed-dim OBJECT-TYPE
    SYNTAX  INTEGER
    MAX-ACCESS read-write
    STATUS  current
    DESCRIPTION
                "Sets the printer's custom paper dimension in the feed
                direction (direction parallel to the direction of paper
                feeding).  The value for this object is specified in
                micrometers or tenthousandths of an inch, depending upon
                the value of CUSTOM-PAPER-DIM-UNIT.  The valid range is
                engine-dependent and should be documented in the POS for
                each product.
                Additional information:
                The valid range for LaserJet 4000 Series is 50000 to 140000 if
                CUSTOM-PAPER-DIM-UNIT is eTenThousandthsOfInches or
                127000 to 355600 if CUSTOM-PAPER-DIM-UNIT is ePmicrometers.
                Attempts to set this object outside the valid range will result
                in a return value of <badValue>."
::= { settings-intray 8 }


custom-paper-xfeed-dim OBJECT-TYPE
    SYNTAX  INTEGER
    MAX-ACCESS read-write
    STATUS  current
    DESCRIPTION
                "Sets the printer's custom paper dimension in the cross-
                feed direction (direction ninety degrees relative to the
                direction of paper feeding).  The value for this object
                is specified in micrometers or tenthousandths of an
                inch, depending upon the value of CUSTOM-PAPER-DIM-UNIT.
                The valid range is engine-dependent and should be
                documented in the POS for each product.
                Additional information:
                The valid range for LaserJet 4000 Series is 30000 to 85000 if
                CUSTOM-PAPER-DIM-UNIT is eTenThousandthsOfInches or
                76200 to 215900 if CUSTOM-PAPER-DIM-UNIT is ePmicrometers.
                Attempts to set this object outside the valid range will result
                in a return value of <badValue>."
::= { settings-intray 9 }

not-ready-tray-missing OBJECT-TYPE
    SYNTAX  OCTET STRING
    MAX-ACCESS read-only
    STATUS  current
    DESCRIPTION
                "Indicates which trays are not currently installed that
                is caused the device to be not ready."
::= { status-intray 1 }


not-ready-tray-empty OBJECT-TYPE
    SYNTAX  OCTET STRING
    MAX-ACCESS read-only
    STATUS  current
    DESCRIPTION
                "Indicates which trays contain no media  causing the
                device to be not ready.  Some devices may treat tray
                missing as a tray empty condition."
::= { status-intray 2 }


status-tray-missing OBJECT-TYPE
    SYNTAX  OCTET STRING
    MAX-ACCESS read-only
    STATUS  current
    DESCRIPTION
                "Indicates which trays are not currently installed that
                is caused the device to be in a warning condition."
::= { status-intray 3 }


status-tray-empty OBJECT-TYPE
    SYNTAX  OCTET STRING
    MAX-ACCESS read-only
    STATUS  current
    DESCRIPTION
                "Indicates which trays contain no media causing the
                device to be in a warning condition.  Some devices may
                treat tray missing as a tray empty condition."
::= { status-intray 4 }

low-marking-agent-processing OBJECT-TYPE
    SYNTAX  INTEGER {
		   eStop(1),
		   eCont(2)
		   }
    MAX-ACCESS read-write
    STATUS  current
    DESCRIPTION
                "Returns or changes how the device processes a low
                marking agent event.  If eCont, then the device
                continues to print.  If eStop, then the device stops
                until a continue event occurs."
::= { settings-marking-agent 3 }


default-ret OBJECT-TYPE
    SYNTAX  INTEGER {
		   eOff(1),
		   eLight(2),
		   eMedium(3),
		   eDark(4)
		   }
    MAX-ACCESS read-write
    STATUS  current
    DESCRIPTION
                "Returns or changes the Resolution Enhancement Technology
                setting.  Devices that only support eOff and on should
                map all other values to on and always return the same
                non-eOff value to indicate on.  The list of supported
                values should be documented in the device POS.
                Additional information:
                Setting this object may cause a status of <noError> to be
                returned, but the new value will not take effect until a job
                boundary is reached. If a get is done on object before the job
                boundary is reached, the value last set will be returned.
                The value of this object is saved over a powercycle."
::= { imaging 5 }


default-print-quality OBJECT-TYPE
    SYNTAX  INTEGER(0..100)
    MAX-ACCESS read-write
    STATUS  current
    DESCRIPTION
                "Returns or sets the default print quality.  A value of
                zero has the lowest print quality.  A value of 100 has
                the highest print quality.  Each POS should document
                what values in the 0 to 100 range are supported.
                Additional information:
                In LaserJet 4050 Series, the supported values are 0 and
                100.  A value of zero has the lowest print
                quality(ECONOMODE=ON), thus minimizes the amount of
                toner used to print a page.  A value of 100 has the
                highest print quality (ECONOMODE=OFF), thus uses more
                toner to print a page.  Setting to an unsupported value
                outside of the 0 to 100 range causes the printer to
                return <badValue> status.
                Setting to an unsupported value inside of the 0 to
                100 range causes the printer to substitute in a snap
                value (listed below) and to return
                <noError> status.
                The snap values are as follow:
                0 to 50 snap to 0
                51 to 100 snap to 100"
::= { imaging 7 }


gdStatusLineState OBJECT-TYPE
    SYNTAX      Integer32 (0..255)
    MAX-ACCESS read-only
    STATUS      current
       DESCRIPTION "This describes the line state of the peripheral.
         When non-zero, the peripheral is off-line.  When
         zero the peripheral is on-line."
::= { gdStatusEntry 1 }


gdStatusPaperState OBJECT-TYPE
    SYNTAX      Integer32 (0..255)
    MAX-ACCESS read-only
    STATUS      current
       DESCRIPTION "This describes the state of the paper on the peripheral.
         When non-zero, the peripheral has a paper problem. When
         zero, the peripheral does not have a paper problem."
::= { gdStatusEntry 2 }


gdStatusInterventionState OBJECT-TYPE
    SYNTAX      Integer32 (0..255)
    MAX-ACCESS read-only
    STATUS      current
       DESCRIPTION "This describes the intervention state of the
         peripheral.  When non-zero, the peripheral requires
         human intervention to continue working.  When
         zero, it requires no assistance."
::= { gdStatusEntry 3 }

gdStatusNewMode OBJECT-TYPE
    SYNTAX  Integer32 (0..255)
    MAX-ACCESS  read-only
    STATUS  obsolete --
    DESCRIPTION
        "This indicates to which read channel state the
         card should move.  When non-zero, the card should
         indicate that the read channel is idle.  When zero,
         the card should indicate that the read channel is
         operating.  This object is Lan Manager io channel
         specific.  It is kept here for backward compatibility.

         Starting with firmware release X.20.06 and subsequent
         releases, this object is obsolete as it provides no
         relevant data for the new hardware architecture.
         No current supported applications use this object."
    ::={ gdStatusEntry 4 }

gdStatusConnectionTerminationAck OBJECT-TYPE
    SYNTAX  Integer32 (0..255)
    MAX-ACCESS  read-only
    STATUS  obsolete --
    DESCRIPTION
        "This indicates whether the peripheral is waiting for
         the Connection termination ACK.  When non-zero, it
         is waiting.  When zero, it is not waiting."
    ::={ gdStatusEntry 5 }

gdStatusPeripheralError OBJECT-TYPE
    SYNTAX      Integer32 (0..255)
    MAX-ACCESS read-only
    STATUS      current
       DESCRIPTION "This is the error code from the peripheral."
::= { gdStatusEntry 6 }


gdStatusPaperOut OBJECT-TYPE
    SYNTAX      Integer32
    MAX-ACCESS read-only
    STATUS      current
       DESCRIPTION "This indicates that the peripheral is out of paper.
                off (0),
                paper-out-or-paper-mount (1),
                manual-paper-feed-needed (2)
         For some peripherals, such as the HP LaserJet IIISi printer
         or HP DesignJet plotter, this value is always a zero (0)."
::= { gdStatusEntry 8 }


gdStatusPaperJam OBJECT-TYPE
    SYNTAX      Integer32
    MAX-ACCESS read-only
    STATUS      current
       DESCRIPTION "This indicates that the peripheral has a paper jam.
              off (0),
              paper-jam(1)
         For some peripherals, such as the HP LaserJet IIISi printer
         or HP DesignJet plotter, this value is always a zero (0)."
::= { gdStatusEntry 9 }


gdStatusTonerLow OBJECT-TYPE
    SYNTAX      Integer32
    MAX-ACCESS read-only
    STATUS      current
       DESCRIPTION "This indicates that the peripheral has a low toner condition.
              off (0),
              toner-low (1),
              no-toner-cartridge (2)
         For some peripherals, such as the HP LaserJet IIISi printer
         or HP DesignJet plotter, this value is always a zero (0)."
::= { gdStatusEntry 10 }


gdStatusPagePunt OBJECT-TYPE
    SYNTAX      Integer32 (0..255)
    MAX-ACCESS read-only
    STATUS      current
       DESCRIPTION "This indicates that the peripheral did not receive data fast
         enough to keep up with the print engine when generating a page.
         For some peripherals, such as the HP LaserJet IIISi printer
         or HP DesignJet plotter, this value is always a zero (0)."
::= { gdStatusEntry 11 }


gdStatusMemoryOut OBJECT-TYPE
    SYNTAX      Integer32 (0..255)
    MAX-ACCESS read-only
    STATUS      current
       DESCRIPTION "This indicates that the peripheral did not have enough memory
         to render an image on a page.
         For some peripherals, such as the HP LaserJet IIISi printer
         or HP DesignJet plotter, this value is always a zero (0)."
::= { gdStatusEntry 12 }


gdStatusIoActive OBJECT-TYPE
    SYNTAX      Integer32 (0..255)
    MAX-ACCESS read-only
    STATUS      current
       DESCRIPTION "This indicates that the peripheral is processing data from
         this I/O interface card. For some peripherals, such as the
         HP LaserJet IIISi printer or HP DesignJet plotter,
         this value is always a zero (0).

         For X.20.06 firmware and later firmware releases, this object is
         not relevant. In order not to break legacy applications which call this
         object in multi-varbind requests, this value is always zero (0)."
::= { gdStatusEntry 13 }


gdStatusBusy OBJECT-TYPE
    SYNTAX      Integer32 (0..255)
    MAX-ACCESS read-only
    STATUS      current
       DESCRIPTION "This indicates that the peripheral is busy processing
         print/plot data.
         For some peripherals, such as the HP LaserJet IIISi printer
         or HP DesignJet plotter, this value is always a zero (0)."
::= { gdStatusEntry 14 }


gdStatusWait OBJECT-TYPE
    SYNTAX      Integer32 (0..255)
    MAX-ACCESS read-only
    STATUS      current
       DESCRIPTION "This indicates that the peripheral is waiting for print/plot
         data to process.
         For some peripherals, such as the HP LaserJet IIISi printer
         or HP DesignJet plotter, this value is always a zero (0)."
::= { gdStatusEntry 15 }


gdStatusInitialize OBJECT-TYPE
    SYNTAX      Integer32
    MAX-ACCESS read-only
    STATUS      current
       DESCRIPTION "This indicates that the peripheral is initializing or
         warming up.
              off (0),
              initializing (1),
              warm-up(2)
         For some peripherals, such as the HP LaserJet IIISi printer
         or HP DesignJet plotter, this value is always a zero (0)."
::= { gdStatusEntry 16 }


gdStatusDoorOpen OBJECT-TYPE
    SYNTAX      Integer32 (0..255)
    MAX-ACCESS read-only
    STATUS      current
       DESCRIPTION "This indicates that the peripheral cover or door is open.
         For some peripherals, such as the HP LaserJet IIISi printer
         or HP DesignJet plotter, this value is always a zero (0)."
::= { gdStatusEntry 17 }


gdStatusPrinting OBJECT-TYPE
    SYNTAX      Integer32
    MAX-ACCESS read-only
    STATUS      current
       DESCRIPTION "This indicates that the peripheral is printing or otherwise
         marking or moving paper.
              off (0),
              ordinary-page (1),
              test-fonts-config-or-start-page (2)
         For some peripherals, such as the HP LaserJet IIISi printer
         or HP DesignJet plotter, this value is always a zero (0)."
::= { gdStatusEntry 18 }


gdStatusPaperOutput OBJECT-TYPE
    SYNTAX      Integer32
    MAX-ACCESS read-only
    STATUS      current
       DESCRIPTION "This indicates that the peripheral has a paper output problem
         such as the output storage bin being full.
              off (0),
              output-storage-full (1)
         For some peripherals, such as the HP LaserJet IIISi printer
         or HP DesignJet plotter, this value is always a zero (0)."
::= { gdStatusEntry 19 }

gdStatusReserved OBJECT-TYPE
    SYNTAX  OCTET STRING (SIZE (0..13))
    MAX-ACCESS  read-only
    STATUS  obsolete --
    DESCRIPTION
        "This is the reserved area that is not currently
         used, but will allow for growth within the gdStatusEntry table."
    ::={ gdStatusEntry 20 }

gdStatusNovBusy OBJECT-TYPE
    SYNTAX  Integer32 (0..255)
    MAX-ACCESS  read-only
    STATUS  obsolete --
    DESCRIPTION
        "This indicates if this channel is active.  If the
         value is 0 then this channel is active or the peripheral
         is idle.  If this value is non-zero then another channel
         is active.  This is the Novell io channel"
    ::={ gdStatusEntry 21 }

gdStatusLlcBusy OBJECT-TYPE
    SYNTAX  Integer32 (0..255)
    MAX-ACCESS  read-only
    STATUS  obsolete --
    DESCRIPTION
        "This indicates if this channel is active.  If the
         value is 0 then this channel is active or the peripheral
         is idle.  If this value is non-zero then another channel
         is active.  This is the LLC io channel"
    ::={ gdStatusEntry 22 }

gdStatusTcpBusy OBJECT-TYPE
    SYNTAX  Integer32 (0..255)
    MAX-ACCESS  read-only
    STATUS  obsolete --
    DESCRIPTION
        "This indicates if this channel is active.  If the
         value is 0 then this channel is active or the peripheral
         is idle.  If this value is non-zero then another channel
         is active.  This is the TCP io channel"
    ::={ gdStatusEntry 23 }

gdStatusAtBusy OBJECT-TYPE
    SYNTAX  Integer32 (0..255)
    MAX-ACCESS  read-only
    STATUS  obsolete --
    DESCRIPTION
        "This indicates if this channel is active.  If the
         value is 0 then this channel is active or the peripheral
         is idle.  If this value is non-zero then another channel
         is active.  This is the Apple talk io channel"
    ::={ gdStatusEntry 24 }


gdStatusBytes OBJECT-TYPE
    SYNTAX      Integer32
    MAX-ACCESS read-only
    STATUS      current
    DESCRIPTION "The number of valid bytes in the gdStatusEntry
                array."
::= { generalDeviceStatus 1 }

gdStatusDisplay OBJECT-TYPE
    SYNTAX  DisplayString
    MAX-ACCESS  read-only
    STATUS  current --
    DESCRIPTION
        "The string diplayed on the peripheral front panel.
         For some peripherals, such as the HP LaserJet IIISi printer
         or HP DesignJet plotter, this is always a zero length string."
    ::={ generalDeviceStatus 3 }

gdStatusJobName OBJECT-TYPE
    SYNTAX  DisplayString
    MAX-ACCESS  read-only
    STATUS  current --
    DESCRIPTION
        "The current job name set by the peripheral.
         For some peripherals, such as the HP LaserJet IIISi printer
         or HP DesignJet plotter, this is always a zero length string."
    ::={ generalDeviceStatus 4 }

gdStatusSource OBJECT-TYPE
    SYNTAX  DisplayString
    MAX-ACCESS  read-only
    STATUS  current --
    DESCRIPTION
        "A string indicating the name of the physical port or protocol
         the printer is currently getting data from."
    ::={ generalDeviceStatus 5 }

gdStatusPapstatus OBJECT-TYPE
    SYNTAX  DisplayString
    MAX-ACCESS  read-only
    STATUS  current --
    DESCRIPTION
        "A string indicating the Appletalk papstatus response."
    ::={ generalDeviceStatus 6 }

gdStatusId OBJECT-TYPE
    SYNTAX  DisplayString
    MAX-ACCESS  read-only
    STATUS  current --
    DESCRIPTION
        "A formatted string describing this peripheral."
    ::={ generalDeviceStatus 7 }

gdStatusDisplayCode OBJECT-TYPE
    SYNTAX  Integer32
    MAX-ACCESS  read-only
    STATUS  obsolete --
    DESCRIPTION
        "This is the display code that the peripheral uses
         to tell the card what type of display the front
         panel of the printer is.

         Starting with firmware release X.20.06 and subsequent
         releases, this object is obsolete as it provides no
         relevant data for the new hardware architecture.
         No current supported applications use this object."
    ::={ generalDeviceStatus 8 }

gdStatusNlsCode OBJECT-TYPE
    SYNTAX  Integer32
    MAX-ACCESS  read-only
    STATUS  current --
    DESCRIPTION
        "This value is the representation of what native
         language the printer is in currently."
    ::={ generalDeviceStatus 9 }

gdStatusJobTimeout OBJECT-TYPE
    SYNTAX  Integer32
    MAX-ACCESS  read-write
    STATUS  obsolete --
    DESCRIPTION
        "This value represents (in seconds) the maximum time of
         inactivity which must elapse before the JetDirect card
         switches from the current network protocol to another when
         a normal end of job is not detected."
    ::={ generalDeviceStatus 10 }

gdStatusPjlUstatus OBJECT-TYPE
    SYNTAX  Integer32
    MAX-ACCESS  read-write
    STATUS  obsolete --
    DESCRIPTION
        "This object will enable/disable PJL ustatus.
                  disabled (0),
                  enabled (1)"
    ::={ generalDeviceStatus 11 }

gdStatusLaaSupport OBJECT-TYPE
    SYNTAX  Integer32
    MAX-ACCESS  read-write
    STATUS  current --
    DESCRIPTION
        "This value represents what protocols Locally Administered
         addressing is supported over.  This is currently 0 for
         802.3 cards and 7 for 802.5 cards.  LAA is not supported
         on 802.3.  The value is a mask of bits, 1 for each of the
         protocols below.
         +-----------------------------------------------+
         | NA  | NA  | NA  | NA  | NA  | TCP | LLC | NOV |
         +-----------------------------------------------+"
    ::={ generalDeviceStatus 12 }


gdPasswords OBJECT-TYPE
    SYNTAX  OCTET STRING (SIZE (0..255))
    MAX-ACCESS  read-write
    STATUS  current --
    DESCRIPTION
        "This object is used as a 256 byte NVRAM area for JetAdmin.  It
         is completely managed by JetAdmin.  Initially it is initialized
         to all zeros.  A coldboot will re-initialize to all zeros."
    ::={ generalDeviceStatus 13 }

gdStatusAtPrinterName OBJECT-TYPE
    SYNTAX  OCTET STRING (SIZE(0..255))
    MAX-ACCESS  read-write
    STATUS  current --
    DESCRIPTION
        "The AppleTalk name of the printer."
    ::={ generalDeviceStatus 18 }

gdStatusAtPrinterType OBJECT-TYPE
    SYNTAX  OCTET STRING (SIZE(0..255))
    MAX-ACCESS  read-only
    STATUS  obsolete --
    DESCRIPTION
        "The AppleTalk type of the printer."
    ::={ generalDeviceStatus 19 }

photo-access-card-error OBJECT-TYPE
    SYNTAX      INTEGER {
                          ePhotoCardAccessNoError(0),
                          ePhotoCardSmartMediaUpsideDown(1),
                          ePhotoCardMediaNotFullyInserted(2),
                          ePhotoCardMoreThenOneInSlots(3),
                          ePhotoCardReadError(4),
                          ePhotoCardRemovedWhileReading(5),
                          ePhotoCardBadFileWhilePrinting(6),
                          ePhotoCardNotInSlot(7),
                          ePhotoCardContainsNoPhotos(8),
                          ePhotoCardWriteError(9),
                          ePhotoCardRemovedWhileWriting(10),
                          ePhotoCardUnknownError(999)
		   }
    MAX-ACCESS read-only
    STATUS      current
       DESCRIPTION "Specifies the error reason for most recent unsucessful photo
		card access.
                Additional information:
                Specifies the error reason for most recent unsucessful photo
                card access."
::= { photo-job 2 }


photo-default-num-copies OBJECT-TYPE
    SYNTAX      INTEGER(1..99)
    MAX-ACCESS read-write
    STATUS      current
       DESCRIPTION "Reads or writes the default number of copies to be printed
		during photo application print jobs. This value is saved over a
		power cycle.
                Additional information:
                Reads or writes the default number of copies to be
                printed during photo application print jobs.  This value is
                saved over a power cycle."
::= { settings-photo-job 1 }


photo-job-num-copies OBJECT-TYPE
    SYNTAX      INTEGER(1..99)
    MAX-ACCESS read-write
    STATUS      current
       DESCRIPTION "Reads or writes the number of copies to be printed during the
		next photo application print job. This value is not saved over
		power cycles.
                Additional information:
                Reads or writes the number of copies to be printed
                during the next photo application print job.  This value is
                not saved over a power cycle."
::= { settings-photo-job 2 }


photo-job-media-size OBJECT-TYPE
    SYNTAX      INTEGER {
                          eUSLetter(2),
                          eISOandJISA4(26),
                          ePhoto4x6(76)
		   }
    MAX-ACCESS read-write
    STATUS      current
       DESCRIPTION "Reads or writes the default media size to be used during the
		next photo application print job. This value is not saved over
		power cycles.
                Additional information:
                Reads or writes the default media size to be
                used during the next photo application print job.  This
                value is not saved over a power cycle."
::= { settings-photo-job 4 }


photo-job-media-name OBJECT-TYPE
    SYNTAX      DisplayString
    MAX-ACCESS read-write
    STATUS      current
       DESCRIPTION "Reads or writes the media type to be used on the next photo
		application print job. This value is not saved over power
		cycles.
                Additional information:
                Reads or writes the media type to be used on the next
                photo application print job. This value is not saved over a
                power cycle."
::= { settings-photo-job 6 }


photo-image-size OBJECT-TYPE
    SYNTAX      INTEGER {
                          eThumbnail(1),
                          eWallet(2),
                          e3halfx5in(3),
                          e3x4in(4),
                          e4x6in(5),
                          e5x7in(6),
                          e6x8in(7),
                          e8x10in(8),
                          e6x8cm(9),
                          e7x10cm(10),
                          e9x13cm(11),
                          e10x15cm(12),
                          e13x18cm(13),
                          e15x21cm(14),
                          e18x24cm(15),
                          e20x25cm(16),
                          eFullPage(17),
                          ePanoramic(18)
		   }
    MAX-ACCESS read-write
    STATUS      current
       DESCRIPTION "Reads or writes the default image size to be used during photo
		application print jobs. This value is saved over power cycles.
                Additional information:
                Reads or writes the default image size to be
                used during photo application print jobs. This value is
                saved over a power cycle. Valid image sizes are determined
                by the PHOTO-IMAGE-SIZE-SET pml object."
::= { settings-photo-job 7 }


photo-job-image-size OBJECT-TYPE
    SYNTAX      INTEGER {
                          eThumbnail(1),
                          eWallet(2),
                          e3halfx5in(3),
                          e3x4in(4),
                          e4x6in(5),
                          e5x7in(6),
                          e6x8in(7),
                          e8x10in(8),
                          e6x8cm(9),
                          e7x10cm(10),
                          e9x13cm(11),
                          e10x15cm(12),
                          e13x18cm(13),
                          e15x21cm(14),
                          e18x24cm(15),
                          e20x25cm(16),
                          eFullPage(17),
                          ePanoramic(18)
		   }
    MAX-ACCESS read-write
    STATUS      current
       DESCRIPTION "Reads or writes the image size to be used during the next photo
		application print job. This value is not saved over power
		cycles.
                Additional information:
                Reads or writes the image size to be used during
                the next photo application print job. This value is not
                saved over a power cycle. Valid image sizes are determined
                by the PHOTO-IMAGE-SIZE-SET pml object."
::= { settings-photo-job 8 }


photo-select-images OBJECT-TYPE
    SYNTAX      OCTET STRING
    MAX-ACCESS read-write
    STATUS      current
       DESCRIPTION "Reads or writes the list of images to print during the next
		photo application print job. Each image number or number range
		must be separated by a comma. The image number corresponds to
		the location of the file on the image card. For example, if
		there are 10 images on the photo card, then you could select
		'1-10' or '1,2,3,4,5' or '1,2,3,4-9'. The same image number can
		also appear multiple times in the list. i.e.
		'1,2,2,2,3,3,4,4,5'. This value is not saved over power cycles
		and only applies to the next job.
                Additional information:
                Reads or writes the list of images to print
                during the next photo application print job. Each image
                number or number range must be separated by a comma.  The
                image number corresponds to the location of the file on
                the image card.  For example, if there are 10 images on
                the photo card, then you could select 1-10 or 1,2,3,4,5 or
                1,2,3,4-9.  The same image number can also appear multiple
                times in the list. i.e. 1,2,2,2,3,3,4,4,5.  This value is
                not saved over a power cycle, and only applies to the next
                job."
::= { settings-photo-job 9 }


photo-images-on-card OBJECT-TYPE
    SYNTAX      INTEGER
    MAX-ACCESS read-only
    STATUS      current
       DESCRIPTION "Reads the number of printable photo images found on the
		inserted memory card. If 0, then no images were found, or the
		card was not properly inserted.
                Additional information:
                Reads the number of printable photo images found
                on the inserted memory card.  If 0, then no images were
                found, or the card was not properly inserted."
::= { settings-photo-job 10 }


photo-job-source OBJECT-TYPE
    SYNTAX      INTEGER {
                          ePhotoPrintProofSheet(1),
                          ePhotoScanProofSheet(2),
                          ePhotoPrintColorJob(3),
                          ePhotoPrintMonochromeJob(4),
                          ePhotoPrintIndexPrint(5)
		   }
    MAX-ACCESS read-write
    STATUS      current
       DESCRIPTION "Controls initiating photo application features.
                Additional information:
                Controls initiating photo application features."
::= { settings-photo-job 11 }


photo-color-page-count OBJECT-TYPE
    SYNTAX      INTEGER
    MAX-ACCESS read-write
    STATUS      current
       DESCRIPTION "Reads or writes the page count for color pages printed by the
		photo application. This value is saved over power cycles.
                Additional information:
                Reads or writes the page count for color pages
                printed by the photo application. This value is saved over
                a power cycle."
::= { settings-photo-job 12 }


photo-mono-page-count OBJECT-TYPE
    SYNTAX      INTEGER
    MAX-ACCESS read-write
    STATUS      current
       DESCRIPTION "Reads or writes the page count for monochrome pages printed by
		the photo application. This value is saved over power cycles.
                Additional information:
                Reads or writes the page count for monochrome pages
                printed by the photo application. This value is saved over
                a power cycle."
::= { settings-photo-job 13 }


photo-image-size-set OBJECT-TYPE
    SYNTAX      INTEGER {
                          eImageSizeSetInch1(1),
                          eImageSizeSetInch2(2),
                          eImageSizeSetCentimeter1(3),
                          eImageSizeSetCentimeter2(4),
                          eImageSizeSetCentimeter3(5)
		   }
    MAX-ACCESS read-write
    STATUS      current
       DESCRIPTION "This is only writable in service mode. This object changes the
		set of valid image sizes for the device. The image sizes groups
		are as follows:
		    eImageSizeSetInch1: Wallet, 3x4in, 3 1/2 x 5in, 4x6in,
			5x7in, 8x10in, full page
		    eImageSizeSetInch2: Wallet, 3 1/2 x 5in, 4x6in, 5x7in,
			6x8in, 8x10in, full page
		    eImageSizeSetCentimeter1: 6x8cm, 7x10cm, 9x13cm, 10x15cm,
			13x18cm, 15x21cm, 20x25cm, full page
		    eImageSizeSetCentimeter2: 7x10cm, 9x13cm, 10x15cm, 13x18cm,
			20x25cm, full page
		eImageSizeSetCentimeter3: 6x8cm, 9x13cm, 10x15cm, 13x18cm,
		15x21cm, 18x24cm, 20x25cm, full page   .
                Additional information:
                This is only writable in service mode.  This object
                changes the set of valid image sizes for the device.  The image
                sizes groups are as follows:
                eImageSizeSetInch1:  Thumbnail, Wallet, 3x4in, 3 1/2 x 5in, 4x6in,
                5x7in, 8x10in, full page, panorama
                eImageSizeSetInch2:  Thumbnail, Wallet, 3 1/2 x 5in, 4x6in, 5x7in,
                6x8in, 8x10in, full page, panorama
                eImageSizeSetCentimeter1:  Thumbnail, 6x8cm, 7x10cm, 9x13cm, 10x15cm,
                13x18cm, 15x21cm, 20x25cm, full page, panorama
                eImageSizeSetCentimeter2:  Thumbnail, 7x10cm, 9x13cm, 10x15cm, 13x18cm,
                20x25cm, full page, panorama
                eImageSizeSetCentimeter3:  Thumbnail, 6x8cm, 9x13cm, 10x15cm, 13x18cm,
                15x21cm, 18x24cm, 20x25cm, full page, panorama"
::= { settings-photo-job 15 }


photo-clear-counts OBJECT-TYPE
    SYNTAX      INTEGER {
                          eClearPageCounts(1),
                          eClearInsertCounts(2),
                          eClearAllCounts(3)
		   }
    MAX-ACCESS read-write
    STATUS      current
       DESCRIPTION "writing this object causes the page counts, insert counts, or
		all photo counts to be cleared and reset to 0.
                Additional information:
                writing this object causes the page counts, insert counts, or all photo counts
                to be cleared and reset to 0."
::= { settings-photo-job 18 }


photo-compact-flash-insert-count OBJECT-TYPE
    SYNTAX      INTEGER
    MAX-ACCESS read-write
    STATUS      current
       DESCRIPTION "Reads or writes the count for the number of times a compact
		flash memory card has been inserted in the device. This value
		is saved over a power cycle.
                Additional information:
                reads or writes the count for the number of times a compact flash memory card
                has been inserted in the device.  This value is saved over a power cycle."
::= { settings-photo-job 19 }


photo-memory-stick-insert-count OBJECT-TYPE
    SYNTAX      INTEGER
    MAX-ACCESS read-write
    STATUS      current
       DESCRIPTION "Reads or writes the count for the number of times a memory
		stick memory card has been inserted in the device. This value
		is saved over a power cycle.
                Additional information:
                reads or writes the count for the number of times a memory stick memory card
                has been inserted in the device.  This value is saved over a power cycle."
::= { settings-photo-job 20 }


photo-memory-stick-pro-insert-count OBJECT-TYPE
    SYNTAX      INTEGER
    MAX-ACCESS read-write
    STATUS      current
       DESCRIPTION "Reads or writes the count for the number of times a memory
		stick pro memory card has been inserted in the device. This
		value is saved over a power cycle.
                Additional information:
                reads or writes the count for the number of times a memory stick pro memory card
                has been inserted in the device.  This value is saved over a power cycle."
::= { settings-photo-job 21 }


photo-smart-media-insert-count OBJECT-TYPE
    SYNTAX      INTEGER
    MAX-ACCESS read-write
    STATUS      current
       DESCRIPTION "Reads or writes the count for the number of times a smart media
		memory card has been inserted in the device. This value is
		saved over a power cycle.
                Additional information:
                reads or writes the count for the number of times a compact flash memory card
                has been inserted in the device.  This value is saved over a power cycle."
::= { settings-photo-job 22 }


photo-secure-digital-insert-count OBJECT-TYPE
    SYNTAX      INTEGER
    MAX-ACCESS read-write
    STATUS      current
       DESCRIPTION "Reads or writes the count for the number of times a secure
		digital memory card has been inserted in the device. This value
		is saved over a power cycle.
                Additional information:
                reads or writes the count for the number of times a compact flash memory card
                has been inserted in the device.  This value is saved over a power cycle."
::= { settings-photo-job 23 }


photo-mmc-insert-count OBJECT-TYPE
    SYNTAX      INTEGER
    MAX-ACCESS read-write
    STATUS      current
       DESCRIPTION "Reads or writes the count for the number of times a
		MultiMediaCard memory card has been inserted in the device.
		This value is saved over a power cycle.
                Additional information:
                reads or writes the count for the number of times a MultiMediaCard memory card
                has been inserted in the device.  This value is saved over a power cycle."
::= { settings-photo-job 24 }


photo-xd-insert-count OBJECT-TYPE
    SYNTAX      INTEGER
    MAX-ACCESS read-write
    STATUS      current
       DESCRIPTION "Reads or writes the count for the number of times an xD-Picture
		memory card has been inserted in the device. This value is
		saved over a power cycle.
                Additional information:
                reads or writes the count for the number of times an xD-Picture memory card
                has been inserted in the device.  This value is saved over a power cycle."
::= { settings-photo-job 25 }


hrstorageindex OBJECT-TYPE
    SYNTAX  INTEGER(1..2147483647)
    MAX-ACCESS read-only
    STATUS  current
    DESCRIPTION
                "A unique value for each logical storage area
              contained by the host.
              Refer to RFC 1514, Host Resources MIB, for more details.
              Additional information (mass storage) :
              Constant.  The index is assigned by the
              person controlling the printer object definition.
              The value of the hrFileSystemStorageIndex and the
              index of the prtStorageRefIndex use the value of
              this object's index.  The value of the object
              matches the value of the object's index.  Returns
              <noSuchName> status if attempting
              to perform a get on this OID with no mass storage device
              installed.  This first volume installed will be number 2,
              followed by the second.  IDE will always be 2.  If ram disk
              and flash disk are installed then Flash disk will be 2 followed
              by ram disk.  The Storage types are:
              IDE (EIO DISK), Flash Disk, Ram Disk"
::= { hrStorageEntry 1 }


hrstoragetype OBJECT-TYPE
    SYNTAX  OBJECT IDENTIFIER
    MAX-ACCESS read-only
    STATUS  current
    DESCRIPTION
                "The type of storage represented by this entry.
              Refer to RFC 1514, Host Resources MIB, for more details.
                Additional information (mass storage):
                 Constant.  Returns
                 <noSuchName> status if attempting
                 to perform a Get on this OID with no mass storage device
                 installed.
                 HRMhrStorageFixedDisk is 1.3.6.1.2.1.25.2.1.4"
::= { hrStorageEntry 2 }


hrstoragedescr OBJECT-TYPE
    SYNTAX  OCTET STRING
    MAX-ACCESS read-only
    STATUS  current
    DESCRIPTION
                "A description of the type and instance of the
              storage described by this entry.
              Refer to RFC 1514, Host Resources MIB, for more details.
                Additional information (printer) :
                This object is not localized.
                Additional information (mass storage) :
                This string indicates the location of the installed
                mass storage device.  The supported values are:
                'Flash disk in DIMM slot 1'
                'Flash disk in DIMM slot 2'
                'Flash disk in DIMM slot 3'
                              'Disk in EIO 1'
                              'Disk in EIO 2'
                              'Disk in EIO 3'
                              'Static RAM disk using system memory'
                 Applications determine the location of the installed mass storage
                 device by getting this object.  This string is not
                 localized.  Returns <noSuchName>
                 status if attempting to perform a Get on this OID
                 with no mass storage device installed."
::= { hrStorageEntry 3 }


hrstorageallocationunits OBJECT-TYPE
    SYNTAX  INTEGER(1..2147483647)
    MAX-ACCESS read-only
    STATUS  current
    DESCRIPTION
                "The size, in bytes, of the data objects allocated
               from this pool.  If this entry is monitoring
               sectors, blocks, buffers, or packets, for example,
               this number will commonly be greater than one.
               Otherwise this number will typically be one.
               Refer to RFC 1514, Host Resources MIB, for more details.
                Additional information (printer) :
                Unit is one byte.
                Additional information (mass storage) :
                Returns the value 1024 if the file system is
                not initialized.  Returns <noSuchName>
                status if attempting to perform a Get on this OID
                with no mass storage device installed."
::= { hrStorageEntry 4 }


hrstorageused OBJECT-TYPE
    SYNTAX  INTEGER(0..2147483647)
    MAX-ACCESS read-only
    STATUS  current
    DESCRIPTION
                "The amount of the storage represented by this
              entry that is allocated, in units of
              hrStorageAllocationUnits.
              Refer to RFC 1514, Host Resources MIB, for more details.
                Additional information:
                This object returns the amount of memory in use
                by the printer at the current time.  This object should not be
                used when creating a print
                job for the device because the amount of memory in use will
                likely be different when the printer processes the print job.
                Additional information (mass storage) :
                Applications can determine the amount of used
                space on the installed mass storage device by getting the
                hrStorageAllocationUnits object and this object.  The amount
                of used space is these two returned values multiplied
                together.  Returns the value 0 if the file system
                is not initialized.  Returns <noSuchName>
                status if attempting to perform a Get on this OID
                with no mass storage device installed."
::= { hrStorageEntry 6 }


hrstorageallocationfailures OBJECT-TYPE
    SYNTAX  INTEGER
    MAX-ACCESS read-only
    STATUS  current
    DESCRIPTION
                "The number of requests for storage represented by
              this entry that could not be honored due to not
              enough storage.  It should be noted that as this
              object has a SYNTAX of Counter, that it does not
              have a defined initial value.  However, it is
              recommended that this object be initialized to
              zero.
              Refer to RFC 1514, Host Resources MIB, for more details.
                Additional information (printer):
                This object is set to zero at power on and when any
                reset is done via prtGeneralReset.
                This object is incremented whenever the printer is
                short on memory (codewise: when PersMemoryCycle is
                called with a parameter of 2).
                Additional information (mass storage):
                Total number of writes that failed
                since power on) due to the mass storage device
                being full.  Returns the value 0 when the file
                system has not been initialized.  Returns
                <noSuchName> status if attempting
                to perform a Get on this OID with no mass storage device
                installed."
::= { hrStorageEntry 7 }


hrdeviceindex OBJECT-TYPE
    SYNTAX  INTEGER(1..2147483647)
    MAX-ACCESS read-only
    STATUS  current
    DESCRIPTION
                "A unique value for each device contained by the
              host.  The value for each device must remain
              constant at least from one re-initialization of the
              agent to the next re-initialization.
              Refer to RFC 1514, Host Resources MIB, for more details.
                Additional information (printer):
                The entry in the Device Table which
                describes the printer.
                Additional information (mass storage):
                Constant.  The index is assigned by the
                person controlling the printer object definition.
                All device/mass storage/file system/partition
                tables in Host Resources MIB and the Printer MIB that
                relate to the mass storage device use the same index value.
                 The value of the index of the following objects is
                    this object's value:
                    prtDeviceRefIndex
                    hrDiskStorageIndex
                    hrPartitionIndex
                    hrFSIndex
                    The value of the object matches the value of the
                    object's index. Returns
                    <noSuchName> status if attempting
                    to perform a Get on this OID with no mass storage device
                    installed."

::= { hrDeviceEntry 1 }


hrdevicetype OBJECT-TYPE
    SYNTAX  OBJECT IDENTIFIER
    MAX-ACCESS read-only
    STATUS  current
    DESCRIPTION
                "An indication of the type of device.
              If this value is `hrDeviceProcessor { hrDeviceTypes
              3 }' then an entry exists in the hrProcessorTable
              which corresponds to this device.
              If this value is `hrDeviceNetwork { hrDeviceTypes 4
              }', then an entry exists in the hrNetworkTable
              which corresponds to this device.
              If this value is `hrDevicePrinter { hrDeviceTypes 5
              }', then an entry exists in the hrPrinterTable
              which corresponds to this device.
              If this value is `hrDeviceDiskStorage {
              hrDeviceTypes 6 }', then an entry exists in the
              hrDiskStorageTable which corresponds to this
              device.
              Refer to RFC 1514, Host Resources MIB, for more details.
               Additional information (mass storage):
               Constant.  Applications should determine if
               a mass storage device is installed by getting this object.
               If the response is something other than HRMhrDeviceDiskStorage,
               the application knows this row in the hrDeviceTable does not
               refer to a mass storage object.  Due to restrictions placed on
               this object by the Host Resources Disk Table, the value of this
               object must be HRMhrDeviceDiskStorge.  Returns
               <noSuchName> status if attempting
               to perform a Get on this OID with no mass storage device
               installed. HRMhrDeviceDiskStorage is 1.3.6.1.2.1.25.3.1.6"
::= { hrDeviceEntry 2 }


hrdevicestatus OBJECT-TYPE
    SYNTAX  INTEGER {
		   eHrunning(2),
		   eHwarning(3),
		   eHdown(5)
		   }
    MAX-ACCESS read-only
    STATUS  current
    DESCRIPTION
                "The current operational state of the device
              described by this row of the table.  A value
              unknown(1) indicates that the current state of the
              device is unknown.  running(2) indicates that the
              device is up and running and that no unusual error
              conditions are known.  The warning(3) state
              indicates that agent has been informed of an
              unusual error condition by the operational software
              (e.g., a disk device driver) but that the device is
              still 'operational'.  An example would be high
              number of soft errors on a disk.  A value of
              testing(4), indicates that the device is not
              available for use because it is in the testing
              state.  The state of down(5) is used only when the
              agent has been informed that the device is not
              available for any use.
              Refer to RFC 1514, Host Resources MIB, for more details.
                Additional information (printer) :
                The printer's condition is mapped as follows (printer):

                eHrunning -- Printer ready to print or is printing.  May be in power save
                mode.

                eHwarning -- A condition exists that needs attention but it is
                not currently preventing printing. A non-critical alert is active.

                eHdown -- Printer is not printing because it is offline or a critical
                alert is active.  Human interaction is needed to bring the printer to
                a ready state.
                Additional information (mass storage) :
                Returns mass storage device status information.
                running -- mass storage device functional.  May be in power save
                mode.
                warning -- The mass storage device failed a self-test but completed
                the power-on initialization sequence.  The mass storage device
                is readable even when the mass storage device fails the power-up
                self-test in order to give the customer a chance to
                retrieve any data that can be made available.
                testing -- Mass storage device is executing a test.
                down -- Mass storage device is non-functional. Returns
                <noSuchName> status if attempting
                to perform a Get on this OID with no mass storage device
                installed."
::= { hrDeviceEntry 5 }


hrprinterstatus OBJECT-TYPE
    SYNTAX  INTEGER {
		   eHother(1),
		   eHidle(3),
		   eHprinting(4),
		   eHwarmup(5)
		   }
    MAX-ACCESS read-only
    STATUS  current
    DESCRIPTION
                "The current status of this printer device.  When
               in the idle(1), printing(2), or warmup(3) state,
               the corresponding hrDeviceStatus should be
               running(2) or warning(3).  When in the unknown
               state, the corresponding hrDeviceStatus should be
               unknown(1).
               Refer to RFC 1514, Host Resources MIB, for more details.
                Additional information:
                The printer's condition is mapped as follows:

                eHother -- The printer is offline or a critical alert is active.

                eHidle -- The printer is not doing any of the items listed below
                for eHprinting status.

                eHprinting -- A job is currently being processed or printed or a PJL job
                is being processed.

                eHwarmup -- If hrDeviceStatus is eHdown, then the printer is currently
                offline but is resolving the condition that caused it be offline.
                If hrDeviceStatus is eHrunning, then the printer was in power save mode
                and is now ready ready to print."
::= { hrPrinterEntry 1 }


hrprinterdetectederrorstate OBJECT-TYPE
    SYNTAX  OCTET STRING
    MAX-ACCESS read-only
    STATUS  current
    DESCRIPTION
                "This object represents any error conditions
               detected by the printer.  The error conditions are
               encoded as bits in an octet string, with the
               following definitions:
                    Condition         Bit #    hrDeviceStatus
                    lowPaper          0        warning(3)
                    noPaper           1        down(5)
                    lowToner          2        warning(3)
                    noToner           3        down(5)
                    doorOpen          4        down(5)
                    jammed            5        down(5)
                    offline           6        down(5)
                    serviceRequested  7        warning(3)
               If multiple conditions are currently detected and
               the hrDeviceStatus would not otherwise be
               unknown(1) or testing(4), the hrDeviceStatus shall
               correspond to the worst state of those indicated,
               where down(5) is worse than warning(3) which is
               worse than running(2).
               Bits are numbered starting with the most
               significant bit of the first byte being bit 0, the
               least significant bit of the first byte being bit
               7, the most significant bit of the second byte
               being bit 8, and so on.  A one bit encodes that
               the condition was detected, while a zero bit
               encodes that the condition was not detected.
               This object is useful for alerting an operator to
               specific warning or error conditions that may
               occur, especially those requiring human
               intervention.
               Refer to RFC 1514, Host Resources MIB, for more details.
                Additional information:
                LaserJet 4050 Series reports error conditions as follows:

                lowPaper -- A tray is empty, but the media to be loaded is not
                currently needed.
                hrDeviceStatus = eHwarning;
                hrPrinterStatus = eHidle or eHprinting;
                A non-critical alert is active.

                noPaper -- A tray is empty and must be filled for printing to continue.
                hrDeviceStatus = eHdown;
                hrPrinterStatus = eHother;
                A critical alert is active.

                lowToner -- Toner is almost gone.  The quality of printed pages will begin
                to deteriorate until the toner is completely gone.
                hrDeviceStatus = eHwarning;
                hrPrinterStatus = eHidle or eHprinting;
                A non-critical alert is active.

                noToner -- LaserJet 4050 Series printers do not report this condition.

                coverOpen -- A printer cover or door is open.
                hrDeviceStatus = eHdown;
                hrPrinterStatus = eHother;
                A critical alert is active.

                jammed -- Paper is jammed and the printer will be unable to continue
                printing until the jam is cleared.
                hrDeviceStatus = eHdown;
                hrPrinterStatus = eHother;
                A critical alert is active.

                offline -- Printer is offline and will not accept new print jobs until
                it is online again.
                hrDeviceStatus = eHdown;
                hrPrinterStatus = eHother;
                A critical alert is active.

                serviceRequested -- Any status or error condition not listed
                above. If the condition prevents printing, the 'offline'
                bit is also set and the hrDeviceStatus and hrPrinterStatus listed for
                offline above are returned.
                hrDeviceStatus = eHwarning;
                hrPrinterStatus = eHidle or eHprinting;
                A non-critical alert is active."
::= { hrPrinterEntry 2 }


prtgeneralconfigchanges OBJECT-TYPE
    SYNTAX  INTEGER(0..2147483648)
    MAX-ACCESS read-only
    STATUS  current
    DESCRIPTION
                "Counts configuration changes that change the capabilities of
        a printer, such as the addition/deletion of input/output bins,
        the addition/deletion of interpreters, or changes in media
        size.  Such changes will often affect the capability of the
        printer to service certain types of print jobs.
        Management applications may cache infrequently changed
        configuration  information about sub-units on the printer.
        This object should be incremented whenever the agent wishes
        such applications to invalidate that cache and re-download
        all of this configuration information, thereby signaling a
        change in the printer's configuration.

        For example, if an input tray that contained paper of
        different dimensions was added, this counter would be
        incremented.
        As an additional example, this counter would not be
        incremented when an input tray is removed or the level of an
		input device changes.
	Refer to Standard Printer MIB for more details.
                Additional information:
                This is a 32 bit counter (unsigned). When it reaches
                its maximum value, it will roll to zero."
::= { prtGeneralEntry 1 }


prtgeneralcurrentlocalization OBJECT-TYPE
    SYNTAX  INTEGER(1..17)
    MAX-ACCESS read-write
    STATUS  current
    DESCRIPTION
                "The value of the prtLocalizationIndex corresponding to the
        current language, country, and character set to be used for
        localized string values that are identified as being dependent
        on the value of this object.  Note that this object does not
        apply to localized strings in the prtConsole group or to any
        object that is not explicitly identified as being localized
        according to prtGeneralCurrentLocalization.
	Refer to Standard Printer MIB for more details.
                Additional information:
                The value of this object is saved in NVRAM."
::= { prtGeneralEntry 2 }


prtgeneralreset OBJECT-TYPE
    SYNTAX  INTEGER {
		   ePnotResetting(3),
		   ePpowerCycleReset(4),
		   ePresetToNVRAM(5),
		   ePresetToFactoryDefaults(6)
		   }
    MAX-ACCESS read-write
    STATUS  current
    DESCRIPTION
                "Setting this value to `powerCycleReset', `resetToNVRAM', or
        `resetToFactoryDefaults' will result in the resetting of the
        printer.  When read, this object will always have the value
        `notResetting(3)', and a SET of the value `notResetting' shall
        have no effect on the printer.  Some of the defined values are
        optional.  However, every implementation must support at least
        the values `notResetting' and 'resetToNVRAM'.
	Refer to Standard Printer MIB for more details.
                Additional information:
                Replaces PML USER-NVRAM-RESET and POWER-ON-RESET.

                The, the following sequence of events occur when this object is set to
                ePpowerCycleReset, ePresetToNVRAM, or ePresetToFactoryDefaults:
                1. Wait until a job boundary.
                2. The paper path is flushed.
                3. The printer is reset per the request. The printer will respond to PML
                requests up to this point in time.

                All settings will make the printer go thru its power-on initialization
                routines and I/O cards are reset.

                When this object is set to ePpowerCycleReset or ePresetToNVRAM, the printer
                performs its power on initialization routines.  I/O cards are reset, although
                NVRAM on the cards is not changed, and all I/O buffers are flushed.  This is
                equivalent to turning the printer off and then on again.

                Setting this object to ePresetToFactoryDefaults causes the same action as
                ePpowerCycleReset exept that it also changes all configurable settings back
                to their factory defaults.  It is equivalent to doing a Cold Reset from the
                control panel while turning on the printer."
::= { prtGeneralEntry 3 }


prtgeneralcurrentoperator OBJECT-TYPE
    SYNTAX  OCTET STRING (SIZE(0..32))
    MAX-ACCESS read-write
    STATUS  current
    DESCRIPTION
                "The name of the person who is responsible for operating
          this printer. It is suggested that this string include
          information that would enable other humans to reach the operator,
          such as a phone number. As a convention to facilitate automatic
          notification of the operator by the agent or the network
          management station, the phone number, fax number or email address
          should be placed on a separate line starting with ASCII LF (hex
          0x0A) and the ASCII text string (without the quotes): 'phone: ',
          'fax: ', and 'email: ', respectively. Phone numbers may contain
          digits, whitespace and parentheses, which shall be ignored. Phone
          numbers may also include ASCII comma characters(hex 2C) that are
          used to indicate a two-second pause during the dialing sequence.
          If either the phone, fax, or email information is not available,
          then a line should not be included for this information.
          NOTE: For interoperability purposes, it is advisable to use email
          addresses formatted according to RFC 822 requirements.
	 Refer to Standard Printer MIB for more details.
                Additional information:
                Replaces PML SYSTEM-CONTACT.
                The maximum supported string length is 32 characters.
                Length of 32 was chosen so a phone number could be
                included with the name.
                If the user entered string is too long, the device
                will store as much as possible and will return the
                <noError> status."
::= { prtGeneralEntry 4 }


prtgeneralserviceperson OBJECT-TYPE
    SYNTAX  OCTET STRING (SIZE(0..32))
    MAX-ACCESS read-write
    STATUS  current
    DESCRIPTION
                "The name of the person responsible for servicing this
          printer. It is suggested that this string include information
          that would enable other humans to reach the service person, such
          as a phone number. As a convention to facilitate automatic
          notification of the service person by the agent or a network
          management station, the phone number, fax number or email address
          should be placed on a separate line starting with ASCII LF (hex
          0x0A) and the ASCII text string (without the quotes): 'phone: ',
          'fax: ', and 'email: ', respectively. Phone numbers may contain
          digits, whitespace and parentheses, which shall be ignored. Phone
          numbers can also include one or more ASCII comma characters(hex
          2C) to indicate a two-second pause during the dialing sequence.
          If either the phone,fax, or email information is not available,
          then a line should not included for this information.
          NOTE: For interoperability purposes, it is advisable to use email
          addresses formatted according to RFC 822 requirements.

	 Refer to Standard Printer MIB for more details.
                Additional information:
                Replaces PML SYSTEM-CONTACT.
                The maximum supported string length is 32 characters.
                Length of 32 was chosen so a phone number could be
                included with the name.
                If the user entered string is too long, the device
                will store as much as possible and will return the
                <noError> status."
::= { prtGeneralEntry 5 }


prtconsolelocalization OBJECT-TYPE
    SYNTAX  INTEGER(1..17)
    MAX-ACCESS read-write
    STATUS  current
    DESCRIPTION
                "The value of the prtLocalizationIndex corresponding to
        the language, country, and character set to be used for the
        console.  This localization applies both to the actual display
        on the console as well as the encoding of these console
        objects in management operations.
	Refer to Standard Printer MIB for more details.
                Additional information:
                The value of this object is saved in NVRAM.
                If a localized string is currently being displayed on the control panel by the
                device, changing this object will cause the displayed string to be changed
                to its new value.  If this object is changed while the printer is processing
                a page that contains localized strings, the results are undefined."
::= { prtGeneralEntry 10 }


prtconsolenumberofdisplaylines OBJECT-TYPE
    SYNTAX  INTEGER(0..65535)
    MAX-ACCESS read-only
    STATUS  current
    DESCRIPTION
                "The number of lines on the printer's physical
        display.  This value is 0 if there are no lines on the
        physical display or if there is no physical display
	Refer to Standard Printer MIB for more details.
                Additional information:
                The printer has two physical lines on the display,
                however, in many cases up to four seperate lines
                of text may be displayed by alternating pairs of
                lines every three seconds.  Thus the display really
                has four logical lines for displaying messages.
                This object will return the number of logical
                display lines supported by the printer."
::= { prtGeneralEntry 11 }


prtconsolenumberofdisplaychars OBJECT-TYPE
    SYNTAX  INTEGER(0..65535)
    MAX-ACCESS read-only
    STATUS  current
    DESCRIPTION
                "The number of characters per line displayed on the physical
        display.  This value is 0 if there are no lines on the
        physical display or if there is no physical display
	Refer to Standard Printer MIB for more details."
::= { prtGeneralEntry 12 }


prtconsoledisable OBJECT-TYPE
    SYNTAX  INTEGER {
		   ePoperatorConsoleEnabled(3),
		   ePoperatorConsoleDisabled(4),
		   ePoperatorConsoleEnabledLevel1(5),
		   ePoperatorConsoleEnabledLevel2(6)
		   }
    MAX-ACCESS read-write
    STATUS  current
    DESCRIPTION
                "If the object prtConsoleDisable has value
          'operatorConsoleDisabled' then input is not accepted from the
          operator console. If the object prtConsoleDisable has the value
          'operatorConsoleEnabled' then input is accepted from the
          operator console. If the object prtConsoleDisable has the value
          'operatorConsoleEnabledLevel1','operatorConsoleEnabledLevel2' or
          'operatorConsoleEnabledLevel3' then limited input is accepted
          from the operator console; the limitations are product specific,
          however, the limitations are generally less restrictive for
          operatorConsoleEnabledLevel1 than for
          operatorConsoleEnabledLeve2, which is less restrictive than
          operatorConsoleEnabledLevel3.
          The value of the prtConsoleDisable object is a type-2
          enumeration.
        Refer to Standard Printer MIB for more details.
                Additional information:
                If the object prtConsoleDisable has value
                'ePoperatorConsoleDisabled' then manual input is not
                accepted from the operator console.  If the object prtConsoleDisable has the
                value 'ePoperatorConsoleEnabled' then manual input is accepted from the
                operator console.
                The following menus are locked with these corresponding
                values:
                ePoperatorConsoleEnabled (no locking)
                ePoperatorConsoleEnabledLevel1 (minimal locking)
                RESETS MENU
                CONFIGURATION MENU
                I/O MENU
                ePoperatorConsoleEnabledLevel2 (moderate locking)
                PRINT QUALITY MENU
                PAPER HANDLING MENU
                menus in level 1
                ePoperatorConsoleDisabled (maximum locking)
                PRINTING MENU
                INFORMATION MENU
                Job Cancel
                menus in levels 1 and 2"
::= { prtGeneralEntry 13 }


prtgeneralstartuppage OBJECT-TYPE
    SYNTAX  INTEGER {
		   ePnotPresent(5)
		   }
    MAX-ACCESS read-only
    STATUS  current
    DESCRIPTION
                "Used to enable or disable printing a startup page. If
		 enabled, a startup page will be printed shortly after
		 power-up, when the device is ready. Typical startup
		 pages include test patterns and/or printer configuration
		 information.
		 Refer to Standard Printer MIB for more details."
::= { prtGeneralEntry 14 }


prtgeneralbannerpage OBJECT-TYPE
    SYNTAX  INTEGER {
		   ePnotPresent(5)
		   }
    MAX-ACCESS read-only
    STATUS  current
    DESCRIPTION
                "Used to enable or disable printing banner pages at the
		 beginning of jobs. This is a master switch which applies
		 to all jobs, regardless of interpreter.
		 Refer to Standard Printer MIB for more details."
::= { prtGeneralEntry 15 }


prtgeneralprintername OBJECT-TYPE
    SYNTAX  OCTET STRING (SIZE(0..32))
    MAX-ACCESS read-write
    STATUS  current
    DESCRIPTION
                "An administrator-specified name for this printer.
          Depending upon implementation of this printer, the value of this
          object may or may not be same as the value for the MIB-II
          'SysName' object.
		 Refer to Standard Printer MIB for more details.
                Additional information:
                The maximum supported string length is 32 characters.
                Length of 32 was chosen so a phone number could be
                included with the name.
                If the user-entered string is too long, the device
                will store as much as possible and will return the
                <noError> status.
                The value of this object is saved over a power cycle."
::= { prtGeneralEntry 16 }


prtgeneralserialnumber OBJECT-TYPE
    SYNTAX  OCTET STRING (SIZE(0..10))
    MAX-ACCESS read-only
    STATUS  current
    DESCRIPTION
                "A recorded serial number for this device that indexes some type
		 device catalog or inventory. This value is usually set by the
		 device manufacturer but the MIB supports the option of
		 writeability for this object for site-specific administration of
		 device inventory or tracking.
		 Refer to Standard Printer MIB for more details."
::= { prtGeneralEntry 17 }


prtalertcriticalevents OBJECT-TYPE
    SYNTAX  INTEGER
    MAX-ACCESS read-only
    STATUS  current
    DESCRIPTION
                "A running counter of the number of critical alert events
          that have been recorded in the alert table. The value of this
          object is RESET in the event of a power cycle operation (i.e.,
          the value is not persistent.
     Refer to Standard Printer MIB for more details.
                Additional information:
                This object is set to zero every time the printer is
                turned on."
::= { prtGeneralEntry 18 }


prtalertallevents OBJECT-TYPE
    SYNTAX  INTEGER
    MAX-ACCESS read-only
    STATUS  current
    DESCRIPTION
                "A running counter of the total number of alert event entries
     (critical and non-critical) that have been recorded in the
     alert table
     Refer to Standard Printer MIB for more details.
                Additional information:
                This object is set to zero every time the printer is
                turned on.  (It is not persistent through a power-cycle.)"
::= { prtGeneralEntry 19 }


prtlocalizationlanguage OBJECT-TYPE
    SYNTAX  OCTET STRING (SIZE(0..2))
    MAX-ACCESS read-only
    STATUS  current
    DESCRIPTION
                "A two character language code from ISO 639.  Examples
          en, gb, ca, fr, de.
	Refer to Standard Printer MIB for more details.
                Additional information:
                The languages supported by LaserJet 4050 Series are English, French,
                German, Italian, Spanish, Swedish, Danish, Norwegian, Dutch, Finnish,
                Portuguese, Turkish, Polish, Japanese, Russian, Czech, and Hungarian."
::= { prtLocalizationEntry 2 }


prtlocalizationcountry OBJECT-TYPE
    SYNTAX  OCTET STRING (SIZE(0..2))
    MAX-ACCESS read-only
    STATUS  current
    DESCRIPTION
                "A two character country code from ISO 3166, a blank string
        (two space characters) shall indicate that the country is
        not defined.  Examples: US, FR, DE, ...
	Refer to Standard Printer MIB for more details.
                Additional information:
                The languages supported by LaserJet 4050 Series (and corresponding
                country) are English (US, United States), French (FR, France),
                German (DE, Germany), Italian (IT, Italy), Spanish (ES, Spain),
                Swedish (SE, Sweden), Danish (DK, Denmark), Norwegian (NO, Norway),
                Dutch (NL, Netherlands), Finnish (FI, Finland), Portuguese (PT, Portugal),
                Turkish (TR, Turkey), Polish (PL, Poland), Japanese (JP, Japan),
                Russian, (RU, Russia), Czech (CS, Czechoslovakia),
                Hungarian (HU, Hungary)"
::= { prtLocalizationEntry 3 }


prtlocalizationcharacterset OBJECT-TYPE
    SYNTAX  INTEGER {
		   ePcsHPRoman8(2004),
		   ePcsISOLatin2(5),
		   ePcsISOLatin5(12),
		   ePcsWindows31J(2024),
		   ePcsISOLatinCyrillic(8)
		   }
    MAX-ACCESS read-only
    STATUS  current
    DESCRIPTION
                "The coded character set used for this localization.
      Refer to Standard Printer MIB for more details."
::= { prtLocalizationEntry 4 }


prtstoragerefindex OBJECT-TYPE
    SYNTAX  INTEGER(1..65535)
    MAX-ACCESS read-only
    STATUS  current
    DESCRIPTION
                "The value of the hrDeviceIndex of the printer device that this
        storageEntry is associated with.
	Refer to Standard Printer MIB for more details.
                  Additional information (mass storage):
                   Constant.  The index value indicates
                   the hrStorageTable index for this storage device.
                   The value indicates the hrDeviceTable index for the
                   printer which uses this storage device.  Returns
                   <noSuchName> status if attempting
                   to perform a Get on this OID with no storage device
                   is installed."
::= { prtStorageRefEntry 2 }


prtdevicerefindex OBJECT-TYPE
    SYNTAX  INTEGER(1..65535)
    MAX-ACCESS read-only
    STATUS  current
    DESCRIPTION
                "The value of the hrDeviceIndex of the printer device that this
        deviceEntry is associated with.
	Refer to Standard Printer MIB for more details.
                Additional information (mass storage) :
                 Constant.  The index indicates the
                 hrDeviceIndex for this mass storage device.  The value indicates
                 the hrDeviceIndex for the printer which uses this
                 mass storage device.  Returns <noSuchName> status
                 if attempting to perform a Get on this OID with no
                    mass storage device installed."

::= { prtDeviceRefEntry 2 }


prtmarkeraddressabilityfeeddir OBJECT-TYPE
    SYNTAX  INTEGER
    MAX-ACCESS read-only
    STATUS  current
    DESCRIPTION
                "The maximum number of addressable marking positions in the feed
        direction per 10000 units of measure specified by
        prtMarkerAddressabilityUnit.  A value of (-1) implies 'other' or
        'infinite' while a value of (-2) implies 'unknown'.
	Refer to Standard Printer MIB for more details.
                Additional information:
                This object indicates the value of the resolution
                (dots per inch) setting for the printer.  LaserJet 5000 Series
                and LaserJet 4000 Series support 300, 600 and 1200 dots per inch.  LaserJet 8100 Series
                and LaserJet 8000 Series supports 300 or 600 dots per inch.   600 dots per inch is
                the default."
::= { prtMarkerEntry 9 }


prtmarkeraddressabilityxfeeddir OBJECT-TYPE
    SYNTAX  INTEGER
    MAX-ACCESS read-only
    STATUS  current
    DESCRIPTION
                "The maximum number of addressable marking positions in the cross
        feed direction in 10000 units of measure specified by
        prtMarkerAddressabilityUnit.  A value of (-1) implies 'other' or
        'infinite' while a value of (-2) implies 'unknown'.
	Refer to Standard Printer MIB for more details.
                Additional information:
                This object indicates the value of the resolution
                (dots per inch) setting for the printer.  LaserJet 5000 Series
                and LaserJet 4000 Series support 300, 600 and 1200 dots per inch.  LaserJet 8100 Series
                and LaserJet 8000 Series supports 300 or 600 dots per inch.   600 dots per inch is
                the default."
::= { prtMarkerEntry 10 }


prtconsoledisplaybuffertext OBJECT-TYPE
    SYNTAX  OCTET STRING (SIZE(0..255))
    MAX-ACCESS read-only
    STATUS  current
    DESCRIPTION
                "The content of a line in the logical display buffer of
        the operator's console of the printer.  When a write
        operation occurs, normally a critical message, to one of
        the LineText strings, the agent should make that line
        displayable if a physical display is present.  Writing
        a zero length string clears the line.  It is an
        implementation-specific matter as to whether the agent allows
        a line to be overwritten before it has been cleared.
        Printer generated strings shall be in the localization
        specified by prtConsoleLocalization.  Management Application
        generated strings should be localized by the Management
        Application.
	Refer to Standard Printer MIB for more details.
                Additional information:
                Replaces PML STATUS-MSG-LINE1-PART1 and
                STATUS-MSG-LINE2-PART1 (read functionality).
                The proprietary objects BACKGROUND-STATUS-MSG-LINE1-PART1
                and BACKGROUND-STATUS-MSG-LINE2-PART1 should be used to
                write messages to the control panel display.

                prtConsoleDisplayBufferText.1.[1..6] maps to logical lines
                1-6 of the display.

                Most of the time the display will show a single one or two line
                message.  This message can be retrieved by reading
                prtConsoleDisplayBufferText.1.1 and
                prtConsoleDisplayBufferText.1.2.  In this case
                prtConsoleDisplayBufferText.1.[3..6] will be NULL.

                If prtConsoleDisplayBufferText.1.3 or
                prtConsoleDisplayBufferText.1.4 is not NULL, the display will
                be alternating.

                If prtConsoleDisplayBufferText.1.[5..6] are NULL, the display
                will alternate prtConsoleDisplayBufferText.1.[1..2] with
                prtConsoleDisplayBufferText.1.[3..4].

                If prtConsoleDisplayBufferText.1.5 or
                prtConsoleDisplayBufferText.1.6 is not NULL, the display will
                show prtConsoleDisplayBufferText.1.[1..2] then
                prtConsoleDisplayBufferText.1.[3..4] then
                prtConsoleDisplayBufferText.1.[5..6].

                The display will alternate between line pairs at three second
                intervals.  "
::= { prtConsoleDisplayBufferEntry 2 }


prtconsoleontime OBJECT-TYPE
    SYNTAX  INTEGER
    MAX-ACCESS read-only
    STATUS  current
    DESCRIPTION
                "This object, in conjunction with prtConsoleOffTime, defines
        the current status of the light.  If both prtConsoleOnTime and
        prtConsoleOffTime are non-zero, the lamp is blinking and the
        values presented define the on time and off time, respectively,
        in milliseconds.  If prtConsoleOnTime is zero and
        prtConsoleOffTime is non-zero, the lamp is off.  If
        prtConsoleOffTime is zero and prtConsoleOnTime is non-zero,
        the lamp is on.  If both values are zero the status of the
        lamp is undefined.
	Refer to Standard Printer MIB for more details.
                Additional information:
                There are three control panel LED's:  Ready (1),
                Data (2), and Attention (3).  When an LED blinks, it is typically on for
                one half second and off for one half second.  The value used for this object
                is 500 when the LED is on or blinking, otherwise it is zero."
::= { prtConsoleLightEntry 2 }


prtconsoleofftime OBJECT-TYPE
    SYNTAX  INTEGER
    MAX-ACCESS read-only
    STATUS  current
    DESCRIPTION
                "This object, in conjunction with prtConsoleOnTime, defines
        the current status of the light.  If both prtConsoleOnTime and
        prtConsoleOffTime are non-zero, the lamp is blinking and the
        values presented define the on time and off time, respectively,
        in milliseconds.  If prtConsoleOnTime is zero and
        prtConsoleOffTime is non-zero, the lamp is off.  If
        prtConsoleOffTime is zero and prtConsoleOnTime is non-zero,
        the lamp is on.  If both values are zero the status of the
        lamp is undefined.
	Refer to Standard Printer MIB for more details.
                Additional information:
                There are three control panel LED's:  Ready (1),
                Data (2), and Attention (3).  When an LED blinks, it is typically on for
                one half second and off for one half second.  The value used for this object
                is 500 when the LED is off or blinking, otherwise it is zero."
::= { prtConsoleLightEntry 3 }


prtconsoledescription OBJECT-TYPE
    SYNTAX  OCTET STRING (SIZE(0..255))
    MAX-ACCESS read-only
    STATUS  current
    DESCRIPTION
                "The vendor description or label of this light in the
        localization specified by prtConsoleLocalization.
	Refer to Standard Printer MIB for more details."
::= { prtConsoleLightEntry 5 }


prtalertseveritylevel OBJECT-TYPE
    SYNTAX  INTEGER {
		   ePother(1),
		   ePcriticalBinaryChangeEvent(3),
		   ePwarningUnaryChangeEvent(4),
		   ePwarningBinaryChangeEvent(5)
		   }
    MAX-ACCESS read-only
    STATUS  current
    DESCRIPTION
                "The level of severity of this alert table entry.  The printer
        determines the severity level assigned to each entry into the
        table.
	Refer to Standard Printer MIB for more details."
::= { prtAlertEntry 2 }


prtalerttraininglevel OBJECT-TYPE
    SYNTAX  INTEGER {
		   ePother(1),
		   ePuntrained(3),
		   ePtrained(4),
		   ePfieldService(5),
		   ePmanagement(6),
		   ePnoInterventionRequired(7)
		   }
    MAX-ACCESS read-only
    STATUS  current
    DESCRIPTION
                "See textual convention PrtAlertTrainingLevelTC
	Refer to Standard Printer MIB for more details.
                Additional information:
                The value of this object depends on the alert.
                Some examples:
                ePfieldService: Marker failure.
                ePtrained: Toner low.
                ePuntrained: Paper low/out.
                ePmanagement: Configuration change."
::= { prtAlertEntry 3 }


prtalertgroup OBJECT-TYPE
    SYNTAX  INTEGER {
		   ePgeneralPrinter(5),
		   ePcover(6),
		   ePinput(8),
		   ePoutput(9),
		   ePmarker(10),
		   ePmarkerSupplies(11),
		   ePchannel(14)
		   }
    MAX-ACCESS read-only
    STATUS  current
    DESCRIPTION
                "The type of sub-unit within the printer model that this alert
        is related.  Input, output, and markers are examples of
        printer model groups, i.e., examples of types of sub-units.
        Wherever possible, these enumerations match the
        sub-identifier that identifies the relevant table in the
        printmib.
	Refer to Standard Printer MIB for more details."
::= { prtAlertEntry 4 }


prtalertgroupindex OBJECT-TYPE
    SYNTAX  INTEGER
    MAX-ACCESS read-only
    STATUS  current
    DESCRIPTION
                "An index of the row within the principle table in the
        group identified by prtAlertGroup that represents the
        sub-unit of the printer that caused this alert.  The
        combination of the prtAlertGroup and the prtAlertGroupIndex defines
        exactly which printer sub-unit caused the alert.; for
        example, Input #3, Output #2, and Marker #1.
        Every object in this MIB is indexed with hrDeviceIndex and
        optionally, another index variable.  If this other index
        variable is present in the table that generated the alert, it
        will be used as the value for this object.  Otherwise, this
        value shall be -1.
	Refer to Standard Printer MIB for more details."
::= { prtAlertEntry 5 }


prtalertlocation OBJECT-TYPE
    SYNTAX  INTEGER
    MAX-ACCESS read-only
    STATUS  current
    DESCRIPTION
                "The sub-unit location that is defined by the printer
        manufacturer to further refine the location of this alert
        within the designated sub-unit.  The location is used in
        conjunction with the Group and GroupIndex values; for
        example, there is an alert in Input #2 at location number 7.
	 The value (-2) indicates unknown
	 Refer to Standard Printer MIB for more details."
::= { prtAlertEntry 6 }


prtalertcode OBJECT-TYPE
    SYNTAX  INTEGER {
		   ePother(1),
		   ePcoverOpened(3),
		   ePjam(8),
		   ePsubunitMissing(9),
		   ePsubunitAlmostEmpty(12),
		   ePsubunitEmpty(13),
		   ePsubunitAlmostFull(14),
		   ePsubunitFull(15),
		   ePsubunitOffline(22),
		   ePsubunitPowerSaver(23),
		   ePsubunitMotorFailure(33),
		   ePsubunitMemoryExhausted(34),
		   ePmarkerFuserUnderTemperature(1001),
		   ePmarkerFuserOverTemperature(1002),
		   ePmarkerTonerEmpty(1101),
		   ePmarkerTonerAlmostEmpty(1104)
		   }
    MAX-ACCESS read-only
    STATUS  current
    DESCRIPTION
                "See associated textual convention PrtAlertCodeTC
	Refer to Standard Printer MIB for more details."
::= { prtAlertEntry 7 }


prtalertdescription OBJECT-TYPE
    SYNTAX  OCTET STRING (SIZE(0..255))
    MAX-ACCESS read-only
    STATUS  current
    DESCRIPTION
                "A description of this alert entry in the localization
        specified by prtGeneralCurrentLocalization.  The description is
        provided by the printer to further elaborate on the enumerated
        alert or provide information in the case where the code is
        classified as `other' or `unknown'.  The printer is required
        to return a description string but the string may be a null
        string.
	Refer to Standard Printer MIB for more details."
::= { prtAlertEntry 8 }


prtalerttime OBJECT-TYPE
    SYNTAX  INTEGER
    MAX-ACCESS read-only
    STATUS  current
    DESCRIPTION
                "The value of sysUpTime at the time that this alert was
        generated.
	Refer to Standard Printer MIB for more details."
::= { prtAlertEntry 9 }


job-input-auto-continue-timeout OBJECT-TYPE
    SYNTAX  INTEGER(-1..3600)
    MAX-ACCESS read-write
    STATUS  current
    DESCRIPTION
                "The number of seconds the device waits after a job
                related continuable error occurs before automatically
                continuing.  An example job related continuable error is
                the job requesting a media size that is not available.
                After the timeout expires, the device will continue
                processing the job as if a continue event occurred, such
                as the front panel continue key being pressed.  If the
                value is -1, the device does not automatically continue
                after a job related continuable error occurs.  If the
                value is 0, the device immediately continues.  If the
                value is greater than 0, the value represents the
                timeout value in seconds.
                Additional information:
                This object is used only for media requests
                		           (size and/or name).   LaserJet 4050 Series supports any value in
                			   the range of -1 to 3600. Setting to a value outside
                			   of that range causes the printer to substitute a
                			   value (listed below) and to return
                			   <noError> status.   The
                			   values are as follow:   <-1 snaps to -1
                			   >3600 snaps to 3600  (60 minutes)   The action that
                			   occurs when this timeout expires is explained by
                			   JOB-INPUT-AUTO-CONTINUE-MODE. It is not the same as
                			   the CONTINUE object being set to eInitiateAction or
                			   the Select key being pressed on the control panel.
                			   See the CONTINUE object description for
                			   information on the actions that occur for those
                			   conditions.
                	                   The data for this object is stored in NVRAM."
::= { status-system 35 }


job-input-auto-continue-mode OBJECT-TYPE
    SYNTAX  OCTET STRING
    MAX-ACCESS read-write
    STATUS  current
    DESCRIPTION
                "Returns or sets the device behavior when the desired
                media is not currently available.
                  cCancelJob - The device cancels the job.  The device
                POS should explain what happens if this item is not the
                only item in the collection.
                  cAutoMediaSizeOverride - The device is allowed to
                substitute a different size media.
                  cAutoMediaNameOverride - The device is allowed to
                substitute a different media name.
                Additional information:
                If cCancelJob is set, the current print job will
                		           be canceled regardless of other item settings. At
                			   least one bit of the collection must be set; setting
                			   this object to zero will cause a status of
                			   <badValue> to be returned.
                			   This object applies to all media requests, including
                			   Manual Feed Requests.   This object describes the
                			   action that is performed when the
                			   JOB-INPUT-AUTO-CONTINUE-TIMEOUT expires. The action
                			   performed by the CONTINUE object being set to
                			   eInitiateAction or the GO key being pressed on the
                			   control panel may cause different actions. See the
                			   CONTINUE object description for information on the
                			   actions that occur for those conditions.
                		           The data for this object is stored in NVRAM."
::= { status-system 36 }


job-output-auto-continue-timeout OBJECT-TYPE
    SYNTAX  INTEGER(-1..3600)
    MAX-ACCESS read-write
    STATUS  current
    DESCRIPTION
                "Returns or sets the time that the printer will wait
                after an output bin becomes full and the printer is
                trying to deliver a sheet of media to that output bin.
                When the timeout expires, the job is processed according
                to the OUTBINn-OVERRIDE-MODE.  A value of -1 indicates
                that the printer will wait for a continue event.  A non-
                negative value is the number of seconds to wait.
                Additional information:
                A value of zero means to continue immediately.
                The value of this object is stored in NVRAM, so
                it is maintained across a power cycle.
                		        The data for this object is stored in NVRAM."
::= { status-system 40 }


phd2-model OBJECT-TYPE
    SYNTAX  DisplayString
    MAX-ACCESS read-only
    STATUS  current
    DESCRIPTION
                "Returns product information identifying PHD device 2.
                Additional information:
                If at least one (1) external paper handling device
                is attached to the printer, then this object will
                exist, otherwise <noSuchName>
                should be returned.
                This object returns product information about the
                first paper handling device in the device chain."
::= { phd2 1 }


phd2-manufacturing-info OBJECT-TYPE
    SYNTAX  DisplayString
    MAX-ACCESS read-only
    STATUS  current
    DESCRIPTION
                "Returns information describing the manufacture of PHD 2.
                May include serial number and firmware revision.
                Additional information:
                If at least one (1) external paper handling device
                is attached to the printer, then this object will
                exist, otherwise <noSuchName>
                should be returned.
                This object returns the name of the manufacturer of
                the first paper handling device."
::= { phd2 2 }


phd2-type OBJECT-TYPE
    SYNTAX  INTEGER {
		   eUnknown(2),
		   eInputPHD(10),
		   eOutputPHD(11),
		   eBindingPHD(13)
		   }
    MAX-ACCESS read-only
    STATUS  current
    DESCRIPTION
                "Returns an indication of the type of option installed in
                PHD interface 2.  See SIMM1-TYPE for an explanation of
                the enumerations.
                Additional information:
                If at least one (1) external paper handling device
                is attached to the printer, then this object will
                exist, otherwise <noSuchName>
                should be returned.
                This object returns whether the device is an input
                device, an output device, or an unknown device which may
                	     be developed in the future."
::= { phd2 3 }


phd2-capacity OBJECT-TYPE
    SYNTAX  INTEGER
    MAX-ACCESS read-only
    STATUS  current
    DESCRIPTION
                "Returns an indication of the capacity of the installed
                option.  See SIMM1-CAPACITY for an explanation of the
                meaning of the value of this object.
                Additional information:
                If at least one (1) external paper handling device
                (EPHD) is attached to the printer, then this object
                will exist, otherwise <noSuchName>
                should be returned.
                This object returns the number of input trays or
                output bins, depending the the device type (see
                PHD2-TYPE) for the first EPHD in the device chain."
::= { phd2 4 }


phd3-model OBJECT-TYPE
    SYNTAX  DisplayString
    MAX-ACCESS read-only
    STATUS  current
    DESCRIPTION
                "Returns product information identifying PHD device 3.
                Additional information:
                If at least two (2) external paper handling devices
                are attached to the printer, then this object will
                exist, otherwise <noSuchName>
                should be returned.
                This object returns product information about the
                second paper handling device in the device chain."
::= { phd3 1 }


phd3-manufacturing-info OBJECT-TYPE
    SYNTAX  DisplayString
    MAX-ACCESS read-only
    STATUS  current
    DESCRIPTION
                "Returns information describing the manufacture of PHD 3.
                May include serial number and firmware revision.
                Additional information:
                If at least two (2) external paper handling devices
                are attached to the printer, then this object will
                exist, otherwise <noSuchName>
                should be returned.
                This object returns the name of the manufacturer of
                the second paper handling device."
::= { phd3 2 }


phd3-type OBJECT-TYPE
    SYNTAX  INTEGER {
		   eUnknown(2),
		   eInputPHD(10),
		   eOutputPHD(11),
		   eBindingPHD(13)
		   }
    MAX-ACCESS read-only
    STATUS  current
    DESCRIPTION
                "Returns an indication of the type of option installed in
                PHD interface 3.  See SIMM1-TYPE for an explanation of
                the enumerations.
                Additional information:
                If at least two (2) external paper handling devices
                are attached to the printer, then this object will
                exist, otherwise <noSuchName>
                should be returned.
                This object returns whether the second device is an
                input device, an output device, or an unknown object which may
                	     be developed in the future."
::= { phd3 3 }


phd3-capacity OBJECT-TYPE
    SYNTAX  INTEGER
    MAX-ACCESS read-only
    STATUS  current
    DESCRIPTION
                "Returns an indication of the capacity of the installed
                option.  See SIMM1-CAPACITY for an explanation of the
                meaning of the value of this object.
                Additional information:
                If at least two (2) external paper handling devices
                (EPHD) are attached to the printer, then this object
                will exist, otherwise <noSuchName>
                should be returned.
                This object returns the number of input trays or
                output bins, depending the the device type (see
                PHD3-TYPE) for the second EPHD in the device chain."
::= { phd3 4 }


phd4-model OBJECT-TYPE
    SYNTAX  DisplayString
    MAX-ACCESS read-only
    STATUS  current
    DESCRIPTION
                "Returns product information identifying PHD device 4.
                Additional information:
                If at least three (3) external paper handling devices
                are attached to the printer, then this object will
                exist, otherwise <noSuchName>
                should be returned.
                This object returns product information about the
                third paper handling device in the device chain."
::= { phd4 1 }


phd4-manufacturing-info OBJECT-TYPE
    SYNTAX  DisplayString
    MAX-ACCESS read-only
    STATUS  current
    DESCRIPTION
                "Returns information describing the manufacture of PHD 4.
                May include serial number and firmware revision.
                Additional information:
                If at least three (3) external paper handling devices
                are attached to the printer, then this object will
                exist, otherwise <noSuchName>
                should be returned.
                This object returns the name of the manufacturer of
                the third paper handling device."
::= { phd4 2 }


phd4-type OBJECT-TYPE
    SYNTAX  INTEGER {
		   eUnknown(2),
		   eInputPHD(10),
		   eOutputPHD(11),
		   eBindingPHD(13)
		   }
    MAX-ACCESS read-only
    STATUS  current
    DESCRIPTION
                "Returns an indication of the type of option installed in
                PHD interface 4.  See SIMM1-TYPE for an explanation of
                the enumerations.
                Additional information:
                If at least three (3) external paper handling devices
                are attached to the printer, then this object will
                exist, otherwise <noSuchName>
                should be returned.
                This object returns whether the third device is an
                input device, an output device, or an unknown device which may
                	     be developed in the future."
::= { phd4 3 }


phd4-capacity OBJECT-TYPE
    SYNTAX  INTEGER
    MAX-ACCESS read-only
    STATUS  current
    DESCRIPTION
                "Returns an indication of the capacity of the installed
                option.  See SIMM1-CAPACITY for an explanation of the
                meaning of the value of this object.
                Additional information:
                If at least three (3) external paper handling devices
                (EPHD) are attached to the printer, then this object
                will exist, otherwise <noSuchName>
                should be returned.
                This object returns the number of input trays or
                output bins, depending the the device type (see
                PHD4-TYPE) for the third EPHD in the device chain."
::= { phd4 4 }


phd5-model OBJECT-TYPE
    SYNTAX  DisplayString
    MAX-ACCESS read-only
    STATUS  current
    DESCRIPTION
                "Returns product information identifying PHD device 3.
                Additional information:
                If at least four (4) external paper handling devices
                are attached to the printer, then this object will
                exist, otherwise <noSuchName>
                should be returned.
                This object returns product information about the
                fourth paper handling device in the device chain."
::= { phd5 1 }


phd5-manufacturing-info OBJECT-TYPE
    SYNTAX  DisplayString
    MAX-ACCESS read-only
    STATUS  current
    DESCRIPTION
                "Returns information describing the manufacture of PHD 5.
                May include serial number and firmware revision.
                Additional information:
                If at least four (4) external paper handling devices
                are attached to the printer, then this object will
                exist, otherwise <noSuchName>
                should be returned.
                This object returns the name of the manufacturer of
                the fourth paper handling device."
::= { phd5 2 }


phd5-type OBJECT-TYPE
    SYNTAX  INTEGER {
		   eUnknown(2),
		   eInputPHD(10),
		   eOutputPHD(11),
		   eBindingPHD(13)
		   }
    MAX-ACCESS read-only
    STATUS  current
    DESCRIPTION
                "Returns an indication of the type of option installed in
                PHD interface 5.  See SIMM1-TYPE for an explanation of
                the enumerations.
                Additional information:
                If at least four (4) external paper handling devices
                are attached to the printer, then this object will
                exist, otherwise <noSuchName>
                should be returned.
                This object returns whether the fourth device is an
                input device, an output device, or an unknown device which may
                be developed in the future."
::= { phd5 3 }


phd5-capacity OBJECT-TYPE
    SYNTAX  INTEGER
    MAX-ACCESS read-only
    STATUS  current
    DESCRIPTION
                "Returns an indication of the capacity of the installed
                option.  See SIMM1-CAPACITY for an explanation of the
                meaning of the value of this object.
                Additional information:
                If at least four (4) external paper handling devices
                (EPHD) are attached to the printer, then this object
                will exist, otherwise <noSuchName>
                should be returned.
                This object returns the number of input trays or
                output bins, depending the the device type (see
                PHD5-TYPE) for the fourth EPHD in the device chain."
::= { phd5 4 }


phd6-model OBJECT-TYPE
    SYNTAX  DisplayString
    MAX-ACCESS read-only
    STATUS  current
    DESCRIPTION
                "Returns product information identifying PHD device 6.
                Additional information:
                If at least five (5) external paper handling devices
                are attached to the printer, then this object will
                exist, otherwise <noSuchName>
                should be returned.
                This object returns product information about the
                fifth paper handling device in the device chain."
::= { phd6 1 }


phd6-manufacturing-info OBJECT-TYPE
    SYNTAX  DisplayString
    MAX-ACCESS read-only
    STATUS  current
    DESCRIPTION
                "Returns information describing the manufacture of PHD 6.
                May include serial number and firmware revision.
                Additional information:
                If at least five (5) external paper handling devices
                are attached to the printer, then this object will
                exist, otherwise <noSuchName>
                should be returned.
                This object returns the name of the manufacturer of
                the fifth paper handling device."
::= { phd6 2 }


phd6-type OBJECT-TYPE
    SYNTAX  INTEGER {
		   eUnknown(2),
		   eInputPHD(10),
		   eOutputPHD(11),
		   eBindingPHD(13)
		   }
    MAX-ACCESS read-only
    STATUS  current
    DESCRIPTION
                "Returns an indication of the type of option installed in
                PHD interface 6.  See SIMM1-TYPE for an explanation of
                the enumerations.
                Additional information:
                If at least five (5) external paper handling devices
                are attached to the printer, then this object will
                exist, otherwise <noSuchName>
                should be returned.
                This object returns whether the fifth device is an
                input device, an output device, or an unknown device which may
                	     be developed in the future."
::= { phd6 3 }


phd6-capacity OBJECT-TYPE
    SYNTAX  INTEGER
    MAX-ACCESS read-only
    STATUS  current
    DESCRIPTION
                "Returns an indication of the capacity of the installed
                option.  See SIMM1-CAPACITY for an explanation of the
                meaning of the value of this object.
                Additional information:
                If at least five (5) external paper handling devices
                (EPHD) are attached to the printer, then this object
                will exist, otherwise <noSuchName>
                should be returned.
                This object returns the number of input trays or
                output bins, depending the the device type (see
                PHD6-TYPE) for the fifth EPHD in the device chain."
::= { phd6 4 }


tray1-phd OBJECT-TYPE
    SYNTAX  INTEGER
    MAX-ACCESS read-only
    STATUS  current
    DESCRIPTION
                "Provides the number of the Paper Handling Device that
                contains this input tray.
                Additional information:
                The internal trays belong to device 0, which is the
                		        base engine. The envelope feeder (if supported) is
                		        considered to be device 1 and the external input devices
                can number between 2 and 6 depending on individual
                user configurations."
::= { intray1 12 }

tray1-fuser-temperature OBJECT-TYPE
    SYNTAX  INTEGER(-1..1)
    MAX-ACCESS read-write
    STATUS  current
    DESCRIPTION
                "The fuser temperature to be used when printing media
                from Tray 1.  The value zero is the default temperature.
                Values less than zero are progressively lower and values
                greater than zero are progressively higher.  The range
                of values supported is device specific.
                Additional information:
                HP LaserJet 2100 Series supports 3 fuser temperatures.
                Zero (0) is the default temperature, one(1) is a higher
                temperature (for use on media like cardstock), negative
                one (-1) is a lower temperature (for use on media like
                transparencies).

                Setting to an unsupported value causes the printer to
                snap to the nearest supported value and to return
                <noError> status along with
                the actual value that was written.

                The snap values are as follows:
                <=-1 snaps to -1
                >=1 snaps to 1"
::= { intray1 13 }

overflow-bin OBJECT-TYPE
    SYNTAX  INTEGER
    MAX-ACCESS read-write
    STATUS  current
    DESCRIPTION
                "Returns or sets the bin that will be used for additional
                sheets of media when the current bin is full and
                printing is allowed to continue.
                Additional information:
                The data for this object is stored in NVRAM."
::= { settings-outbin 4 }


outbin1-override-mode OBJECT-TYPE
    SYNTAX  OCTET STRING
    MAX-ACCESS read-write
    STATUS  current
    DESCRIPTION
                "Returns or sets the device behavior when this output bin
                condition causes printing to stop.
                  cCancelJob - The device cancels the job.
                  cOutbinFullOverride - The device sends subsequent
                media to the overflow bin.
                  cOutbinAttentionOverride - The device ignores the
                attention condition and continues printing.
                  cBinderAttentionOverride - The device ignores the
                binder attention condition and continues printing.
                Additional information:
                If cCancelJob is set, the current print job will
                be cancelled regardless of other item settings.
                If cOutbinFullOverride is set and this bin is the
                designated overflow bin (OVERFLOW-BIN = 1), then the
                bit is ignored.  This object describes the action
                that is performed when the
                JOB-OUTPUT-AUTO-CONTINUE-TIMEOUT expires. If no bits
                are set, no override action is taken (the printer
                will continue to wait).
                The action performed by the CONTINUE object being set
                to eInitiateAction or the GO key being pressed on the
                control panel may cause different actions. See the
                CONTINUE object
                description for information on the actions that occur
                for those conditions."
::= { outbin1 9 }

outbin1-maximum-capacity OBJECT-TYPE
    SYNTAX  INTEGER
    MAX-ACCESS read-only
    STATUS  current
    DESCRIPTION
                "Maximum capacity of the output bin, in sheets of 20
                pound paper."
::= { outbin1 1 }

outbin2-override-mode OBJECT-TYPE
    SYNTAX  OCTET STRING
    MAX-ACCESS read-write
    STATUS  current
    DESCRIPTION
                "Returns or sets the device behavior when this output bin
                condition causes printing to stop.
                  cCancelJob - The device cancels the job.
                  cOutbinFullOverride - The device sends subsequent
                media to the overflow bin.
                  cOutbinAttentionOverride - The device ignores the
                attention condition and continues printing.
                  cBinderAttentionOverride - The device ignores the
                binder attention condition and continues printing.
                Additional information:
                See OUTBIN1-OVERRIDE-MODE."
::= { outbin2 9 }

phd2-device-specific-command OBJECT-TYPE
    SYNTAX  OCTET STRING
    MAX-ACCESS read-write
    STATUS  current
    DESCRIPTION
                "This object is used to send device-specific data to the
                paper handling device.  The meaning of the device-
                specific command is dependent on the paper handling
                device and must be specified in the POS.
                If the paper handling device does not accept the
                command, then an <badValue> will
                be returned.  If the device accepts the command, it may
                still be processing the command after the response has
                been returned.  Depending on the device, the application
                may need to query PHDx-DEVICE-MEMORY to see when the
                command has completed.
                Additional information:
                If at least one (1) external paper handling device
                is attached to the printer, then this object will
                exist, otherwise <noSuchName>
                will be returned.
                Since the data formats can vary from device to
                device, this information must be documented for
                each device by the manufacturer of the device.
                If the device does not support this command, then
                an <badValue> error message
                will be returned.
                Since it will usually take longer to send this
                command to the device than PML allows for <Set>
                operations, this object will have a return value
                that does not necessarily match the value currently
                received by the first device."
::= { ph2 2 }


phd2-device-memory OBJECT-TYPE
    SYNTAX  OCTET STRING
    MAX-ACCESS read-only
    STATUS  current
    DESCRIPTION
                "This object is used to read the current values stored in
                shared memory available from the paper handling device.
                Additional information:
                If at least one (1) external paper handling device
                is attached to the printer, then this object will
                exist, otherwise <noSuchName>
                should be returned.
                This object returns the current memory stored in
                the printer's NVRAM (non-volatile RAM) for the
                first paper handling device.  Currently, the
                printer allocates 16 bytes for each device."
::= { ph2 4 }


phd3-device-specific-command OBJECT-TYPE
    SYNTAX  OCTET STRING
    MAX-ACCESS read-write
    STATUS  current
    DESCRIPTION
                "This object is used to send device-specific data to the
                paper handling device.  The meaning of the device-
                specific command is dependent on the paper handling
                device and must be specified in the POS.
                If the paper handling device does not accept the
                command, then an <badValue> will
                be returned.  If the device accepts the command, it may
                still be processing the command after the response has
                been returned.  Depending on the device, the application
                may need to query PHDx-DEVICE-MEMORY to see when the
                command has completed.
                Additional information:
                If at least two (2) external paper handling devices
                are attached to the printer, then this object will
                exist, otherwise <noSuchName>
                will be returned.
                Since the data formats can vary from device to
                device, this information must be documented for
                each device by the manufacturer of the device.
                If the device does not support this command, then
                an <badValue> error message
                will be returned.
                Since it will usually take longer to send this
                command to the device than PML allows for <Set>
                operations, this object will have a return value
                that does not necessarily match the value currently
                received by the second device."
::= { ph3 2 }


phd3-device-memory OBJECT-TYPE
    SYNTAX  OCTET STRING
    MAX-ACCESS read-only
    STATUS  current
    DESCRIPTION
                "This object is used to read the current values stored in
                shared memory available from the paper handling device.
                Additional information:
                If at least two (2) external paper handling devices
                are attached to the printer, then this object will
                exist, otherwise <noSuchName>
                should be returned.
                This object returns the current memory stored in
                the printer's NVRAM (non-volatile RAM) for the
                second paper handling device.  Currently, the
                printer allocates 16 bytes for each device."
::= { ph3 4 }


phd4-device-specific-command OBJECT-TYPE
    SYNTAX  OCTET STRING
    MAX-ACCESS read-write
    STATUS  current
    DESCRIPTION
                "This object is used to send device-specific data to the
                paper handling device.  The meaning of the device-
                specific command is dependent on the paper handling
                device and must be specified in the POS.
                If the paper handling device does not accept the
                command, then an <badValue> will
                be returned.  If the device accepts the command, it may
                still be processing the command after the response has
                been returned.  Depending on the device, the application
                may need to query PHDx-DEVICE-MEMORY to see when the
                command has completed.
                Additional information:
                If at least three (3) external paper handling devices
                are attached to the printer, then this object will
                exist, otherwise <noSuchName>
                will be returned.
                Since the data formats can vary from device to
                device, this information must be documented for
                each device by the manufacturer of the device.
                If the device does not support this command, then
                an <badValue> error message
                will be returned.
                Since it will usually take longer to send this
                command to the device than PML allows for <Set>
                operations, this object will have a return value
                that does not necessarily match the value currently
                received by the third device."
::= { ph4 2 }


phd4-device-memory OBJECT-TYPE
    SYNTAX  OCTET STRING
    MAX-ACCESS read-only
    STATUS  current
    DESCRIPTION
                "This object is used to read the current values stored in
                shared memory available from the paper handling device.
                Additional information:
                If at least three (3) external paper handling devices
                are attached to the printer, then this object will
                exist, otherwise <noSuchName>
                should be returned.
                This object returns the current memory stored in
                the printer's NVRAM (non-volatile RAM) for the
                second paper handling device.  Currently, the
                printer allocates 16 bytes for each device."
::= { ph4 4 }


phd5-device-specific-command OBJECT-TYPE
    SYNTAX  OCTET STRING
    MAX-ACCESS read-write
    STATUS  current
    DESCRIPTION
                "This object is used to send device-specific data to the
                paper handling device.  The meaning of the device-
                specific command is dependent on the paper handling
                device and must be specified in the POS.
                If the paper handling device does not accept the
                command, then an <badValue> will
                be returned.  If the device accepts the command, it may
                still be processing the command after the response has
                been returned.  Depending on the device, the application
                may need to query PHDx-DEVICE-MEMORY to see when the
                command has completed.
                Additional information:
                If at least four (4) external paper handling devices
                are attached to the printer, then this object will
                exist, otherwise <noSuchName>
                will be returned.
                Since the data formats can vary from device to
                device, this information must be documented for
                each device by the manufacturer of the device.
                If the device does not support this command, then
                an <badValue> error message
                will be returned.
                Since it will usually take longer to send this
                command to the device than PML allows for <Set>
                operations, this object will have a return value
                that does not necessarily match the value currently
                received by the fourth device."
::= { ph5 2 }


phd5-device-memory OBJECT-TYPE
    SYNTAX  OCTET STRING
    MAX-ACCESS read-only
    STATUS  current
    DESCRIPTION
                "This object is used to read the current values stored in
                shared memory available from the paper handling device.
                Additional information:
                If at least four (4) external paper handling devices
                are attached to the printer, then this object will
                exist, otherwise <noSuchName>
                should be returned.
                This object returns the current memory stored in
                the printer's NVRAM (non-volatile RAM) for the
                second paper handling device.  Currently, the
                printer allocates 16 bytes for each device."
::= { ph5 4 }


phd6-device-specific-command OBJECT-TYPE
    SYNTAX  OCTET STRING
    MAX-ACCESS read-write
    STATUS  current
    DESCRIPTION
                "This object is used to send device-specific data to the
                paper handling device.  The meaning of the device-
                specific command is dependent on the paper handling
                device and must be specified in the POS.
                If the paper handling device does not accept the
                command, then an <badValue> will
                be returned.  If the device accepts the command, it may
                still be processing the command after the response has
                been returned.  Depending on the device, the application
                may need to query PHDx-DEVICE-MEMORY to see when the
                command has completed.
                Additional information:
                If at least five (5) external paper handling devices
                are attached to the printer, then this object will
                exist, otherwise <noSuchName>
                will be returned.
                Since the data formats can vary from device to
                device, this information must be documented for
                each device by the manufacturer of the device.
                If the device does not support this command, then
                an <badValue> error message
                will be returned.
                Since it will usually take longer to send this
                command to the device than PML allows for <Set>
                operations, this object will have a return value
                that does not necessarily match the value currently
                received by the fifth device."
::= { ph6 2 }


phd6-device-memory OBJECT-TYPE
    SYNTAX  OCTET STRING
    MAX-ACCESS read-only
    STATUS  current
    DESCRIPTION
                "This object is used to read the current values stored in
                shared memory available from the paper handling device.
                Additional information:
                If at least five (5) external paper handling devices
                are attached to the printer, then this object will
                exist, otherwise <noSuchName>
                should be returned.
                This object returns the current memory stored in
                the printer's NVRAM (non-volatile RAM) for the
                second paper handling device.  Currently, the
                printer allocates 16 bytes for each device."
::= { ph6 4 }


north-edge-offset OBJECT-TYPE
    SYNTAX  INTEGER
    MAX-ACCESS read-write
    STATUS  current
    DESCRIPTION
                "Returns or sets the number of 300 dpi dots by which the
                image is shifted. Shift is relative to the leading edge
                of the medium as the medium flows through the marking
                engine with the side to be imaged facing the observer.
                The leading edge is the North edge and the other edges
                are defined by the normal compass layout of  directions
                with the compass facing the observer. The adjustment is
                for  all pages printed. A positive value  moves the
                image away from the leading edge of the medium. A
                negative value moves the image closer to the leading
                edge of the medium. The value 0 will return the image to
                its factory default position.
                Additional information:
                The value of this object is stored in NVRAM."
::= { settings-print-media 2 }


media1-name OBJECT-TYPE
    SYNTAX  DisplayString (SIZE(1..24))
    MAX-ACCESS read-only
    STATUS  current
    DESCRIPTION
                "Media 1 name.
                Additional information:
                The symbol set for this string is Roman-8."
::= { media1 1 }


media1-short-name OBJECT-TYPE
    SYNTAX  DisplayString (SIZE(1..9))
    MAX-ACCESS read-only
    STATUS  current
    DESCRIPTION
                "Length restricted version of the media name 1.  The
                length restriction is required to allow the media name
                to be displayed on the device's control panel.  The
                device POS must state the maximum number of characters
                allowed.  If the device also has a limitation on what
                characters in a character set can be used (e.g. only
                uppercase characters allowed), the POS should also state
                character restrictions.
                Additional information:
                 The maximum supported string length is 9 characters.  If
                the user entered string is too long, the device will store
                the first 9 characters and will return the
                <noError> status.
                The characters must be in the range 20H to 7FH except 5C
                cannot be used. The default symbol set is Roman-8 for
                English; additional legal symbol sets are ISOLatin5,
                ISOLatin2 and Windows31J. Setting this object with characters
                outside of the range or of an illegal symbol set will cause an
                error status of <badValue> to be returned."
::= { media1 2 }


media1-page-count OBJECT-TYPE
    SYNTAX  INTEGER
    MAX-ACCESS read-only
    STATUS  current
    DESCRIPTION
                "Number of sheets of media 1 that have been printed.  The
                device POS should state whether this value is lost
                across a power cycle or kept in NVRAM.
                Additional information:
                For LaserJet 4050 Series this page count is saved in NVRAM after every 10
                		pages. The maximum value is 4,294,967,295 which will never be reached in
                normal operation.
                The page count is incremented when a sheet of media is pulled from an input
                tray. A duplex printed sheet will cause this counter to be incremented by
                one.
                		The data for this object is stored in NVRAM."
::= { media1 3 }


media1-engine-media-mode OBJECT-TYPE
    SYNTAX  INTEGER
    MAX-ACCESS read-write
    STATUS  current
    DESCRIPTION
                "The engine processing characteristics that are to be
                applied to this media. The processing characteristics
                are device specific.
                Additional information:
                The engine processing characteristics that are to
                be applied to this media type. Currently, 'engine
                processing characteristics' denotes changes to
                fusing temperature and/or transfer roller voltage.
                		        The data for this object is stored in NVRAM."
::= { media1 4 }


media2-name OBJECT-TYPE
    SYNTAX  DisplayString (SIZE(1..24))
    MAX-ACCESS read-only
    STATUS  current
    DESCRIPTION
                "Media 2 name.
                Additional information:
                See MEDIA1-NAME."
::= { media2 1 }


media2-short-name OBJECT-TYPE
    SYNTAX  DisplayString (SIZE(1..9))
    MAX-ACCESS read-only
    STATUS  current
    DESCRIPTION
                "Length restricted version of the media name 2.  See
                MEDIA1-SHORT-NAME for details.
                Additional information:
                See MEDIA1-SHORT-NAME."
::= { media2 2 }


media2-page-count OBJECT-TYPE
    SYNTAX  INTEGER
    MAX-ACCESS read-only
    STATUS  current
    DESCRIPTION
                "Number of sheets of media 2 that have been printed.  See
                MEDIA1-PAGE-COUNT for details.
                Additional information:
                See MEDIA1-PAGE-COUNT."
::= { media2 3 }


media2-engine-media-mode OBJECT-TYPE
    SYNTAX  INTEGER
    MAX-ACCESS read-write
    STATUS  current
    DESCRIPTION
                "The engine processing characteristics that are to be
                applied to this media. The processing characteristics
                are device specific.
                Additional information:
                See the description for MEDIA1-ENGINE-MEDIA-MODE."
::= { media2 4 }


media3-name OBJECT-TYPE
    SYNTAX  DisplayString (SIZE(1..24))
    MAX-ACCESS read-only
    STATUS  current
    DESCRIPTION
                "Media 3 name.
                Additional information:
                See MEDIA1-NAME."
::= { media3 1 }


media3-short-name OBJECT-TYPE
    SYNTAX  DisplayString (SIZE(1..9))
    MAX-ACCESS read-only
    STATUS  current
    DESCRIPTION
                "Length restricted version of the media name 3.  See
                MEDIA1-SHORT-NAME for details.
                Additional information:
                See MEDIA1-SHORT-NAME."
::= { media3 2 }


media3-page-count OBJECT-TYPE
    SYNTAX  INTEGER
    MAX-ACCESS read-only
    STATUS  current
    DESCRIPTION
                "Number of sheets of media 3 that have been printed.  See
                MEDIA1-PAGE-COUNT for details.
                Additional information:
                See MEDIA1-PAGE-COUNT."
::= { media3 3 }


media3-engine-media-mode OBJECT-TYPE
    SYNTAX  INTEGER
    MAX-ACCESS read-write
    STATUS  current
    DESCRIPTION
                "The engine processing characteristics that are to be
                applied to this media. The processing characteristics
                are device specific.
                Additional information:
                See the description for MEDIA1-ENGINE-MEDIA-MODE."
::= { media3 4 }


media4-name OBJECT-TYPE
    SYNTAX  DisplayString (SIZE(1..24))
    MAX-ACCESS read-only
    STATUS  current
    DESCRIPTION
                "Media 4 name.
                Additional information:
                See MEDIA1-NAME."
::= { media4 1 }


media4-short-name OBJECT-TYPE
    SYNTAX  DisplayString (SIZE(1..9))
    MAX-ACCESS read-only
    STATUS  current
    DESCRIPTION
                "Length restricted version of the media name 4.  See
                MEDIA1-SHORT-NAME for details.
                Additional information:
                See MEDIA1-SHORT-NAME."
::= { media4 2 }


media4-page-count OBJECT-TYPE
    SYNTAX  INTEGER
    MAX-ACCESS read-only
    STATUS  current
    DESCRIPTION
                "Number of sheets of media 4 that have been printed.  See
                MEDIA1-PAGE-COUNT for details.
                Additional information:
                See MEDIA1-PAGE-COUNT."
::= { media4 3 }


media5-name OBJECT-TYPE
    SYNTAX  DisplayString (SIZE(1..24))
    MAX-ACCESS read-only
    STATUS  current
    DESCRIPTION
                "Media 5 name.
                Additional information:
                See MEDIA1-NAME."
::= { media5 1 }


media5-short-name OBJECT-TYPE
    SYNTAX  DisplayString (SIZE(1..9))
    MAX-ACCESS read-only
    STATUS  current
    DESCRIPTION
                "Length restricted version of the media name 5.  See
                MEDIA1-SHORT-NAME for details.
                Additional information:
                See MEDIA1-SHORT-NAME."
::= { media5 2 }


media5-page-count OBJECT-TYPE
    SYNTAX  INTEGER
    MAX-ACCESS read-only
    STATUS  current
    DESCRIPTION
                "Number of sheets of media 5 that have been printed.  See
                MEDIA1-PAGE-COUNT for details.
                Additional information:
                See MEDIA1-PAGE-COUNT."
::= { media5 3 }


media5-engine-media-mode OBJECT-TYPE
    SYNTAX  INTEGER
    MAX-ACCESS read-write
    STATUS  current
    DESCRIPTION
                "The engine processing characteristics that are to be
                applied to this media. The processing characteristics
                are device specific.
                Additional information:
                See the description for MEDIA1-ENGINE-MEDIA-MODE."
::= { media5 4 }


media6-name OBJECT-TYPE
    SYNTAX  DisplayString (SIZE(1..24))
    MAX-ACCESS read-only
    STATUS  current
    DESCRIPTION
                "Media 6 name.
                Additional information:
                See MEDIA1-NAME."
::= { media6 1 }


media6-short-name OBJECT-TYPE
    SYNTAX  DisplayString (SIZE(1..9))
    MAX-ACCESS read-only
    STATUS  current
    DESCRIPTION
                "Length restricted version of the media name 6.  See
                MEDIA1-SHORT-NAME for details.
                Additional information:
                See MEDIA1-SHORT-NAME."
::= { media6 2 }


media6-page-count OBJECT-TYPE
    SYNTAX  INTEGER
    MAX-ACCESS read-only
    STATUS  current
    DESCRIPTION
                "Number of sheets of media 6 that have been printed.  See
                MEDIA1-PAGE-COUNT for details.
                Additional information:
                See MEDIA1-PAGE-COUNT."
::= { media6 3 }


media7-name OBJECT-TYPE
    SYNTAX  DisplayString (SIZE(1..24))
    MAX-ACCESS read-only
    STATUS  current
    DESCRIPTION
                "Media 7 name.
                Additional information:
                See MEDIA1-NAME."
::= { media7 1 }


media7-short-name OBJECT-TYPE
    SYNTAX  DisplayString (SIZE(1..9))
    MAX-ACCESS read-only
    STATUS  current
    DESCRIPTION
                "Length restricted version of the media name 7.  See
                MEDIA1-SHORT-NAME for details.
                Additional information:
                See MEDIA1-SHORT-NAME."
::= { media7 2 }


media7-page-count OBJECT-TYPE
    SYNTAX  INTEGER
    MAX-ACCESS read-only
    STATUS  current
    DESCRIPTION
                "Number of sheets of media 7 that have been printed.  See
                MEDIA1-PAGE-COUNT for details.
                Additional information:
                See MEDIA1-PAGE-COUNT."
::= { media7 3 }


media7-engine-media-mode OBJECT-TYPE
    SYNTAX  INTEGER
    MAX-ACCESS read-write
    STATUS  current
    DESCRIPTION
                "The engine processing characteristics that are to be
                applied to this media. The processing characteristics
                are device specific.
                Additional information:
                See the description for MEDIA1-ENGINE-MEDIA-MODE."
::= { media7 4 }


media8-name OBJECT-TYPE
    SYNTAX  DisplayString (SIZE(1..24))
    MAX-ACCESS read-only
    STATUS  current
    DESCRIPTION
                "Media 8 name.
                Additional information:
                See MEDIA1-NAME."
::= { media8 1 }


media8-short-name OBJECT-TYPE
    SYNTAX  DisplayString (SIZE(1..9))
    MAX-ACCESS read-only
    STATUS  current
    DESCRIPTION
                "Length restricted version of the media name 8.  See
                MEDIA1-SHORT-NAME for details.
                Additional information:
                See MEDIA1-SHORT-NAME."
::= { media8 2 }


media8-page-count OBJECT-TYPE
    SYNTAX  INTEGER
    MAX-ACCESS read-only
    STATUS  current
    DESCRIPTION
                "Number of sheets of media 8 that have been printed.  See
                MEDIA1-PAGE-COUNT for details.
                Additional information:
                See MEDIA1-PAGE-COUNT."
::= { media8 3 }


media8-engine-media-mode OBJECT-TYPE
    SYNTAX  INTEGER
    MAX-ACCESS read-write
    STATUS  current
    DESCRIPTION
                "The engine processing characteristics that are to be
                applied to this media. The processing characteristics
                are device specific.
                Additional information:
                See the description for MEDIA1-ENGINE-MEDIA-MODE."
::= { media8 4 }


media9-name OBJECT-TYPE
    SYNTAX  DisplayString (SIZE(1..24))
    MAX-ACCESS read-only
    STATUS  current
    DESCRIPTION
                "Media 9 name.
                Additional information:
                See MEDIA1-NAME."
::= { media9 1 }


media9-short-name OBJECT-TYPE
    SYNTAX  DisplayString (SIZE(1..9))
    MAX-ACCESS read-only
    STATUS  current
    DESCRIPTION
                "Length restricted version of the media name 9.  See
                MEDIA1-SHORT-NAME for details.
                Additional information:
                See MEDIA1-SHORT-NAME."
::= { media9 2 }


media9-page-count OBJECT-TYPE
    SYNTAX  INTEGER
    MAX-ACCESS read-only
    STATUS  current
    DESCRIPTION
                "Number of sheets of media 9 that have been printed.  See
                MEDIA1-PAGE-COUNT for details.
                Additional information:
                See MEDIA1-PAGE-COUNT."
::= { media9 3 }


media9-engine-media-mode OBJECT-TYPE
    SYNTAX  INTEGER
    MAX-ACCESS read-write
    STATUS  current
    DESCRIPTION
                "The engine processing characteristics that are to be
                applied to this media. The processing characteristics
                are device specific.
                Additional information:
                See the description for MEDIA1-ENGINE-MEDIA-MODE."
::= { media9 4 }


media10-name OBJECT-TYPE
    SYNTAX  DisplayString (SIZE(1..24))
    MAX-ACCESS read-only
    STATUS  current
    DESCRIPTION
                "Media 10 name.
                Additional information:
                See MEDIA1-NAME."
::= { media10 1 }


media10-short-name OBJECT-TYPE
    SYNTAX  DisplayString (SIZE(1..9))
    MAX-ACCESS read-only
    STATUS  current
    DESCRIPTION
                "Length restricted version of the media name 10.  See
                MEDIA1-SHORT-NAME for details.
                Additional information:
                See MEDIA1-SHORT-NAME."
::= { media10 2 }


media10-page-count OBJECT-TYPE
    SYNTAX  INTEGER
    MAX-ACCESS read-only
    STATUS  current
    DESCRIPTION
                "Number of sheets of media 10 that have been printed.
                See MEDIA1-PAGE-COUNT for details.
                Additional information:
                See MEDIA1-PAGE-COUNT."
::= { media10 3 }


media11-name OBJECT-TYPE
    SYNTAX  DisplayString (SIZE(1..24))
    MAX-ACCESS read-only
    STATUS  current
    DESCRIPTION
                "Media 11 name.
                Additional information:
                See MEDIA1-NAME."
::= { media11 1 }


media11-short-name OBJECT-TYPE
    SYNTAX  DisplayString (SIZE(1..9))
    MAX-ACCESS read-only
    STATUS  current
    DESCRIPTION
                "Length restricted version of the media name 11.  See
                MEDIA1-SHORT-NAME for details.
                Additional information:
                See MEDIA1-SHORT-NAME."
::= { media11 2 }


media11-page-count OBJECT-TYPE
    SYNTAX  INTEGER
    MAX-ACCESS read-only
    STATUS  current
    DESCRIPTION
                "Number of sheets of media 11 that have been printed.
                See MEDIA1-PAGE-COUNT for details.
                Additional information:
                See MEDIA1-PAGE-COUNT."
::= { media11 3 }

media12-name OBJECT-TYPE
    SYNTAX  DisplayString (SIZE(1..24))
    MAX-ACCESS read-only
    STATUS  current
    DESCRIPTION
                "Media 12 name.
                Additional information:
                See MEDIA1-NAME."
::= { media12 1 }


media12-short-name OBJECT-TYPE
    SYNTAX  DisplayString (SIZE(1..9))
    MAX-ACCESS read-only
    STATUS  current
    DESCRIPTION
                "Length restricted version of the media name 12.  See
                MEDIA1-SHORT-NAME for details.
                Additional information:
                See MEDIA1-SHORT-NAME."
::= { media12 2 }


media12-page-count OBJECT-TYPE
    SYNTAX  INTEGER
    MAX-ACCESS read-only
    STATUS  current
    DESCRIPTION
                "Number of sheets of media 12 that have been printed.
                See MEDIA1-PAGE-COUNT for details.
                Additional information:
                See MEDIA1-PAGE-COUNT."
::= { media12 3 }


media12-engine-media-mode OBJECT-TYPE
    SYNTAX  INTEGER
    MAX-ACCESS read-write
    STATUS  current
    DESCRIPTION
                "The engine processing characteristics that are to be
                applied to this media. The processing characteristics
                are device specific.
                Additional information:
                See the description for MEDIA1-ENGINE-MEDIA-MODE."
::= { media12 4 }


media13-name OBJECT-TYPE
    SYNTAX  DisplayString (SIZE(1..24))
    MAX-ACCESS read-write
    STATUS  current
    DESCRIPTION
                "Media 13 name.
                Additional information:
                The maximum supported string length is 24
                bytes.  If the user entered string is too long,
                the device will store the first 24 bytes and
                return the <noError> status.
                See CAUTION statement under Product Specific Use."
::= { media13 1 }


media13-short-name OBJECT-TYPE
    SYNTAX  DisplayString (SIZE(1..9))
    MAX-ACCESS read-write
    STATUS  current
    DESCRIPTION
                "Length restricted version of the media name 13.  See
                MEDIA1-SHORT-NAME for details.
                Additional information:
                 The maximum supported string length is 9 characters.  If
                the user entered string is too long, the device will store
                the first 9 characters and will return the
                <noError> status.
                The characters must be in the range 20H to 7FH except 5C
                cannot be used. The default symbol set is Roman-8 for
                English; additional legal symbol sets are ISOLatin5,
                ISOLatin2 and Windows31J. Setting this object with characters
                outside of the range or of an illegal symbol set will cause an
                error status of <badValue> to be returned."
::= { media13 2 }


media13-page-count OBJECT-TYPE
    SYNTAX  INTEGER
    MAX-ACCESS read-only
    STATUS  current
    DESCRIPTION
                "Number of sheets of media 13 that have been printed.
                See MEDIA1-PAGE-COUNT for details.
                Additional information:
                See MEDIA1-PAGE-COUNT."
::= { media13 3 }


media13-engine-media-mode OBJECT-TYPE
    SYNTAX  INTEGER
    MAX-ACCESS read-write
    STATUS  current
    DESCRIPTION
                "The engine processing characteristics that are to be
                applied to this media. The processing characteristics
                are device specific.
                Additional information:
                See the description for MEDIA1-ENGINE-MEDIA-MODE."
::= { media13 4 }


media14-name OBJECT-TYPE
    SYNTAX  DisplayString (SIZE(1..24))
    MAX-ACCESS read-write
    STATUS  current
    DESCRIPTION
                "Media 14 name.
                Additional information:
                See MEDIA13-NAME."
::= { media14 1 }


media14-short-name OBJECT-TYPE
    SYNTAX  DisplayString (SIZE(1..9))
    MAX-ACCESS read-write
    STATUS  current
    DESCRIPTION
                "Length restricted version of the media name 14.  See
                MEDIA1-SHORT-NAME for details.
                Additional information:
                See MEDIA13-SHORT-NAME."
::= { media14 2 }


media14-page-count OBJECT-TYPE
    SYNTAX  INTEGER
    MAX-ACCESS read-only
    STATUS  current
    DESCRIPTION
                "Number of sheets of media 14 that have been printed.
                See MEDIA1-PAGE-COUNT for details.
                Additional information:
                See MEDIA13-PAGE-COUNT."
::= { media14 3 }


media14-engine-media-mode OBJECT-TYPE
    SYNTAX  INTEGER
    MAX-ACCESS read-write
    STATUS  current
    DESCRIPTION
                "The engine processing characteristics that are to be
                applied to this media. The processing characteristics
                are device specific.
                Additional information:
                See the description for MEDIA1-ENGINE-MEDIA-MODE."
::= { media14 4 }


media15-name OBJECT-TYPE
    SYNTAX  DisplayString (SIZE(1..24))
    MAX-ACCESS read-write
    STATUS  current
    DESCRIPTION
                "Media 15 name.
                Additional information:
                See MEDIA13-NAME."
::= { media15 1 }


media15-short-name OBJECT-TYPE
    SYNTAX  DisplayString (SIZE(1..9))
    MAX-ACCESS read-write
    STATUS  current
    DESCRIPTION
                "Length restricted version of the media name 15.  See
                MEDIA1-SHORT-NAME for details.
                Additional information:
                See MEDIA13-SHORT-NAME."
::= { media15 2 }


media15-page-count OBJECT-TYPE
    SYNTAX  INTEGER
    MAX-ACCESS read-only
    STATUS  current
    DESCRIPTION
                "Number of sheets of media 15 that have been printed.
                See MEDIA1-PAGE-COUNT for details.
                Additional information:
                See MEDIA13-PAGE-COUNT."
::= { media15 3 }


media15-engine-media-mode OBJECT-TYPE
    SYNTAX  INTEGER
    MAX-ACCESS read-write
    STATUS  current
    DESCRIPTION
                "The engine processing characteristics that are to be
                applied to this media. The processing characteristics
                are device specific.
                Additional information:
                See the description for MEDIA1-ENGINE-MEDIA-MODE."
::= { media15 4 }


media16-name OBJECT-TYPE
    SYNTAX  DisplayString (SIZE(1..24))
    MAX-ACCESS read-write
    STATUS  current
    DESCRIPTION
                "Media 16 name.
                Additional information:
                See MEDIA13-NAME."
::= { media16 1 }


media16-short-name OBJECT-TYPE
    SYNTAX  DisplayString (SIZE(1..9))
    MAX-ACCESS read-write
    STATUS  current
    DESCRIPTION
                "Length restricted version of the media name 16.  See
                MEDIA1-SHORT-NAME for details.
                Additional information:
                See MEDIA13-SHORT-NAME."
::= { media16 2 }


media16-page-count OBJECT-TYPE
    SYNTAX  INTEGER
    MAX-ACCESS read-only
    STATUS  current
    DESCRIPTION
                "Number of sheets of media 16 that have been printed.
                See MEDIA1-PAGE-COUNT for details.
                Additional information:
                See MEDIA13-PAGE-COUNT."
::= { media16 3 }


media16-engine-media-mode OBJECT-TYPE
    SYNTAX  INTEGER
    MAX-ACCESS read-write
    STATUS  current
    DESCRIPTION
                "The engine processing characteristics that are to be
                applied to this media. The processing characteristics
                are device specific.
                Additional information:
                See the description for MEDIA1-ENGINE-MEDIA-MODE."
::= { media16 4 }


media17-name OBJECT-TYPE
    SYNTAX  DisplayString (SIZE(1..24))
    MAX-ACCESS read-write
    STATUS  current
    DESCRIPTION
                "Media 17 name.
                Additional information:
                See MEDIA13-NAME."
::= { media17 1 }


media17-short-name OBJECT-TYPE
    SYNTAX  DisplayString (SIZE(1..9))
    MAX-ACCESS read-write
    STATUS  current
    DESCRIPTION
                "Length restricted version of the media name 17.  See
                MEDIA1-SHORT-NAME for details.
                Additional information:
                See MEDIA13-SHORT-NAME."
::= { media17 2 }


media17-page-count OBJECT-TYPE
    SYNTAX  INTEGER
    MAX-ACCESS read-only
    STATUS  current
    DESCRIPTION
                "Number of sheets of media 17 that have been printed.
                See MEDIA1-PAGE-COUNT for details.
                Additional information:
                See MEDIA13-PAGE-COUNT."
::= { media17 3 }


media17-engine-media-mode OBJECT-TYPE
    SYNTAX  INTEGER
    MAX-ACCESS read-write
    STATUS  current
    DESCRIPTION
                "The engine processing characteristics that are to be
                applied to this media. The processing characteristics
                are device specific.
                Additional information:
                See the description for MEDIA1-ENGINE-MEDIA-MODE."
::= { media17 4 }


prtinputdefaultindex OBJECT-TYPE
    SYNTAX  INTEGER
    MAX-ACCESS read-only
    STATUS  current
    DESCRIPTION
                "The value of prtInputIndex corresponding to the default input
        sub-unit: that is, this object selects the default source of
        input media.
   This value shall be -1 if there is no default input subunit specified
   for the printer as a whole.  In this case, the actual default
   input subunit may be specified by means outside the scope of this
   MIB, such as by each interpreter in a printer with multiple
   interpreters.
   Refer to Standard Printer MIB for more details.
                Additional information:
                The default input tray is determined by the printer
                based on DEFAULT-MEDIA-SIZE and DEFAULT-MEDIA-NAME, and whether or
                not optional trays are installed.
                If Tray 1 is set in FIRST mode then the size of paper loaded in
                Tray 1 is assumed to be the requested size. In this case, the printer will
                pick from Tray 1 without regard to the requested size unless the
                print job's paper size, paper type and tray designations exactly
                match the configuration of another tray; in that case, the requested
                tray will be picked."
::= { prtGeneralEntry 6 }


prtmarkerdefaultindex OBJECT-TYPE
    SYNTAX  INTEGER(1..65535)
    MAX-ACCESS read-only
    STATUS  current
    DESCRIPTION
                "The value of prtMarkerIndex corresponding to the
        default marker sub-unit; that is, this object selects the
        default marker.
	Refer to Standard Printer MIB for more details.
                Additional information:
                LaserJet 4050 Series only has one marker subunit."
::= { prtGeneralEntry 8 }


prtmediapathdefaultindex OBJECT-TYPE
    SYNTAX  INTEGER(1..3)
    MAX-ACCESS read-write
    STATUS  current
    DESCRIPTION
                "The value of prtMediaPathIndex corresponding to
        the default media path; that is, the selection of the
        default media path.
	Refer to Standard Printer MIB for more details.
                Additional information:
                If the duplex unit is not installed, the only valid
                value for this object is 1; with duplex unit installed,
                		       1-3 values are valid.  1 is simplex, 2 is
                		       LongEdgeBindingDuplex, and 3 is ShortEdgeBindingDuplex.
                If the printer is not idle, the new value of this object
                		       may not take effect until a job boundary is reached.
                		       If a get is done on this object before the job boundary
                		       is reached, the value last set will be returned."
::= { prtGeneralEntry 9 }


prtcoverdescription OBJECT-TYPE
    SYNTAX  OCTET STRING (SIZE(0..255))
    MAX-ACCESS read-only
    STATUS  current
    DESCRIPTION
                "The manufacturer provided cover sub-mechanism  name in the
        localization specified by prtGeneralCurrentLocalization.
	Refer to Standard Printer MIB for more details."
::= { prtCoverEntry 2 }


prtcoverstatus OBJECT-TYPE
    SYNTAX  INTEGER {
		   ePdoorOpen(3),
		   ePdoorClosed(4)
		   }
    MAX-ACCESS read-only
    STATUS  current
    DESCRIPTION
                "The status of this cover sub-unit.
	Refer to Standard Printer MIB for more details.
                Additional information:
                Replaces PML NOT-READY-DOOR-OPEN."
::= { prtCoverEntry 3 }


prtmarkermarktech OBJECT-TYPE
    SYNTAX  INTEGER {
		   ePelectrophotographicLaser(4)
		   }
    MAX-ACCESS read-only
    STATUS  current
    DESCRIPTION
                "The type of marking technology used for this marking sub-unit.
	Refer to Standard Printer MIB for more details.
                Additional information:
                ePelectrophotographicLaser is the only value that applies
                for the LaserJet 4050 Series products, and this is the value that will
                always be returned for this object."
::= { prtMarkerEntry 2 }


prtmarkercounterunit OBJECT-TYPE
    SYNTAX  INTEGER {
		   ePimpressions(7)
		   }
    MAX-ACCESS read-only
    STATUS  current
    DESCRIPTION
                "The unit that will be used by the printer when reporting
        counter values for this marking sub-unit.  The
        time units of measure are provided for a device like a
        strip recorder that does not or cannot track the physical
        dimensions of the media and does not use characters,
        lines or sheets.
	Refer to Standard Printer MIB for more details.
                Additional information:
                Since LaserJet 4050 Series keeps track of pages printed, the
                counter unit will be defined as ePimpressions which would be
                like saying pages printed."
::= { prtMarkerEntry 3 }


prtmarkerlifecount OBJECT-TYPE
    SYNTAX  INTEGER
    MAX-ACCESS read-only
    STATUS  current
    DESCRIPTION
                "The count of the number of units of measure counted during
        the life of printer using units of measure as specified by
        prtMarkerCounterUnit.
	Refer to Standard Printer MIB for more details.
                Additional information:
                Replaces PML TOTAL-ENGINE-PAGE-COUNT.
                The total engine page count is kept in NVRAM however
                		       the NVRAM value is only updated every 10 impressions.
                		       NOTE: The value returned by this OID will be incremented
                		       every page but if power is lost between NVRAM updates,
                		       up to 9 impressions of the page count may be lost.  The
                		       counter will be reset to zero after 999999 pages.
                The page count is incremented when a sheet of media is
                		       pulled from an input tray. A duplex printed sheet will
                		       cause this counter to be incremented by two."
::= { prtMarkerEntry 4 }


prtmarkerpoweroncount OBJECT-TYPE
    SYNTAX  INTEGER
    MAX-ACCESS read-only
    STATUS  current
    DESCRIPTION
                "The count of the number of units of measure counted since the
        equipment was most recently powered on using units of measure as
        specified by prtMarkerCounterUnit.
	Refer to Standard Printer MIB for more details."
::= { prtMarkerEntry 5 }


prtmarkerprocesscolorants OBJECT-TYPE
    SYNTAX  INTEGER(0..65535)
    MAX-ACCESS read-only
    STATUS  current
    DESCRIPTION
                "The number of process colors supported by this marker.  A
        process color of 1 implies monochrome.  The value of this
        object and prtMarkerSpotColorants cannot both be 0.  The value of
        prtMarkerProcessColorants must be 0 or greater.
	Refer to Standard Printer MIB for more details."
::= { prtMarkerEntry 6 }


prtmarkerspotcolorants OBJECT-TYPE
    SYNTAX  INTEGER(0..65535)
    MAX-ACCESS read-only
    STATUS  current
    DESCRIPTION
                "The number of spot colors supported by this marker.  The
        value of this object and prtMarkerProcessColorants cannot
        both be 0.  Must be 0 or greater.
	Refer to Standard Printer MIB for more details."
::= { prtMarkerEntry 7 }


prtmarkeraddressabilityunit OBJECT-TYPE
    SYNTAX  INTEGER {
		   ePtenThousandthsOfInches(3)
		   }
    MAX-ACCESS read-only
    STATUS  current
    DESCRIPTION
                "The unit of measure of distances, as applied to the marker's
         resolution.
	 Refer to Standard Printer MIB for more details.
                Additional information:
                This will always be ePtenThousandthsOfInches, no matter
                what COLD-RESET-MEDIA-SIZE is because we are talking about
                resolution and toner addressability, which is always dpi."
::= { prtMarkerEntry 8 }


prtmarkernorthmargin OBJECT-TYPE
    SYNTAX  INTEGER
    MAX-ACCESS read-only
    STATUS  current
    DESCRIPTION
                "The margin, in units identified by prtMarkerAddressabilityUnit,
        from the leading edge of the medium as the medium flows
        through the marking engine with the side to be imaged
        facing the observer. The leading edge is the North edge
        and the other edges are defined by the normal compass
        layout of  directions with the compass facing the
        observer.  Printing within the area bounded by all four
        margins is guaranteed for all interpreters.   The value
        (-2) means unknown.
	Refer to Standard Printer MIB for more details."
::= { prtMarkerEntry 11 }


prtmarkersouthmargin OBJECT-TYPE
    SYNTAX  INTEGER
    MAX-ACCESS read-only
    STATUS  current
    DESCRIPTION
                "The margin from the South edge  (see prtMarkerNorthMargin)
        of the medium in units identified by
        prtMarkerAddressabilityUnit.  Printing within the area bounded by
        all four margins  is guaranteed for all interpreters.
        The value (-2) means unknown.
	Refer to Standard Printer MIB for more details."
::= { prtMarkerEntry 12 }


prtmarkerwestmargin OBJECT-TYPE
    SYNTAX  INTEGER
    MAX-ACCESS read-only
    STATUS  current
    DESCRIPTION
                "The margin from the West edge (see prtMarkerNorthMargin) of the
        medium in units identified by prtMarkerAddressabilityUnit.
        Printing within the area bounded by all four margins is
        guaranteed for all interpreters.   The value (-2) means
        unknown.
	Refer to Standard Printer MIB for more details."
::= { prtMarkerEntry 13 }


prtmarkereastmargin OBJECT-TYPE
    SYNTAX  INTEGER
    MAX-ACCESS read-only
    STATUS  current
    DESCRIPTION
                "The margin from the East edge (see prtMarkerNorthMargin) of the
        medium in units identified by prtMarkerAddressabilityUnit.
        Printing within the area bounded by all four margins is
        guaranteed for all interpreters. The value (-2) means
        unknown.
	Refer to Standard Printer MIB for more details."
::= { prtMarkerEntry 14 }


prtmarkerstatus OBJECT-TYPE
    SYNTAX  INTEGER
    MAX-ACCESS read-only
    STATUS  current
    DESCRIPTION
                "The current status of this marker sub-unit.
	Refer to Standard Printer MIB for more details.
                Additional information:
                Replaces PML NOT-READY-DESTINATION-PRINT-ENGINE and
                STATUS-DESTINATION-PRINT-ENGINE.
                51 = No toner cart.
                49 = Low toner and toner low = stop in config menu
                14 = Low toner and toner low = continue in config menu
                			     and paper is moving.
                08 = Low toner and toner low = continue in config menu
                			     and no paper is moving.
                00 = OK.
                The default value assumes no malfunctions."
::= { prtMarkerEntry 15 }


prtmarkersuppliesmarkerindex OBJECT-TYPE
    SYNTAX  INTEGER(0..65535)
    MAX-ACCESS read-only
    STATUS  current
    DESCRIPTION
                "The value of prtMarkerIndex corresponding to the
        marking sub-unit with which this marker supply
        sub-unit is associated.
	Refer to Standard Printer MIB for more details.
                Additional information:
                LaserJet 4050 Series has just one marker supply, the toner
                cartridge, so this value is always 1."
::= { prtMarkerSuppliesEntry 2 }


prtmarkersuppliescolorantindex OBJECT-TYPE
    SYNTAX  INTEGER(0..65535)
    MAX-ACCESS read-only
    STATUS  current
    DESCRIPTION
                "The value of prtMarkerColorantIndex
        corresponding to the colorant with which this
        marker supply sub-unit is associated.  This value
        shall be 0 if there is no colorant table.
	Refer to Standard Printer MIB for more details."
::= { prtMarkerSuppliesEntry 3 }


prtmarkersuppliesclass OBJECT-TYPE
    SYNTAX  INTEGER {
		   ePsupplyThatIsConsumed(3)
		   }
    MAX-ACCESS read-only
    STATUS  current
    DESCRIPTION
                "Indicates whether this supply entity represents a supply
        that is consumed or a receptacle that is filled.
	Refer to Standard Printer MIB for more details.
                Additional information:
                ePsupplyThatIsConsumed is the only value that applies
                for the LaserJet 4050 Series products, and this is the value that will
                always be returned for this object."
::= { prtMarkerSuppliesEntry 4 }


prtmarkersuppliestype OBJECT-TYPE
    SYNTAX  INTEGER {
		   ePtoner(3)
		   }
    MAX-ACCESS read-only
    STATUS  current
    DESCRIPTION
                "The type of this supply.
	Refer to Standard Printer MIB for more details.
                Additional information:
                ePtoner is the only value that applies for the LaserJet 4050 Series
                products, and this is the value that will always be
                returned for this object."
::= { prtMarkerSuppliesEntry 5 }


prtmarkersuppliessupplyunit OBJECT-TYPE
    SYNTAX  INTEGER {
		   ePtenthsOfGrams(13)
		   }
    MAX-ACCESS read-only
    STATUS  current
    DESCRIPTION
                "Unit of measure of this marker supply container/receptacle.
	Refer to Standard Printer MIB for more details.
                Additional information:
                ePtenthsOfGrams will always be returned for this object."
::= { prtMarkerSuppliesEntry 7 }


prtmarkercolorantmarkerindex OBJECT-TYPE
    SYNTAX  INTEGER(0..65535)
    MAX-ACCESS read-only
    STATUS  current
    DESCRIPTION
                "The value of prtMarkerIndex corresponding to the
        marker sub-unit with which this colorant entry is
        associated.
                Additional information:
                LaserJet 4500 only has one marker.  Therefore, the
                value of these objects is always 1."
::= { prtMarkerColorantEntry 2 }


prtmarkercolorantrole OBJECT-TYPE
    SYNTAX  INTEGER {
		   ePother(1),
		   ePprocess(3),
		   ePspot(4)
		   }
    MAX-ACCESS read-only
    STATUS  current
    DESCRIPTION
                "The role played by this colorant.
                Additional information:
                All LaserJet 4500 colorants are process colorants."
::= { prtMarkerColorantEntry 3 }


prtmarkercolorantvalue OBJECT-TYPE
    SYNTAX  OCTET STRING (SIZE(0..255))
    MAX-ACCESS read-only
    STATUS  current
    DESCRIPTION
                "The name of the color of this
        colorant using standardized string names from ISO 10175 (DPA)
        and ISO 10180 (SPDL) which are:
          other
          unknown
          white
          red
          green
          blue
          cyan
          magenta
          yellow
          black
        Implementors may add additional string values. The naming
        conventions in ISO 9070 are recommended in order to avoid
        potential name clashes"
::= { prtMarkerColorantEntry 4 }


prtmarkercoloranttonality OBJECT-TYPE
    SYNTAX  INTEGER
    MAX-ACCESS read-only
    STATUS  current
    DESCRIPTION
                "The distinct levels of tonality realizable by a marking
        sub-unit when using this colorant.  This value does not
        include the number of levels of tonal difference that an
        interpreter can obtain by techniques such as half toning.
        This value must be at least 2.
                Additional information:
                LaserJet 4500 supports eight bits per pixel."
::= { prtMarkerColorantEntry 5 }



prtmediapathmaxspeedprintunit OBJECT-TYPE
    SYNTAX  INTEGER {
		   ePimpressionsPerHour(7)
		   }
    MAX-ACCESS read-only
    STATUS  current
    DESCRIPTION
                "The unit of measure used in specifying the speed of all media
        paths in the printer.
	Refer to Standard Printer MIB for more details.
                Additional information:
                ePimpressionsPerHour is the value that will
                always be returned for this object. (Print Speed is
                measured in pages-per-minute (impressions per minute),
                so ePimpressionsPerHour is a natural extension)."
::= { prtMediaPathEntry 2 }


prtmediapathmediasizeunit OBJECT-TYPE
    SYNTAX  INTEGER {
		   ePtenThousandthsOfInches(3),
		   ePmicrometers(4)
		   }
    MAX-ACCESS read-only
    STATUS  current
    DESCRIPTION
                "The units of measure of media size for use in calculating and
        relaying dimensional values for all media paths in the printer.
	Refer to Standard Printer MIB for more details."
::= { prtMediaPathEntry 3 }


prtmediapathtype OBJECT-TYPE
    SYNTAX  INTEGER {
		   ePlongEdgeBindingDuplex(3),
		   ePshortEdgeBindingDuplex(4),
		   ePsimplex(5)
		   }
    MAX-ACCESS read-only
    STATUS  current
    DESCRIPTION
                "The type of the media path for this media path.
	Refer to Standard Printer MIB for more details.
                Additional information:
                Replaces PML DUPLEX-INSTALLED."
::= { prtMediaPathEntry 9 }


prtmediapathdescription OBJECT-TYPE
    SYNTAX  OCTET STRING (SIZE(0..255))
    MAX-ACCESS read-only
    STATUS  current
    DESCRIPTION
                "The manufacturer-provided description of this media path in
        the localization specified by prtGeneralCurrentLocalization.
	Refer to Standard Printer MIB for more details."
::= { prtMediaPathEntry 10 }


prtmediapathstatus OBJECT-TYPE
    SYNTAX  INTEGER
    MAX-ACCESS read-only
    STATUS  current
    DESCRIPTION
                "The current status of this media path.
	Refer to Standard Printer MIB for more details.
                Additional information:
                The default values assume the printer is idle."
::= { prtMediaPathEntry 11 }


collated-originals-support OBJECT-TYPE
    SYNTAX  OCTET STRING
    MAX-ACCESS read-only
    STATUS  current
    DESCRIPTION
                "Indicates that the printer can create multiple, collated
                'originals' of a job and shows the level of support for
                this capability.
                  cCollatedOriginals - The printer can create multiple
                collated originals, or 'mopies'.  This is the base
                functionality required by the other collection items.
                  cProofAndHold - The printer saves a copy of the job
                while printing the first mopy.  Later, this held job can
                be released and the rest of the mopies will print.
                  cSecurityPrint - The printer spools the job and holds
                the job until the user releases the job by entering a
                password at the printer's control panel.
                  cAutoHighlight - The printer prints  the job a number
                of times with a mail distribution list prepended to each
                job.  A different mailing address is highlighted on each
                mopy.
                  cCollatedAtSpeed - The printer can create multiple
                collated copies where all copies after the original are
                printed at engine speed.
                Additional information:
                Indicates that the printer can create multiple, collated
                originals of a job and shows the level of support for this
                capability.
                cCollatedOriginals - The printer can create multiple collated
                originals, or mopies.

                This is the base functionality required by the other
                collection items.  None of them are supported by Jonah.
                Without disk, this object will not exist. This will be set at
                boot-up initialization. If the disk fails, in any way, then
                the disk error functionality will handle the situation.

                The value of this object will be:
                !cCollatedOriginals - Only FLASH installed
                cCollatedOriginals  - IDE is installed combined
                with/without FLASH
                	       cCollatedOriginals  - RAMDISK is On combined with/without FLASH"
::= { status-system 42 }

-- 1.3.6.1.4.1.11.2.3.9.4.2.1.4.1.10.7.
consumable-current-state   OBJECT-TYPE
     SYNTAX          INTEGER {
                                             cAuthLevel1(0),
                                            cAuthLevel2(1),
                                            cAuthLevel3(2),
                                            cAuthLevel4(3),
                                            cAuthLevel5(4),
                                            cAuthLevel6(5),
                                            cAuthLevel7(6),
                                            cGenuineHPUnsupported(8),
                                            cELabelDefective(9),
                                            cELabelMissing(10),
                                            cLowCondition(11),
                                            cOutCondition(12),
                                            cIncorrect(13),
                                            cMissing(14),
                                            cPastOutCondition(15),
                                            cConfigurableLow(16),
                                            cExpired(17),
                                            cFailure(18),
                                            cLeak(19),
                                            cUnknownManufacturer(20),
                                            cUnsupported(21),
                                            cUnavailable(22),
                                            cIncompatible(23),
                                            cStatusAreValid(31)
                             }
     MAX-ACCESS read-only
     STATUS            current
     DESCRIPTION " This PML object returns the current state of the particular
     consumable. \\
             cAuthLevel1 - Consumable is at Authentication Level 1 \\
             cAuthLevel2 - Consumable is at Authentication Level 2 \\
             cAuthLevel3 - Consumable is at Authentication Level 3 \\
             cAuthLevel4 - Consumable is at Authentication Level 4 \\
             cAuthLevel5 - Consumable is at Authentication Level 5 \\
             cGenuineHPUnsupported - Cartridge is GenuineHP intended for another product \\
        cDefectiveMemory - Cartridge has a defective memory tag \\
        cMissingMemory - Memory tag is missing from the cartridge\\
        cLowCondition - Consumable has reached the engine low threshold \\
        cOutCondition - Consumable has reached its out threshold \\
        cIncorrect - Cartridge inserted is not the correct one \\
        cMissing - Consumable is missing from the printer \\
        cConfigurableLow - Consumable has reached the configurable low threshold value \\
        cStatusArevalid - The status reported on other bits are
                valid only if the bit is set to 1. If it is 0, the values are invalid. \\
        cExpired - Is the cartridge expired, which is determined \\
                        by the formatter.\\
        cFailure - Cartridge has failed determined by the engine. \\
        cLeak - Cartridge has a leak as determined by the engine. \\
        cUnknownManufacturer - the brand of the cartridge is \\
        unknown as determined by the engine. \\
        cUnsupported --- Cartridge is not supported as determined\\
                                        by the engine. \\
        cIncompatible - When installed consumable is incompatible with
                current printer. These are the possible states and whenever the
                consumable is in any of these states, the appropriate bit will
                be set. The cLowCondition will be set when the consumable
                reaches the engine low threshold, and cConfigurableLow will be
                set when the consumable reaches the Configurable Low threshold
                value. For non-cartridge supplies only cLowCondition,
                cOutCondition, and cMissing will be supported "
::= { consumables 7 }

-- 1.3.6.1.4.1.11.2.3.9.4.2.1.4.1.10.9
device-used-while-cartridge-out-override-active   OBJECT-TYPE
    SYNTAX          INTEGER {
                              eNotUsed(1),
                             eUsed(2)
                    }
    MAX-ACCESS read-only
    STATUS            current
    DESCRIPTION " Returns eUsed if the device has ever been used while Cartridge
    Out Override is activated. Merely enabling cartridge out
    override will not cause eUsed to be returned. Cartridge Out
    Override must be activated by a cartridge becoming out and
    device must be used in that mode"
::= { consumables 9 }

-- 1.3.6.1.4.1.11.2.3.9.4.2.1.4.1.10.11.
consumable-pages-printed-with-supply   OBJECT-TYPE
    SYNTAX          INTEGER
    MAX-ACCESS read-only
    STATUS            current
    DESCRIPTION " This PML object returns the number of pages printed with a
    cartridge consumable. This PML object returns the value that
    should be displayed under 'Pages Printed With This Supply' for
    cartridges in color products"
::= { consumables 11 }

-- 1.3.6.1.4.1.11.2.3.9.4.2.1.4.1.10.15.
total-kilo-pixels-per-cartridge   OBJECT-TYPE
    SYNTAX          INTEGER
    MAX-ACCESS read-only
    STATUS            current
    DESCRIPTION " Returns the total number of kilo-pixels at 600dpi in the
    cartridge. That is, the number returned by this object should
    be multiplied by 1000 to determine the total number of pixels
    at 600dpi in the cartridge "
::= { consumables 15 }

-- 1.3.6.1.4.1.11.2.3.9.4.2.1.4.1.10.16
consumable-replacement-count   OBJECT-TYPE
    SYNTAX          INTEGER
    MAX-ACCESS read-write
    STATUS            current
    DESCRIPTION "The total number of times a consumable has been replaced.
         "
::= { consumables 16 }

-- 1.3.6.1.4.1.11.2.3.9.4.2.1.4.1.10.18
consumable-pages-since-replacement   OBJECT-TYPE
    SYNTAX          INTEGER
    MAX-ACCESS read-write
    STATUS            current
    DESCRIPTION "The total number of pages fed since the last replacement of the
    consumable.
         "
::= { consumables 18 }

-- 1.3.6.1.4.1.11.2.3.9.4.2.1.4.1.10.5.2
supplies-at-very-low-delay   OBJECT-TYPE
    SYNTAX           INTEGER {
                              eDisabled(1),
                             eEnabled(2)
                    }
    MAX-ACCESS read-write
    STATUS            current
    DESCRIPTION " Indicates if the transition to a VERY LOW state should be
    delayed by the number of pages specified in
    SUPPLIES-AT-VERY-LOW-DELAY-LIMIT"
::= { consumables-status 2 }

-- 1.3.6.1.4.1.11.2.3.9.4.2.1.4.1.10.5.1.1.
consumable-life-usage-units-remaining   OBJECT-TYPE
    SYNTAX          INTEGER
    MAX-ACCESS read-only
    STATUS            current
    DESCRIPTION " This object reports the current estimate of the number of usage
    units that remain before this supply is depleted. An installed
    supply that cannot report such a number will return a value of
    -2. It is the reponsibility of the host application to query
    each supply in order to determine an overall device
    USAGE-UNITS-REMAINING number - the lowest value returned. The
    unit of measure for this life estimate is determined by reading
    the corresponding CONSUMABLE-LIFE-USAGE-UNITS object"
::= { consumables-life 1 }

-- 1.3.6.1.4.1.11.2.3.9.4.2.1.4.1.10.5.1.2.
consumable-life-usage-units   OBJECT-TYPE
    SYNTAX          INTEGER {
                              ePagesRemaining(1),
                             eEstimatedPagesRemaining(2),
                             eUnknownUnits(3),
                             ePagesSinceLow(4),
                             ePagesSinceOut(5),
                             ePagesPicked(6),
                             ePercentLifeRemaining(7),
                             e4X6ImagesPrinted(8),
                             eEngineDropCount(9),
                             eEngineWebAdvances(10)
                    }
    MAX-ACCESS read-only
    STATUS            current
    DESCRIPTION " This object reports current usage units in use by the
    corresponding CONSUMABLE-LIFE-USAGE-UNITS-REMAINING object"
::= { consumables-life 2 }

-- 1.3.6.1.4.1.11.2.3.9.4.2.1.4.1.10.5.1.3.
consumable-life-low-threshold   OBJECT-TYPE
    SYNTAX          INTEGER
    MAX-ACCESS read-write
    STATUS            current
    DESCRIPTION " This object is used to report and modify a threshold value
    indicating the point in the life of a consumable or supply at
    which a transition to a LOW state will occur"
::= { consumables-life 3 }

-- 1.3.6.1.4.1.11.2.3.9.4.2.1.4.1.10.5.1.4.
estimated-page-yield   OBJECT-TYPE
    SYNTAX          INTEGER
    MAX-ACCESS read-only
    STATUS            current
    DESCRIPTION " Returns the estimated yield of the cartridge in
    ESTIMATED-PAGE-YIELD-UNIT units"
::= { consumables-life 4 }

-- 1.3.6.1.4.1.11.2.3.9.4.2.1.4.1.10.5.1.5.
estimated-page-yield-unit   OBJECT-TYPE
    SYNTAX          INTEGER {
                              e5PercentPages(1),
                             eISOPages(2)
                    }
    MAX-ACCESS read-only
    STATUS            current
    DESCRIPTION " Returns the unit used for ESTIMATED-PAGE-YIELD"
::= { consumables-life 5 }

-- 1.3.6.1.4.1.11.2.3.9.4.2.1.4.1.10.5.1.6.
supplies-at-very-low-delay-limit   OBJECT-TYPE
    SYNTAX           INTEGER
    MAX-ACCESS read-write
    STATUS            current
    DESCRIPTION " This object is used to report and modify a very low delay limit
    value indicating the number of pages to delay the transition to
    a very low state for a supply."
::= { consumables-life 6 }

printer-average-marking-agent-units-per-gram OBJECT-TYPE
   SYNTAX      OCTET STRING
   MAX-ACCESS  read-only
   STATUS      current
   DESCRIPTION "This object is used to read the marking agent units of measure
        per gram. This is typically a conversion factor for converting
        pixels of toner to grams. This pixels-per-gram value is used to
        calculate the estimated number of pages remaining for a given
        marking agent."
::= { printer-average 4 }


printer-average-marking-agent-coverage-actual OBJECT-TYPE
   SYNTAX      OCTET STRING
   MAX-ACCESS  read-only
   STATUS      current
   DESCRIPTION "This object is used to read the actual average marking agent
        coverage for a given color plane. It is a real number that
        represents percent coverage and will read from 0 to 100%. This
        object will return the same value as
        PRINTER-AVERAGE-MARKING-AGENT-COVERAGE except under certain
        conditions which will be specified in the device POS."
::= { printer-average 5 }

file-system-memory OBJECT-TYPE
    SYNTAX  INTEGER
    MAX-ACCESS read-only
    STATUS  current
    DESCRIPTION
                "The amount of memory, in bytes, used by the file system
                to buffer file data.
                Additional information:
                Reports the amount of memory, in bytes,
                reserved for use by the file system.  Returns
                <noSuchName> status if attempting
                to access this object and there is no storage device
                is installed.  The values remain constant across reboots.
                	   Possible Values:
                	     FILE-SYSTEM-MAX-OPEN-FILES    32       512
                	       EIO DISK                   69916    198556
                	       EIO DISK + 1 2MB Flash     88940    217580
                	       1 2MB Flash                33052    161692"
::= { settings-file-system 1 }


file-system-test-return-code OBJECT-TYPE
    SYNTAX  OCTET STRING
    MAX-ACCESS read-write
    STATUS  current
    DESCRIPTION
                "This test object that will not be supported in any
                released product.  Setting this object allows the next
                file system call return code to be specified or to
                simulate uninitialized or unistalled volumes.  The POS
                will specify the binary format.
                Additional information:
                A three byte binary value.  The first
                byte indicates what function is being effected by
                this set.
                value | function
                ------+------------------
                1   | PersFSCtl
                2   | PersFSDirClose
                3   | PersFSDirCreate
                4   | PersFSDirDelete
                5   | PersFSDirOpen
                6   | PersFSDirRead
                7   | PersFSDirReadStd
                8   | PersFSDirRewind
                9   | PersFSDirSeek
                10  | PersFSDirTell
                11  | PersFSFileClose
                12  | PersFSFileDelete
                13  | PersFSFileMove
                14  | PersFSFileOpen
                15  | PersFSFileRead
                16  | PersFSFileSeek
                17  | PersFSFileStatus
                18  | PersFSFileWrite
                19  | PersFSFlush
                20  | PersFSVolChk
                21  | PersFSVolFix
                22  | PersFSVolInit
                23  | PersFSVolStatus
                The return value of the function being effected will
                return the value -1 to indicate an error occurred.
                The second byte is the
                value returned by the next call to PersFSErrNo()
                (after the call being effected is called).  Refer to
                the 'Copernicus Personality Interface Volume 2 Disk
                File System' documentation for a list of values
                returned by PersFSErrNo().  The third byte indicates
                which call to the specified file system routine will
                fail.  A value of one means the first call will fail.
                A value of two means the second call will fail, and
                so on.  Writing this object causes any previous write to
                this object to be invalidated.
                Note: The error triggering
                mechanism is actually implemented at the message
                interface to the file system rather than at the PersFSxxx()
                function call interface.  This is easier to do, and
                it is better for NFS because NFS uses the message
                interface rather than the PersFSxxx() functions.
                Fortunately there is a one-to-one mapping between
                messages and PersFSxxx() functions so everything
                works out nicely.
                The printer will uninitialize the mass storage device if
                the first byte is one of the values listed below.
                value | meaning
                ------+------------------
                101  | Effects the printer state
                102  | Effects the data on the device
                The Moby printer supports 3 volumes zero, so the
                second byte must be 0 - 2. The third byte has no meaning
                and must be zero."
::= { settings-file-system 3 }


file-system-statistic-read-open OBJECT-TYPE
    SYNTAX  INTEGER
    MAX-ACCESS read-only
    STATUS  current
    DESCRIPTION
                "The number of times the file system has received
                requests to open a file for reading.  Opening a file for
                both reading and writing will cause this value to
                change.  The POS should state if a power cycle causes
                the counter is be reset to zero.
                Additional information:
                Reset to the factory default value after
                a power cycle.
                Returns <noSuchName>
                status if attempting to access this object and there
                is no storage device is installed.  This value is
                	   increamented when a file is opened."
::= { status-file-system 1 }


file-system-statistic-write-open OBJECT-TYPE
    SYNTAX  INTEGER
    MAX-ACCESS read-only
    STATUS  current
    DESCRIPTION
                "The number of times the file system has received
                requests to open a file for writing.  Opening a file for
                both reading and writing will cause this value to
                change.  The POS should state if a power cycle causes
                the counter is be reset to zero.
                Additional information:
                Reset to the factory default value after
                a power cycle.
                Returns <noSuchName>
                status if attempting to access this object and there
                is no storage device is installed.  This value is
                	   increamented when a file is opened."
::= { status-file-system 2 }


file-system-statistic-successful OBJECT-TYPE
    SYNTAX  INTEGER
    MAX-ACCESS read-only
    STATUS  current
    DESCRIPTION
                "A counter indicating the number of file system requests
                that completed successfully.  The POS should state if a
                power cycle causes the counter is be reset to zero.
                Additional information:
                Reset to the factory default value after
                a power cycle.
                Returns <noSuchName>
                status if attempting to access this object and there
                is no storage device is installed."
::= { status-file-system 3 }


file-system-statistic-unsuccessful OBJECT-TYPE
    SYNTAX  INTEGER
    MAX-ACCESS read-only
    STATUS  current
    DESCRIPTION
                "A counter indicating the number of file system requests
                that completed unsuccessfully.  The POS should state if
                a power cycle causes the counter is be reset to zero.
                Additional information:
                Reset to the factory default value after
                a power cycle.
                Returns <noSuchName>
                status if attempting to access this object and there
                is no storage device is installed."
::= { status-file-system 4 }


file-system-statistic-current-memory-usage OBJECT-TYPE
    SYNTAX  INTEGER
    MAX-ACCESS read-only
    STATUS  current
    DESCRIPTION
                "A value indicating the number of bytes of RAM currently
                used by the file system firmware.
                Additional information:
                Reset to the factory default value after
                a power cycle.
                Returns <noSuchName>
                status if attempting to access this object and there
                is no storage device is installed.  This will veri
                	   depending on the number and size of Mass Storage
                	   devices installed."
::= { status-file-system 5 }


file-system-statistic-max-memory-usage OBJECT-TYPE
    SYNTAX  INTEGER
    MAX-ACCESS read-only
    STATUS  current
    DESCRIPTION
                "A value indicating the maximum number of bytes of RAM
                used by the file system firmware.  The POS should state
                if the value is reset to zero after a power cycle.
                Additional information:
                Reset to the factory default value after
                a power cycle.
                Returns <noSuchName>
                status if attempting to access this object and there
                is no storage device is installed."
::= { status-file-system 6 }

file-system1-initialized OBJECT-TYPE
    SYNTAX  INTEGER {
		   eFalse(1),
		   eTrue(2)
		   }
    MAX-ACCESS read-only
    STATUS  current
    DESCRIPTION
                "Returns eTrue if a file system has been written to the
                mass storage device(s) which will hold file data
                contained in this file system.  Returns eFalse
                otherwise.  Each POS needs to specify the relationship
                between file systems and the physical storage devices
                that can hold the data contained in those file systems.
                Additional information:
                This objects is only supported if a disk is
                installed.
                Returns <noSuchName> status if
               	attempting to perform a Get on this OID with no disk
               	installed.
               	Returns <noSuchName>
               	status if attempting to perform a Set, EnableTrap, or
               	DisableTrap on this OID with no disk installed."
::= { file-system1 1 }


file-system1-capacity OBJECT-TYPE
    SYNTAX  INTEGER
    MAX-ACCESS read-only
    STATUS  current
    DESCRIPTION
                "Returns the total size, in bytes, of the mass storage
                space configured to hold the file data (and file system
                information) assoicated with files stored in this file
                system.  This refers to hardware capacity, independent
                of any space consumed by the file system overhead or
                user files.
                Additional information:
                This objects is only supported if a disk is
               	installed.
               	Returns <noSuchName> status if
               	attempting to perform a Get on this OID with no disk
               	installed.
               	Returns <noSuchName>
               	status if attempting to perform a Set, EnableTrap, or
               	DisableTrap on this OID with no disk installed."
::= { file-system1 2 }


file-system1-free-space OBJECT-TYPE
    SYNTAX  INTEGER
    MAX-ACCESS read-only
    STATUS  current
    DESCRIPTION
                "Returns the total amount, in bytes, of unused storage
                space currently available to this file system.
                Additional information:
                This objects is only supported if a disk is
               	installed.
               	Returns <noSuchName> status if
               	attempting to perform a Get on this OID with no disk
               	installed.
               	Returns <noSuchName>
               	status if attempting to perform a Set, EnableTrap, or
               	DisableTrap on this OID with no disk installed."
::= { file-system1 3 }


file-system1-write-protect OBJECT-TYPE
    SYNTAX  INTEGER {
		   eDisabled(1),
		   eEnabled(2)
		   }
    MAX-ACCESS read-write
    STATUS  current
    DESCRIPTION
                "Supports write-protecting the file system.  Setting
                FILE-SYSTEM-WRITE-PROTECT to eEnabled blocks any
                modification of the contents of the file system.
                Setting FILE-SYSTEM-WRITE-PROTECT to eDisabled allows
                modification of the contents of the file system.
                Additional information:
                This objects is only supported if a disk is
               	installed.
               	Returns <noSuchName> status if
               	attempting to perform a Get, or Set on this OID
               	with no disk installed.
               	Returns <noSuchName>
               	status if attempting to perform an EnableTrap, or
               	DisableTrap on this OID with no disk installed."
::= { file-system1 4 }


file-system2-initialize-volume OBJECT-TYPE
    SYNTAX  INTEGER {
		   eInitializing(2)
		   }
    MAX-ACCESS read-write
    STATUS  current
    DESCRIPTION
                "Setting this object to eInitializing causes file system
                2 to be initialized.  Reading this object indicates if
                the file system is currently being initialized.
                Additional information:
                The hrDeviceIndex value for the mass storage
                device is the same value that is used to index into the
                FILE-SYSTEM sub-tree.  Since this product supports
                up to 3  mass storage device, and since the hrDeviceIndex
                for the mass storage devices will start at 2 if the mass
                	   storage device is installed, the FILE-SYSTEM2-INITIALIZE-VOLUME
                	   object will be the object that allows the mass storage device to be
                initialized that is the 1st device."
::= { file-system2 6 }


file-system3-initialize-volume OBJECT-TYPE
    SYNTAX  INTEGER {
		   eInitializing(2)
		   }
    MAX-ACCESS read-write
    STATUS  current
    DESCRIPTION
                "Setting this object to eInitializing causes file system
                3 to be initialized.  Reading this object indicates if
                the file system is currently being initialized.
                Additional information:
                The hrDeviceIndex value for the mass storage
                device is the same value that is used to index into the
                FILE-SYSTEM sub-tree.  Since this product supports
                up to 3  mass storage device, and since the hrDeviceIndex
                for the mass storage devices will start at 2 if the mass
                	   storage device is installed, the FILE-SYSTEM3-INITIALIZE-VOLUME
                	   object will be the object that allows the mass storage device to be
                initialized that is the 2nd device."
::= { file-system3 6 }


file-system4-initialize-volume OBJECT-TYPE
    SYNTAX  INTEGER {
		   eInitializing(2)
		   }
    MAX-ACCESS read-write
    STATUS  current
    DESCRIPTION
                "Setting this object to eInitializing causes file system
                4 to be initialized.  Reading this object indicates if
                the file system is currently being initialized.
                Additional information:
                The hrDeviceIndex value for the mass storage
                device is the same value that is used to index into the
                FILE-SYSTEM sub-tree.  Since this product supports
                up to 3  mass storage devices, and since the hrDeviceIndex
                for the mass storage devices will start at 2 if the mass
                	   storage device is installed, the FILE-SYSTEM4-INITIALIZE-VOLUME
                	   object will be the object that allows the mass storage device to be
                initialized that is the 3rd device."
::= { file-system4 6 }


mass-storage-resource-change-counter OBJECT-TYPE
    SYNTAX  INTEGER
    MAX-ACCESS read-only
    STATUS  current
    DESCRIPTION
                "A counter which changes when a mass storage based
                resource has been added or deleted.
                Additional information:
                The value of this counter changes
                each time the MASS-STORAGE-RESOURCE-CHANGED object
                is set to eTrue.  The value also changes when the
                mass storage device is initialized.  However, the value does not
                change when a mass storage device is removed and a different
                mass storage device is installed.  Initializing all volumes sets
                this object back to the factory default value.  A reboot sets
                	   this object back to the factory devalut value.
                Returns <noSuchName>
                status if attempting to access this object and there
                is no storage device is installed."
::= { mass-storage-resources 1 }


mass-storage-resource-changed OBJECT-TYPE
    SYNTAX  INTEGER {
		   eTrue(2)
		   }
    MAX-ACCESS read-write
    STATUS  current
    DESCRIPTION
                "Setting to eTrue causes MASS-STORAGE-RESOURCE-CHANGE-
                COUNTER to be incremented.
                Additional information:
                Returns <noSuchName>
                status if attempting to access this object and there
                is no storage device is installed."
::= { mass-storage-resources 2 }


hrstoragesize OBJECT-TYPE
    SYNTAX  INTEGER(0..2147483647)
    MAX-ACCESS read-only
    STATUS  current
    DESCRIPTION
                "The size of the storage represented by this entry,
              in units of hrStorageAllocationUnits.
              Refer to RFC 1514, Host Resources MIB, for more details.
                Additional information (printer):
                Total formatter RAM.
                Additional information (mass storage):
                Applications can determine the size of the
                installed mass storage device by getting the
                hrStorageAllocationUnits object and this object. The size
                of the mass storage device is these two returned values multiplied
                together.  Returns <noSuchName>
                status if attempting to perform a Get on this OID
                with no mass storage device installed."
::= { hrStorageEntry 5 }


hrdevicedescr OBJECT-TYPE
    SYNTAX  OCTET STRING (SIZE(0..64))
    MAX-ACCESS read-only
    STATUS  current
    DESCRIPTION
                "A textual description of this device, including
              the device's manufacturer and revision, and
              optionally, its serial number.
              Refer to RFC 1514, Host Resources MIB, for more details.
                Additional information (printer) :
                The serial number is not returned with this object.
                This object is not localized.
                Additional information (mass storage) :
                Returns <noSuchName>
                status if attempting to perform a Get on this OID
                with no mass storage device installed."
::= { hrDeviceEntry 3 }


hrdeviceid OBJECT-TYPE
    SYNTAX  OBJECT IDENTIFIER
    MAX-ACCESS read-only
    STATUS  current
    DESCRIPTION
                "The product ID for this device.
              Refer to RFC 1514, Host Resources MIB, for more details.
                Additional information (printer) :
                The complete OID reported by this object is:
                .1.3.6.1.4.1.11.2.3.9.1.2.12
                Additional information (mass storage) :
                Constant.  Since we don't know all the
                possible registered OIDs for each mass storage device model that
                could be installed in this printer, this object
                always returns the unknown product ID.  Returns
                <noSuchName> status if attempting
                to perform a Get on this OID with no mass storage device
                installed."
::= { hrDeviceEntry 4 }


hrdeviceerrors OBJECT-TYPE
    SYNTAX  INTEGER
    MAX-ACCESS read-only
    STATUS  current
    DESCRIPTION
                "The number of errors detected on this device.  It
               should be noted that as this object has a SYNTAX
               of Counter, that it does not have a defined
               initial value.  However, it is recommended that
               this object be initialized to zero.
               Refer to RFC 1514, Host Resources MIB, for more details.
                Additional information (mass storage):
                Total number of read and write errors
                that have occurred since the printer was turned on.
                Returns <noSuchName> status if
                attempting to perform a Get on this OID with no mass storage device
                installed.  Returns 0 if the mass storage device is
                	   uninitialized."
::= { hrDeviceEntry 6 }


hrdiskstorageaccess OBJECT-TYPE
    SYNTAX  INTEGER {
		   eHreadWrite(1),
		   eHreadOnly(2)
		   }
    MAX-ACCESS read-write
    STATUS  current
    DESCRIPTION
                "An indication if this long-term storage device is
              readable and writable or only readable.  This
              should reflect the media type, any write-protect
              mechanism, and any device configuration that
              affects the entire device.
              Refer to RFC 1514, Host Resources MIB, for more details.
                Additional information:
                This object can be set to write protect
                the mass storage device, even though the host resources MIB
                documents the object as read-only.  Applications wanting to
                know if the mass storage device is writable should get this
                object.  Applications wanting to change the read/write access
                of the mass storage device should set this object.
                If this object is set to write-protect while a file is being
                written to the mass storage device, the write-protect takes effect
                immediately and the new file doesn't appear in the file system.
                Returns <noSuchName> status if attempting to
                perform a Get on this OID with no mass storage device installed."
::= { hrDiskStorageEntry 1 }


hrdiskstoragemedia OBJECT-TYPE
    SYNTAX  INTEGER {
		   eHother(1),
		   eHhardDisk(3),
		   eHramDisk(8)
		   }
    MAX-ACCESS read-only
    STATUS  current
    DESCRIPTION
                "An indication of the type of media used in this
              long-term storage device.
              Refer to RFC 1514, Host Resources MIB, for more details.
                Additional information:
                Constant.  Applications can determine if the
                installed mass storage device is a disk or is flash by
                getting this value.
                		  Possible Values:
                		    EIO DISK returns   eHhardDisk
                		    Ram Disk returns   eHramDisk
                		    Flash Disk returns eHother
                	   Returns <noSuchName> status if attempting
                to perform a Get on this OID with no mass storage device
                installed."
::= { hrDiskStorageEntry 2 }


hrdiskstorageremoveble OBJECT-TYPE
    SYNTAX  INTEGER {
		   eHfalse(2)
		   }
    MAX-ACCESS read-only
    STATUS  current
    DESCRIPTION
                "Denotes whether or not the disk media may be
               removed from the drive.
               Refer to RFC 1514, Host Resources MIB, for more details.
                Additional information:
                Constant.  Returns
                <noSuchName> status if attempting
                to perform a Get on this OID with no mass storage device
                installed."
::= { hrDiskStorageEntry 3 }


hrdiskstoragecapacity OBJECT-TYPE
    SYNTAX  INTEGER
    MAX-ACCESS read-only
    STATUS  current
    DESCRIPTION
                "The total size for this long-term storage device.
              Refer to RFC 1514, Host Resources MIB, for more details.
                Additional information:
                The capacity is in Kbytes.  Returns
                <noSuchName> status if attempting
                to perform a Get on this OID with no mass storage device
                installed."
::= { hrDiskStorageEntry 4 }


hrpartitionindex OBJECT-TYPE
    SYNTAX  INTEGER(1..2147483647)
    MAX-ACCESS read-only
    STATUS  current
    DESCRIPTION
                "A unique value for each partition on this long-
              term storage device.  The value for each long-term
              storage device must remain constant at least from
              one re-initialization of the agent to the next re-
              initialization.
              Refer to RFC 1514, Host Resources MIB, for more details.
                Additional information:
                Constant.  The first and second index
                indicates the hrDeviceIndex for this mass storage device.
                The value of this object is the same as
                the second index.  The printer only supports one
                partition per mass storage device.  Returns
                <noSuchName> status if attempting
                to perform a Get on this OID with no mass storage device
                installed."
::= { hrPartitionEntry 1 }


hrpartitionlabel OBJECT-TYPE
    SYNTAX  OCTET STRING (SIZE(0..11))
    MAX-ACCESS read-write
    STATUS  current
    DESCRIPTION
                "A textual description of this partition.
              Refer to RFC 1514, Host Resources MIB, for more details.
                Additional information:
                The MS-DOS volume label.  The volume
                label is writable.  Returns
                <noSuchName> status if attempting
                to perform a Get on this OID with no mass storage device installed.
                This object is settable and returns the empty
                string if the mass storage device has not been initialized.  NOTE
                	   the RamDisk will lose this value after a PowerCycle."
::= { hrPartitionEntry 2 }


hrpartitionid OBJECT-TYPE
    SYNTAX  OCTET STRING
    MAX-ACCESS read-only
    STATUS  current
    DESCRIPTION
                "A descriptor which uniquely represents this
              partition to the responsible operating system.  On
              some systems, this might take on a binary
              representation.
              Refer to RFC 1514, Host Resources MIB, for more details.
                Additional information:
                Constant.  The value returned is the
                ASCII string version of the hrDeviceIndex for
                this mass storage device.  Returns
                <noSuchName> status if attempting
                to perform a Get on this OID with no mass storage device
                installed."
::= { hrPartitionEntry 3 }


hrpartitionsize OBJECT-TYPE
    SYNTAX  INTEGER
    MAX-ACCESS read-only
    STATUS  current
    DESCRIPTION
                "The size of this partition.
               Refer to RFC 1514, Host Resources MIB, for more details.
                Additional information:
                The capacity is in Kbytes.  Returns the
                same value as hrDiskStorageCapacity.  Returns
                <noSuchName> status if attempting
                to perform a Get on this OID with no mass storage device
                installed."
::= { hrPartitionEntry 4 }


hrpartitionfsindex OBJECT-TYPE
    SYNTAX  INTEGER(0..2147483647)
    MAX-ACCESS read-only
    STATUS  current
    DESCRIPTION
                "The index of the file system mounted on this
               partition.  If no file system is mounted on this
               partition, then this value shall be zero.  Note
               that multiple partitions may point to one file
               system, denoting that that file system resides on
               those partitions.  Multiple file systems may not
               reside on one partition.
               Refer to RFC 1514, Host Resources MIB, for more details.
                Additional information:
                Indicates if the mass storage device has been
                initialized.  Applications determine if the storage device
                has been initialized by getting this object.  Returns zero
                if the mass storage device is not
                initialized, otherwise the value matches the
                hrDeviceIndex value for this mass storage device.
                The value indicates the
                hrFileSystemTable index for the file system stored
                on this partition.  Returns
                <noSuchName> status if attempting
                to perform a Get on this OID with no mass storage device
                installed."
::= { hrPartitionEntry 5 }


hrfsindex OBJECT-TYPE
    SYNTAX  INTEGER(1..2147483647)
    MAX-ACCESS read-only
    STATUS  current
    DESCRIPTION
                "A unique value for each file system local to this
               host.  The value for each file system must remain
               constant at least from one re-initialization of
               the agent to the next re-initialization.
               Refer to RFC 1514, Host Resources MIB, for more details.
                Additional information:
                Constant.  The index is assigned by the
                person controlling the printer object definition.
                Returns <noSuchName> status if
                attempting to perform a Get on this OID with no mass storage device
                installed or if the file system has not been
                initialized."
::= { hrFSEntry 1 }


hrfsmountpoint OBJECT-TYPE
    SYNTAX  OCTET STRING
    MAX-ACCESS read-only
    STATUS  current
    DESCRIPTION
                "The path name of the root of this file system.
               Refer to RFC 1514, Host Resources MIB, for more details.
                Additional information:
                Constant.  Returns
                <noSuchName> status if attempting
                to perform a Get on this OID with no mass storage device installed
                or if the file system has not been initialized."
::= { hrFSEntry 2 }


hrfsremotemountpoint OBJECT-TYPE
    SYNTAX  OCTET STRING
    MAX-ACCESS read-only
    STATUS  current
    DESCRIPTION
                "A description of the name and/or address of the
               server that this file system is mounted from.
               This may also include parameters such as the mount
               point on the remote file system.  If this is not a
               remote file system, this string should have a
               length of zero.
               Refer to RFC 1514, Host Resources MIB, for more details.
                Additional information:
                Constant.  This printer does not support
                remote file system mounting.  Returns
                <noSuchName> status if attempting
                to perform a Get on this OID with no mass storage device installed
                or if the file system has not been initialized."
::= { hrFSEntry 3 }


hrfstype OBJECT-TYPE
    SYNTAX  OBJECT IDENTIFIER
    MAX-ACCESS read-only
    STATUS  current
    DESCRIPTION
                "The value of this object identifies the type of
              this file system.
              Refer to RFC 1514, Host Resources MIB, for more details.
                Additional information:
                Constant.  Returns
                <noSuchName> status if attempting
                to perform a Get on this OID with no mass storage device installed
                or if the file system has not been initialized."
::= { hrFSEntry 4 }


hrfsaccess OBJECT-TYPE
    SYNTAX  INTEGER {
		   eHreadWrite(1),
		   eHreadOnly(2)
		   }
    MAX-ACCESS read-write
    STATUS  current
    DESCRIPTION
                "An indication if this file system is logically
              configured by the operating system to be readable
              and writable or only readable.  This does not
              represent any local access-control policy, except
              one that is applied to the file system as a whole.
              Refer to RFC 1514, Host Resources MIB, for more details.
                Additional information:
                Returns the same value as
                hrDiskStorageAccess.  Returns
                <noSuchName> status if attempting
                to perform a Get on this OID with no mass storage device installed
                or if the file system has not been initialized."
::= { hrFSEntry 5 }


hrfsbootable OBJECT-TYPE
    SYNTAX  INTEGER {
		   eHfalse(2)
		   }
    MAX-ACCESS read-only
    STATUS  current
    DESCRIPTION
                "A flag indicating whether this file system is
              bootable.
              Refer to RFC 1514, Host Resources MIB, for more details.
                Additional information:
                Constant.  Returns
                <noSuchName> status if attempting
                to perform a Get on this OID with no mass storage device installed
                or if the file system has not been initialized."
::= { hrFSEntry 6 }


hrfsstorageindex OBJECT-TYPE
    SYNTAX  INTEGER(0..2147483647)
    MAX-ACCESS read-only
    STATUS  current
    DESCRIPTION
                "The index of the hrStorageEntry that represents
               information about this file system.  If there is
               no such information available, then this value
               shall be zero.  The relevant storage entry will be
               useful in tracking the percent usage of this file
               system and diagnosing errors that may occur when
               it runs out of space.
               Refer to RFC 1514, Host Resources MIB, for more details.
                Additional information:
                Constant.  The value indicates the
                hrStorageTable index for this mass storage device.  Returns
                <noSuchName> status if attempting
                to perform a Get on this OID with no mass storage device installed
                or if the file system has not been initialized."
::= { hrFSEntry 7 }


hrfslastfullbackupdate OBJECT-TYPE
    SYNTAX  OCTET STRING
    MAX-ACCESS read-only
    STATUS  current
    DESCRIPTION
                "The last date at which this complete file system
              was copied to another storage device for backup.
              This information is useful for ensuring that
              backups are being performed regularly.
              If this information is not known, then this
              variable shall have the value corresponding to
              January 1, year 0000, 00:00:00.0, which is encoded
              as (hex)'00 00 01 01 00 00 00 00'.
              Refer to RFC 1514, Host Resources MIB, for more details.
                Additional information:
                Constant.
                The default value is the value defined
                to represent an unknown time of January 1, year 0000,
                00:00:00.0.  Returns <noSuchName>
                status if attempting to perform a Get on this OID
                with no mass storage device installed or if the file system has not
                been initialized."
::= { hrFSEntry 8 }


hrfslastpartialbackupdate OBJECT-TYPE
    SYNTAX  OCTET STRING
    MAX-ACCESS read-only
    STATUS  current
    DESCRIPTION
                "The last date at which a portion of this file
              system was copied to another storage device for
              backup.  This information is useful for ensuring
              that backups are being performed regularly.
              If this information is not known, then this
              variable shall have the value corresponding to
              January 1, year 0000, 00:00:00.0, which is encoded
              as (hex)'00 00 01 01 00 00 00 00'.
              Refer to RFC 1514, Host Resources MIB, for more details.
                Additional information:
                Constant.
                The default value is the value defined
                to represent an unknown time of January 1, year 0000,
                00:00:00.0.  Returns <noSuchName>
                status if attempting to perform a Get on this OID
                with no mass storage device installed or if the file system has not
                been initialized."
::= { hrFSEntry 9 }



mio1-model-name OBJECT-TYPE
    SYNTAX  DisplayString
    MAX-ACCESS read-only
    STATUS  current
    DESCRIPTION
                "Returns product information identifying the I/O card.
                Example: XXXX"
::= { mio1 2 }


mio1-manufacturing-info OBJECT-TYPE
    SYNTAX  DisplayString
    MAX-ACCESS read-only
    STATUS  current
    DESCRIPTION
                "Returns information describing the manufacture of the
                I/O card installed in MIO/EIO slot 1.  May include
                serial number and firmware revision.
                Additional information:
                The format of the string returned is determined by
                the manufacturer of the EIO device. There is no standard for content of the
                string."
::= { mio1 3 }


mio1-type OBJECT-TYPE
    SYNTAX  INTEGER {
		   eEmpty(1),
		   eUnknown(2),
		   eDiskDrive(8),
		   eIOCard(12)
		   }
    MAX-ACCESS read-only
    STATUS  current
    DESCRIPTION
                "Returns an indication of the type of option installed in
                MIO/EIO slot 1.  See SIMM1-TYPE for an explanation of
                the enumerations."
::= { mio1 4 }


mio2-model-name OBJECT-TYPE
    SYNTAX  DisplayString
    MAX-ACCESS read-only
    STATUS  current
    DESCRIPTION
                "Returns product information identifying the I/O card.
                Example: XXXX"
::= { mio2 2 }


mio2-manufacturing-info OBJECT-TYPE
    SYNTAX  DisplayString
    MAX-ACCESS read-only
    STATUS  current
    DESCRIPTION
                "Returns information describing the manufacture of the
                I/O card installed in MIO/EIO slot 2.  May include
                serial number and firmware revision.
                Additional information:
                The format of the string returned is determined by
                the manufacturer of the EIO device. There is no standard for content of the
                string."
::= { mio2 3 }


mio2-type OBJECT-TYPE
    SYNTAX  INTEGER {
		   eEmpty(1),
		   eUnknown(2),
		   eDiskDrive(8),
		   eIOCard(12)
		   }
    MAX-ACCESS read-only
    STATUS  current
    DESCRIPTION
                "Returns an indication of the type of option installed in
                MIO/EIO slot 2.  See SIMM1-TYPE for an explanation of
                the enumerations."
::= { mio2 4 }

mio3-model-name OBJECT-TYPE
    SYNTAX  DisplayString
    MAX-ACCESS read-only
    STATUS  current
    DESCRIPTION
                "Returns product information identifying the I/O card.
                Example: XXXX"
::= { mio3 2 }


mio3-manufacturing-info OBJECT-TYPE
    SYNTAX  DisplayString
    MAX-ACCESS read-only
    STATUS  current
    DESCRIPTION
                "Returns information describing the manufacture of the
                I/O card installed in MIO/EIO interface 3.  May include
                serial number and firmware revision.
                Additional information:
                The format of the string returned is determined by
                the manufacturer of the EIO device. There is no standard for content of the
                string."
::= { mio3 3 }


mio3-type OBJECT-TYPE
    SYNTAX  INTEGER {
		   eEmpty(1),
		   eUnknown(2),
		   eDiskDrive(8),
		   eIOCard(12)
		   }
    MAX-ACCESS read-only
    STATUS  current
    DESCRIPTION
                "Returns an indication of the type of option installed in
                MIO/EIO interface 3.  See SIMM1-TYPE for an explanation
                of the enumerations."
::= { mio3 4 }

-- 1.3.6.1.4.1.11.2.3.9.4.2.1.1.4.3.4.2
mio4-model-name   OBJECT-TYPE
    SYNTAX          OCTET STRING
    MAX-ACCESS read-only
    STATUS            current
    DESCRIPTION " Returns product information identifying the I/O card. Example:
    XXXX"
::= { mio4 2 }

-- 1.3.6.1.4.1.11.2.3.9.4.2.1.1.4.3.4.3
mio4-manufacturing-info   OBJECT-TYPE
    SYNTAX          OCTET STRING
    MAX-ACCESS read-only
    STATUS          current
    DESCRIPTION " Returns information describing the manufacture of the I/O card
    installed in MIO/EIO interface 4. May include serial number and
    firmware revision"
::= { mio4 3 }

-- 1.3.6.1.4.1.11.2.3.9.4.2.1.1.4.3.4.4
mio4-type   OBJECT-TYPE
     SYNTAX          INTEGER {
                                            eEmpty(1),
                                            eUnknown(2),
                                            eUnSupported(3),
                                            eReadOnlyMemory(4),
                                            eVolatileRandomAccessMemory(5),
                                            eNonVolatileRandomAccessMemory(6),
                                            eFlashMemory(7),
                                            eDiskDrive(8),
                                            eRamRom(9),
                                            eInputPHD(10),
                                            eOutputPHD(11),
                                            eIOCard(12),
                                            eBindingPHD(13),
                                            eSDRandomAccessMemory(14),
                                            eSRandomAccessMemory(15),
                                            eFPMRandomAccessMemory(16),
                                            eEDORandomAccessMemory(17)
                             }
     MAX-ACCESS read-only
     STATUS            current
     DESCRIPTION " Returns an indication of the type of option installed in
     MIO/EIO interface 4. See SIMM1-TYPE for an explanation of the
     enumerations"
::= { mio4 4 }

job-info-change-id OBJECT-TYPE
    SYNTAX  OCTET STRING (SIZE(16))
    MAX-ACCESS read-only
    STATUS  current
    DESCRIPTION
                "Returns the current value of an object in the job-info
                sub-tree whose value has changed.  Define the object
                identifier for the object whose value has changed as
                job-info.required-field.optional-field.job-id.  job-info
                represents the OID prefix of all objects in the job-info
                sub-tree.  Required-field represents the OID field value
                that follows the job-info prefix.  Since some objects in
                the job-info sub-tree have two OID fields between the
                job-info prefix and the job-id, the optional-field
                represents the OID field between the required-field and
                the job-id field, if present.  Using this definition,
                the format for the JOB-INFO-CHANGE-ID binary value can
                be described as follows:
                  Bytes  0-3 :  required-field
                  Bytes  4-7 :  optional-field, or all zeros if there
                                is no optional field
                  Bytes  8-11: Job ID.
                  Bytes 12-n : The value of the object job-info.
                               required-field.optional-field.job-id.
                All multi-byte values stored in Motorola (big-endian)
                format, where the most significant byte occurs first.
                Additional information:
                LaserJet 4050 Series will use this object to report
                changes to the job-info-pages-printed and job-info-state
                objects.  The required-field (bytes 0 through 3) will
                designate whether the change to be reported involves the
                pages printed (13) or job state (15).  The optional-field
                (bytes 4 through 7) will always be zeroes.  The value-field
                (bytes 12 through 15) will contain the new value for pages
                printed or job state cast to a 32-bit integer."
::= { settings-job 3 }


hold-job-timeout OBJECT-TYPE
    SYNTAX  INTEGER
    MAX-ACCESS read-write
    STATUS  current
    DESCRIPTION
                "The time, in minutes, that the printer will wait before
                automatically deleting a held job.  This allows the
                printer to automatically clean up jobs that have been
                forgotten (held but never released).
                Additional information:
                This only applies to temporary held jobs, i.e., HOLD=ON or
                PROOF.  This is a global timer that only affects the jobs
                that are sent after it is set.
                		A value of 0 means never delete the jobs.
                		Setting it to an unsupported value causes
                		the printer to substitute a value (listed
                		below) and to return <noError>
                		status.
                		LaserJet 4050 Series supports values of 0, 60, 240, 1440, and 10080
                		The values are as follows:
                <=0 snap to 0   (disabled)
                >=1 and <=150 snap to 60 (60 minutes)
                >=151 and <=840 snap to 240 (4 hours)
                >=841 and <=2880 snap to 1440 (1 day)
                >=2881 snap to 10080  (1 week)"
::= { settings-job 10 }


current-job-parsing-id OBJECT-TYPE
    SYNTAX  INTEGER(-1..32767)
    MAX-ACCESS read-only
    STATUS  current
    DESCRIPTION
                "Contains the printer assigned job identification for the
                job currently being processed by the processing PDL sub-
                system.  The job ID is a monotonically increasing
                number.  The job ID may be reset to zero at power-up and
                may roll over to zero after reaching some maximum
                value.
                Additional information:
                A value of -1 is returned when the printer
                is not parsing a job.

                When data for a new job is detected, this object is
                updated (the job may or may not turn out to be a Null
                Job); however, the trap does not occur until the printer
                determines that it is not a Null Job.  (A job is considered
                to be a 'null job' if it has no name or job attribute,
                causes no pages to be printed, and consumes MIN_JOB_SIZE
                (9) or fewer bytes.)  A trapped value will differ from
                the previous value by one or more.

                Some job-info- objects are created when the first data
                bytes are received.  If the printer determines that the
                job is a Null Job, the job-info- objects related to the
                Null Job are deleted.  LaserJet 4050 Series retains the job-info-
                objects for the MAX_JOBS_IN_LIST (12) most recent jobs
                that are not Null Jobs.

                The first job received after power-up will have job ID 1,
                and the job ID will increment to 32767 before rolling
                to zero.  To distinguish whether a power cycle or a
                rollover causes a reduction in the job ID value, the
                object prtGeneralConfigChanges can be watched and if it
                increments at the same time as the drop is observed in
                the value of CURRENT-JOB-PARSING-ID, then a power cycle
                is the most likely cause."
::= { job-being-parsed 1 }


job-info-name1 OBJECT-TYPE
    SYNTAX  DisplayString
    MAX-ACCESS read-only
    STATUS  current
    DESCRIPTION
                "Contains the first part of this print job's name.  The
                last OID field for this dynamic object contains the job
                ID.
                Additional information:
                The job name is the string specified by the
                NAME= parameter of the @PJL JOB command which allows a
                maximum of 80 characters.  The first 40 characters are
                in this object and the second 40 are in job-info-name2.
                The symbol set is Roman-8.

                When jobs are nested, the value assigned to this object
                is the name provided by the most recent @PJL JOB NAME=
                command.  If no name is provided, a null string is
                returned."
::= { job-info 1 }


job-info-name2 OBJECT-TYPE
    SYNTAX  DisplayString
    MAX-ACCESS read-only
    STATUS  current
    DESCRIPTION
                "Contains the second part of this print job's name.  The
                last OID field for this dynamic object contains the job
                ID.
                Additional information:
                See job-info-name1."
::= { job-info 2 }


job-info-stage OBJECT-TYPE
    SYNTAX  OCTET STRING
    MAX-ACCESS read-only
    STATUS  current
    DESCRIPTION
                "Indicates what printer sub-systems are currently
                processing this print job.  The last OID field for this
                dynamic object contains the job ID.
                  cSourceSubsystem -  some of the job is in the printer
                I/O subsystem.
                  cProcessingSubsystem - some of the job is in the
                printer imaging processing subsystem.
                  cDestinationSubsystem -  some of the job is being
                printed.
                Additional information:
                For LaserJet 4050 Series, cSourceSubsystem and
                cProcessingSubsystem will always be set and cleared
                together.  They are set when the beginning of the
                job is detected, and they are cleared when the end
                of the job is parsed.

                A non-printing job will never set
                cDestinationSubsystem.

                When a page is ready to be printed (the intermediate has
                been built and the page is `closed' by the personality),
                cDestinationSubsystem will be set even if a page of a
                previous job is currently being printed.
                cDestinationSubsystem remains set until the last page of
                the job has finished printing.

                If a page requires extensive processing and allows all
                the previous pages of a job to complete printing,
                cDestinationSubsystem will remain set until the last
                page of the job has finished printing."
::= { job-info 10 }


job-info-io-source OBJECT-TYPE
    SYNTAX  INTEGER
    MAX-ACCESS read-only
    STATUS  current
    DESCRIPTION
                "Indicates which I/O source, the print job was received
                over.  The value maps to port numbering scheme supported
                in the DEVICE/SOURCE-SUBSYSTEM/IO/PORTS sub-tree."
::= { job-info 11 }


job-info-pages-processed OBJECT-TYPE
    SYNTAX  INTEGER
    MAX-ACCESS read-only
    STATUS  current
    DESCRIPTION
                "Indicates the number of pages processed by the
                processing subsystem.  If neither the cSourceSubsystem
                or the cProcessingSubsystem items are in the associated
                JOB-INFO-STAGE object, then this object contains the
                total number of pages processed for this job.  The last
                OID field for this dynamic object contains the job ID.
                Additional information:
                This object is incremented by one when a
                page is processed (`closed' by the personality), regardless
                of the number of pages that are printed as a result of the
                single page processed.  In other words, it does not matter
                how many identical copies of a page are printed or no pages
                may be printed if operating in silent run mode, this count
                is incremented exactly once.

                A page is considered processed when all of the input
                data has been processed for a page (that is, when the
                intermediate has been produced, and the personality has
                `closed' the page.  At this time, the image of the page is
                not necessarily completely formed.)"
::= { job-info 12 }


job-info-pages-printed OBJECT-TYPE
    SYNTAX  INTEGER
    MAX-ACCESS read-only
    STATUS  current
    DESCRIPTION
                "Indicates the number of pages printed by the destination
                subsystem.  If non of the cSourceSubsystem,
                cProcessingSubsystem or cDestinationSubsystem items are
                in the associated JOB-INFO-STAGE object, then this
                object contains the total number of pages printed for
                this job.  This value may increase by two each time for
                duplex jobs.  The last OID field for this dynamic object
                contains the job ID.
                Additional information:
                If multiple copies of a page are printed,
                each copy is counted individually."
::= { job-info 13 }


job-info-size OBJECT-TYPE
    SYNTAX  INTEGER
    MAX-ACCESS read-only
    STATUS  current
    DESCRIPTION
                "Indicates the number of bytes of data processed by the
                processing subsystem.  If neither of the
                cSourceSubsystem or cProcessingSubsystem items are in
                the associated JOB-INFO-STAGE object, then this object
                contains the size of this job, in bytes.  The last OID
                field for this dynamic object contains the job ID.
                Additional information:
                This count may be incremented by values
                other than one as blocks of data are processed; blocks
                of data (which may be as large as 2K bytes) will be
                processed in a varying amount of time.

                During the processing of a job and even when a job completes,
                an exact count of the number of I/O bytes processed by the
                job is not necessarily to be expected."
::= { job-info 14 }


job-info-state OBJECT-TYPE
    SYNTAX  INTEGER {
		   eAborted(3),
		   eWaitingForResources(4),
		   ePrinted(5),
		   eTerminating(7),
		   eCancelled(10),
		   eProcessing(11)
		   }
    MAX-ACCESS read-only
    STATUS  current
    DESCRIPTION
                "Indicates the state of the job.  The last OID field for
                this dynamic object contains the job ID.
                  eAborted - the print job was aborted.
                  eWaitingForResources - the print job requires
                resources that are not currently available.  Example
                resources that can cause the job to wait include the
                print engine or PDL processor being unavailable.  The
                print engine could be unavailable due to paper out,
                paper jam, staple out, stapler jam, marking agent low,
                output bin full, etc.  The PDL processor could be
                unavailable due to an off-line condition.  Each printer
                specific object specification should state which
                conditions cause a job to be waiting for resources and
                also state which objects can be retrieved by an
                application to determine the exact cause of a resource
                being unavailable.
                  ePrinted - the job has printed.  The related JOB-INFO-
                OUTCOME object indicates if any problems were
                encountered while the job was processed.
                  eRetained - the job can be reprinted.
                  eTerminating - the job was aborted or cancelled and is
                currently is terminating.
                  eInterrupted - the job has been interrupted.  The job
                can be continued.
                  ePaused - the job has been paused.  The job can be
                continuted.
                  eCancelled - the job has been cancelled.
                  eProcessing - the job is currently being printed
                normally."
::= { job-info 15 }


job-info-outcome OBJECT-TYPE
    SYNTAX  INTEGER {
		   eOk(3)
		   }
    MAX-ACCESS read-only
    STATUS  current
    DESCRIPTION
                "Indicates if any warning or error conditions were
                encountered while processing the assoicated job.  The
                last OID field for this dynamic object contains the job
                ID.
                Additional information:
                In LaserJet 4050 Series, warnings and errors are not recorded
                in this object.  Although no meaningful information can be
                obtained from this object, it is kept around for the
                compatibility needs of existing software."
::= { job-info 19 }


job-info-attr-1 OBJECT-TYPE
    SYNTAX  OCTET STRING (SIZE(1..80))
    MAX-ACCESS read-only
    STATUS  current
    DESCRIPTION
                "Returns the value that was set in PJL via the SET
                JOBATTR= command.  Attribute objects are saved
                sequentially, starting with 1, after the start of a job.
                If more attributes are set than there are objects to
                store them, the excess JOBATTR values are ignored.  If
                the corresponding SET JOBATTR= command has not been
                received when a get is done for this object, a status of
                <noSuchName> will be returned."
::= { job-info-attribute 1 }


job-info-attr-2 OBJECT-TYPE
    SYNTAX  OCTET STRING (SIZE(1..80))
    MAX-ACCESS read-only
    STATUS  current
    DESCRIPTION
                "Returns the value that was set in PJL via the SET
                JOBATTR= command.  See JOB-INFO-ATTR-1 for details."
::= { job-info-attribute 2 }


job-info-attr-3 OBJECT-TYPE
    SYNTAX  OCTET STRING (SIZE(1..80))
    MAX-ACCESS read-only
    STATUS  current
    DESCRIPTION
                "Returns the value that was set in PJL via the SET
                JOBATTR= command.  See JOB-INFO-ATTR-1 for details."
::= { job-info-attribute 3 }


job-info-attr-4 OBJECT-TYPE
    SYNTAX  OCTET STRING (SIZE(1..80))
    MAX-ACCESS read-only
    STATUS  current
    DESCRIPTION
                "Returns the value that was set in PJL via the SET
                JOBATTR= command.  See JOB-INFO-ATTR-1 for details."
::= { job-info-attribute 4 }


job-info-attr-5 OBJECT-TYPE
    SYNTAX  OCTET STRING (SIZE(1..80))
    MAX-ACCESS read-only
    STATUS  current
    DESCRIPTION
                "Returns the value that was set in PJL via the SET
                JOBATTR= command.  See JOB-INFO-ATTR-1 for details."
::= { job-info-attribute 5 }


job-info-attr-6 OBJECT-TYPE
    SYNTAX  OCTET STRING (SIZE(1..80))
    MAX-ACCESS read-only
    STATUS  current
    DESCRIPTION
                "Returns the value that was set in PJL via the SET
                JOBATTR= command.  See JOB-INFO-ATTR-1 for details."
::= { job-info-attribute 6 }


job-info-attr-7 OBJECT-TYPE
    SYNTAX  OCTET STRING (SIZE(1..80))
    MAX-ACCESS read-only
    STATUS  current
    DESCRIPTION
                "Returns the value that was set in PJL via the SET
                JOBATTR= command.  See JOB-INFO-ATTR-1 for details."
::= { job-info-attribute 7 }


job-info-attr-8 OBJECT-TYPE
    SYNTAX  OCTET STRING (SIZE(1..80))
    MAX-ACCESS read-only
    STATUS  current
    DESCRIPTION
                "Returns the value that was set in PJL via the SET
                JOBATTR= command.  See JOB-INFO-ATTR-1 for details."
::= { job-info-attribute 8 }


job-info-attr-9 OBJECT-TYPE
    SYNTAX  OCTET STRING (SIZE(1..80))
    MAX-ACCESS read-only
    STATUS  current
    DESCRIPTION
                "Returns the value that was set in PJL via the SET
                JOBATTR= command.  See JOB-INFO-ATTR-1 for details."
::= { job-info-attribute 9 }


job-info-attr-10 OBJECT-TYPE
    SYNTAX  OCTET STRING (SIZE(1..80))
    MAX-ACCESS read-only
    STATUS  current
    DESCRIPTION
                "Returns the value that was set in PJL via the SET
                JOBATTR= command.  See JOB-INFO-ATTR-1 for details."
::= { job-info-attribute 10 }


job-info-attr-11 OBJECT-TYPE
    SYNTAX  OCTET STRING (SIZE(1..80))
    MAX-ACCESS read-only
    STATUS  current
    DESCRIPTION
                "Returns the value that was set in PJL via the SET
                JOBATTR= command.  See JOB-INFO-ATTR-1 for details."
::= { job-info-attribute 11 }


job-info-attr-12 OBJECT-TYPE
    SYNTAX  OCTET STRING (SIZE(1..80))
    MAX-ACCESS read-only
    STATUS  current
    DESCRIPTION
                "Returns the value that was set in PJL via the SET
                JOBATTR= command.  See JOB-INFO-ATTR-1 for details."
::= { job-info-attribute 12 }


job-info-attr-13 OBJECT-TYPE
    SYNTAX  OCTET STRING (SIZE(1..80))
    MAX-ACCESS read-only
    STATUS  current
    DESCRIPTION
                "Returns the value that was set in PJL via the SET
                JOBATTR= command.  See JOB-INFO-ATTR-1 for details."
::= { job-info-attribute 13 }


job-info-attr-14 OBJECT-TYPE
    SYNTAX  OCTET STRING (SIZE(1..80))
    MAX-ACCESS read-only
    STATUS  current
    DESCRIPTION
                "Returns the value that was set in PJL via the SET
                JOBATTR= command.  See JOB-INFO-ATTR-1 for details."
::= { job-info-attribute 14 }


job-info-attr-15 OBJECT-TYPE
    SYNTAX  OCTET STRING (SIZE(1..80))
    MAX-ACCESS read-only
    STATUS  current
    DESCRIPTION
                "Returns the value that was set in PJL via the SET
                JOBATTR= command.  See JOB-INFO-ATTR-1 for details."
::= { job-info-attribute 15 }


job-info-attr-16 OBJECT-TYPE
    SYNTAX  OCTET STRING (SIZE(1..80))
    MAX-ACCESS read-only
    STATUS  current
    DESCRIPTION
                "Returns the value that was set in PJL via the SET
                JOBATTR= command.  See JOB-INFO-ATTR-1 for details."
::= { job-info-attribute 16 }

job-info-attr-17 OBJECT-TYPE
    SYNTAX  OCTET STRING (SIZE(1..80))
    MAX-ACCESS read-only
    STATUS  current
    DESCRIPTION
                "Returns the value that was set in PJL via the SET
                JOBATTR= command.  See JOB-INFO-ATTR-1 for details."
::= { job-info-attribute 17 }


job-info-attr-18 OBJECT-TYPE
    SYNTAX  OCTET STRING (SIZE(1..80))
    MAX-ACCESS read-only
    STATUS  current
    DESCRIPTION
                "Returns the value that was set in PJL via the SET
                JOBATTR= command.  See JOB-INFO-ATTR-1 for details."
::= { job-info-attribute 18 }


job-info-attr-19 OBJECT-TYPE
    SYNTAX  OCTET STRING (SIZE(1..80))
    MAX-ACCESS read-only
    STATUS  current
    DESCRIPTION
                "Returns the value that was set in PJL via the SET
                JOBATTR= command.  See JOB-INFO-ATTR-1 for details."
::= { job-info-attribute 19 }


job-info-attr-20 OBJECT-TYPE
    SYNTAX  OCTET STRING (SIZE(1..80))
    MAX-ACCESS read-only
    STATUS  current
    DESCRIPTION
                "Returns the value that was set in PJL via the SET
                JOBATTR= command.  See JOB-INFO-ATTR-1 for details."
::= { job-info-attribute 20 }


job-info-attr-21 OBJECT-TYPE
    SYNTAX  OCTET STRING (SIZE(1..80))
    MAX-ACCESS read-only
    STATUS  current
    DESCRIPTION
                "Returns the value that was set in PJL via the SET
                JOBATTR= command.  See JOB-INFO-ATTR-1 for details."
::= { job-info-attribute 21 }


job-info-attr-22 OBJECT-TYPE
    SYNTAX  OCTET STRING (SIZE(1..80))
    MAX-ACCESS read-only
    STATUS  current
    DESCRIPTION
                "Returns the value that was set in PJL via the SET
                JOBATTR= command.  See JOB-INFO-ATTR-1 for details."
::= { job-info-attribute 22 }


job-info-attr-23 OBJECT-TYPE
    SYNTAX  OCTET STRING (SIZE(1..80))
    MAX-ACCESS read-only
    STATUS  current
    DESCRIPTION
                "Returns the value that was set in PJL via the SET
                JOBATTR= command.  See JOB-INFO-ATTR-1 for details."
::= { job-info-attribute 23 }


job-info-attr-24 OBJECT-TYPE
    SYNTAX  OCTET STRING (SIZE(1..80))
    MAX-ACCESS read-only
    STATUS  current
    DESCRIPTION
                "Returns the value that was set in PJL via the SET
                JOBATTR= command.  See JOB-INFO-ATTR-1 for details."
::= { job-info-attribute 24 }


job-info-attr-25 OBJECT-TYPE
    SYNTAX  OCTET STRING (SIZE(1..80))
    MAX-ACCESS read-only
    STATUS  current
    DESCRIPTION
                "Returns the value that was set in PJL via the SET
                JOBATTR= command.  See JOB-INFO-ATTR-1 for details."
::= { job-info-attribute 25 }


job-info-attr-26 OBJECT-TYPE
    SYNTAX  OCTET STRING (SIZE(1..80))
    MAX-ACCESS read-only
    STATUS  current
    DESCRIPTION
                "Returns the value that was set in PJL via the SET
                JOBATTR= command.  See JOB-INFO-ATTR-1 for details."
::= { job-info-attribute 26 }


job-info-attr-27 OBJECT-TYPE
    SYNTAX  OCTET STRING (SIZE(1..80))
    MAX-ACCESS read-only
    STATUS  current
    DESCRIPTION
                "Returns the value that was set in PJL via the SET
                JOBATTR= command.  See JOB-INFO-ATTR-1 for details."
::= { job-info-attribute 27 }


job-info-attr-28 OBJECT-TYPE
    SYNTAX  OCTET STRING (SIZE(1..80))
    MAX-ACCESS read-only
    STATUS  current
    DESCRIPTION
                "Returns the value that was set in PJL via the SET
                JOBATTR= command.  See JOB-INFO-ATTR-1 for details."
::= { job-info-attribute 28 }


job-info-attr-29 OBJECT-TYPE
    SYNTAX  OCTET STRING (SIZE(1..80))
    MAX-ACCESS read-only
    STATUS  current
    DESCRIPTION
                "Returns the value that was set in PJL via the SET
                JOBATTR= command.  See JOB-INFO-ATTR-1 for details."
::= { job-info-attribute 29 }


job-info-attr-30 OBJECT-TYPE
    SYNTAX  OCTET STRING (SIZE(1..80))
    MAX-ACCESS read-only
    STATUS  current
    DESCRIPTION
                "Returns the value that was set in PJL via the SET
                JOBATTR= command.  See JOB-INFO-ATTR-1 for details."
::= { job-info-attribute 30 }


job-info-attr-31 OBJECT-TYPE
    SYNTAX  OCTET STRING (SIZE(1..80))
    MAX-ACCESS read-only
    STATUS  current
    DESCRIPTION
                "Returns the value that was set in PJL via the SET
                JOBATTR= command.  See JOB-INFO-ATTR-1 for details."
::= { job-info-attribute 31 }


job-info-attr-32 OBJECT-TYPE
    SYNTAX  OCTET STRING (SIZE(1..80))
    MAX-ACCESS read-only
    STATUS  current
    DESCRIPTION
                "Returns the value that was set in PJL via the SET
                JOBATTR= command.  See JOB-INFO-ATTR-1 for details."
::= { job-info-attribute 32 }


job-info-requested-originals OBJECT-TYPE
    SYNTAX  INTEGER
    MAX-ACCESS read-only
    STATUS  current
    DESCRIPTION
                "The number of requested collated copies.  The value was
                supplied with the job via PJL QTY variable, the
                PostScript Collate and NumCopies entries in the page
                device dictionary, or via some other mechansim."
::= { job-info 24 }


job-info-page-count-current-original OBJECT-TYPE
    SYNTAX  INTEGER
    MAX-ACCESS read-only
    STATUS  current
    DESCRIPTION
                "The page number being printed within the current copy of
                a collated multi-copy job.  This value changes when the
                job-info-pages-printed changes.  The job-info-pages-
                printed indicates the total number of pages printed in
                the job, while this object indicates the number of pages
                printed for this copy of a collated multi-copy job.
                Additional information:
                The number of pages in the current copy of a collated
                multi-copy job which have been completely printed and
                safely delivered to the output bin."
::= { job-info 25 }


job-info-pages-in-original OBJECT-TYPE
    SYNTAX  INTEGER
    MAX-ACCESS read-only
    STATUS  current
    DESCRIPTION
                "Number of pages in a single copy of a collated multi-
                copy job."
::= { job-info 26 }


job-info-printed-originals OBJECT-TYPE
    SYNTAX  INTEGER
    MAX-ACCESS read-only
    STATUS  current
    DESCRIPTION
                "Number of collated copies completely printed and
                delivered to the output bin at time of query."
::= { job-info 27 }

not-ready-processing-pdl OBJECT-TYPE
    SYNTAX  OCTET STRING
    MAX-ACCESS read-only
    STATUS  current
    DESCRIPTION
                "Indicates if the PDL sub-system in the device is not
                ready.  If there are no items in the collection (i.e. no
                bits are set), then the PDL sub-system is ready.  If
                there is an item present, then the item indicates what
                is causing the PDL sub-system to be not ready.  cOffLine
                indicates the PDL processing sub-system is off line.
                cPrintDataMemoryOverflow indicates the print job was
                sufficiently complex to use up all memory available for
                processing print job data.  cSoftResourceMemoryOverflow
                indicates the print job contained soft resources (fonts,
                macros, etc.) that over flowed the available memory."
::= { status-pdl 1 }

form-feed-needed OBJECT-TYPE
    SYNTAX  INTEGER {
		   eFalse(1),
		   eTrue(2)
		   }
    MAX-ACCESS read-only
    STATUS  current
    DESCRIPTION
                "Indicates if the PDL processing sub-system has made
                marks on the current page and the source subsystem has
                been idle for a device specific amount of time.
                Additional information:
                LaserJet 4050 Series will set this object to eTrue when it
                has made marks on the current page, the IO-TIMEOUT has
                expired while PCL was running in `backward-compatibility
                mode' (which is caused by jobs consisting purely of PCL
                data with no prepended PJL commands), and no data is pending
                on another I/O.  Once it is set to eTrue, more data on the
                same I/O will cause this object to be set to eFalse, until
                the above conditions are met again."
::= { status-pdl 2 }


jetsend-mode OBJECT-TYPE
    SYNTAX  INTEGER {
		   eOff(1),
		   eOn(2)
		   }
    MAX-ACCESS read-write
    STATUS  current
    DESCRIPTION
                "Enables or disables the JetSend processing sub-system.
                Additional information:
                Enables or disables the JetSend processing subsystem.
                The valid values are eOff and eOn. (Specifying an invalid mode
                causes an <badValue> error to be returned.).
                	   This object will be enabled in IR devices even if is does not
                	   detect an EIO card."
::= { settings-jetsend 1 }


jetsend-contact-password OBJECT-TYPE
    SYNTAX  OCTET STRING (SIZE(16))
    MAX-ACCESS read-write
    STATUS  current
    DESCRIPTION
                "A C structure containing the following fields:
                 typedef struct {
                     ubyte old_password[8];
                     ubyte new_password[8];/
                 } jetsend_change_contact_password_t;
                where ubyte is an unsigned byte (0-255).
                Additional information:
                Controls access to the JetSend processing subsystem.
                Password absence/presence determines whether the device will allow
                a session to be established. The following C data structure
                contains the relevant fields (described in subsequent paragraphs):

                typedef struct {
                unsigned char old_password[8];
                unsigned char new_password[8];
                }

                Whenever the password is disabled (i.e., is zero-filled for its
                entire length), the device is indicating its willingness to allow
                session establishment. Whenever the password is enabled (i.e., has
                one or more non-zero-filled values), the device is controlling
                session establishment -- all in-progress JetSend sessions must
                supply a matching password or the device will reject the in-progress
                session.

                To disable the password, specify the matching password via the
                'old_password' field and zero-fill the 'new_password' field.
                To enable the password for the first time, zero-fill the
                'old_password' field and specify the new password via the
                'new_password' field (the new password should not be
                zero-filled; otherwise, the password will remain disabled).
                To enable or change the password thereafter, specify the
                matching password via the 'old_password' field and specify
                the new password via the 'new_password' field (the new
                desired password should not be zero-filled; otherwise,
                the password will be disabled). To determine if the password
                is enabled, zero-fill both the 'old_password' and 'new_password'
                fields. If an error occurs, the password is enabled; otherwise,
                the password is disabled.

                (Specifying either an 'old_password' or 'new_password'
                fields greater than eight (8) bytes causes the error
                <badValue> to be returned.)

                	   This object will be enabled in IR devices even if is does not
                	   detect an EIO card."
::= { settings-jetsend-contact 1 }


jetsend-contact-ip-address-security OBJECT-TYPE
    SYNTAX  OCTET STRING (SIZE(16))
    MAX-ACCESS read-write
    STATUS  current
    DESCRIPTION
                "A C structure containing the following fields:
                 typedef struct {
                     ubyte reserved[3];
                     ubyte command; /* command: 0 to 1 */
                     ubyte password[8];
                     ubyte IPAddress[4];
                 } jetsend_contact_ip_address_security_t;
                where ubyte is an unsigned byte (0-255).  The defined
                values defined for command are:

                When command is 0:
                  IPAddress is 0:  device is locked, no one can contact
                it
                  IPAddress is > 0:  only that address is allowed to
                contact the device

                When command is 1:
                  IPAddress is 0:  any device can contact it
                  IPAddress is > 0:  any device matching this mask can
                contact it.  If the result of logically anding the mask
                value supplied in the IPAddress field with the sending
                device's IP address matches the result of logically
                anding the mask value supplied in the IPAddress field
                with this device's IP address, then JetSend will allow
                the session to be established.
                Additional information:
                Controls the device or class of device(s) which may
                communicate with the JetSend processing subsystem. The following C
                data structure contains the relevant fields (described in subsequent
                paragraphs):

                typedef struct {
                unsigned char reserved[3];
                unsigned char command;
                unsigned char password[8];
                unsigned char IPAddress[4];
                }

                The 'reserved' field is not used and should remain zero-filled.
                The 'command' field interpretation differs based on its value:

                0 = Accept session(s) only from the specific device whose
                IP address matches the specified IP address; all other
                session request(s) from non-matching device(s) are rejected.
                1 = Accept session(s) only from the specific device(s) whose
                IP address(es) conform to the mask specified in the 'IPAddress'
                field; all other session request(s) from device(s) with
                non-matching submask(s) are rejected. (If the result of
                logically AND'ing the mask value supplied in the 'IPAddress'
                field with the sending device's IP address matches the result
                of logically AND'ing the mask value supplied in the 'IPAddress'
                field with this device's IP address, then JetSend will allow
                session establishment.

                Password absence/presence determines whether the device will allow
                the caller to alter the IP address security. If the password is
                disabled, the caller may set the 'command' and 'IPAddress' fields
                directly. If the password is enabled, the caller may (re-)set the
                'command' and 'IPAddress' fields only after specifying the matching
                'password' field. (Refer to the aforementioned 'JETSEND-CONTACT-PASSWORD'
                object ID.)

                (Specifying either an invalid 'command' field value or a 'password'
                field greater than eight (8) bytes or an 'IPAddress' field greater
                than four (4) bytes causes the error <badValue>
                to be returned.)

                	   This object will be enabled in IR devices even if is does not
                	   detect an EIO card."
::= { settings-jetsend-contact 2 }


host-application-available-memory OBJECT-TYPE
    SYNTAX  INTEGER
    MAX-ACCESS read-only
    STATUS  current
    DESCRIPTION
                "Returns the amount of memory, in bytes, that the device
                has available for job-related processing or resources.
                Also known as driver work space (DWS) memory."
::= { status-system 59 }


held-job-user-name OBJECT-TYPE
    SYNTAX  DisplayString (SIZE(0..40))
    MAX-ACCESS read-only
    STATUS  current
    DESCRIPTION
                "User name that is obtained by the driver through some
                internal method or from user input.
                Additional information:
                The following is a general description for all the JOB-MANAGEMENT
                objects described below.  These object describe the attributes of the
                dynamic list containing all the stored jobs on the disk available for
                printing or deleting via the job-management feature.  The jobs on this
                list are not deleted from the disk unless explicitly specified by the
                user.  A print job may be specified for retention by PJL commands in the
                data stream.

                Following is a list of the PJL commands (i.e. these comments describe
                the PJL implementation and in some cases do not reflect the PML
                implementation.):

                @PJL SET HOLD=OFF|ON|PROOF|STORE|PRINT

                GENERAL DESCRIPTION:

                This variable specifies the retention classification of the job.  The
                values indicate whether the job is printed immediately and/or stored.

                OFF:  The job is printed but not retained on disk after printing.  This
                is the default value.

                ON:  This setting may be thought of as free proof-and-hold.  The
                requested number of copies will be printed and the job will be
                temporarily stored on disk.  The job will then be available for printing
                additional copies through the control panel and through PML.  There will
                be a limit to the number of these temporary jobs that may be stored, and
                when the limit is exceeded the oldest job will be removed from the disk.

                PROOF:  One copy of the job is printed and remaining copies are stored
                on disk.  The job is then available to select for printing via the
                control panel menus or PML.  The job will be deleted from the disk when
                the disk space is needed for another proof and hold job but only after
                the additional copies have been printed.  It will also be deleted when
                the user sends down another proof and hold job with the same job name,
                or the user explicitly deletes the job.

                STORE:  The job is not printed immediately but is retained on disk.  The
                job is available to select for printing via the control panel

                DEFAULT VALUE: OFF

                The value will be stored in RAM only, not in NVRAM.
                The legal PJL commands are SET and INQUIRE.  DEFAULT is not allowed.
                The variable will appear in the PJL INFO VARIABLES list.

                @PJL SET USERNAME=<80 bytes>

                GENERAL DESCRIPTION:

                Eighty-character user name that is obtained by the driver through some
                internal method or from user input.  If the job stream does not contain
                a USERNAME the default value will be NO USER NAME.  The driver is
                responsible for determining the size of the printers control panel and
                sending a string of appropriate length.

                DEFAULT VALUE: NO USER NAME

                The value will be stored in RAM only, not in NVRAM.
                The legal PJL commands are SET and, INQUIRE. DEFAULT is not allowed.
                The variable will appear in the PJL INFO VARIABLES list.

                @PJL SET JOBNAME=<80 bytes>

                GENERAL DESCRIPTION:

                Eighty-character job name that may be generated by the driver or
                obtained from user input.  This value may be used in conjunction with
                the USERNAME to select a job from the front panel.  If the job stream
                does not contain a JOBNAME, the printer will assume no job name; each
                subsequent job that is sent down by the same user would replace the
                users last job on disk.  The driver is responsible for determining the
                size of the printers control panel and sending a string of appropriate
                length.

                NOTE:  The limit of 80 bytes is a PJL limit.  The limit for PML will
                be 40 bytes.

                DEFAULT VALUE: NULL STRING

                The value will be stored in RAM only, not in NVRAM.
                The legal PJL commands are SET and INQUIRE. DEFAULT is not allowed.
                The variable will appear in the PJL INFO VARIABLES list.

                @PJL SET HOLDTYPE=PUBLIC|PRIVATE

                GENERAL DESCRIPTION:

                This variable specifies the privacy level of the job.

                PUBLIC:  The job does not require a PIN in order to be released for
                printing.  This is the default value.

                PRIVATE:  The job requires a PIN in order to be released for printing.
                The PIN is specified by the HOLDKEY variable.  If the

                HOLDTYPE is set to PRIVATE, a HOLDKEY value must be specified.  If no
                HOLDKEY is specified, the job will be considered PUBLIC.

                DEFAULT VALUE: PUBLIC

                The value will be stored in RAM only, not in NVRAM.
                The legal PJL commands are SET and INQUIRE. DEFAULT is not allowed.
                The variable will appear in the PJL INFO VARIABLES list.

                @PJL SET HOLDKEY=4 digits, 0000...9999

                GENERAL DESCRIPTION:

                A 4-digit string, each digit 0-9, that is specified in the job stream
                and then required to be entered in order to release the job for
                printing.  If a HOLDTYPE is PRIVATE, a HOLDKEY value must be specified.
                If no HOLDKEY value is specified, a job will be considered PUBLIC.

                DEFAULT VALUE: NULL STRING

                The value will be stored in RAM only, not in NVRAM.
                The legal PJL commands are SET and INQUIRE. DEFAULT is not allowed.
                The variable will appear in the PJL INFO VARIABLES list.


                The format for the OID is as follows:

                3.4.1.6.x.y
                <-----> | |
                |    |  \
                /     |  job-id in the system
                /       \
                PML_JOB_MGNT_ROOT_OID  \
                job attribute 1..6

                x values are 1..6:

                1) user-name:  user name that is obtained by the driver through some
                internal method or from user input.

                2) job-name:  job name may be generated by the driver or obtained from
                user input.

                3) hold:  indicates the retention classification of the job.  The values
                indicate whether the job is printed immediately and/or stored.  There
                are 4 options:
                OFF:    The job is printed but not retained on the disk.
                ON:     The job is printed and stored temporarily on the disk.
                STORE:  The job is not printed but stored on the disk.
                PROOF:  One copy of the job is printed and the remaining copies are
                stored on the disk.

                4) holdtype:  The variable specifies the security level of the job.
                PUBLIC:  The job does not require a PIN in order to release the job for
                printing.
                PRIVATE:  The job requires a PIN in order to be released for printing.

                5) quantity:  number of copies to print.  Valid values are 0..999.

                6) pin:  A 4 digit string, each digit is 0-9, that is specified in the
                job stream and then required to be entered in order to release the job
                for printing.

                y :  an unsigned 15 bit number which uniquely identifies the job.  The job
                id for the job remains the same for the job until it is deleted from the
                held jobs list.


                For example, the OID below is asking for the user name of the
                job whose id is 3.  The application would issue:

                OID
                get 3.4.1.6.1.3

                For example, the <getnext> OID values sequence is as follows:

                OID                returned OID
                getnext 3.4.1.6         3.4.1.6.1.1
                getnext 3.4.1.6.1.1     3.4.1.6.1.2
                getnext 3.4.1.6.2.1     3.4.1.6.2.2
                ...
                getnext 3.4.1.6.1.6     3.4.1.6.1.7
                getnext 3.4.1.6.2.1     3.4.1.6.2.2
                getnext 3.4.1.6.5.2828  3.4.1.6.6.1

                NOTE: for example above, job id 2828 is the last job in the list of
                held jobs.
                ...

                Also supported is <getnext> on the job attributes:
                OID                returned OID
                getnext 3.4.1.6.1       3.4.1.6.1.1
                getnext 3.4.1.6.6       3.4.1.6.6.1"
::= { held-job-info 1 }


held-job-job-name OBJECT-TYPE
    SYNTAX  DisplayString (SIZE(0..40))
    MAX-ACCESS read-only
    STATUS  current
    DESCRIPTION
                "The job name may be generated by the driver or obtained
                from user input."
::= { held-job-info 2 }


held-job-retention OBJECT-TYPE
    SYNTAX  INTEGER {
		   eHoldOff(1),
		   eHoldOn(2),
		   eHoldStore(3),
		   eHoldProof(4)
		   }
    MAX-ACCESS read-only
    STATUS  current
    DESCRIPTION
                "Indicates the retention classification of the job.  The
                values indicate whether the job is printed immediately
                and/or stored.  There are 4 options:
OFF:    The job is printed but not retained on the disk.
ON:     The job is printed and stored temporarily on the disk.
PROOF:  One copy of the job is printed and the remaining copies are stored on the disk.
STORE:  The job is not printed but stored on the disk."
::= { held-job-info 3 }


held-job-security OBJECT-TYPE
    SYNTAX  INTEGER {
		   eHoldTypePublic(1),
		   eHoldTypePrivate(2)
		   }
    MAX-ACCESS read-only
    STATUS  current
    DESCRIPTION
                "The variable specifies the security level of the job.
PUBLIC:  The job does not require a PIN in order to release the job for printing.
PRIVATE: The job requires a PIN in order to be released for printing."
::= { held-job-info 4 }


held-job-quantity OBJECT-TYPE
    SYNTAX  INTEGER(1..999)
    MAX-ACCESS read-only
    STATUS  current
    DESCRIPTION
                "Number of copies to print."
::= { held-job-info 5 }


held-job-pin OBJECT-TYPE
    SYNTAX  DisplayString (SIZE(0..4))
    MAX-ACCESS read-only
    STATUS  current
    DESCRIPTION
                "A string that is specified in the job stream and then
                required to be entered in order to release the job for
                printing.  PIN stands for Personal Identification
                Number.
                Additional information:
                Must be a 4 digit string, each digit must be 0..9 or a null string
                if there is no pin."
::= { held-job-info 6 }


held-job-print OBJECT-TYPE
    SYNTAX  OCTET STRING (SIZE(8))
    MAX-ACCESS read-write
    STATUS  current
    DESCRIPTION
                "Instructs the printer to schedule the specified held job
                for printing with the specified number of copies.  The
                job-id is used to identify which job to print.  A held
                job can also be printed from the control panel.
                Additional information:
                Bytes 0-3 is the job id of the job to print.
                Bytes 4-7 is the number of copies to print."
::= { held-job-control 1 }


held-job-delete OBJECT-TYPE
    SYNTAX  INTEGER(0..32768)
    MAX-ACCESS read-write
    STATUS  current
    DESCRIPTION
                "Instructs the printer to delete the specified held job
                from the list.  The job-id is used to identify which job
                to delete.  A held job can also be deleted from the
                control panel.
                Additional information:
                "
::= { held-job-control 2 }


held-job-set-queue-size OBJECT-TYPE
    SYNTAX  INTEGER(0..50)
    MAX-ACCESS read-write
    STATUS  current
    DESCRIPTION
                "Sets the maximum number of jobs which can be stored in
                the held job list.
                Additional information:
                Sets the size of the temporary job lists queue."
::= { held-job-control 3 }


held-job-enable OBJECT-TYPE
    SYNTAX  INTEGER {
		   eDisabled(1),
		   eEnabled(2)
		   }
    MAX-ACCESS read-write
    STATUS  current
    DESCRIPTION
                "Enables or disables Job Retention (Job Hold).  The valid
                values are eDisabled and eEnabled.  (Specifying an
                invalid mode causes an <badValue>
                error to be returned.) When eDisabled is specified all
                Job Retention (Hold, Proof, Store, PIN Printing) is
                disabled.  When eEnabled is specified, the Job Retention
                characteristics of a given job are defined by the PJL
                variable SET HOLD.
                Additional information:
                When disabled, currently held jobs are not removed,
                but must be explicitly removed through the Control Panel
                or the PML object HELD-JOB-DELETE."
::= { held-job-control 4 }


usage-printer-total-charge OBJECT-TYPE
    SYNTAX  INTEGER
    MAX-ACCESS read-only
    STATUS  current
    DESCRIPTION
                "Total printer charge for all paper sizes printed."
::= { printer-accounting 2 }


usage-average-toner-coverage OBJECT-TYPE
    SYNTAX  INTEGER
    MAX-ACCESS read-only
    STATUS  current
    DESCRIPTION
                "Reports the average toner area coverage of all pages
                printed over the life of the device.  Counts pixels on
                each page, divides pixel count by pixels possible on a
                page to give the percentage of coverage, and keeps a
                rolling average percent weighted by area printed."
::= { printer-accounting 3 }


usage-staple-count OBJECT-TYPE
    SYNTAX  INTEGER(0..930576247)
    MAX-ACCESS read-only
    STATUS  current
    DESCRIPTION
                "Total number of staples used."
::= { printer-accounting 4 }


usage-instructions-line1 OBJECT-TYPE
    SYNTAX  DisplayString (SIZE(0..40))
    MAX-ACCESS read-write
    STATUS  current
    DESCRIPTION
                "The first line of usage instructions for the device
                user.Appears on Line 1 of the usage page."
::= { printer-accounting 5 }


usage-instructions-line2 OBJECT-TYPE
    SYNTAX  DisplayString (SIZE(0..40))
    MAX-ACCESS read-write
    STATUS  current
    DESCRIPTION
                "The second line of usage instructions for the device
                user.Appears on Line 1 of the usage page."
::= { printer-accounting 6 }


usage-instructions-line3 OBJECT-TYPE
    SYNTAX  DisplayString (SIZE(0..40))
    MAX-ACCESS read-write
    STATUS  current
    DESCRIPTION
                "The third line of usage instructions for the device
                user.Appears on Line 1 of the usage page."
::= { printer-accounting 7 }


usage-instructions-line4 OBJECT-TYPE
    SYNTAX  DisplayString (SIZE(0..40))
    MAX-ACCESS read-write
    STATUS  current
    DESCRIPTION
                "The fourth line of usage instructions for the device
                user.Appears on Line 1 of the usage page."
::= { printer-accounting 8 }


scanned-media-simplex-count OBJECT-TYPE
    SYNTAX  INTEGER(0..930576247)
    MAX-ACCESS read-only
    STATUS  current
    DESCRIPTION
                "Total number of simplex pages scanned, for this media
                size.
                Additional information:
                The 5 usage (simplex/duplex count, simplex/duplex click
                charge and paper size total) objects described here and
                below detail the usage for the scanner for each paper
                size defined in the PCL Implementor's Guide and in the
                Media Size Table in the hpmib.txt.  The OID binding is
                based on the click attribute and paper size.
                For example:

                The format for the OID is as follows:

                3.4.1.5.x.y
                <-----> | |
                |    |  \
                /     |  paper size
                /       \
                PRINTER-CLICK_TOTALS ROOT   \
                OID                      click attribute 1..5

                x values are 1..5:

                1) simplex count
                2) simplex click charge
                3) duplex count
                4) duplex click charge
                5) printer or scanner paper size total (i.e. depends if the
                root OID is referrring to the printer or scanner).

                y : paper size as defined in the Media Size Table in the
                hpmib.txt

                		The click charge objects are of data type real and have a single
                		digit of precision. Setting these objects to more than a single
                		digit of precision will cause truncation at a single digit, for
                		example, if click charge is set to 15.475 and later retrieved with
                		a get, the value will be 15.400 for this object."
::= { scanned-media-usage 1 }


scanned-media-simplex-charge OBJECT-TYPE
    SYNTAX  INTEGER
    MAX-ACCESS read-write
    STATUS  current
    DESCRIPTION
                "Charge for each simplex page printed in this media
                size."
::= { scanned-media-usage 2 }


scanned-media-duplex-count OBJECT-TYPE
    SYNTAX  INTEGER(0..930576247)
    MAX-ACCESS read-only
    STATUS  current
    DESCRIPTION
                "Total number of duplex pages scanned, for this media
                size."
::= { scanned-media-usage 3 }


scanned-media-duplex-charge OBJECT-TYPE
    SYNTAX  INTEGER
    MAX-ACCESS read-write
    STATUS  current
    DESCRIPTION
                "Charge for each duplex page scanned, for this media
                size."
::= { scanned-media-usage 4 }


scanned-media-total-charge OBJECT-TYPE
    SYNTAX  INTEGER
    MAX-ACCESS read-only
    STATUS  current
    DESCRIPTION
                "The total charge for pages scanned, for this media
                size."
::= { scanned-media-usage 5 }


usage-scanner-total-charge OBJECT-TYPE
    SYNTAX  INTEGER
    MAX-ACCESS read-only
    STATUS  current
    DESCRIPTION
                "Total scanner charge or cost for all paper sizes
                scanned."
::= { scanner-accounting 2 }


scan-contrast OBJECT-TYPE
    SYNTAX  INTEGER(-127..127)
    MAX-ACCESS read-write
    STATUS  current
    DESCRIPTION
                "Behaves as SCL's 'Set Scanner Contrast Level' command
                which is used for setting the scanner contrast level.
                Range is 0..100.
                Additional information:
                There are 11 different tonemap that will
                be used on scan images to change the contrast. Software
                can set the contrast setting to -125, -100, -75, -50, -25,
                0, 50, 75, 100, and 125 to select the different tonemaps.
                A user can also set the value to -127, which is a special
                mode used by manufacturing to tell the device to use all
                linear tonemaps and to perform no gamma correction.  The
                scan pml object does not snap the pml scan-contrast.  However,
                the contrast setting is mapped to the correct tonemap within
                the device."
::= { settings-scanner 1 }


scan-resolution OBJECT-TYPE
    SYNTAX  OCTET STRING (SIZE(1..64))
    MAX-ACCESS read-write
    STATUS  current
    DESCRIPTION
                "struct {
                  unsigned_32bit x_res; /* 1st four bytes; big endian */
                  unsigned_32bit y_res; /* 2nd four bytes; big endian */
                }
                Sets the scanning resolution.  The x and y resolutions
                in this object are in fixed-point with 16 bits of
                fraction, and 16 bits of integer, and are in dots per
                inch.  X is horizontal; Y is vertical.
                Examples of computing x_res and y_res:
                   300 dots/inch:round(300 * 65536) = 19660800
                   16 dots/mm:   round(16 * 25.4 * 65536) = 26633830.
                If the device does not support the given combination,
                then it'll select the nearest supported values in a
                device-dependent manner (documented in the POS).
                Additional information:
                The 4-pack device will support only: 100,
                150, 200, 300 and 600.  The Host SW may scale the image to
                many more resolutions. If an invalid resolution setting
                is passed to the device or the setting is greater than
                the max value(600ppi), the device will set the resolution
                to the default value.  If the resolution setting is not
                100, 150, 200, 300 or 600, the value is snapped up.  For
                instance, if the value is < 100, the resolution is snapped
                to 100.  If the value is between 101-149, the value is
                snapped to 150, etc. NOTE: The last 16 bits of the
                horizontal and vertical settings are ignored.  Only the
                first 16 bits of the horizontal and vertical resolution
                setting are used."
::= { settings-scanner 2 }


scan-pixel-data-type OBJECT-TYPE
    SYNTAX  INTEGER {
		   eBiLevelThesholded(1),
		   eGrey256(8),
		   e24BitColor(24)
		   }
    MAX-ACCESS read-write
    STATUS  current
    DESCRIPTION
                "Sets the method used when scanning.
                  eBiLevelThesholded - One bit per pixel, using simple
                thresholding of greyscale scan data.
                  eBiLevelHalfToned - One bit per pixel, using some kind
                of half-toning technique (such as dithering or error-
                diffusion) to approximate greyscale scan data.
                  eGrey16 - 4 bits per pixel to represent 16 shades of
                grey.
                  eGrey64 - 6 bits per pixel to represent 64 shades of
                grey.
                  e3BitColor - 1 bit thresholded per Red, Green, and
                Blue plane.
                  eGrey128 - 7 bits per pixel to represent 128 shades of
                grey.
                  eGrey256 - 8 bits per pixel to represent 256 shades of
                grey.
                  e24BitColor - 24 bits per pixel, 8 bits for Red, 8 bit
                for Green, and 8 bits for Blue."
::= { settings-scanner 3 }


scan-compression OBJECT-TYPE
    SYNTAX  INTEGER {
		   eCompressNone(1),
		   eCompressDefault(2),
		   eCompressionMMR(5),
		   eCompressionJPEG(6)
		   }
    MAX-ACCESS read-write
    STATUS  current
    DESCRIPTION
                "Indicates the type of data compression applied to the
                image data in the scanning upload session."
::= { settings-scanner 4 }


scan-compression-factor OBJECT-TYPE
    SYNTAX  INTEGER(0..100)
    MAX-ACCESS read-write
    STATUS  current
    DESCRIPTION
                "Indicates the level of compression to be applied to the
                scanned image data for upload.  Range is normalized to
                be between 0..100.  The device POS determines the
                mapping of the normalized scale to the actual Q factor
                for JPEG.
                Additional information:
                The 4-pack will use the
                SCAN-COMPRESSION-FACTOR for JPEG as described above
                in the General Description."
::= { settings-scanner 5 }


scan-upload-error OBJECT-TYPE
    SYNTAX  INTEGER
    MAX-ACCESS read-only
    STATUS  current
    DESCRIPTION
                "Error status of the image scanning upload session."
::= { settings-scanner 6 }


scan-upload OBJECT-TYPE
    SYNTAX  INTEGER {
		   eScanUploadIdle(1),
		   eScanUploadStart(2),
		   eScanUploadActive(3),
		   eScanUploadAborted(4),
		   eScanUploadDone(5),
		   eScanUploadNewPage(6)
		   }
    MAX-ACCESS read-write
    STATUS  current
    DESCRIPTION
                "Handshake mechanism between host and device to initiate
                scan operation and coordinate the transfer of scanned
                image data to the host.  This object serves both as an
                indicator of scan upload activity as well as a trigger
                for the host to alter scan upload progress.  The
                handshake is on a per page basis to allow greater host
                control.
                  eScanUploadIdle - indicates the scan upload activity
                is not occurring.  Host setting this object to
                eScanUploadIdle from eScanUploadActive will cause the
                scan upload activity to be prematurely terminated.  Host
                may set object to this state at any time.  Device sets
                object to this state only upon initial power up but will
                otherwise never set to this state of its own accord.
                  eScanUploadStart - indicates host requesting to
                commence a scan to host operation.  Host may set object
                to this state from eScanUploadIdle or
                eScanUploadNewPage.  Device will not set object to this
                state of its own accord.
                  eScanUploadActive - indicates scan upload activity is
                occurring.  The device sets object to this state to
                indicate host may commence receiving scanned image data.
                During this state, the device will be writing scanned
                image data to the I/O channel.
                  eScanUploadAborted - indicates the scanning and scan
                upload activity has terminated in error state.  This
                value is set by the device.  This state is not settable
                by the host.  The host should transition this state to
                eScanUploadIdle.
                  eScanUploadDone - indicates the device is signaling
                successful completion of scan upload activity and there
                are no more document pages in the scanner/ADF.  The
                application should set this object to eScanUploadIdle.
                  eScanUploadNewPage - indicates the device is signaling
                successful completion of scan upload activity for the
                current page and there remains at least one page in the
                scanner/ADF available for scanning.  Host may choose to
                begin scan upload cycle by setting object to
                eScanUploadStart or end the cycle by setting object to
                eScanUploadIdle.
                Additional information:
                eScanUploadNewPage - indicates
                the device is signaling successful completion
                of scan upload activity for the current page. There
                may be a page in the device or not.  The device will
                wait to prefeed another page until the application sets
                the object to eScanUploadStart.  This was to fix
                a bug on HP LaserJet 1100 that a prefed page would cause a jam
                if the application set the object to eScanUploadIdle.
                The application could not create another scan job until
                the prefed page was removed.

                Host may choose to begin scan upload cycle by
                setting object to eScanUploadStart or end the cycle
                by setting object to eScanUploadIdle."
::= { settings-scanner 12 }


default-scanner-margin-left OBJECT-TYPE
    SYNTAX  INTEGER(0..5088)
    MAX-ACCESS read-write
    STATUS  current
    DESCRIPTION
                "Sets the left scanner margin. The unit of measure should
                be documented in the device POS.
                Additional information:
                The margin value must be a multiple of 4
                for alignment reasons.  If the entered value is not
                a multiple of 4, the resolution value will be snapped
                down to the closest value divisible by 4."
::= { settings-scanner 16 }


default-scanner-margin-right OBJECT-TYPE
    SYNTAX  INTEGER(32..5120)
    MAX-ACCESS read-write
    STATUS  current
    DESCRIPTION
                "Sets the right scanner margin. The unit of measure
                should be documented in the device POS.
                Additional information:
                The margin value must be a multiple of 4
                for alignment reasons.  If the entered value is not
                a multiple of 4, the resolution value will be snapped
                down to the closest value divisible by 4."
::= { settings-scanner 17 }


scanner-accessory-serial-number OBJECT-TYPE
    SYNTAX  INTEGER(0..65535)
    MAX-ACCESS read-only
    STATUS  current
    DESCRIPTION
                "Identifies the serial number for the scanner accessory.
                If this is a writable object, the POS should indicate
                the maximum supported string length.  This string should
                only use characters from the US-ASCII code set.
                Additional information:
                The serial number is 5 digit decimal number."
::= { settings-scanner 18 }


scanner-accessory-model-number OBJECT-TYPE
    SYNTAX  DisplayString (SIZE(0..32))
    MAX-ACCESS read-only
    STATUS  current
    DESCRIPTION
                "Model number of the scanner accessory.  This string
                should only use characters from the US-ASCII code set.
                Additional information:
                Model number for the Fujitsu scanner."
::= { settings-scanner 19 }


scanner-accessory-adf-sheet-count OBJECT-TYPE
    SYNTAX  INTEGER(0..2147483647)
    MAX-ACCESS read-only
    STATUS  current
    DESCRIPTION
                "Total number of sheets that have been fed through the
                Automatic Document Feed (ADF) accessory.
                Additional information:
                The Automatic Document Feed (ADF) count is
                incremented each time a sheet feeds through the
                ADF."
::= { settings-scanner 20 }


scanner-accessory-flatbed-scan-count OBJECT-TYPE
    SYNTAX  INTEGER(0..2147483647)
    MAX-ACCESS read-only
    STATUS  current
    DESCRIPTION
                "Total number of scans performed by a flatbed scanner
                accessory.
                Additional information:
                The count is only incremented when a sheet is
                scanned on the FLATBED."
::= { settings-scanner 21 }


scanner-accessory-cleaning-interval OBJECT-TYPE
    SYNTAX  INTEGER(0..2147483647)
    MAX-ACCESS read-only
    STATUS  current
    DESCRIPTION
                "Recommended cleaning interval in units of sheets
                scanned.
                Additional information:
                Recommended cleaning interval is in units of sheets
                scanned."
::= { settings-scanner 22 }


scanner-accessory-cleaning-count OBJECT-TYPE
    SYNTAX  INTEGER(0..2147483647)
    MAX-ACCESS read-only
    STATUS  current
    DESCRIPTION
                "The number of sheets scanned since the last cleaning was
                performed.
                Additional information:
                The number of sheets that have gone through the
                ADF since the last cleaning was performed."
::= { settings-scanner 23 }


scanner-accessory-maintenance-interval OBJECT-TYPE
    SYNTAX  INTEGER(0..2147483647)
    MAX-ACCESS read-only
    STATUS  current
    DESCRIPTION
                "Recommended maintenance interval in units of sheets
                scanned.
                Additional information:
                Recommended maintenance interval is in units of sheets
                scanned."
::= { settings-scanner 24 }


scanner-accessory-maintenance-count OBJECT-TYPE
    SYNTAX  INTEGER(0..2147483647)
    MAX-ACCESS read-only
    STATUS  current
    DESCRIPTION
                "The number of sheets scanned since the last maintenance
                was performed.
                Additional information:
                The number of sheets that have gone through the
                ADF since the last maintenance was performed."
::= { settings-scanner 25 }


scanner-accessory-rom-revision OBJECT-TYPE
    SYNTAX  DisplayString (SIZE(0..32))
    MAX-ACCESS read-only
    STATUS  current
    DESCRIPTION
                "ROM revision of the scanner accessory firmware.
                Additional information:
                ROM revision of the Fujitsu scanner is
                downloaded from the scanner after the attached
                scanner establishes communications to the
                printer."
::= { settings-scanner 26 }


scanner-accessory-copy-processor-boot-revision OBJECT-TYPE
    SYNTAX  DisplayString (SIZE(0..32))
    MAX-ACCESS read-only
    STATUS  current
    DESCRIPTION
                "Boot ROM revision of scanner copy processor firmware.
                Boot code to initialize the copy processor, establish
                communications with the scanner, and load the runtime
                code.
                Additional information:
                Boot ROM revision of the Pixel Magic - Copy
                Processor firmware is downloaded from the scanner
                after the attached scanner establishes
                communications to the printer."
::= { settings-scanner 27 }


scanner-accessory-copy-processor-runtime-revision OBJECT-TYPE
    SYNTAX  DisplayString (SIZE(0..32))
    MAX-ACCESS read-only
    STATUS  current
    DESCRIPTION
                "Revision of the runtime firmware for the scanner copy
                processor.  Runtime code which retrieves scanned data
                from the scanner and sends it to other devices such as a
                printer or PC host.
                Additional information:
                Revision of Pixel Magic - Copy Processor
                firmware shipped on the disk which is download
                into RAM for execution."
::= { settings-scanner 28 }


scanner-accessory-service-agent-revision OBJECT-TYPE
    SYNTAX  DisplayString (SIZE(0..32))
    MAX-ACCESS read-only
    STATUS  current
    DESCRIPTION
                "Revision of scanner service agent firmware.  Service
                agent which accepts scanned data and processes scanner
                copy processor requests, resident in a device such as a
                printer or PC host.
                Additional information:
                Revision of the Scanner Service Agent firmware
                shipped on the disk as a Service Provider entity
                to retrieve scanned data from the scanner."
::= { settings-scanner 29 }


scanner-accessory-control-panel-user-interface-revision OBJECT-TYPE
    SYNTAX  DisplayString (SIZE(0..32))
    MAX-ACCESS read-only
    STATUS  current
    DESCRIPTION
                "Revision of the control panel user interface firmware.
                Additional information:
                Revision of the copy processor user interface
                firmware shipped on the disk."
::= { settings-scanner 30 }


scanner-accessory-nvram OBJECT-TYPE
    SYNTAX  OCTET STRING (SIZE(1..40))
    MAX-ACCESS read-only
    STATUS  current
    DESCRIPTION
                "Returns the contents of the NVRAM (Non-Volatile RAM)
                located in the scanner accessory.
                Additional information:
                Read bytes 0..39 of the NVRAM in the
                scanner.  The Fujitsu Controller board has a
                total of 128 bytes of NVRAM."
::= { settings-scanner 33 }


scanner-accessory-nvram2 OBJECT-TYPE
    SYNTAX  OCTET STRING (SIZE(1..40))
    MAX-ACCESS read-only
    STATUS  current
    DESCRIPTION
                "Returns the second part of the contents of the NVRAM
                (Non-Volatile RAM) located in the scanner accessory.
                Additional information:
                Read bytes 40..79 of the NVRAM in the
                scanner.  The Fujitsu Controller board has a
                total of 128 bytes of NVRAM."
::= { settings-scanner 34 }


scanner-accessory-nvram3 OBJECT-TYPE
    SYNTAX  OCTET STRING (SIZE(1..40))
    MAX-ACCESS read-only
    STATUS  current
    DESCRIPTION
                "Returns the third part of the contents of the NVRAM
                (Non-Volatile RAM) located in the scanner accessory.
                Additional information:
                Read bytes 80..119 of the NVRAM in the
                scanner.  The Fujitsu Controller board has a
                total of 128 bytes of NVRAM."
::= { settings-scanner 35 }


scanner-accessory-nvram4 OBJECT-TYPE
    SYNTAX  OCTET STRING (SIZE(1..8))
    MAX-ACCESS read-only
    STATUS  current
    DESCRIPTION
                "Returns the fourth part of the contents of the NVRAM
                (Non-Volatile RAM) located in the scanner accessory.
                Additional information:
                Read bytes 120..127 of the NVRAM in the
                scanner.  The Fujitsu Controller board has a
                total of 128 bytes of NVRAM."
::= { settings-scanner 36 }


ui-add-option OBJECT-TYPE
    SYNTAX  DisplayString
    MAX-ACCESS read-write
    STATUS  current
    DESCRIPTION
                "Lets the host application set up target (eg.scan) destinations.
                The destinations can be a host network address and/or an
                application to be launched on that host. The string sent
                down has a list of 'KEYWORD=value;' items. The data sent
                down also contains a string to be displayed in the device
                LCD display.  The device POS specifies the number of strings
                that can be handled (eg. 20) and the replacement/expiration
                policy as new target destinations are added.
                Additional information:
                For push scanning on the 4-pack, there will be a
                limitation to the number of unique strings sent to the device
                via UI-ADD-OPTION.  A host registers for push scanning by using
                the UI-ADD-OPTION object. HP Laserjet 3200 will limit the number of hosts
                registered for push scanning to 20.  HP LaserJet 1220 will have a
                limitation of 1.  Another limitation for the 4-pack is that the
                DISPLAY value must be at most 18 characters.  This limitation is
                due to the control panel display. "
::= { settings-scanner 37 }


ui-select-option OBJECT-TYPE
    SYNTAX  DisplayString
    MAX-ACCESS read-only
    STATUS  current
    DESCRIPTION
                "Triggers a job from the device based on the option selected."
::= { settings-scanner 38 }


ui-delete-option OBJECT-TYPE
    SYNTAX  DisplayString
    MAX-ACCESS read-write
    STATUS  current
    DESCRIPTION
                "Lets the host application delete target eg. scan
                destinations that were setup with UI-ADD-OPTION.
                The host sends down the entire string that was
                sent earlier. The firmware looks for an exact
                match in its lists and deletes the requested
                option.
                Additional information:
                Removes an existing option only if it is
                uniquely matched by the given object value."
::= { settings-scanner 42 }


scanner-jam-page-count OBJECT-TYPE
    SYNTAX  INTEGER
    MAX-ACCESS read-write
    STATUS  current
    DESCRIPTION
                "Indicates a count of the total pages jammed in the scanner'slifetime."
::= { settings-scanner 43 }


scanner-adf-page-count OBJECT-TYPE
    SYNTAX  INTEGER
    MAX-ACCESS read-write
    STATUS  current
    DESCRIPTION
                "Indicates a count of the total pages scanned through the ADF on the
                device. This may include scan to host jobs, copyjobs, and fax jobs. If
                only the total pages scanned to the host are wanted, use
                SCAN-ADF-PAGE-COUNT."
::= { settings-scanner 44 }


scan-adf-page-count OBJECT-TYPE
    SYNTAX  INTEGER
    MAX-ACCESS read-write
    STATUS  current
    DESCRIPTION
                "Indicates the total pages scanned through the ADF to the host from the
                device. If the total pages scanned through the scanner are needed for
                all features, including copy and fax jobs, use the
                SCANNER-ADF-PAGE-COUNT object."
::= { settings-scanner 45 }


scan-image-type OBJECT-TYPE
    SYNTAX  INTEGER {
		   eText(1),
		   ePhoto(2),
		   eMixed(3)
		   }
    MAX-ACCESS read-write
    STATUS  current
    DESCRIPTION
                "Indicates the image type of the scan data."
::= { settings-scanner 46 }


scan-subsample OBJECT-TYPE
    SYNTAX  INTEGER {
		   eFourToOneToOne(1),
		   eFourToTwoToTwo(2),
		   eFourToThreeToThree(3),
		   eFourToFourToFour(4)
		   }
    MAX-ACCESS read-write
    STATUS  current
    DESCRIPTION
                "Indicates the subsampling used for Scan Data. 4:1:1, 4:2:2, and
                4:3:3 subsampling are used to modify the scan image quality and amount
                of scan data by reducing the number of samples or pixels of the
                luminous and chrominance data."
::= { settings-scanner 47 }


scanner-retrieve-scanline OBJECT-TYPE
    SYNTAX  OCTET STRING
    MAX-ACCESS read-write
    STATUS  current
    DESCRIPTION
                "This object facilitates the sending of a scan line of data from the
                scanner to a host.  It grabs either raw or corrected data.
                SERVICE-PASSWORD must be set correctly to use this object.
                 cScannerRequestRawScanLine - This is set by the host in order to
                signal to the firmware that it wants an scan line of raw (no PRNU or
                DSNU correction)data to be sent back up to the host.
                 cScannerRequestCorrectedScanLine - This is set by the host in order to
                signal to the firmware that it wants a scan line of corrected (PRNU or
                DSNU correction) data to be sent back up to the host.
                 cScannerSendDataRequest - This is set by firmware to indicate that it
                has acquired the scan line from scan engine and is ready to send the
                data to the host.
                 cScannerSendDataOK - This is set by the host to
                indicate that it is ready to receive the data from the device.
                 cScannerSendDataDone - This is set by the firmware to indicate that
                the transfer of data is complete.
                 cScannerPickSheet - This is set by the
                host to tell the device to pick and stage the sheet of paper in the
                ADF.
                 cScannerFlushSheet - This is set by the host to tell the device to
                flush the sheet of paper currently in the device.
                Additional information:
                This object is meant to be used by Manufacturing
                		in order to facilitate the sending of a scan line of data from
                		 the scanner over HDT.  It
                		grabs either raw or corrected data."
::= { settings-scanner 48 }


scanner-motor-control OBJECT-TYPE
    SYNTAX  INTEGER
    MAX-ACCESS read-write
    STATUS  current
    DESCRIPTION
                "This objects is set to the number of steps that the scan motor should move.
                  SERVICE-PASSWORD must be setcorrectly to use this object.
                Additional information:
                This objects is set to the number of steps that
                		the scan motor should move. It is meant to be used by Manufacturing
                		in order to position the scanner shipping blocks."
::= { settings-scanner 49 }


scan-height OBJECT-TYPE
    SYNTAX  INTEGER(0..25200)
    MAX-ACCESS read-write
    STATUS  current
    DESCRIPTION
                "Used to set the height of a scan image in Decapoints.  The use of
                 Decapoints as units of measure eliminates the need for the user to
                 understand the scanner mechanics and the device supported resolutions.
                Additional information:
                This object will be used to set the height of the
                scan image.  The height will be entered using the
                measurement of 1/720th  of an inch.  This will eliminate
                the host being tied to the scanner mechanics and needing
                to know what resolutions and number of lines the device
                supports."
::= { settings-scanner 50 }


scanner-scanline-statistics OBJECT-TYPE
    SYNTAX  DisplayString
    MAX-ACCESS read-only
    STATUS  current
    DESCRIPTION
                "This object is used to obtain statistics about the scan line
                 that was previously obtained using the SCANNER-RETRIEVE-SCANLINE
                 object. Just as SERVICE-PASSWORD must be set correctly for
                 SCANNER-RETRIEVE-SCANLINE, it must be set correctly to use this
                 object as well.
                Additional information:
                This object is used to obtain statistics about
                the scan line that was previously grabbed using the SCANNER_
                RETRIEVE_SCANLINE object, max string is 256 bytes.  The format
                is the following: max red value; position; min red value; position;
                max red pixel to pixel difference; position; red mean; max blue value;
                position; min blue value; position; max blue pixel to pixel difference;
                position; blue mean; max green value; position; min green value;
                position; max green pixel to pixel difference; position; green mean;"
::= { settings-scanner 51 }


scan-control-descriptor OBJECT-TYPE
    SYNTAX  DisplayString
    MAX-ACCESS read-only
    STATUS  current
    DESCRIPTION
                "Describes the control language and formats supported for this scanner."
::= { settings-scanner 52 }


scan-gamma-correction OBJECT-TYPE
    SYNTAX  OCTET STRING (SIZE(1..32))
    MAX-ACCESS read-write
    STATUS  current
    DESCRIPTION
                "A 32-bit quantity that indicates the gamma correction to
               use on the scan image. The first 16 bits indicate the
               integral portion of the gamma correction.  The last 16
               bits indicate the fraction portion in units of 1/65536.
               An example is gamma correction value of 2.2 will be
               representedas 0x00023333 (2 & 13107/65536ths)).

               The 4-pack products (HP Laserjet 3200, HP Laserjet 1220, HP Laserjet 2200 & HP Laserjet 1200)
               software will set the gamma correction to be applied on
               the scan data.  IPE SW will request a value of 1.0, which
               indicates no gamma correction. TWAIN software will request a
               value of 2.2 for grayscale scans and 2.9 for color scans.

               The device pos will indicate any deviation from the
               above description.
                Additional information:
                Indicates the gamma correction to use on the
                scan image. The first 16 bits indicate the integral portion
                of the gamma correction.  The last 16 bits indicate the fraction
                portion and in units of 1/65536.  An example is gamma correction
                value of 2.2 will be represented as 0x00023333 (2 & 13107/65536ths). "
::= { settings-scanner 53 }


scan-pad-image OBJECT-TYPE
    SYNTAX  INTEGER {
		   eOff(1),
		   eOn(2)
		   }
    MAX-ACCESS read-write
    STATUS  current
    DESCRIPTION
                "Indicates if the scan image should be padded with white data
               or not."
::= { settings-scanner 54 }

-- 1.3.6.1.4.1.11.2.3.9.4.2.1.2.2.1.63
scanner-accessory-total-copy-pages-printed   OBJECT-TYPE
    SYNTAX          INTEGER
    MAX-ACCESS read-only
    STATUS            current
    DESCRIPTION " This relates to the number of copy pages printed on a device.
    The output sheet that is duplexed (made 2- sided) should be
    counted as 2 pages"
::= { settings-scanner 63 }

scan-flatbed-page-count OBJECT-TYPE
    SYNTAX      INTEGER
    MAX-ACCESS read-write
    STATUS      current
       DESCRIPTION "This object tracks the page count for the pages scanned from
		the flatbed."
::= { settings-scanner 73 }


scanner-flatbed-page-count OBJECT-TYPE
    SYNTAX      INTEGER
    MAX-ACCESS read-write
    STATUS      current
       DESCRIPTION "This object tracks the page count for the pages scanned for all
		jobs from the flatbed. This includes scan to host jobs, fax
		jobs, and copy jobs. "
::= { settings-scanner 74 }


scanner-modular-hardware OBJECT-TYPE
    SYNTAX      OCTET STRING
    MAX-ACCESS read-only
    STATUS      current
       DESCRIPTION "Used to specify whether optional hardware is installed or not.
                Additional information:
                This HP LaserJet MFP uses this object to allow
                a host to query whether or not it has an ADF installed,
                		Letter/A4 flatbed, or Legal flatbed."
::= { settings-scanner 75 }


scanner-clock-edge-modifiers OBJECT-TYPE
    SYNTAX      OCTET STRING
    MAX-ACCESS read-write
    STATUS      current
       DESCRIPTION "This object accesses a table used by firmware to modify clock
		edge values for CCD scanner modules.
                Additional information:
                This object accesses a table used by firmware to modify
                	  	   clock edge values for CCD scanner modules."
::= { settings-scanner 84 }


scan-clock-edges OBJECT-TYPE
    SYNTAX      OCTET STRING
    MAX-ACCESS read-only
    STATUS      current
       DESCRIPTION "Returns a table of clock edges used by the scanner.
                Additional information:
                Returns a table of clock edges used by the scanner."
::= { settings-scanner 85 }


scan-emulate-copy OBJECT-TYPE
    SYNTAX      INTEGER {
                          eYes(1),
                          eNo(2)
		   }
    MAX-ACCESS read-write
    STATUS      current
       DESCRIPTION "Setting this object to eYes will cause firmware to run the next
		scan job as if it were a copy job, using copy values for
		scanner h/w and image processing, and then return the data to
		the host as if it were a scan job. Setting this object to eNo
		will cause firmware to process scan jobs in the normal way.
                Additional information:
                Setting this object to eYes will cause firmware to run
                the next scan job as if it were a copy job, using copy
                values for scanner h/w and image processing, and then
                return the data to the host as if it were a scan job.
                Setting this object to eNo will cause firmware to
                process scan jobs in the normal way."
::= { settings-scanner 86 }


scan-calibration-target OBJECT-TYPE
    SYNTAX  INTEGER {
		   eWhiteSheet(1),
		   ePlaten(2)
		   }
    MAX-ACCESS read-only
    STATUS  current
    DESCRIPTION
                "This object is used by the host to check which type of calibration
                 this scan device supports.  The device pos will describe the meaning
                 and intent of each type of scan calibration supported.
                Additional information:
                This object is used by the host to check which
                type of calibration the firmware supports.  This is in
                anticipation of the fact that the initial release of HP Laserjet 3200
                will be calibrated off of a sheet, but the 'Rest of World'
                release will be calibrated off of the platen."
::= { scan-calibration 18 }


not-ready-source-scanner OBJECT-TYPE
    SYNTAX  OCTET STRING
    MAX-ACCESS read-only
    STATUS  current
    DESCRIPTION
                "Indicates whether and why the scanner is not ready.  A
                set bit indicates a problem.
                Additional information:
                ISSUES: HP LaserJet 1100 only used
                cScannerFeederJam.  Tahiti does not have
                an ADF sensor.  Can cScannerFeederEmpty still
                be used (i.e. when the device tries to pull
                a page, but the ADF is empty or a mispick
                occurred).  cInvalidScannerMediaSize may be used.
                If a page is longer that 33 inches normally this would be
                shown to the host as a Jam.  However, can the device
                use cInvalidScannerMediaSize instead?"
::= { status-scanner 1 }


scan-resolution-range OBJECT-TYPE
    SYNTAX  DisplayString
    MAX-ACCESS read-only
    STATUS  current
    DESCRIPTION
                "Enumerates the range of selectable scanning resolutions.
                Format as follows: Each supported resolution is in the
                format: (m)x(n) where m describes the x dpi resolution
                along the paper width.  n describes the y dpi resolution
                along the paper length.  A scanner that supports several
                resolutions would enumerate each resolution separated by
                a comma.  A scanner that supports a continuous
                resolution range would format its range as: (m1-m2)x(n1-
                n2) where m1 < m2, n1 < n2 "
::= { status-scanner 3 }


scan-calibration-download OBJECT-TYPE
    SYNTAX  OCTET STRING
    MAX-ACCESS read-write
    STATUS  current
    DESCRIPTION
                "Returns or changes the state of the calibration
                operation.
                cScanCalibrationIdle - indicates that calibration is not
                in progress.
                cScanCalibrationStart - This state is set by host to
                request calibration initiation. Device should not set to
                this state.
                cScanCalibrationActive - Indicates device is in
                calibration mode.  Device sets cScanCalibrationActive to
                signal calibration is in process.
                cScanCalibrationAborted - Set by device to indicate
                calibration was prematurely terminated. Set by host when
                a calibration error occurs.
                cScanCalibrationSendDataRequest - Set by host when host
                wants to send data to the device.
                cScanCalibrationSendDataRequestOK - Set by the device to
                tell the host that the device is ready to accept data.
                cScanCalibrationSendDataRequestDone -Set by the device
                to indicate the data was received by the device.
                cScanCalibrationRequestScanBuffer - Set by the host to
                request a buffer from the device.
                cScanCalibrationDone - Set by the host to inform the
                device calibration is complete.
                The sequence of bits being set and the restrictions for
                setting bits should be documented in the device POS.
                Additional information:
                This object was originally defined for
                		use on HP LaserJet 1100. HP Laserjet 3200 we will not be using
                		values 3-6.  These are no longer applicable since
                		the calibration is completely contained within firmware."
::= { status-scanner 5 }


scan-calibration-error OBJECT-TYPE
    SYNTAX  INTEGER {
		   eNoError(1),
		   eUnknownCalibrationError(2),
		   eScannerFeederEmpty(3),
		   eLowMemory(4),
		   eWriteFailed(5),
		   eScannerBusy(6),
		   eADFMispick(7),
		   eADFJam(8),
		   eUncorrectablePixels(9)
		   }
    MAX-ACCESS read-only
    STATUS  current
    DESCRIPTION
                "Error status of the most recent calibration session.
                eNoError(1) - The calibation was successful.
                eUnknownCalibrationError(2) - An unknown error
                occurred.
                eScannerFeederEmpty(3) - The feeder contained nothing to
                scan.
                eLowMemory(4) - Insufficient memory available to
                complete the calibration.
                eWriteFailed(5) - Write to NVRAM failure.
                eScannerBusy(6) - Scanner is busy.
                Detailed information about the cause and remedy for each
                error should be documented in the device POS.
                Additional information:
                This object was originally defined for use on
                		HP LaserJet 1100. We are proposing the new enums number 7-9.
                	        Note: Option 9 would only be set during a factory calibration
                to indicate that at least one pixel was not correctable by
                the digital calibration factors."
::= { status-scanner 6 }


scanner-button-status OBJECT-TYPE
    SYNTAX  INTEGER {
		   eOff(1),
		   eOn(2)
		   }
    MAX-ACCESS read-write
    STATUS  current
    DESCRIPTION
                "Indicates the scanner button has been pressed. The value
                changes to eOn(2) when the button is pressed. The host
                acknowledges the button press by setting the value to
                eOff(1)."
::= { status-scanner 7 }


scanner-lamp-gain-value OBJECT-TYPE
    SYNTAX      DisplayString
    MAX-ACCESS read-only
    STATUS      current
       DESCRIPTION "Provides PWM and analog gain for the color channels. The range
		will vary based on scan mode. The device specific POS should
		describe the valid range. The format is the following:
		    PWM value; red analog gain; green analog gain; blue analog
			gain.
                Additional information:
                 The range will vary based on scan mode.  The values
                will differ from those of San Diego.  The initial value
                can be obtained at the start of warmup and the final
                value can be obtained at the end of warmup. The warmup period is about
                2 minutes.  The format is the following PWM value; red analog gain;
                green analog gain; blue analog gain;.  The valid values for PWM value
                are 580 - 730 and the valid values for analog gains are 1.00-5.80.
                The gains are reported with accuracy to 2 decimal places.
                A sample return value would be '584;1.00;1.34;1.00;' "
::= { status-scanner 8 }


scanner-light-monitor-window OBJECT-TYPE
    SYNTAX      OCTET STRING
    MAX-ACCESS read-only
    STATUS      current
       DESCRIPTION "Provides the pixel at which the LMW starts, as the ratio of the
		average LMW value to the six pixel average value. The device
		specific pos should specify the valid ranges for each value.
		The format is the following:
		    LMW position; ratio of LMWavg to 6 pixel avg.
                Additional information:
                Provides the pixel at which the LMW starts as well as
                the ratio of the average LMW value over a 6 pixel average value.
                A algebraic representation of this ratio is:
                Average of Light Monitor Window pixels
                ______________________________________
                Average of 6 test point pixels

                The 6 test point pixels do not inlcude any of the Light Monitor Window.
                A sample return value would be '50;0.059;'. "
::= { status-scanner 9 }


scanner-reference-position OBJECT-TYPE
    SYNTAX      DisplayString
    MAX-ACCESS read-only
    STATUS      current
       DESCRIPTION "Provides 3 pairs of x,y coordinates within a specified range of
		the calibrate reference position. The device specific POS
		should specify the valid ranges. The format is the following:
		'x;y;x;y;x;y'
                Additional information:
                Provides x,y coordinates within 1/300 of a line of the
                calibrate reference position.  The 3 locations in order that are
                reported are the 1st Reference Mark, the 2nd Reference Mark, and
                the Document Origin.  A sample return value would be
                80,471;2523,2914;80,471;1;34326;27,32;193;35748;28,27;194;0,0;0;0;0;0;0;0;0,0;0;0;0;0;0;0;0,0;0;0,0;0;0;0
                The extra 0's on the end are used specifically to gather information during
                the cimation process. "
::= { status-scanner 10 }


scanner-sensor-manufacturer OBJECT-TYPE
    SYNTAX      DisplayString
    MAX-ACCESS read-only
    STATUS      current
       DESCRIPTION "Reports the scan sensor manufacturer. The device specific POS
		should list valid manufacturers.
                Additional information:
                Reports the scan sensor manufacturer.  The device specific
                POS should list valid manufacturers."
::= { status-scanner 11 }


rpc-test-return-code OBJECT-TYPE
    SYNTAX  OCTET STRING
    MAX-ACCESS read-write
    STATUS  current
    DESCRIPTION
                "This test object that will not be supported in any
                released product.  Setting this object allows the next
                RPC call return code to be specified.  The POS will
                specify the binary format.
                Additional information:
                The format of the binary data is a one
                of three formats.  The first format is no binary
                data, which indicates the next RPC reply should not
                be modified.  The other two formats are described in
                RFC 1057 and encoded using XDR (i.e.  the value is
                the data used to instead of the actual RPC reply).
                The second format is when reply_stat is MSG_ACCEPTED
                and accept_stat is something other than SUCCESS.
                The third format is when reply_stat is MSG_DENIED.
                Notice that all RPC replies that do not contain any
                'results' are supported."
::= { settings-rpc 1 }


rpc-bind-protocol-address OBJECT-TYPE
    SYNTAX  OCTET STRING
    MAX-ACCESS read-write
    STATUS  current
    DESCRIPTION
                "Array of Berkeley sockets style protocol addresses used
                to bind RPC to a communications protocol family.
                Setting an instance of this array object to a zero
                length binary value disables the transport protocol
                indicated by that instance.  All multi-bytes fields are
                in network (or big-endian) order.  Bytes 1 and 2
                indicate the transport protocol.  Some of the transport
                protocol mapping information can be found in RFC 1010
                Assigned Numbers.  A list of interesting transport
                protocol number mappings include:
                Protocol | Number
                ---------+-------
                 UDP/IP  |  17
                  IPX    |  1000
                  MLC    |  4660
                Bytes 3 and 4 indicate the address family.  The address
                family uses the same mapping as the BSD sockets address
                family.  A list of interesting address family mappings
                include:
                Address Family | Number
                ---------------+-------
                    Internet   |   2
                    NetWare    |   6
                    MLC        | 22136
                The format the fifth and following bytes is dependent on
                the address family.  For the Internet address family,
                bytes 5 and 6 contain the port number, bytes 7 through
                10 contain the IP address, and the following eight bytes
                are unused.  For NetWare, bytes 5 through 8 are the
                network number, bytes 9 through 14 are the node number,
                and bytes 15 and 16 are the socket number.
                Additional information:
                The length of the binary value is zero
                if the instance of an object in the rpc-bind-protocol-address
                array is not in use.   An unfortunate side effect of the
                implementation is initializing the mass storage device sets this object
                back to the factory default value.
                Returns <noSuchName>
                status if attempting to access this object and there
                is no storage device is installed."
::= { settings-rpc 2 }


rpc-statistic-successful OBJECT-TYPE
    SYNTAX  INTEGER
    MAX-ACCESS read-only
    STATUS  current
    DESCRIPTION
                "A counter indicating the number of RPC requests that
                completed successfully (reply_data stat is SUCCESS).
                The POS should state if a power cycle causes the counter
                is be reset to zero.
                Additional information:
                Reset to the factory default value after
                a power cycle.
                Returns <noSuchName>
                status if attempting to access this object and there
                is no storage device is installed."
::= { status-rpc 1 }


rpc-statistic-unsuccessful OBJECT-TYPE
    SYNTAX  INTEGER
    MAX-ACCESS read-only
    STATUS  current
    DESCRIPTION
                "A counter indicating the number of RPC requests that
                completed unsuccessfully (reply_data stat is not
                SUCCESS).  The POS should state if a power cycle causes
                the counter is be reset to zero.
                Additional information:
                Reset to the factory default value after
                a power cycle.
                Returns <noSuchName>
                status if attempting to access this object and there
                is no storage device is installed."
::= { status-rpc 2 }


rpc-bound-protocol-address OBJECT-TYPE
    SYNTAX  OCTET STRING
    MAX-ACCESS read-only
    STATUS  current
    DESCRIPTION
                "An array of Berkeley sockets style protocol addresses
                that the NFS service has been bound to successful.  The
                format is that same as the array of RPC-BIND-PROTOCOL-
                ADDRESS of objects.
                Additional information:
                Returns <noSuchName>
                status if attempting to access this object and there
                is no storage device is installed."
::= { status-rpc 3 }

mount-test-return-code OBJECT-TYPE
    SYNTAX  OCTET STRING
    MAX-ACCESS read-write
    STATUS  current
    DESCRIPTION
                "This test object that will not be supported in any
                released product.  Setting this object allows the next
                mount call return code to be specified.  The POS will
                specify the binary format.
                Additional information:
                A one byte binary value.  The
                byte indicates what procedure is being effected by
                this set.
                value | function
                ------+------------------
                1   | Mount will return an fhstatus of 0.
                2   | Dump will return an empty table."
::= { settings-mount 1 }

nfs-server-memory OBJECT-TYPE
    SYNTAX  INTEGER
    MAX-ACCESS read-only
    STATUS  current
    DESCRIPTION
                "The amount of memory, in bytes, used by the Network File
                System server to buffer file data.
                Additional information:
                Reports the amount of memory, in bytes,
                reserved for use by the NFS server.  An unfortunate
                side effect of the implementation is initializing
                the mass storage device sets this object back to the factory
                default value.  Also includes the memory used by
                other firmware components in addition to the NFS
                server.  Returns <noSuchName>
                status if attempting to access this object and there
                is no storage device is installed."
::= { settings-nfs-server 1 }


nfs-server-read-size OBJECT-TYPE
    SYNTAX  INTEGER(256..1500)
    MAX-ACCESS read-write
    STATUS  current
    DESCRIPTION
                "The maximum amount of data transferred in one NFS server
                read data call.
                Additional information:
                An unfortunate side effect of the
                implementation is initializing the mass storage device
                	   sets this object back to the factory default value.
                Returns <noSuchName>
                status if attempting to access this object and there
                is no storage device is installed.  Rebooting causes
                	   this value to reset to factory default.
                	      value < 256 snaps to 256
                	      value > 1500 snaps to 1500"
::= { settings-nfs-server 2 }


nfs-server-write-size OBJECT-TYPE
    SYNTAX  INTEGER(256..1500)
    MAX-ACCESS read-write
    STATUS  current
    DESCRIPTION
                "The maximum amount of data transferred in one NFS server
                write data call.
                Additional information:
                An unfortunate side effect of the
                implementation is initializing the mass storage device sets this object
                back to the factory default value.
                Returns <noSuchName>
                status if attempting to access this object and there
                is no storage device is installed."
::= { settings-nfs-server 3 }


nfs-server-test-return-code OBJECT-TYPE
    SYNTAX  OCTET STRING
    MAX-ACCESS read-write
    STATUS  current
    DESCRIPTION
                "This test object that will not be supported in any
                released product.  Setting this object allows the next
                NFS call return code to be specified.  The POS will
                specify the binary format.
                Additional information:
                A three byte binary value.  The first
                byte indicates what procedure is being effected by
                this set.
                value | function
                ------+------------------
                1   | GetAttr
                2   | SetAttr
                3   | reserved
                4   | Lookup
                5   | reserved
                6   | Read
                7   | reserved
                8   | Write
                9   | Create
                10  | Remove
                11  | Rename
                12  | reserved
                13  | reserved
                14  | MkDir
                15  | RmDir
                16  | ReadDir
                17  | StatFS
                The second byte is the stat value returned by the next
                call to procedure specified by the value of the
                first byte.  The second byte can not be zero.  Refer
                to RFC 1094 for a list of stat values.  The third byte
                indicates
                which call to the specified file system routine will
                fail.  A value of one means the first call will fail.
                A value of two means the second call will fail, and
                so on.  Writing this object causes any previous write to
                this object to be invalidated."
::= { settings-nfs-server 4 }


nfs-server-statistic-successful OBJECT-TYPE
    SYNTAX  INTEGER
    MAX-ACCESS read-only
    STATUS  current
    DESCRIPTION
                "A counter indicating the number of NFS requests that
                completed without error.  The POS should state if a
                power cycle causes the counter is be reset to zero.
                Additional information:
                Reset to the factory default value after
                a power cycle.
                Returns <noSuchName>
                status if attempting to access this object and there
                is no storage device is installed."
::= { status-nfs-server 1 }


nfs-server-statistic-unsuccessful OBJECT-TYPE
    SYNTAX  INTEGER
    MAX-ACCESS read-only
    STATUS  current
    DESCRIPTION
                "A counter indicating the number of NFS requests that
                completed with an NFS status other than NFS_OK (0).  The
                POS should state if a power cycle causes the counter is
                be reset to zero.
                Additional information:
                Reset to the factory default value after
                a power cycle.
                Returns <noSuchName>
                status if attempting to access this object and there
                is no storage device is installed."
::= { status-nfs-server 2 }


nfs-server-statistic-current-memory-usage OBJECT-TYPE
    SYNTAX  INTEGER
    MAX-ACCESS read-only
    STATUS  current
    DESCRIPTION
                "A value indicating the number of bytes of RAM currently
                used by the NFS firmware.
                Additional information:
                Reset to the factory default value after
                a power cycle.
                Returns <noSuchName>
                status if attempting to access this object and there
                is no storage device is installed."
::= { status-nfs-server 4 }


nfs-server-statistic-max-memory-usage OBJECT-TYPE
    SYNTAX  INTEGER
    MAX-ACCESS read-only
    STATUS  current
    DESCRIPTION
                "A value indicating the maximum number of bytes of RAM
                used by the NFS firmware.  The POS should state if the
                value is reset to zero after a power cycle.
                Additional information:
                Reset to the factory default value after
                a power cycle.
                Returns <noSuchName>
                status if attempting to access this object and there
                is no storage device is installed."
::= { status-nfs-server 5 }


rpc-bind-test-return-code OBJECT-TYPE
    SYNTAX  OCTET STRING
    MAX-ACCESS read-write
    STATUS  current
    DESCRIPTION
                "This test object that will not be supported in any
                released product.  Setting this object allows the next
                RPC bind call return code to be specified.  The POS will
                specify the binary format.
                Additional information:
                A one byte value.
                value | meaning
                ------+------------------
                1   | Next GetPort or GetAddr will receive port 0
                | (indicating the service is not supported).
                2   | Next Dump will receive an empty table."
::= { settings-rpc-bind 1 }


rpc-bind-statistic-successful OBJECT-TYPE
    SYNTAX  INTEGER
    MAX-ACCESS read-only
    STATUS  current
    DESCRIPTION
                "A counter indicating the number of RPC bind (RPC program
                number 100000, version 2) requests that completed
                successfully.  The POS should state if a power cycle
                causes the counter is be reset to zero.
                Additional information:
                Reset to the factory default value after
                a power cycle.
                Returns <noSuchName>
                status if attempting to access this object and there
                is no storage device is installed."
::= { status-rpc-bind 1 }


rpc-bind-statistic-unsuccessful OBJECT-TYPE
    SYNTAX  INTEGER
    MAX-ACCESS read-only
    STATUS  current
    DESCRIPTION
                "A counter indicating the number of RPC bind (RPC program
                number 100000, version 2) requests that completed
                unsuccessfully.  The POS should state if a power cycle
                causes the counter is be reset to zero.
                Additional information:
                Reset to the factory default value after
                a power cycle.
                Returns <noSuchName>
                status if attempting to access this object and there
                is no storage device is installed."
::= { status-rpc-bind 2 }


xip-statistic-processed OBJECT-TYPE
    SYNTAX  INTEGER
    MAX-ACCESS read-only
    STATUS  current
    DESCRIPTION
                "A counter indicating the number of XIP requests that
                were processed.  The POS should state if a power cycle
                causes the counter is be reset to zero.
                Additional information:
                The number of XIP datagrams that have
                been received by the XIP service.  Reset to the
                factory default value after a power cycle.  Returns
                <noSuchName> status if attempting
                to access this object and there is no storage device
                is installed."
::= { status-xip 1 }


xip-statistic-data-in-dropped OBJECT-TYPE
    SYNTAX  INTEGER
    MAX-ACCESS read-only
    STATUS  current
    DESCRIPTION
                "A counter indicating the number of XIP data in datagrams
                that were dropped (typically due to the printer being
                flooded with XIP requests ).  The POS should state if a
                power cycle causes the counter is be reset to zero.
                Additional information:
                Reset to the factory default value after
                a power cycle.
                Returns <noSuchName>
                status if attempting to access this object and there
                is no storage device is installed."
::= { status-xip 2 }


prtinterpreterlangfamily OBJECT-TYPE
    SYNTAX  INTEGER {
		   ePother(1),
		   ePlangPCL(3),
		   ePlangPJL(5),
		   ePlangPS(6),
		   ePlangAutomatic(37),
		   ePlangPCLXL(47)
		   }
    MAX-ACCESS read-only
    STATUS  current
    DESCRIPTION
                "The family name of a Page Description Language (PDL) or
        control language which this interpreter in the printer can
		interpret or emulate.
	Refer to Standard Printer MIB for more details.
                Additional information:
                ePlangAutomatic refers to the `super-language'
                made available by implicit language switching."
::= { prtInterpreterEntry 2 }


prtinterpreterlanglevel OBJECT-TYPE
    SYNTAX  OCTET STRING (SIZE(0..31))
    MAX-ACCESS read-only
    STATUS  current
    DESCRIPTION
                "The level of the language which this interpreter is
        interpreting or emulating.  This might contain a value like
        '5e' for an interpreter which is emulating level 5e of the PCL
        language.  It might contain '2' for an interpreter which is
        emulating level 2 of the PostScript language.  Similarly it
        might contain '2' for an interpreter which is emulating level
        2 of the HPGL language.
	Refer to Standard Printer MIB for more details.
                Additional information:
                Replaces PML PCL-VERSION."
::= { prtInterpreterEntry 3 }


prtinterpreterlangversion OBJECT-TYPE
    SYNTAX  OCTET STRING (SIZE(0..31))
    MAX-ACCESS read-only
    STATUS  current
    DESCRIPTION
                "The date code or version of the language which this interpreter
        is interpreting or emulating.
	Refer to Standard Printer MIB for more details.
                Additional information:
                Replaces PML FW-ROM-DATECODE, PJL-DATECODE,
                PCL-DATECODE and PS-DATECODE

                These values are derived from the dateCode field of the personality
                entities.  (ePlangAutomatic uses the PJL dateCode.)"
::= { prtInterpreterEntry 4 }


prtinterpreterdescription OBJECT-TYPE
    SYNTAX  OCTET STRING (SIZE(0..255))
    MAX-ACCESS read-only
    STATUS  current
    DESCRIPTION
                "A string to identify this interpreter in the localization
        specified by prtGeneralCurrentLocalization as opposed to the
        language which is being interpreted.  It is anticipated that
        this string will allow manufacturers to unambiguously identify
        their interpreters.
	Refer to Standard Printer MIB for more details.
                Additional information:
                These values are obtained from the persName fields
                of the personality entities (except for the hard-coded value
                of 'Automatic Language Switching'.)

                These strings are not localized."
::= { prtInterpreterEntry 5 }


prtinterpreterversion OBJECT-TYPE
    SYNTAX  OCTET STRING (SIZE(0..31))
    MAX-ACCESS read-only
    STATUS  current
    DESCRIPTION
                "The date code, version number, or other product specific
        information tied to this interpreter.  This value is
        associated with the interpreter, rather than with the version
        of the language which is being interpreted or emulated.
	Refer to Standard Printer MIB for more details.
                Additional information:
                Same as prtInterpreterLangVersion."
::= { prtInterpreterEntry 6 }


prtinterpreterdefaultorientation OBJECT-TYPE
    SYNTAX  INTEGER {
		   ePportrait(3),
		   ePlandscape(4)
		   }
    MAX-ACCESS read-write
    STATUS  current
    DESCRIPTION
                "The current orientation default for this interpreter.  This
        value may be overridden for a particular job (e.g., by a
        command in the input data stream).
	Refer to Standard Printer MIB for more details.
                Additional information:
                The value of the system's DEFAULT-ORIENTATION is
                set or retrieved without regard to interpreters.  Setting this
                object for one interpreter will change it for all installed
                interpreters.

                The valid values are ePportrait and ePlandscape.  Attempting
                to set the orientation to a different value will cause
                <badValue> to be returned."
::= { prtInterpreterEntry 7 }


prtinterpreterfeedaddressability OBJECT-TYPE
    SYNTAX  INTEGER
    MAX-ACCESS read-only
    STATUS  current
    DESCRIPTION
                "The maximum interpreter addressability in the feed
        direction in 10000 prtMarkerAddressabilityUnits (see
        prtMarkerAddressabilityFeedDir ) for this interpreter.
        The value (-1) means other and specifically indicates
        that the sub-unit places no restrictions on this parameter.
	Refer to Standard Printer MIB for more details."
::= { prtInterpreterEntry 8 }


prtinterpreterxfeedaddressability OBJECT-TYPE
    SYNTAX  INTEGER
    MAX-ACCESS read-only
    STATUS  current
    DESCRIPTION
                "The maximum interpreter addressability in the cross feed
        direction in 10000 prtMarkerAddressabilityUnits (see
        prtMarkerAddressabilityXFeedDir) for this interpreter.
        The value (-1) means other and specifically indicates
        that the sub-unit places no restrictions on this
        parameter.
	Refer to Standard Printer MIB for more details."
::= { prtInterpreterEntry 9 }


prtinterpreterdefaultcharsetin OBJECT-TYPE
    SYNTAX  INTEGER {
		   ePcsASCII(3),
		   ePcsISOLatin1(4),
		   ePcsISOLatin2(5),
		   ePcsISOLatin5(12),
		   ePcsISOLatin6(13),
		   ePcsISO4UnitedKingdom(20),
		   ePcsISO11SwedishforNames(21),
		   ePcsISO15Italian(22),
		   ePcsISO17Spanish(23),
		   ePcsISO21German(24),
		   ePcsISO60DanishNorwegian(25),
		   ePcsISO69French(26),
		   ePcsUnicodeIBM2039(1004),
		   ePcsWindows30Latin1(2000),
		   ePcsWindows31Latin1(2001),
		   ePcsWindows31Latin2(2002),
		   ePcsWindows31Latin5(2003),
		   ePcsHPRoman8(2004),
		   ePcsAdobeStandardEncoding(2005),
		   ePcsPC850Multilingual(2009),
		   ePcsPCp852(2010),
		   ePcsPC8CodePage437(2011),
		   ePcsPC8DNDanishNorwegian(2012),
		   ePcsHPPC8Turkish(2014),
		   ePcsHPLegal(2017),
		   ePcsHPDeskTop(2021),
		   ePcsMacintosh(2027),
		   ePcsPC775Baltic(2087),
		   ePcsWindows1257Baltic(2257)
		   }
    MAX-ACCESS read-write
    STATUS  current
    DESCRIPTION
                "The default coded character set for input octets
        encountered outside a context in which the Page
        Description Language established the interpretation
        of the octets. (Input octets are presented to the
        interpreter through a path defined in the channel group.)
        This value shall be (2) if there is no default.
	Refer to Standard Printer MIB for more details.
                Additional information:
                The object corresponding to PCL has read-write access;
                For all other interpreters, the object is read-only.

                The above list corresponds to the following symbol sets as they
                appear on the Control Panel:

                ePcsASCII( 3) - ISO-6
                ePcsISOLatin1( 4) - ISO L1
                ePcsISOLatin2( 5) - IS L2
                ePcsISOLatin5( 12) - ISO L5
                ePcsISOLatin6( 13) - ISO L6
                ePcsISO4UnitedKingdom( 20) - ISO-4
                ePcsISO11SwedishforNames( 21) - ISO-11
                ePcsISO15Italian( 22) - ISO-15
                ePcsISO17Spanish( 23) - ISO-17
                ePcsISO21German( 24) - ISO-21
                ePcsISO60DanishNorwegian( 25) - ISO-60
                ePcsISO69French( 26) - ISO-69
                ePcsUnicodeIBM2039(1004) - PC-1004
                ePcsWindows30Latin1( 2000) - WIN 3.0
                ePcsWindows31Latin1( 2001) - WIN L1
                ePcsWindows31Latin2( 2002) - WIN L2
                ePcsWindows31Latin5( 2003) - WIN L5
                ePcsHPRoman8( 2004) - ROMAN-8
                ePcsAdobeStandardEncoding( 2005) - PS TEXT
                ePcsPC850Multilingual( 2009) - PC-850
                ePcsPCp852( 2010) - PC-852
                ePcsPC8CodePage437( 2011) - PC-8
                ePcsPC8DNDanishNorwegian( 2012) - PC-8DN
                ePcsHPPC8Turkish( 2014) - PC-8 TK
                ePcsHPLegal( 2017) - LEGAL
                ePcsHPDeskTop( 2021) - DESKTOP
                ePcsMacintosh(2027) - MC TEXT
                ePcsPC775Baltic( 2087) - PC-775
                ePcsWindows1257Baltic( 2257) - WINBALT"
::= { prtInterpreterEntry 10 }


prtinterpreterdefaultcharsetout OBJECT-TYPE
    SYNTAX  INTEGER {
		   ePcsNoDefault(2),
		   ePcsASCII(3),
		   ePcsHPRoman8(2004),
		   ePcsAdobeStandardEncoding(2005)
		   }
    MAX-ACCESS read-only
    STATUS  current
    DESCRIPTION
                "The default character set for data coming from this interpreter
        through the printer's output channel (i.e. the 'backchannel').
        This value shall be (2) if there is no default.
	Refer to Standard Printer MIB for more details."
::= { prtInterpreterEntry 11 }


prtinterpretertwoway OBJECT-TYPE
    SYNTAX  INTEGER {
		   ePyes(3),
		   ePno(4)
		   }
    MAX-ACCESS read-only
    STATUS  current
    DESCRIPTION
                "Indicates whether or not this interpreter returns information
        back to the host.
	Refer to Standard Printer MIB for more details."
::= { prtInterpreterEntry 12 }


energy-star OBJECT-TYPE
    SYNTAX  INTEGER
    MAX-ACCESS read-write
    STATUS  current
    DESCRIPTION
                "Returns or changes the Energy Star sleep value.  If the
                value is greater than zero, then the device will go into
                energy saving sleep mode after the print engine has been
                idle for the number of seconds specified by this object.
                A value of zero means Energy Star is disabled and the
                device will not go to sleep based on print engine idle
                time.  The value must be non-negative.
                Additional information:
                Returns or changes the Energy Star sleep value.
                The device will go into energy saving sleep
                mode after the print engine has been idle for
                the number of seconds specified by this
                object.

                LaserJet 4050 Series supports values of 0, 900, 1800,
                3600, 7200, and 10800.  A value of 0 means
                never go to sleep based on print engine idle
                time.  Setting to an unsupported value causes
                the printer to substitute a value (listed
                below) and to return <noError>
                status.
                The values are as follow:
                <=0 snap to 0
                >=1 and <=1349 snap to 900 (15 minutes)
                >=1350 and <=2699 snap to 1800 (30 minutes)
                >=2700 and <=5399 snap to 3600 (1 hour)
                >=5400 and <=8999 snap to 7200 (2 hours)
                >=9000 snap to 10800  (3 hours)"
::= { settings-system 1 }

sleep-mode OBJECT-TYPE
    SYNTAX  INTEGER {
		   eFalse(1),
		   eTrue(2)
		   }
    MAX-ACCESS read-write
    STATUS  current
    DESCRIPTION
                "Returns eTrue if the device is in energy saving sleep
                mode, otherwise returns eFalse.  Setting SLEEP-MODE to
                eFalse causes the device to wake up, if it is in sleep
                mode.  Setting SLEEP-MODE to eTrue causes the device to
                go into sleep mode.
                Additional information:
                This object returns eTrue if the device is in
                energy saving sleep mode, otherwise it returns eFalse.
                Setting this object to eTrue while the printer
                is awake will not change the printer's current state
                and will return <genErr>
                status.  NOTE: This object should behave this way
                when the printer does not have an instant-on fuser.
                Setting this object to eTrue while printer is already
                in Sleep Mode will not change the printer's
                current state and will return <noError> status.
                Setting this object to eFalse while printer is already
                awake  will not change the printer's current state and
                will return <noError> status.
                Setting this object to eFalse while the printer is
                asleep causes the device to wake up.   "
::= { settings-system 2 }

control-panel-lock OBJECT-TYPE
    SYNTAX  INTEGER {
		   eDisabled(1),
		   eEnabled(2)
		   }
    MAX-ACCESS read-write
    STATUS  current
    DESCRIPTION
                "Device control panel lock.  A value of eDisabled means
                the control panel is unlocked and the device's
                configuration can be modified from the control panel.  A
                value of eEnabled means the control panel is locked,
                thus the device's configuration cannot be modified from
                the control panel."
::= { settings-system 8 }

service-password OBJECT-TYPE
    SYNTAX  INTEGER
    MAX-ACCESS read-write
    STATUS  current
    DESCRIPTION
                "When set to the password value, other service related
                objects become 'visible' (i.e readable) and/or become
                writable.  When written with any other value, the
                service related objects become 'hidden' (i.e. are no
                longer readable) and/or are not longer writable.  The
                objects that can be effected by the SERVICE-PASSWORD
                object include: SERIAL-NUMBER and TOTAL-ENGINE-PAGE-
                COUNT.  The password value, and the list of objects
                effected by the SERVICE-PASSWORD being set to the
                correct value, should be documented in the device POS.
                Additional information:
                The objects that can be effected by the SERVICE-
                PASSWORD are:  SCANNER-JAM-PAGE-COUNT, SCANNER-ADF-PAGE
                -COUNT, SCAN-ADF-PAGE-COUNT, SCANNER-RETRIEVE-SCANLINE,
                SCANNER-MOTOR-CONTROL, COPIER-ADF-PAGE-COUNT, COPIER-
                PRINT-PAGE-COUNT, TOTAL-ENGINE-PAGE-COUNT, PRINT-ENGINE-
                JAM-COUNT, PRINT-ENGINE-MISPICK-COUNT"
::= { settings-system 9 }


device-cfg-download OBJECT-TYPE
    SYNTAX  INTEGER {
		   eCfgDownloadIdle(1),
		   eCfgDownloadStart(2),
		   eCfgDownloadActive(3),
		   eCfgDownloadAborted(4),
		   eCfgDownloadDone(5)
		   }
    MAX-ACCESS read-write
    STATUS  current
    DESCRIPTION
                "Handshaking mechanism between host and device to coordinate the download of device specific data.
  eCfgDownloadIdle - indicates device configuration download activity is not occurring.  Device powers up in this state but will otherwise never transition to this state.  This state is host settable from eCfgDownloadActive, eCfgDownloadDone, and eCfgDownloadAborted.  Host setting to eCfgDownloadIdle while object is in eCfgDownloadActive will cause the download activity to be prematurely terminated.  Host setting to this state resets the object to permit another download activity to be initiated.
  eCfgDownloadStart - indicates host wishes to commence a device configuration download activity.  This state is only host settable from eCfgDownloadIdle.  Only the device can transition this object from this state to eCfgDownloadActive or eCfgDownloadAborted.  Device will not set to this state.
  eCfgDownloadActive - indicates download activity is in progress.  Device transitions object to this state only from eCfgDownloadStart, to signal data download can commence.  The device can transition from this state to eCfgDownloadDone or eCfgDownloadAborted.  The host can transition from this state to eCfgDownloadIdle.  This state is not host settable.
  eCfgDownloadAborted - indicates the download activity was terminated by the device.  Only the device can set to this state from eCfgDownloadStart or eCfgDownloadActive.  Only the host can transition from this state to eCfgDownloadIdle.  This state is not host settable.
   eCfgDownloadDone - indicates device has completely received the download data.  Device transitions to this state only from eCfgDownloadActive.  Only the host can transition from this state to eCfgDownloadIdle.  This state is not host settable."
::= { settings-system 11 }


device-cfg-download-data-type OBJECT-TYPE
    SYNTAX  INTEGER {
		   eSpeedDials(5),
		   eFaxLogs(6),
		   eConfigPrams(7),
		   eJunkFaxDialStrings(9)
		   }
    MAX-ACCESS read-write
    STATUS  current
    DESCRIPTION
                "Indicates the type of device specific data to be
                downloaded."
::= { settings-system 12 }


device-cfg-upload OBJECT-TYPE
    SYNTAX  INTEGER {
		   eCfgUploadIdle(1),
		   eCfgUploadStart(2),
		   eCfgUploadActive(3),
		   eCfgUploadAborted(4),
		   eCfgUploadDone(5)
		   }
    MAX-ACCESS read-write
    STATUS  current
    DESCRIPTION
                "Handshaking mechanism between host and device to
                coordinate the upload of device specific data.
                  eCfgUploadIdle - indicates device configuration upload
                activity is not occurring.  Device powers up in this
                state but will otherwise never transition to this state.
                This state is host settable from eCfgUploadActive,
                eCfgUploadDone, and eCfgUploadAborted.  Host setting to
                eCfgUploadIdle while object is in eCfgUploadActive will
                cause the upload activity to be prematurely terminated.
                Host setting to this state resets the object allowing a
                new upload to be initiated.
                  eCfgUploadStart - indicates host wishes to commence a
                device configuration upload activity.  This state is
                only host settable from eCfgUploadIdle.  Only the device
                can transition this object from this state to
                eCfgUploadActive or eCfgUploadAborted.  Device will not
                set to this state.
                  eCfgUploadActive - indicates upload activity is in
                progress.  Device transitions object to this state only
                from eCfgUploadStart, to signal data upload can
                commence.  The device can transition from this state to
                eCfgUploadDone or eCfgUploadAborted.  The host can
                transition from this state to eCfgUploadIdle.  This
                state is not host settable.
                  eCfgUploadAborted - indicates the upload activity was
                terminated by the device.  Only the device can set to
                this state from eCfgUploadStart or eCfgUploadActive.
                Only the host can transition from this state to
                eCfgUploadIdle.  This state is not host settable.
                  eCfgUploadDone - indicates device completely
                transmitted the upload data.  Device transitions to this
                state only from eCfgUploadActive.  Only the host can
                transition from this state to eCfgUploadIdle.  This
                state is not host settable."
::= { settings-system 13 }


device-cfg-upload-data-type OBJECT-TYPE
    SYNTAX  INTEGER {
		   eSpeedDials(5),
		   eFaxLogs(6),
		   eConfigPrams(7),
		   eJunkFaxDialStrings(9)
		   }
    MAX-ACCESS read-write
    STATUS  current
    DESCRIPTION
                "Indicates the type of device specific data to be
                uploaded."
::= { settings-system 14 }


download-timeout OBJECT-TYPE
    SYNTAX  INTEGER
    MAX-ACCESS read-write
    STATUS  current
    DESCRIPTION
                "Specifies the number of seconds that device will wait
                for data from the host before the device determines the
                host is being unresponsive.  This timeout condition may
                cause the device to take recourse action regarding the
                disposition of the download activity.  A value of zero
                indicates device will wait forever for the host data.
                POS should indicate whether this object value, when set
                by the host, is remembered between device power cycles.
                Additional information:
                This object is volatile and as such will not be
                retained by the device between power cycles."
::= { settings-system 17 }


upload-timeout OBJECT-TYPE
    SYNTAX  INTEGER
    MAX-ACCESS read-write
    STATUS  current
    DESCRIPTION
                "Specifies the number of seconds that device will wait
                for response from the host after transmitting a unit of
                data before the device determines the host is being
                unresponsive.  This timeout condition may cause the
                device to take recourse action regarding the disposition
                of the upload activity.  A value of zero indicates
                device will wait forever for the host response.  POS
                should indicate whether this object value, when set by
                the host, is remembered between device power cycles
                Additional information:
                This object is volatile and as such will not be
                retained by the device between power cycles."
::= { settings-system 18 }


run-location OBJECT-TYPE
    SYNTAX  INTEGER(0..9)
    MAX-ACCESS read-write
    STATUS  current
    DESCRIPTION
                "Returns or changes the location from which code
                executes. The object allows the user to pick a memory
                bank to run code from which is different than the
                default running code bank. A value of 0 means the code
                executes from the default code bank, which should be
                documented in the device POS. The list of supported
                values should be documented in the device POS. Setting
                to an unsupported value causes the device to return
                <badValue>.
                Additional information:
                Returns or changes the location from which code
                		should be run.  The object allows the user to pick a ram bank
                		to run code from which is potentially faster than the onboard
                		ROM.  LaserJet 8100 Series and LaserJet 8000 Series support values of 0,4-9.  A value of 0
                		means run code from default ROM device.  Values other than 0
                		indicate a valid RAM bank of size >= 8MBs.  Setting to an
                		unsupported value causes the printer to leave the run location
                		set to its previous value."
::= { settings-system 21 }

date-display OBJECT-TYPE
    SYNTAX  INTEGER {
		   eDateDisplayMMDDYY(1),
		   eDateDisplayDDMMYY(2),
		   eDateDisplayYYMMDD(3)
		   }
    MAX-ACCESS read-write
    STATUS  current
    DESCRIPTION
                "Controls front-panel date display format."
::= { settings-system 22 }


device-cfg-param-command OBJECT-TYPE
    SYNTAX  OCTET STRING
    MAX-ACCESS read-write
    STATUS  current
    DESCRIPTION
                "A C structure containing the following fields:
                   typedef struct {
                   u8bit list_id;
                   s8bit auto_incr;
                   u16bit max_index;
                   u16bit rec_size;
                   u16bit index;
                   u8bit data[];
                } PML_device_cfg_param_cmd_t;
                where u8bit is an unsigned byte (0..255), s8bit is a
                signed byte (-128..127), and u16bit is an big endian
                format unsigned short (0..65535).  The POS should state
                which list_id's the device supports.
                Additional information:
                HP Laserjet 3200 supports two values for list_id:
                0 for configuration parameters and
                1 for default configuration parameters."
::= { settings-system 23 }


copier-token OBJECT-TYPE
    SYNTAX  OCTET STRING (SIZE(1..128))
    MAX-ACCESS read-write
    STATUS  current
    DESCRIPTION
                "Provides an advisory locking mechanism for hosts to coordinate
                 exclusive access to a copier device. Setting the object to a
                 unique id will only succeed if the token is currently set to 0.
                 The token is unlocked when it is set to 0. If the token is set
                 to a any value other than 0, then token is locked. If the token
                 was set to a unique id (locked), then an attempt to set (lock)
                 the token will fail. If the token was set to 0 (unlocked), then
                 an attempt to set (lock) the token will succeed in locking the
                 token. A get operation on COPIER-TOKEN will return its current
                 setting. The device does not prevent access to any objects. It
                 is assumed that hosts will be well behaved; respecting this
                 advisory locking mechanism by:
                 1) acquiring the lock before changing copier objects, and
                 2) releasing the lock when done changing copier objects.
                Additional information:
                Provides an advisory locking mechanism for hosts to
                coordinate exclusive access.  Setting the object to a unique id
                will only succeed if the token is currently set to 0.  The token
                is unlocked when it is set to 0. If the token is set to a any
                value other than 0, then token is locked.

                If the token was set to a unique id (locked), then an
                attempt to set (lock) the token will fail.

                If the token was set to 0 (unlocked), then an attempt to set (lock)
                the token will succeed in locking the token.

                A get operation on COPY-TOKEN will return its current setting.
                The device does not prevent access to any objects.  It is assumed
                that hosts will be well behaved; respecting this advisory locking
                mechanism by:
                1) acquiring the lock before changing copy objects, and
                2) releasing the lock when done changing copy objects."
::= { settings-system 24 }


fax-upload-token OBJECT-TYPE
    SYNTAX  OCTET STRING (SIZE(1..128))
    MAX-ACCESS read-write
    STATUS  current
    DESCRIPTION
                "Provides an advisory locking mechanism for hosts to coordinate
                 exclusive access to the fax upload features of a device. Setting
                 the object to a unique id will only succeed if the token is
                 currently set to 0. The token is unlocked when it is set to 0.
                 If the token is set to a any value other than 0, then token is
                 locked. If the token was set to a unique id (locked), then an
                 attempt to set (lock) the token will fail. If the token was set
                 to 0 (unlocked), then an attempt to set (lock) the token will
                 succeed in locking the token. A get operation on FAX-UPLOAD-TOKEN
                 will return its current setting. The device does not prevent
                 MAX-ACCESS to any objects. It is assumed that hosts will be well behaved;
                 respecting this advisory locking mechanism by:
                 1) acquiring the lock before changing any fax-upload objects, and
                 2) releasing the lock when done changing scan objects.
                Additional information:
                Provides an advisory locking mechanism for hosts to
                coordinate exclusive access.  Setting the object to a unique id
                will only succeed if the token is currently set to 0.  The token
                is unlocked when it is set to 0. If the token is set to a any
                value other than 0, then token is locked.

                If the token was set to a unique id (locked), then an
                attempt to set (lock) the token will fail.

                If the token was set to 0 (unlocked), then an attempt to set (lock)
                the token will succeed in locking the token.

                A get operation on FAX-UPLOAD-TOKEN will return its current setting.
                The device does not prevent access to any objects.  It is assumed
                that hosts will be well behaved; respecting this advisory locking
                mechanism by:
                1) acquiring the lock before changing fax objects, and
                2) releasing the lock when done changing fax objects."
::= { settings-system 26 }


fax-download-token OBJECT-TYPE
    SYNTAX  OCTET STRING (SIZE(1..128))
    MAX-ACCESS read-write
    STATUS  current
    DESCRIPTION
                "Provides an advisory locking mechanism for hosts to coordinate
                 exclusive access to the fax download features of a device. Setting
                 the object to a unique id will only succeed if the token is
                 currently set to 0. The token is unlocked when it is set to 0.
                 If the token is set to a any value other than 0, then token is
                 locked. If the token was set to a unique id (locked), then an
                 attempt to set (lock) the token will fail. If the token was set
                 to 0 (unlocked), then an attempt to set (lock) the token will
                 succeed in locking the token. A get operation on FAX-DOWNLOAD-TOKEN
                 will return its current setting. The device does not prevent
                 MAX-ACCESS to any objects. It is assumed that hosts will be well behaved;
                 respecting this advisory locking mechanism by:
                 1) acquiring the lock before changing any fax-download objects, and
                 2) releasing the lock when done changing scan objects.
                Additional information:
                Provides an advisory locking mechanism for hosts to
                coordinate exclusive access.  Setting the object to a unique id
                will only succeed if the token is currently set to 0.  The token
                is unlocked when it is set to 0. If the token is set to a any
                value other than 0, then token is locked.

                If the token was set to a unique id (locked), then an
                attempt to set (lock) the token will fail.

                If the token was set to 0 (unlocked), then an attempt to set (lock)
                the token will succeed in locking the token.

                A get operation on FAX-DOWNLOAD-TOKEN will return its current setting.
                The device does not prevent access to any objects.  It is assumed
                that hosts will be well behaved; respecting this advisory locking
                mechanism by:
                1) acquiring the lock before changing fax objects, and
                2) releasing the lock when done changing fax objects."
::= { settings-system 27 }

device-config-token OBJECT-TYPE
    SYNTAX  OCTET STRING (SIZE(128))
    MAX-ACCESS read-write
    STATUS  current
    DESCRIPTION
                "Provides an advisory locking mechanism for hosts to coordinate
                 exclusive access to a specific device or subset of device
                 capabilities. Setting the object to a unique id will only succeed
                 if the token is currently set to 0. The token is unlocked when it
                 is set to 0. If the token is set to a any value other than 0, then
                 token is locked. If the token was set to a unique id (locked),
                 then an attempt to set (lock) the token will fail. If the token
                 was set to 0 (unlocked), then an attempt to set (lock) the token
                 will succeed in locking the token. A get operation on
                 DEVICE-CONFIG-TOKEN will return its current setting. The device
                 does not prevent access to any objects. It is assumed that hosts
                 will be well behaved; respecting this advisory locking mechanism by:
                 1) acquiring the lock before changing device config objects, and
                 2) releasing the lock when done changing device config objects.
                Additional information:
                Provides an advisory locking mechanism for hosts to
                coordinate exclusive access.  Setting the object to a unique id
                will only succeed if the token is currently set to 0.  The token
                is unlocked when it is set to 0. If the token is set to a any
                value other than 0, then token is locked.

                If the token was set to a unique id (locked), then an
                attempt to set (lock) the token will fail.

                If the token was set to 0 (unlocked), then an attempt to set (lock)
                the token will succeed in locking the token.

                A get operation on CONFIG-TOKEN will return its current setting.
                The device does not prevent access to any objects.  It is assumed
                that hosts will be well behaved; respecting this advisory locking
                mechanism by:
                1) acquiring the lock before changing CONFIG objects, and
                2) releasing the lock when done changing CONFIG objects."
::= { settings-system 28 }


mono-color-switching-mode OBJECT-TYPE
    SYNTAX      INTEGER {
                          eNeverSwitch(1),
                          eAlwaysSwitch(2),
                          eLookAheadSwitch(3)
		   }
    MAX-ACCESS read-write
    STATUS      current
       DESCRIPTION "This object allows the user to view/change the color/mono
                switching mode for a device.
                Additional information:
                This object allows the user to view/change the color/mono
                switching mode for a device."
::= { settings-system 31 }


control-panel-button-press-delay OBJECT-TYPE
    SYNTAX      INTEGER
    MAX-ACCESS read-write
    STATUS      current
       DESCRIPTION "This object gives the number of seconds to wait before
		simulating the button press when CONTROL-PANEL-BUTTON-PRESS is
		next called.
                Additional information:
                This object gives the number of seconds to wait before
                simulating the button press when CONTROL-PANEL-BUTTON-PRESS is
                next called."
::= { settings-system 47 }


low-power OBJECT-TYPE
    SYNTAX      INTEGER
    MAX-ACCESS read-write
    STATUS      current
       DESCRIPTION "Returns or changes the Auto Low Power sleep value. The device
		will go into energy saving Auto Low Power mode after the print
		engine has been idle for the number of seconds specified by
		this object. Frida supports values of 300 until 14400 seconds.
		If the value is invalid then it will return status of
		PML_Status_ErrUnsupValue and will not issue command to the
		engine.
                Additional information:
                Returns or changes the Auto Low Power sleep value. The device
                will go into energy saving Auto Low Power mode after the print
                engine has been idle for the number of seconds specified by
                this object. The product supports values of 0 (Off), 60 (1
                minute), 900 (15 minutes), 1800 (30 minutes), 3600 (1 hour),
                and 7200 (2 hours).
                If the value is invalid then it will return a status of
                PML_ERROR_INVALID_OR_UNSUPPORTED_VALUE and will not issue
                a command to the engine."
::= { settings-system 49 }


fuser-pressure-release OBJECT-TYPE
    SYNTAX      INTEGER {
                          eDisengage(1)
		   }
    MAX-ACCESS read-write
    STATUS      current
       DESCRIPTION "This object is used to disengage the pressure on the fuser to
		prevent roller marks on the fuser, which can occur when the
		pressure is engaged for long periods of time.
                Additional information:
                This object is used to disengage the pressure on the
                	fuser to prevent roller marks on the fuser, which can occur when
                	the pressure is engaged for long periods of time."
::= { settings-system 53 }


control-panel-display-contrast OBJECT-TYPE
    SYNTAX      INTEGER {
                          eLightest(1),
                          eLight(2),
                          eMedium(3),
                          eDark(4),
                          eDarkest(5)
		   }
    MAX-ACCESS read-write
    STATUS      current
       DESCRIPTION "This object returns or sets the display contrast setting if the
		control panel has a display and it supports contrast
		adjustment. The setting Is stored in NVRAM, so the value is
		saved over power cycles.
                Additional information:
                This object returns or sets the display contrast setting
                			if the control panel has a display and it supports
                			contrast adjustment. The setting is stored in NVRAM,
                			so the value is saved over power cycles."
::= { settings-system 73 }

calibration-lowspeed-enable OBJECT-TYPE
    SYNTAX      INTEGER {
                          eDisable(1),
                          eEnable(2)
		   }
    MAX-ACCESS read-write
    STATUS      current
       DESCRIPTION "Enable or disable an optional low speed calibration. This
		calibration will allow the device to obtain accurate data for
		use with low speed print modes.
                Additional information:
                Enable or disable an optional low speed calibration. This
                		calibration will allow the device to obtain accurate data for
                		use with low speed print modes."
::= { settings-system 85 }


start-engine-early-warmup OBJECT-TYPE
    SYNTAX      INTEGER {
                          eValue1(1)
		   }
    MAX-ACCESS read-write
    STATUS      current
       DESCRIPTION "This PML object is used by HP SW drivers to signal the printer
		that a job is coming, and to start the warm-up process
		early.The effect of warming up early will reduce the First Page
		Out time.
                Additional information:
                This PML object is used by HP SW drivers to signal the printer
                that a job is coming, and to start the warm-up process
                early.The effect of warming up early will reduce the First Page
                Out time."
::= { settings-system 99 }


enable-engine-early-warmup OBJECT-TYPE
    SYNTAX      INTEGER {
                          eDisable(1),
                          eEnable(2)
		   }
    MAX-ACCESS read-write
    STATUS      current
       DESCRIPTION "This PML object is used by HP SW to enable/disable the printer
		to send the signal of warm-up process early to engine. The
		effect of warming up early will reduce the First Page Out
		time.
                Additional information:
                This PML object is used by HP SW to enable/disable the printer
                to send the signal of warm-up process early to engine. The
                effect of warming up early will reduce the First Page Out
                time."
::= { settings-system 101 }

-- 1.3.6.1.4.1.11.2.3.9.4.2.1.1.25.1
toner-miser-plus-value   OBJECT-TYPE
    SYNTAX          OCTET STRING
    MAX-ACCESS read-write
    STATUS            current
    DESCRIPTION " This object is used to enable/disable toner miser plus
    feature"
::= { settings-system2 1 }

-- 1.3.6.1.4.1.11.2.3.9.4.2.1.1.25.2
toner-miser-plus-supported   OBJECT-TYPE
    SYNTAX          INTEGER {
                              eOff(1),
                             eOn(2)
                    }
    MAX-ACCESS read-only
    STATUS            current
    DESCRIPTION " The supported values are ON and OFF. The toner miser plus
    feature is turned OFF by default"
::= { settings-system2 2 }

-- 1.3.6.1.4.1.11.2.3.9.4.2.1.1.25.17
protect-ews-info-tab   OBJECT-TYPE
    SYNTAX          INTEGER {
                              eOff(1),
                             eOn(2)
                    }
    MAX-ACCESS read-write
    STATUS            current
    DESCRIPTION " This PML object is used by the WJA tool to allow administrators
    to enable or disable EWS information tab protection. When this
    option in selected/turned on the user will not be able to
    MAX-ACCESS anything on the EWS without logging in with the EWS
    device <<hidden>>(in case the EWS device <<hidden>> is configured).
    If the option is turned off the user will be able to access the
    information tab on the EWS page without providing the EWS
    device <<hidden>>(in case the EWS device <<hidden>> is configured),
    for all other tabs on the EWS page the user will have to login with EWS device <<hidden>>"
::= { settings-system2 17 }

-- 1.3.6.1.4.1.11.2.3.9.4.2.1.1.25.19
eprint-opt-in   OBJECT-TYPE
    SYNTAX          INTEGER {
                              eOff(1),
                             eOn(2)
                    }
    MAX-ACCESS read-write
    STATUS            current
    DESCRIPTION " This object is the master switch for the ePrint feature. By
    default this should be eOff(1). This differs from
    EPRINT-ENABLED in that ePrint connot be registered with the
    cloud when this is diabled while EPRINT-ENABLED allows
    registration and temporary disablement"
::= { settings-system2 19 }

-- 1.3.6.1.4.1.11.2.3.9.4.2.1.1.25.20
eprint-enabled   OBJECT-TYPE
    SYNTAX          INTEGER {
                              eOff(1),
                             eOn(2)
                    }
    MAX-ACCESS read-write
    STATUS            current
    DESCRIPTION " Returns the current setting of the ePrint feature"
::= { settings-system2 20 }

-- 1.3.6.1.4.1.11.2.3.9.4.2.1.1.25.21
eprint-email-address   OBJECT-TYPE
    SYNTAX          OCTET STRING
    MAX-ACCESS read-write
    STATUS            current
    DESCRIPTION " This is the configured ePrint email address"
::= { settings-system2 21 }

-- 1.3.6.1.4.1.11.2.3.9.4.2.1.1.25.22
eprint-email   OBJECT-TYPE
    SYNTAX          INTEGER {
                              eOff(1),
                             eOn(2)
                    }
    MAX-ACCESS read-write
    STATUS            current
    DESCRIPTION " This object reports the current setting of ePrint e-mail"
::= { settings-system2 22 }

-- 1.3.6.1.4.1.11.2.3.9.4.2.1.1.25.23
eprint-printer-code   OBJECT-TYPE
    SYNTAX          OCTET STRING
    MAX-ACCESS read-write
    STATUS            current
    DESCRIPTION " This is the configured ePrint printer code"
::= { settings-system2 23 }

-- 1.3.6.1.4.1.11.2.3.9.4.2.1.1.25.24
eprint-hp-web-services   OBJECT-TYPE
    SYNTAX          INTEGER {
                              eOff(1),
                             eOn(2)
                    }
    MAX-ACCESS read-write
    STATUS            current
    DESCRIPTION " This object reports the current setting of the ePrint web
    services"
::= { settings-system2 24 }

-- 1.3.6.1.4.1.11.2.3.9.4.2.1.1.25.25
eprint-jdi-interface   OBJECT-TYPE
    SYNTAX          INTEGER {
                              eJDIInterface1(1),
                             eJDIInterface2(2),
                             eJDIInterface3(3),
                             eJDIInterface4(4),
                             eJDIInterface5(5),
                             eJDIInterface6(6),
                             eJDIInterface7(7),
                             eJDIInterface8(8),
                             eJDIInterface9(9),
                             eJDIInterface10(10)
                    }
    MAX-ACCESS read-write
    STATUS            current
    DESCRIPTION " This number represents the instance of jdi that has ePrint
    registered"
::= { settings-system2 25 }

-- 1.3.6.1.4.1.11.2.3.9.4.2.1.1.25.31
eprint-supported   OBJECT-TYPE
    SYNTAX          INTEGER {
                              eOff(1),
                             eOn(2)
                    }
    MAX-ACCESS read-write
    STATUS            current
    DESCRIPTION " This object is used to indicate whether the device supports
    ePrint or not. By default this should be eOff(1), but will be
    set to eOn(2) if the device supports ePrint"
::= { settings-system2 31 }

-- 1.3.6.1.4.1.11.2.3.9.4.2.1.1.25.32
eprint-supported-jdi   OBJECT-TYPE
    SYNTAX          INTEGER {
                              eOff(1),
                             eOn(2)
                    }
    MAX-ACCESS read-write
    STATUS            current
    DESCRIPTION " This object is used to indicate whether the JDI supports ePrint
    or not. By default this should be eOff(1), but will be set to
    eOn(2) if JDI supports ePrint"
::= { settings-system2 32 }

-- 1.3.6.1.4.1.11.2.3.9.4.2.1.1.25.47
fax-init-at-command   OBJECT-TYPE
    SYNTAX          OCTET STRING
    MAX-ACCESS read-write
    STATUS            current
    DESCRIPTION "This custom fax modem commands will be executed on the modem
    every time a fax modem is initialized along with the predefined
    set of commands
         "
::= { settings-system2 47 }

-- 1.3.6.1.4.1.11.2.3.9.4.2.1.1.25.59
set-primary-interface-index   OBJECT-TYPE
    SYNTAX          INTEGER
    MAX-ACCESS read-write
    STATUS            current
    DESCRIPTION "Sets the index of the primary network interface to be used for outbound routing. Index 1 is EIO, 2 is wireless station, 3 is wireless access point and 4 is JDI."
::= { settings-system2 59 }

-- 1.3.6.1.4.1.11.2.3.9.4.2.1.1.25.60
wireless-direct-print-setting   OBJECT-TYPE
    SYNTAX          INTEGER {
                            eDisabled(1),
                            eEnabled(2)
                            }
    MAX-ACCESS read-write
    STATUS            current
    DESCRIPTION "Enable or disable wireless direct printing."
::= { settings-system2 60 }

copy-scanner-dimensions OBJECT-TYPE
    SYNTAX      DisplayString
    MAX-ACCESS read-only
    STATUS      current
       DESCRIPTION "This object is used to obtain the exact pixel scan dimensions
		for copy. The dimensions returned correspond to the quality,
		reduce/enlarge, and media size currently selected.
                Additional information:
                This object is used to obtain the exact pixel scan dimensions for copy.
                			     The dimensions returned correspond to the quality, reduce/enlarge,
                			     and media size currently selected."
::= { status-scanner 13 }


device-configure-generic-language-prompt OBJECT-TYPE
    SYNTAX      INTEGER {
                          eDisabled(1),
                          eEnabled(2)
		   }
    MAX-ACCESS read-write
    STATUS      current
       DESCRIPTION "This object is used to determine whether to prompt the user to
		enter the appropriate language.
                Additional information:
                This object is used to determine whether to
                		     prompt the user to enter the appropriate language
                	   	     at boot."
::= { device-configure 10 }


device-configure-generic-country-prompt OBJECT-TYPE
    SYNTAX      INTEGER {
                          eDisabled(1),
                          eEnabled(2)
		   }
    MAX-ACCESS read-write
    STATUS      current
       DESCRIPTION " This object is used to determine whether to prompt the user to
		enter the appropriate country at boot.
                Additional information:
                This object is used to determine whether to
                	 	     prompt the user to enter the appropriate country
                	    	     at boot."
::= { device-configure 11 }


device-configure-generic-country OBJECT-TYPE
    SYNTAX      INTEGER {
                          eKorea(4),
                          eIndonesia(5),
                          eChina(6),
                          eTaiwan(7),
                          ePhilippines(8),
                          eThailand(9),
                          eSriLanka(10),
                          eBrazil(12),
                          eCanada(13),
                          eMexico(14),
                          eUnitedStates(15),
                          eArgentina(16),
                          eChile(17),
                          eNewZealand(19),
                          eIsrael(21),
                          eAustralia(23),
                          eIndia(25),
                          ePakistan(26),
                          eMalaysia(27),
                          eHongKong(29),
                          eSingapore(30),
                          eUnitedKingdom(31),
                          eAustria(34),
                          eNetherlands(35),
                          eGermany(39),
                          eDenmark(40),
                          eSweden(41),
                          eSouthAfrica(42),
                          eNorway(43),
                          eIreland(44),
                          eBelgium(45),
                          eFinland(46),
                          eFrance(47),
                          eTurkey(48),
                          eGreece(49),
                          ePortugal(50),
                          eItaly(51),
                          eSpain(55),
                          ePoland(56),
                          eBulgaria(57),
                          eCroatia(58),
                          eRomania(59),
                          eSlovakRepublic(60),
                          eCzechRepublic(61),
                          eHungary(62),
                          eRussia(64),
                          ePeru(70),
                          eJordan(78),
                          eLebanon(79),
                          eSwitzerland(82),
                          eVietnam(83),
                          eLuxemberg(85),
                          eNorthAfrica(86),
                          eBelarus(66),
                          eBrunei(33),
                          eCambodia(94),
                          eCyprus(95),
                          eEgypt(67),
                          eEstonia(54),
                          eIceland(96),
                          eLatvia(53),
                          eLiechtentstein(98),
                          eLithuania(52),
                          eMalta(99),
                          eMorocco(65),
                          eSaudiArabia(28),
                          eTunisia(32),
                          eUAE(88),
                          eUkraine(63)
		   }
    MAX-ACCESS read-write
    STATUS      current
       DESCRIPTION "Set the location configuration for the device. This affects
		parameters that vary per region like the default paper size,
		symbol set, supply reorder URL, and fax parameters if
		applicable."
::= { device-configure 16 }


device-configure-secure-nvram-items OBJECT-TYPE
    SYNTAX      OCTET STRING
    MAX-ACCESS read-write
    STATUS      current
       DESCRIPTION "This object is used to configure product settings that are
		stored in secure area of nvram. The object consists of a 16-bit
		variable in secure nvram. Bits 15-8 are product specific. Bits
		7-0 are system specific.
                Additional information:
                This object is used to configure product settings that are
                stored in secure area of nvram. The object consists of a 16-bit
                variable in secure nvram. Bits 15-8 are product specific. Bits
                7-0 are system specific."
::= { device-configure 17 }


device-configure-cpe-feature OBJECT-TYPE
    SYNTAX      OCTET STRING
    MAX-ACCESS read-write
    STATUS      current
       DESCRIPTION "This object allows CPE to enable specific bug fixes or
		enhancements in post-release products.
                Additional information:
                This object allows CPE to enable specific bug fixes or
                enhancements in post-release products."
::= { device-configure 18 }


device-configure-custom-product-number OBJECT-TYPE
    SYNTAX      OCTET STRING
    MAX-ACCESS read-only
    STATUS      current
       DESCRIPTION "This object allows manufacturing to change the product number
		to a pre-defined alternate after release. This feature will
		allow manufacturing to assign unique product numbers to custom
		product bundles when the device is unable to determine its
		product number in firmware. For example, A HP Color LaserJet
		CP1515n could be configured to display CP1516n to the customer.
		This product number must be defined prior to release.
                Additional information:
                This object allows manufacturing to change the product number
                to a pre-defined alternate after release. This feature will
                allow manufacturing to assign unique product numbers to custom
                product bundles when the device is unable to determine its
                product number in firmware. For example, A HP Color LaserJet
                CP1515n could be configured to display CP1516n to the customer.
                This product number must be defined prior to release."
::= { device-configure 19 }


device-configure-preferred-boot-localization-language OBJECT-TYPE
    SYNTAX      INTEGER {
                          eEnglish(1),
                          eFrench(2),
                          eGerman(3),
                          eSpanish(4),
                          eItalian(5),
                          eSwedish(6),
                          eDanish(7),
                          eNorwegian(8),
                          eDutch(9),
                          eFinnish(10),
                          ePortuguese(12),
                          ePolish(13),
                          eTurkish(14),
                          eTradChinese(16),
                          eSimpChinese(17),
                          eRussian(18),
                          eCzech(19),
                          eHungarian(20),
                          eKorean(21),
                          eThai(22),
                          eUnknownLanguage(44)
		   }
    MAX-ACCESS read-write
    STATUS      current
       DESCRIPTION "Preferred localization language used by the device at boot up
		time. Setting this object will instruct the device to boot up
		in that language. Setting this language does not impact device
		generated PML strings, control panel messages, and text
		contained in any of the printer generated printed pages. The
		order of these languages is the same order that is defined for
		LOCALIZATION-LANGUAGE.
                Additional information:
                Preferred localization language used by the device at
                boot up time.  Setting this object will instruct the device to boot
                up in that language.  This will allow the device to NOT show the
                generic prompt on the CP display, since the device already knows
                the language."
::= { device-configure 20 }


date-and-time OBJECT-TYPE
    SYNTAX      DisplayString
    MAX-ACCESS read-write
    STATUS      current
       DESCRIPTION "A C structure containing the following fields:    typedef
		struct {
		    ubyte yr; /* year: 0 to 99 */
		    ubyte mon; /* month: 1 to 12 */
		    ubyte day; /* day: 1 to 31 */
		    ubyte wday; /* Day of week: 1 to 07 */
		    ubyte hr; /* hour: 0 to 23 */
		    ubyte min; /* minute: 0 to 59 */
		    ubyte sec; /* second: 0 to 59 */
		    } date_t;
		where ubyte is an unsigned byte (0-255)."
::= { status-system 17 }


time-display OBJECT-TYPE
    SYNTAX      INTEGER {
                          eTimeDisplayTwelveHour(1),
                          eTimeDisplayTwentyFourHour(2)
		   }
    MAX-ACCESS read-write
    STATUS      current
       DESCRIPTION "Controls front-panel time display format. Set to
		eTimeDisplayTwelveHour for AM/PM display. Set to
		eTimeDisplayTwentyFourHour for military-type display."
::= { status-system 28 }


device-cfg-download-error OBJECT-TYPE
    SYNTAX      INTEGER
    MAX-ACCESS read-only
    STATUS      current
       DESCRIPTION "Error status of the configuration download session. POS should
		indicate the actual error values reserving value 0 as NO
		ERROR.
                Additional information:
                A value of 0 indicates NO ERROR."
::= { status-system 43 }


device-cfg-upload-error OBJECT-TYPE
    SYNTAX      INTEGER
    MAX-ACCESS read-only
    STATUS      current
       DESCRIPTION "Error status of the configuration upload session. POS should
		indicate the actual error values reserving value 0 as NO
		ERROR.
                Additional information:
                A value of 0 indicates NO ERROR."
::= { status-system 45 }


ship-cartridge-installed-in-printer OBJECT-TYPE
    SYNTAX      INTEGER {
                          eFalse(1),
                          eTrue(2)
		   }
    MAX-ACCESS read-write
    STATUS      current
       DESCRIPTION "Set developer motor cams in the position needed for shipping
		the cartridges installed in the printer if set to eTrue.
                Additional information:
                Notifies the engine that it needs to change it's shipping state."
::= { status-system 97 }


device-mac-address OBJECT-TYPE
    SYNTAX      DisplayString
    MAX-ACCESS read-only
    STATUS      current
       DESCRIPTION "The device's MAC address.
                Additional information:
                The device's MAC address."
::= { status-system 120 }


extended-print-modes-modified OBJECT-TYPE
    SYNTAX      INTEGER {
                          eYes(1),
                          eNo(2)
		   }
    MAX-ACCESS read-only
    STATUS      current
       DESCRIPTION "This object allows the user to view whether the extended print
		modes have been modified from their default settings.
                Additional information:
                This object allows the user to view whether the extended print
                modes have been modified from their default settings."
::= { status-system 121 }

-- 1.3.6.1.4.1.11.2.3.9.4.2.1.1.23.1.1
supports-pjl-user-groups   OBJECT-TYPE
    SYNTAX          INTEGER {
                              eFalse(1),
                             eTrue(2)
                    }
    MAX-ACCESS read-only
    STATUS            current
    DESCRIPTION " Returns eTrue if the device is able to process PJL user group
    variables. See the PJL Technical Reference for the proper
    syntax for setting these variables. Because there may be many
    user groups in some environments, this object allows a client
    application to optimize the print job by including user groups
    only when the device is able to process them"
::= { settings-security 1 }


simm1-bank1-type OBJECT-TYPE
    SYNTAX  INTEGER {
		   eEmpty(1),
		   eUnknown(2),
		   eUnSupported(3),
		   eReadOnlyMemory(4),
		   eFlashMemory(7),
		   eSDRandomAccessMemory(14),
		   eSRandomAccessMemory(15),
		   eFPMRandomAccessMemory(16),
		   eEDORandomAccessMemory(17)
		   }
    MAX-ACCESS read-only
    STATUS  current
    DESCRIPTION
                "Returns an indication of the type of option installed in
                Bank 1 of SIMM slot 1.  See SIMM1-TYPE for a
                description.
                Additional information:
                This object is used for describing the type
                of DIMM banks.  Each physical DIMM slot has up to 2 banks."
::= { simm1-bank1 1 }


simm1-bank1-capacity OBJECT-TYPE
    SYNTAX  INTEGER
    MAX-ACCESS read-only
    STATUS  current
    DESCRIPTION
                "Returns an indication of the capacity of Bank 1 of the
                SIMM installed in SIMM slot 1.  See SIMM1-CAPACITY for a
                description.
                Additional information:
                Returns an indication of the capacity of the
                installed bank option in bytes.  This object is not
                supported unless the SIMM1-BANK1-TYPE type is
                eReadOnlyMemory, eFlashMemory, eEDORandomAccessMemory,
                eSDRandomAccessMemory, eSRandomAccessMemory,
                or eFPMRandomAccessMemory."
::= { simm1-bank1 2 }


simm1-bank2-type OBJECT-TYPE
    SYNTAX  INTEGER {
		   eEmpty(1),
		   eUnknown(2),
		   eUnSupported(3),
		   eReadOnlyMemory(4),
		   eFlashMemory(7),
		   eSDRandomAccessMemory(14),
		   eSRandomAccessMemory(15),
		   eFPMRandomAccessMemory(16),
		   eEDORandomAccessMemory(17)
		   }
    MAX-ACCESS read-only
    STATUS  current
    DESCRIPTION
                "Returns an indication of the type of option installed in
                Bank 2 of SIMM slot 1.  See SIMM1-TYPE for a
                description.
                Additional information:
                This object is used for describing the type
                of DIMM banks.  Each physical DIMM slot has up to 2 banks."
::= { simm1-bank2 1 }


simm1-bank2-capacity OBJECT-TYPE
    SYNTAX  INTEGER
    MAX-ACCESS read-only
    STATUS  current
    DESCRIPTION
                "Returns an indication of the capacity of Bank 2 of the
                SIMM installed in SIMM slot 1.  See SIMM1-CAPACITY for a
                description.
                Additional information:
                Returns an indication of the capacity of the
                installed bank option in bytes.  This object is not
                supported unless the SIMM1-BANK2-TYPE type is
                eReadOnlyMemory, eFlashMemory, eEDORandomAccessMemory,
                eSDRandomAccessMemory, eSRandomAccessMemory,
                or eFPMRandomAccessMemory."
::= { simm1-bank2 2 }


simm2-bank1-type OBJECT-TYPE
    SYNTAX  INTEGER {
		   eEmpty(1),
		   eUnknown(2),
		   eUnSupported(3),
		   eReadOnlyMemory(4),
		   eFlashMemory(7),
		   eSDRandomAccessMemory(14),
		   eSRandomAccessMemory(15),
		   eFPMRandomAccessMemory(16),
		   eEDORandomAccessMemory(17)
		   }
    MAX-ACCESS read-only
    STATUS  current
    DESCRIPTION
                "Returns an indication of the type of option installed in
                Bank 1 of SIMM slot 2.  See SIMM1-TYPE for a
                description.
                Additional information:
                This object is used for describing the type
                of DIMM banks.  Each physical DIMM slot has up to 2 banks."
::= { simm2-bank1 1 }


simm2-bank1-capacity OBJECT-TYPE
    SYNTAX  INTEGER
    MAX-ACCESS read-only
    STATUS  current
    DESCRIPTION
                "Returns an indication of the capacity of Bank 1 of the
                SIMM installed in SIMM slot 2.  See SIMM1-CAPACITY for a
                description.
                Additional information:
                Returns an indication of the capacity of the
                installed bank option in bytes.  This object is not
                supported unless the SIMM2-BANK1-TYPE type is
                eReadOnlyMemory, eFlashMemory, eEDORandomAccessMemory,
                eSDRandomAccessMemory, eSRandomAccessMemory,
                or eFPMRandomAccessMemory."
::= { simm2-bank1 2 }


simm2-bank2-type OBJECT-TYPE
    SYNTAX  INTEGER {
		   eEmpty(1),
		   eUnknown(2),
		   eUnSupported(3),
		   eReadOnlyMemory(4),
		   eFlashMemory(7),
		   eSDRandomAccessMemory(14),
		   eSRandomAccessMemory(15),
		   eFPMRandomAccessMemory(16),
		   eEDORandomAccessMemory(17)
		   }
    MAX-ACCESS read-only
    STATUS  current
    DESCRIPTION
                "Returns an indication of the type of option installed in
                Bank 2 of SIMM slot 2.  See SIMM1-TYPE for a
                description.
                Additional information:
                This object is used for describing the type
                of DIMM banks.  Each physical DIMM slot has up to 2 banks."
::= { simm2-bank2 1 }


simm2-bank2-capacity OBJECT-TYPE
    SYNTAX  INTEGER
    MAX-ACCESS read-only
    STATUS  current
    DESCRIPTION
                "Returns an indication of the capacity of Bank 2 of the
                SIMM installed in SIMM slot 2.  See SIMM1-CAPACITY for a
                description.
                Additional information:
                Returns an indication of the capacity of the
                installed bank option in bytes.  This object is not
                supported unless the SIMM2-BANK2-TYPE type is
                eReadOnlyMemory, eFlashMemory, eEDORandomAccessMemory,
                eSDRandomAccessMemory, eSRandomAccessMemory,
                or eFPMRandomAccessMemory."
::= { simm2-bank2 2 }


simm3-bank1-type OBJECT-TYPE
    SYNTAX  INTEGER {
		   eEmpty(1),
		   eUnknown(2),
		   eUnSupported(3),
		   eReadOnlyMemory(4),
		   eFlashMemory(7),
		   eSDRandomAccessMemory(14),
		   eSRandomAccessMemory(15),
		   eFPMRandomAccessMemory(16),
		   eEDORandomAccessMemory(17)
		   }
    MAX-ACCESS read-only
    STATUS  current
    DESCRIPTION
                "Returns an indication of the type of option installed in
                Bank 1 of SIMM slot 3.  See SIMM1-TYPE for a
                description.
                Additional information:
                This object is used for describing the type
                of DIMM banks.  Each physical DIMM slot has up to 2 banks."
::= { simm3-bank1 1 }


simm3-bank1-capacity OBJECT-TYPE
    SYNTAX  INTEGER
    MAX-ACCESS read-only
    STATUS  current
    DESCRIPTION
                "Returns an indication of the capacity of Bank 1 of the
                SIMM installed in SIMM slot 3.  See SIMM1-CAPACITY for a
                description.
                Additional information:
                Returns an indication of the capacity of the
                installed bank option in bytes.  This object is not
                supported unless the SIMM3-BANK1-TYPE type is
                eReadOnlyMemory, eFlashMemory, eEDORandomAccessMemory,
                eSDRandomAccessMemory, eSRandomAccessMemory,
                or eFPMRandomAccessMemory."
::= { simm3-bank1 2 }


simm3-bank2-type OBJECT-TYPE
    SYNTAX  INTEGER {
		   eEmpty(1),
		   eUnknown(2),
		   eUnSupported(3),
		   eReadOnlyMemory(4),
		   eFlashMemory(7),
		   eSDRandomAccessMemory(14),
		   eSRandomAccessMemory(15),
		   eFPMRandomAccessMemory(16),
		   eEDORandomAccessMemory(17)
		   }
    MAX-ACCESS read-only
    STATUS  current
    DESCRIPTION
                "Returns an indication of the type of option installed in
                Bank 2 of SIMM slot 3.  See SIMM1-TYPE for a
                description.
                Additional information:
                This object is used for describing the type
                of DIMM banks.  Each physical DIMM slot has up to 2 banks."
::= { simm3-bank2 1 }


simm3-bank2-capacity OBJECT-TYPE
    SYNTAX  INTEGER
    MAX-ACCESS read-only
    STATUS  current
    DESCRIPTION
                "Returns an indication of the capacity of Bank 2 of the
                SIMM installed in SIMM slot 3.  See SIMM1-CAPACITY for a
                description.
                Additional information:
                Returns an indication of the capacity of the
                installed bank option in bytes.  This object is not
                supported unless the SIMM3-BANK2-TYPE type is
                eReadOnlyMemory, eFlashMemory, eEDORandomAccessMemory,
                eSDRandomAccessMemory, eSRandomAccessMemory,
                or eFPMRandomAccessMemory."
::= { simm3-bank2 2 }


ram-disk-mode OBJECT-TYPE
    SYNTAX  INTEGER {
		   eOff(1),
		   eOn(2),
		   eAuto(3)
		   }
    MAX-ACCESS read-write
    STATUS  current
    DESCRIPTION
                "Returns or controls RAM disk support.  eOFF turns off
                the RAM disk functionality. eOn turns on the RAM disk
                functionality and creates a RAM disk whose size is
                controlled by the RAM-DISK-SIZE object.  eAuto turns on
                the RAM disk functionality and creates a RAM disk size
                determined by the printer based on installed options and
                other memory related settings.
                Additional information:
                Returns or controls RAM disk support.  eOFF turns off
                the RAM disk functionality. eOn turns on the RAM disk
                functionality and creates a RAM disk whose size is
                controlled by the RAM-DISK-SIZE object.  eAuto turns on
                the RAM disk functionality and creates a RAM disk size
                determined by the printer based on the amount of installed
                memory.  The automatic size will be 25 percent of all memory
                above 4MB."
::= { settings-mass-storage-bd 1 }


ram-disk-size OBJECT-TYPE
    SYNTAX  INTEGER
    MAX-ACCESS read-write
    STATUS  current
    DESCRIPTION
                "Returns or controls the size of the RAM disk.   The
                device POS specifies the minimum memory requirements.
                The object MAXIMUM-RAM-DISK-MEMORY specifies the maximum
                memory available for the RAM disk.
                Additional information:
                Returns or controls the size of the RAM disk.  The values
                that can be set depend on the current setting of the
                RAM-DISK-MODE object, and the amount of memory available
                above 4MB.  Use the MAXIMUM-RAM-DISK-MEMORY object to
                determine the amount of additional memory available
                for the RAM disk."
::= { settings-mass-storage-bd 2 }


maximum-ram-disk-memory OBJECT-TYPE
    SYNTAX  INTEGER
    MAX-ACCESS read-only
    STATUS  current
    DESCRIPTION
                "This object's name is misleading.  This object does not
                return the maximum configurable RAM disk size.  Instead,
                it returns the maximum amount of memory, in bytes, that
                can used to increase the size of the RAM disk.
                Additional information:
                This object returns the maximum amount of additional
                memory that is available for increasing the size of the RAM
                disk."
::= { status-mass-storage-bd 1 }


device-configure-print-engine-speed OBJECT-TYPE
    SYNTAX  INTEGER {
		   eNormal(1),
		   eSlowDown1(2)
		   }
    MAX-ACCESS read-write
    STATUS  current
    DESCRIPTION
                "Return or set the value of the print engine speed. Where
                eNormal is the default speed and with each eSlowDownN setting
                the printer gets progressively slower than the previous speed.
                Additional information:
                This object will only be registered once the
                PE_TEST_PASSWORD is set. This object is used to
                return or set the value for the engine's print speed.
                This value is written to NVRAM and is persistant.
                eNormal = Normal engine speed.
                eSlowDown1 = Decreased engine speed."
::= { device-configure 5 }


device-configure-duplexer-enabled OBJECT-TYPE
    SYNTAX  INTEGER {
		   eDisabled(1),
		   eEnabled(2)
		   }
    MAX-ACCESS read-write
    STATUS  current
    DESCRIPTION
                "Return or set the value for the duplexer installed. eEnabled =
                The duplexer is installed. eDisabled = The duplexer is not
                installed.
                Additional information:
                This object will only be registered once the
                PE_TEST_PASSWORD is set. This object is used to
                return or set the value controlling the duplexer
                This value is written to NVRAM and is persistant.
                eDisabled = Disabled Duplexer.
                eEnabled = Enabled Duplexer."
::= { device-configure 8 }


disk-storage-block-driver2-test-return-code OBJECT-TYPE
    SYNTAX  OCTET STRING
    MAX-ACCESS read-write
    STATUS  current
    DESCRIPTION
                "This test object will not be supported in any released
                product.  Setting this object allows the next call to
                the mass storage block driver 2 to return the specified
                code.  The POS will specify the binary format.
                Additional information:
                The hrDeviceIndex value for the mass storage
                device is the same value that is used to index into the
                DISK-STORAGE-BLOCK-DRIVERS sub-tree.  Since this product
                only supports one mass storage device, the hrDeviceIndex
                for the mass storage device will be 2 if the mass storage device is
                installed.  The value is a two byte value.  The value
                of the first byte indicates the return code, as described
                in the following table:
                value | meaning
                ------+------------------
                1   | After the next power cycle, indicate the
                | mass storage device is not installed.  Only affects the
                | printer state after the next power cycle.
                2   | After the next power cycle, indicate the
                | mass storage device is not initialized.  Changes the
                | contents of the mass storage device so the mass storage device becomes
                | uninitialized.
                3   | After the next power cycle, indicate the
                | mass storage device is defective.  Only affects the
                | printer state after the next power cycle.
                4   | Cause the specified call to the read block
                | routine to indicate read failure.
                5   | Cause the specified call to the write block
                | routine to indicate write failure.
                6   |  After the next power cycle, indicate the
                | mass storage device failed the power-on self-test, but
                | completed the initialization sequence
                | successfully.  Only affects the
                | printer state after the next power cycle.
                7   | Cause the driver to behave, after the next power
                | cycle, as if the mass storage device had the serial number
                | 'SN00000000'.  This is a one-shot effect and the
                | driver reverts to normal behavior if the printer
                | is power cycled a second time.
                The second byte indicates on which call to the specified
                block driver the failure will start to occur.
                If the value of the first bytes is four or five, then the
                value of the second byte in indicates which call to the
                specified block driver routine will  fail.  A value of one
                means the first call will fail. A value of two means the
                second call will fail, and so on.  If the value of the
                first byte is one, two, three, six, or seven, then the
                value of the second byte is ignored.  Writing this object
                causes any previous write to this object to be invalidated."
::= { settings-msbd2 1 }

mopy-mode OBJECT-TYPE
    SYNTAX  INTEGER {
		   eOff(1),
		   eStandard(4),
		   eEnhanced(5)
		   }
    MAX-ACCESS read-write
    STATUS  current
    DESCRIPTION
                "Controls or reports how mopies are generated.  eOff
                turns off the mopy feature. eAuto allows the device to
                determine the best method for generating mopies based on
                the device configuration. eStandard spools the I/O data
                and replays the I/O data multiple times to generate the
                mopies.  eEnhanced spools the rasterized page images and
                replays the rasterized data to generate the mopies.
                Typically, the rasterized data will be larger and will
                allow all but the first mopy to print at speed.  If the
                job being mopied is not extremely complex, then the
                first mopy will print at speed also."
::= { settings-spooler 1 }


engine-media-modes-supported1 OBJECT-TYPE
    SYNTAX  DisplayString
    MAX-ACCESS read-only
    STATUS  current
    DESCRIPTION
                "The list of engine media modes supported by the device.
                The modes are each separated by a comma character.  An
                example string would be: 'Normal,Rough,Low,Vellum'."
::= { media-modes 1 }


hrmemorysize OBJECT-TYPE
    SYNTAX  INTEGER
    MAX-ACCESS read-only
    STATUS  current
    DESCRIPTION
                "The amount of physical main memory contained by
              the host.
              Refer to RFC 1514, Host Resources MIB, for more details.
                Additional information:
                The unit of measure for this object is 1024 bytes.
                The default value assumes the base printer with no
                additional memory."
::= { hrStorage 2 }


prtconsolecolor OBJECT-TYPE
    SYNTAX  INTEGER {
		   ePother(1),
		   ePunknown(2),
		   ePwhite(3),
		   ePred(4),
		   ePgreen(5),
		   ePblue(6),
		   ePcyan(7),
		   ePmagenta(8),
		   ePyellow(9),
		   ePorange(10)
		   }
    MAX-ACCESS read-only
    STATUS  current
    DESCRIPTION
                "The color of this light.
	Refer to Standard Printer MIB for more details."
::= { prtConsoleLightEntry 4 }


phd1-model OBJECT-TYPE
    SYNTAX  DisplayString
    MAX-ACCESS read-only
    STATUS  current
    DESCRIPTION
                "Returns product information identifying the PHD device.
                Example: XXXX"
::= { phd1 1 }


phd1-manufacturing-info OBJECT-TYPE
    SYNTAX  DisplayString
    MAX-ACCESS read-only
    STATUS  current
    DESCRIPTION
                "Returns information describing the manufacture of this
                particular PHD.  May include serial number and firmware
                revision."
::= { phd1 2 }


phd1-type OBJECT-TYPE
    SYNTAX  INTEGER {
		   eEmpty(1),
		   eInputPHD(10)
		   }
    MAX-ACCESS read-only
    STATUS  current
    DESCRIPTION
                "Returns an indication of the type of option installed as
                PHD 1. See SIMM1-TYPE for an explanation of the
                enumerations.
                Additional information:
                 Returns an indication of whether or not the
                envelope feeder is installed on the printer.  A value of eEmpty means that
                the envelope feeder is not installed."
::= { phd1 3 }


phd1-capacity OBJECT-TYPE
    SYNTAX  INTEGER
    MAX-ACCESS read-only
    STATUS  current
    DESCRIPTION
                "Returns an indication of the capacity of the installed
                option.  See SIMM1-CAPACITY for an explanation of the
                meaning of the value of this object.
                Additional information:
                The LaserJet 4000 Series envelope feeder has a single tray."
::= { phd1 4 }


override-media-size OBJECT-TYPE
    SYNTAX  INTEGER {
		   eUSExecutive(1),
		   eUSLetter(2),
		   eUSLegal(3),
		   eISOandJISA5(25),
		   eISOandJISA4(26),
		   eJISB5(45),
		   eMonarch(80),
		   eCommercial10(81),
		   eInternationalDL(90),
		   eInternationalC5(91),
		   eInternationalB5(100),
		   eCustom(101)
		   }
    MAX-ACCESS read-write
    STATUS  current
    DESCRIPTION
                "Sets the media size that is to be used in place of the
                currently requested media size.
                Additional information:
                When a request is received to print on a size and
                type of media that is not currently available, this object contains the
                desired size as set by the print job. This object should be set to a media
                size that is currently available to the printer.
                If a paper mount request is not pending, attempting to get or set this object
                will cause <noSuchName> to be returned."
::= { settings-prt-eng 3 }


tray1-media-size-loaded OBJECT-TYPE
        SYNTAX  INTEGER {
        eUSExecutive(1),
        eUSLetter(2),
        eUSLegal(3),
        eFoolscap(10),
	eLedger(11),
        eStatement(15),
	eROC16K(17),
	eISOandJISA6(24),
	eISOandJISA5(25),
        eISOandJISA4(26),
	eISOandJISA3(27),
	ePRC16K195X270(34),
	eJISB6(44),
        eJISB5(45),
	eJISB4(46),
        eJapanesePostcardSingle(71),
	eJapanesePostcardDouble(72),
	eIndexCard4x6(74),
        eIndexCard5x8(75),
	eIndexCard3x5(78),
	eMonarch(80),
        eCommercial10(81),
	ePRC16K184X260(89),
        eInternationalDL(90),
        eInternationalC5(91),
        eInternationalC6(92),
        eInternationalB5(100),
        eCustom(101),
	eJapanseEnvLong3(110),
        eJapanseEnvLong4(111),
	ePhoto10x15(118),
	ePhotoLSizeCard(121),
	eIndexCard5x7(122),
	eLegal216x340(127),
	eJapaneseOufuku148x200(328),
	eAnySize(32765)
        }
        MAX-ACCESS read-write
    STATUS  current
    DESCRIPTION
                "Returns the media size that is currently loaded in tray
                #1.  This object can be set to indicate the media size
                currently loaded, if the printer supports input trays
                that can not sense the media size.  Complete list of
                supported media sizes along with their dimensions are
                listed in the ``Media Size Table'' near the end of this
                document."
::= { intray1 1 }


tray1-media-available OBJECT-TYPE
    SYNTAX  INTEGER(-1..100)
    MAX-ACCESS read-only
    STATUS  current
    DESCRIPTION
                "Returns a number that indicates how full the input tray
                is.  If the device can only detect empty / not empty the
                device returns -1 for not empty and 0 for empty.  If the
                device can determine how full the tray is, the device
                returns a percentage full from 0% to 100%
                Additional information:
                LaserJet 4V can only detect empty/not empty tray.
                It returns -1 for not empty and 0 for empty."
::= { intray1 2 }


tray1-name OBJECT-TYPE
    SYNTAX  DisplayString
    MAX-ACCESS read-only
    STATUS  current
    DESCRIPTION
                "Returns the device specific name for tray 1."
::= { intray1 3 }

tray1-media-name OBJECT-TYPE
        SYNTAX  DisplayString
        MAX-ACCESS read-write
        STATUS  current
        DESCRIPTION
        "Contains a string identifying the media that is currently
        loaded in tray #1. The media name string is the name associated
        with the loaded media. The strings identifying different media
        are user defined. Examples media name strings include 'HR
        Company LetterHead', '1091 Invoice Form', 'White Bond',
        'Canary', and 'White Recycled'."
::= { intray1 4 }

tray1-custom-media-width OBJECT-TYPE
        SYNTAX  INTEGER
        MAX-ACCESS read-only
        STATUS  current
        DESCRIPTION
        "Width of media (in decipoints) loaded in tray 1."
::= { intray1 10 }

tray1-custom-media-length OBJECT-TYPE
        SYNTAX  INTEGER
        MAX-ACCESS read-only
        STATUS  current
        DESCRIPTION
        "Length of media (in decipoints) loaded in tray 1."
::= { intray1 11 }

tray1-type OBJECT-TYPE
        SYNTAX  INTEGER {
        eTray(1),
        eManualRoll(2),
        eArss(3),
        eManualSheet(4)
        }
        MAX-ACCESS read-write
        STATUS  current
        DESCRIPTION
        "Indicates the type of input media support installed. eTray (1)
        if the paper source is a tray eManualRoll (2) if the paper
        source is a manually loaded roll eArss (3) if the paper source
        is an anutomatically loaded roll (ARSS) eManualSheet (4) if the
        paper source is only for a manually loaded single sheet"
::= { intray1 17 }

tray1-media-key OBJECT-TYPE
        SYNTAX  OCTET STRING
        MAX-ACCESS read-only
        STATUS  current
        DESCRIPTION
        "Contains the media key (index) in the database."
::= { intray1 20 }
tray2-media-size-loaded OBJECT-TYPE
        SYNTAX  INTEGER {
        eUSExecutive(1),
        eUSLetter(2),
	eUSLegal(3),
	eLedger(11),
        eStatement(15),
	eROC16K(17),
	eISOandJISA5(25),
        eISOandJISA4(26),
	eISOandJISA3(27),
	ePRC16K195X270(34),
        eJISB5(45),
	eJISB4(46),
        eCommercial10(81),
	ePRC16K184X260(89),
        eInternationalDL(90),
        eInternationalC5(91),
	eInternationalB5(100),
        eJapanseEnvLong3(110),
	eCustom(101),
	eUnknownMediaSize(32767)
        }
        MAX-ACCESS read-write
    STATUS  current
    DESCRIPTION
                "Returns the media size that is currently configured in
                tray #2.  Complete list of supported media sizes along
                with their dimensions are listed in the ''Media Size
                Table'' near the end of this document.
                Additional information:
                If the tray drawer is open, a get on this object
                will cause a status of
                <genErr> to be
                returned.  If the tray is empty, the size that the
                tray is configured for will be returned. If Tray 2
                is a 500-sheet standard tray, eJISB5 and eUSExecutive
                are not valid values."
::= { intray2 1 }

tray2-media-available OBJECT-TYPE
    SYNTAX  INTEGER(-1..100)
    MAX-ACCESS read-only
    STATUS  current
    DESCRIPTION
                "Returns a number that indicates how full the input tray
                is.  If the device can only detect empty / not empty the
                device returns -1 for not empty and 0 for empty.  If the
                device can determine how full the tray is, the device
                returns a percentage full from 0% to 100%
                Additional information:
                LaserJet 4V can only detect empty/not empty tray.
                It returns -1 for not empty and 0 for empty."
::= { intray2 2 }


tray2-name OBJECT-TYPE
    SYNTAX  DisplayString
    MAX-ACCESS read-only
    STATUS  current
    DESCRIPTION
                "Returns the device specific name for tray 2."
::= { intray2 3 }

tray2-media-name OBJECT-TYPE
        SYNTAX  DisplayString
        MAX-ACCESS read-write
        STATUS  current
        DESCRIPTION
        "Contains a string identifying the media that is currently
        loaded in tray 2. See TRAY1-MEDIA-NAME for a complete
        description."
::= { intray2 4 }

tray2-custom-media-width OBJECT-TYPE
        SYNTAX  INTEGER
        MAX-ACCESS read-only
        STATUS  current
        DESCRIPTION
        "Width of media (in decipoints) loaded in tray 2."
::= { intray2 10 }

tray2-custom-media-length OBJECT-TYPE
        SYNTAX  INTEGER
        MAX-ACCESS read-only
        STATUS  current
        DESCRIPTION
        "Length of media (in decipoints) loaded in tray 2."
::= { intray2 11 }

tray2-phd OBJECT-TYPE
    SYNTAX  INTEGER
    MAX-ACCESS read-only
    STATUS  current
    DESCRIPTION
                "Provides the number of the Paper Handling Device that
                contains this input tray."
::= { intray2 12 }

tray2-fuser-temperature OBJECT-TYPE
    SYNTAX  INTEGER(-1..1)
    MAX-ACCESS read-write
    STATUS  current
    DESCRIPTION
                "The fuser temperature to be used when printing media
                from Tray 2.  The value zero is the default temperature.
                Values less than zero are progressively lower and values
                greater than zero are progressively higher.  The range
                of values supported is device specific.
                Additional information:
                See TRAY1-FUSER-TEMPERATURE."
::= { intray2 13 }

tray2-type OBJECT-TYPE
        SYNTAX  INTEGER {
        eTray(1),
        eManualRoll(2),
        eArss(3),
        eManualSheet(4)
        }
        MAX-ACCESS read-write
        STATUS  current
        DESCRIPTION
        "Indicates the type of input media support installed. eTray (1)
        if the paper source is a tray eManualRoll (2) if the paper
        source is a manually loaded roll eArss (3) if the paper source
        is an anutomatically loaded roll (ARSS) eManualSheet (4) if the
        paper source is only for a manually loaded single sheet"
::= { intray2 17 }

tray2-media-key OBJECT-TYPE
        SYNTAX  OCTET STRING
        MAX-ACCESS read-only
        STATUS  current
        DESCRIPTION
        "Contains the media key (index) in the database."
::= { intray2 20 }

tray3-media-size-loaded OBJECT-TYPE
        SYNTAX  INTEGER {
        eUSExecutive(1),
        eUSLetter(2),
        eUSLegal(3),
        eFoolscap(10),
	eLedger(11),
	eStatement(15),
	eROC16K(17),
	eISOandJISA5(25),
        eISOandJISA4(26),
	eISOandJISA3(27),
	ePRC16K195X270(34),
        eJISB5(45),
	eJISB4(46),
        ePRC16K184X260(89),
        eCustom(101),
	eLegal216x340(127),
	eUnknownMediaSize(32767)
        }
        MAX-ACCESS read-write
    STATUS  current
    DESCRIPTION
                "Returns the media size that is currently configured in
                tray #3.  Complete list of supported media sizes along
                with their dimensions are listed in the ''Media Size
                Table'' near the end of this document.
                Additional information:
                If the tray drawer is open, a get on this object
                will cause a status of
                <genErr> to be
                returned.  If the tray is empty, the size that the
                tray is configured for will be returned."
::= { intray3 1 }

tray3-media-available OBJECT-TYPE
    SYNTAX  INTEGER(-1..100)
    MAX-ACCESS read-only
    STATUS  current
    DESCRIPTION
                "Returns a number that indicates how full the input tray
                is.  If the device can only detect empty / not empty the
                device returns -1 for not empty and 0 for empty.  If the
                device can determine how full the tray is, the device
                returns a percentage full from 0% to 100%
                Additional information:
                LaserJet 4V can only detect empty/not empty tray.
                It returns -1 for not empty and 0 for empty.
               	This object is only supported if a LC is installed.
               	Returns <noSuchName> status
               	if attempting to perform a Get on this OID with
               	no LC installed.
                Returns <noSuchName>
               	status if attempting to perform a Set, EnableTrap, or
               	DisableTrap on this OID with no LC installed."
::= { intray3 2 }


tray3-name OBJECT-TYPE
    SYNTAX  DisplayString
    MAX-ACCESS read-only
    STATUS  current
    DESCRIPTION
                "Returns the device specific name for tray 3.
                Additional information:
                This object is only supported if a LC is
               	installed.
               	Returns <noSuchName> status if
               	attempting to perform a Get on this OID with no LC
               	installed.
                Returns <noSuchName>
                status if attempting to perform a Set, EnableTrap, or
               	DisableTrap on this OID with no LC installed."
::= { intray3 3 }

tray3-media-name OBJECT-TYPE
        SYNTAX  OCTET STRING
        MAX-ACCESS read-write
        STATUS  current
        DESCRIPTION
        "Contains a string identifying the media that is currently
        loaded in tray 3. See TRAY1-MEDIA-NAME for a complete
        description."
::= { intray3 4 }

tray3-custom-media-width OBJECT-TYPE
        SYNTAX  INTEGER
        MAX-ACCESS read-only
        STATUS  current
        DESCRIPTION
        "Width of media (in decipoints) loaded in tray 3."
::= { intray3 10 }

tray3-custom-media-length OBJECT-TYPE
        SYNTAX  INTEGER
        MAX-ACCESS read-only
        STATUS  current
        DESCRIPTION
        "Length of media (in decipoints) loaded in tray 3."
::= { intray3 11 }

tray3-phd OBJECT-TYPE
    SYNTAX  INTEGER
    MAX-ACCESS read-only
    STATUS  current
    DESCRIPTION
                "Provides the number of the Paper Handling Device that
                contains this input tray."
::= { intray3 12 }

tray3-fuser-temperature OBJECT-TYPE
    SYNTAX  INTEGER(-1..1)
    MAX-ACCESS read-write
    STATUS  current
    DESCRIPTION
                "The fuser temperature to be used when printing media
                from Tray 3.  The value zero is the default temperature.
                Values less than zero are progressively lower and values
                greater than zero are progressively higher.  The range
                of values supported is device specific.
                Additional information:
                See TRAY1-FUSER-TEMPERATURE."
::= { intray3 13 }

tray3-type OBJECT-TYPE
        SYNTAX  INTEGER {
        eTray(1),
        eManualRoll(2),
        eArss(3),
        eManualSheet(4)
        }
        MAX-ACCESS read-write
        STATUS  current
        DESCRIPTION
        "Indicates the type of input media support installed. eTray (1)
        if the paper source is a tray eManualRoll (2) if the paper
        source is a manually loaded roll eArss (3) if the paper source
        is an anutomatically loaded roll (ARSS) eManualSheet (4) if the
        paper source is only for a manually loaded single sheet"
::= { intray3 17 }

tray3-media-key OBJECT-TYPE
        SYNTAX  OCTET STRING
        MAX-ACCESS read-only
        STATUS  current
        DESCRIPTION
        "Contains the media key (index) in the database."
::= { intray3 20 }

tray4-media-size-loaded OBJECT-TYPE
    SYNTAX  INTEGER {
		   eUSLetter(2),
		   eUSLegal(3),
		   eLedger(11),
		   eISOandJISA3(27),
		   eISOandJISA4(26),
		   eJISB4(46)
		   }
    MAX-ACCESS read-only
    STATUS  current
    DESCRIPTION
                "Returns the media size that is currently configured in
                tray #4.  Complete list of supported media sizes along
                with their dimensions are listed in the ''Media Size
                Table'' near the end of this document.
                Additional information:
                The Media Size Table does not exist in this document.
                		Attempting to access this object when the tray is not installed
                		will result in an ErrorUnknownObjectIdentifier response from
                		the printer."
::= { intray4 1 }

tray4-phd OBJECT-TYPE
    SYNTAX  INTEGER
    MAX-ACCESS read-only
    STATUS  current
    DESCRIPTION
                "Provides the number of the Paper Handling Device that
                contains this input tray."
::= { intray4 12 }


tray5-media-size-loaded OBJECT-TYPE
        SYNTAX  INTEGER {
        eUSExecutive(1),
        eUSLetter(2),
        eUSLegal(3),
	eFoolscap(10),
        eStatement(15),
	eROC16K(17),
        eISOandJISA5(25),
	eISOandJISA4(26),
        ePRC16K195X270(34),
	eJISB5(45),
        ePRC16K184X260(89),
	eCustom(101),
	eLegal216x340(127),
	eUnknownMediaSize(32767)
        }
        MAX-ACCESS read-write
    STATUS  current
    DESCRIPTION
                "Returns the media size that is currently configured in
                tray #5.  Complete list of supported media sizes along
                with their dimensions are listed in the ''Media Size
                Table'' near the end of this document.
                Additional information:
                If the tray drawer is open, a get on this object
                will cause a status of
                <genErr> to be
                returned.  If the tray is empty, the size that the
                tray is configured for will be returned."
::= { intray5 1 }

tray5-media-name OBJECT-TYPE
        SYNTAX  OCTET STRING
        MAX-ACCESS read-write
        STATUS  current
        DESCRIPTION
        "Contains a string identifying the media that is currently
        loaded in tray 4. See TRAY1-MEDIA-NAME for a complete
        description."
::= { intray5 4 }

tray5-custom-media-width OBJECT-TYPE
        SYNTAX  INTEGER
        MAX-ACCESS read-only
        STATUS  current
        DESCRIPTION
        "Width of media (in decipoints) loaded in tray 4."
::= { intray5 10 }

tray5-custom-media-length OBJECT-TYPE
        SYNTAX  INTEGER
        MAX-ACCESS read-only
        STATUS  current
        DESCRIPTION
        "Length of media (in decipoints) loaded in tray 4."
::= { intray5 11 }

tray5-phd OBJECT-TYPE
    SYNTAX  INTEGER
    MAX-ACCESS read-only
    STATUS  current
    DESCRIPTION
                "Provides the number of the Paper Handling Device that
                contains this input tray."
::= { intray5 12 }

tray5-type OBJECT-TYPE
        SYNTAX  INTEGER {
        eTray(1),
        eManualRoll(2),
        eArss(3),
        eManualSheet(4)
        }
        MAX-ACCESS read-write
        STATUS  current
        DESCRIPTION
        "Indicates the type of input media support installed. eTray (1)
        if the paper source is a tray eManualRoll (2) if the paper
        source is a manually loaded roll eArss (3) if the paper source
        is an anutomatically loaded roll (ARSS) eManualSheet (4) if the
        paper source is only for a manually loaded single sheet"
::= { intray5 17 }

tray5-media-key OBJECT-TYPE
        SYNTAX  OCTET STRING
        MAX-ACCESS read-only
        STATUS  current
        DESCRIPTION
        "Contains the media key (index) in the database."
::= { intray5 20 }

tray6-media-size-loaded OBJECT-TYPE
    SYNTAX  INTEGER {
		   eUSLetter(2),
		   eUSLegal(3),
		   eISOandJISA4(26),
		   eJISB4(46)
		   }
    MAX-ACCESS read-only
    STATUS  current
    DESCRIPTION
                "Returns the media size that is currently configured in
                tray #5.  Complete list of supported media sizes along
                with their dimensions are listed in the ''Media Size
                Table'' near the end of this document.
                Additional information:
                If the tray drawer is open, a get on this object
                will cause a status of
                <genErr> to be
                returned.  If the tray is empty, the size that the
                tray is configured for will be returned"
::= { intray6 1 }


tray6-phd OBJECT-TYPE
    SYNTAX  INTEGER
    MAX-ACCESS read-only
    STATUS  current
    DESCRIPTION
                "Provides the number of the Paper Handling Device that
                contains this input tray.
                Additional information:
                The internal trays belong to device 0 (base engine), the
                envelope feeder is considered to be device 1
                and the external input devices can number
                between 2 and 6 depending on individual user
                configurations."
::= { intray6 12 }


tray7-media-size-loaded OBJECT-TYPE
    SYNTAX  INTEGER {
		   eUSLetter(2),
		   eUSLegal(3),
		   eLedger(11),
		   eISOandJISA4(26),
		   eISOandJISA3(27),
		   eJISB4(46)
		   }
    MAX-ACCESS read-only
    STATUS  current
    DESCRIPTION
                "Returns the media size that is currently configured in
                tray #5.  Complete list of supported media sizes along
                with their dimensions are listed in the ''Media Size
                Table'' near the end of this document.
                Additional information:
                If the tray drawer is open, a get on this object
                will cause a status of
                <genErr> to be
                returned.  If the tray is empty, the size that the
                tray is configured for will be returned"
::= { intray7 1 }


tray7-phd OBJECT-TYPE
    SYNTAX  INTEGER
    MAX-ACCESS read-only
    STATUS  current
    DESCRIPTION
                "Provides the number of the Paper Handling Device that
                contains this input tray.
                Additional information:
                The internal trays belong to device 0 (base engine), the
                envelope feeder is considered to be device 1
                and the external input devices can number
                between 2 and 6 depending on individual user
                configurations.
                NOTE: only TRAY6 and TRAY7 are listed here
                because HP does not make a device with more than
                two trays, but the Specification requires
                support of up to 10 external trays. Therefore the
                objects for TRAY8-PHD ... TRAY15-PHD will exist if
                that many trays exist."
::= { intray7 12 }



outbin3-override-mode OBJECT-TYPE
    SYNTAX  OCTET STRING
    MAX-ACCESS read-write
    STATUS  current
    DESCRIPTION
                "Returns or sets the device behavior when this output bin
                condition causes printing to stop.
                  cCancelJob - The device cancels the job.
                  cOutbinFullOverride - The device sends subsequent
                media to the overflow bin.
                  cOutbinAttentionOverride - The device ignores the
                attention condition and continues printing.
                  cBinderAttentionOverride - The device ignores the
                binder attention condition and continues printing.
                Additional information:
                If cCancelJob is set, the current print job will
                be cancelled regardless of other item settings.
                This object describes the action that is performed
                when the JOB-OUTPUT-AUTO-CONTINUE-TIMEOUT expires.
                The action performed by the CONTINUE object being set
                to eInitiateAction or the GO key being pressed on the
                control panel may cause different actions. See the
                CONTINUE object
                description for information on the actions that
                occur for those conditions.
                NOTE: Because HP is marketing a device with a max of
                16 bins the OUTBIN-OVERRIDE-MODE objects are 3-18 but
                the external device specification requires support of
                up to 315 output bins.  Therefore if these bins exist
                above 16, then the coresponding objects will also exist
                OUTBIN19-OVERRIDE-MODE through OUTBIN317-OVERRIDE-MODE
                			The data for this object is stored in NVRAM."
::= { outbin3 9 }


outbin3-maximum-binding OBJECT-TYPE
    SYNTAX  INTEGER
    MAX-ACCESS read-only
    STATUS  current
    DESCRIPTION
                "The maximum number of sheets of 20 pound paper that can
                be bound by the binding device that serves this output
                bin.  If a job exceeds this number and the job has
                requested binding, cBindingError will be set in NOT-
                READY-DESTINATION-PRINT-ENGINE.
                Additional information:
                This is a read only object that returns the number of
                20# pages that this bin can bind(i.e. staple).  This
                number is used by the host applications to prevent
                jobs that exceed this amount from being sent to this
                bin.  If this bin does not have a finishing function
                like stapling where this object is necessary the
                object will return <badValue>.
                NOTE: Because HP is marketing a device with a max of
                16 bins the OUTBIN-MAXIMUM-BINDING objects are 3-18 but
                the external device specification requires support of
                up to 315 output bins.  Therefore if these bins exist
                above 16, then the coresponding objects will also exist
                OUTBIN19-MAXIMUM-BINDING ... OUTBIN317-MAXIMUM-BINDING"
::= { outbin3 10 }


outbin3-phd OBJECT-TYPE
    SYNTAX  INTEGER
    MAX-ACCESS read-only
    STATUS  current
    DESCRIPTION
                "Provides the number of the Paper Handling Device that
                contains this output bin.
                Additional information:
                This object will return the the device number that
                contains this output bin.  The envelope feed is
                considered PHD1 thus this object will return
                2-6 depending on where in the device chain the bin
                exists.
                NOTE: Because HP is marketing a device with a max of
                16 bins the OUTBIN-OVERRIDE-MODE objects are 3-18 but
                the external device specification requires support of
                up to 315 output bins.  Therefore if these bins exist
                above 16, then the coresponding objects will also exist
                OUTBIN19-PHD through OUTBIN317-PHD"
::= { outbin3 11 }


outbin3-error-info OBJECT-TYPE
    SYNTAX  OCTET STRING (SIZE(0..65535))
    MAX-ACCESS read-only
    STATUS  current
    DESCRIPTION
                "A device specific description of the last error
                encountered for output bin 3.  Each POS should document
                the meaning of all supported error information.
                Additional information:
                This is a description of the current error state of a
                finishing device. (ie stapler).  If the bin does not
                support any finishing capabilities then the object
                will return <badValue>.
                The possible return values are as follows:
                Byte1, Byte2, and Byte3 should be 0x00. as they are
                reserved for future use.
                Byte4 is a bit field that can be interpreted as
                follows:
                bit 0 -- unused
                bit 1 -- eBinderOut   Out of staples
                bit 2 -- eBinderLimit Too many pages to finish
                bit 3 -- eBinderJam   Staple jammed in stapler
                bit 4 -- eBinderAlign Pages aren't aligned correctly
                to finish.
                bit 5 -- unused
                bit 6 -- unused
                bit 7 -- unused

                NOTE: Because HP is marketing a device with a max of
                16 bins the OUTBIN-MAXIMUM-BINDING objects are 3-18 but
                the external device specification requires support of
                up to 315 output bins.  Therefore if these bins exist
                above 16, then the coresponding objects will also exist
                OUTBIN19-MAXIMUM-BINDING ... OUTBIN317-MAXIMUM-BINDING"
::= { outbin3 12 }

outbin4-override-mode OBJECT-TYPE
    SYNTAX  OCTET STRING
    MAX-ACCESS read-write
    STATUS  current
    DESCRIPTION
                "Returns or sets the device behavior when this output bin
                condition causes printing to stop.
                  cCancelJob - The device cancels the job.
                  cOutbinFullOverride - The device sends subsequent
                media to the overflow bin.
                  cOutbinAttentionOverride - The device ignores the
                attention condition and continues printing.
                  cBinderAttentionOverride - The device ignores the
                binder attention condition and continues printing.
                Additional information:
                See OUTBIN3-OVERRIDE-MODE."
::= { outbin4 9 }


outbin4-maximum-binding OBJECT-TYPE
    SYNTAX  INTEGER
    MAX-ACCESS read-only
    STATUS  current
    DESCRIPTION
                "The maximum number of sheets of 20 pound paper that can
                be bound by the binding device that serves this output
                bin.  If a job exceeds this number and the job has
                requested binding, cBindingError will be set in NOT-
                READY-DESTINATION-PRINT-ENGINE.
                Additional information:
                See OUTBIN3-MAXIMUM-BINDING."
::= { outbin4 10 }


outbin4-phd OBJECT-TYPE
    SYNTAX  INTEGER
    MAX-ACCESS read-only
    STATUS  current
    DESCRIPTION
                "Provides the number of the Paper Handling Device that
                contains this output bin.
                Additional information:
                See OUTBIN3-PHD."
::= { outbin4 11 }

outbin5-override-mode OBJECT-TYPE
    SYNTAX  OCTET STRING
    MAX-ACCESS read-write
    STATUS  current
    DESCRIPTION
                "Returns or sets the device behavior when this output bin
                condition causes printing to stop.
                  cCancelJob - The device cancels the job.
                  cOutbinFullOverride - The device sends subsequent
                media to the overflow bin.
                  cOutbinAttentionOverride - The device ignores the
                attention condition and continues printing.
                  cBinderAttentionOverride - The device ignores the
                binder attention condition and continues printing.
                Additional information:
                See OUTBIN3-OVERRIDE-MODE."
::= { outbin5 9 }


outbin5-maximum-binding OBJECT-TYPE
    SYNTAX  INTEGER
    MAX-ACCESS read-only
    STATUS  current
    DESCRIPTION
                "The maximum number of sheets of 20 pound paper that can
                be bound by the binding device that serves this output
                bin.  If a job exceeds this number and the job has
                requested binding, cBindingError will be set in NOT-
                READY-DESTINATION-PRINT-ENGINE.
                Additional information:
                See OUTBIN3-MAXIMUM-BINDING."
::= { outbin5 10 }


outbin5-phd OBJECT-TYPE
    SYNTAX  INTEGER
    MAX-ACCESS read-only
    STATUS  current
    DESCRIPTION
                "Provides the number of the Paper Handling Device that
                contains this output bin.
                Additional information:
                See OUTBIN3-PHD."
::= { outbin5 11 }


outbin6-override-mode OBJECT-TYPE
    SYNTAX  OCTET STRING
    MAX-ACCESS read-write
    STATUS  current
    DESCRIPTION
                "Returns or sets the device behavior when this output bin
                condition causes printing to stop.
                  cCancelJob - The device cancels the job.
                  cOutbinFullOverride - The device sends subsequent
                media to the overflow bin.
                  cOutbinAttentionOverride - The device ignores the
                attention condition and continues printing.
                  cBinderAttentionOverride - The device ignores the
                binder attention condition and continues printing.
                Additional information:
                See OUTBIN3-OVERRIDE-MODE."
::= { outbin6 9 }


outbin6-maximum-binding OBJECT-TYPE
    SYNTAX  INTEGER
    MAX-ACCESS read-only
    STATUS  current
    DESCRIPTION
                "The maximum number of sheets of 20 pound paper that can
                be bound by the binding device that serves this output
                bin.  If a job exceeds this number and the job has
                requested binding, cBindingError will be set in NOT-
                READY-DESTINATION-PRINT-ENGINE.
                Additional information:
                See OUTBIN3-MAXIMUM-BINDING."
::= { outbin6 10 }


outbin6-phd OBJECT-TYPE
    SYNTAX  INTEGER
    MAX-ACCESS read-only
    STATUS  current
    DESCRIPTION
                "Provides the number of the Paper Handling Device that
                contains this output bin.
                Additional information:
                See OUTBIN3-PHD."
::= { outbin6 11 }


outbin7-override-mode OBJECT-TYPE
    SYNTAX  OCTET STRING
    MAX-ACCESS read-write
    STATUS  current
    DESCRIPTION
                "Returns or sets the device behavior when this output bin
                condition causes printing to stop.
                  cCancelJob - The device cancels the job.
                  cOutbinFullOverride - The device sends subsequent
                media to the overflow bin.
                  cOutbinAttentionOverride - The device ignores the
                attention condition and continues printing.
                  cBinderAttentionOverride - The device ignores the
                binder attention condition and continues printing.
                Additional information:
                See OUTBIN3-OVERRIDE-MODE."
::= { outbin7 9 }


outbin7-maximum-binding OBJECT-TYPE
    SYNTAX  INTEGER
    MAX-ACCESS read-only
    STATUS  current
    DESCRIPTION
                "The maximum number of sheets of 20 pound paper that can
                be bound by the binding device that serves this output
                bin.  If a job exceeds this number and the job has
                requested binding, cBindingError will be set in NOT-
                READY-DESTINATION-PRINT-ENGINE.
                Additional information:
                See OUTBIN3-MAXIMUM-BINDING."
::= { outbin7 10 }


outbin7-phd OBJECT-TYPE
    SYNTAX  INTEGER
    MAX-ACCESS read-only
    STATUS  current
    DESCRIPTION
                "Provides the number of the Paper Handling Device that
                contains this output bin.
                Additional information:
                See OUTBIN3-PHD."
::= { outbin7 11 }


outbin8-override-mode OBJECT-TYPE
    SYNTAX  OCTET STRING
    MAX-ACCESS read-write
    STATUS  current
    DESCRIPTION
                "Returns or sets the device behavior when this output bin
                condition causes printing to stop.
                  cCancelJob - The device cancels the job.
                  cOutbinFullOverride - The device sends subsequent
                media to the overflow bin.
                  cOutbinAttentionOverride - The device ignores the
                attention condition and continues printing.
                  cBinderAttentionOverride - The device ignores the
                binder attention condition and continues printing.
                Additional information:
                See OUTBIN3-OVERRIDE-MODE."
::= { outbin8 9 }


outbin8-maximum-binding OBJECT-TYPE
    SYNTAX  INTEGER
    MAX-ACCESS read-only
    STATUS  current
    DESCRIPTION
                "The maximum number of sheets of 20 pound paper that can
                be bound by the binding device that serves this output
                bin.  If a job exceeds this number and the job has
                requested binding, cBindingError will be set in NOT-
                READY-DESTINATION-PRINT-ENGINE.
                Additional information:
                See OUTBIN3-MAXIMUM-BINDING."
::= { outbin8 10 }


outbin8-phd OBJECT-TYPE
    SYNTAX  INTEGER
    MAX-ACCESS read-only
    STATUS  current
    DESCRIPTION
                "Provides the number of the Paper Handling Device that
                contains this output bin.
                Additional information:
                See OUTBIN3-PHD."
::= { outbin8 11 }


outbin9-override-mode OBJECT-TYPE
    SYNTAX  OCTET STRING
    MAX-ACCESS read-write
    STATUS  current
    DESCRIPTION
                "Returns or sets the device behavior when this output bin
                condition causes printing to stop.
                  cCancelJob - The device cancels the job.
                  cOutbinFullOverride - The device sends subsequent
                media to the overflow bin.
                  cOutbinAttentionOverride - The device ignores the
                attention condition and continues printing.
                  cBinderAttentionOverride - The device ignores the
                binder attention condition and continues printing.
                Additional information:
                See OUTBIN3-OVERRIDE-MODE."
::= { outbin9 9 }


outbin9-maximum-binding OBJECT-TYPE
    SYNTAX  INTEGER
    MAX-ACCESS read-only
    STATUS  current
    DESCRIPTION
                "The maximum number of sheets of 20 pound paper that can
                be bound by the binding device that serves this output
                bin.  If a job exceeds this number and the job has
                requested binding, cBindingError will be set in NOT-
                READY-DESTINATION-PRINT-ENGINE.
                Additional information:
                See OUTBIN3-MAXIMUM-BINDING."
::= { outbin9 10 }


outbin9-phd OBJECT-TYPE
    SYNTAX  INTEGER
    MAX-ACCESS read-only
    STATUS  current
    DESCRIPTION
                "Provides the number of the Paper Handling Device that
                contains this output bin.
                Additional information:
                See OUTBIN3-PHD."
::= { outbin9 11 }

outbin9-error-info OBJECT-TYPE
    SYNTAX  OCTET STRING (SIZE(0..65535))
    MAX-ACCESS read-only
    STATUS  current
    DESCRIPTION
                "A device specific description of the last error
                encountered for output bin 9.  Each POS should document
                the meaning of all supported error information.
                Additional information:
                This is a description of the current error state of a
                finishing device. (ie stapler).  If the bin does not
                support any finishing capabilities then the object
                will return <badValue>.
                The possible return values are as follows:
                Byte1, Byte2, and Byte3 should be 0x00. as they are
                reserved for future use.
                Byte4 is a bit field that can be interpreted as
                follows:
                bit 0 -- unused
                bit 1 -- eBinderOut   Out of staples
                bit 2 -- eBinderLimit Too many pages to finish
                bit 3 -- eBinderJam   Staple jammed in stapler
                bit 4 -- eBinderAlign Pages aren't aligned correctly
                to finish.
                bit 5 -- unused
                bit 6 -- unused
                bit 7 -- unused

		OUTBIN3 is the topmost bin on the output device.  This bin
       	        replaces the left output bin on the base printer.  OUTBIN4
                through OUTBIN8 are the additional 5 regular bins supplied
       		by the MBM5S device.  OUTBIN9 is the stapler unit and is
       	        the lowest bin in the device.
                NOTE: Because HP is marketing a device with a max of
                7 bins (MBM5S) the OUTBINn-ERROR-INFO objects are
       		3-9 but the external device specification requires
       		support of up to 315 output bins.  Therefore if these
       		bins exist above 7, then the coresponding objects will
       		also exist OUTBIN10-ERROR-INFO through OUTBIN317-ERROR-INFO."
::= { outbin9 12 }

outbin10-override-mode OBJECT-TYPE
    SYNTAX  OCTET STRING
    MAX-ACCESS read-write
    STATUS  current
    DESCRIPTION
                "Returns or sets the device behavior when this output bin
                condition causes printing to stop.
                  cCancelJob - The device cancels the job.
                  cOutbinFullOverride - The device sends subsequent
                media to the overflow bin.
                  cOutbinAttentionOverride - The device ignores the
                attention condition and continues printing.
                  cBinderAttentionOverride - The device ignores the
                binder attention condition and continues printing.
                Additional information:
                See OUTBIN3-OVERRIDE-MODE."
::= { outbin10 9 }


outbin10-maximum-binding OBJECT-TYPE
    SYNTAX  INTEGER
    MAX-ACCESS read-only
    STATUS  current
    DESCRIPTION
                "The maximum number of sheets of 20 pound paper that can
                be bound by the binding device that serves this output
                bin.  If a job exceeds this number and the job has
                requested binding, cBindingError will be set in NOT-
                READY-DESTINATION-PRINT-ENGINE.
                Additional information:
                See OUTBIN3-MAXIMUM-BINDING."
::= { outbin10 10 }


outbin10-phd OBJECT-TYPE
    SYNTAX  INTEGER
    MAX-ACCESS read-only
    STATUS  current
    DESCRIPTION
                "Provides the number of the Paper Handling Device that
                contains this output bin.
                Additional information:
                See OUTBIN3-PHD."
::= { outbin10 11 }


outbin11-override-mode OBJECT-TYPE
    SYNTAX  OCTET STRING
    MAX-ACCESS read-write
    STATUS  current
    DESCRIPTION
                "Returns or sets the device behavior when this output bin
                condition causes printing to stop.
                  cCancelJob - The device cancels the job.
                  cOutbinFullOverride - The device sends subsequent
                media to the overflow bin.
                  cOutbinAttentionOverride - The device ignores the
                attention condition and continues printing.
                  cBinderAttentionOverride - The device ignores the
                binder attention condition and continues printing.
                Additional information:
                See OUTBIN3-OVERRIDE-MODE."
::= { outbin11 9 }


outbin11-maximum-binding OBJECT-TYPE
    SYNTAX  INTEGER
    MAX-ACCESS read-only
    STATUS  current
    DESCRIPTION
                "The maximum number of sheets of 20 pound paper that can
                be bound by the binding device that serves this output
                bin.  If a job exceeds this number and the job has
                requested binding, cBindingError will be set in NOT-
                READY-DESTINATION-PRINT-ENGINE.
                Additional information:
                See OUTBIN3-MAXIMUM-BINDING."
::= { outbin11 10 }


outbin11-phd OBJECT-TYPE
    SYNTAX  INTEGER
    MAX-ACCESS read-only
    STATUS  current
    DESCRIPTION
                "Provides the number of the Paper Handling Device that
                contains this output bin.
                Additional information:
                See OUTBIN3-PHD."
::= { outbin11 11 }


media-names-available OBJECT-TYPE
    SYNTAX  OCTET STRING
    MAX-ACCESS read-write
    STATUS  current
    DESCRIPTION
                "The value of this object controls which of the MEDIAx-
                NAME objects are supported.  If a bit is set to zero,
                then attempting to get or set the corresponding MEDIAx-
                NAME objects will return
                <noSuchName>.
                Additional information:
                Setting a bit to one will cause the corresponding
                MEDIAn- objects to be available (attempting to access
                an unavailable object will return <noSuchName>).
                MEDIA1- objects are always present in LaserJet 4000 Series, as this is the default
                media. If this object is set to a value that does not include
                cMediaName1Available, that bit will be set and a status of
                <noError> will be returned.
                cMediaName12Available cannot be changed on LaserJet 4000 Series, as MediaName12
                is not a supported Media Name for that product. Attempts to set
                cMediaName12Available will cause <badValue>
                to be returned."
::= { settings-print-media 1 }


media4-engine-media-mode OBJECT-TYPE
    SYNTAX  INTEGER
    MAX-ACCESS read-write
    STATUS  current
    DESCRIPTION
                "The engine processing characteristics that are to be
                applied to this media. The processing characteristics
                are device specific.
                Additional information:
                See the description for MEDIA1-ENGINE-MEDIA-MODE."
::= { media4 4 }


media6-engine-media-mode OBJECT-TYPE
    SYNTAX  INTEGER
    MAX-ACCESS read-write
    STATUS  current
    DESCRIPTION
                "The engine processing characteristics that are to be
                applied to this media. The processing characteristics
                are device specific.
                Additional information:
                See the description for MEDIA1-ENGINE-MEDIA-MODE."
::= { media6 4 }


media10-engine-media-mode OBJECT-TYPE
    SYNTAX  INTEGER
    MAX-ACCESS read-write
    STATUS  current
    DESCRIPTION
                "The engine processing characteristics that are to be
                applied to this media. The processing characteristics
                are device specific.
                Additional information:
                See the description for MEDIA1-ENGINE-MEDIA-MODE."
::= { media10 4 }


media11-engine-media-mode OBJECT-TYPE
    SYNTAX  INTEGER
    MAX-ACCESS read-write
    STATUS  current
    DESCRIPTION
                "The engine processing characteristics that are to be
                applied to this media. The processing characteristics
                are device specific.
                Additional information:
                See the description for MEDIA1-ENGINE-MEDIA-MODE."
::= { media11 4 }

engine-media-mode1-page-count OBJECT-TYPE
    SYNTAX  INTEGER
    MAX-ACCESS read-only
    STATUS  current
    DESCRIPTION
                "The number of sheets printed using this media mode.  The
                device POS should state whether this value is lost
                across a power cycle or is kept in permanent storage.
                Additional information:
                The value of this object is persistent across a power cycle.
                Engine media mode 1 is normal fusing.
                Engine media mode 2 is transparency fusing.
                Engine media mode 3 is glossy fusing.
                Enigne media mode 4 is heavy media fusing.
                Engine media mode 5 is envelope fusing."
::= { media-mode1 2 }


engine-media-mode2-page-count OBJECT-TYPE
    SYNTAX  INTEGER
    MAX-ACCESS read-only
    STATUS  current
    DESCRIPTION
                "The number of sheets printed using this media mode.  The
                device POS should state whether this value is lost
                across a power cycle or is kept in permanent storage.
                Additional information:
                The value of this object is persistent across a power cycle.
                Engine media mode 1 is normal fusing.
                Engine media mode 2 is transparency fusing.
                Engine media mode 3 is glossy fusing.
                Enigne media mode 4 is heavy media fusing.
                Engine media mode 5 is envelope fusing."
::= { media-mode2 2 }


engine-media-mode3-page-count OBJECT-TYPE
    SYNTAX  INTEGER
    MAX-ACCESS read-only
    STATUS  current
    DESCRIPTION
                "The number of sheets printed using this media mode.  The
                device POS should state whether this value is lost
                across a power cycle or is kept in permanent storage.
                Additional information:
                The value of this object is persistent across a power cycle.
                Engine media mode 1 is normal fusing.
                Engine media mode 2 is transparency fusing.
                Engine media mode 3 is glossy fusing.
                Enigne media mode 4 is heavy media fusing.
                Engine media mode 5 is envelope fusing."
::= { media-mode3 2 }


engine-media-mode4-page-count OBJECT-TYPE
    SYNTAX  INTEGER
    MAX-ACCESS read-only
    STATUS  current
    DESCRIPTION
                "The number of sheets printed using this media mode.  The
                device POS should state whether this value is lost
                across a power cycle or is kept in permanent storage.
                Additional information:
                The value of this object is persistent across a power cycle.
                Engine media mode 1 is normal fusing.
                Engine media mode 2 is transparency fusing.
                Engine media mode 3 is glossy fusing.
                Enigne media mode 4 is heavy media fusing.
                Engine media mode 5 is envelope fusing."
::= { media-mode4 2 }


engine-media-mode5-page-count OBJECT-TYPE
    SYNTAX  INTEGER
    MAX-ACCESS read-only
    STATUS  current
    DESCRIPTION
                "The number of sheets printed using this media mode.  The
                device POS should state whether this value is lost
                across a power cycle or is kept in permanent storage.
                Additional information:
                The value of this object is persistent across a power cycle.
                Engine media mode 1 is normal fusing.
                Engine media mode 2 is transparency fusing.
                Engine media mode 3 is glossy fusing.
                Enigne media mode 4 is heavy media fusing.
                Engine media mode 5 is envelope fusing."
::= { media-mode5 2 }

media-size-count OBJECT-TYPE
    SYNTAX  INTEGER
    MAX-ACCESS read-only
    STATUS  current
    DESCRIPTION
                "The number of impressions printed on sheets of this
                media size.  The device POS should state whether this
                value is lost across a power cycle or is kept in
                permanent storage.
                Additional information:
                The value of this object is persistent across a power cycle.

                The index for these objects, the last number of the OID, uniquely identifies the paper size.  This value
                corresponds to the page sizes listed below.  These values are also documented in the PCL Implementor's Guide
                and the PML Master MIB.

                1 US-Executive
                2 US-Letter
                3 US-Legal
                25 ISO and JIS A5
                26 ISO and JIS A4
                45 JIS B5
                80 LaserJet 4500
                81 Commercal-10
                90 International DL
                91 International C5
                100 International B5
                101 Custom"
::= { media-size 1 }

media-size-west-edge-first-side-offset OBJECT-TYPE
    SYNTAX  INTEGER
    MAX-ACCESS read-write
    STATUS  current
    DESCRIPTION
                "Returns or sets the number of 300 dpi dots by which the
                image is shifted relative to the west edge of the medium
                (see NORTH-EDGE-OFFSET).  The adjustment is for the
                first printed side of the medium only.  A positive value
                moves the image away from the west edge of the medium.
                A negative value moves the image closer to the west edge
                of the medium.  The value 0 will return the image to its
                factory default position.
                Additional information:
                Returns or sets the number of 300 dpi dots by which the
                image is shifted relative to the west edge of the medium
                (see NORTH-EDGE-OFFSET).  The adjustment is for the
                first printed side of the medium only.  A positive value
                moves the image away from the west edge of the medium.
                A negative value moves the image closer to the west edge
                of the medium.  The value 0 will return the image to its
                factory default position.  The values in the sub array index
                		    are from the media size table in the hpmib.
                		    The data for this object is stored in NVRAM."
::= { media-size 2 }


media-size-west-edge-second-side-offset OBJECT-TYPE
    SYNTAX  INTEGER
    MAX-ACCESS read-write
    STATUS  current
    DESCRIPTION
                "Returns or sets the number of 300 dpi dots by which the
                image is shifted relative to the west edge of the medium
                (see NORTH-EDGE-OFFSET).  The adjustment is for the
                second printed side of the medium only.  A positive
                value moves the image away from the west edge of the
                medium.  A negative value moves the image closer to the
                west edge of the medium.  The value 0 will return the
                image to its factory default position.
                Additional information:
                Returns or sets the number of 300 dpi dots by which the
                image is shifted relative to the west edge of the medium
                (see NORTH-EDGE-OFFSET).  The adjustment is for the
                second printed side of the medium only.  A positive value
                moves the image away from the west edge of the medium.
                A negative value moves the image closer to the west edge
                of the medium.  The value 0 will return the image to its
                factory default position.  The values in the sub array index
                		    are from the media size table in the hpmib.
                		    The data for this object is stored in NVRAM."
::= { media-size 3 }


prtoutputdefaultindex OBJECT-TYPE
    SYNTAX  INTEGER
    MAX-ACCESS read-write
    STATUS  current
    DESCRIPTION
                "The  value of prtOutputIndex  corresponding to the default
        output sub-unit; that is, this object selects the default
        output destination.
   This value shall be -1 if there is no default output subunit specified
   for the printer as a whole.  In this case, the actual default
   output subunit may be specified by means outside the scope of this
   MIB, such as by each interpreter in a printer with multiple
   interpreters.

   Refer to Standard Printer MIB for more details.
                Additional information:
                LaserJet 4050 Series (LaserJet 4050) has two output bins in the
                base product: a face-up bin on the back of the engine and a
                face-down bin on the top of the engine. These bins are not
                firmware-selectable; instead, paper is diverted to the face-down
                bin only if the face-up bin is physically closed.  Therefore,
                these bins are considered together as the 'standard' bin. However,
                if an HCO is attached to the engine, users will be able to select
                between an HCO bin and the 'standard' bin, which may be either the
                face-up or face-down bin, depending upon whether the face-up bin
                is open. With external output bins attached, the value of this
                object will be settable from the control panel and by the PJL
                OUTBIN variable."
::= { prtGeneralEntry 7 }


prtinputtype OBJECT-TYPE
    SYNTAX  INTEGER {
		   ePother(1),
		   ePunknown(2),
		   ePsheetFeedAutoRemovableTray(3),
		   ePsheetFeedAutoNonRemovableTray(4),
		   ePsheetFeedManual(5),
		   ePcontinuousRoll(6),
		   ePcontinuousFanFold(7)
		   }
    MAX-ACCESS read-only
    STATUS  current
    DESCRIPTION
                "The type of technology (discriminated primarily according to
        feeder mechanism type) employed by the input sub-unit.  Note,
        the Optional Input Class provides for a descriptor field to
        further qualify the other choice.
	Refer to Standard Printer MIB for more details.
                Additional information:
                Tray 1 is the multi-purpose tray and is always present.
                It supports both sheets and envelopes. Its type is
                ePsheetFeedAutoNonRemovableTray.
                Tray 2 is a removable tray that comes standard
                with the printer, although it is usually not removed
                from the printer.  It is of type
                ePsheetFeedAutoRemovableTray.
                Tray 3 is either a 250-sheet standard tray in the
                2x250 base engine configuration or a 500-sheet optional tray
                in the 1x500 base engine configuration. (The optional
                tray is only recognized if it's installed before the
                printer is powered on.) It is of type
                ePsheetFeedAutoRemovableTray.
                The 4th tray in this array is the envelope feeder.  It
                can be detected even when it is installed while the
                printer is powered on.
                Tray 5 is a 500-sheet optional tray that cannot be
                installed while the printer is powered on. It is of type
                ePsheetFeedAutoRemovableTray."
::= { prtInputEntry 2 }


prtinputdimunit OBJECT-TYPE
    SYNTAX  INTEGER {
		   ePtenThousandthsOfInches(3),
		   ePmicrometers(4)
		   }
    MAX-ACCESS read-only
    STATUS  current
    DESCRIPTION
                "The unit of measurement for use calculating and relaying
         dimensional values for this input sub-unit.
	 Refer to Standard Printer MIB for more details.
                Additional information:
                Following is a table of paper sizes and dimensions
                for each paper size supported by LaserJet 4000 Series:

                Size               Inches (ten-thousandths)    Millimeters
                ---------------    ------------------------    -----------
                eUSExecutive       72500 x 105000              184150 x 266700
                eUSLetter          85000 x 110000              215900 x 279400
                eUSLegal           85000 x 140000              215900 x 355600
                eISOandJISA5       58286 x 82677               148000 x 210000
                eISOandJISA4       82677 x 116929              210000 x 297000
                eJISB5             71654 x 101181              182000 x 257000
                eMonarch           38750 x 75000               98425  x 190500
                eCommercial10      41250 x 95000               104775 x 241300
                eInternationalDL   43307 x 86614               110000 x 220000
                eInternationalC5   63780 x 90157               162000 x 229000
                eInternationalB5   69291 x 98425               176000 x 250000
                eCustom            85000 x 140000 (max)        215900 x 355600 (max)  "
::= { prtInputEntry 3 }


prtinputmediadimfeeddirdeclared OBJECT-TYPE
    SYNTAX  INTEGER
    MAX-ACCESS read-write
    STATUS  current
    DESCRIPTION
                "This object provides the value of the declared dimension, in
        the feed direction, of the media that is (or, if empty, was or
        will be) in this input sub-unit.  The feed direction is the
        direction in which the media is fed on this sub-unit.  This
        dimension is measured in input sub-unit dimensional units
        (prtInputDimUnit).  If this input sub-unit can reliably sense
        this value, the value is sensed by the printer and may not be
        changed by management requests.  Otherwise, the value may be
        changed. The value (-1) means other and specifically means
        that this sub-unit places no restriction on this parameter.
        The value (-2) indicates unknown.
	Refer to Standard Printer MIB for more details.
                Additional information:
                For trays 2, 3, and 5 (which can reliably sense this
                value) these objects behave exactly the same as prtInputMediaDimFeedDirChosen.
                Attempting to set the objects for tray 2, 3, or 5 will cause
                <noSuchName> to be returned.
                The default values assume the trays are configured for letter size paper (or COM10,
                in the case of the envelope feeder). For tray 1, the value is the dimension for
                the media size currently declared. For the envelope feeder (tray 4), the value is
                the dimension for the media size currently declared.
                Valid values are 0 to 268435455. If a value within 0.2 inches of a standard
                size (e.g. 85001) is chosen when setting these objects, the standard size will
                be set for the specified tray if the value of prtInputMediaDimXFeedDirDeclared
                is also set to within 0.2 inches of the same standard size. If the value is not
                within 0.2 inches, Custom will be chosen as the size if it is supported by the
                specified tray, otherwise the first available standard size for the tray will
                be selected."
::= { prtInputEntry 4 }


prtinputmediadimxfeeddirdeclared OBJECT-TYPE
    SYNTAX  INTEGER
    MAX-ACCESS read-write
    STATUS  current
    DESCRIPTION
                "This object provides the value of the declared dimension, in
        the cross feed direction, of the media that is (or, if empty,
        was or will be) in this input sub-unit.  The cross  feed
        direction is ninety degrees relative to the feed direction
        associated with this sub-unit. This dimension is measured in
        input sub-unit dimensional units (prtInputDimUnit).  If this
        input sub-unit can reliably sense this value, the value is
        sensed by the printer and may not be changed by management
        requests. Otherwise, the value may be changed. The value (-1)
        means other and specifically means that this sub-unit places
        no restriction on this parameter. The value (-2) indicates
        unknown.
	Refer to Standard Printer MIB for more details.
                Additional information:
                For trays 2, 3, and 5 (which can reliably sense this
                value) these objects behave exactly the same as prtInputMediaDimXFeedDirChosen.
                Attempting to set these objects for tray 2, 3, and 5 will cause
                <noSuchName> to be returned.
                The default values assume the trays are configured for letter size paper (or COM10,
                in the case of the envelope feeder). For tray 1 the value is the dimension for the
                media size currently declared.
                Valid values are 0 to 268435455. If a value within 0.2 inches of a standard
                size (e.g. 85001) is chosen when setting these objects, the standard size will
                be set for the specified tray if the value of prtInputMediaDimFeedDirDeclared
                is also set to within 0.2 inches of the same standard size. If the value is not
                within 0.2 inches, Custom will be chosen as the size if it is supported by the
                specified tray, otherwise the first available standard size for the tray will
                be selected."
::= { prtInputEntry 5 }


prtinputmediadimfeeddirchosen OBJECT-TYPE
    SYNTAX  INTEGER
    MAX-ACCESS read-only
    STATUS  current
    DESCRIPTION
                "The printer will act as if media of the chosen dimension (in
        the feed direction) is present in this input source.  Note
        that this value will be used even if the input tray is empty.
        Feed dimension measurements are taken relative to the feed
        direction associated with that sub-unit and are in input sub-unit
        dimensional units (MediaUnit). If the printer supports the
        declared dimension, the granted dimension is the same as
        the declared dimension. If not, the granted dimension is
        set to the closest dimension that the printer supports
        when the declared dimension is set. The value (-1) means
        other and specifically indicates that this sub-unit
        places no restriction on this parameter. The value (-2)
        indicates unknown.
	Refer to Standard Printer MIB for more details.
                Additional information:
                The objects for trays 2, 3, and 5 reflect the
                configuration of the corresponding trays. When the tray is removed, a value
                of -2 is returned. The default values assume the trays are configured for
                letter size paper (or COM10, in the case of the envelope feeder).  For tray 1
                and the envelope feeder, the object returns the value of the media size for
                which the tray is currently configured because those trays cannot sense what
                size media they contain."
::= { prtInputEntry 6 }


prtinputmediadimxfeeddirchosen OBJECT-TYPE
    SYNTAX  INTEGER
    MAX-ACCESS read-only
    STATUS  current
    DESCRIPTION
                "The printer will act as if media of the chosen dimension (in
        the cross feed direction) is present in this input source.
        Note that this value will be used even if the input tray is
        empty.  The cross feed direction is ninety degrees relative
        to the feed direction associated with this sub-unit. This
        dimension is measured in input sub-unit dimensional units
        (MediaUnit).  If the printer supports the declared
        dimension, the granted dimension is the same as the
        declared dimension. If not, the granted dimension is set
        to the closest dimension that the printer supports when
        the declared dimension is set. The value (-1) means other
        and specifically indicates that this sub-unit places no
        restriction on this parameter.  The value (-2) indicates
        unknown.
	Refer to Standard Printer MIB for more details.
                Additional information:
                The objects for trays 2, 3, and 5 reflect the
                configuration of the corresponding trays. When the tray is removed, a value
                of -2 is returned. The default values assume the trays are configured for
                letter size paper (or COM10, in the case of the envelope feeder).  The objects
                for tray 1 and the envelope feeder return the value of the media size for which
                the tray is currently configured because those trays cannot sense what size media
                they contain."
::= { prtInputEntry 7 }


prtinputcapacityunit OBJECT-TYPE
    SYNTAX  INTEGER {
		   ePtenThousandthsOfInches(3),
		   ePmicrometers(4),
		   ePsheets(8),
		   ePfeet(16),
		   ePmeters(17)
		   }
    MAX-ACCESS read-only
    STATUS  current
    DESCRIPTION
                "The unit of measurement for use in calculating and relaying
        capacity values for this input sub-unit.
	Refer to Standard Printer MIB for more details.
                Additional information:
                A sheet is a single piece of 20 pound paper. For tray
                4, the envelope feeder, a sheet is one envelope"
::= { prtInputEntry 8 }


prtinputmaxcapacity OBJECT-TYPE
    SYNTAX  INTEGER
    MAX-ACCESS read-only
    STATUS  current
    DESCRIPTION
                "The maximum capacity of the input sub-unit in input
        sub-unit capacity units (PrtCapacityUnitTC).  There is no
        convention associated with the media itself so this value
        reflects claimed capacity. If this input sub-unit can
        reliably sense this value, the value is sensed by the
        printer and may not be changed by management requests;
        otherwise, the value may be written (by a Remote
        Control Panel or a Management Application).
        The value (-1) means other and specifically
        indicates that the sub-unit places no restrictions
        on this parameter.  The value (-2) means unknown.
	Refer to Standard Printer MIB for more details.
                Additional information:
                Replaces PML TRAYn-MAXIMUM-CAPACITY.  This is
                specified assuming 20 pound paper for the paper trays."
::= { prtInputEntry 9 }


prtinputcurrentlevel OBJECT-TYPE
    SYNTAX  INTEGER
    MAX-ACCESS read-only
    STATUS  current
    DESCRIPTION
                "The current capacity of the input sub-unit in input
        sub-unit capacity units (PrtCapacityUnitTC). If this input
        sub-unit can reliably sense this value, the value is
        sensed by the printer and may not be changed by
        management requests; otherwise, the value may
        be written (by a Remote Contol Panel or a
        Management Application).  The value (-1) means other and
        specifically indicates that the sub-unit places no
        restrictions on this parameter. The value (-2) means unknown.
        The value (-3) means that the printer knows that at least one
        unit remains.
	Refer to Standard Printer MIB for more details.
                Additional information:
                LaserJet 4000 Series can only detect empty/not empty for its
                trays. It returns -3 for not empty and 0 for empty.
                If a tray is removed, a value of -2 (unknown) will
                be returned."
::= { prtInputEntry 10 }


prtinputstatus OBJECT-TYPE
    SYNTAX  INTEGER
    MAX-ACCESS read-only
    STATUS  current
    DESCRIPTION
                "The current status of this input sub-unit.
	Refer to Standard Printer MIB for more details.
                Additional information:
                Replaces PML STATUS-TRAY-MISSING and
                STATUS-TRAY-EMPTY.
                Values returned by the firmware are detailed in the
                following table. 'Value Or'd Due To Condition' indicates
                that the specified value will be logically or'd into the
                value for this object when the specified Condition occurs.
                Condition                       Value Or'd Due To Condition
                -----------------------         ------------------------
                Tray Lifter Error               3
                Tray not installed or
                not inserted or not
                occupied                        1
                Tray is current source tray
                and paper is moving             6
                Tray involved in paper mount    16 + 32
                Value 3 or 1 is Or'd in         8
                Tray is lifting                 64  "
::= { prtInputEntry 11 }


prtinputmedianame OBJECT-TYPE
    SYNTAX  OCTET STRING (SIZE(0..63))
    MAX-ACCESS read-write
    STATUS  current
    DESCRIPTION
                "A description of the media contained in this input sub-unit;
        This description is intended for display to a human operator.
        This description is not processed by the printer.  It is used
        to provide information not expressible in terms of the other
        media attributes (e.g. prtInputMediaDimFeedDirChosen,
        prtInputMediaDimXFeedDirChosen, prtInputMediaWeight,
        prtInputMediaType). An example would be `legal tender bond
        paper'.
	Refer to Standard Printer MIB for more details.
                Additional information:
                Replaces PML TRAYn-MEDIA-NAME.
                	If set to a string other than one contained by a MEDIAn-NAME
                	object, a status of <badValue> is returned.
                	If set to a string that is unsupported for the specified tray
                	object, a status of <badValue> is returned.
                	After Build5.0 (LaserJet 8100 Series) Cassette trays will not support
                	Transparency nor Label media types.
                	The value of this object is saved across a power cycle."
::= { prtInputEntry 12 }


prtinputname OBJECT-TYPE
    SYNTAX  OCTET STRING (SIZE(0..63))
    MAX-ACCESS read-only
    STATUS  current
    DESCRIPTION
                "The name assigned to this input sub-unit.
	Refer to Standard Printer MIB for more details.
                Additional information:
                Replaces PML TRAYn-NAME."
::= { prtInputEntry 13 }


prtinputvendorname OBJECT-TYPE
    SYNTAX  OCTET STRING (SIZE(0..63))
    MAX-ACCESS read-only
    STATUS  current
    DESCRIPTION
                "The vendor name of this input sub-unit.
	Refer to Standard Printer MIB for more details."
::= { prtInputEntry 14 }


prtinputmodel OBJECT-TYPE
    SYNTAX  OCTET STRING (SIZE(0..63))
    MAX-ACCESS read-only
    STATUS  current
    DESCRIPTION
                "The model name of this input sub-unit.
	Refer to Standard Printer MIB for more details.
                Additional information:
                LaserJet 4000 Series does not specify a model name for Tray1 or Tray2,
                nor for Tray 3 in the 2x250 tray configuration. However, if Tray 3
                is installed in the 1x500 configuration, 'Optional Cassette C4124A' will
                be returned. Tray 3, 4, and 5 objects do not exist unless those trays
                are installed."
::= { prtInputEntry 15 }


prtinputversion OBJECT-TYPE
    SYNTAX  OCTET STRING (SIZE(0..63))
    MAX-ACCESS read-only
    STATUS  current
    DESCRIPTION
                "The version of this input sub-unit.
	Refer to Standard Printer MIB for more details.
                Additional information:
                LaserJet 4000 Series does not specify a version number
                for the input trays."
::= { prtInputEntry 16 }


prtinputserialnumber OBJECT-TYPE
    SYNTAX  OCTET STRING (SIZE(0..63))
    MAX-ACCESS read-only
    STATUS  current
    DESCRIPTION
                "The serial number assigned to this input sub-unit.
	Refer to Standard Printer MIB for more details.
                Additional information:
                LaserJet 4000 Series does not specify a serial number for the
                input trays."
::= { prtInputEntry 17 }


prtinputdescription OBJECT-TYPE
    SYNTAX  OCTET STRING (SIZE(0..255))
    MAX-ACCESS read-only
    STATUS  current
    DESCRIPTION
                "A free-form text description of this input
        sub-unit in the localization specified by
        prtGeneralCurrentLocalization.
	Refer to Standard Printer MIB for more details."
::= { prtInputEntry 18 }


prtinputsecurity OBJECT-TYPE
    SYNTAX  INTEGER {
		   ePother(1),
		   ePon(3),
		   ePoff(4),
		   ePnotPresent(5)
		   }
    MAX-ACCESS read-only
    STATUS  current
    DESCRIPTION
                "Indicates if this input sub-unit has some security
        associated with it.
	Refer to Standard Printer MIB for more details.
                Additional information:
                No security mechanism provided."
::= { prtInputEntry 19 }


prtinputmedialoadtimeout OBJECT-TYPE
    SYNTAX  INTEGER
    MAX-ACCESS read-only
    STATUS  current
    DESCRIPTION
                "When the printer is not able to print due to a subunit
          being empty or the requested media must be manually loaded, the
          printer will wait for the duration (in seconds) specified by this
          object. Upon expiration of the timeout, the printer will take the
          action specified by prtInputNextIndex.
          The event which causes the printer to enter the waiting state is
          product specific. If the printer is not waiting for manually fed
          media, it may switch from an empty subunit to a different subunit
          without waiting for the timeout to expire.
          A value of (-1) implies 'other' or 'infinite' which translates to
          'wait forever'. The action which causes printing to continue is
          product specific. A value of (-2) implies 'unknown'.

		Refer to Standard Printer MIB for more details.
                Additional information:
                This object simply reflects the value of the
                JOB-INPUT-AUTO-CONTINUE-TIMEOUT object. See the description of that object
                for additional information."
::= { prtInputEntry 24 }


prtinputnextindex OBJECT-TYPE
    SYNTAX  INTEGER
    MAX-ACCESS read-only
    STATUS  current
    DESCRIPTION
                "The value of prtInputIndex corresponding to the input
          subunit which will be used when this input subunit is emptied and
          the timeout specified by prtInputMediaLoadTimeout expires. A
          value of zero(0) indicates that auto input switching will not
          occur when this input subunit is emptied. If the timeout
          specified by prtInputLoadMediaTimeout expires and this value is
          zero(0), the job will be aborted. A value of (-1) means other.
          The value (-2) means 'unknown' and specifically indicates that an
          implementation specific method will determine the next input
          subunit to use at the time this subunit is emptied and the
          timeout expires. The value(-3) means input switching is not
          supported for this subunit.
		 Refer to Standard Printer MIB for more details.
                Additional information:
                This object reflects the state of JOB-INPUT-AUTO-CONTINUE-MODE
                and JOB-INPUT-AUTO-CONTINUE-TIMEOUT. If
                JOB-INPUT-AUTO-CONTINUE-TIMEOUT is set to -1 or
                JOB-INPUT-AUTO-CONTINUE-MODE is set up to cancel the job,
                this object will return 0. If JOB-INPUT-AUTO-CONTINUE-TIMEOUT
                is >= 0 and JOB-INPUT-AUTO-CONTINUE-MODE is not set up to
                cancel the job, this object will return -2, meaning that
                a product-specific tray switching action will occur."
::= { prtInputEntry 26 }


prtoutputtype OBJECT-TYPE
    SYNTAX  INTEGER {
		   ePother(1),
		   ePunknown(2),
		   ePremovableBin(3),
		   ePunRemovableBin(4),
		   ePcontinuousRollDevice(5),
		   ePmailBox(6),
		   ePcontinousFanFold(7)
		   }
    MAX-ACCESS read-only
    STATUS  current
    DESCRIPTION
                "The type of technology supported by this output sub-unit.
	Refer to Standard Printer MIB for more details.
                Additional information:
                LaserJet 4000 Series has two built-in output bins: a face-down
                bin located at the top of the printer and a face-up bin located
                at the rear of the printer. However, neither of these bins is
                firmware-selectable, so both bins are considered together as the
                'standard' bin. LaserJet 4000 Series supports HCO devices as well as a
                stacker/stapler, but these devices are currently T.B.D."
::= { prtOutputEntry 2 }


prtoutputcapacityunit OBJECT-TYPE
    SYNTAX  INTEGER {
		   ePtenThousandthsOfInches(3),
		   ePmicrometers(4),
		   ePsheets(8),
		   ePfeet(16),
		   ePmeters(17)
		   }
    MAX-ACCESS read-only
    STATUS  current
    DESCRIPTION
                "The unit of measurement for use in calculating and relaying
        capacity values for this output sub-unit.
	Refer to Standard Printer MIB for more details.
                Additional information:
                A sheet is a single piece of 20 pound paper."
::= { prtOutputEntry 3 }


prtoutputmaxcapacity OBJECT-TYPE
    SYNTAX  INTEGER
    MAX-ACCESS read-only
    STATUS  current
    DESCRIPTION
                "The maximum capacity of this output sub-unit in output
        sub-unit capacity units (PrtCapacityUnitTC). There is no
        convention associated with the media itself so this value
        essentially reflects claimed capacity. If this output
        sub-unit can reliably sense this value, the value is
        sensed by the printer and may not be changed by management
        requests; otherwise, the value may be written
        (by a Remote Control Panel or a Management Application).
        The value (-1) means other and specifically indicates
        that the sub-unit places no restrictions on this parameter.
        The value (-2) means unknown.
	Refer to Standard Printer MIB for more details.
                Additional information:
                Replaces PML OUTBINn-MAXIMUM-CAPACITY.
                LaserJet 4000 Series cannot sense the amount of paper in its standard output
                bin; however, the face-up bin can hold 50 sheets of 20lb. paper,
                and the face-down bin can hold 250 sheets. External output devices
                are currently T.B.D."
::= { prtOutputEntry 4 }


prtoutputremainingcapacity OBJECT-TYPE
    SYNTAX  INTEGER
    MAX-ACCESS read-only
    STATUS  current
    DESCRIPTION
                "The remaining capacity of the possible output sub-unit
        capacity in output sub-unit capacity units (PrtCapacityUnitTC)
        of this output sub-unit. If this output sub-unit can
        reliably sense this value, the value is sensed by the
        printer and may not be modified by management requests;
        otherwise, the value may be written (by
        a Remote Control Panel or a Management
        Application).  The value (-1) means other and
        specifically indicates that the sub-unit places no
        restrictions on this parameter.  The value (-2) means
        unknown.  The value (-3) means that the printer knows that
        there remains capacity for at least one unit.
	Refer to Standard Printer MIB for more details.
                Additional information:
                Replaces PML NOT-READY-OUTBIN-FULL and
                STATUS-OUTBIN-FULL.
                LaserJet 4000 Series is capable of determining when the face-down
                bin goes full, but not the level of that bin. LaserJet 4000 Series
                is not capable of determining whether the face-up bin
                is full. RemainingCapacity capabilities of the
                stapler/stacker, as well as unplanned HCO devices,
                are currently T.B.D.
                LaserJet 4000 Series will report a value of 0 when the face-down
                bin is full and -3 when the face down bin is not full."
::= { prtOutputEntry 5 }


prtoutputstatus OBJECT-TYPE
    SYNTAX  INTEGER
    MAX-ACCESS read-only
    STATUS  current
    DESCRIPTION
                "The current status of this output sub-unit.
	Refer to Standard Printer MIB for more details.
                Additional information:
                Replaces PML NOT-READY-OUTBIN-MISSING and
                STATUS-OUTBIN-MISING.
                The default values assume all bins are empty.
                See SubUnitStatus in RFC1759 Printer MIB for details on values reported by
                this object. LaserJet 4000 Series will not include values Available and Standby (2),
                Available and Active (4), Unknown (5) or Transitioning to Intended State
                (64).
                Values returned by the firmware are detailed in the
                following table. 'Value Or'd Due To Condition' indicates
                that the specified value will be logically or'd into the
                value for this object when the specified Condition occurs.
                Condition                       Value Or'd Due To Condition
                -----------------------         ------------------------
                Binder Error                    3
                Bin full, binder empty,
                bind limit reached, binder
                align error, bin attention
                error, or bin attention
                warning                         1
                Bin is current bin and
                paper is moving                 6
                Bin is the bin responsible
                for Bin Full error message
                being displayed                 16 + 32
                Value 1 or 3 is Or'd in         8  "
::= { prtOutputEntry 6 }


prtoutputname OBJECT-TYPE
    SYNTAX  OCTET STRING (SIZE(0..15))
    MAX-ACCESS read-only
    STATUS  current
    DESCRIPTION
                "The name assigned to this output sub-unit.
	Refer to Standard Printer MIB for more details.
                Additional information:
                Replaces PML OUTBINn-NAME.
                	        The characters must be in the range 20H to 7FH except
                		5C cannot be used. When this string is displayed on
                		the control panel the Roman-8 symbol set is used."
::= { prtOutputEntry 7 }


prtoutputvendorname OBJECT-TYPE
    SYNTAX  OCTET STRING (SIZE(0..63))
    MAX-ACCESS read-only
    STATUS  current
    DESCRIPTION
                "The vendor name of this output sub-unit.
	Refer to Standard Printer MIB for more details."
::= { prtOutputEntry 8 }


prtoutputmodel OBJECT-TYPE
    SYNTAX  OCTET STRING (SIZE(0..63))
    MAX-ACCESS read-only
    STATUS  current
    DESCRIPTION
                "The name assigned to this output sub-unit.
	Refer to Standard Printer MIB for more details.
                Additional information:
                LaserJet 4000 Series does not support a model number for its
                built-in output bins. This object may change in the
                future when external output devices are added."
::= { prtOutputEntry 9 }


prtoutputversion OBJECT-TYPE
    SYNTAX  OCTET STRING (SIZE(0..63))
    MAX-ACCESS read-only
    STATUS  current
    DESCRIPTION
                "The version of this output sub-unit.
	Refer to Standard Printer MIB for more details.
                Additional information:
                Returns device-specific information about the configuration
                of the output bin. May include information about the type of
                processing that can be done to media sent to this bin;
                processing includes but is not limited to binding, punching,
                folding and sealing. Format of this object is specified by
                the output device documentation."
::= { prtOutputEntry 10 }


prtoutputserialnumber OBJECT-TYPE
    SYNTAX  OCTET STRING (SIZE(0..63))
    MAX-ACCESS read-only
    STATUS  current
    DESCRIPTION
                "The serial number assigned to this output sub-unit.
	Refer to Standard Printer MIB for more details.
                Additional information:
                LaserJet 4000 Series does not support a serial number for output
                devices."
::= { prtOutputEntry 11 }


prtoutputdescription OBJECT-TYPE
    SYNTAX  OCTET STRING (SIZE(0..255))
    MAX-ACCESS read-only
    STATUS  current
    DESCRIPTION
                "  A free-form text description of this output sub-unit in the
        localization specified by prtGeneralCurrentLocalization.
	Refer to Standard Printer MIB for more details."
::= { prtOutputEntry 12 }


prtoutputsecurity OBJECT-TYPE
    SYNTAX  INTEGER {
		   ePother(1),
		   ePon(3),
		   ePoff(4),
		   ePnotPresent(5)
		   }
    MAX-ACCESS read-only
    STATUS  current
    DESCRIPTION
                "Indicates if this output sub-unit has some security associated
        with it and if that security is enabled or not.
	Refer to Standard Printer MIB for more details.
                Additional information:
                No security mechanism provided."
::= { prtOutputEntry 13 }


prtoutputdimunit OBJECT-TYPE
    SYNTAX  INTEGER {
		   ePtenThousandthsOfInches(3),
		   ePmicrometers(4)
		   }
    MAX-ACCESS read-only
    STATUS  current
    DESCRIPTION
                "The unit of measurement for use in calculating and relaying
        dimensional values for this output sub-unit.
	Refer to Standard Printer MIB for more details.
                Additional information:
                See the description for prtInputDimUnit for a table
                of supported paper sizes and their dimensions for LaserJet 4000 Series."
::= { prtOutputEntry 14 }


prtoutputmaxdimfeeddir OBJECT-TYPE
    SYNTAX  INTEGER
    MAX-ACCESS read-only
    STATUS  current
    DESCRIPTION
                "The maximum dimensions supported by this output sub-unit
        for measurements taken parallel relative to the feed
        direction associated with that sub-unit in output
        sub-unit dimensional units (MediaUnit). If this output
        sub-unit can reliably sense this value, the value is
        sensed by the printer and may not be changed with
        management protocol operations.
	Refer to Standard Printer MIB for more details.
                Additional information:
                LaserJet 4000 Series has two output bins in the base product:
                a face-up bin on the back of the engine and a face-down bin on
                the top of the engine. These bins are not firmware-selectable;
                instead, paper is diverted to the face-down bin only if the face-up
                bin is physically closed.  Therefore, these bins are considered
                together as the 'standard' bin.
                The value returned by this object depends on the value
                of prtOutputDimUnit. It is 140000 if prtOutputDimUnit is
                ePtenThousandthsOfInches or 355600 if prtOutputDimUnit is ePmicrometers."
::= { prtOutputEntry 15 }


prtoutputmaxdimxfeeddir OBJECT-TYPE
    SYNTAX  INTEGER
    MAX-ACCESS read-only
    STATUS  current
    DESCRIPTION
                "The maximum dimensions supported by this output sub-unit
        for measurements taken ninety degrees relative to the
        feed direction associated with that sub-unit in output
        sub-unit dimensional units (MediaUnit). If this output
        sub-unit can reliably sense this value, the value is
        sensed by the printer and may not be changed with
        management protocol operations.
	Refer to Standard Printer MIB for more details.
                Additional information:
                LaserJet 4000 Series has two output bins in the base product:
                a face-up bin on the back of the engine and a face-down bin on
                the top of the engine. These bins are not firmware-selectable;
                instead, paper is diverted to the face-down bin only if the face-up
                bin is physically closed.  Therefore, these bins are considered
                together as the 'standard' bin.
                The value returned by this object depends on the value
                of prtOutputDimUnit. It is 85000 if prtOutputDimUnit is
                ePtenThousandthsOfInches and 215900 if prtOutputDimUnit
                is ePmicrometers."
::= { prtOutputEntry 16 }


prtoutputmindimfeeddir OBJECT-TYPE
    SYNTAX  INTEGER
    MAX-ACCESS read-only
    STATUS  current
    DESCRIPTION
                "The minimum dimensions supported by this output sub-unit
        for measurements taken parallel relative to the feed
        direction associated with that sub-unit in output
        sub-unit dimensional units (DimUnit).  If this output
        sub-unit can reliably sense this value, the value is
        sensed by the printer and may not be changed with
        management protocol operations.
	Refer to Standard Printer MIB for more details.
                Additional information:
                LaserJet 4000 Series has two output bins in the base product:
                a face-up bin on the back of the engine and a face-down bin on
                the top of the engine. These bins are not firmware-selectable;
                instead, paper is diverted to the face-down bin only if the face-up
                bin is physically closed.  Therefore, these bins are considered
                together as the 'standard' bin.
                The value returned by this object depends on the value
                of prtOutputDimUnit. It is 50000 if prtOutputDimUnit is
                ePtenThousandthsOfInches or 127000 if prtOutputDimUnit is
                ePmicrometers."
::= { prtOutputEntry 17 }


prtoutputmindimxfeeddir OBJECT-TYPE
    SYNTAX  INTEGER
    MAX-ACCESS read-only
    STATUS  current
    DESCRIPTION
                "The minimum dimensions supported by this output sub-unit
        for measurements taken ninety degrees relative to the
        feed direction associated with that sub-unit in output
        sub-unit dimensional units (DimUnit). If this output
        sub-unit can reliably sense this value, the value is
        sensed by the printer and may not be changed with
        management protocol operations.
	Refer to Standard Printer MIB for more details.
                Additional information:
                LaserJet 4000 Series has two output bins in the base product:
                a face-up bin on the back of the engine and a face-down bin on
                the top of the engine. These bins are not firmware-selectable;
                instead, paper is diverted to the face-down bin only if the face-up
                bin is physically closed.  Therefore, these bins are considered
                together as the 'standard' bin.
                The value returned by this object depends on the value
                of prtOutputDimUnit. It is 30000 if prtOutputDimUnit is
                ePtenThousandthsOfInches or 76200 if prtOutputDimUnit is ePmicrometers."
::= { prtOutputEntry 18 }


prtoutputstackingorder OBJECT-TYPE
    SYNTAX  INTEGER {
		   ePunknown(2),
		   ePfirstToLast(3),
		   ePlastToFirst(4)
		   }
    MAX-ACCESS read-only
    STATUS  current
    DESCRIPTION
                "The current state of the stacking order for the
        associated output sub-unit. `FirstToLast' means
        that as pages are output the front of the next page is
        placed against the back of the previous page.
        `LasttoFirst' means that as pages are output the back
        of the next page is placed against the front of the
        previous page.
	Refer to Standard Printer MIB for more details.
                Additional information:
                Replaces PML OUTBINn-STACK-ORDER."
::= { prtOutputEntry 19 }


prtoutputpagedeliveryorientation OBJECT-TYPE
    SYNTAX  INTEGER {
		   ePfaceUp(3),
		   ePfaceDown(4)
		   }
    MAX-ACCESS read-only
    STATUS  current
    DESCRIPTION
                "The reading surface that will be `up' when pages are
        delivered to the associated output sub-unit. Values are
        faceUp and faceDown. (Note: interpretation of these
        values is in general context-dependent based on locale;
        presentation of these values to an end-user should be
        normalized to the expectations of the user).
	Refer to Standard Printer MIB for more details."
::= { prtOutputEntry 20 }


prtoutputbursting OBJECT-TYPE
    SYNTAX  INTEGER {
		   ePother(1),
		   ePon(3),
		   ePoff(4),
		   ePnotPresent(5)
		   }
    MAX-ACCESS read-only
    STATUS  current
    DESCRIPTION
                "This object indicates that the outputting sub-unit
        supports bursting, and if so, whether the feature is enabled.
        Bursting is the process by which continuous media is separated
        into individual sheets, typically by bursting along pre-formed
        perforations.
	Refer to Standard Printer MIB for more details."
::= { prtOutputEntry 21 }


prtoutputdecollating OBJECT-TYPE
    SYNTAX  INTEGER {
		   ePother(1),
		   ePon(3),
		   ePoff(4),
		   ePnotPresent(5)
		   }
    MAX-ACCESS read-only
    STATUS  current
    DESCRIPTION
                "This object indicates that the output supports
        supports decollating, and if so, whether the feature
        is enabled. Decollating is the process by which the
        individual parts within a multi-part form are separated
        and sorted into separate stacks for each part.
	Refer to Standard Printer MIB for more details."
::= { prtOutputEntry 22 }


prtoutputpagecollated OBJECT-TYPE
    SYNTAX  INTEGER {
		   ePother(1),
		   ePon(3),
		   ePoff(4),
		   ePnotPresent(5)
		   }
    MAX-ACCESS read-only
    STATUS  current
    DESCRIPTION
                "This object indicates that the output sub-unit
        supports page collation, and if so, whether the feature is
        enabled. See glossary for definition of how this document defines
        collation.
	Refer to Standard Printer MIB for more details."
::= { prtOutputEntry 23 }


prtoutputoffsetstacking OBJECT-TYPE
    SYNTAX  INTEGER {
		   ePother(1),
		   ePon(3),
		   ePoff(4),
		   ePnotPresent(5)
		   }
    MAX-ACCESS read-only
    STATUS  current
    DESCRIPTION
                "This object indicates that the output supports
        supports offset stacking, and if so, whether the feature is
        enabled. See glossary for how Offset Stacking is defined by this
        document.
	Refer to Standard Printer MIB for more details."
::= { prtOutputEntry 24 }


prtmarkersuppliesdescription OBJECT-TYPE
    SYNTAX  OCTET STRING (SIZE(0..255))
    MAX-ACCESS read-only
    STATUS  current
    DESCRIPTION
                "The description of this supply container/receptacle in the
        localization specified by prtGeneralCurrentLocalization.
	Refer to Standard Printer MIB for more details."
::= { prtMarkerSuppliesEntry 6 }


prtmarkersuppliesmaxcapacity OBJECT-TYPE
    SYNTAX  INTEGER
    MAX-ACCESS read-only
    STATUS  current
    DESCRIPTION
                "The maximum capacity of this supply container/receptacle
        expressed in prtMarkerSuppliesSupplyUnit. If this supply
        container/receptacle can reliably sense this value, the
        value is reported by the printer and is read-only;
        otherwise, the value may be written (by a Remote Control
        Panel or a Management Application). The value (-1) means
        other and specifically indicates that the sub-unit places
        no restrictions on this parameter. The value (-2) means
        unknown.
	Refer to Standard Printer MIB for more details.
                Additional information:
                LaserJet 4050 Series - LaserJet 4050 Series now has the same toner-mesuring feature
                as LaserJet 8100 Series which utilizes the GRIN ASICS's ability to detect the
                number of pixels placed on a page.  The default value units are
                in 10ths of a gram.  A 27X toner cartridge holds 460 grams of
                toner. Note :a 27A cartidge holds 303 g but we are using the
                27X value."
::= { prtMarkerSuppliesEntry 8 }


prtmarkersupplieslevel OBJECT-TYPE
    SYNTAX  INTEGER
    MAX-ACCESS read-only
    STATUS  current
    DESCRIPTION
                "The current level if this supply is a container; the
        remaining space if this supply is a receptacle. If this
        supply container/receptacle can reliably sense this
        value, the value is reported by the printer and is
        read-only; otherwise, the value may be written (by a
        Remote Control Panel or a Management Application). The
        value (-1) means other and specifically indicates that
        the sub-unit places no restrictions on this parameter.
        The value (-2) means unknown.  A value of (-3) means that the
        printer knows that there is some supply/remaining space,
        respectively.
	Refer to Standard Printer MIB for more details.
                Additional information:
                LaserJet 4050 Series will have a new toner-measuring feature that
                utilizes the GRIN ASIC's ability to detect the amount of pixels
                that have been placed on a single page.  This Pixel-Counting
                Gas Gauge should be able to calculate toner levels within 10%.
                Because textual printing and graphics printing utilize different
                pixel usage, accuracy for the counting algorithms have been
                biased toward textual printing. Heavy graphics printing will
                cause the cartridge to appear to be emptier than it really is.
                Over time however, statistical averaging values that are kept in
                NVRAM will help make the gauge more accurate according to
                individual customer usage models.  The new values will vary
                between 0 and 4600 depending on how much toner has been
                calculated to have been used."
::= { prtMarkerSuppliesEntry 9 }


prtmediapathmaxspeed OBJECT-TYPE
    SYNTAX  INTEGER
    MAX-ACCESS read-only
    STATUS  current
    DESCRIPTION
                "The maximum printing speed of this media path expressed in
        prtMediaPathMaxSpeedUnit's.  A value of (-1) implies
        'other'.
	Refer to Standard Printer MIB for more details.
                Additional information:
                Replaces PML PRINT-ENGINE-PERFORMANCE.
                The page size for this performance is 8.5x11. The
                duplex speed is based on 6 ppm."
::= { prtMediaPathEntry 4 }


prtmediapathmaxmediafeeddir OBJECT-TYPE
    SYNTAX  INTEGER
    MAX-ACCESS read-only
    STATUS  current
    DESCRIPTION
                "The maximum physical media size in the feed direction of this
        media path expressed in units of measure specified by
        PrtMediaPathMediaSizeUnit.  A value of (-1) implies 'unlimited',
        a value of (-2) implies 'unknown'.
	Refer to Standard Printer MIB for more details.
                Additional information:
                The value returned by this object depends on the value
                of prtMediaPathMediaSizeUnit. It is 140000 if prtMediaPathMediaSizeUnit is
                ePtenThousandthsOfInches or 355600 if prtMediaPathMediaSizeUnit is ePmicrometers."
::= { prtMediaPathEntry 5 }


prtmediapathmaxmediaxfeeddir OBJECT-TYPE
    SYNTAX  INTEGER
    MAX-ACCESS read-only
    STATUS  current
    DESCRIPTION
                "The maximum physical media size across the feed direction of
        this media path expressed in units of measure specified by
        prtMediaPathMediaSizeUnit.  A value of (-2) implies 'unknown'.
	Refer to Standard Printer MIB for more details.
                Additional information:
                The value returned by this object depends on the value
                of prtMediaPathMediaSizeUnit. It is 85000 if prtMediaPathMediaSizeUnit is
                ePtenThousandthsOfInches and 215900 if prtMediaPathMediaSizeUnit is ePmicrometers."
::= { prtMediaPathEntry 6 }


prtmediapathminmediafeeddir OBJECT-TYPE
    SYNTAX  INTEGER
    MAX-ACCESS read-only
    STATUS  current
    DESCRIPTION
                "The minimum physical media size in the feed direction of this
        media path expressed in units of measure specified by
        prtMediaPathMediaSizeUnit. A value of (-2) implies 'unknown'.
	Refer to Standard Printer MIB for more details.
                Additional information:
                The value returned by this object depends on the value
                of prtMediaPathMediaSizeUnit. It is 50000 if prtMediaPathMediaSizeUnit is
                ePtenThousandthsOfInches or 127000 if prtMediaPathMediaSizeUnit is ePmicrometers."
::= { prtMediaPathEntry 7 }


prtmediapathminmediaxfeeddir OBJECT-TYPE
    SYNTAX  INTEGER
    MAX-ACCESS read-only
    STATUS  current
    DESCRIPTION
                "The minimum physical media size across the feed direction of
        this media path expressed in units of measure specified by
        prtMediaPathMediaSizeUnit.  A value of (-2) implies 'unknown'.
	Refer to Standard Printer MIB for more details.
                Additional information:
                The value returned by this object depends on the value
                of prtMediaPathMediaSizeUnit. It is 30000 if prtMediaPathMediaSizeUnit is
                ePtenThousandthsOfInches or 76200 if prtMediaPathMediaSizeUnit is ePmicrometers."
::= { prtMediaPathEntry 8 }


file-system-max-open-files OBJECT-TYPE
    SYNTAX  INTEGER(32..512)
    MAX-ACCESS read-write
    STATUS  current
    DESCRIPTION
                "The number of open files allowed at one time. Opening a
                file when the maximum number of files are currently open
                will fail.
                Additional information:
                Indicates the number of open files a
                personality (e.g. PCL or PostScript) is guaranteed to be
                able to open before the file system runs out of file handles.
                After writing this object, the printer
                must be rebooted (powercycled) before the change takes effect.
                This object supports any value between 32 - 512 inclusive.
                If a value Less then 32 then it snaps to 32 if greater then
                	       512 it snaps to 512.
                The factory default value is dependent on the amount of
                installed RAM.  The default value of 32 is when
                	       Memory <= 4MB, 128 is if the memory is > 4MB.
                Performing a cold reset sets this object
                back to the factory default value.  Returns
                <noSuchName>
                status if attempting to access this object and there
                is no storage device is installed.
                		   Default for LaserJet 4000 Series/LaserJet 5000 Series is 32
                		   Default for LaserJet 8000 Series/LaserJet 8100 Series/LaserJet 4050 Series is 128"
::= { settings-file-system 2 }


file-system-set-system-partition-writeable OBJECT-TYPE
    SYNTAX  OCTET STRING
    MAX-ACCESS read-write
    STATUS  current
    DESCRIPTION
                "This object allows the system partition to be written to. It
                consists of a C structure containing the following fields:
                    typedef struct {
                    ubyte password[8];
                    ubyte volumenumber;
                    } fs_writeable_system_partition_t;
                    which is described below:
                    Bytes 0 - 7: contain the password
                    Byte 8 : is the volume number
                MAX-ACCESS to this command is controlled by the password. If the
                password supplied is incorrect the command will fail. The
                volumenumber is a volume number of an existing system
                partition.
                Additional information:
                Returns <noSuchName>
                status if attempting to access this object and there
                is no storage device is installed.
                Returns <badValue> if the password is incorrect or if
                		   the volume requested is not present."
::= { settings-file-system 6 }


file-system-set-system-partition-readonly OBJECT-TYPE
    SYNTAX  INTEGER
    MAX-ACCESS read-write
    STATUS  current
    DESCRIPTION
                "Changes a system partition to be READ-ONLY. The value is the
                volume number to change. If the volume number specified is NOT
                a system partition an error is returned.
                Additional information:
                Returns <noSuchName>
                status if attempting to access this object and there
                is no storage device is installed.
                Returns <badValue> if the volume requested
                		   is not present."
::= { settings-file-system 7 }


file-system-delete-files OBJECT-TYPE
    SYNTAX  OCTET STRING
    MAX-ACCESS read-write
    STATUS  current
    DESCRIPTION
                "Setting this object causes the specified filename to be
                deleted, after first validating that the authentication data is
                correct for the specified user ID.
                    The format for this object is a C structure:
                    typedef struct {
                    sint32 UserId;
                    uint16 AuthenticationDataLen
                    ubyte AuthenticationData[]
                    char Filename[];
                    } fs_delete_files_t;
                    which is described below:
                    Bytes 0 - 3: contains a user id represented as a multi-byte
                        value that is stored in big-endian format, where the
                        most significant byte occurs first.
                    Bytes 4 - 5 : Length of the Athentication data that follows
                        starting at offset 6. Stored as a multi-byte value that
                        is stored in big-endian format, where the most
                        significant byte occurs first.
                    Bytes 6 - 6+AuthenticationDataLen : a ubyte array
                        containing the Authentication data used to verify
                        MAX-ACCESS for this operation.
                    Bytes starting at offset (6+AuthenticationDataLen+1): A
                        null terminated character array representing the ASCII
                        file name to be deleted. The length of the string will
                        be limited by the remaining space in the object.
                This string represents a fully-qualified path name which may
                specify a filename or a regular expression that may match
                multiple files (e.g <path>/*.exe). Access to this command is
                controlled by the UserId and the authentication data. If the
                UserID or authentication data supplied is incorrect the command
                will fail. The device POS will specify any limitations to the
                length of the filename string, what constitutes a correct user
                ID, what constitutes correct authentication data, and the
                significance of any return values.
                Additional information:
                Setting this object causes the specified filename
                to be deleted, after first validating that the
                authentication data is correct for the specified
                user ID.  This object is always present.

                The format for this object is a C structure:

                typedef struct {
                sint32 UserId;
                uint16 AuthenticationDataLen
                ubyte  AuthenticationData[]
                char   Filename[];
                } fs_delete_files_t;

                Bytes 0 - 3: contains a user id represented
                as a multi-byte value that is stored in big-endian
                format, where the most significant byte occurs first.

                Bytes 4 - 5 : Length of the authentication data that
                follows starting at offset 6. Stored as a multi-byte
                value that is stored in big-endian format, where the
                most significant byte occurs first.

                Bytes 6 - 6+AuthenticationDataLen : a ubyte array
                containing the authentication data used to verify
                MAX-ACCESS for this operation.

                Bytes starting at offset (6+AuthenticationDataLen+1):
                A null terminated character array representing the
                ASCII file name to be deleted. The length of the
                string will be limited by the remaining space in the
                object.  This string represents a fully-qualified path
                name which may specify a filename or a file-type regular
                expression that may match multiple files (e.g.,
                <path>/*.exe).

                MAX-ACCESS to this command is controlled by the UserId
                and the authentication data.  If the UserID or
                authentication data supplied is incorrect the
                command will fail.

                The device POS will specify any limitations to the
                length of the filename string, what constitutes a
                correct user ID, what constitutes correct
                authentication data, and the significance of any
                return values."
::= { settings-file-system 8 }


file-system-security-access-password OBJECT-TYPE
    SYNTAX  DisplayString
    MAX-ACCESS read-write
    STATUS  current
    DESCRIPTION
                "This object acts as a gate keeper for write access to the PML
                objects FILE-SYSTEM-EXTERNAL-ACCESS-CAPABILITIES,
                FILE-SYSTEM-ERASE-MODE, and FILE-SYSTEM-WIPE-DISK. The object
                can be viewed as always being in one of 4 states:
                    State 0 --> Un-initialized:
                        FILE-SYSTEM-SECURITY-ACCESS-PASSWORD is the empty
                        string and a pmlget operation on the object will return
                        the string '0'. This will be the state after an NVRAM
                        init which is the only way to set the object to the
                        empty string. It cannot be set to the empty string
                        through PML. In this state write access to
                        FILE-SYSTEM-EXTERNAL-ACCESS-CAPABILITIES,
                        FILE-SYSTEM-ERASE-MODE and FILE-SYSTEM-WIPE-DISK is
                        disabled while write access to the object itself is
                        enabled. A successful set operation on the object in
                        this state will return the string 'SET' and will result
                        in a transition to State 3.
                    State 1 --> The Password is set to a non-empty string: A
                        pmlget operation on the object will return the string
                        '1' regardless of the actual stored password value. In
                        this state write access to
                        FILE-SYSTEM-EXTERNAL-ACCESS-CAPABILITIES,
                        FILE-SYSTEM-ERASE-MODE and FILE-SYSTEM-WIPE-DISK is
                        disabled. The only string the object itself can be
                        successfully set to while in this state is the current
                        value of the password. Setting the object to its
                        current value causes a transition to State 2 which is
                        an authenticated state. The value returned from such a
                        set operation will be the string 'OK'.
                    State 2 --> The password is in an authenticated state: The
                        'gate' to write to the PML objects
                        FILE-SYSTEM-EXTERNAL-ACCESS-CAPABILITIES,
                        FILE-SYSTEM-ERASE-MODE, and FILE-SYSTEM-WIPE-DISK is
                        open. One, and only one, write operation can be
                        performed on one of these three objects. During such a
                        write operation the object itself will transition to
                        State 1 thus closing the gate. In State 2 a pmlset
                        operation on the object will result in the password
                        being set and a transfer to State 3. The value returned
                        from a set operation in this state on
                        FILE-SYSTEM-SECURITY-ACCESS-PASSWORD will be 'SET'. A
                        pmlget operation on the object will return the string
                        '2' regardless of the actual password value.
                    State 3 --> The password was just changed: A pmlget
                        operation on the object will return the string '3'.
                        Otherwise behaviors in State 3 are exactly like in
                        State 1.   "
::= { settings-file-system 9 }


file-system-external-access-capabilities OBJECT-TYPE
    SYNTAX  OCTET STRING
    MAX-ACCESS read-write
    STATUS  current
    DESCRIPTION
                "This object is used to control access to the file system of the
                device. It is always readable. It is writable when
                FILE-SYSTEM-SECURITY-ACCESS-PASSWORD is not the empty string,
                and a successful write to that object with the current password
                has preceded the write to this object. In other words, the
                FILE-SYSTEM-SECURITY-ACCESS-PASSWORD must be in the
                'authenticated state' for a write on
                FILE-SYSTEM-EXTERNAL-ACCESS-CAPABILITIES to succeed. After the
                object has successfully been written to, it becomes read-only,
                and the FILE-SYSTEM-SECURITY-ACCESS-PASSWORD object exits the
                authenticated state. FILE-SYSTEM-SECURITY-ACCESS-PASSWORD must
                then be written to again with the current password in order to
                make another write operation on
                FILE-SYSTEM-EXTERNAL-ACCESS-CAPABILITIES possible.
                    cDisablePJLFileSystemAccess - All file system access
                        through PJL will be disabled.
                    cDisablePMLFileSystemWrite - All file-systems-related PML
                        objects such as FILE-SYSTEM-DELETE-FILES or
                        hrPartitionLabel become read-only. For objects that are
                        normally write-only this means that no successful
                        operations can now be performed on them.
                    cDisableNFSFileSystemAccess - All NFS file system access
                        will be disabled.
                    cDisablePSFileSystemAccess - All file system access through
                        PostScript will be disabled.
                    cDisableEWSFileSystemAccess - All access to the file system
                        by the Embedded Web Server will be disabled.   "
::= { settings-file-system 10 }


file-system-erase-mode OBJECT-TYPE
    SYNTAX  OCTET STRING
    MAX-ACCESS read-write
    STATUS  current
    DESCRIPTION
                "This object is used to control how file data is handled when
                files are deleted. It is always readable. It is writable when
                FILE-SYSTEM-SECURITY-ACCESS-PASSWORD is the empty string or
                when a write to FILE-SYSTEM-SECURITY-ACCESS-PASSWORD with the
                current password has preceeded the write to the object. When
                FILE-SYSTEM-SECURITY-ACCESS-PASSWORD is not the empty string
                then this object becomes read-only after a successful write to
                it. FILE-SYSTEM-SECURITY-ACCESS-PASSWORD must then be written
                to again with the current password in order to make another
                write operation on the object possible. If the
                FILE-SYSTEM-SECURITY-ACCESS-PASSWORD is incorrectly set, this
                object becomes read-only until the password is correctly set.
                The logical settings for this object are:
                    NonSecureFastErase - When a file is deleted, only the
                        reference to it in the file system tables is removed.
                        No file data is overwritten. This is the default
                        setting. This is the setting when both bits in the
                        collection are set to 0.
                    SecureFastErase - File information is overwritten with
                        identical, random character pattern when it is deleted.
                        This is the setting when cEraseMode0 is set to 1 and
                        cEraseMode1 is set to 0.
                    SecureSanitizeErase - Secure, repetitive algorithm used to
                        overwrite all deleted file information and remove any
                        residual data persistence. A random character is
                        written to all bytes of deleted sectors. Then the
                        complement of that character and finally, another
                        random character is written. This is the setting when
                        cEraseMode0 is set to 0 and cEraseMode1 is set to 1.
                Note that an error will be returned for an attempt to set both
                bits of the collection to 1."
::= { settings-file-system 11 }


file-system-wipe-disk OBJECT-TYPE
    SYNTAX  INTEGER
    MAX-ACCESS read-write
    STATUS  current
    DESCRIPTION
                "This object is a non-leaf node which will have one leaf node
                under it for each file system in the printer. The leaf nodes
                will be in a 1-to-1 correspondence with the hrDeviceIndex
                objects. This object specifies for each leaf node whether the
                file system on the device is going to be erased according to
                the setting of the FILE-SYSTEM-ERASE-MODE referenced by the
                corresponding hrDeviceIndex. A file system will be overwritten
                on system reboot if this object is set to 1. It will be
                unchanged if this object is set to 0. If this object's value is
                -1 then the file system cannot be wiped. If the file system
                contains the permstore, the permstore will be saved off and
                restored after the file-system wipe is completed. This object
                is always readable. It is writable when
                FILE-SYSTEM-SECURITY-ACCESS-PASSWORD is the empty string or
                when a write to FILE-SYSTEM-SECURITY-ACCESS-PASSWORD with the
                current password has preceeded the write to the object. When
                FILE-SYSTEM-SECURITY-ACCESS-PASSWORD is not the empty string
                then this object becomes read-only after a successful write to
                it. FILE-SYSTEM-SECURITY-ACCESS-PASSWORD must then be written
                to again with the current password in order to make another
                write operation on the object possible. If the
                FILE-SYSTEM-SECURITY-ACCESS-PASSWORD is incorrectly set, this
                object becomes read-only until the password is correctly set."
::= { settings-file-system 12 }


file-system-wipe-disk-status OBJECT-TYPE
    SYNTAX  INTEGER
    MAX-ACCESS read-only
    STATUS  current
    DESCRIPTION
                "This object is a non-leaf node which will have one leaf node
                under it for each file system in the printer. The leaf nodes
                will be in a 1-to-1 correspondence with the hrDeviceIndex
                objects. This object specifies for each leaf node the status of
                a disk wipe in progress. A return value of -1 indicates that no
                disk wipe is in progress. A return value in the range of 0 to
                100 indicates the percent done for a disk wipe in progress. All
                other values are illegal."
::= { settings-file-system 13 }

-- 1.3.6.1.4.1.11.2.3.9.4.2.1.1.4.6.1.4
web-proxy-config-enable   OBJECT-TYPE
    SYNTAX          INTEGER {
                              eOff(0),
                             eOn(1)
                    }
    MAX-ACCESS read-only
    STATUS            current
    DESCRIPTION " This object is a OCTET STRING enumeration which the peripheral uses
    to inform the JetDirect card that the Jet-Direct card embedded
    web server should display the web proxy configuration settings.
    The Jet Direct card web server will display the if and only if
    this object is both implemented and set to eOn. A peripheral
    may implement this object in order to have another host, like a
    JetDirect card, include a reference to the peripheral's web
    content. The peripheral will read the proxy configuration using
    the XIP2 sysInfo Get methods"
::= { settings-web-server 4 }

-- 1.3.6.1.4.1.11.2.3.9.4.2.1.1.4.6.1.5
ews-request-control-panel-supplies-status   OBJECT-TYPE
    SYNTAX          INTEGER {
                              eFalse(1),
                             eTrue(2)
                    }
    MAX-ACCESS read-write
    STATUS            current
    DESCRIPTION " System variable EWS_REQUEST_CONTROL_PANEL_SUPPPLIES_STATUS
    requires a PML interface so that WJA can directly access it
    without needing EWS support for that"
::= { settings-web-server 5 }

channelnumberofchannels OBJECT-TYPE
    SYNTAX  INTEGER
    MAX-ACCESS read-write
    STATUS  current
    DESCRIPTION
                "An indication of how many print data channels the I/O
                card supports.
                Additional information:
                This object is used by the IIO card to tell the
                peripheral firmware how many logical channels will be used by
                the card.  This object can only be set once per physical
                channel.  If an attempt is made to set it a subsequent time
                it is ignored and an return code of
                <genErr>.  is returned.
                If new firmware is dynamically downloaded to the I/O
                card, and if that firmware uses more logical channels, it is
                necessary to reset the printer."
::= { channel 1 }


channelprinteralert OBJECT-TYPE
    SYNTAX  OCTET STRING
    MAX-ACCESS read-only
    STATUS  current
    DESCRIPTION
                "Identifies the values of prtAlertIndex,
                prtAlertSeverityLevel, prtAlertGroup,
                prtAlertGroupIndex, prtAlertLocation, and prtAlertCode
                for the latest critical evnet in the prtAlertTable.  The
                binary string is defined as following:
                ------------------------------------------------------
                 Field | Filed  | Description
                Offset | Length |
                ------------------------------------------------------
                   0   |    4   | the value of prtAlertIndex
                   4   |    4   | the value of prtAlertSeverityLevel
                   8   |    4   | the value of prtAlertGroup
                  12   |    4   | the value of prtAlertGroupIndex
                  16   |    4   | the value of prtAlertLocation
                  20   |    4   | the value of prtAlertCode
                ------------------------------------------------------
                Each field is in Big Endian style.
                Additional information:
                This object is used to pass alert information
                from the peripheral to the IIO card.  The standard printer
                MIB contains the following description:

                printerAlert TRAP-TYPE
                ENTERPRISE printerV1Alert
                VARIABLES { prtAlertIndex, prtAlertSeverityLevel, prtAlertGroup,
                prtAlertGroupIndex, prtAlertLocation, prtAlertCode }
                DESCRIPTION
                'This trap is sent whenever a critical event is added to the
                prtAlertTable.'

                In order to provide this information in the trap packet, the
                IIO card enables traps on channelPrinterAlert.  When a
                critical alert is generated the peripheral fills the
                appropriate value into this object and sends it to the card.
                This object is a structure which contains 24 bytes of data.
                The structure is:

                struct structAlertInfo {
                sint32 prtAlertIndex;
                sint32 prtAlertSeverityLevel;
                sint32 prtAlertGroup;
                sint32 prtAlertGroupIndex;
                sint32 prtAlertLocation;
                sint32 prtAlertCode;
                } thisAlertData;"
::= { channel 2 }


channeltype OBJECT-TYPE
    SYNTAX  INTEGER {
		   eChOther(1),
		   eChAppleTalkPAP(7),
		   eChLPDServer(8),
		   eChNetwareRPrinter(9),
		   eChNetwarePServer(10),
		   eChPort9100(11),
		   eChDLCLLCPort(15),
		   eChBidirPortTCP(38)
		   }
    MAX-ACCESS read-write
    STATUS  current
    DESCRIPTION
                "Identifies the type of MIO print data channel.
                Additional information:
                After telling the peripheral how many logical
                channels will be used, the IIO card tells the printer the
                type of each of the channels.  The type information is passed
                using the channelType object.  Values are then saved by the
                peripheral and reported when users request the value of
                prtChannelType."
::= { channelEntry 2 }


channelprotocolversion OBJECT-TYPE
    SYNTAX  OCTET STRING
    MAX-ACCESS read-write
    STATUS  current
    DESCRIPTION
                "The version of the protocol used on this MIO print data
                channel.
                Additional information:
                After telling the peripheral how many logical
                channels will be used, the IIO card tells the printer the
                protocol version of each of the channels.  The protocol
                version information is passed using the
                channelProtocolVersion object.  Values are then saved by the
                peripheral and reported when users request the value of
                prtChannelProtocolVersion."
::= { channelEntry 3 }


channelstate OBJECT-TYPE
    SYNTAX  INTEGER {
		   eChOther(1),
		   eChPrintDataAccecped(3),
		   eChNoDataAccepted(4)
		   }
    MAX-ACCESS read-write
    STATUS  current
    DESCRIPTION
                "The state of this print data channel. The value
                determines whether control information and print data is
                allowed through this channel or not.
                Additional information:
                After telling the peripheral how many logical
                channels will be used, the IIO card tells the printer the
                state of each of the channels.  The state can change from
                time to time.  The state information is passed using the
                channelState object.  Values are saved by the peripheral and
                reported when users request the value of prtChannelState."
::= { channelEntry 4 }


channelifindex OBJECT-TYPE
    SYNTAX  INTEGER
    MAX-ACCESS read-write
    STATUS  current
    DESCRIPTION
                "The value of ifIndex which corresponds to this channel.
                Additional information:
                After telling the peripheral how many logical
                channels will be used, the IIO card tells the printer the
                value of the IfIndex for each channel.  The IfIndex is used
                as part of MIB-II.  The values are saved by the peripheral
                and reported when users request the value of
                prtChannelIfIndex."
::= { channelEntry 5 }


channelstatus OBJECT-TYPE
    SYNTAX  INTEGER
    MAX-ACCESS read-write
    STATUS  current
    DESCRIPTION
                "Sub-unit status is reported in the entries of the
                principle table in the Group that represents the sub-
                unit. For sub-units that report a status, there is a
                status column in the table and the value of this column
                is always an integer formed in the following way.
                The SubUnitStatus is an integer that is the sum of 5
                distinct values, Availability, Non-Critical, Critical,
                On-line, and Transitioning.  These values are:
                Availability                      value
                  Available and Idle              0       000'b
                  Available and Standby           2       010'b
                  Available and Active            4       100'b
                  Available and Busy              6       110'b
                  Unavailable and OnRequest       1       001'b
                  Unavailable because Broken      3       011'b
                  Unknown                         5       101'b
                Non-Critical
                  No Non-Critical Alerts          0
                  Non-Critical Alerts             8
                Critical
                  No Critical Alerts              0
                  Critical Alerts                 16
                On-Line
                  Intended state is On-Line       0
                  Intended state is Off-Line      32
                Transitioning
                  At intended state               0
                  Transitioning to intended state 64
                Additional information:
                After telling the peripheral how many logical
                channels will be used, the IIO card tells the printer the
                status of each of the channels.  The status can change from
                time to time.  The status information is passed using the
                channelStatus object.  Values are saved by the peripheral and
                reported when users request the value of prtChannelStatus."
::= { channelEntry 6 }


channelinformation OBJECT-TYPE
    SYNTAX  OCTET STRING
    MAX-ACCESS read-write
    STATUS  current
    DESCRIPTION
                "Auxiliary information to allow a printing application to
                use the channel for data submission to the printer.  An
                application capable of using a specific PrtChannelType
                should be able to use the combined information from the
                prtChannelInformation and other channel and interface
                group objects to 'bootstrap' its use of the channel.
                prtChannelInformation is not intended to provide a
                general channel description, nor to provide information
                that is available once the channel is in use.  The
                encoding and interpretation of the prtChannelInformation
                object is specific to channel type.  The description of
                each PrtChannelType enum value for which
                prtChannelInformation is defined specifies the
                appropriate encoding and interpretation, including
                interaction with other objects.  For channel types that
                do not specify a prtChannelInformation value, its value
                shall be null (0 length).   When a new PrtChannelType
                enumeration value is registered, its accompanying
                description must specify the encoding and interpretation
                of the prtChannelInformation value for the channel type.
                prtChannelInformation semantics for an existing
                PrtChannelType may be added or amended in the same
                manner as described in section 2.4.1 for type 2
                enumeration values.  The prtChannelInformation specifies
                values for a collection of channel attributes,
                represented as text according to the following rules:
                  1. The prtChannelInformation is coded in the NVT ASCII
                character set.  It is not affected by localization.
                  2. The prtChannelInformation is a list of entries
                representing the attribute values.  Each entry consists
                of the following items, in order:
                    a. a keyword, composed of alphabetic characters (A-
                Z, a-z), that identifies a channel attribute,
                    b. an Equals Sign (=) to delimit the keyword,
                    c. a data value, consisting of NVT ASCII graphics
                characters (codes 32-126),
                    d. a Line Feed character (code 10) to delimit the
                data value.
                  No other characters shall be present.  Keywords are
                case-sensitive.  Conventionally, keywords are
                capitalized (including each word of a multi-word
                keyword), and, since they occupy space in the
                prtChannelInformation, they are kept short.
                  3. If a channel attribute has multiple values, it is
                represented by multiple entries with the same keyword,
                each specifying one value.  Otherwise, there shall be at
                most one entry for each attribute.
                  4. By default, entries may appear in any order.  If
                there are ordering constraints for particular entries,
                these must be specified in their definitions.
                  5. The prtChannelInformation value may represent
                information that is not normally coded in textual form,
                or that is coded in a character set other than NVT
                ASCII.  In these cases, whatever symbolic representation
                is conventionally used for the information should be
                used for encoding the prtChannelInformation.  (For
                instance, a binary port value might be represented as a
                decimal number, Unicode would be represented in UTF-8
                format.)
                  6. For each PrtChannelType for which
                prtChannelInformation entries are defined, the
                descriptive text associated with the PrtChannelType
                enumeration value shall specify the following
                information for each entry:
                    Title: Brief description phrase, e.g.: 'Port
                name,'Service Name,'
                    Keyword: The keyword value, eg: 'Port,' 'Service'
                    Syntax: The encoding of the entry value, if it
                cannot be directly represented by NVT ASCII,
                    Status:  'Mandatory,' 'Optional,' or 'Conditionally
                Mandatory,'
                    Multiplicity: 'Single' or 'Multiple,' to indicate
                whether the entry may be present multiple times,
                    Description: Description of the use of the entry,
                other information required to complete the definition
                (e.g.: ordering contstraints, interactions between
                entries).
                Applications that interpret prtChannelInformation should
                ignore unrecognized entries, so they are not affected if
                new entry types are added.
                Additional information:
                After telling the peripheral how many logical
                channels will be used, the IIO card tells the printer the
                value of the information value of each of the channels.  The
                information is auxiliary information used in conjunction with
                the channel Type."
::= { channelEntry 7 }


channel-bytes-sent OBJECT-TYPE
    SYNTAX  INTEGER
    MAX-ACCESS read-only
    STATUS  current
    DESCRIPTION
                "The low order 31 bits of the number of bytes sent from
                the printer to the host on this logical channel."
::= { channel-entry 2 }


channel-bytes-received OBJECT-TYPE
    SYNTAX  INTEGER
    MAX-ACCESS read-only
    STATUS  current
    DESCRIPTION
                "The low order 31 bits of the number of bytes received by
                the printer from the host on this logical channel."
::= { channel-entry 3 }


channel-io-errors OBJECT-TYPE
    SYNTAX  INTEGER
    MAX-ACCESS read-only
    STATUS  current
    DESCRIPTION
                "The low order 31 bits of the number of I/O errors which
                have occured on this logical channel."
::= { channel-entry 4 }


channel-jobs-received OBJECT-TYPE
    SYNTAX  INTEGER
    MAX-ACCESS read-only
    STATUS  current
    DESCRIPTION
                "The low order 31 bits of the number of print jobs which
                have been received on this logical channel."
::= { channel-entry 5 }


channel-mio OBJECT-TYPE
    SYNTAX  INTEGER
    MAX-ACCESS read-only
    STATUS  current
    DESCRIPTION
                "The number of the MIO card associated with this logical
                channel.  If this logical channel is not associated with
                an MIO card a zero is returned.  The value returned for
                each logical channel is the  MIO card's physical slot
                number.    The list of supported values should be
                documented in the device POS.
                Additional information:
                The value returned will be zero for channels 1..3.
                If an MIOA card is installed, channels 4..10 will
                return a value of one or two.
                If an MIOB card is installed, channels 11..17 will
                return a value of one or two but not the
                same as channels 4..10.
                When two IIO cards are installed, the value
                returned by any channel 4..17 may change after the
                printer is power cycled."
::= { channel-entry 6 }


prtchanneltype OBJECT-TYPE
    SYNTAX  INTEGER {
		   ePother(1),
		   ePchSerialPort(3),
		   ePchIEEE1284Port(5),
		   ePchAppleTalkPAP(7),
		   ePchNetwareRPrinter(9),
		   ePchNetwarePServer(10),
		   ePchBidirPortTCP(38),
		   ePchDLCLLCPort(15)
		   }
    MAX-ACCESS read-only
    STATUS  current
    DESCRIPTION
                "The type of this print data channel.  This
        object provides the linkage to ChannelType-specific
        groups that may (conceptually) extend the prtChannelTable
        with additional details about that channel.
	Refer to Standard Printer MIB for more details.
                Additional information:
                This object, in conjunction with prtChannelProtocolVersion,
                replaces the PML object PORTn-DESCRIPTION.
                IIO based channels provide their own values."
::= { prtChannelEntry 2 }


prtchannelprotocolversion OBJECT-TYPE
    SYNTAX  OCTET STRING (SIZE(0..63))
    MAX-ACCESS read-only
    STATUS  current
    DESCRIPTION
                "The version of the protocol used on this
        channel.  The format used for version numbering depends
        on prtChannelType.
	Refer to Standard Printer MIB for more details.
                Additional information:
                This object, in conjunction with prtChannelType,
                replaces the PML object PORTn-DESCRIPTION.
                IIO-based channels provide their own values.
                The channel 1 value includes (separated by semi colons)
                different aspectsof the spec:  electrical: logical; and
                physical connector."
::= { prtChannelEntry 3 }


prtchannelcurrentjobcntllangindex OBJECT-TYPE
    SYNTAX  INTEGER
    MAX-ACCESS read-only
    STATUS  current
    DESCRIPTION
                "The value of prtInterpreterIndex  corresponding to the
        Control Language Interpreter for this channel. This
        interpreter defines the syntax used for control
        functions, such as querying or changing environment
        variables and identifying job boundaries (e.g. PJL,
        PostScript, NPAP). Must be 1 or greater.
	Refer to Standard Printer MIB for more details.
                Additional information:
                This object points to the PJL language. It is
                read-only because PJL is the printer's only job
                control language."
::= { prtChannelEntry 4 }


prtchanneldefaultpagedesclangindex OBJECT-TYPE
    SYNTAX  INTEGER
    MAX-ACCESS read-write
    STATUS  current
    DESCRIPTION
                "The value of prtInterpreterIndex  corresponding to the
        Page Description Language Interpreter for this channel.
        This interpreter defines the default Page Description
        Language interpreter to be used for the print data unless
        the Control Language is used to select a specific
        interpreter (e.g.,  PCL, PostScript Language,
        auto-sense). Must be 1 or greater.
	Refer to Standard Printer MIB for more details.
                Additional information:
                Replaces PML DEFAULT-PDL.  The default points to the
                automatic language switcher. If this object is changed
                for one channel, all channels will be changed."
::= { prtChannelEntry 5 }


prtchannelstate OBJECT-TYPE
    SYNTAX  INTEGER {
		   ePother(1),
		   ePprintDataAccepted(3),
		   ePnoDataAccepted(4)
		   }
    MAX-ACCESS read-only
    STATUS  current
    DESCRIPTION
                "The state of this print data channel.  The value determines
        whether control information and print data is allowed through
        this channel or not.
	Refer to Standard Printer MIB for more details.
                Additional information:
                IIO-based channels provide their own values for this
                object.  The base-printer's ports always report a value of
                ePprintDataAccepted.
                If the printer is offline, that is detected by reading the
                Host Resources General Printer Status objects, not by reading
                this object."
::= { prtChannelEntry 6 }


prtchannelifindex OBJECT-TYPE
    SYNTAX  INTEGER
    MAX-ACCESS read-only
    STATUS  current
    DESCRIPTION
                "The value of ifIndex (in the ifTable; see the interface
        section of MIB-2/RFC 1213) which corresponds to this channel.
        When more than one row of the ifTable is relevant, this is
        the index of the row representing the topmost layer in the
        interface hierarchy.  A value of zero indicates that no
        interface is associated with this channel.
	Refer to Standard Printer MIB for more details.
                Additional information:
                IIO-based channels provide their own values for this
                object."
::= { prtChannelEntry 7 }


prtchannelstatus OBJECT-TYPE
    SYNTAX  INTEGER
    MAX-ACCESS read-only
    STATUS  current
    DESCRIPTION
                "The current status of the channel.
	Refer to Standard Printer MIB for more details.
                Additional information:
                IIO-based channels provide their own values for this
                object."
::= { prtChannelEntry 8 }


prtchannelinformation OBJECT-TYPE
    SYNTAX  OCTET STRING (SIZE(0..255))
    MAX-ACCESS read-only
    STATUS  current
    DESCRIPTION
                "Auxiliary information to allow a printing application to use
        the channel for data submission to the printer.  An application
        capable of using a specific PrtChannelType should be able to use
        the combined information from the prtChannelInformation and
        other channel and interface group objects to 'bootstrap' its use
        of the channel.  prtChannelInformation is not intended to
        provide a general channel description, nor to provide
        information that is available once the channel is in use.
        The encoding and interpretation of the prtChannelInformation
        object is specific to channel type.  The description of each
        PrtChannelType enum value for which prtChannelInformation is
        defined specifies the appropriate encoding and interpretation,
        including interaction with other objects.  For channel types
        that do not specify a prtChannelInformation value, its value
        shall be null (0 length).
        When a new PrtChannelType enumeration value is registered, its
        accompanying description must specify the encoding and
        interpretation of the prtChannelInformation value for the
        channel type.  prtChannelInformation semantics for an existing
        PrtChannelType may be added or amended in the same manner as
        described in section 2.4.1 for type 2 enumeration values.
        The prtChannelInformation specifies values for a collection of
        channel attributes, represented as text according to the
        following rules:
         1. The prtChannelInformation is coded in the NVT ASCII
            character set.  It is not affected by localization.
         2. The prtChannelInformation is a list of entries representing
            the attribute values.  Each entry consists of the following
            items, in order:
             a. a keyword, composed of alphabetic characters (A-Z,
                a-z), that identifies a channel attribute,
             b. an Equals Sign (=) to delimit the keyword,
             c. a data value, consisting of NVT ASCII graphics
                characters (codes 32-126),
             d. a Line Feed character (code 10) to delimit the data
                value.
            No other characters shall be present.
            Keywords are case-sensitive.  Conventionally, keywords are
            capitalized (including each word of a multi-word keyword),
            and, since they occupy space in the prtChannelInformation,
            they are kept short.
         3. If a channel attribute has multiple values, it is
            represented by multiple entries with the same keyword, each
            specifying one value.  Otherwise, there shall be at most
            one entry for each attribute.
         4. By default, entries may appear in any order.  If there are
            ordering constraints for particular entries, these must be
            specified in their definitions.
         5. The prtChannelInformation value may represent information
            that is not normally coded in textual form, or that is coded
            in a character set other than NVT ASCII.  In these cases,
            whatever symbolic representation is conventionally used for
            the information should be used for encoding the
            prtChannelInformation.  (For instance, a binary port value
            might be represented as a decimal number, Unicode would
            be represented in UTF-8 format.)
         6. For each PrtChannelType for which prtChannelInformation
            entries are defined, the descriptive text associated with the
            PrtChannelType enumeration value shall specify the following
            information for each entry:
            Title:          Brief description phrase, e.g.: 'Port name',
                            'Service Name',
            Keyword:        The keyword value, eg: 'Port', 'Service'
            Syntax:         The encoding of the entry value, if it
                            cannot be directly represented by NVT ASCII,
            Status:         'Mandatory', 'Optional', or 'Conditionally
                            Mandatory',
            Multiplicity:   'Single' or 'Multiple', to indicate whether
                            the entry may be present multiple times,
            Description:    Description of the use of the entry, other
                            information required to complete the
                            definition (e.g.: ordering contstraints,
                            interactions between entries).
        Applications that interpret prtChannelInformation should ignore
        unrecognized entries, so they are not affected if new entry
        types are added.

	Refer to Standard Printer MIB for more details.
                Additional information:
                IIO-based channels provide their own values for this
                object."
::= { prtChannelEntry 9 }


job-info-outbins-used OBJECT-TYPE
    SYNTAX  OCTET STRING
    MAX-ACCESS read-only
    STATUS  current
    DESCRIPTION
                "Indicates which output bins this job has delivered
                printed pages to.  The last OID field for this dynamic
                object contains the job ID.
                Additional information:
                The bins designated by this collection include
                the printer's own output bins as well as the `logical output
                bins' associated with any attached external paper handling
                devices.  (The mapping of the physical output bins of an
                external paper handling device to its `logical output bins'
                depends on the usage mode of the device.  For instance, in
                `mailbox mode', there is one-to-one correspondence of
                `logical output bins' to physical bins, whereas in `stacker
                mode', one `logical output bin' may map to several physical
                bins.)

                Although LaserJet 5000 Series and LaserJet 4000 Series both come with two output
                bins -- a face-down bin on the top of the device and a
                face-up bin at the back of the device -- firmware will not
                provide a means of selecting between the two, nor will it
                report which of the two gets used.  For this reason, bit 0
                (cOutbin1) of this collection is being used to designate
                both of these bins together."
::= { job-info 20 }


job-info-physical-outbins-used OBJECT-TYPE
    SYNTAX  OCTET STRING
    MAX-ACCESS read-only
    STATUS  current
    DESCRIPTION
                "Indicates which physical output bins this job has
                delivered printed pages to.  The last OID field for this
                dynamic object contains the job ID.
                Additional information:
                The output bins designated by the bits of
                this collection include the standard output bin(s) plus the
                physical bins of attached external paper handling devices.
                The configuration (if any) of external paper handling devices
                will determine the mapping of individual bits in this
                collection to the physical bins of the devices.
                For LaserJet 4050 Series (LaserJet 4050), the cOutbin1 is used for Face Down
                bin, cOutbin2 is used for Face Up bin, and 3-15 are used for
                the 13 optional output bins (12 plus an extension to the Face
                Up bin) for backwards compatibility with LaserJet 8000 Series/LaserJet 8100 Series and
                forwards compatibility with future printers.  However, since LaserJet 4050 Series
                cannot distinguish output going to the Face Up or Face Down
                bin in the firmware because the diverter can only be moved
                manually, bit 0 (cOutbin1) is being used to designate
                both of these bits together.  If an external paper handling
                output device is connected, then bit 2 (cOutbin3) will
                represent the device's first output bin (and so on)."
::= { job-info 22 }

-- 1.3.6.1.4.1.11.2.3.9.4.2.1.1.16.4.1.1.
printed-modes-mono-count   OBJECT-TYPE
    SYNTAX          INTEGER
    MAX-ACCESS read-only
    STATUS            current
    DESCRIPTION " Total number of mono pages printed in this fuser mode"
::= { printed-modes-usage 1 }

-- 1.3.6.1.4.1.11.2.3.9.4.2.1.1.16.4.1.3.
printed-modes-color-count   OBJECT-TYPE
    SYNTAX          INTEGER
    MAX-ACCESS read-only
    STATUS            current
    DESCRIPTION " Total number of color pages printed in this fuser mode"
::= { printed-modes-usage 3 }

-- 1.3.6.1.4.1.11.2.3.9.4.2.1.1.16.4.1.5.
printed-modes-total-count   OBJECT-TYPE
    SYNTAX          INTEGER
    MAX-ACCESS read-only
    STATUS            current
    DESCRIPTION " The total count for pages printed in this fuser mode"
::= { printed-modes-usage 5 }

printed-media-simplex-count OBJECT-TYPE
    SYNTAX  INTEGER(0..930576247)
    MAX-ACCESS read-only
    STATUS  current
    DESCRIPTION
                "Total number of simplex pages printed in this media
                size.
                Additional information:
                The 5 usage (simplex/duplex count, simplex/duplex click
                charge and paper size total) objects described here and
                below detail the usage for the printer for each paper
                size defined in the PCL Implementor's Guide and in the
                Media Size Table in the hpmib.txt.  The OID binding is
                based on the click attribute and paper size.
                For example:

                The format for the OID is as follows:

                3.4.1.5.x.y
                <-----> | |
                |    |  \
                /     |  paper size
                /       \
                PRINTER-CLICK_TOTALS ROOT   \
                OID                      click attribute 1..5

                x values are 1..5:

                1) simplex count
                2) simplex click charge
                3) duplex count
                4) duplex click charge
                5) printer or scanner paper size total (i.e. depends if the
                root OID is referrring to the printer or scanner).

                y : paper size as defined in the Media Size Table in the
                hpmib.txt "
::= { printed-media-usage 1 }


printed-media-simplex-charge OBJECT-TYPE
    SYNTAX  INTEGER
    MAX-ACCESS read-write
    STATUS  current
    DESCRIPTION
                "Charge for each simplex page printed in this media
                size."
::= { printed-media-usage 2 }


printed-media-duplex-count OBJECT-TYPE
    SYNTAX  INTEGER(0..930576247)
    MAX-ACCESS read-only
    STATUS  current
    DESCRIPTION
                "Total number of duplex pages printed in this media
                size."
::= { printed-media-usage 3 }


printed-media-duplex-charge OBJECT-TYPE
    SYNTAX  INTEGER
    MAX-ACCESS read-write
    STATUS  current
    DESCRIPTION
                "Charge for each duplex page printed in this media size.
                Additional information:
                The click charges for duplex printed media."
::= { printed-media-usage 4 }


printed-media-total-charge OBJECT-TYPE
    SYNTAX  INTEGER
    MAX-ACCESS read-only
    STATUS  current
    DESCRIPTION
                "The total charge for pages printed in this media size."
::= { printed-media-usage 5 }

-- 1.3.6.1.4.1.11.2.3.9.4.2.1.1.16.1.1.7.
printed-media-combined-total   OBJECT-TYPE
    SYNTAX          INTEGER
    MAX-ACCESS read-write
    STATUS            current
    DESCRIPTION " Total number of letter equivalently weighted pages both color
    and mono combined with this printer"
::= { printed-media-usage 7 }

-- 1.3.6.1.4.1.11.2.3.9.4.2.1.1.16.1.1.10.
printed-media-dimplex-count   OBJECT-TYPE
    SYNTAX          INTEGER
    MAX-ACCESS read-only
    STATUS            current
    DESCRIPTION " Total number of mono dimplex pages printed in this media size.
    A dimplex page is one that has been printed in duplex mode but
    the back side is blank. Dimplex pages occur when the printer
    firmware inserts a blank page in order to complete a duplexed
    job which is sent to the printer with an odd number of pages"
::= { printed-media-usage 10 }

-- 1.3.6.1.4.1.11.2.3.9.4.2.1.1.16.1.1.11.
printed-media-combined-simplex-count   OBJECT-TYPE
    SYNTAX          INTEGER
    MAX-ACCESS read-only
    STATUS            current
    DESCRIPTION " Total number of simplex pages printed on this media size"
::= { printed-media-usage 11 }

-- 1.3.6.1.4.1.11.2.3.9.4.2.1.1.16.1.1.12.
printed-media-combined-duplex-count   OBJECT-TYPE
    SYNTAX          INTEGER
    MAX-ACCESS read-only
    STATUS            current
    DESCRIPTION " Total number of duplex pages printed on this media size"
::= { printed-media-usage 12 }

-- 1.3.6.1.4.1.11.2.3.9.4.2.1.1.16.1.1.15
impression-based-duplex-count-supported   OBJECT-TYPE
    SYNTAX          INTEGER {
                              eFalse(1),
                             eTrue(2)
                    }
    MAX-ACCESS read-only
    STATUS            current
    DESCRIPTION " The object is used to get the information on new duplex
    counting mechanism. With this new mechanism the Duplex count
    would represent actual Duplex count and not half of the count.
    eTrue means feature is available for the user"
::= { printed-media-usage 15 }

-- 1.3.6.1.4.1.11.2.3.9.4.2.1.1.16.5.1.1.
source-tray-usage-count   OBJECT-TYPE
    SYNTAX          INTEGER
    MAX-ACCESS read-only
    STATUS            current
    DESCRIPTION " Total number of pages printed from this source tray"
::= { source-tray-usage 1 }

-- 1.3.6.1.4.1.11.2.3.9.4.2.1.1.16.6.1.1.
destination-bin-usage-count   OBJECT-TYPE
    SYNTAX          INTEGER
    MAX-ACCESS read-only
    STATUS            current
    DESCRIPTION " Total number of pages printed to this destination bin"
::= { destination-bin-usage 1 }

-- 1.3.6.1.4.1.11.2.3.9.4.2.1.1.16.1.14.2.
print-meter-usage-threshold   OBJECT-TYPE
    SYNTAX          INTEGER
    MAX-ACCESS read-only
    STATUS            current
    DESCRIPTION " A value indicating the threshold value for this category of
    pages. The device POS will indicate the units of measure for
    this threshold value"
::= { print-meter-usage 2 }

-- 1.3.6.1.4.1.11.2.3.9.4.2.1.1.16.1.14.3.
print-meter-print-quality   OBJECT-TYPE
    SYNTAX          INTEGER {
                              ePrintQualityMono(1),
                             ePrintQualityGood(2),
                             ePrintQualityBest(3)
                    }
    MAX-ACCESS read-only
    STATUS            current
    DESCRIPTION " This enumeration describes the selected print quality for this
    category of printed pages
         "
::= { print-meter-usage 3 }

-- 1.3.6.1.4.1.11.2.3.9.4.2.1.1.16.1.14.4
print-meter-simplex-count   OBJECT-TYPE
    SYNTAX          INTEGER
    MAX-ACCESS read-only
    STATUS            current
    DESCRIPTION " Total number of simplex pages printed for this category of
    printed pages"
::= { print-meter-usage 4 }

-- 1.3.6.1.4.1.11.2.3.9.4.2.1.1.16.1.14.5
print-meter-duplex-count   OBJECT-TYPE
    SYNTAX          INTEGER
    MAX-ACCESS read-only
    STATUS            current
    DESCRIPTION " Total number of duplex pages printed for this category of
    printed pages"
::= { print-meter-usage 5 }

-- 1.3.6.1.4.1.11.2.3.9.4.2.1.1.16.1.14.6
print-meter-total-charge   OBJECT-TYPE
    SYNTAX          INTEGER
    MAX-ACCESS read-only
    STATUS            current
    DESCRIPTION " Total number of simplex plus duplex pages printed multiplied by
    the unit charge for each given media size for this category of
    printed pages"
::= { print-meter-usage 6 }

-- 1.3.6.1.4.1.11.2.3.9.4.2.1.1.16.1.14.7
print-meter-dimplex-count   OBJECT-TYPE
    SYNTAX          INTEGER
    MAX-ACCESS read-only
    STATUS            current
    DESCRIPTION " Total number of dimplex pages printed for this category of
    printed pages"
::= { print-meter-usage 7 }

-- 1.3.6.1.4.1.11.2.3.9.4.2.1.1.16.1.14.8.
print-meter-simplex-total   OBJECT-TYPE
    SYNTAX          INTEGER
    MAX-ACCESS read-only
    STATUS            current
    DESCRIPTION " Total number of simplex pages printed for this category of
    printed pages"
::= { print-meter-usage 8 }

-- 1.3.6.1.4.1.11.2.3.9.4.2.1.1.16.1.14.9.
print-meter-duplex-total   OBJECT-TYPE
    SYNTAX          INTEGER
    MAX-ACCESS read-only
    STATUS            current
    DESCRIPTION " Total number of duplex pages printed for this category of
    printed pages"
::= { print-meter-usage 9 }

-- 1.3.6.1.4.1.11.2.3.9.4.2.1.1.16.1.14.10.
print-meter-category-total   OBJECT-TYPE
    SYNTAX          INTEGER
    MAX-ACCESS read-only
    STATUS            current
    DESCRIPTION " Total number of simplex plus duplex pages printed for this
    category of printed pages"
::= { print-meter-usage 10 }

-- 1.3.6.1.4.1.11.2.3.9.4.2.1.1.16.1.14.11.
print-meter-dimplex-total   OBJECT-TYPE
    SYNTAX          INTEGER
    MAX-ACCESS read-only
    STATUS            current
    DESCRIPTION " Total number of dimplex pages printed for this category of
    printed pages"
::= { print-meter-usage 11 }

-- 1.3.6.1.4.1.11.2.3.9.4.2.1.1.16.3.1.1.
printed-media-color-simplex-count   OBJECT-TYPE
    SYNTAX          INTEGER
    MAX-ACCESS read-only
    STATUS            current
    DESCRIPTION " Total number of color simplex pages printed in this media
    size"
::= { printed-media-color-usage 1 }

-- 1.3.6.1.4.1.11.2.3.9.4.2.1.1.16.3.1.3.
printed-media-color-duplex-count   OBJECT-TYPE
    SYNTAX          INTEGER
    MAX-ACCESS read-only
    STATUS            current
    DESCRIPTION " Total number of color duplex pages printed in this media size"
::= { printed-media-color-usage 3 }

-- 1.3.6.1.4.1.11.2.3.9.4.2.1.1.16.3.1.5.
printed-media-color-total-count   OBJECT-TYPE
    SYNTAX          INTEGER
    MAX-ACCESS read-only
    STATUS            current
    DESCRIPTION " The total count for color pages printed in this media size"
::= { printed-media-color-usage 5 }

-- 1.3.6.1.4.1.11.2.3.9.4.2.1.1.16.3.1.6.
printed-media-color-dimplex-count   OBJECT-TYPE
    SYNTAX          INTEGER
    MAX-ACCESS read-only
    STATUS            current
    DESCRIPTION " Total number of color dimplex pages printed in this media size.
    A color dimplex page is a color page that has been printed in
    duplex mode but the back side is blank. Dimplex pages occur
    when the printer firmware inserts a blank page in order to
    complete a duplexed job which is sent to the printer with an
    odd number of pages"
::= { printed-media-color-usage 6 }

firmware-download-write-status-supported OBJECT-TYPE
    SYNTAX  INTEGER {
		   eFalse(1),
		   eTrue(2)
		   }
    MAX-ACCESS read-only
    STATUS  current
    DESCRIPTION
                "This object provides information on whether the printer has the
                ability to communicate the write-status of the firmware
                download while the download is taking place."
::= { firmware-download 1 }


firmware-download-write-time OBJECT-TYPE
    SYNTAX  INTEGER
    MAX-ACCESS read-only
    STATUS  current
    DESCRIPTION
                "If the design of the firmware-download implementation does not
                allow PML interaction during the download process, this value
                provides an estimation of the time where the printer will not
                be able to engage in PML communication.
                Additional information:
                If the design of the firmware-download
                			implementation does not allow PML interaction during
                			the download process, this value provides an
                			estimation of the time where the printer will not be
                			able to engage in PML communication. The calculated
                			time is expected to be 140 secs. However, this time
                			may increase as high as 280 secs as the flash part
                			nears the maximum flash count."
::= { firmware-download 2 }


firmware-download-write-count OBJECT-TYPE
    SYNTAX  INTEGER
    MAX-ACCESS read-only
    STATUS  current
    DESCRIPTION
                "Tells the number of times that firmware has been downloaded to
                the flash part.
                Additional information:
                Tells the number of times that firmware has been
                	downloaded to the flash part. The default value will
                			vary depending on how many times the firmware is
                			rolled before shipping."
::= { firmware-download 3 }


firmware-download-current-state OBJECT-TYPE
    SYNTAX  INTEGER {
		   eIdle(1),
		   eReceivingImage(2),
		   eReceivedImageError(3),
		   eVerifyingImage(4),
		   eVerifiedImageError(5),
		   eWritingImage(6),
		   eWritingImageError(7),
		   eDownloadComplete(8),
		   eOKtoShutDown(9),
		   eCancelDownload(10),
		   eShuttingDown(11)
		   }
    MAX-ACCESS read-write
    STATUS  current
    DESCRIPTION
                "Provides the current or last reportable state of the firmware
                download process. The current state may not necessarily be the
                current state, but could be the post-mortem state."
::= { firmware-download 4 }


firmware-download-maximum-write-count OBJECT-TYPE
    SYNTAX  INTEGER
    MAX-ACCESS read-only
    STATUS  current
    DESCRIPTION
                "Reports the manufacturer specified number of times that
                firmware can be downloaded to the flash part. A value of -1
                means that there is no limit. A value of 0 means that
                downloading firmware is not permitted by this part. Any other
                positive integer value corresponds to the number of times that
                firmware can be downloaded to the flash part.
                Additional information:
                Reports the manufacturer specified number of
                			times that firmware can be downloaded to the flash
                			part.  A value of -1 means that there is no limit.
                			A value of 0 means that downloading firmware is not
                			permitted by this part.  Any other positive integer
                			value corresponds to the number of times that
                			firmware can be downloaded to the flash part. The
                			current maximum write count is 500. This may change
                			as flash technology evolves."
::= { firmware-download 5 }


firmware-download-name OBJECT-TYPE
    SYNTAX  DisplayString
    MAX-ACCESS read-only
    STATUS  current
    DESCRIPTION
                "This returns the name of the printer. This should match the
                name in the header of the upgrade image being sent to the flash
                part. If the name does not match with the name returned then
                the image that we are attempting to download does not upgrade
                the printer firmware.
                Additional information:
                This object returns the HP name of the printer.
                			     This should match what is in the PJL header of the RFU job
                			     Web Jet Admin uses this to ensure the printer is available
                		   	     to be upgraded."
::= { firmware-download 6 }


firmware-download-version OBJECT-TYPE
    SYNTAX  DisplayString
    MAX-ACCESS read-only
    STATUS  current
    DESCRIPTION
                "This object will return a string value representing the current
                revision of firmware that the printer is operating with. This
                is used to determine if code needs to be upgraded when an
                firmware bundle comes in, in an upgrade job.
                Additional information:
                Web Jet Admin uses the version string that is returned to
                			     determine what peices of an RFU bundle need to be upgraded
                			     when an RFU job is being built. This objects will return
                			     the version string of the printer."
::= { firmware-download 7 }


upgradable-devices-write-status-supported OBJECT-TYPE
    SYNTAX  INTEGER {
		   eFalse(1),
		   eTrue(2)
		   }
    MAX-ACCESS read-only
    STATUS  current
    DESCRIPTION
                "This object provides information on whether the upgradable
                device has the ability to communicate the write-status of the
                upgrade while the upgrade is taking place."
::= { upgradable-devices 1 }


upgradable-devices-write-time OBJECT-TYPE
    SYNTAX  INTEGER
    MAX-ACCESS read-only
    STATUS  current
    DESCRIPTION
                "If the design of the device upgrade implementation does not
                allow PML interaction during the download process, this value
                provides an estimation of the time where the device will not
                be able to engage in PML communication.  The time returned
                will depend upon what device is attempting to be upgraded."
::= { upgradable-devices 2 }


upgradable-devices-write-count OBJECT-TYPE
    SYNTAX  INTEGER
    MAX-ACCESS read-only
    STATUS  current
    DESCRIPTION
                "Tells the number of times that firmware for device X has been
                downloaded to the flash part.  The default value will vary
                depending on how many times the firmware is rolled before
                shipping."
::= { upgradable-devices 3 }


upgradable-devices-current-state OBJECT-TYPE
    SYNTAX  INTEGER {
		   eIdle(1),
		   eReceivedImage(2),
		   eReceivedImageError(3),
		   eVerifiedImage(4),
		   eVerifiedImageError(5),
		   eWritingImage(6),
		   eWritingImageError(7),
		   eUpgradeComplete(8)
		   }
    MAX-ACCESS read-only
    STATUS  current
    DESCRIPTION
                "Provides the current or last reportable state of the device
                upgrade process.  The current state may not necessarily be the
                current state, but could be the post-mortem state."
::= { upgradable-devices 4 }


upgradable-devices-max-write-count OBJECT-TYPE
    SYNTAX  INTEGER
    MAX-ACCESS read-only
    STATUS  current
    DESCRIPTION
                "Reports the manufacturer specified number of times that
                firmware for device X can be downloaded to the flash part.  A
                value of -1 means that there is no limit.  A value of 0 means
                that downloading firmware is not permitted by this part.  Any
                other positive integer value corresponds to the number of
                times that the firmware for device X can be downloaded to the
                flash part.  The current maximum write count is 500.  This may
                change as flash technology evolves."
::= { upgradable-devices 5 }


upgradable-devices-name OBJECT-TYPE
    SYNTAX  DisplayString
    MAX-ACCESS read-only
    STATUS  current
    DESCRIPTION
                "This returns the name of the upgradable device.  This should
                match the name in the header of the upgrade image being sent
                to the flash part.  If the name does not match with any of the
                names returned then the device that we are attempting to
                upgrade is unavailable for upgrading.
                Additional information:
                This object returns the HP name of the printer and the upgradable
                			     devices. There is one Name object per upgradable device.
                			     This should match what is in the PJL header of the RFU job
                			     Web Jet Admin uses this to ensure the printer or device  is
                			     available to be upgraded."
::= { upgradable-devices 6 }


upgradable-devices-version OBJECT-TYPE
    SYNTAX  DisplayString
    MAX-ACCESS read-only
    STATUS  current
    DESCRIPTION
                "This object will return a string value representing the
                current revision of firmware that device X is operating with.
                This is used to determine if code needs to be upgraded when an
                firmware bundle comes in, in an upgrade job.
                Additional information:
                Web Jet Admin uses the version string that is returned to
                			     determine what peices of an RFU bundle need to be upgraded
                			     when an RFU job is being built. This internal object will
                			     return the current version string of the printer or device
                			     that it corresponds to."
::= { upgradable-devices 7 }


remote-upgrade-enable OBJECT-TYPE
    SYNTAX  INTEGER {
		   eOff(1),
		   eOn(2)
		   }
    MAX-ACCESS read-write
    STATUS  current
    DESCRIPTION
                "Enables or disables the ability to upgrade the firmware
                associated with any device that is available to be upgraded.
                This will be set to on or off at the RFU level in that if this
                mode is on any available device can be upgraded and if this
                mode is off none of the devices can be upgraded.  There is not
                an individual mode for each device.  Trying to set this to a
                value other than eOn or eOff will cause an UnsupportedValue
                error to occur."
::= { upgradable-devices 8 }


END
