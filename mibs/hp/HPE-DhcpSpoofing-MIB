HPE-DhcpSpoofing-MIB DEFINITIONS ::= BEGIN

-- Title:               HPE LOCALIZATION ROS
--                      This Private MIB supports the dhcp spoofing feature
-- Version:             7.39.02.03
-- Date:                15 May 2006



IMPORTS
    nm                                     FROM HPE-MIB
    OBJECT-TYPE,
    MODULE-IDENTITY                         FROM SNMPv2-SMI
    PortList, dot1qVlanIndex                FROM Q-BRIDGE-MIB
    TruthValue                              FROM SNMPv2-TC;



rlDhcpSpoofing MODULE-IDENTITY
         LAST-UPDATED "200605150000Z"
         ORGANIZATION "HPE"
         CONTACT-INFO
			"HPE"
         DESCRIPTION
                "The private MIB module definition for DhcpSpoofing."
         REVISION "200605150000Z"
         DESCRIPTION
                "Initial revision."
        ::= { nm 113 }

rlDhcpSpoofingServerPorts OBJECT-TYPE
    SYNTAX      PortList
    MAX-ACCESS  read-write
    STATUS      current
    DESCRIPTION
        "Each bit that is set in this portList represent a port that
        A dhcp server reside."
    ::= { rlDhcpSpoofing 1 }


rlDhcpSpoofingVlanTable OBJECT-TYPE
    SYNTAX      SEQUENCE OF RlDhcpSpoofingVlanEntry
    MAX-ACCESS  not-accessible
    STATUS      current
    DESCRIPTION
        "A table that contains all existing vlans."
    ::= { rlDhcpSpoofing 2 }

rlDhcpSpoofingVlanEntry OBJECT-TYPE
    SYNTAX      RlDhcpSpoofingVlanEntry
    MAX-ACCESS  not-accessible
    STATUS      current
    DESCRIPTION
        "A vlan."
    INDEX       { dot1qVlanIndex }
    ::= { rlDhcpSpoofingVlanTable 1 }

RlDhcpSpoofingVlanEntry::=
    SEQUENCE {
        rlDhcpSpoofingEnabled
            TruthValue
    }


rlDhcpSpoofingEnabled OBJECT-TYPE
    SYNTAX      TruthValue
    MAX-ACCESS  read-write
    STATUS      current
    DESCRIPTION
        "DHCP spoofing enabled or not."
    ::= { rlDhcpSpoofingVlanEntry 1 }


END
