-- ==================================================================
-- Copyright (c) 2010-2013 Hewlett-Packard Development Company, L.P.
--
-- Description: Rmon alarm Information MIB
-- Reference:
-- Version: V1.1
-- History:
--(1) Created by Qizhenglin, 2002.8.15
-- V1.1 2004-10-12 updated by gaolong
--      Change MAX-ACCESS to ACCESS.
--      Change current to mandatory.
-- ==================================================================

-- ==================================================================
--
-- Varibles and types be imported
--
-- ==================================================================

HPN-ICF-LswSMON-MIB DEFINITIONS ::= BEGIN

              IMPORTS
                  OBJECT-TYPE
                      FROM RFC-1212
                  hpnicfRhw
                      FROM HPN-ICF-OID-MIB;

-- ==================================================================
--
-- ======================= definition begin =========================
--
-- ==================================================================

hpnicfSmonExtend         OBJECT IDENTIFIER ::= { hpnicfRhw 26 }

hpnicfsmonExtendObject        OBJECT IDENTIFIER ::= { hpnicfSmonExtend 1 }


hpnicfdot1qVlanStatNumber OBJECT-TYPE
     SYNTAX  INTEGER
     ACCESS  read-only
     STATUS  mandatory
     DESCRIPTION
         "The number of vlans that can collect statistics of packets."
     ::= { hpnicfsmonExtendObject 1 }

-- ==================================================================
--
-- VLAN statistics status table (for SMON)
--
-- ==================================================================
 hpnicfdot1qVlanStatStatusTable OBJECT-TYPE
     SYNTAX     SEQUENCE OF Hpnicfdot1qVlanStatStatusEntry
     ACCESS     not-accessible
     STATUS     mandatory
     DESCRIPTION
         "VLAN statistics status table."
     ::= { hpnicfsmonExtendObject 2 }

 hpnicfdot1qVlanStatStatusEntry OBJECT-TYPE
     SYNTAX     Hpnicfdot1qVlanStatStatusEntry
     ACCESS	not-accessible
     STATUS     mandatory
     DESCRIPTION
         " VLAN statistics status table entry."
     INDEX { hpnicfdot1qVlanStatEnableIndex }
     ::= { hpnicfdot1qVlanStatStatusTable 1 }


    Hpnicfdot1qVlanStatStatusEntry ::= SEQUENCE {
        hpnicfdot1qVlanStatEnableIndex                INTEGER,
        hpnicfdot1qVlanStatEnableStatus               INTEGER
    }


    hpnicfdot1qVlanStatEnableIndex  OBJECT-TYPE
        SYNTAX     INTEGER
        ACCESS 	    read-only
        STATUS      mandatory
        DESCRIPTION
        "Vlan index ."
        ::= { hpnicfdot1qVlanStatStatusEntry 1 }

    hpnicfdot1qVlanStatEnableStatus  OBJECT-TYPE
        SYNTAX     INTEGER
        {
            enabled(1),
            disabled(2)
        }
        ACCESS read-write
        STATUS      mandatory
        DESCRIPTION
        "VLAN Statistics Status.It represent the current VLAN supports statistic or not."
        ::= { hpnicfdot1qVlanStatStatusEntry 2 }

   END
