--  (C) COPYRIGHT HEWLETT-PACKARD COMPANY 2015.
--
--  LaserJet 2025 Printer Model Specific MIB.
--
--  Generated on Jan. 26, 2015.
--
--  Company names and product names mentioned herein may be
--  trademarks, and/or registered trademarks of their respective
--  companies.
--
--  For internal and external use.
--
--  This MIB describes all the printer model specific
--  objects supported by the LaserJet 2025 printer
--  when networked connected.
--
--  The following MIBs also contain objects supported
--  by a LaserJet 2025 printer:
--
--  IEEE 802.11 MIB
--  IEEE 802.1X MIB
--  rfc 2790 Host Resources MIB
--  rfc 3411 SNMP Framework MIB
--  rfc 3412 SNMP MPD MIB
--  rfc 3418 SNMP MIB
--  rfc 3805 Printer MIB
--  rfc 4022 TCP MIB
--  rfc 4293 IP MIB
--  rfc 4113 UDP MIB
--  PWG 5107.1-2005 Printer Port Monitor MIB
--
--  This MIB complies with the following RFCs:
--
--  rfc 1157 Simple Network Management Protocol
--  rfc 2578 Structure of Management Information Version 2
--
--  Notes:
--
--  1) Objects containing a string which are defined in this MIB use the
--     first two bytes to hold the symbol set used to encode the string.
--     The Roman-8 symbol set has a hex encoding of 0x0115.  Other
--     symbol sets are listed in the PCL 5 Comparison Guide in table
--     C-1 Symbol Set Values.
--
--  2) Some of the objects included are only supported if an accessory
--     is installed.  These accessories include:
--       MIO based accessories
--       SIMM based accessories
--       Paper handling accessories

LJ2025-MIB DEFINITIONS ::= BEGIN

IMPORTS
	OBJECT-TYPE
		FROM RFC-1212

	DisplayString
		FROM SNMPv2-TC;

hpPrintServer OBJECT IDENTIFIER ::= { iso(1) org(3) dod(6) internet(1) private(4) enterprises(1) 11}
dm OBJECT IDENTIFIER ::= { hpPrintServer nm(2) hpsystem(3) net-peripheral(9) netdm(4) 2}

device                                 OBJECT IDENTIFIER ::=  { dm 1 }
system                                 OBJECT IDENTIFIER ::=  { device 1 }
settings-system                        OBJECT IDENTIFIER ::=  { system 1 }
destination-subsystem                  OBJECT IDENTIFIER ::=  { device 4 }
print-engine                           OBJECT IDENTIFIER ::=  { destination-subsystem 1 }
settings-prt-eng                       OBJECT IDENTIFIER ::=  { print-engine 1 }
marking-agent-density                  OBJECT IDENTIFIER ::=  { settings-prt-eng 9 }
status-prt-eng                         OBJECT IDENTIFIER ::=  { print-engine 2 }
marking-agent                          OBJECT IDENTIFIER ::=  { print-engine 5 }
settings-marking-agent                 OBJECT IDENTIFIER ::=  { marking-agent 1 }
print-engine-test                      OBJECT IDENTIFIER ::=  { print-engine 9 }
hrm                                    OBJECT IDENTIFIER ::=  { dm 3 }
hrStorage                              OBJECT IDENTIFIER ::=  { hrm 2 }
hrStorageTable                         OBJECT IDENTIFIER ::=  { hrStorage 3 }
hrStorageEntry                         OBJECT IDENTIFIER ::=  { hrStorageTable 1 }
hrDevice                               OBJECT IDENTIFIER ::=  { hrm 3 }
hrDeviceTable                          OBJECT IDENTIFIER ::=  { hrDevice 2 }
hrDeviceEntry                          OBJECT IDENTIFIER ::=  { hrDeviceTable 1 }
hrPrinterTable                         OBJECT IDENTIFIER ::=  { hrDevice 5 }
hrPrinterEntry                         OBJECT IDENTIFIER ::=  { hrPrinterTable 1 }
org                                    OBJECT IDENTIFIER ::=  { iso 3 }
dod                                    OBJECT IDENTIFIER ::=  { org 6 }
internet                               OBJECT IDENTIFIER ::=  { dod 1 }
private                                OBJECT IDENTIFIER ::=  { internet 4 }
enterprises                            OBJECT IDENTIFIER ::=  { private 1 }
nm                                     OBJECT IDENTIFIER ::=  { hpPrintServer 2 }
interface                              OBJECT IDENTIFIER ::=  { nm 4 }
npCard                                 OBJECT IDENTIFIER ::=  { interface 3 }
snmpAccess                             OBJECT IDENTIFIER ::=  { nm 15 }
community                              OBJECT IDENTIFIER ::=  { snmpAccess 1 }
npSys                                  OBJECT IDENTIFIER ::=  { npCard 1 }
npConns                                OBJECT IDENTIFIER ::=  { npCard 4 }
npCfg                                  OBJECT IDENTIFIER ::=  { npCard 5 }
npCtl                                  OBJECT IDENTIFIER ::=  { npCard 7 }
npPort                                 OBJECT IDENTIFIER ::=  { npCard 13 }
npDhcp                                 OBJECT IDENTIFIER ::=  { npCard 16 }
system                                 OBJECT IDENTIFIER ::=  { nm 3 }
netPeripheral                          OBJECT IDENTIFIER ::=  { system 9 }
netPrinter                             OBJECT IDENTIFIER ::=  { netPeripheral 1 }
generalDeviceStatus                    OBJECT IDENTIFIER ::=  { netPrinter 1 }
npNpi                                  OBJECT IDENTIFIER ::=  { npCard 8 }
npNpiPeripheralAttributeEntry          OBJECT IDENTIFIER ::=  { npNpi 3 }
npNpiCardAttributeEntry                OBJECT IDENTIFIER ::=  { npNpi 4 }
gdStatusEntry                          OBJECT IDENTIFIER ::=  { generalDeviceStatus 2 }
device-configure                       OBJECT IDENTIFIER ::=  { settings-system 32 }
source-subsystem                       OBJECT IDENTIFIER ::=  { device 2 }
io                                     OBJECT IDENTIFIER ::=  { source-subsystem 1 }
settings-io                            OBJECT IDENTIFIER ::=  { io 1 }
processing-subsystem                   OBJECT IDENTIFIER ::=  { device 3 }
pdl                                    OBJECT IDENTIFIER ::=  { processing-subsystem 3 }
settings-pdl                           OBJECT IDENTIFIER ::=  { pdl 1 }
pdl-pcl                                OBJECT IDENTIFIER ::=  { pdl 3 }
pdl-postscript                         OBJECT IDENTIFIER ::=  { pdl 4 }
pdl-pclxl                              OBJECT IDENTIFIER ::=  { pdl 16 }
pjl                                    OBJECT IDENTIFIER ::=  { processing-subsystem 5 }
intray                                 OBJECT IDENTIFIER ::=  { print-engine 3 }
settings-intray                        OBJECT IDENTIFIER ::=  { intray 1 }
intrays                                OBJECT IDENTIFIER ::=  { intray 3 }
intray1                                OBJECT IDENTIFIER ::=  { intrays 1 }
intray2                                OBJECT IDENTIFIER ::=  { intrays 2 }
intray3                                OBJECT IDENTIFIER ::=  { intrays 3 }
imaging                                OBJECT IDENTIFIER ::=  { print-engine 6 }
print-media                            OBJECT IDENTIFIER ::=  { print-engine 8 }
settings-print-media                   OBJECT IDENTIFIER ::=  { print-media 1 }
media-info                             OBJECT IDENTIFIER ::=  { print-media 3 }
media1                                 OBJECT IDENTIFIER ::=  { media-info 1 }
media2                                 OBJECT IDENTIFIER ::=  { media-info 2 }
media3                                 OBJECT IDENTIFIER ::=  { media-info 3 }
media4                                 OBJECT IDENTIFIER ::=  { media-info 4 }
media5                                 OBJECT IDENTIFIER ::=  { media-info 5 }
media6                                 OBJECT IDENTIFIER ::=  { media-info 6 }
media7                                 OBJECT IDENTIFIER ::=  { media-info 7 }
media8                                 OBJECT IDENTIFIER ::=  { media-info 8 }
media9                                 OBJECT IDENTIFIER ::=  { media-info 9 }
media10                                OBJECT IDENTIFIER ::=  { media-info 10 }
media11                                OBJECT IDENTIFIER ::=  { media-info 11 }
media12                                OBJECT IDENTIFIER ::=  { media-info 12 }
media13                                OBJECT IDENTIFIER ::=  { media-info 13 }
media14                                OBJECT IDENTIFIER ::=  { media-info 14 }
media15                                OBJECT IDENTIFIER ::=  { media-info 15 }
media16                                OBJECT IDENTIFIER ::=  { media-info 16 }
media17                                OBJECT IDENTIFIER ::=  { media-info 17 }
media18                                OBJECT IDENTIFIER ::=  { media-info 18 }
media19                                OBJECT IDENTIFIER ::=  { media-info 19 }
media20                                OBJECT IDENTIFIER ::=  { media-info 20 }
media21                                OBJECT IDENTIFIER ::=  { media-info 21 }
media22                                OBJECT IDENTIFIER ::=  { media-info 22 }
media23                                OBJECT IDENTIFIER ::=  { media-info 23 }
media24                                OBJECT IDENTIFIER ::=  { media-info 24 }
media25                                OBJECT IDENTIFIER ::=  { media-info 25 }
media26                                OBJECT IDENTIFIER ::=  { media-info 26 }
media27                                OBJECT IDENTIFIER ::=  { media-info 27 }
media28                                OBJECT IDENTIFIER ::=  { media-info 28 }
media29                                OBJECT IDENTIFIER ::=  { media-info 29 }
media30                                OBJECT IDENTIFIER ::=  { media-info 30 }
media31                                OBJECT IDENTIFIER ::=  { media-info 31 }
media-modes                            OBJECT IDENTIFIER ::=  { print-media 4 }
consumables                            OBJECT IDENTIFIER ::=  { print-engine 10 }


mono-color-switching-mode OBJECT-TYPE
    SYNTAX      INTEGER {
                          eNeverSwitch(1),
                          eAlwaysSwitch(2),
                          eLookAheadSwitch(3)
		   }
    ACCESS      read-write
    STATUS      optional
       DESCRIPTION "This object allows the user to view/change the color/mono
                switching mode for a device.
                Additional information:
                This object allows the user to view/change the color/mono
                switching mode for a device."
::= { settings-system 31 }


calibration-power-on-initiation OBJECT-TYPE
    SYNTAX      INTEGER {
                          eOff(1),
                          eOn(2),
                          eDelayed(3)
		   }
    ACCESS      read-write
    STATUS      optional
       DESCRIPTION "This object determines when a power on calibration occurs. If
                eOn, then the calibration occurs immediately following boot. If
                eOff, then it never occurs. If eDelayed, then refer to the
                CALIBRATION-POWER-ON-DELAY PML object for the delay interval."
::= { settings-prt-eng 20 }


calibration-power-on-delay OBJECT-TYPE
    SYNTAX      INTEGER
    ACCESS      read-write
    STATUS      optional
       DESCRIPTION "This is the delay interval for the power on calibration in
                minutes. This PML object is only used if the
                CALIBRATION-POWER-ON-INITIATION PML object is set to eDelayed.
                Additional information:
                This is the delay interval for the power on
                		calibration in minutes. The range in minutes for the product
                		is 1-60 minutes. "
::= { settings-prt-eng 21 }


calibration-pages-printed-initiation OBJECT-TYPE
    SYNTAX      INTEGER
    ACCESS      read-write
    STATUS      optional
       DESCRIPTION "The number of pages that will be printed prior to an
                automatically initiated print calibration. If set to 0, it
                turns this calibration off.
                Additional information:
                This is the number of pages that will be printed
                		prior to an automatically initiated print calibration.
                		If set to 0, it turns this calibration off. The range for
                		the product will be 0-500. On Raptor the default value is
                	        200.  On Kiwi the default value is 150"
::= { settings-prt-eng 22 }


calibration-timer-initiation OBJECT-TYPE
    SYNTAX      INTEGER
    ACCESS      read-write
    STATUS      optional
       DESCRIPTION "This is a timer in minutes that will be set in between
                calibrations. When the timer expires, a calibration will
                automatically be initiated. If set to 0, it turns this
                calibration off.
                Additional information:
                This is a timer in minutes that will be set in
                		between calibrations.   If set to 0,
                		it turns this calibration off. The range for the product
                		will be 0-10080. When you set to a value of 2 (min) or any
                		other legal value other than 0, the device does not
                		immediately begin calibrating when the timer expires.
                		The calibration takes place after the timer expires,
                		the next job has finished printing, and a 15 minute period
                	        of inactivity has passed."
::= { settings-prt-eng 23 }


calibration-cpr-pages-printed-initiation OBJECT-TYPE
    SYNTAX      INTEGER
    ACCESS      read-write
    STATUS      optional
       DESCRIPTION "The number of pages that will be printed prior to an
                automatically initiated CPR calibration. If set to 0, it turns
                this calibration off.
                Additional information:
                The number of pages that will be printed prior to an
                automatically initiated CPR calibration. If set to 0, it turns
                this calibration off."
::= { settings-prt-eng 32 }


total-mono-page-count OBJECT-TYPE
    SYNTAX      INTEGER
    ACCESS      read-write
    STATUS      optional
       DESCRIPTION "Total number of black pages printed by the device.
                Additional information:
                Total number of mono pages printed by the device."
::= { status-prt-eng 6 }


total-color-page-count OBJECT-TYPE
    SYNTAX      INTEGER
    ACCESS      read-write
    STATUS      optional
       DESCRIPTION "Total number of color pages printed by the device.
                Additional information:
                Total number of color pages printed
                				by the device."
::= { status-prt-eng 7 }


marker-density-calibration OBJECT-TYPE
    SYNTAX      INTEGER {
                          eNotCallibrating(1),
                          eCalibrateALL(2),
                          eCalibrateColor(3),
                          eCalibrateColorPlaneRegistration(5)
		   }
    ACCESS      read-write
    STATUS      optional
       DESCRIPTION "Returns the calibration status or triggers a calibration cycle.
                All calibration procedures are used if set to eCalibrateALL. If
                set to eCalibrateColor then a full density engine calibration
                is triggered. If set to eCalibrateHalftone, then a Halftone
                calibration is triggered. If set to
                eCalibrateColorPlaneRegistration, then a Color Plane
                Registration calibration is triggered. If set to
                eCalibrateDrumPhaseAdjustment, then a Drum Phase Adjustment
                calibration is triggered.If set to eCalibrateLowSpeedColor,
                then a Low Speed Color calibration is triggered.If set to
                eCalibrateDrumSpeedAdjustment, then a Drum Speed Adjustment
                calibration is triggered.If set to eCalibrateNeutrals, then a
                Gray Axis Control calibration is triggered.
                Additional information:
                Returns the calibration status or triggers a
                				calibration cycle."
::= { settings-marking-agent 11 }


pe-test-abort-calibration OBJECT-TYPE
    SYNTAX      INTEGER {
                          eFalse(1),
                          eTrue(2)
		   }
    ACCESS      read-write
    STATUS      optional
       DESCRIPTION "Aborts all executing and scheduled calibrations if set to
                eTrue.
                Additional information:
                All scheduled caliberations will abort.  Any currently
                	                     executing calibration will finish normally."
::= { print-engine-test 94 }


setCommunityName OBJECT-TYPE
    SYNTAX      OCTET STRING
    ACCESS      read-write
    STATUS      current
       DESCRIPTION "This object controls access of snmp read-write requests.  Factory
        default configuration provides authentication of incoming packets
        with community names: internal and public.  This object overrides the
        factory default settings so that the factory default setttings no longer
        work. This object returns SET or NOT_SET."
::= { community 1 }


getCommunityName OBJECT-TYPE
    SYNTAX      OCTET STRING
    ACCESS      read-write
    STATUS      current
       DESCRIPTION "This object controls access of snmp read requests.  Factory
        default configuration provides authentication of incoming packets
        with community names: internal and public.  This object provides
        access in addition to the factory default settings. If
        set, then authentication will succeed with any of the following
        community names: internal, public, getCommunityName, or
        setCommunityName. This object returns SET or NOT_SET."
::= { community 2 }


npSysStatusMessage OBJECT-TYPE
    SYNTAX      DisplayString
    ACCESS      read-only
    STATUS      current
       DESCRIPTION "A status string reflecting the current state of the card
         and peripheral."
::= { npSys 2 }


npSysModelNumber OBJECT-TYPE
    SYNTAX      OCTET STRING
    ACCESS      read-only
    STATUS      current
       DESCRIPTION "The HP model number of the device."
::= { npSys 10 }


npSysNetworkConnectors OBJECT-TYPE
    SYNTAX      Integer32
    ACCESS      read-only
    STATUS      current
       DESCRIPTION "This object describes the network connectors supported by the
	 device.  The value is a bit mask.  A set bit indicates the
         connector is supported.
         Bit      Value     Connector
          0       0x01      Ethernet, BNC
          1       0x02      Ethernet, AUI
          2       0x04      Ethernet, RJ-45
          3       0x08      TokenRing, DB-9
          4       0x10      TokenRing, RJ-45
          5       0x20      LocalTalk
          6       0x40      100VG, RJ-45
          7       0x80      100T, RJ-45"
::= { npSys 11 }


npSysCardServices1 OBJECT-TYPE
    SYNTAX      Integer32
    ACCESS      read-only
    STATUS      current
       DESCRIPTION "This object is a bitmap showing what services are available
         on the card.

         Bit  0 - IPX/SPX/NCP protocol stack
         Bit  1 - IP/TCP protocol stack
         Bit  2 - LLC/DLC protocol stack
         Bit  3 - Ethertalk protocol stack
         Bit  4 - IPv6 protocol stack
         Bit  5 - IPSec protocol stack
         Bits  6 - 11 Reserved
         Bit 12 - LPD print services
         Bit 13 - FTP print services
         Bit 14 - Port 9100 print services
         Bit 15 - IPP print services
         Bits 16 - 23 Reserved
         Bit 24 - Queue Server Bindery
         Bit 25 - Queue Server NDS
         Bit 26 - Remote Printer
         Bit 27 - SPX Direct Mode
         Bit 28 - DLC Print Services
         Bit 29 - EtherTalk Print Services
         Bits 30 - 31 Reserved"
::= { npSys 16 }


npSysCardServices2 OBJECT-TYPE
    SYNTAX      Integer32
    ACCESS      read-only
    STATUS      current
       DESCRIPTION "This object is a bitmap showing what services are available
         on the card.

         Bit  0 - XIP2
         Bit  1 - PML Get/Set
         Bit  2 - PML Traps
         Bit  3 - Scan to Web Browser
         Bit  4 - Scan to Email
         Bit  5 - MFP Scan Support
         Bits  6 - 11 Reserved
         Bit 12 - Telnet API
         Bit 13 - Web API
         Bit 14 - SNMP V2
         Bit 15 - SNMP Traps
         Bit 16 - Download
         Bit 17 - TFTP
         Bit 18 - RCFG
         Bit 19 - SLP
         Bit 20 - Syslog
         Bit 21 - DHCP
         Bit 22 - BOOTP
         Bit 23 - RARP
         Bit 24 - SNMP V3
         Bit 25 - SSL Functionality
         Bit 26 - Auto IP
         Bits 27 - 31 Reserved"
::= { npSys 17 }


npSysCardServices3 OBJECT-TYPE
    SYNTAX      Integer32
    ACCESS      read-only
    STATUS      current
       DESCRIPTION "This object is a bitmap showing what services are available
         on the card.

         Bit  0 - 100T
         Bit  1 - Token Ring 802.5
         Bit  2 - 802.11b
         Bit  3 - 80211.a
         Bit  4 - Bluetooth
         Bits 5 - 11 Reserved
         Bit  12 -  EIO. For embedded Jetdirect this bit will be 1.
         Bit  13 - LIO
         Bit  14 - USB
         Bit  15 - Firewire
         Bit  16 - TCP Download

         Bits 17 - 31 Reserved"
::= { npSys 22 }


npConnsIP OBJECT-TYPE
    SYNTAX      IpAddress
    ACCESS      read-only
    STATUS      current
       DESCRIPTION "Remote IP address of the node currently connected to the card.
         Zero if no connection is active."
::= { npConns 11 }


npCfgSource OBJECT-TYPE
    SYNTAX      INTEGER {manual-one(1),
                          bootp-two(2),
                          manual-three(3),
                          bootp-four(4),
                          dhcp(5),
                          not-configured(6),
                          default-config(7),
                          rarp(8),
                          read-only(9),
		   auto-ip(10)}
    ACCESS      read-write
    STATUS      current
       DESCRIPTION "This object indicates how the device obtained its IP configuration."
::= { npCfg 1 }


npCfgYiaddr OBJECT-TYPE
    SYNTAX      IpAddress
    ACCESS      read-write
    STATUS      current
       DESCRIPTION "The IP address assigned to the card from the BOOTP reply
         yiaddr field."
::= { npCfg 2 }


npCfgSubnetMask OBJECT-TYPE
    SYNTAX      IpAddress
    ACCESS      read-write
    STATUS      current
       DESCRIPTION "The subnet mask associated with the IP address of this card."
::= { npCfg 12 }


npCfgDefaultGateway OBJECT-TYPE
    SYNTAX      IpAddress
    ACCESS      read-write
    STATUS      current
       DESCRIPTION "This variable contains the IP address of the default router for this
         card."
::= { npCfg 13 }


npCfgDomainName OBJECT-TYPE
    SYNTAX      OCTET STRING
    ACCESS      read-write
    STATUS      current
       DESCRIPTION "The print server domain name."
::= { npCfg 16 }


npCfgWINSNameServerIdPri OBJECT-TYPE
    SYNTAX      IpAddress
    ACCESS      read-write
    STATUS      current
       DESCRIPTION "Primary name server for NetBIOS over TCP/IP."
::= { npCfg 22 }


npCfgPasswd1Verify OBJECT-TYPE
    SYNTAX      OCTET STRING
    ACCESS      read-write
    STATUS      current
       DESCRIPTION "Compares string value to passwd1 and returns OK if match,
     GENERAL ERROR if doesn't match."
::= { npCfg 28 }


npCfgPasswd1 OBJECT-TYPE
    SYNTAX      DisplayString
    ACCESS      read-write
    STATUS      current
       DESCRIPTION "Password for root or administrator. Get request returns
     either 'SET' or 'NOT_SET'."
::= { npCfg 29 }


npCfgLinkType OBJECT-TYPE
    SYNTAX      INTEGER {autoNegotiate(1),
                          full10T(2),
                          half10T(3),
                          full100T(4),
                          half100T(5),
                          auto100T(6),
		   full1000T(7)}
    ACCESS      read-write
    STATUS      current
       DESCRIPTION "Network link speed and communication mode."
::= { npCfg 35 }


npCfgBonjourDomainName OBJECT-TYPE
    SYNTAX      OCTET STRING
    ACCESS      read-only
    STATUS      current
       DESCRIPTION "The name used as the 'target name' in the DNS SRV records by
     Multicast Domain Name System (Bonjour)."
::= { npCfg 46 }


npCtlReconfig OBJECT-TYPE
    SYNTAX      Integer32
    ACCESS      read-write
    STATUS      current
       DESCRIPTION "Writing any value to this variable causes the card to
         reconfigure itself by doing the BOOTP/TFTP configuration
         activity."
::= { npCtl 8 }


npCtlProtocolSet OBJECT-TYPE
    SYNTAX      Integer32
    ACCESS      read-write
    STATUS      current
       DESCRIPTION "This is a 4 byte integer value.  The least significant bytes
         represent the protocols on the card.  A value of '1' indicates
         a protocol that is enabled.  A value of '0' indicates a
         protocol that is disabled.
         The 32-bit protocol enable 'structure' is defined as:

    		bits 31-28:  Number of I/O channels/protocols present (NUM_CHAN)
    		bits 27-24:  Number of I/O channels which may operate concurrently
                    (NUM_OP_CHAN)
    		bits 23-16:  unused, reserved
    		bits 15-1:   Individual I/O channel/protocol enable bits,
                    0 == disable, 1 == enable
                    MIO_IOCHAN_NOVELL   bit   1
                    MIO_IOCHAN_LLC      bit   2
                    MIO_IOCHAN_TCP      bit   3
                    MIO_IOCHAN_ATALK    bit   4
                    MIO_IOCHAN_IPV6	bit   5
    		bit  0:      When NUM_OP_CHAN == 1, auto-protocol select enable bit,
                    0 == disable, 1 == enable  (APS_ON)"
::= { npCtl 9 }


npCtlSnmpVersionAccess OBJECT-TYPE
    SYNTAX      INTEGER {snmpV1RW-snmpV3RW(1),
                          snmpV1RO-snmpV3RW(2),
                          snmpV1NoAccess-snmpV3RW(3),
                          snmpV1RW-snmpV3NoAccess(4),
		   snmpV1RO-snmpV3NoAccess(5)}
    ACCESS      read-write
    STATUS      current
       DESCRIPTION "Manages an SNMP version's read and write access to the MIB."
::= { npCtl 27 }


npCtlBonjour OBJECT-TYPE
    SYNTAX      Integer32 (0..1)
    ACCESS      read-write
    STATUS      current
       DESCRIPTION "Configure Multicast Domain Name Service.
            (0) = Bonjour disabled
            (1) = Bonjour enabled"
::= { npCtl 29 }


npPortNumPorts OBJECT-TYPE
    SYNTAX      Integer32 (0..255)
    ACCESS      read-only
    STATUS      current
       DESCRIPTION "The number of peripheral interfaces supported by this device."
::= { npPort 1 }


npDHCPserver OBJECT-TYPE
    SYNTAX      IpAddress
    ACCESS      read-only
    STATUS      current
       DESCRIPTION "IP address of DHCP server that provided this unit with an IP
         address via the DHCP protocol."
::= { npDhcp 2 }


gdStatusBytes OBJECT-TYPE
    SYNTAX      Integer32
    ACCESS      read-only
    STATUS      current
       DESCRIPTION "The number of valid bytes in the gdStatusEntry
         array."
::= { generalDeviceStatus 1 }


gdStatusDisplay OBJECT-TYPE
    SYNTAX      DisplayString
    ACCESS      read-only
    STATUS      current
       DESCRIPTION "The string diplayed on the peripheral front panel.
         For some peripherals, such as the HP LaserJet IIISi printer
         or HP DesignJet plotter, this is always a zero length string."
::= { generalDeviceStatus 3 }


gdStatusId OBJECT-TYPE
    SYNTAX      OCTET STRING
    ACCESS      read-only
    STATUS      current
       DESCRIPTION "A formatted string of NVT ASCII
         charactersdescribing this peripheral."
::= { generalDeviceStatus 7 }


gdStatusJobTimeout OBJECT-TYPE
    SYNTAX      Integer32
    ACCESS      read-write
    STATUS      obsolete
::= { generalDeviceStatus 10 }


gdPasswords OBJECT-TYPE
    SYNTAX      OCTET STRING
    ACCESS      read-write
    STATUS      current
       DESCRIPTION "This object is used as a 256 byte NVRAM area for JetAdmin.  It
         is completely managed by JetAdmin.  Initially it is initialized
         to all zeros.  A coldboot will re-initialize to all zeros."
::= { generalDeviceStatus 13 }


npNpiPaeClass OBJECT-TYPE
    SYNTAX      INTEGER {printer(1),
                          plotter(2),
		   xStation(3)}
    ACCESS      read-only
    STATUS      current
       DESCRIPTION "The class assigned to the peripheral onto which
         this card is plugged."
::= { npNpiPeripheralAttributeEntry 2 }


npNpiPaeIdentification OBJECT-TYPE
    SYNTAX      INTEGER {laserjet-IIISI(1),
		   laserjet-4SI(5)}
    ACCESS      read-only
    STATUS      current
       DESCRIPTION "The Identification number of the peripheral.  These values are
         defined in the MIO spec.  DesignJet, PaintJet XL300, and
         DesignJet/600 peripherals will identify themselves as
         LaserJet-IIIsi."
::= { npNpiPeripheralAttributeEntry 3 }


npNpiCaeClass OBJECT-TYPE
    SYNTAX      INTEGER {rs-232(1),
                          centronics(2),
                          csma-cd-network(3),
                          token-ring-network(4),
                          scsi(5),
                          hpib(6),
                          localtalk(7),
                          hpna(8),
                          usb(9),
                          firewire(10),
                          bluetooth(11),
		   ieee802-11b(12)}
    ACCESS      read-only
    STATUS      current
       DESCRIPTION "The class of this network peripheral card."
::= { npNpiCardAttributeEntry 2 }


gdStatusLineState OBJECT-TYPE
    SYNTAX      Integer32 (0..255)
    ACCESS      read-only
    STATUS      current
       DESCRIPTION "This describes the line state of the peripheral.
         When non-zero, the peripheral is off-line.  When
         zero the peripheral is on-line."
::= { gdStatusEntry 1 }


gdStatusPaperState OBJECT-TYPE
    SYNTAX      Integer32 (0..255)
    ACCESS      read-only
    STATUS      current
       DESCRIPTION "This describes the state of the paper on the peripheral.
         When non-zero, the peripheral has a paper problem. When
         zero, the peripheral does not have a paper problem."
::= { gdStatusEntry 2 }


gdStatusInterventionState OBJECT-TYPE
    SYNTAX      Integer32 (0..255)
    ACCESS      read-only
    STATUS      current
       DESCRIPTION "This describes the intervention state of the
         peripheral.  When non-zero, the peripheral requires
         human intervention to continue working.  When
         zero, it requires no assistance."
::= { gdStatusEntry 3 }


gdStatusPeripheralError OBJECT-TYPE
    SYNTAX      Integer32 (0..255)
    ACCESS      read-only
    STATUS      current
       DESCRIPTION "This is the error code from the peripheral."
::= { gdStatusEntry 6 }


gdStatusPaperOut OBJECT-TYPE
    SYNTAX      Integer32
    ACCESS      read-only
    STATUS      current
       DESCRIPTION "This indicates that the peripheral is out of paper.
                off (0),
                paper-out-or-paper-mount (1),
                manual-paper-feed-needed (2)
         For some peripherals, such as the HP LaserJet IIISi printer
         or HP DesignJet plotter, this value is always a zero (0)."
::= { gdStatusEntry 8 }


gdStatusPaperJam OBJECT-TYPE
    SYNTAX      Integer32
    ACCESS      read-only
    STATUS      current
       DESCRIPTION "This indicates that the peripheral has a paper jam.
              off (0),
              paper-jam(1)
         For some peripherals, such as the HP LaserJet IIISi printer
         or HP DesignJet plotter, this value is always a zero (0)."
::= { gdStatusEntry 9 }


gdStatusTonerLow OBJECT-TYPE
    SYNTAX      Integer32
    ACCESS      read-only
    STATUS      current
       DESCRIPTION "This indicates that the peripheral has a low toner condition.
              off (0),
              toner-low (1),
              no-toner-cartridge (2)
         For some peripherals, such as the HP LaserJet IIISi printer
         or HP DesignJet plotter, this value is always a zero (0)."
::= { gdStatusEntry 10 }


gdStatusPagePunt OBJECT-TYPE
    SYNTAX      Integer32 (0..255)
    ACCESS      read-only
    STATUS      current
       DESCRIPTION "This indicates that the peripheral did not receive data fast
         enough to keep up with the print engine when generating a page.
         For some peripherals, such as the HP LaserJet IIISi printer
         or HP DesignJet plotter, this value is always a zero (0)."
::= { gdStatusEntry 11 }


gdStatusMemoryOut OBJECT-TYPE
    SYNTAX      Integer32 (0..255)
    ACCESS      read-only
    STATUS      current
       DESCRIPTION "This indicates that the peripheral did not have enough memory
         to render an image on a page.
         For some peripherals, such as the HP LaserJet IIISi printer
         or HP DesignJet plotter, this value is always a zero (0)."
::= { gdStatusEntry 12 }


gdStatusIoActive OBJECT-TYPE
    SYNTAX      Integer32 (0..255)
    ACCESS      read-only
    STATUS      current
       DESCRIPTION "This indicates that the peripheral is processing data from
         this I/O interface card. For some peripherals, such as the
         HP LaserJet IIISi printer or HP DesignJet plotter,
         this value is always a zero (0).

         For X.20.06 firmware and later firmware releases, this object is
         not relevant. In order not to break legacy applications which call this
         object in multi-varbind requests, this value is always zero (0)."
::= { gdStatusEntry 13 }


gdStatusBusy OBJECT-TYPE
    SYNTAX      Integer32 (0..255)
    ACCESS      read-only
    STATUS      current
       DESCRIPTION "This indicates that the peripheral is busy processing
         print/plot data.
         For some peripherals, such as the HP LaserJet IIISi printer
         or HP DesignJet plotter, this value is always a zero (0)."
::= { gdStatusEntry 14 }


gdStatusWait OBJECT-TYPE
    SYNTAX      Integer32 (0..255)
    ACCESS      read-only
    STATUS      current
       DESCRIPTION "This indicates that the peripheral is waiting for print/plot
         data to process.
         For some peripherals, such as the HP LaserJet IIISi printer
         or HP DesignJet plotter, this value is always a zero (0)."
::= { gdStatusEntry 15 }


gdStatusInitialize OBJECT-TYPE
    SYNTAX      Integer32
    ACCESS      read-only
    STATUS      current
       DESCRIPTION "This indicates that the peripheral is initializing or
         warming up.
              off (0),
              initializing (1),
              warm-up(2)
         For some peripherals, such as the HP LaserJet IIISi printer
         or HP DesignJet plotter, this value is always a zero (0)."
::= { gdStatusEntry 16 }


gdStatusDoorOpen OBJECT-TYPE
    SYNTAX      Integer32 (0..255)
    ACCESS      read-only
    STATUS      current
       DESCRIPTION "This indicates that the peripheral cover or door is open.
         For some peripherals, such as the HP LaserJet IIISi printer
         or HP DesignJet plotter, this value is always a zero (0)."
::= { gdStatusEntry 17 }


gdStatusPrinting OBJECT-TYPE
    SYNTAX      Integer32
    ACCESS      read-only
    STATUS      current
       DESCRIPTION "This indicates that the peripheral is printing or otherwise
         marking or moving paper.
              off (0),
              ordinary-page (1),
              test-fonts-config-or-start-page (2)
         For some peripherals, such as the HP LaserJet IIISi printer
         or HP DesignJet plotter, this value is always a zero (0)."
::= { gdStatusEntry 18 }


gdStatusPaperOutput OBJECT-TYPE
    SYNTAX      Integer32
    ACCESS      read-only
    STATUS      current
       DESCRIPTION "This indicates that the peripheral has a paper output problem
         such as the output storage bin being full.
              off (0),
              output-storage-full (1)
         For some peripherals, such as the HP LaserJet IIISi printer
         or HP DesignJet plotter, this value is always a zero (0)."
::= { gdStatusEntry 19 }


energy-star OBJECT-TYPE
    SYNTAX      INTEGER
    ACCESS      read-only
    STATUS      optional
       DESCRIPTION "Returns or changes the Energy Star sleep value. If the value
                is greater than zero, then the device will go into energy
                saving sleep mode after the print engine has been idle for the
                number of seconds specified by this object. A value of zero
                means Energy Star is disabled and the device will not go to
                sleep based on print engine idle time. The value must be
                non-negative.
                Additional information:
                The product will always be in
                sleep mode when not processing data.  This object will
                always return a value of 1."
::= { settings-system 1 }


sleep-mode OBJECT-TYPE
    SYNTAX      INTEGER {
                          eFalse(1),
                          eTrue(2)
		   }
    ACCESS      read-only
    STATUS      optional
       DESCRIPTION "Returns eTrue if the device is in energy saving sleep mode,
                otherwise returns eFalse. Setting SLEEP-MODE to eFalse causes
                the device to wake up, if it is in sleep mode. Setting
                SLEEP-MODE to eTrue causes the device to go into sleep mode.
                Additional information:
                The product will always be in
                sleep mode except when either processing a print job or
                in an error state."
::= { settings-system 2 }


service-password OBJECT-TYPE
    SYNTAX      INTEGER
    ACCESS      write-only
    STATUS      optional
       DESCRIPTION "When set to the password value, other service related objects
                become 'visible' (i.e readable) or become writable. When
                written with any other value, the service related objects
                become 'hidden' (i.e. are no longer readable) or are not longer
                writable. The objects that can be effected by the
                SERVICE-PASSWORD object include: SERIAL-NUMBER and
                TOTAL-ENGINE-PAGE-COUNT. The password value, and the list of
                objects effected by the SERVICE-PASSWORD being set to the
                correct value, should be documented in the device POS.
                Additional information:
                The objects that can be effected by the SERVICE-
                PASSWORD are:  SCANNER-JAM-PAGE-COUNT, SCANNER-ADF-PAGE
                -COUNT, SCAN-ADF-PAGE-COUNT, SCANNER-RETRIEVE-SCANLINE,
                SCANNER-MOTOR-CONTROL, COPIER-ADF-PAGE-COUNT, COPIER-
                PRINT-PAGE-COUNT, TOTAL-ENGINE-PAGE-COUNT, PRINT-ENGINE-
                JAM-COUNT, PRINT-ENGINE-MISPICK-COUNT, CLEAR-NVRAM"
::= { settings-system 9 }


device-configure-custom-product-number OBJECT-TYPE
    SYNTAX      OCTET STRING
    ACCESS      read-only
    STATUS      optional
       DESCRIPTION "This object allows manufacturing to change the product number
                to a pre-defined alternate after release. This feature will
                allow manufacturing to assign unique product numbers to custom
                product bundles when the device is unable to determine its
                product number in firmware. For example, A HP Color LaserJet
                CP1515n could be configured to display CP1516n to the customer.
                This product number must be defined prior to release.
                Additional information:
                This object allows manufacturing to change the product number
                to a pre-defined alternate after release. This feature will
                allow manufacturing to assign unique product numbers to custom
                product bundles when the device is unable to determine its
                product number in firmware. For example, A HP Color LaserJet
                CP1515n could be configured to display CP1516n to the customer.
                This product number must be defined prior to release."
::= { device-configure 19 }


control-panel-button-press-delay OBJECT-TYPE
    SYNTAX      INTEGER
    ACCESS      read-write
    STATUS      optional
       DESCRIPTION "This object gives the number of seconds to wait before
                simulating the button press when CONTROL-PANEL-BUTTON-PRESS is
                next called.
                Additional information:
                This object gives the number of seconds to wait before
                simulating the button press when CONTROL-PANEL-BUTTON-PRESS is
                next called."
::= { settings-system 47 }


low-power OBJECT-TYPE
    SYNTAX      INTEGER
    ACCESS      read-write
    STATUS      optional
       DESCRIPTION "Returns or changes the Auto Low Power sleep value. The device
                will go into energy saving Auto Low Power mode after the print
                engine has been idle for the number of seconds specified by
                this object. Frida supports values of 300 until 14400 seconds.
                If the value is invalid then it will return status of
                PML_Status_ErrUnsupValue and will not issue command to the
                engine.
                Additional information:
                Returns or changes the Auto Low Power sleep value. The device
                will go into energy saving Auto Low Power mode after the print
                engine has been idle for the number of seconds specified by
                this object. The product supports values of 0 (Off), 60 (1
                minute), 900 (15 minutes), 1800 (30 minutes), 3600 (1 hour),
                7200 (2 hours), and 14400 (4 hours).
                If the value is invalid then it will return a status of
                PML_ERROR_INVALID_OR_UNSUPPORTED_VALUE and will not issue
                a command to the engine."
::= { settings-system 49 }


control-panel-display-contrast OBJECT-TYPE
    SYNTAX      INTEGER {
                          eLightest(1),
                          eLight(2),
                          eMedium(3),
                          eDark(4),
                          eDarkest(5)
		   }
    ACCESS      read-write
    STATUS      optional
       DESCRIPTION "This object returns or sets the display contrast setting if the
                control panel has a display and it supports contrast
                adjustment. The setting Is stored in NVRAM, so the value is
                saved over power cycles.
                Additional information:
                This object returns or sets the display contrast setting
                			if the control panel has a display and it supports
                			contrast adjustment. The setting is stored in NVRAM,
                			so the value is saved over power cycles."
::= { settings-system 73 }


io-timeout OBJECT-TYPE
    SYNTAX      INTEGER(5..7200)
    ACCESS      read-write
    STATUS      optional
       DESCRIPTION "The amount of time, in seconds, to wait for more print job data
                to be received before an I/O timeout occurs. The I/O channel
                being timed is the I/O channel that received the data
                associated with the current print job. If an I/O timeout
                occurs, the PDL processing sub-system assumes all the data
                associated with the current print job has been received, and
                processes the end of job in a PDL specific manner. The POS
                specifies the supported values.
                Additional information:
                If an I/O timeout occurs,the PDL processing
                sub-system will consider it an end of job condition only
                if there is data from another I/O subsystem waiting to be
                processed.
                The supported values are 5 to 7200 seconds.  Setting to a
                value outside the supported range returns
                <badValue> status."
::= { settings-io 1 }


io-switch OBJECT-TYPE
    SYNTAX      INTEGER {
                          eYes(1)
		   }
    ACCESS      read-only
    STATUS      optional
       DESCRIPTION "Indicates if the device will switch between I/O channels when a
                job boundary is encountered and print job data is available on
                another I/O channel."
::= { settings-io 2 }


default-copies OBJECT-TYPE
    SYNTAX      INTEGER(1..999)
    ACCESS      read-write
    STATUS      optional
       DESCRIPTION "Returns or changes default copies. Default copies is the
                default values used by the PDL to control the number of copies
                of each page in the print job that are printed. The print job
                can override this value. The list of supported values should be
                documented in the device POS.
                Additional information:
                 The supported values are 1 through 999.
                Setting to an unsupported value causes the printer to
                substitute in a snap value and to return
                <noError> status.
                The snaps are as follows:
                <1 snaps to
                >999 snaps to 999"
::= { settings-pdl 4 }


default-vertical-black-resolution OBJECT-TYPE
    SYNTAX      INTEGER
    ACCESS      read-write
    STATUS      optional
       DESCRIPTION "Returns or changes the value of the default vertical black
                resolution. The units are dots per inch.
                Additional information:
                In the product, changing this OID
                also causes DEFAULT-HORIZONTAL-BLACK RESOLUTION to
                change.  DEFAULT-HORIZONTAL-BLACK-RESOLUTION and
                DEFAULT-VERTICAL-BLACK-RESOLUTION must always be the
                same.  The supported values are 600, and 1200.
                		When the default monochrome resolution or bits-per-pixel
                		are changed to anything other than 600x1 the product
                no longer prints color jobs.  Color jobs are always 600x1.

                Setting to an unsupported value causes the printer to
                substitute in a snap value and to return
                <noError> status.

                The snap values are as follows:
                <450 will snap to 600
                >=450 and <900 will snap to 600
                >=900 will snap to 1200"
::= { settings-pdl 8 }


default-horizontal-black-resolution OBJECT-TYPE
    SYNTAX      INTEGER
    ACCESS      read-write
    STATUS      optional
       DESCRIPTION "Returns or changes the value of the default horizontal black
                resolution. The units are dots per inch.
                Additional information:
                In the product, changing this OID
                also causes DEFAULT-VERTICAL-BLACK RESOLUTION to change.
                DEFAULT-HORIZONTAL-BLACK-RESOLUTION and
                DEFAULT-VERTICAL-BLACK-RESOLUTION must always be the
                same.  The supported values are 600 and 1200. When the default
                		monochrome resolution or bits-per-pixel are changed to
                		anything other than 600x1 the product no longer prints color
                		jobs. Color jobs are always 600x1.


                Setting to an unsupported value causes the printer to
                substitute in a snap value and to return
                <noError> status.

                The snap values are as follows:
                <450 snaps to 600
                >=450 and <900 snaps to 600
                >=900 snaps to 1200"
::= { settings-pdl 9 }


default-lines-per-page OBJECT-TYPE
    SYNTAX      INTEGER
    ACCESS      read-write
    STATUS      optional
       DESCRIPTION "Returns or changes the default number of lines per page. The
                POS indicates the supported values. An unsupported value causes
                the printer to use the closest supported value, causing the
                printer to return the <noError>.
                Additional information:
                The supported values in the product
                are 5 to 128.  Setting to an unsupported value
                causes the printer to substitute in a snap value and to
                return <noError> status.

                The snap values are as follows:
                <5 snaps to 5
                >128 snaps to 128"
::= { settings-pdl 11 }


default-vmi OBJECT-TYPE
    SYNTAX      INTEGER
    ACCESS      read-write
    STATUS      optional
       DESCRIPTION "Returns or changes the default vertical motion index. The unit
                of measure for VMI is centipoints per line. The POS indicates
                the supported values. An unsupported value causes the printer
                to use the closest supported value, causing the printer to
                return <noError>.
                Additional information:
                Setting this object may cause
                DEFAULT-LINES-PER-PAGE to change."
::= { settings-pdl 12 }


default-media-size OBJECT-TYPE
    SYNTAX      INTEGER {
                          eUSExecutive(1),
                          eUSLetter(2),
                          eUSLegal(3),
                          eFoolscap(10),
                          eROC16K(17),
                          eISOandJISA4(26),
                          eISOandJISA5(25),
                          eROC16K195X270(34),
                          eJISB5(45),
                          eISOB5(65),
                          eJapanesePostcardSingle(71),
                          eJapanesePostcardDouble(72),
                          eMonarch(80),
                          eCommercial10(81),
                          eROC16K184X260(89),
                          eInternationalDL(90),
                          eInternationalC5(91),
                          eInternationalB5(100),
                          eCustom(101)
		   }
    ACCESS      read-write
    STATUS      optional
       DESCRIPTION "This indicates the default media size. A write of an
                unsupported value causes an <ErrorInvalidOrUnsupported Value>.		Complete list of supported media sizes along with their
                dimensions are listed in the ''Media Size Table'' near the end
                of this document. (for a full list of media size enums see the
                end of this file) "
::= { settings-pdl 13 }


cold-reset-media-size OBJECT-TYPE
    SYNTAX      INTEGER {
                          eUSLetter(2),
                          eISOandJISA4(26)
		   }
    ACCESS      read-write
    STATUS      optional
       DESCRIPTION "Returns or sets the media size that is used as the
                DEFAULT-MEDIA-SIZE when a cold reset occurs."
::= { settings-pdl 19 }


default-media-name OBJECT-TYPE
    SYNTAX      OCTET STRING
    ACCESS      read-write
    STATUS      optional
       DESCRIPTION "Returns or sets the media name that is used until the media
                name is changed by a print job command.
                Additional information:
                This string must be one of the MEDIAn-NAME
                objects, except it cannot be set to ANY.
                The value of this object is saved across
                		            a power cycle."
::= { settings-pdl 22 }


reprint OBJECT-TYPE
    SYNTAX      INTEGER {
                          eOff(1),
                          eOn(2),
                          eAuto(3)
		   }
    ACCESS      read-write
    STATUS      optional
       DESCRIPTION "Returns or changes the reprint (jam recovery) setting. If eOn,
                then the device will reprint pages jammed pages. If eOff, the
                device will not attempt to reprint jammed pages. If eAuto, a
                device dependent algorithm (which should be documented in the
                POS) will be used to determine if the page gets reprinted. This
                object controls all PDLs, unless a specific PDL supports its
                own reprint control mechanism. To date, only PostScript has a
                PDL reprint control mechanism.
                Additional information:
                Setting this object when the printer is not
                idle, may cause a status of <noError> to be returned, but
                the new value will not take effect until a job boundary
                is reached.  If a get is done on object before the job
                boundary is reached, the value last set will be
                returned.

                When the value is set to eOff, pages will not be stored
                in the printer, and in the event of a paper jam, will
                have to be reprinted.  When the value is set to eOn,
                pages will be stored until delivery, therefore, in the
                event of a paper jam, the page will be reprinted.

                When the value is set to eAuto, the printer will behave
                as though it is eOff when there is less than seven
                megabytes of memory installed in the printer.  When
                additional memory is installed, to total at least seven
                megabytes of RAM, the setting of eAuto will behave as
                though it was set to eOn."
::= { settings-pdl 36 }


wide-a4 OBJECT-TYPE
    SYNTAX      INTEGER {
                          eOff(1),
                          eOn(2)
		   }
    ACCESS      read-write
    STATUS      optional
       DESCRIPTION "Returns or changes the wide A4 logical page size setting. If
                eOn, then the margins/printable area of A4 paper will be
                changed to allow 80 10-pitch characters to be printed on a
                single line. If eOff then the industry standard A4 logical page
                size is used."
::= { settings-pdl 37 }


dark-courier OBJECT-TYPE
    SYNTAX      INTEGER {
                          eOff(1),
                          eOn(2)
		   }
    ACCESS      read-write
    STATUS      optional
       DESCRIPTION "Returns or changes the dark Courier setting. If eOn, then the
                Courier font used will approximate the same darkness as the
                LaserJet III printer. If eOff, then the Courier font used will
                approximate the same darkness as the LaserJet 4 printer."
::= { settings-pdl 38 }


default-bits-per-pixel OBJECT-TYPE
    SYNTAX      INTEGER
    ACCESS      read-write
    STATUS      optional
       DESCRIPTION "Controls the number of levels used (per pixel) when printing
                grayscale or color images."
::= { settings-pdl 39 }


pcl-total-page-count OBJECT-TYPE
    SYNTAX      INTEGER
    ACCESS      read-write
    STATUS      optional
       DESCRIPTION "Total number of PCL pages printed by the device."
::= { pdl-pcl 5 }


pcl-default-font-height OBJECT-TYPE
    SYNTAX      INTEGER
    ACCESS      read-write
    STATUS      optional
       DESCRIPTION "Returns or changes the default PCL height. Height is an
                approximate measure of the body of the type in centipoints. A
                centipoint is 1/7200 inch. Height applies only to proportional
                fonts. Point size, in points, can be converted to font height,
                in centipoints, by multiplying the point size by 100. The POS
                indicates the supported values. An unsupported value causes the
                printer to use the closest supported value, causing the printer
                to return <noError>. ''Closest'' means
                the smallest absolute difference.
                Additional information:
                This object refers to the font point size
                with 400 representing the smallest settable font (4) and
                99975 representing the largest settable font (999.75).
                The default of 1200 is a font point size of 12.

                Supported values range from 400 to 99975.  Setting to an
                unsupported value causes the printer to substitute in a
                snap value and to return
                <noError> status.

                The snap values are as follows:
                <=400 snaps to 400
                >=99975 snaps to 99975

                Fonts are settable to the nearest quarter point size
                (i.e.  10, 10.25, 10.50, 10.75).  Unsupported values in
                the range 401 to 99974 snap DOWN to the previous
                supported value (i.e 25293 snaps to 25275 or 75038 snaps
                to 75025)."
::= { pdl-pcl 13 }


pcl-default-font-source OBJECT-TYPE
    SYNTAX      INTEGER {
                          eInternal(1),
                          ePermanentSoft(2),
                          eRomSimm1(10)
		   }
    ACCESS      read-write
    STATUS      optional
       DESCRIPTION "Returns or changes the value of the default font source
                variable in NVRAM."
::= { pdl-pcl 14 }


pcl-default-font-number OBJECT-TYPE
    SYNTAX      INTEGER(0..255)
    ACCESS      read-write
    STATUS      optional
       DESCRIPTION "Returns or changes the value of the default font number
                variable in NVRAM. Writing an unsupported value causes the
                printer to generate an <badValue>.
                Additional information:
                Valid numbers or 0 - 255, but only font
                numbers that are included in the PCL FONT LIST are
                selectable."
::= { pdl-pcl 15 }


pcl-default-font-width OBJECT-TYPE
    SYNTAX      INTEGER
    ACCESS      read-write
    STATUS      optional
       DESCRIPTION "Returns or changes the default PCL font width. Width is
                expressed as the width of a character in centipoints. A
                centipoint is 1/7200 inch. Width applies only to fixed space
                fonts. Pitch, in character per inch, can be converted to font
                width, in centipoints, by dividing 7200 by the pitch. The POS
                indicates the supported values. An unsupported value causes the
                printer to use the closest supported value, causing the printer
                to return <noError>. ''Closest'' means
                the smallest absolute difference.
                Additional information:
                Setting to an unsupported value causes the
                printer to substitue in a snap value (listed below) and
                return <noError> status.

                The snap values for pitch are as follow:
                <=44 snaps to 44
                >=9999 snaps to 9999

                Unsupported values in the range 44 - 9999 (.44 - 99.99)
                snap DOWN to the next supported value."
::= { pdl-pcl 16 }


postscript-total-page-count OBJECT-TYPE
    SYNTAX      INTEGER
    ACCESS      read-write
    STATUS      optional
       DESCRIPTION "Total number of PostScript pages printed by the device."
::= { pdl-postscript 5 }


postscript-print-errors OBJECT-TYPE
    SYNTAX      INTEGER {
                          eOff(1),
                          eOn(2)
		   }
    ACCESS      read-write
    STATUS      optional
       DESCRIPTION "Returns or changes the value of the print PostScript errors
                setting. If eOn, PostScript prints an error page showing the
                error encountered and the stack at the time of the error.
                Additional information:
                Returns or changes the value of the print PostScript errors
                setting. If eOn, PostScript prints an error page showing the
                error encountered and the stack at the time of the error."
::= { pdl-postscript 11 }


pclxl-total-page-count OBJECT-TYPE
    SYNTAX      INTEGER
    ACCESS      read-write
    STATUS      optional
       DESCRIPTION "Total number of PCLXL pages printed by the device."
::= { pdl-pclxl 1 }


pjl-password OBJECT-TYPE
    SYNTAX      INTEGER
    ACCESS      read-only
    STATUS      optional
       DESCRIPTION "Returns PJL password, if the password is not set (zero). If the
                password is set, then attempting to retrieve the password
                causes an <genErr> to occur and will return
                the <NullValue>."
::= { pjl 1 }


print-density OBJECT-TYPE
    SYNTAX      INTEGER(1..5)
    ACCESS      read-write
    STATUS      optional
       DESCRIPTION "Returns or sets the print density setting. Print density is the
                instantaneous amount of marking agent applied to the paper
                while printing. A value of zero has the lowest print density,
                yielding a lighter page. A value of 10 has the highest print
                density, yielding a darker page. Each POS should document what
                values in the 0 to 10 range are supported.
                Additional information:
                When this value is written, the page
                pipeline will be flushed (all pages being printed are
                completed, no new ones are started), the new density
                setting is set and printing resumes.  The acutal change
                in print density may be gradual over several pages.

                The supported values are 1 through 5.  Setting to an
                unsupported value causes the printer to substitue in a
                a snap value and to return <noError>
                status.

                The snap values are as follows:
                <1 snaps to 1
                >5 snaps to 5."
::= { settings-prt-eng 5 }


invalid-personality-reports-enabled OBJECT-TYPE
    SYNTAX      INTEGER {
                          eDisabled(1),
                          eEnabled(2)
		   }
    ACCESS      read-write
    STATUS      optional
       DESCRIPTION "Read or configure wether invalid personality reports are
                enabled or disabled for a product."
::= { settings-prt-eng 18 }


total-engine-page-count OBJECT-TYPE
    SYNTAX      INTEGER
    ACCESS      read-write
    STATUS      optional
       DESCRIPTION "Total number of pages printed by the device. POS indicates if
                the total engine page count is kept in NVRAM, and the maximum
                supported value before the page count rolls over to zero.
                Additional information:
                This object is stored in NVRAM.  The maximum value of
                this count is 1000000 before it rolls over to zero."
::= { status-prt-eng 5 }


print-engine-jam-count OBJECT-TYPE
    SYNTAX      INTEGER
    ACCESS      read-write
    STATUS      optional
       DESCRIPTION "Total number of pages jammed in the print engine's life time.
                The POS indicates if the total jam count is kept in NVRAM and
                the maximum supported value before the jam count rolls over to
                zero.
                Additional information:
                This object is stored in NVRAM. The maximum value of
                this count is 65000 before it rolls over to zero."
::= { status-prt-eng 34 }


print-engine-mispick-count OBJECT-TYPE
    SYNTAX      INTEGER
    ACCESS      read-write
    STATUS      optional
       DESCRIPTION "Total number of pages mispicked in the print engine's life
                time. The POS indicates if the total mispick count is kept in
                NVRAM and the maximum supported value before the mispick count
                rolls over to zero.
                Additional information:
                This object is stored in NVRAM. The maximum value of
                this count is 65000 before it rolls over to zero."
::= { status-prt-eng 35 }


supply-out-device-state OBJECT-TYPE
    SYNTAX      INTEGER {
                          eNoSupplyOut(1),
                          eOffline(2),
                          eSupplyOutOverride(3),
                          eMonochromePrintingAfterColorCartridgeOut(4)
		   }
    ACCESS      read-only
    STATUS      optional
       DESCRIPTION "This PML object indicates the current behavior of the device if
                one or more supplies have reached out. If no supply has reached
                out, the value of this PML object is eNoSupplyOut. If one or
                more supplies have reached out, the value of this PML object
                will indicate if the printer is online and if so what mode is
                being used to continue printing.
                Additional information:
                This PML object indicates the current behavior of the device if
                one or more supplies have reached out. If no supply has reached
                out, the value of this PML object is eNoSupplyOut. If one or
                more supplies have reached out, the value of this PML object
                will indicate if the printer is online and if so what mode is
                being used to continue printing. If the printer is in both
                eSupplyOutOverride and eMonochromePrintingAfterColorCartridgeOut
                then eMonochromePrintingAfterColorCartridgeOut will be returned."
::= { status-prt-eng 49 }


duplex-page-count OBJECT-TYPE
    SYNTAX      INTEGER
    ACCESS      read-write
    STATUS      optional
       DESCRIPTION "Total number of sheets of media that have been duplex printed.
                A sheet is counted if it travels through the duplex page path,
                regardless of whether or not marks are made on the page. The
                POS will indicate if the value is kept in NVRAM.
                Additional information:
                Total number of sheets of media that have been duplex printed.
                	     A sheet is counted if it travels through the duplex page path,
                	     regardless of whether or not marks are made on the page.
                	                     This object is stored in NVRAM. The maximum value of
                		     this count is 65000 before it rolls over to zero."
::= { status-prt-eng 22 }


print-engine-revision OBJECT-TYPE
    SYNTAX      OCTET STRING
    ACCESS      read-only
    STATUS      optional
       DESCRIPTION "Print engine revision string.
                Additional information:
                Print engine revision string."
::= { status-prt-eng 26 }


custom-paper-dim-unit OBJECT-TYPE
    SYNTAX      INTEGER {
                          eTenThousandthsOfInches(3),
                          eMicrometers(4)
		   }
    ACCESS      read-write
    STATUS      optional
       DESCRIPTION "The units of measure used to specify the width and height of
                the printer's custom paper. The unit of measure of
                eTenThousandthsOfInches is 0.0001 inches.
                Additional information:
                The only valid values for this object are
                eTenThousandthsOfInches (3), and eMicrometers (4).  The
                data for this object is stored in NVRAM."
::= { settings-intray 7 }


custom-paper-feed-dim OBJECT-TYPE
    SYNTAX      INTEGER(50000..140000)
    ACCESS      read-write
    STATUS      optional
       DESCRIPTION "Sets the printer's custom paper dimension in the feed direction
                (direction parallel to the direction of paper feeding). The
                value for this object is specified in micrometers or
                tenthousandths of an inch, depending upon the value of
                CUSTOM-PAPER-DIM-UNIT. The valid range is engine-dependent and
                should be documented in the POS for each product.
                Additional information:
                 The valid range is 50000 to 140000 if
                CUSTOM-PAPER_DIM_UNIT is eTenThousandthsOfInches or 127000 to
                355600 if CUSTOM-PAPER-DIM-UNIT is ePmicrometers.  Attempts
                to set this object outside the valid range will result in a
                return value of ERROR_INVALID_OR_UNSUPPORTED_VALUE."
::= { settings-intray 8 }


custom-paper-xfeed-dim OBJECT-TYPE
    SYNTAX      INTEGER(30000..85000)
    ACCESS      read-write
    STATUS      optional
       DESCRIPTION "Sets the printer's custom paper dimension in the cross-feed
                direction (direction ninety degrees relative to the direction
                of paper feeding). The value for this object is specified in
                micrometers or tenthousandths of an inch, depending upon the
                value of CUSTOM-PAPER-DIM-UNIT. The valid range is
                engine-dependent and should be documented in the POS for each
                product.
                Additional information:
                The valid range for the product
                		is 30000 to 85000 if CUSTOM-PAPER-DIM-UNIT is
                eTenThousandthsOfInches or 76200 to 215900 if
                CUSTOM-PAPER-DIM-UNIT is ePmicrometers.  Attempts to set
                this object outside the valid range will result in a
                return value of <badValue>."
::= { settings-intray 9 }


tray1-media-size-loaded OBJECT-TYPE
    SYNTAX      INTEGER {
                          eUSExecutive(1),
                          eUSLetter(2),
                          eUSLegal(3),
                          eFoolscap(10),
                          eROC16K(17),
                          eISOandJISA6(24),
                          eISOandJISA5(25),
                          eISOandJISA4(26),
                          eROC16K195X270(34),
                          eJISB5(45),
                          eJapansePostcardSingle(71),
                          eJapansePostcardDouble(72),
                          eIndexCard5x8(75),
                          ePhoto4x6(76),
                          eMonarch(80),
                          eCommercial10(81),
                          eROC16K184X260(89),
                          eInternationalDL(90),
                          eInternationalC5(91),
                          eInternationalB5(100),
                          eCustom(101),
                          ePhoto10x15(118),
                          eAnySize(32765)
		   }
    ACCESS      read-write
    STATUS      optional
       DESCRIPTION "Returns the media size that is currently configuredconfigured
                in tray #1. This object can be set to indicate the media size
                currently loaded, if the printer supports input trays that can
                not sense the media size. Complete list of supported media
                sizes along with their dimensions are listed in the ''Media
                Size Table'' near the end of this document."
::= { intray1 1 }


tray2-media-size-loaded OBJECT-TYPE
    SYNTAX      INTEGER {
                          eUSExecutive(1),
                          eUSLetter(2),
                          eUSLegal(3),
                          eFoolscap(10),
                          eROC16K(17),
                          eISOandJISA6(24),
                          eISOandJISA5(25),
                          eISOandJISA4(26),
                          eROC16K195X270(34),
                          eJISB5(45),
                          eJapansePostcardSingle(71),
                          eJapansePostcardDouble(72),
                          eIndexCard5x8(75),
                          ePhoto4x6(76),
                          eMonarch(80),
                          eCommercial10(81),
                          eROC16K184X260(89),
                          eInternationalDL(90),
                          eInternationalC5(91),
                          eInternationalB5(100),
                          eCustom(101),
                          ePhoto10x15(118),
                          eAnySize(32765)
		   }
    ACCESS      read-write
    STATUS      optional
       DESCRIPTION "Returns the media size that is currently configured in tray #2.
                Complete list of supported media sizes along with their
                dimensions are listed in the ''Media Size Table'' near the end
                of this document."
::= { intray2 1 }


tray3-media-size-loaded OBJECT-TYPE
    SYNTAX      INTEGER {
                          eUSExecutive(1),
                          eUSLetter(2),
                          eUSLegal(3),
                          eFoolscap(10),
                          eROC16K(17),
                          eISOandJISA6(24),
                          eISOandJISA5(25),
                          eISOandJISA4(26),
                          eROC16K195X270(34),
                          eJISB5(45),
                          eJapansePostcardSingle(71),
                          eJapansePostcardDouble(72),
                          eIndexCard5x8(75),
                          ePhoto4x6(76),
                          eMonarch(80),
                          eCommercial10(81),
                          eROC16K184X260(89),
                          eInternationalDL(90),
                          eInternationalC5(91),
                          eInternationalB5(100),
                          eCustom(101),
                          ePhoto10x15(118),
                          eAnySize(32765)
		   }
    ACCESS      read-write
    STATUS      optional
       DESCRIPTION "Returns the media size that is currently configured in tray #3.
                Complete list of supported media sizes along with their
                dimensions are listed in the ''Media Size Table'' near the end
                of this document."
::= { intray3 1 }


default-ret OBJECT-TYPE
    SYNTAX      INTEGER {
                          eOff(1),
                          eLight(2),
                          eMedium(3),
                          eDark(4)
		   }
    ACCESS      read-write
    STATUS      optional
       DESCRIPTION "Returns or changes the Resolution Enhancement Technology
                setting. Devices that only support eOff and eOn should map all
                other values to eOn and always return the same non-eOff value
                to indicatep on. The list of supported values should be
                documented in the device POS."
::= { imaging 5 }


media-names-available OBJECT-TYPE
    SYNTAX      OCTET STRING
    ACCESS      read-only
    STATUS      optional
       DESCRIPTION "The value of this object controls which of the MEDIAx-NAME
                objects are supported. If a bit is set to zero, then attempting
                to get or set the corresponding MEDIAx-NAME objects will return
                <noSuchName>.
                Additional information:
                Since this object is read-only, the corresponding MEDIAx
                			objects will always be available.  The DEFAULTS below
                represent which MediaNameX is available on this product
                of the total possible available defined in SYNTAX, so the
                collection is like a bitfield. Raptor does not support
                cMediaName32Available"
::= { settings-print-media 1 }


media1-name OBJECT-TYPE
    SYNTAX      OCTET STRING
    ACCESS      read-only
    STATUS      optional
       DESCRIPTION "Media 1 name.
                Additional information:
                The symbol set for this string is Roman-8."
::= { media1 1 }


media1-engine-media-mode OBJECT-TYPE
    SYNTAX      INTEGER
    ACCESS      read-only
    STATUS      optional
       DESCRIPTION "The engine processing characteristics that are to be applied to
                this media. The processing characteristics are device
                specific.
                Additional information:
                The engine processing characteristics that are to
                be applied to this media type. Currently, 'engine
                processing characteristics' denotes changes to
                fusing temperature and/or transfer roller voltage."
::= { media1 4 }


media2-name OBJECT-TYPE
    SYNTAX      OCTET STRING
    ACCESS      read-only
    STATUS      optional
       DESCRIPTION "Media 2 name.
                Additional information:
                The symbol set for this string is Roman-8."
::= { media2 1 }


media2-engine-media-mode OBJECT-TYPE
    SYNTAX      INTEGER
    ACCESS      read-write
    STATUS      optional
       DESCRIPTION "The engine processing characteristics that are to be applied to
                this media. The processing characteristics are device
                specific.
                Additional information:
                See the description for MEDIA1-ENGINE-MEDIA-MODE."
::= { media2 4 }


media3-name OBJECT-TYPE
    SYNTAX      OCTET STRING
    ACCESS      read-only
    STATUS      optional
       DESCRIPTION "Media 3 name.
                Additional information:
                The symbol set for this string is Roman-8."
::= { media3 1 }


media3-engine-media-mode OBJECT-TYPE
    SYNTAX      INTEGER
    ACCESS      read-write
    STATUS      optional
       DESCRIPTION "The engine processing characteristics that are to be applied to
                this media. The processing characteristics are device
                specific.
                Additional information:
                See the description for MEDIA1-ENGINE-MEDIA-MODE."
::= { media3 4 }


media4-name OBJECT-TYPE
    SYNTAX      OCTET STRING
    ACCESS      read-only
    STATUS      optional
       DESCRIPTION "Media 4 name.
                Additional information:
                The symbol set for this string is Roman-8."
::= { media4 1 }


media4-engine-media-mode OBJECT-TYPE
    SYNTAX      INTEGER
    ACCESS      read-write
    STATUS      optional
       DESCRIPTION "The engine processing characteristics that are to be applied to
                this media. The processing characteristics are device
                specific.
                Additional information:
                See the description for MEDIA1-ENGINE-MEDIA-MODE."
::= { media4 4 }


media5-name OBJECT-TYPE
    SYNTAX      OCTET STRING
    ACCESS      read-only
    STATUS      optional
       DESCRIPTION "Media 5 name.
                Additional information:
                The symbol set for this string is Roman-8."
::= { media5 1 }


media5-engine-media-mode OBJECT-TYPE
    SYNTAX      INTEGER
    ACCESS      read-write
    STATUS      optional
       DESCRIPTION "The engine processing characteristics that are to be applied to
                this media. The processing characteristics are device
                specific.
                Additional information:
                See the description for MEDIA1-ENGINE-MEDIA-MODE.
                Raptor will havea  default value of 4"
::= { media5 4 }


media6-name OBJECT-TYPE
    SYNTAX      OCTET STRING
    ACCESS      read-only
    STATUS      optional
       DESCRIPTION "Media 6 name.
                Additional information:
                The symbol set for this string is Roman-8."
::= { media6 1 }


media6-engine-media-mode OBJECT-TYPE
    SYNTAX      INTEGER
    ACCESS      read-write
    STATUS      optional
       DESCRIPTION "The engine processing characteristics that are to be applied to
                this media. The processing characteristics are device
                specific.
                Additional information:
                Raptor will have a default value of 5.
                See the description for MEDIA1-ENGINE-MEDIA-MODE."
::= { media6 4 }


media7-name OBJECT-TYPE
    SYNTAX      OCTET STRING
    ACCESS      read-only
    STATUS      optional
       DESCRIPTION "Media 7 name.
                Additional information:
                The symbol set for this string is Roman-8."
::= { media7 1 }


media7-engine-media-mode OBJECT-TYPE
    SYNTAX      INTEGER
    ACCESS      read-write
    STATUS      optional
       DESCRIPTION "The engine processing characteristics that are to be applied to
                this media. The processing characteristics are device
                specific.
                Additional information:
                Raptor will have a default value of 5.
                See the description for MEDIA1-ENGINE-MEDIA-MODE."
::= { media7 4 }


media8-name OBJECT-TYPE
    SYNTAX      OCTET STRING
    ACCESS      read-only
    STATUS      optional
       DESCRIPTION "Media 8 name.
                Additional information:
                The symbol set for this string is Roman-8."
::= { media8 1 }


media8-engine-media-mode OBJECT-TYPE
    SYNTAX      INTEGER
    ACCESS      read-write
    STATUS      optional
       DESCRIPTION "The engine processing characteristics that are to be applied to
                this media. The processing characteristics are device
                specific.
                Additional information:
                Raptor will have a default value of 6.
                See the description for MEDIA1-ENGINE-MEDIA-MODE."
::= { media8 4 }


media9-name OBJECT-TYPE
    SYNTAX      OCTET STRING
    ACCESS      read-only
    STATUS      optional
       DESCRIPTION "Media 9 name.
                Additional information:
                The symbol set for this string is Roman-8."
::= { media9 1 }


media9-engine-media-mode OBJECT-TYPE
    SYNTAX      INTEGER
    ACCESS      read-write
    STATUS      optional
       DESCRIPTION "The engine processing characteristics that are to be applied to
                this media. The processing characteristics are device
                specific.
                Additional information:
                Raptor will have a default value of 7.
                See the description for MEDIA1-ENGINE-MEDIA-MODE."
::= { media9 4 }


media10-name OBJECT-TYPE
    SYNTAX      OCTET STRING
    ACCESS      read-only
    STATUS      optional
       DESCRIPTION "Media 10 name.
                Additional information:
                The symbol set for this string is Roman-8."
::= { media10 1 }


media10-engine-media-mode OBJECT-TYPE
    SYNTAX      INTEGER
    ACCESS      read-write
    STATUS      optional
       DESCRIPTION "The engine processing characteristics that are to be applied to
                this media. The processing characteristics are device
                specific.
                Additional information:
                See the description for MEDIA1-ENGINE-MEDIA-MODE."
::= { media10 4 }


media11-name OBJECT-TYPE
    SYNTAX      OCTET STRING
    ACCESS      read-only
    STATUS      optional
       DESCRIPTION "Media 11 name.
                Additional information:
                The symbol set for this string is Roman-8."
::= { media11 1 }


media11-engine-media-mode OBJECT-TYPE
    SYNTAX      INTEGER
    ACCESS      read-write
    STATUS      optional
       DESCRIPTION "The engine processing characteristics that are to be applied to
                this media. The processing characteristics are device
                specific.
                Additional information:
                Raptor will have a default value of 8.
                See the description for MEDIA1-ENGINE-MEDIA-MODE."
::= { media11 4 }


media12-name OBJECT-TYPE
    SYNTAX      OCTET STRING
    ACCESS      read-only
    STATUS      optional
       DESCRIPTION "Media 12 name.
                Additional information:
                Raptor will have a default value of 'Light'.
                The symbol set for this string is Roman-8."
::= { media12 1 }


media12-engine-media-mode OBJECT-TYPE
    SYNTAX      INTEGER
    ACCESS      read-write
    STATUS      optional
       DESCRIPTION "The engine processing characteristics that are to be applied to
                this media. The processing characteristics are device
                specific.
                Additional information:
                Raptor will have a default value of 2.
                See the description for MEDIA1-ENGINE-MEDIA-MODE."
::= { media12 4 }


media13-name OBJECT-TYPE
    SYNTAX      OCTET STRING
    ACCESS      read-only
    STATUS      optional
       DESCRIPTION "Media 13 name.
                Additional information:
                Raptor will have a default value of 'Mid Weight'
                The symbol set for this string is Roman-8."
::= { media13 1 }


media13-engine-media-mode OBJECT-TYPE
    SYNTAX      INTEGER
    ACCESS      read-write
    STATUS      optional
       DESCRIPTION "The engine processing characteristics that are to be applied to
                this media. The processing characteristics are device
                specific.
                Additional information:
                Raptor will have a default value of 3
                See the description for MEDIA1-ENGINE-MEDIA-MODE."
::= { media13 4 }


media14-name OBJECT-TYPE
    SYNTAX      OCTET STRING
    ACCESS      read-only
    STATUS      optional
       DESCRIPTION "Media 14 name.
                Additional information:
                Raptor will have a default value of 'Heavy'
                The symbol set for this string is Roman-8."
::= { media14 1 }


media14-engine-media-mode OBJECT-TYPE
    SYNTAX      INTEGER
    ACCESS      read-write
    STATUS      optional
       DESCRIPTION "The engine processing characteristics that are to be applied to
                this media. The processing characteristics are device
                specific.
                Additional information:
                Raptor will have a default value of 4
                See the description for MEDIA1-ENGINE-MEDIA-MODE."
::= { media14 4 }


media15-name OBJECT-TYPE
    SYNTAX      OCTET STRING
    ACCESS      read-only
    STATUS      optional
       DESCRIPTION "Media 15 name.
                Additional information:
                Raptor will have a default value of 'Extra Heavy'
                The symbol set for this string is Roman-8."
::= { media15 1 }


media15-engine-media-mode OBJECT-TYPE
    SYNTAX      INTEGER
    ACCESS      read-write
    STATUS      optional
       DESCRIPTION "The engine processing characteristics that are to be applied to
                this media. The processing characteristics are device
                specific.
                Additional information:
                Raptor will have a default value of 5
                See the description for MEDIA1-ENGINE-MEDIA-MODE."
::= { media15 4 }


media16-name OBJECT-TYPE
    SYNTAX      OCTET STRING
    ACCESS      read-only
    STATUS      optional
       DESCRIPTION "Media 16 name.
                Additional information:
                Raptor will have a default value of 'Heavy Gloss'
                The symbol set for this string is Roman-8."
::= { media16 1 }


media16-engine-media-mode OBJECT-TYPE
    SYNTAX      INTEGER
    ACCESS      read-write
    STATUS      optional
       DESCRIPTION "The engine processing characteristics that are to be applied to
                this media. The processing characteristics are device
                specific.
                Additional information:
                Raptor will have a default value of 6
                See the description for MEDIA1-ENGINE-MEDIA-MODE."
::= { media16 4 }


media17-name OBJECT-TYPE
    SYNTAX      OCTET STRING
    ACCESS      read-only
    STATUS      optional
       DESCRIPTION "Media 17 name.
                Additional information:
                Raptor will have a default value of 'Extra Heavy Gloss'
                The symbol set for this string is Roman-8."
::= { media17 1 }


media17-engine-media-mode OBJECT-TYPE
    SYNTAX      INTEGER
    ACCESS      read-write
    STATUS      optional
       DESCRIPTION "The engine processing characteristics that are to be applied to
                this media. The processing characteristics are device
                specific.
                Additional information:
                Raptor will have a default value of 7
                See the description for MEDIA1-ENGINE-MEDIA-MODE."
::= { media17 4 }


media18-name OBJECT-TYPE
    SYNTAX      OCTET STRING
    ACCESS      read-only
    STATUS      optional
       DESCRIPTION "Media 18 name.
                Additional information:
                Raptor will have a default value of 'Card Glossy'
                The symbol set for this string is Roman-8."
::= { media18 1 }


media18-engine-media-mode OBJECT-TYPE
    SYNTAX      INTEGER
    ACCESS      read-write
    STATUS      optional
       DESCRIPTION "The engine processing characteristics that are to be applied to
                this media. The processing characteristics are device
                specific.
                Additional information:
                Raptor will have a default value of 8.
                See the description for MEDIA1-ENGINE-MEDIA-MODE."
::= { media18 4 }


media19-name OBJECT-TYPE
    SYNTAX      OCTET STRING
    ACCESS      read-only
    STATUS      optional
       DESCRIPTION "Media 19 name.
                Additional information:
                Raptor will have a default value of 'Transparency'
                The symbol set for this string is Roman-8."
::= { media19 1 }


media19-engine-media-mode OBJECT-TYPE
    SYNTAX      INTEGER
    ACCESS      read-write
    STATUS      optional
       DESCRIPTION "The engine processing characteristics that are to be applied to
                this media. The processing characteristics are device
                specific.
                Additional information:
                Raptor will have a default value of 10
                See the description for MEDIA1-ENGINE-MEDIA-MODE."
::= { media19 4 }


media20-name OBJECT-TYPE
    SYNTAX      OCTET STRING
    ACCESS      read-only
    STATUS      optional
       DESCRIPTION "Media 20 name.
                Additional information:
                Raptor will have a default value of 'Labels'
                The symbol set for this string is Roman-8."
::= { media20 1 }


media20-engine-media-mode OBJECT-TYPE
    SYNTAX      INTEGER
    ACCESS      read-write
    STATUS      optional
       DESCRIPTION "The engine processing characteristics that are to be applied to
                this media. The processing characteristics are device
                specific.
                Additional information:
                Raptor will have a default value of 11
                See the description for MEDIA1-ENGINE-MEDIA-MODE."
::= { media20 4 }


media21-name OBJECT-TYPE
    SYNTAX      OCTET STRING
    ACCESS      read-only
    STATUS      optional
       DESCRIPTION "Media 21 name.
                Additional information:
                Raptor will have a default value of 'Letterhead'
                The symbol set for this string is Roman-8."
::= { media21 1 }


media21-engine-media-mode OBJECT-TYPE
    SYNTAX      INTEGER
    ACCESS      read-write
    STATUS      optional
       DESCRIPTION "The engine processing characteristics that are to be applied to
                this media. The processing characteristics are device
                specific.
                Additional information:
                Raptor will have a default value of 1.
                See the description for MEDIA1-ENGINE-MEDIA-MODE."
::= { media21 4 }


media22-name OBJECT-TYPE
    SYNTAX      OCTET STRING
    ACCESS      read-only
    STATUS      optional
       DESCRIPTION "Media 22 name.
                Additional information:
                Raptor will have a default value of 'Envelope'
                The symbol set for this string is Roman-8."
::= { media22 1 }


media22-engine-media-mode OBJECT-TYPE
    SYNTAX      INTEGER
    ACCESS      read-write
    STATUS      optional
       DESCRIPTION "The engine processing characteristics that are to be applied to
                this media. The processing characteristics are device
                specific.
                Additional information:
                Raptor will have a default value of 12.
                See the description for MEDIA1-ENGINE-MEDIA-MODE."
::= { media22 4 }


media23-name OBJECT-TYPE
    SYNTAX      OCTET STRING
    ACCESS      read-only
    STATUS      optional
       DESCRIPTION "Media 23 name.
                Additional information:
                Raptor will have a default value of 'Heavy Envelope'
                The symbol set for this string is Roman-8."
::= { media23 1 }


media23-engine-media-mode OBJECT-TYPE
    SYNTAX      INTEGER
    ACCESS      read-write
    STATUS      optional
       DESCRIPTION "The engine processing characteristics that are to be applied to
                this media. The processing characteristics are device
                specific.
                Additional information:
                Raptor will have a default value of 13
                See the description for MEDIA1-ENGINE-MEDIA-MODE."
::= { media23 4 }


media24-name OBJECT-TYPE
    SYNTAX      OCTET STRING
    ACCESS      read-only
    STATUS      optional
       DESCRIPTION "Media 24 name.
                Additional information:
                Raptor will have a default value of 'Preprinted'
                The symbol set for this string is Roman-8."
::= { media24 1 }


media24-engine-media-mode OBJECT-TYPE
    SYNTAX      INTEGER
    ACCESS      read-write
    STATUS      optional
       DESCRIPTION "The engine processing characteristics that are to be applied to
                this media. The processing characteristics are device
                specific.
                Additional information:
                Raptor will have a default value of 1
                See the description for MEDIA1-ENGINE-MEDIA-MODE."
::= { media24 4 }


media25-name OBJECT-TYPE
    SYNTAX      OCTET STRING
    ACCESS      read-only
    STATUS      optional
       DESCRIPTION "Media 25 name.
                Additional information:
                Raptor will have a default value of 'Prepunched'
                The symbol set for this string is Roman-8."
::= { media25 1 }


media25-engine-media-mode OBJECT-TYPE
    SYNTAX      INTEGER
    ACCESS      read-write
    STATUS      optional
       DESCRIPTION "The engine processing characteristics that are to be applied to
                this media. The processing characteristics are device
                specific.
                Additional information:
                Raptor will have a default value of 1
                See the description for MEDIA1-ENGINE-MEDIA-MODE."
::= { media25 4 }


media26-name OBJECT-TYPE
    SYNTAX      OCTET STRING
    ACCESS      read-only
    STATUS      optional
       DESCRIPTION "Media 26 name.
                Additional information:
                Raptor will have a default value of 'Color'
                The symbol set for this string is Roman-8."
::= { media26 1 }


media26-engine-media-mode OBJECT-TYPE
    SYNTAX      INTEGER
    ACCESS      read-write
    STATUS      optional
       DESCRIPTION "The engine processing characteristics that are to be applied to
                this media. The processing characteristics are device
                specific.
                Additional information:
                See the description for MEDIA1-ENGINE-MEDIA-MODE."
::= { media26 4 }


media27-name OBJECT-TYPE
    SYNTAX      OCTET STRING
    ACCESS      read-only
    STATUS      optional
       DESCRIPTION "Media 27 name.
                Additional information:
                Raptor will have a default value of 'Bond'
                The symbol set for this string is Roman-8."
::= { media27 1 }


media27-engine-media-mode OBJECT-TYPE
    SYNTAX      INTEGER
    ACCESS      read-write
    STATUS      optional
       DESCRIPTION "The engine processing characteristics that are to be applied to
                this media. The processing characteristics are device
                specific.
                Additional information:
                Raptor will have a default value of 3
                See the description for MEDIA1-ENGINE-MEDIA-MODE."
::= { media27 4 }


media28-name OBJECT-TYPE
    SYNTAX      OCTET STRING
    ACCESS      read-only
    STATUS      optional
       DESCRIPTION "Media 28 name.
                Additional information:
                Raptor will have a default value of 'Recycled'
                The symbol set for this string is Roman-8."
::= { media28 1 }


media28-engine-media-mode OBJECT-TYPE
    SYNTAX      INTEGER
    ACCESS      read-write
    STATUS      optional
       DESCRIPTION "The engine processing characteristics that are to be applied to
                this media. The processing characteristics are device
                specific.
                Additional information:
                See the description for MEDIA1-ENGINE-MEDIA-MODE."
::= { media28 4 }


media29-name OBJECT-TYPE
    SYNTAX      OCTET STRING
    ACCESS      read-only
    STATUS      optional
       DESCRIPTION "Media 29 name.
                Additional information:
                Raptor will have a default value of 'Rough'
                The symbol set for this string is Roman-8."
::= { media29 1 }


media29-engine-media-mode OBJECT-TYPE
    SYNTAX      INTEGER
    ACCESS      read-write
    STATUS      optional
       DESCRIPTION "The engine processing characteristics that are to be applied to
                this media. The processing characteristics are device
                specific.
                Additional information:
                See the description for MEDIA1-ENGINE-MEDIA-MODE."
::= { media29 4 }


media30-name OBJECT-TYPE
    SYNTAX      OCTET STRING
    ACCESS      read-only
    STATUS      optional
       DESCRIPTION "Media 30 name.
                Additional information:
                Raptor will have a default value of 'Heavy Rough'
                The symbol set for this string is Roman-8."
::= { media30 1 }


media30-engine-media-mode OBJECT-TYPE
    SYNTAX      INTEGER
    ACCESS      read-write
    STATUS      optional
       DESCRIPTION "The engine processing characteristics that are to be applied to
                this media. The processing characteristics are device
                specific.
                Additional information:
                Raptor will have a default value of 5.
                See the description for MEDIA1-ENGINE-MEDIA-MODE."
::= { media30 4 }


media31-name OBJECT-TYPE
    SYNTAX      OCTET STRING
    ACCESS      read-only
    STATUS      optional
       DESCRIPTION "Media 31 name.
                Additional information:
                Raptor will have a default value of 'HP Tough Paper'.
                The symbol set for this string is Roman-8."
::= { media31 1 }


media31-engine-media-mode OBJECT-TYPE
    SYNTAX      INTEGER
    ACCESS      read-write
    STATUS      optional
       DESCRIPTION "The engine processing characteristics that are to be applied to
                this media. The processing characteristics are device
                specific.
                Additional information:
                Raptor will have a default value of 14.
                See the description for MEDIA1-ENGINE-MEDIA-MODE."
::= { media31 4 }


engine-media-modes-supported1 OBJECT-TYPE
    SYNTAX      OCTET STRING
    ACCESS      read-only
    STATUS      optional
       DESCRIPTION "The list of engine media modes supported by the device. The
                modes are each separated by a comma character. An example
                string would be: 'Normal,Rough,Low,Vellum'.
                Additional information:
                The list of engine media modes supported by the device. The
                modes are each separated by a comma character. An example
                string would be: 'Normal,Rough,Low,Vellum'. Raptor does not support
                'Photo2' but supports 'Extra Heavy'"
::= { media-modes 1 }


pe-test-cause-assert OBJECT-TYPE
    SYNTAX      INTEGER {
                          e49DEAD(1),
                          e494C02(2)
		   }
    ACCESS      write-only
    STATUS      optional
       DESCRIPTION "This object allows the user to cause a 49 Error.
                Additional information:
                This object allows the user to cause a 49 Error."
::= { print-engine-test 111 }


pe-test-cause-79error OBJECT-TYPE
    SYNTAX      INTEGER {
                          e79DEAD(1)
		   }
    ACCESS      write-only
    STATUS      optional
       DESCRIPTION "This object allows the user to cause a 79 Error.
                Additional information:
                This object allows the user to cause a 79 Error."
::= { print-engine-test 116 }


consumable-reorder-url OBJECT-TYPE
    SYNTAX      OCTET STRING (SIZE(0..64))
    ACCESS      read-write
    STATUS      optional
       DESCRIPTION "This object is used to read and write the URL that can be used
                to reorder consumables for this device. This URL is set at the
                factory but can be updated by a reseller or third party.
                Additional information:
                The URL can be up to 64 characters long."
::= { consumables 2 }


END
