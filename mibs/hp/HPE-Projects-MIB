HPE-Projects-MIB DEFINITIONS ::= BEGIN
    IMPORTS
        enterprises FROM RFC1155-SMI;

-- /* 11,2,3,7,11,0 */
hp					OBJECT IDENTIFIER ::= { enterprises 11 }
--otherEnterprises	OBJECT IDENTIFIER ::= { hp 2 }
--hp1					OBJECT IDENTIFIER ::= {otherEnterprises 3}
--hp2					OBJECT IDENTIFIER ::= { hp1 7 }
--hp3					OBJECT IDENTIFIER ::= { hp2 11 }
nm					OBJECT IDENTIFIER ::= { hp 2 }
--rndMib				OBJECT IDENTIFIER ::= { hp 2 }

END
