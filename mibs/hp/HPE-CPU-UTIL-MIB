HPE-CPU-UTIL-MIB DEFINITIONS ::= BEGIN

IMPORTS
   	enterprises,
	MODULE-IDENTITY,
	OBJECT-TYPE,
	Integer32,
	NOTIFICATION-TYPE
		FROM SNMPv2-SMI
	hpVCSE-40Gb-F8-Module
		FROM HPSVRMGMT-OID;

hpeCpuUtilMIB  MODULE-IDENTITY
      LAST-UPDATED "201912190000Z"
      ORGANIZATION "Hewlett Packard Enterprise"
      CONTACT-INFO "Hewlett Packard Enterprise Support Center
                   www.hpe.com/support<http://www.hpe.com/support>
                   US, Canada & Caribbean: 1-800-633-3600
                   UK & Ireland: 0845 161 0050
                   Asia Pacific Region: 61-3-8877-5000"
      DESCRIPTION
          "Initial version of CPU utilization MIB"
      REVISION "201912190000Z"
	      DESCRIPTION
		  "Initial version."

		  ::= { hpeSynergyCpuUtilMIBObjects 4130 }

hpeSynergyCpuUtilMIBObjects OBJECT IDENTIFIER ::= { hpVCSE-40Gb-F8-Module 1 }

-- ------------------------------------------------------------
--         groups in the MIB
-- ------------------------------------------------------------
    hpeCpuUtilConfig  OBJECT IDENTIFIER ::=  { hpeCpuUtilMIB 1 }
    hpeCpuUtiStatus   OBJECT IDENTIFIER ::=  { hpeCpuUtilMIB 2 }
    hpeCpuUtilTraps   OBJECT IDENTIFIER ::=  { hpeCpuUtilMIB 3 }

-- ------------------------------------------------------------------
--         hpeCpuUtilConfig Group
-- ------------------------------------------------------------------
hpeSwitchMaxCPUThreshold    OBJECT-TYPE
    SYNTAX          Integer32 (1..100)
    MAX-ACCESS      read-write
    STATUS          current
    DESCRIPTION
    "Indicates the maximum CPU usage of the switch in percentage.
     When CPU load exceeds the threshold value,
     an SNMP trap with maximum severity will be sent to the manager."

     DEFVAL { 95 }
     ::= {  hpeCpuUtilConfig 1 }

hpeSwitchMinCPUThreshold    OBJECT-TYPE
    SYNTAX          Integer32 (1..100)
    MAX-ACCESS      read-write
    STATUS          current
    DESCRIPTION
    "Indicates the minimum CPU usage of the switch in percentage.
     When CPU load goes below the threshold value,
     an SNMP trap with maximum severity will be sent to the manager."

     DEFVAL { 75 }
     ::= {  hpeCpuUtilConfig 2 }

-- ------------------------------------------------------------------
--         hpeCpuUtilStatus Group
-- ------------------------------------------------------------------
hpeSwitchAverageCPUUtilization OBJECT-TYPE
     SYNTAX      Integer32
     UNITS       "percentage"
     MAX-ACCESS  read-only
     STATUS      current
     DESCRIPTION "This object retrieves the average CPU utilization of the switch.
     The average is calculated over 30 samples taken at the interval
     of 10 seconds"
     ::= {  hpeCpuUtiStatus 1 }

-- ------------------------------------------------------------------
--       hpeCpuUtil Traps
-- ------------------------------------------------------------------

hpeTrapMaxCPUThreshold NOTIFICATION-TYPE
     OBJECTS      {
                    hpeSwitchMaxCPUThreshold,
                    hpeSwitchAverageCPUUtilization
                  }
     STATUS       current
     DESCRIPTION
         "This notification is sent when CPU load exceeds
          the threshold value"
     ::= { hpeCpuUtilTraps 1 }

hpeTrapMinCPUThreshold NOTIFICATION-TYPE
     OBJECTS      {
                    hpeSwitchMinCPUThreshold,
                    hpeSwitchAverageCPUUtilization
                  }
     STATUS       current
     DESCRIPTION
         "This notification is sent when CPU load goes below
          the threshold value"
     ::= { hpeCpuUtilTraps 2 }

END
