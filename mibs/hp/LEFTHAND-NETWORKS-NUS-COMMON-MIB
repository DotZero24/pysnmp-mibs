LEFTHAND-NETWORKS-NUS-COMMON-MIB DEFINITIONS ::= BEGIN

-- LeftHand Networks Standard Definitions:
--
-- This file contains definitions which are common to
-- all LeftHand Network products.

IMPORTS
    lhnModules, lhnNusCommonMIB
        FROM LEFTHAND-NETWORKS-GLOBAL-REG
    MODULE-COMPLIANCE, OBJECT-GROUP
        FROM SNMPv2-CONF
    MODULE-IDENTITY, OBJECT-IDENTITY
        FROM SNMPv2-SMI;

--
-- Module definition
--
leftHandNetworksNusCommonModule MODULE-IDENTITY
    LAST-UPDATED "200106010000Z"
    ORGANIZATION "LeftHand Networks, Inc."
    CONTACT-INFO
	 "
         Primary Author: Jose Faria

         postal:    6185 Arapahoe Rd.
                    Boulder, CO 80301
         phone:     +1 303 449-4100
         email:     jfaria@lefthandnetworks.com"
    DESCRIPTION
	"This file defines LeftHand Networks NUS Common MIBs."

    ::= { lhnModules 2 }

lhnNusCommonConfs OBJECT IDENTIFIER -- Conformance Statements
  ::= { lhnNusCommonMIB 1 }

lhnNusCommonGroups OBJECT IDENTIFIER -- Object and Event groups
      ::= { lhnNusCommonConfs 1 }

lhnNusCommonCompl OBJECT IDENTIFIER -- Module Compliance
      ::= { lhnNusCommonConfs 2 }

lhnNusCommonObjs OBJECT IDENTIFIER -- Objects
   ::= { lhnNusCommonMIB 2 }

   lhnNusCommonInfo OBJECT IDENTIFIER
      ::= { lhnNusCommonObjs 1 }

   lhnNusCommonNetwork OBJECT IDENTIFIER
      ::= { lhnNusCommonObjs 2 }

   lhnNusCommonDNS OBJECT IDENTIFIER
       ::= { lhnNusCommonObjs 3 }

   lhnNusCommonStorage OBJECT IDENTIFIER
       ::= { lhnNusCommonObjs 4 }

   lhnNusCommonNTP OBJECT IDENTIFIER
       ::= { lhnNusCommonObjs 5 }

   lhnNusCommonNIS OBJECT IDENTIFIER
       ::= { lhnNusCommonObjs 6 }

   lhnNusCommonAEBS OBJECT IDENTIFIER
       ::= { lhnNusCommonObjs 7 }

   lhnNusCommonShares OBJECT IDENTIFIER
       ::= { lhnNusCommonObjs 8 }

   lhnNusCommonNTDomain OBJECT IDENTIFIER
       ::= { lhnNusCommonObjs 9 }

   lhnNusCommonSysOptions OBJECT IDENTIFIER
       ::= { lhnNusCommonObjs 10 }

   lhnNusCommonSecurity OBJECT IDENTIFIER
       ::= { lhnNusCommonObjs 11 }

   lhnNusCommonClustering OBJECT IDENTIFIER
       ::= { lhnNusCommonObjs 12 }

   lhnNusCommonNotification OBJECT IDENTIFIER
       ::= { lhnNusCommonObjs 13 }

   lhnNusCommonStatus OBJECT IDENTIFIER
       ::= { lhnNusCommonObjs 99 }

lhnNusCommonEvents OBJECT IDENTIFIER -- Events
   ::= { lhnNusCommonMIB 3 }

lhnNusCommonBasicGroup OBJECT-GROUP
   OBJECTS       {lhnNusCommonInfo, lhnNusCommonNetwork, lhnNusCommonDNS,
                  lhnNusCommonStorage, lhnNusCommonNTP, lhnNusCommonNIS,
                  lhnNusCommonAEBS, lhnNusCommonShares, lhnNusCommonNTDomain,
                  lhnNusCommonSysOptions, lhnNusCommonSecurity,
                  lhnNusCommonClustering, lhnNusCommonNotification,
                  lhnNusCommonStatus }
   STATUS        current
   DESCRIPTION   "The common objects to control NUS devices"
   ::= { lhnNusCommonGroups 1 }

lhnNusCommonComplianceV1 MODULE-COMPLIANCE
   STATUS           current
   DESCRIPTION      "All NUS Devices should provide this level of support"
   MODULE           -- this module
   MANDATORY-GROUPS { lhnNusCommonBasicGroup }
   ::= { lhnNusCommonCompl 1 }

END
