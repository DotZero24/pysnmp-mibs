--  (C) COPYRIGHT HEWLETT-PACKARD COMPANY 2014.
--
--  LaserJet 251 Printer Model Specific MIB.
--
--  Generated on May. 21, 2014.
--
--  Company names and product names mentioned herein may be
--  trademarks, and/or registered trademarks of their respective
--  companies.
--
--  For internal and external use.
--
--  This MIB describes all the printer model specific
--  objects supported by the LaserJet 251 printer
--  when networked connected.
--
--  The following MIBs also contain objects supported
--  by a LaserJet 251 printer:
--
--  IEEE 802.11 MIB
--  IEEE 802.1X MIB
--  rfc 2790 Host Resources MIB
--  rfc 3411 SNMP Framework MIB
--  rfc 3412 SNMP MPD MIB
--  rfc 3418 SNMP MIB
--  rfc 3805 Printer MIB
--  rfc 4022 TCP MIB
--  rfc 4293 IP MIB
--  rfc 4113 UDP MIB
--  PWG 5107.1-2005 Printer Port Monitor MIB
--
--  This MIB complies with the following RFCs:
--
--  rfc 1157 Simple Network Management Protocol
--  rfc 2578 Structure of Management Information Version 2
--
--  Notes:
--
--  1) Objects containing a string which are defined in this MIB use the
--     first two bytes to hold the symbol set used to encode the string.
--     The Roman-8 symbol set has a hex encoding of 0x0115.  Other
--     symbol sets are listed in the PCL 5 Comparison Guide in table
--     C-1 Symbol Set Values.
--
--  2) Some of the objects included are only supported if an accessory
--     is installed.  These accessories include:
--       MIO based accessories
--       SIMM based accessories
--       Paper handling accessories

LJ251-MIB DEFINITIONS ::= BEGIN

IMPORTS
	OBJECT-TYPE
		FROM RFC-1212

	DisplayString
		FROM SNMPv2-TC;

hpPrintServer OBJECT IDENTIFIER ::= { iso(1) org(3) dod(6) internet(1) private(4) enterprises(1) 11}
dm OBJECT IDENTIFIER ::= { hpPrintServer nm(2) hpsystem(3) net-peripheral(9) netdm(4) 2}

device                                 OBJECT IDENTIFIER ::=  { dm 1 }
system                                 OBJECT IDENTIFIER ::=  { device 1 }
settings-system                        OBJECT IDENTIFIER ::=  { system 1 }
destination-subsystem                  OBJECT IDENTIFIER ::=  { device 4 }
print-engine                           OBJECT IDENTIFIER ::=  { destination-subsystem 1 }
settings-prt-eng                       OBJECT IDENTIFIER ::=  { print-engine 1 }
marking-agent-density                  OBJECT IDENTIFIER ::=  { settings-prt-eng 9 }
status-prt-eng                         OBJECT IDENTIFIER ::=  { print-engine 2 }
printer-calibration-dhalf              OBJECT IDENTIFIER ::=  { status-prt-eng 37 }
printer-cal-dhalf-data                 OBJECT IDENTIFIER ::=  { printer-calibration-dhalf 3 }
printer-calibration-cpr                OBJECT IDENTIFIER ::=  { status-prt-eng 38 }
marking-agent                          OBJECT IDENTIFIER ::=  { print-engine 5 }
settings-marking-agent                 OBJECT IDENTIFIER ::=  { marking-agent 1 }
print-engine-test                      OBJECT IDENTIFIER ::=  { print-engine 9 }
hrm                                    OBJECT IDENTIFIER ::=  { dm 3 }
hrStorage                              OBJECT IDENTIFIER ::=  { hrm 2 }
hrStorageTable                         OBJECT IDENTIFIER ::=  { hrStorage 3 }
hrStorageEntry                         OBJECT IDENTIFIER ::=  { hrStorageTable 1 }
hrDevice                               OBJECT IDENTIFIER ::=  { hrm 3 }
hrDeviceTable                          OBJECT IDENTIFIER ::=  { hrDevice 2 }
hrDeviceEntry                          OBJECT IDENTIFIER ::=  { hrDeviceTable 1 }
hrPrinterTable                         OBJECT IDENTIFIER ::=  { hrDevice 5 }
hrPrinterEntry                         OBJECT IDENTIFIER ::=  { hrPrinterTable 1 }
iso                                    OBJECT IDENTIFIER ::=  { dm 1 }
org                                    OBJECT IDENTIFIER ::=  { iso 3 }
dod                                    OBJECT IDENTIFIER ::=  { org 6 }
internet                               OBJECT IDENTIFIER ::=  { dod 1 }
private                                OBJECT IDENTIFIER ::=  { internet 4 }
enterprises                            OBJECT IDENTIFIER ::=  { private 1 }
nm                                     OBJECT IDENTIFIER ::=  { hpPrintServer 2 }
interface                              OBJECT IDENTIFIER ::=  { nm 4 }
npCard                                 OBJECT IDENTIFIER ::=  { interface 3 }
npCRCTable                             OBJECT IDENTIFIER ::=  { npCard 15 }
npCRCEntry                             OBJECT IDENTIFIER ::=  { npCRCTable 1 }
inetTrap                               OBJECT IDENTIFIER ::=  { npCard 22 }
inetTrapDestination                    OBJECT IDENTIFIER ::=  { inetTrap 1 }
inetTrapDestinationTable               OBJECT IDENTIFIER ::=  { inetTrapDestination 2 }
inetTrapDestinationEntry               OBJECT IDENTIFIER ::=  { inetTrapDestinationTable 1 }
trap                                   OBJECT IDENTIFIER ::=  { nm 13 }
trapDest                               OBJECT IDENTIFIER ::=  { trap 1 }
trapFQDNTable                          OBJECT IDENTIFIER ::=  { trapDest 7 }
trapFQDNEntry                          OBJECT IDENTIFIER ::=  { trapFQDNTable 1 }
snmpAccess                             OBJECT IDENTIFIER ::=  { nm 15 }
community                              OBJECT IDENTIFIER ::=  { snmpAccess 1 }
npSys                                  OBJECT IDENTIFIER ::=  { npCard 1 }
npConns                                OBJECT IDENTIFIER ::=  { npCard 4 }
npCfg                                  OBJECT IDENTIFIER ::=  { npCard 5 }
npCfgAccessListTable                   OBJECT IDENTIFIER ::=  { npCfg 9 }
npCfgAccessListEntry                   OBJECT IDENTIFIER ::=  { npCfgAccessListTable 1 }
npTcp                                  OBJECT IDENTIFIER ::=  { npCard 6 }
npCtl                                  OBJECT IDENTIFIER ::=  { npCard 7 }
npPort                                 OBJECT IDENTIFIER ::=  { npCard 13 }
npDhcp                                 OBJECT IDENTIFIER ::=  { npCard 16 }
npWeb                                  OBJECT IDENTIFIER ::=  { npCard 18 }
npSecurity                             OBJECT IDENTIFIER ::=  { npCard 20 }
npSecurityDot11EncryptedWEPKeyTable    OBJECT IDENTIFIER ::=  { npSecurity 7 }
npSecurityDot11EncryptedWEPKeyEntry    OBJECT IDENTIFIER ::=  { npSecurityDot11EncryptedWEPKeyTable 1 }
npSecurityDot11SSIDTable               OBJECT IDENTIFIER ::=  { npSecurity 9 }
npSecurityDot11SSIDEntry               OBJECT IDENTIFIER ::=  { npSecurityDot11SSIDTable 1 }
system                                 OBJECT IDENTIFIER ::=  { nm 3 }
netPeripheral                          OBJECT IDENTIFIER ::=  { system 9 }
netPrinter                             OBJECT IDENTIFIER ::=  { netPeripheral 1 }
generalDeviceStatus                    OBJECT IDENTIFIER ::=  { netPrinter 1 }
netPML                                 OBJECT IDENTIFIER ::=  { netPeripheral 4 }
netPMLtrap                             OBJECT IDENTIFIER ::=  { netPML 1 }
npNpi                                  OBJECT IDENTIFIER ::=  { npCard 8 }
npNpiPeripheralAttributeEntry          OBJECT IDENTIFIER ::=  { npNpi 3 }
npNpiCardAttributeEntry                OBJECT IDENTIFIER ::=  { npNpi 4 }
gdStatusEntry                          OBJECT IDENTIFIER ::=  { generalDeviceStatus 2 }
job                                    OBJECT IDENTIFIER ::=  { system 6 }
photo-job                              OBJECT IDENTIFIER ::=  { job 8 }
settings-photo-job                     OBJECT IDENTIFIER ::=  { photo-job 3 }
device-configure                       OBJECT IDENTIFIER ::=  { settings-system 32 }
status-system                          OBJECT IDENTIFIER ::=  { system 2 }
display                                OBJECT IDENTIFIER ::=  { status-system 20 }
display-status                         OBJECT IDENTIFIER ::=  { display 1 }
id                                     OBJECT IDENTIFIER ::=  { system 3 }
interface                              OBJECT IDENTIFIER ::=  { system 4 }
simm                                   OBJECT IDENTIFIER ::=  { interface 1 }
simm1                                  OBJECT IDENTIFIER ::=  { simm 1 }
usb-interface                          OBJECT IDENTIFIER ::=  { interface 9 }
usb                                    OBJECT IDENTIFIER ::=  { usb-interface 2 }
test                                   OBJECT IDENTIFIER ::=  { system 5 }
settings-job                           OBJECT IDENTIFIER ::=  { job 1 }
active-print-jobs                      OBJECT IDENTIFIER ::=  { job 2 }
job-being-parsed                       OBJECT IDENTIFIER ::=  { active-print-jobs 1 }
job-info                               OBJECT IDENTIFIER ::=  { job 5 }
job-info-attribute                     OBJECT IDENTIFIER ::=  { job-info 23 }
errorlog                               OBJECT IDENTIFIER ::=  { system 11 }
error1                                 OBJECT IDENTIFIER ::=  { errorlog 1 }
error2                                 OBJECT IDENTIFIER ::=  { errorlog 2 }
error3                                 OBJECT IDENTIFIER ::=  { errorlog 3 }
error4                                 OBJECT IDENTIFIER ::=  { errorlog 4 }
error5                                 OBJECT IDENTIFIER ::=  { errorlog 5 }
error6                                 OBJECT IDENTIFIER ::=  { errorlog 6 }
error7                                 OBJECT IDENTIFIER ::=  { errorlog 7 }
error8                                 OBJECT IDENTIFIER ::=  { errorlog 8 }
error9                                 OBJECT IDENTIFIER ::=  { errorlog 9 }
error10                                OBJECT IDENTIFIER ::=  { errorlog 10 }
firmware-download                      OBJECT IDENTIFIER ::=  { system 18 }
source-subsystem                       OBJECT IDENTIFIER ::=  { device 2 }
io                                     OBJECT IDENTIFIER ::=  { source-subsystem 1 }
settings-io                            OBJECT IDENTIFIER ::=  { io 1 }
processing-subsystem                   OBJECT IDENTIFIER ::=  { device 3 }
pdl                                    OBJECT IDENTIFIER ::=  { processing-subsystem 3 }
settings-pdl                           OBJECT IDENTIFIER ::=  { pdl 1 }
pdl-pcl                                OBJECT IDENTIFIER ::=  { pdl 3 }
pdl-postscript                         OBJECT IDENTIFIER ::=  { pdl 4 }
pdl-pclxl                              OBJECT IDENTIFIER ::=  { pdl 16 }
pjl                                    OBJECT IDENTIFIER ::=  { processing-subsystem 5 }
intray                                 OBJECT IDENTIFIER ::=  { print-engine 3 }
settings-intray                        OBJECT IDENTIFIER ::=  { intray 1 }
intrays                                OBJECT IDENTIFIER ::=  { intray 3 }
intray1                                OBJECT IDENTIFIER ::=  { intrays 1 }
imaging                                OBJECT IDENTIFIER ::=  { print-engine 6 }
print-media                            OBJECT IDENTIFIER ::=  { print-engine 8 }
settings-print-media                   OBJECT IDENTIFIER ::=  { print-media 1 }
media-info                             OBJECT IDENTIFIER ::=  { print-media 3 }
media1                                 OBJECT IDENTIFIER ::=  { media-info 1 }
media2                                 OBJECT IDENTIFIER ::=  { media-info 2 }
media3                                 OBJECT IDENTIFIER ::=  { media-info 3 }
media4                                 OBJECT IDENTIFIER ::=  { media-info 4 }
media5                                 OBJECT IDENTIFIER ::=  { media-info 5 }
media6                                 OBJECT IDENTIFIER ::=  { media-info 6 }
media7                                 OBJECT IDENTIFIER ::=  { media-info 7 }
media8                                 OBJECT IDENTIFIER ::=  { media-info 8 }
media9                                 OBJECT IDENTIFIER ::=  { media-info 9 }
media10                                OBJECT IDENTIFIER ::=  { media-info 10 }
media11                                OBJECT IDENTIFIER ::=  { media-info 11 }
media12                                OBJECT IDENTIFIER ::=  { media-info 12 }
media13                                OBJECT IDENTIFIER ::=  { media-info 13 }
media14                                OBJECT IDENTIFIER ::=  { media-info 14 }
media15                                OBJECT IDENTIFIER ::=  { media-info 15 }
media16                                OBJECT IDENTIFIER ::=  { media-info 16 }
media17                                OBJECT IDENTIFIER ::=  { media-info 17 }
media18                                OBJECT IDENTIFIER ::=  { media-info 18 }
media19                                OBJECT IDENTIFIER ::=  { media-info 19 }
media20                                OBJECT IDENTIFIER ::=  { media-info 20 }
media21                                OBJECT IDENTIFIER ::=  { media-info 21 }
media22                                OBJECT IDENTIFIER ::=  { media-info 22 }
media23                                OBJECT IDENTIFIER ::=  { media-info 23 }
media24                                OBJECT IDENTIFIER ::=  { media-info 24 }
media25                                OBJECT IDENTIFIER ::=  { media-info 25 }
media26                                OBJECT IDENTIFIER ::=  { media-info 26 }
media27                                OBJECT IDENTIFIER ::=  { media-info 27 }
media28                                OBJECT IDENTIFIER ::=  { media-info 28 }
media29                                OBJECT IDENTIFIER ::=  { media-info 29 }
media30                                OBJECT IDENTIFIER ::=  { media-info 30 }
media31                                OBJECT IDENTIFIER ::=  { media-info 31 }
media32                                OBJECT IDENTIFIER ::=  { media-info 32 }
media33                                OBJECT IDENTIFIER ::=  { media-info 33 }
media34                                OBJECT IDENTIFIER ::=  { media-info 34 }
media-modes                            OBJECT IDENTIFIER ::=  { print-media 4 }
consumables                            OBJECT IDENTIFIER ::=  { print-engine 10 }
consumables-1                          OBJECT IDENTIFIER ::=  { consumables 1 }
consumable-status                      OBJECT IDENTIFIER ::=  { consumables-1 1 }
consumables-status                     OBJECT IDENTIFIER ::=  { consumables 5 }
consumables-life                       OBJECT IDENTIFIER ::=  { consumables-status 1 }
consumables-test                       OBJECT IDENTIFIER ::=  { consumables 6 }
printmib                               OBJECT IDENTIFIER ::=  { dm 2 }
prtGeneral                             OBJECT IDENTIFIER ::=  { printmib 5 }
prtGeneralTable                        OBJECT IDENTIFIER ::=  { prtGeneral 1 }
prtGeneralEntry                        OBJECT IDENTIFIER ::=  { prtGeneralTable 1 }
prtCover                               OBJECT IDENTIFIER ::=  { printmib 6 }
prtCoverTable                          OBJECT IDENTIFIER ::=  { prtCover 1 }
prtCoverEntry                          OBJECT IDENTIFIER ::=  { prtCoverTable 1 }
prtLocalization                        OBJECT IDENTIFIER ::=  { printmib 7 }
prtLocalizationTable                   OBJECT IDENTIFIER ::=  { prtLocalization 1 }
prtLocalizationEntry                   OBJECT IDENTIFIER ::=  { prtLocalizationTable 1 }
prtStorageRefTable                     OBJECT IDENTIFIER ::=  { prtGeneral 2 }
prtStorageRefEntry                     OBJECT IDENTIFIER ::=  { prtStorageRefTable 1 }
prtDeviceRefTable                      OBJECT IDENTIFIER ::=  { prtGeneral 3 }
prtDeviceRefEntry                      OBJECT IDENTIFIER ::=  { prtDeviceRefTable 1 }
prtInput                               OBJECT IDENTIFIER ::=  { printmib 8 }
prtInputTable                          OBJECT IDENTIFIER ::=  { prtInput 2 }
prtInputEntry                          OBJECT IDENTIFIER ::=  { prtInputTable 1 }
prtOutput                              OBJECT IDENTIFIER ::=  { printmib 9 }
prtOutputTable                         OBJECT IDENTIFIER ::=  { prtOutput 2 }
prtOutputEntry                         OBJECT IDENTIFIER ::=  { prtOutputTable 1 }
prtMarker                              OBJECT IDENTIFIER ::=  { printmib 10 }
prtMarkerTable                         OBJECT IDENTIFIER ::=  { prtMarker 2 }
prtMarkerEntry                         OBJECT IDENTIFIER ::=  { prtMarkerTable 1 }
prtMarkerSupplies                      OBJECT IDENTIFIER ::=  { printmib 11 }
prtMarkerSuppliesTable                 OBJECT IDENTIFIER ::=  { prtMarkerSupplies 1 }
prtMarkerSuppliesEntry                 OBJECT IDENTIFIER ::=  { prtMarkerSuppliesTable 1 }
prtMarkerColorant                      OBJECT IDENTIFIER ::=  { printmib 12 }
prtMarkerColorantTable                 OBJECT IDENTIFIER ::=  { prtMarkerColorant 1 }
prtMarkerColorantEntry                 OBJECT IDENTIFIER ::=  { prtMarkerColorantTable 1 }
prtMediaPath                           OBJECT IDENTIFIER ::=  { printmib 13 }
prtMediaPathTable                      OBJECT IDENTIFIER ::=  { prtMediaPath 4 }
prtMediaPathEntry                      OBJECT IDENTIFIER ::=  { prtMediaPathTable 1 }
prtInterpreter                         OBJECT IDENTIFIER ::=  { printmib 15 }
prtInterpreterTable                    OBJECT IDENTIFIER ::=  { prtInterpreter 1 }
prtInterpreterEntry                    OBJECT IDENTIFIER ::=  { prtInterpreterTable 1 }
prtConsoleDisplayBuffer                OBJECT IDENTIFIER ::=  { printmib 16 }
prtConsoleDisplayBufferTable           OBJECT IDENTIFIER ::=  { prtConsoleDisplayBuffer 5 }
prtConsoleDisplayBufferEntry           OBJECT IDENTIFIER ::=  { prtConsoleDisplayBufferTable 1 }
prtConsoleLights                       OBJECT IDENTIFIER ::=  { printmib 17 }
prtConsoleLightTable                   OBJECT IDENTIFIER ::=  { prtConsoleLights 6 }
prtConsoleLightEntry                   OBJECT IDENTIFIER ::=  { prtConsoleLightTable 1 }


mono-color-switching-mode OBJECT-TYPE
    SYNTAX      INTEGER {
                          eNeverSwitch(1),
                          eAlwaysSwitch(2),
                          eLookAheadSwitch(3)
		   }
    ACCESS      read-write
    STATUS      optional
       DESCRIPTION "This object allows the user to view/change the color/mono
		switching mode for a device.
                Additional information:
                This object allows the user to view/change the color/mono
                switching mode for a device."
::= { settings-system 31 }


marking-agent-density-setting OBJECT-TYPE
    SYNTAX      INTEGER
    ACCESS      read-write
    STATUS      optional
       DESCRIPTION "Returns or sets the marking agent density setting for each of
		the marking agents installed. The Marking Agent (aka Print)
		density is the instantaneous amount of marking agent applied to
		the media while printing. A value of zero has the lowest print
		density, yielding a lighter page. A value of 10 has the highest
		print density, yielding a darker page. The device POS will
		document what values are supported.
                Additional information:
                See the description for PRINT-DENSITY ."
::= { marking-agent-density 1 }


marking-agent-highlights-density-setting OBJECT-TYPE
    SYNTAX      INTEGER
    ACCESS      read-write
    STATUS      optional
       DESCRIPTION "Returns or sets the marking agent highlights density setting
		for each of the marking agents installed. The value of this
		object is in the range of -5..+5. The Marking Agent (aka Print)
		density is the instantaneous amount of marking agent applied to
		the media while printing. A value of -5 has the lowest print
		density, yeilding a lighter pageA value of +5 the highest print
		density, yielding a darker page."
::= { marking-agent-density 2 }


marking-agent-midtones-density-setting OBJECT-TYPE
    SYNTAX      INTEGER
    ACCESS      read-write
    STATUS      optional
       DESCRIPTION "Returns or sets the marking agent midtones density setting for
		each of the marking agents installed. The value of this object
		is in the range of -5..+5. See
		MARKING-AGENT-HIGHLIGHTS-DENSITY-SETTING for a more specific
		description."
::= { marking-agent-density 3 }


marking-agent-shadows-density-setting OBJECT-TYPE
    SYNTAX      INTEGER
    ACCESS      read-write
    STATUS      optional
       DESCRIPTION "Returns or sets the marking agent shadows density setting for
		each of the marking agents installed. The value of this object
		is in the range of -5..+5. See
		MARKING-AGENT-HIGHLIGHTS-DENSITY-SETTING for a more specific
		description."
::= { marking-agent-density 4 }


calibration-power-on-initiation OBJECT-TYPE
    SYNTAX      INTEGER {
                          eOff(1),
                          eOn(2),
                          eDelayed(3)
		   }
    ACCESS      read-write
    STATUS      optional
       DESCRIPTION "This object determines when a power on calibration occurs. If
		eOn, then the calibration occurs immediately following boot. If
		eOff, then it never occurs. If eDelayed, then refer to the
		CALIBRATION-POWER-ON-DELAY PML object for the delay interval."
::= { settings-prt-eng 20 }


calibration-power-on-delay OBJECT-TYPE
    SYNTAX      INTEGER
    ACCESS      read-write
    STATUS      optional
       DESCRIPTION "This is the delay interval for the power on calibration in
		minutes. This PML object is only used if the
		CALIBRATION-POWER-ON-INITIATION PML object is set to eDelayed.
                Additional information:
                This is the delay interval for the power on
                		calibration in minutes. The range in minutes for the product
                		is 1-60 minutes. "
::= { settings-prt-eng 21 }


calibration-pages-printed-initiation OBJECT-TYPE
    SYNTAX      INTEGER
    ACCESS      read-write
    STATUS      optional
       DESCRIPTION "The number of pages that will be printed prior to an
		automatically initiated print calibration. If set to 0, it
		turns this calibration off.
                Additional information:
                This is the number of pages that will be printed
                		prior to an automatically initiated print calibration.
                		If set to 0, it turns this calibration off."
::= { settings-prt-eng 22 }


calibration-timer-initiation OBJECT-TYPE
    SYNTAX      INTEGER
    ACCESS      read-write
    STATUS      optional
       DESCRIPTION "This is a timer in minutes that will be set in between
		calibrations. When the timer expires, a calibration will
		automatically be initiated. If set to 0, it turns this
		calibration off.
                Additional information:
                This is a timer in minutes that will be set in
                		between calibrations.   If set to 0,
                		it turns this calibration off. The range for the product
                		will be 0-10080. When you set to a value of 2 (min) or any
                		other legal value other than 0, the device does not
                		immediately begin calibrating when the timer expires.
                		The calibration takes place after the timer expires,
                		the next job has finished printing, and a 15 minute period
                	        of inactivity has passed."
::= { settings-prt-eng 23 }


calibration-cpr-pages-printed-initiation OBJECT-TYPE
    SYNTAX      INTEGER
    ACCESS      read-write
    STATUS      optional
       DESCRIPTION "The number of pages that will be printed prior to an
		automatically initiated CPR calibration. If set to 0, it turns
		this calibration off.
                Additional information:
                The number of pages that will be printed prior to an
                automatically initiated CPR calibration. If set to 0, it turns
                this calibration off."
::= { settings-prt-eng 32 }


total-mono-page-count OBJECT-TYPE
    SYNTAX      INTEGER
    ACCESS      read-write
    STATUS      optional
       DESCRIPTION "Total number of black pages printed by the device.
                Additional information:
                Total number of mono pages printed by the device."
::= { status-prt-eng 6 }


total-color-page-count OBJECT-TYPE
    SYNTAX      INTEGER
    ACCESS      read-write
    STATUS      optional
       DESCRIPTION "Total number of color pages printed by the device.
                Additional information:
                Total number of color pages printed
                				by the device."
::= { status-prt-eng 7 }


printer-cal-dhalf-applied-data1 OBJECT-TYPE
    SYNTAX      OCTET STRING
    ACCESS      read-only
    STATUS      optional
       DESCRIPTION "Provides a device specific set of Dhalf calibration data as a
		binary string of byte values. It will be necessary to have a
		decoder for each engine to interpret the data. The data
		provided reflects the calibration values currently being
		applied to pages. This object will return
		ErrorActionCannotBePerformedNow when the data is being updated
		based on a recent calibration. The object will return undefined
		data while the object is being updated. When
		ErrorActionCannotBePerformedNow is received, the requester
		should attempt again after waiting a reasonable short period of
		time.
                Additional information:
                Provides a device specific set of Dhalf calibration data.
                It will be necessary to have a decoder for each engine to interpret
                		the data. The data provided reflects the calibration values currently
                		being applied to pages. The subrays provide information in this order:
                		Cyan(1), Magenta(2), Yellow(3), Black(4), Status(5)."
::= { printer-cal-dhalf-data 3 }


printer-cal-cpr-applied-data OBJECT-TYPE
    SYNTAX      OCTET STRING
    ACCESS      read-only
    STATUS      optional
       DESCRIPTION "Provides a device specific set of CPR calibration data as a
		binary string of byte values. It will be necessary to have a
		decoder for each engine to interpret the data. The data
		provided reflects the calibration values currently being
		applied to pages. This object will return
		ErrorActionCannotBePerformedNow when the data is being updated
		based on a recent calibration. The object will return undefined
		data while the object is being updated. When
		ErrorActionCannotBePerformedNow is received, the requester
		should attempt again after waiting a reasonable short period of
		time.
                Additional information:
                Provides a device specific set of CPR calibration data.
                It will be necessary to have a decoder for each engine to interpret
                		the data. The data provided reflects the calibration values currently
                		being applied to pages."
::= { printer-calibration-cpr 4 }


marker-density-calibration OBJECT-TYPE
    SYNTAX      INTEGER {
                          eNotCallibrating(1),
                          eCalibrateALL(2),
                          eCalibrateColor(3),
                          eCalibrateColorPlaneRegistration(5)
		   }
    ACCESS      read-write
    STATUS      optional
       DESCRIPTION "Returns the calibration status or triggers a calibration cycle.
		All calibration procedures are used if set to eCalibrateALL. If
		set to eCalibrateColor then a full density engine calibration
		is triggered. If set to eCalibrateHalftone, then a Halftone
		calibration is triggered. If set to
		eCalibrateColorPlaneRegistration, then a Color Plane
		Registration calibration is triggered. If set to
		eCalibrateDrumPhaseAdjustment, then a Drum Phase Adjustment
		calibration is triggered.If set to eCalibrateLowSpeedColor,
		then a Low Speed Color calibration is triggered.If set to
		eCalibrateDrumSpeedAdjustment, then a Drum Speed Adjustment
		calibration is triggered.If set to eCalibrateNeutrals, then a
		Gray Axis Control calibration is triggered.
                Additional information:
                Returns the calibration status or triggers a
                				calibration cycle."
::= { settings-marking-agent 11 }


pe-test-abort-calibration OBJECT-TYPE
    SYNTAX      INTEGER {
                          eFalse(1),
                          eTrue(2)
		   }
    ACCESS      read-write
    STATUS      optional
       DESCRIPTION "Aborts all executing and scheduled calibrations if set to
		eTrue.
                Additional information:
                All scheduled caliberations will abort.  Any currently
                	                     executing calibration will finish normally."
::= { print-engine-test 94 }


hrMemorySize OBJECT-TYPE
    SYNTAX      INTEGER
    ACCESS      read-only
    STATUS      mandatory
       DESCRIPTION "The amount of physical main memory contained by
              the host.
              Refer to RFC 1514, Host Resources MIB, for more details.
                Additional information:
                The unit of measure for this object is 1024
                bytes. The default value assumes the base printer with no
                additional memory."
::= { hrStorage 2 }


hrStorageIndex OBJECT-TYPE
    SYNTAX      INTEGER(1..2147483647)
    ACCESS      read-only
    STATUS      mandatory
       DESCRIPTION "A unique value for each logical storage area
              contained by the host.
              Refer to RFC 1514, Host Resources MIB, for more details."
::= { hrStorageEntry 1 }


hrStorageType OBJECT-TYPE
    SYNTAX      OBJECT IDENTIFIER
    ACCESS      read-only
    STATUS      mandatory
       DESCRIPTION "The type of storage represented by this entry.
              Refer to RFC 1514, Host Resources MIB, for more details.
                Additional information:
                The object is constant for the product."
::= { hrStorageEntry 2 }


hrStorageDescr OBJECT-TYPE
    SYNTAX      OCTET STRING
    ACCESS      read-only
    STATUS      mandatory
       DESCRIPTION "A description of the type and instance of the
              storage described by this entry.
              Refer to RFC 1514, Host Resources MIB, for more details.
                Additional information:
                This object is not localized.  For the product, this
                object is constant."
::= { hrStorageEntry 3 }


hrStorageAllocationUnits OBJECT-TYPE
    SYNTAX      INTEGER(1..2147483647)
    ACCESS      read-only
    STATUS      mandatory
       DESCRIPTION "The size, in bytes, of the data objects allocated
               from this pool.  If this entry is monitoring
               sectors, blocks, buffers, or packets, for example,
               this number will commonly be greater than one.
               Otherwise this number will typically be one.
               Refer to RFC 1514, Host Resources MIB, for more details.
                Additional information:
                Unit is one byte.  For the product,
                this object is constant."
::= { hrStorageEntry 4 }


hrStorageSize OBJECT-TYPE
    SYNTAX      INTEGER(0..2147483647)
    ACCESS      read-only
    STATUS      mandatory
       DESCRIPTION "The size of the storage represented by this entry,
              in units of hrStorageAllocationUnits.
              Refer to RFC 1514, Host Resources MIB, for more details.
                Additional information:
                Total formatter RAM.  (The value of this object
                is hrMemorySize times the unit of measure for hrMemorySize.
                For this procduct this is 65536*1024 bytes.)"
::= { hrStorageEntry 5 }


hrStorageUsed OBJECT-TYPE
    SYNTAX      INTEGER(0..2147483647)
    ACCESS      read-only
    STATUS      mandatory
       DESCRIPTION "The amount of the storage represented by this
              entry that is allocated, in units of
              hrStorageAllocationUnits.
              Refer to RFC 1514, Host Resources MIB, for more details.
                Additional information:
                This object returns the amount of memory in use
                by the printer at the current time.  This object should not
                be used when creating a print job for the device because the
                amount of memory in use will likely be different when the
                printer processes the print job."
::= { hrStorageEntry 6 }


hrDeviceIndex OBJECT-TYPE
    SYNTAX      INTEGER(1..2147483647)
    ACCESS      read-only
    STATUS      mandatory
       DESCRIPTION "A unique value for each device contained by the
              host.  The value for each device must remain
              constant at least from one re-initialization of the
              agent to the next re-initialization.
              Refer to RFC 1514, Host Resources MIB, for more details.
                Additional information:
                The entry in the Device Table which describes
                the printer."
::= { hrDeviceEntry 1 }


hrDeviceType OBJECT-TYPE
    SYNTAX      OBJECT IDENTIFIER
    ACCESS      read-only
    STATUS      mandatory
       DESCRIPTION "An indication of the type of device.
              If this value is `hrDeviceProcessor { hrDeviceTypes
              3 }' then an entry exists in the hrProcessorTable
              which corresponds to this device.
              If this value is `hrDeviceNetwork { hrDeviceTypes 4
              }', then an entry exists in the hrNetworkTable
              which corresponds to this device.
              If this value is `hrDevicePrinter { hrDeviceTypes 5
              }', then an entry exists in the hrPrinterTable
              which corresponds to this device.
              If this value is `hrDeviceDiskStorage {
              hrDeviceTypes 6 }', then an entry exists in the
              hrDiskStorageTable which corresponds to this
              device.
              Refer to RFC 1514, Host Resources MIB, for more details."
::= { hrDeviceEntry 2 }


hrDeviceDescr OBJECT-TYPE
    SYNTAX      OCTET STRING (SIZE(0..64))
    ACCESS      read-only
    STATUS      mandatory
       DESCRIPTION "A textual description of this device, including
              the device's manufacturer and revision, and
              optionally, its serial number.
              Refer to RFC 1514, Host Resources MIB, for more details.
                Additional information:
                The serial number is not returned with this
                object.  This object is not localized."
::= { hrDeviceEntry 3 }


hrDeviceID OBJECT-TYPE
    SYNTAX      OBJECT IDENTIFIER
    ACCESS      read-only
    STATUS      mandatory
       DESCRIPTION "The product ID for this device.
              Refer to RFC 1514, Host Resources MIB, for more details.
                Additional information:
                The complete OID reported by this object is:
                .1.3.6.1.4.1.11.2.3.9.1.2.99"
::= { hrDeviceEntry 4 }


hrDeviceStatus OBJECT-TYPE
    SYNTAX      INTEGER {
                          eHrunning(2),
                          eHwarning(3),
                          eHdown(5)
		   }
    ACCESS      read-only
    STATUS      mandatory
       DESCRIPTION "The current operational state of the device
              described by this row of the table.  A value
              unknown(1) indicates that the current state of the
              device is unknown.  running(2) indicates that the
              device is up and running and that no unusual error
              conditions are known.  The warning(3) state
              indicates that agent has been informed of an
              unusual error condition by the operational software
              (e.g., a disk device driver) but that the device is
              still 'operational'.  An example would be high
              number of soft errors on a disk.  A value of
              testing(4), indicates that the device is not
              available for use because it is in the testing
              state.  The state of down(5) is used only when the
              agent has been informed that the device is not
              available for any use.
              Refer to RFC 1514, Host Resources MIB, for more details.
                Additional information:
                The printer's condition is mapped as follows:

                eHrunning -- Printer ready to print or is printing.  It may
                be in power save mode.

                eHwarning -- A condition exists that needs attention, but it
                is not currently preventing printing.  A non-critical alert
                is active.

                eHdown -- Printer is not printing because it is offline, or
                a critical alert is active.  Human interaction is needed to
                bring the printer to a ready state."
::= { hrDeviceEntry 5 }


hrDeviceErrors OBJECT-TYPE
    SYNTAX      INTEGER
    ACCESS      read-only
    STATUS      mandatory
       DESCRIPTION "The number of errors detected on this device.  It
               should be noted that as this object has a SYNTAX
               of Counter, that it does not have a defined
               initial value.  However, it is recommended that
               this object be initialized to zero.
               Refer to RFC 1514, Host Resources MIB, for more details.
                Additional information:
                This is the number of critical alerts that have
                been entered into the alert table since the device was
                powered on.  The maximum value for this object is 2^32-1.  At
                power-on, this object will be set to zero."
::= { hrDeviceEntry 6 }


hrPrinterStatus OBJECT-TYPE
    SYNTAX      INTEGER {
                          eHother(1),
                          eHidle(3),
                          eHprinting(4),
                          eHwarmup(5)
		   }
    ACCESS      read-only
    STATUS      mandatory
       DESCRIPTION "The current status of this printer device.  When
               in the idle(1), printing(2), or warmup(3) state,
               the corresponding hrDeviceStatus should be
               running(2) or warning(3).  When in the unknown
               state, the corresponding hrDeviceStatus should be
               unknown(1).
               Refer to RFC 1514, Host Resources MIB, for more details.
                Additional information:
                The printer's condition is mapped as follows:

                eHother -- The printer is offline, or a critical alert is
                active.

                eHidle -- The printer is not performing any of the items
                listed under eHprinting status.

                eHprinting -- A job is currently being processed or printed,
                or a PJL job is being processed.

                eHwarmup -- If hrDeviceStatus is eHdown, the printer is
                currently offline but is resolving the condition that caused
                it to be offline. It will be online when it is ready to
                print.  If hrDeviceStatus is eHrunning, the printer was
                in power save mode and is now becoming ready to print.  (In
                the product, this status only occurs very
                briefly at boot time.  At no other time does the printer
                report 'eHwarmup' status.)"
::= { hrPrinterEntry 1 }


hrPrinterDetectedErrorState OBJECT-TYPE
    SYNTAX      OCTET STRING
    ACCESS      read-only
    STATUS      mandatory
       DESCRIPTION "This object represents any error conditions
               detected by the printer.  The error conditions are
               encoded as bits in an octet string, with the
               following definitions:
                    Condition         Bit #    hrDeviceStatus
                    lowPaper          0        warning(3)
                    noPaper           1        down(5)
                    lowToner          2        warning(3)
                    noToner           3        down(5)
                    doorOpen          4        down(5)
                    jammed            5        down(5)
                    offline           6        down(5)
                    serviceRequested  7        warning(3)
               If multiple conditions are currently detected and
               the hrDeviceStatus would not otherwise be
               unknown(1) or testing(4), the hrDeviceStatus shall
               correspond to the worst state of those indicated,
               where down(5) is worse than warning(3) which is
               worse than running(2).
               Bits are numbered starting with the most
               significant bit of the first byte being bit 0, the
               least significant bit of the first byte being bit
               7, the most significant bit of the second byte
               being bit 8, and so on.  A one bit encodes that
               the condition was detected, while a zero bit
               encodes that the condition was not detected.
               This object is useful for alerting an operator to
               specific warning or error conditions that may
               occur, especially those requiring human
               intervention.
               Refer to RFC 1514, Host Resources MIB, for more details.
                Additional information:
                The product reports error
                conditions as follows:

                noPaper - A tray is empty and must be filled for printing to
                continue.
                hrDeviceStatus = eHdown;
                hrPrinterStatus = eHother;
                A critical alert is active.

                coverOpen -- A cover or door is open.
                hrDeviceStatus = eHdown;
                hrPrinterStatus = eHother;
                A critical alert is active.

                jammed -- A jam condition is preventing printing.
                hrDeviceStatus = eHdown;
                hrPrinterStatus = eHother;
                A critical alert is active.

                offline -- Printer is offline and will not accept new print
                jobs until it is online.  This condition is rare in the
                and may indicate some other error.
                hrDeviceStatus = eHdown;
                hrPrinterStatus = eHother;
                A critical alert is active.

                serviceRequested -- Any status or error condition not listed
                above.  These fall into two categories:
                (1) If the condition prevents printing, the 'offline' bit
                is also set and status values are as for offline.  i.e.:
                hrDeviceStatus = eHdown;
                hrPrinterStatus = eHother;
                A critical alert is active.
                (2) If the condition does not prevent printing the status
                values are:
                hrDeviceStatus = eHwarning;
                hrPrinterStatus = eHidle or eHprinting;
                A non-critical alert is active.

                lowToner -- The product can report this condition.

                noToner -- The product can report this condition."
::= { hrPrinterEntry 2 }


npCRCTable OBJECT-TYPE
    SYNTAX      SEQUENCE OF NpCRCEntry
    ACCESS      not-accessible
    STATUS      current
       DESCRIPTION ""
::= { npCard 15 }


npCRCEntry OBJECT-TYPE
    SYNTAX      NpCRCEntry
    ACCESS      not-accessible
    STATUS      current
       DESCRIPTION ""
::= { npCRCTable 1 }


npCRCIndex OBJECT-TYPE
    SYNTAX      Integer32
    ACCESS      read-only
    STATUS      current
       DESCRIPTION ""
::= { npCRCEntry 1 }


npCRCText OBJECT-TYPE
    SYNTAX      OCTET STRING
    ACCESS      read-only
    STATUS      current
       DESCRIPTION ""
::= { npCRCEntry 2 }


npCRCChannel OBJECT-TYPE
    SYNTAX      Integer32
    ACCESS      read-only
    STATUS      current
       DESCRIPTION ""
::= { npCRCEntry 3 }


inetTrapDestinationNum OBJECT-TYPE
    SYNTAX      Integer32
    ACCESS      read-only
    STATUS      current
       DESCRIPTION "Total number of ACTIVE rows in the inetTrapDestination table."
::= { inetTrapDestination 1 }


inetTrapDestinationTable OBJECT-TYPE
    SYNTAX      SEQUENCE OF InetTrapDestinationEntry
    ACCESS      not-accessible
    STATUS      current
       DESCRIPTION "List of inetTrap destinations to which the agent sends traps."
::= { inetTrapDestination 2 }


inetTrapDestinationEntry OBJECT-TYPE
    SYNTAX      InetTrapDestinationEntry
    ACCESS      not-accessible
    STATUS      current
       DESCRIPTION "Entries are inetAddress Specific sequence of trap destination parameters."
::= { inetTrapDestinationTable 1 }


inetTrapRowIndex OBJECT-TYPE
    SYNTAX      Integer32
    ACCESS      read-only
    STATUS      current
       DESCRIPTION "Row Index of the inetTrapDestination table"
::= { inetTrapDestinationEntry 1 }


inetTrapRowStatus OBJECT-TYPE
    SYNTAX      Integer32
    ACCESS      read-write
    STATUS      current
       DESCRIPTION "Individual Row Status
			1 - Row is Active - Row is activated and ready.
			2 - Not-In-Service - Row is suspended.
			3 - Not Ready - Row is not activated and still needs some columnar values to move to ready state.
			4 - Create and Go - This is set when the client uses multivarbind request to configure the trap table.
			5 - Create and Wait - This is set when the client does sequential configuration of the trap table.
			6 - Destroy - This is set when the client wants to delete the row from the table.
			"
::= { inetTrapDestinationEntry 2 }


inetTrapAddressType OBJECT-TYPE
    SYNTAX      INTEGER
    ACCESS      read-write
    STATUS      current
       DESCRIPTION "Protocol family for trap.  Possible values:
			ipv4(1)		An IPv4 address as defined by the
						InetAddressIPv4 textual convention.

			ipv6(2)     An IPv6 address as defined by the
						InetAddressIPv6 textual convention.

			dns(16)		A DNS domain name as defined by the
						InetAddressDNS textual convention."
::= { inetTrapDestinationEntry 3 }


inetTrapAddress OBJECT-TYPE
    SYNTAX      OCTET STRING
    ACCESS      read-write
    STATUS      current
       DESCRIPTION "IPv4/IPv6/FQDN address of trap destination node."
::= { inetTrapDestinationEntry 4 }


inetTrapPort OBJECT-TYPE
    SYNTAX      Integer32
    ACCESS      read-write
    STATUS      current
       DESCRIPTION "Port number of the inetTrap Destination to which the trap is sent."
::= { inetTrapDestinationEntry 5 }


inetTrapCommunityName OBJECT-TYPE
    SYNTAX      OCTET STRING
    ACCESS      read-write
    STATUS      current
       DESCRIPTION "Trap community name specified in the trap packet."
::= { inetTrapDestinationEntry 6 }


inetTrapVersion OBJECT-TYPE
    SYNTAX      INTEGER
    ACCESS      read-write
    STATUS      current
       DESCRIPTION "Trap version, one of the following
			0 = snmpV1
			1 = snmpV2
			3 = Inform
			Default is  1 = snmpV2.
			This value remains persistent through a powercycle."
::= { inetTrapDestinationEntry 7 }


inetTrapStyle OBJECT-TYPE
    SYNTAX      INTEGER {selectable-pml-traps(1),
                          aps-and-general-or-nrdpe-traps(2),
		   both-of-the-above(3)}
    ACCESS      read-write
    STATUS      current
       DESCRIPTION "This OID is read-write.
			If the user wants to receive only the PML traps, then trapStyle can be set to 1.
			If the user wants to receive only APS and General or NOT-READY-DESTINATION-PRINT-ENGINE traps, then trapStyle can be set to 2.
			If the user wants to receive the both kinds of above traps, then trapStyle can be set to 3."
::= { inetTrapDestinationEntry 8 }


inetTrapPMLOids OBJECT-TYPE
    SYNTAX      OCTET STRING
    ACCESS      read-write
    STATUS      current
       DESCRIPTION "This OID is a read-write. This will have tokens of PML trappable OIDs.
			Each token (OID) will be separated by a semi-colon. If a trap destination entry is
			registered for only APS and general/NRDPE traps, then the pmlTrapOids OID will be a NULL string."
::= { inetTrapDestinationEntry 9 }


inetTrapErrorValue OBJECT-TYPE
    SYNTAX      Integer32
    ACCESS      read-only
    STATUS      current
       DESCRIPTION "Gives the error value in case if the server is not able to send the traps
			to the configured trapDestination entry. It will be set to below defined error values
			if there the agent finds any error while dispatching a trap.

			10 - Invalid value for rowStatus. Should be 1, 2, 3 or 6.
			11 - Ivalid value for InetTrapAddressType. Should be 1, 2 or 16.
			12 - Invalid for IP Address or FQDN.
			13 - Ivalid value for inetTrapPort. Should be greater than 0 or less than 65536.
			14 - Invalid valur for inetTrapCommunityName.
			15 - Invalid value for inetTrapVersion. Should be 0, 1 or 3.
			16 - Invalid value for inetTrapStyle. Should be either 1, 2 or 3.
			17 - Unable to resgister SOME or ALL PML trappable OIDs.

			51 - InetTrapAddressType & InetTrapAddress does not macth.
			52 - It is a Duplicate entry.
			53 - Unable to move the row to ACTIVE state because of insufficient/invalid entries.

			80 - Unable to resolve name: no DNS server.
			81 - Unable to resolve name: no DNS records present for name.
			82 - Unable to resolve name: no dns records matching FQDN Resolution Value.
			"
::= { inetTrapDestinationEntry 10 }


inetTrapTest OBJECT-TYPE
    SYNTAX      Integer32
    ACCESS      write-only
    STATUS      current
       DESCRIPTION "Causes agent to send an snmp trap to hosts registered in the trap
			destination table.  Value specified will be used as the specific
			trap id."
::= { inetTrapDestination 3 }


inetTrapFilterDelay OBJECT-TYPE
    SYNTAX      Integer32
    ACCESS      read-write
    STATUS      current
       DESCRIPTION "The purpose of the trap filter feature is to prevent multiple traps
			of the same specificTrapId to be sent within a short period of time.
			This object assigns the period of time within which a duplicate trap
			will be blocked.  This value is in 1/10 second intervals and the default
			value is set to 50 corresponding to 5 seconds.
			This value remains persistent through a powercycle."
::= { inetTrapDestination 4 }


inetTrapBaseTimeout OBJECT-TYPE
    SYNTAX      Integer32
    ACCESS      read-write
    STATUS      current
       DESCRIPTION "Applicable only if trapVersion is set to Inform.
			Units are 1/10 second intervals.  Default is 2
			corresponding to 200 milliseconds.  This value corresponds
			to the time of the first retry following the initial inform
			request. Additional retries are sent at times corresponding to
			the retry number multiplied by the inetTrapBaseTimeout.
			This value remains persistent through a powercycle."
::= { inetTrapDestination 5 }


inetTrapRetryNum OBJECT-TYPE
    SYNTAX      Integer32
    ACCESS      read-write
    STATUS      current
       DESCRIPTION "Applicable only if trapVersion is set to Inform.
			This is the maximum number of inform retries that will be sent to
			this destination.  Retries are sent if no inform reply is received
			within the timeout value.  The timeout value is calculated as
			described under inetTrapBaseTimeout.
			This value remains persistent through a powercycle."
::= { inetTrapDestination 6 }


inetTrapFQDNResolution OBJECT-TYPE
    SYNTAX      INTEGER {resolve-for-IPv4-address(1),
                          resolve-for-IPv6-address(2),
		   resolve-for-both(10)}
    ACCESS      read-write
    STATUS      current
       DESCRIPTION "The purpose of this field is to configure various options for resolving FQDN.
			If configured as 1  - then FQDN names will be resolved for IPv4 addresses only
			If configured as 2  - then FQDN names will be resolved for IPv6 addresses only.
			If configured as 10 - then FQDN names will be resolved for both IPv4 and IPv6 addresses."
::= { inetTrapDestination 7 }


inetTrapFQDNMultipleAddressBehavior OBJECT-TYPE
    SYNTAX      INTEGER {send-to-first-resolved-address(1),
		   send-to-all-resolved-address(2)}
    ACCESS      read-write
    STATUS      current
       DESCRIPTION "1 - Send traps to the first resolved address
			 2 - Send traps to all resolved address.
			 "
::= { inetTrapDestination 8 }


inetTrapUseDNSCache OBJECT-TYPE
    SYNTAX      INTEGER {enable(1),
		   disable(0)}
    ACCESS      read-write
    STATUS      current
       DESCRIPTION "Depending upon the value of this field resolution of FQDN will happen everytime when a trap is sent."
::= { inetTrapDestination 9 }


trapDestinationNum OBJECT-TYPE
    SYNTAX      Integer32
    ACCESS      read-only
    STATUS      current
       DESCRIPTION "The number of trap destinations."
::= { trapDest 1 }


trapDestinationTable OBJECT-TYPE
    SYNTAX      SEQUENCE OF TrapDestinationEntry
    ACCESS      not-accessible
    STATUS      current
       DESCRIPTION "Protocol specific list of destinations
                  to which the agent sends traps."
::= { trapDest 2 }


trapDestinationEntry OBJECT-TYPE
    SYNTAX      TrapDestinationEntry
    ACCESS      not-accessible
    STATUS      current
       DESCRIPTION "Entries are a protocol specific sequence of trap
          destination parameters."
::= { trapDestinationTable 1 }


trapTest OBJECT-TYPE
    SYNTAX      Integer32
    ACCESS      read-write
    STATUS      current
       DESCRIPTION "Causes agent to send an snmp trap to hosts registered in the trap
               destination table.  Value specified will be used as the specific
trap id."
::= { trapDest 3 }


trapSource OBJECT-TYPE
    SYNTAX      Integer32
    ACCESS      read-only
    STATUS      current
       DESCRIPTION "Sets the agent internal source for traps.  Possibilities are as follows:
         0 = ALL_TRAPS_ON
         1 = ASYNC_PERIPHERAL_STATUS traps only
         2 = proprietary PML traps only
         3 = alert table traps only

         This object was changed to read-only to accommodate the SNMPv3
         Notifiaction tables requirement to recieve all traps.  SNMPv3 tags
         are used to filter SNMP Trap sources."
::= { trapDest 4 }


trapFilterDelay OBJECT-TYPE
    SYNTAX      Integer32
    ACCESS      read-write
    STATUS      current
       DESCRIPTION "The purpose of the trap filter feature is to prevent multiple traps
        of the same specificTrapId to be sent within a short period of time.
        This object assigns the period of time within which a duplicate trap
        will be blocked.  This value is in 1/10 second intervals and the default
        value is set to 50 corresponding to 5 seconds. This value remains
persistent
        through a powercycle."
::= { trapDest 5 }


trapFQDNNum OBJECT-TYPE
    SYNTAX      Integer32
    ACCESS      read-only
    STATUS      current
       DESCRIPTION "Number of trapFQDNTable rows."
::= { trapDest 6 }


trapFQDNTable OBJECT-TYPE
    SYNTAX      SEQUENCE OF TrapFQDNEntry
    ACCESS      not-accessible
    STATUS      current
       DESCRIPTION "The trap destination entries can be mapped to destination's FQDN name in this table."
::= { trapDest 7 }


trapFQDNEntry OBJECT-TYPE
    SYNTAX      TrapFQDNEntry
    ACCESS      not-accessible
    STATUS      current
       DESCRIPTION "An FQDN destination entry indexed by the destination's IP address."
::= { trapFQDNTable 1 }


trapIPAddress OBJECT-TYPE
    SYNTAX      IpAddress
    ACCESS      read-only
    STATUS      current
       DESCRIPTION "The trap destination IP address."
::= { trapFQDNEntry 1 }


trapFQDN OBJECT-TYPE
    SYNTAX      OCTET STRING
    ACCESS      read-write
    STATUS      current
       DESCRIPTION "The trap destination's FQDN. This will be resolved to IP address(es) at trap destination time."
::= { trapFQDNEntry 2 }


setCommunityName OBJECT-TYPE
    SYNTAX      OCTET STRING
    ACCESS      read-write
    STATUS      current
       DESCRIPTION "This object controls access of snmp read-write requests.  Factory
        default configuration provides authentication of incoming packets
        with community names: internal and public.  This object overrides the
        factory default settings so that the factory default setttings no longer
        work. This object returns SET or NOT_SET."
::= { community 1 }


getCommunityName OBJECT-TYPE
    SYNTAX      OCTET STRING
    ACCESS      read-write
    STATUS      current
       DESCRIPTION "This object controls access of snmp read requests.  Factory
        default configuration provides authentication of incoming packets
        with community names: internal and public.  This object provides
        access in addition to the factory default settings. If
        set, then authentication will succeed with any of the following
        community names: internal, public, getCommunityName, or
        setCommunityName. This object returns SET or NOT_SET."
::= { community 2 }


npSysStatusMessage OBJECT-TYPE
    SYNTAX      DisplayString
    ACCESS      read-only
    STATUS      current
       DESCRIPTION "A status string reflecting the current state of the card
         and peripheral."
::= { npSys 2 }


npSysModelNumber OBJECT-TYPE
    SYNTAX      OCTET STRING
    ACCESS      read-only
    STATUS      current
       DESCRIPTION "The HP model number of the device."
::= { npSys 10 }


npSysNetworkConnectors OBJECT-TYPE
    SYNTAX      Integer32
    ACCESS      read-only
    STATUS      current
       DESCRIPTION "This object describes the network connectors supported by the
	 device.  The value is a bit mask.  A set bit indicates the
         connector is supported.
         Bit      Value     Connector
          0       0x01      Ethernet, BNC
          1       0x02      Ethernet, AUI
          2       0x04      Ethernet, RJ-45
          3       0x08      TokenRing, DB-9
          4       0x10      TokenRing, RJ-45
          5       0x20      LocalTalk
          6       0x40      100VG, RJ-45
          7       0x80      100T, RJ-45"
::= { npSys 11 }


npSysCardServices1 OBJECT-TYPE
    SYNTAX      Integer32
    ACCESS      read-only
    STATUS      current
       DESCRIPTION "This object is a bitmap showing what services are available
         on the card.

         Bit  0 - IPX/SPX/NCP protocol stack
         Bit  1 - IP/TCP protocol stack
         Bit  2 - LLC/DLC protocol stack
         Bit  3 - Ethertalk protocol stack
         Bit  4 - IPv6 protocol stack
         Bit  5 - IPSec protocol stack
         Bits  6 - 11 Reserved
         Bit 12 - LPD print services
         Bit 13 - FTP print services
         Bit 14 - Port 9100 print services
         Bit 15 - IPP print services
         Bits 16 - 23 Reserved
         Bit 24 - Queue Server Bindery
         Bit 25 - Queue Server NDS
         Bit 26 - Remote Printer
         Bit 27 - SPX Direct Mode
         Bit 28 - DLC Print Services
         Bit 29 - EtherTalk Print Services
         Bits 30 - 31 Reserved"
::= { npSys 16 }


npSysCardServices2 OBJECT-TYPE
    SYNTAX      Integer32
    ACCESS      read-only
    STATUS      current
       DESCRIPTION "This object is a bitmap showing what services are available
         on the card.

         Bit  0 - XIP2
         Bit  1 - PML Get/Set
         Bit  2 - PML Traps
         Bit  3 - Scan to Web Browser
         Bit  4 - Scan to Email
         Bit  5 - MFP Scan Support
         Bits  6 - 11 Reserved
         Bit 12 - Telnet API
         Bit 13 - Web API
         Bit 14 - SNMP V2
         Bit 15 - SNMP Traps
         Bit 16 - Download
         Bit 17 - TFTP
         Bit 18 - RCFG
         Bit 19 - SLP
         Bit 20 - Syslog
         Bit 21 - DHCP
         Bit 22 - BOOTP
         Bit 23 - RARP
         Bit 24 - SNMP V3
         Bit 25 - SSL Functionality
         Bit 26 - Auto IP
         Bits 27 - 31 Reserved"
::= { npSys 17 }


npSysCardServices3 OBJECT-TYPE
    SYNTAX      Integer32
    ACCESS      read-only
    STATUS      current
       DESCRIPTION "This object is a bitmap showing what services are available
         on the card.

         Bit  0 - 100T
         Bit  1 - Token Ring 802.5
         Bit  2 - 802.11b
         Bit  3 - 80211.a
         Bit  4 - Bluetooth
         Bits 5 - 11 Reserved
         Bit  12 -  EIO. For embedded Jetdirect this bit will be 1.
         Bit  13 - LIO
         Bit  14 - USB
         Bit  15 - Firewire
         Bit  16 - TCP Download

         Bits 17 - 31 Reserved"
::= { npSys 22 }


npConnsIP OBJECT-TYPE
    SYNTAX      IpAddress
    ACCESS      read-only
    STATUS      current
       DESCRIPTION "Remote IP address of the node currently connected to the card.
         Zero if no connection is active."
::= { npConns 11 }


npCfgSource OBJECT-TYPE
    SYNTAX      INTEGER {manual-one(1),
                          bootp-two(2),
                          manual-three(3),
                          bootp-four(4),
                          dhcp(5),
                          not-configured(6),
                          default-config(7),
                          rarp(8),
                          read-only(9),
		   auto-ip(10)}
    ACCESS      read-write
    STATUS      current
       DESCRIPTION "This object indicates how the device obtained its IP configuration."
::= { npCfg 1 }


npCfgYiaddr OBJECT-TYPE
    SYNTAX      IpAddress
    ACCESS      read-write
    STATUS      current
       DESCRIPTION "The IP address assigned to the card from the BOOTP reply
         yiaddr field."
::= { npCfg 2 }


npCfgSiaddr OBJECT-TYPE
    SYNTAX      IpAddress
    ACCESS      read-only
    STATUS      current
       DESCRIPTION "The IP address of the TFTP server from the BOOTP reply
         siaddr field."
::= { npCfg 3 }


npCfgLogServer OBJECT-TYPE
    SYNTAX      IpAddress
    ACCESS      read-write
    STATUS      current
       DESCRIPTION "The IP address of the Syslog Server. If set via BOOTP (Tag: 7 field,
         lg=<ipaddress> ) then SNMP set will fail. If not set via BOOTP then SNMP set
         will succeed. Value saved across warm boot power cycles. BOOTP will always
         overwrite SNMP set values."
::= { npCfg 5 }


npCfgSyslogFacility OBJECT-TYPE
    SYNTAX      Integer32
    ACCESS      read-only
    STATUS      current
       DESCRIPTION "This specifies the facility identifier used in syslog messages
         generated by the card."
::= { npCfg 6 }


npCfgAccessState OBJECT-TYPE
    SYNTAX      INTEGER {allowed(1),
		   not-allowed(2)}
    ACCESS      read-only
    STATUS      current
       DESCRIPTION "An indication of whether or not the requesting host
         is allowed to connect to the card as dictated by the
         access list."
::= { npCfg 7 }


npCfgAccessListNum OBJECT-TYPE
    SYNTAX      Integer32
    ACCESS      read-only
    STATUS      current
       DESCRIPTION "The number of access list entries."
::= { npCfg 8 }


npCfgAccessListTable OBJECT-TYPE
    SYNTAX      SEQUENCE OF NpCfgAccessListEntry
    ACCESS      not-accessible
    STATUS      current
       DESCRIPTION "List of access addresses and masks."
::= { npCfg 9 }


npCfgAccessListEntry OBJECT-TYPE
    SYNTAX      NpCfgAccessListEntry
    ACCESS      not-accessible
    STATUS      current
       DESCRIPTION "Each entry contains an access address and mask."
::= { npCfgAccessListTable 1 }


npCfgAccessListIndex OBJECT-TYPE
    SYNTAX      Integer32 (0..9)
    ACCESS      read-only
    STATUS      current
       DESCRIPTION "Index to the configuration access list table."
::= { npCfgAccessListEntry 1 }


npCfgAccessListAddress OBJECT-TYPE
    SYNTAX      IpAddress
    ACCESS      read-write
    STATUS      current
       DESCRIPTION "The Access List Address contains the list of hosts or network
         of hosts that are allowed to connect to the print server over ip.
         When setting this object npCfgAccessListAddrMask should also
         be set in the same varbind packet. NpCfgAccessListAddress
         should always preceed npCfgAccessListAddrMask in the set packet.
         If npCfgAccessListAddrMask is not set, the default value of
         255.255.255.255 will be assigned to npCfgAccessListAddrMask
         for that particular npCfgAccessListAddress entry. Duplicate host
         addresses are possible and, once set, it is not possible to change
         any particular row other than to clear the Access List Table.
         To clear the Access List Table set npCfgAccessListAddress to 0.0.0.0.
         This table has a maximum of 10 rows."
::= { npCfgAccessListEntry 2 }


npCfgAccessListAddrMask OBJECT-TYPE
    SYNTAX      IpAddress
    ACCESS      read-write
    STATUS      current
       DESCRIPTION "Address mask used to help determine whether or not a given
         IP address is allowed access to the print server.  An IP address
         is allowed access if (Addr & AddrMask) == (IP & AddrMask).
         A set of this object may only be done if npCfgAccessListAddress
         preceeds it in the same varbind packet."
::= { npCfgAccessListEntry 3 }


npCfgSubnetMask OBJECT-TYPE
    SYNTAX      IpAddress
    ACCESS      read-write
    STATUS      current
       DESCRIPTION "The subnet mask associated with the IP address of this card."
::= { npCfg 12 }


npCfgDefaultGateway OBJECT-TYPE
    SYNTAX      IpAddress
    ACCESS      read-write
    STATUS      current
       DESCRIPTION "This variable contains the IP address of the default router for this
         card."
::= { npCfg 13 }


npCfgDomainName OBJECT-TYPE
    SYNTAX      OCTET STRING
    ACCESS      read-write
    STATUS      current
       DESCRIPTION "The print server domain name."
::= { npCfg 16 }


npCfgIPP OBJECT-TYPE
    SYNTAX      Integer32
    ACCESS      read-write
    STATUS      current
       DESCRIPTION "Below are the different values accepted by this OID.

				0 - Disable IPP and IPP-S
				1 - Enable IPP and IPP-S
				2 - Enable IPP-S only
				3 - Enable IPP only
			"
::= { npCfg 18 }


npCfgWINSNameServerIdPri OBJECT-TYPE
    SYNTAX      IpAddress
    ACCESS      read-write
    STATUS      current
       DESCRIPTION "Primary name server for NetBIOS over TCP/IP."
::= { npCfg 22 }


npCfgPasswd1Verify OBJECT-TYPE
    SYNTAX      OCTET STRING
    ACCESS      read-write
    STATUS      current
       DESCRIPTION "Compares string value to passwd1 and returns OK if match,
     GENERAL ERROR if doesn't match."
::= { npCfg 28 }


npCfgPasswd1 OBJECT-TYPE
    SYNTAX      DisplayString
    ACCESS      read-write
    STATUS      current
       DESCRIPTION "Password for root or administrator. Get request returns
     either 'SET' or 'NOT_SET'."
::= { npCfg 29 }


npCfgBanner OBJECT-TYPE
    SYNTAX      Integer32 (0..1)
    ACCESS      read-write
    STATUS      current
       DESCRIPTION "Line Printer Daemon Protocol (LPD) banner page per I/O port.
       (0) = Disabled
       (1) = Enabled
     Enabled by default."
::= { npCfg 31 }


npCfgLinkType OBJECT-TYPE
    SYNTAX      INTEGER {autoNegotiate(1),
                          full10T(2),
                          half10T(3),
                          full100T(4),
                          half100T(5),
                          auto100T(6),
		   full1000T(7)}
    ACCESS      read-write
    STATUS      current
       DESCRIPTION "Network link speed and communication mode."
::= { npCfg 35 }


npCfgSnmpDefaultReadCmnty OBJECT-TYPE
    SYNTAX      Integer32 (0..1)
    ACCESS      read-write
    STATUS      current
       DESCRIPTION "Controls Default Read Community Name access.
       (0) = Disabled, i.e., default get community names FAIL to access target.
       (1) = Enabled,  i.e., default get community names SUCCEED to access target."
::= { npCfg 40 }


npCfgBonjourServiceName OBJECT-TYPE
    SYNTAX      OCTET STRING
    ACCESS      read-write
    STATUS      current
       DESCRIPTION "The name by which all the Jetdirect services will be advertised by
       Multicast Domain Name System (Bonjour). Must set a non empty string"
::= { npCfg 44 }


npCfgBonjourDomainName OBJECT-TYPE
    SYNTAX      OCTET STRING
    ACCESS      read-only
    STATUS      current
       DESCRIPTION "The name used as the 'target name' in the DNS SRV records by
     Multicast Domain Name System (Bonjour)."
::= { npCfg 46 }


npCfgIPv6DomainName OBJECT-TYPE
    SYNTAX      OCTET STRING
    ACCESS      read-write
    STATUS      current
       DESCRIPTION "IPv6 Domain Name."
::= { npCfg 49 }


npCfgIPv6ConfigState OBJECT-TYPE
    SYNTAX      INTEGER {ipv6-going-down(0),
		   ipv6-is-up(1)}
    ACCESS      read-only
    STATUS      current
       DESCRIPTION "IPv6 stack status event; IPv6 enabled/disabled."
::= { npCfg 50 }


npCfgIPv6DNSAddr1 OBJECT-TYPE
    SYNTAX      InetAddress
    ACCESS      read-write
    STATUS      current
       DESCRIPTION "IPv6 DNS Address, priority 1."
::= { npCfg 56 }


npCfgIPv6DNSAddr2 OBJECT-TYPE
    SYNTAX      InetAddress
    ACCESS      read-write
    STATUS      current
       DESCRIPTION "IPv6 DNS Address, priority 2."
::= { npCfg 57 }


npCfgIPConfigPrecedence OBJECT-TYPE
    SYNTAX      OCTET STRING
    ACCESS      read-write
    STATUS      current
       DESCRIPTION "Allows to set uniform rules for parameter overwrite by
			different configuration methods.
			0 - Manual
			1 - TFTP
			2 - DHCPv4/Bootp
			3 - DHCPv6     - only if ipv6 is supported
			3/4 - Default  - 4 if ipv6 is supported otherwise 3
			The set string should be 0:1:2:3:4 (or 0:1:2:3 when ipv6 is not supported)
			or any colon separated combination of the 5 (or 4) integral values. The
			string should contain all integral values atleast and atmost once."
::= { npCfg 59 }


npCfgPortConfig OBJECT-TYPE
    SYNTAX      INTEGER {half10T(10),
                          full10T(11),
                          half100T(12),
                          full100T(13),
		   full1000T(19)}
    ACCESS      read-only
    STATUS      current
       DESCRIPTION "Network link speed and communication mode."
::= { npCfg 65 }


npTcpTFTPFileName OBJECT-TYPE
    SYNTAX      OCTET STRING
    ACCESS      read-only
    STATUS      current
       DESCRIPTION "The TFTP configuration file name."
::= { npTcp 9 }


npTcpTFTPServerId OBJECT-TYPE
    SYNTAX      IpAddress
    ACCESS      read-only
    STATUS      current
       DESCRIPTION "TFTP server from which configuration
         information is obtained."
::= { npTcp 10 }


npTcpSyslogMax OBJECT-TYPE
    SYNTAX      Integer32 (0..1000)
    ACCESS      read-write
    STATUS      current
       DESCRIPTION "Maximum number of syslog packets to be sent
         per minute. 0 = Disabled."
::= { npTcp 11 }


npTcpAppSyslogPriority OBJECT-TYPE
    SYNTAX      Integer32 (0..8)
    ACCESS      read-write
    STATUS      current
       DESCRIPTION "Priority below which the syslog messages will
         not be sent.
         Valid priority levels = 0 through 7.
         Disabled = 8."
::= { npTcp 12 }


npCtlReconfig OBJECT-TYPE
    SYNTAX      Integer32
    ACCESS      read-write
    STATUS      current
       DESCRIPTION "Writing any value to this variable causes the card to
         reconfigure itself by doing the BOOTP/TFTP configuration
         activity."
::= { npCtl 8 }


npCtlProtocolSet OBJECT-TYPE
    SYNTAX      Integer32
    ACCESS      read-write
    STATUS      current
       DESCRIPTION "This is a 4 byte integer value.  The least significant bytes
         represent the protocols on the card.  A value of '1' indicates
         a protocol that is enabled.  A value of '0' indicates a
         protocol that is disabled.
         The 32-bit protocol enable 'structure' is defined as:

    		bits 31-28:  Number of I/O channels/protocols present (NUM_CHAN)
    		bits 27-24:  Number of I/O channels which may operate concurrently
                    (NUM_OP_CHAN)
    		bits 23-16:  unused, reserved
    		bits 15-1:   Individual I/O channel/protocol enable bits,
                    0 == disable, 1 == enable
                    MIO_IOCHAN_NOVELL   bit   1
                    MIO_IOCHAN_LLC      bit   2
                    MIO_IOCHAN_TCP      bit   3
                    MIO_IOCHAN_ATALK    bit   4
                    MIO_IOCHAN_IPV6	bit   5
    		bit  0:      When NUM_OP_CHAN == 1, auto-protocol select enable bit,
                    0 == disable, 1 == enable  (APS_ON)"
::= { npCtl 9 }


npCtlSNMPEnableDisable OBJECT-TYPE
    SYNTAX      Integer32 (0..1)
    ACCESS      read-write
    STATUS      current
       DESCRIPTION "0 = SNMP disabled
        1 = SNMP enabled
        If SNMP is enabled, setting this object to 0 will
        disable SNMP on the print server. Once disabled it is not
        possible to enable SNMP via SNMP. When enabled,
        a get request will return 1. SNMP may be enabled
        via a different user interface, such as telnet or
        the print server Embedded Web Server."
::= { npCtl 14 }


npCtlTelnet OBJECT-TYPE
    SYNTAX      Integer32 (0..1)
    ACCESS      read-write
    STATUS      current
       DESCRIPTION "Configure Telnet service.
            (0) = Telnet disabled
            (1) = Telnet enabled"
::= { npCtl 19 }


npCtlFTP OBJECT-TYPE
    SYNTAX      Integer32 {
                          printDisable-downloadDisable(0),
                          printEnable-downloadEnable(1),
                          printEnable-downloadDisable(2),
                          printDisable-downloadEnable(3)
		   }
    ACCESS      read-write
    STATUS      current
       DESCRIPTION "Configure File Transfer Protocol (FTP) service.
            (0) = Both FTP Print and Download Disabled
            (1) = Both FTP Print and Download Enabled
            (2) = FTP Print Enabled and FTP Download Disabled
            (3) = FTP Print Disabled and FTP Download Enabled
            "
::= { npCtl 20 }


npCtlSLP OBJECT-TYPE
    SYNTAX      Integer32 (0..1)
    ACCESS      read-write
    STATUS      current
       DESCRIPTION "Configure Service Location Protocol (SLP) service.
            (0) = SLP disabled
            (1) = SLP enabled"
::= { npCtl 21 }


npCtlLPD OBJECT-TYPE
    SYNTAX      Integer32 (0..1)
    ACCESS      read-write
    STATUS      current
       DESCRIPTION "Configure Line Printer Daemon Protocol (LPD) service.
            (0) = LPD disabled
            (1) = LPD enabled"
::= { npCtl 22 }


npCtl9100 OBJECT-TYPE
    SYNTAX      Integer32 (0..1)
    ACCESS      read-write
    STATUS      current
       DESCRIPTION "Configure TCP port 9100 printing.
            (0) = port 9100 printing disabled
            (1) = port 9100 printing enabled"
::= { npCtl 24 }


npCtlSysLog OBJECT-TYPE
    SYNTAX      Integer32 (0..1)
    ACCESS      read-write
    STATUS      current
       DESCRIPTION "Configure Syslog service.
            (0) = Syslog service disabled
            (1) = Syslog service enabled
         Enabled by default."
::= { npCtl 26 }


npCtlSnmpVersionAccess OBJECT-TYPE
    SYNTAX      INTEGER {snmpV1RW-snmpV3RW(1),
                          snmpV1RO-snmpV3RW(2),
                          snmpV1NoAccess-snmpV3RW(3),
                          snmpV1RW-snmpV3NoAccess(4),
		   snmpV1RO-snmpV3NoAccess(5)}
    ACCESS      read-write
    STATUS      current
       DESCRIPTION "Manages an SNMP version's read and write access to the MIB."
::= { npCtl 27 }


npCtlSnmpV3InitAccount OBJECT-TYPE
    SYNTAX      INTEGER {destroy(0),
		   blockInitEncrypt(4)}
    ACCESS      read-write
    STATUS      current
       DESCRIPTION "Used to create initial SNMPv3 account.  The following rules apply:

         0 = clear init account, only if previously 0.
         4 = Block init account, only cold reset will clear or use Web User interface.

      Setting this object to blocked (4) will block an initial account
      creation until a cold reset."
::= { npCtl 28 }


npCtlBonjour OBJECT-TYPE
    SYNTAX      Integer32 (0..1)
    ACCESS      read-write
    STATUS      current
       DESCRIPTION "Configure Multicast Domain Name Service.
            (0) = Bonjour disabled
            (1) = Bonjour enabled"
::= { npCtl 29 }


npCtlNetworkConnectionMode OBJECT-TYPE
    SYNTAX      INTEGER {auto-cable-detect(1),
                          disable-radio(2),
		   disable-wired(3)}
    ACCESS      read-write
    STATUS      current
       DESCRIPTION "This object controls the selection of the active network
         interface used for communication. This is applicable to
         products supporting dual wired and wireless network interfaces"
::= { npCtl 32 }


npCtlIPSecurityPolicy OBJECT-TYPE
    SYNTAX      INTEGER {disable(0),
		   enable(1)}
    ACCESS      read-write
    STATUS      current
       DESCRIPTION "Disable IP Security (IPSec) or Firewall. Only disabling is allowed."
::= { npCtl 34 }


npCtlWSDiscovery OBJECT-TYPE
    SYNTAX      INTEGER {disable(0),
		   enable(1)}
    ACCESS      read-write
    STATUS      current
       DESCRIPTION "Web Services Discovery enable/disable."
::= { npCtl 36 }


npCtlWSPrint OBJECT-TYPE
    SYNTAX      INTEGER {disable(0),
		   enable(1)}
    ACCESS      read-write
    STATUS      current
       DESCRIPTION "Web Services Print enable/disable."
::= { npCtl 37 }


npCtlLLMNR OBJECT-TYPE
    SYNTAX      INTEGER {disable(0),
		   enable(1)}
    ACCESS      read-write
    STATUS      current
       DESCRIPTION "Link-Local Multicast Name Resolution( LLMNR ) enable/disable."
::= { npCtl 38 }


npCtlFpDot11WirelessState OBJECT-TYPE
    SYNTAX      INTEGER {disable(0),
		   enable(1)}
    ACCESS      read-write
    STATUS      current
       DESCRIPTION "Use for enabling and disabling Wireless Radio.
			The following values are defined:
			Disable		= 0
			Enable		= 1
			Default		= 1(Enabled)"
::= { npCtl 47 }


npCtlAirPrintStatus OBJECT-TYPE
    SYNTAX      INTEGER {disable(0),
		   enable(1)}
    ACCESS      read-write
    STATUS      current
       DESCRIPTION " Use to Enabled/Disabled AirPrint functionality.
			Disable				= 0
			Enable(Default)		= 1
		    "
::= { npCtl 68 }


npCtlAllowRFC5746TLS-SSLCompatibilityMode OBJECT-TYPE
    SYNTAX      INTEGER {disable(0),
		   enable(1)}
    ACCESS      read-write
    STATUS      current
       DESCRIPTION "  Added to support RFC-5746.
			   This OID can be use to enable/disable legacy SSL renegotiation.
			    Disable				= 0
			    Enable(Default)		= 1
		    "
::= { npCtl 70 }


npPortNumPorts OBJECT-TYPE
    SYNTAX      Integer32 (0..255)
    ACCESS      read-only
    STATUS      current
       DESCRIPTION "The number of peripheral interfaces supported by this device."
::= { npPort 1 }


npDHCPserver OBJECT-TYPE
    SYNTAX      IpAddress
    ACCESS      read-only
    STATUS      current
       DESCRIPTION "IP address of DHCP server that provided this unit with an IP
         address via the DHCP protocol."
::= { npDhcp 2 }


npDhcpFQDNBehavior OBJECT-TYPE
    SYNTAX      INTEGER {present-JD-Behavior(0),
		   rFC4702-compliant-Behavior(1)}
    ACCESS      read-write
    STATUS      current
       DESCRIPTION "This object defines the FQDN behavior in Jetdirect. Set this to
			 ( 0 ) - Present Jetdirect Behavior
			 ( 1 ) - RFC 4702 compliant behavior"
::= { npDhcp 4 }


npWebCheckACLforHTTP OBJECT-TYPE
    SYNTAX      Integer32 (0..1)
    ACCESS      read-write
    STATUS      current
       DESCRIPTION "Configure checking of HTTP web connections against Access Control List.
      (0) = Disable ACL checking
      (1) = Enable ACL checking"
::= { npWeb 17 }


npSecurityDot11ServerAuthentication OBJECT-TYPE
    SYNTAX      INTEGER {eap-md5(1),
                          eap-tls(2),
                          leap(4),
                          peap(8),
		   ttls(16)}
    ACCESS      read-write
    STATUS      current
       DESCRIPTION "Server-Based Authentication with the following bitwise values:
	   None(0),
	   EAP-MD5(1),
	   EAP-TLS(2),
	   LEAP(4),
	   PEAP(8),
	   TTLS(16)"
::= { npSecurity 1 }


npSecurityDot1xEapMd5Identity OBJECT-TYPE
    SYNTAX      OCTET STRING
    ACCESS      read-write
    STATUS      current
       DESCRIPTION "Radius MD5 authentication User Name."
::= { npSecurity 2 }


npSecurityDot1xTLSAuthServerId OBJECT-TYPE
    SYNTAX      OCTET STRING
    ACCESS      read-write
    STATUS      current
       DESCRIPTION "TLS authentication Server ID."
::= { npSecurity 3 }


npSecurityPublicKey OBJECT-TYPE
    SYNTAX      OCTET STRING
    ACCESS      read-only
    STATUS      current
       DESCRIPTION "The public key of a public/private key pair to be
	  used by applications to set encrypted values."
::= { npSecurity 4 }


npSecurityDot11EncryptedDot11NetworkName OBJECT-TYPE
    SYNTAX      OCTET STRING
    ACCESS      write-only
    STATUS      current
       DESCRIPTION "The encrypted network name (SSID).  Use the
        npSecurityPublicKey to encrypt this value.
	  Setting this object will cause the card to reconfigure."
::= { npSecurity 5 }


npSecurityDot11EncryptedDot1xEapMd5Secret OBJECT-TYPE
    SYNTAX      OCTET STRING
    ACCESS      write-only
    STATUS      current
       DESCRIPTION "The encrypted dot1xEapMD5Secret authentication password.
	  Use the npSecurityPublicKey to encrypt this value.
        Setting this object will cause the card to reconfigure."
::= { npSecurity 6 }


npSecurityDot11EncryptedWEPKeyTable OBJECT-TYPE
    SYNTAX      SEQUENCE OF NpSecurityDot11EncryptedWEPKeyEntry
    ACCESS      not-accessible
    STATUS      current
       DESCRIPTION "Encrypted interface to the WEP Keys."
::= { npSecurity 7 }


npSecurityDot11EncryptedWEPKeyEntry OBJECT-TYPE
    SYNTAX      NpSecurityDot11EncryptedWEPKeyEntry
    ACCESS      not-accessible
    STATUS      current
       DESCRIPTION "Each row of the table gives a WEP Key"
::= { npSecurityDot11EncryptedWEPKeyTable 1 }


npSecurityDot11EncryptedWEPKey OBJECT-TYPE
    SYNTAX      OCTET STRING
    ACCESS      write-only
    STATUS      current
       DESCRIPTION "The encrypted WEP Key value.  Use
        the npSecurityDot11PublicKey to encrypt this value.
        Setting this object will cause the card to reconfigure."
::= { npSecurityDot11EncryptedWEPKeyEntry 2 }


npSecurityDot11SignalStrength OBJECT-TYPE
    SYNTAX      INTEGER {level-1-TBD(1),
                          level-2-TBD(2),
                          level-3-TBD(3),
                          level-4-TBD(4),
		   level-5-TBD(5)}
    ACCESS      read-only
    STATUS      current
       DESCRIPTION "A weighted average over time of the signal strength
        between the access point and the print server in infrastructure
        mode. Not applicable when in ad hoc mode."
::= { npSecurity 8 }


npSecurityDot11SSIDTable OBJECT-TYPE
    SYNTAX      SEQUENCE OF NpSecurityDot11SSIDEntry
    ACCESS      not-accessible
    STATUS      current
       DESCRIPTION "List of discovered SSIDs."
::= { npSecurity 9 }


npSecurityDot11SSIDEntry OBJECT-TYPE
    SYNTAX      NpSecurityDot11SSIDEntry
    ACCESS      not-accessible
    STATUS      current
       DESCRIPTION "Each row of the table gives a discovered SSID value."
::= { npSecurityDot11SSIDTable 1 }


npSecurityDot11SSID OBJECT-TYPE
    SYNTAX      OCTET STRING
    ACCESS      read-only
    STATUS      current
       DESCRIPTION "A discovered SSID value."
::= { npSecurityDot11SSIDEntry 2 }


npSecurityDot11SSIDTableNumEntries OBJECT-TYPE
    SYNTAX      Integer32
    ACCESS      read-only
    STATUS      current
       DESCRIPTION "Displays the number of discovered SSIDs in
         the SSID Table."
::= { npSecurity 10 }


npSecuritySnmpV3EncryptedUserName OBJECT-TYPE
    SYNTAX      OCTET STRING
    ACCESS      write-only
    STATUS      current
       DESCRIPTION "The encrypted SNMPv3 User Name.
	Use the npSecurityPublicKey to encrypt this value.
	The new SNMPv3 User Account will be installed after the
	npSecuritySnmpV3EncryptedUserName, npSecuritySnmpV3EncryptedMD5Key
	and npSecuritySnmpV3EncryptedDesKey have been set."
::= { npSecurity 13 }


npSecuritySnmpV3AuthKeyPassPhrase OBJECT-TYPE
    SYNTAX      OCTET STRING
    ACCESS      write-only
    STATUS      current
       DESCRIPTION "The encrypted SNMPv3 MD5 authentication key.
	Use the npSecurityPublicKey to encrypt this value.
	The new SNMPv3 User Account will be installed after the
	npSecuritySnmpV3EncryptedUserName, npSecuritySnmpV3EncryptedMD5Key
	and npSecuritySnmpV3EncryptedDesKey have been set."
::= { npSecurity 14 }


npSecuritySnmpV3PrivKeyPassPharse OBJECT-TYPE
    SYNTAX      OCTET STRING
    ACCESS      write-only
    STATUS      current
       DESCRIPTION "The encrypted SNMPv3 DES encryption key.
	Use the npSecurityPublicKey to encrypt this value.
	The new SNMPv3 User Account will be installed after the
	npSecuritySnmpV3EncryptedUserName, npSecuritySnmpV3EncryptedMD5Key
	and npSecuritySnmpV3EncryptedDesKey have been set."
::= { npSecurity 15 }


npSecurityDot11BSSID OBJECT-TYPE
    SYNTAX      OCTET STRING
    ACCESS      read-only
    STATUS      current
       DESCRIPTION "The BSSID value (hardware address of the access point)."
::= { npSecurity 16 }


npSecurityDot11ExactMatchServerId OBJECT-TYPE
    SYNTAX      INTEGER {true(1),
		   false(2)}
    ACCESS      read-write
    STATUS      current
       DESCRIPTION "Indicates if an exact match is required on the EAP Server ID."
::= { npSecurity 19 }


npSecurityDot11EncryptionStrength OBJECT-TYPE
    SYNTAX      INTEGER {low(1),
                          medium(2),
		   high(3)}
    ACCESS      read-write
    STATUS      current
       DESCRIPTION "Indicates the EAP encrytpion strength."
::= { npSecurity 20 }


npSecuritySslRedirection OBJECT-TYPE
    SYNTAX      INTEGER {redirectionEnabled(1),
		   redirectionDisabled(2)}
    ACCESS      read-write
    STATUS      current
       DESCRIPTION "Setting this object causes the SSL redirection connection
         to be enabled or disabled."
::= { npSecurity 23 }


npSecurityServicesSupported OBJECT-TYPE
    SYNTAX      Integer32
    ACCESS      read-only
    STATUS      current
       DESCRIPTION "BITWISE indication of the 802.11 security services this device supports.
        The following bits are defined:

        MD5       						(0)
        TLS       						(1)
        TTLS      						(2)
        LEAP      						(3)
        PEAP      						(4)
        Reserved  						(5 - 15)
        WEP       						(16)
        WPA       						(17)
        AES       						(18)
        WPA2      						(19)
        AUTO_FOR_WEP_SUPPORTED      	(20)
        AUTO_FOR_WPA_SUPPORTED      	(21)
        AUTO_FOR_ENCRYPTION_SUPPORTED   (22)
        Reserved  (23 - 31)"
::= { npSecurity 27 }


npSecurityDot11Encryption OBJECT-TYPE
    SYNTAX      Integer32
    ACCESS      read-write
    STATUS      current
       DESCRIPTION "802.11 encryption method currently enabled.
        The following values are defined:

       	NONE       (0x00)
       	SSN/WEP    (0x01)
       	TKIP       (0x02)
	    AES        (0x03)
	    AUTO       (0x04)
        Reserved  (5 - 31)

        It is advised not to use dot11PrivacyInvoked OID anymore, instead use npSecurityDot11Encryption.
        Since Jetdirect updates the same variable when the set happens through any of the two OIDs and
        npSecurityDot11Encryption is more versatile, it is recommended to use this OID.
        "
::= { npSecurity 28 }


npSecurityDot11MulticastCipher OBJECT-TYPE
    SYNTAX      Integer32
    ACCESS      read-write
    STATUS      current
       DESCRIPTION "BITWISE indication of the multicast cipher method currently enabled.
         At minimum, one bit must be set.
         The following bits are defined:

	      WEP       (0)
	      WPA       (1)
         Reserved  (2 - 31)"
::= { npSecurity 29 }


npSecurityDot11BeaconTableNumEntries OBJECT-TYPE
    SYNTAX      Integer32
    ACCESS      read-only
    STATUS      current
       DESCRIPTION "Displays the number of discovered SSIDs in the DOT11 Beacon Table."
::= { npSecurity 34 }


npSecurityDot11OpenSSIDEnabled OBJECT-TYPE
    SYNTAX      TruthValue
    ACCESS      read-only
    STATUS      current
       DESCRIPTION "Indicates if the Open SSID is enabled (Spirit-only)."
::= { npSecurity 35 }


npSecurityDot11EncryptedWPAConfigPSKPassPhrase OBJECT-TYPE
    SYNTAX      OCTET STRING
    ACCESS      write-only
    STATUS      current
       DESCRIPTION "The encrypted WPA Config PSK PassPhrase.  Use the
          npSecurityPublicKey to encrypt this value"
::= { npSecurity 36 }


npSecurityDot11DynamicEncryption OBJECT-TYPE
    SYNTAX      INTEGER {nONE(0),
                          bASIC(1),
                          wPA(2),
                          wPA2(3),
		   aUTO(4)}
    ACCESS      read-write
    STATUS      current
       DESCRIPTION "WPA mode.
			(0x00) = NONE
			(0x01) = BASIC
			(0x02) = WPA
			(0x03) = WPA2
			(0x04) = AUTO"
::= { npSecurity 42 }


npSecurityDot11LinkAuthentication OBJECT-TYPE
    SYNTAX      INTEGER {open(1),
                          shared-key(2),
                          leap(128),
		   auto(143)}
    ACCESS      read-write
    STATUS      current
       DESCRIPTION "DOT11 Link Authentication modes.
			(1) = OPEN
			(2) = SHARED-KEY
			(128) = LEAP
			(143) = AUTO

			We can set the Link Authentication using the object dot11AuthenticationAlgorithmsEnable ( OID: 1.2.840.10036.1.2.1.3.x )
			Since the dot11AuthenticationAlgorithsmEnable object does not supports setting of AUTO option, we provide this object.

			Through this OID you can set to any one of the above options.
			Whereas using the dot11AuthenticationAlgorithmsEnable object we can set either OPEN OR SHARED mode only."
::= { npSecurity 43 }


gdStatusBytes OBJECT-TYPE
    SYNTAX      Integer32
    ACCESS      read-only
    STATUS      current
       DESCRIPTION "The number of valid bytes in the gdStatusEntry
         array."
::= { generalDeviceStatus 1 }


gdStatusDisplay OBJECT-TYPE
    SYNTAX      DisplayString
    ACCESS      read-only
    STATUS      current
       DESCRIPTION "The string diplayed on the peripheral front panel.
         For some peripherals, such as the HP LaserJet IIISi printer
         or HP DesignJet plotter, this is always a zero length string."
::= { generalDeviceStatus 3 }


gdStatusId OBJECT-TYPE
    SYNTAX      OCTET STRING
    ACCESS      read-only
    STATUS      current
       DESCRIPTION "A formatted string of NVT ASCII
         charactersdescribing this peripheral."
::= { generalDeviceStatus 7 }


gdStatusJobTimeout OBJECT-TYPE
    SYNTAX      Integer32
    ACCESS      read-write
    STATUS      obsolete
::= { generalDeviceStatus 10 }


gdPasswords OBJECT-TYPE
    SYNTAX      OCTET STRING
    ACCESS      read-write
    STATUS      current
       DESCRIPTION "This object is used as a 256 byte NVRAM area for JetAdmin.  It
         is completely managed by JetAdmin.  Initially it is initialized
         to all zeros.  A coldboot will re-initialize to all zeros."
::= { generalDeviceStatus 13 }


pmlTrapEnable OBJECT-TYPE
    SYNTAX      OBJECT IDENTIFIER
    ACCESS      read-write
    STATUS      current
       DESCRIPTION "This OID is used to enable individual peripheral trappable objects through the print server."
::= { netPMLtrap 1 }


pmlTrapDisable OBJECT-TYPE
    SYNTAX      OBJECT IDENTIFIER
    ACCESS      read-write
    STATUS      current
       DESCRIPTION "This OID is used to disable individual peripheral trappable objects through the print server."
::= { netPMLtrap 2 }


npNpiPaeClass OBJECT-TYPE
    SYNTAX      INTEGER {printer(1),
                          plotter(2),
		   xStation(3)}
    ACCESS      read-only
    STATUS      current
       DESCRIPTION "The class assigned to the peripheral onto which
         this card is plugged."
::= { npNpiPeripheralAttributeEntry 2 }


npNpiPaeIdentification OBJECT-TYPE
    SYNTAX      INTEGER {laserjet-IIISI(1),
		   laserjet-4SI(5)}
    ACCESS      read-only
    STATUS      current
       DESCRIPTION "The Identification number of the peripheral.  These values are
         defined in the MIO spec.  DesignJet, PaintJet XL300, and
         DesignJet/600 peripherals will identify themselves as
         LaserJet-IIIsi."
::= { npNpiPeripheralAttributeEntry 3 }


npNpiCaeClass OBJECT-TYPE
    SYNTAX      INTEGER {rs-232(1),
                          centronics(2),
                          csma-cd-network(3),
                          token-ring-network(4),
                          scsi(5),
                          hpib(6),
                          localtalk(7),
                          hpna(8),
                          usb(9),
                          firewire(10),
                          bluetooth(11),
		   ieee802-11b(12)}
    ACCESS      read-only
    STATUS      current
       DESCRIPTION "The class of this network peripheral card."
::= { npNpiCardAttributeEntry 2 }


gdStatusLineState OBJECT-TYPE
    SYNTAX      Integer32 (0..255)
    ACCESS      read-only
    STATUS      current
       DESCRIPTION "This describes the line state of the peripheral.
         When non-zero, the peripheral is off-line.  When
         zero the peripheral is on-line."
::= { gdStatusEntry 1 }


gdStatusPaperState OBJECT-TYPE
    SYNTAX      Integer32 (0..255)
    ACCESS      read-only
    STATUS      current
       DESCRIPTION "This describes the state of the paper on the peripheral.
         When non-zero, the peripheral has a paper problem. When
         zero, the peripheral does not have a paper problem."
::= { gdStatusEntry 2 }


gdStatusInterventionState OBJECT-TYPE
    SYNTAX      Integer32 (0..255)
    ACCESS      read-only
    STATUS      current
       DESCRIPTION "This describes the intervention state of the
         peripheral.  When non-zero, the peripheral requires
         human intervention to continue working.  When
         zero, it requires no assistance."
::= { gdStatusEntry 3 }


gdStatusPeripheralError OBJECT-TYPE
    SYNTAX      Integer32 (0..255)
    ACCESS      read-only
    STATUS      current
       DESCRIPTION "This is the error code from the peripheral."
::= { gdStatusEntry 6 }


gdStatusPaperOut OBJECT-TYPE
    SYNTAX      Integer32
    ACCESS      read-only
    STATUS      current
       DESCRIPTION "This indicates that the peripheral is out of paper.
                off (0),
                paper-out-or-paper-mount (1),
                manual-paper-feed-needed (2)
         For some peripherals, such as the HP LaserJet IIISi printer
         or HP DesignJet plotter, this value is always a zero (0)."
::= { gdStatusEntry 8 }


gdStatusPaperJam OBJECT-TYPE
    SYNTAX      Integer32
    ACCESS      read-only
    STATUS      current
       DESCRIPTION "This indicates that the peripheral has a paper jam.
              off (0),
              paper-jam(1)
         For some peripherals, such as the HP LaserJet IIISi printer
         or HP DesignJet plotter, this value is always a zero (0)."
::= { gdStatusEntry 9 }


gdStatusTonerLow OBJECT-TYPE
    SYNTAX      Integer32
    ACCESS      read-only
    STATUS      current
       DESCRIPTION "This indicates that the peripheral has a low toner condition.
              off (0),
              toner-low (1),
              no-toner-cartridge (2)
         For some peripherals, such as the HP LaserJet IIISi printer
         or HP DesignJet plotter, this value is always a zero (0)."
::= { gdStatusEntry 10 }


gdStatusPagePunt OBJECT-TYPE
    SYNTAX      Integer32 (0..255)
    ACCESS      read-only
    STATUS      current
       DESCRIPTION "This indicates that the peripheral did not receive data fast
         enough to keep up with the print engine when generating a page.
         For some peripherals, such as the HP LaserJet IIISi printer
         or HP DesignJet plotter, this value is always a zero (0)."
::= { gdStatusEntry 11 }


gdStatusMemoryOut OBJECT-TYPE
    SYNTAX      Integer32 (0..255)
    ACCESS      read-only
    STATUS      current
       DESCRIPTION "This indicates that the peripheral did not have enough memory
         to render an image on a page.
         For some peripherals, such as the HP LaserJet IIISi printer
         or HP DesignJet plotter, this value is always a zero (0)."
::= { gdStatusEntry 12 }


gdStatusIoActive OBJECT-TYPE
    SYNTAX      Integer32 (0..255)
    ACCESS      read-only
    STATUS      current
       DESCRIPTION "This indicates that the peripheral is processing data from
         this I/O interface card. For some peripherals, such as the
         HP LaserJet IIISi printer or HP DesignJet plotter,
         this value is always a zero (0).

         For X.20.06 firmware and later firmware releases, this object is
         not relevant. In order not to break legacy applications which call this
         object in multi-varbind requests, this value is always zero (0)."
::= { gdStatusEntry 13 }


gdStatusBusy OBJECT-TYPE
    SYNTAX      Integer32 (0..255)
    ACCESS      read-only
    STATUS      current
       DESCRIPTION "This indicates that the peripheral is busy processing
         print/plot data.
         For some peripherals, such as the HP LaserJet IIISi printer
         or HP DesignJet plotter, this value is always a zero (0)."
::= { gdStatusEntry 14 }


gdStatusWait OBJECT-TYPE
    SYNTAX      Integer32 (0..255)
    ACCESS      read-only
    STATUS      current
       DESCRIPTION "This indicates that the peripheral is waiting for print/plot
         data to process.
         For some peripherals, such as the HP LaserJet IIISi printer
         or HP DesignJet plotter, this value is always a zero (0)."
::= { gdStatusEntry 15 }


gdStatusInitialize OBJECT-TYPE
    SYNTAX      Integer32
    ACCESS      read-only
    STATUS      current
       DESCRIPTION "This indicates that the peripheral is initializing or
         warming up.
              off (0),
              initializing (1),
              warm-up(2)
         For some peripherals, such as the HP LaserJet IIISi printer
         or HP DesignJet plotter, this value is always a zero (0)."
::= { gdStatusEntry 16 }


gdStatusDoorOpen OBJECT-TYPE
    SYNTAX      Integer32 (0..255)
    ACCESS      read-only
    STATUS      current
       DESCRIPTION "This indicates that the peripheral cover or door is open.
         For some peripherals, such as the HP LaserJet IIISi printer
         or HP DesignJet plotter, this value is always a zero (0)."
::= { gdStatusEntry 17 }


gdStatusPrinting OBJECT-TYPE
    SYNTAX      Integer32
    ACCESS      read-only
    STATUS      current
       DESCRIPTION "This indicates that the peripheral is printing or otherwise
         marking or moving paper.
              off (0),
              ordinary-page (1),
              test-fonts-config-or-start-page (2)
         For some peripherals, such as the HP LaserJet IIISi printer
         or HP DesignJet plotter, this value is always a zero (0)."
::= { gdStatusEntry 18 }


gdStatusPaperOutput OBJECT-TYPE
    SYNTAX      Integer32
    ACCESS      read-only
    STATUS      current
       DESCRIPTION "This indicates that the peripheral has a paper output problem
         such as the output storage bin being full.
              off (0),
              output-storage-full (1)
         For some peripherals, such as the HP LaserJet IIISi printer
         or HP DesignJet plotter, this value is always a zero (0)."
::= { gdStatusEntry 19 }


photo-access-card-error OBJECT-TYPE
    SYNTAX      INTEGER {
                          ePhotoCardAccessNoError(0),
                          ePhotoCardSmartMediaUpsideDown(1),
                          ePhotoCardMediaNotFullyInserted(2),
                          ePhotoCardMoreThenOneInSlots(3),
                          ePhotoCardReadError(4),
                          ePhotoCardRemovedWhileReading(5),
                          ePhotoCardBadFileWhilePrinting(6),
                          ePhotoCardNotInSlot(7),
                          ePhotoCardContainsNoPhotos(8),
                          ePhotoCardWriteError(9),
                          ePhotoCardRemovedWhileWriting(10),
                          ePhotoCardUnknownError(999)
		   }
    ACCESS      read-only
    STATUS      optional
       DESCRIPTION "Specifies the error reason for most recent unsucessful photo
		card access.
                Additional information:
                Specifies the error reason for most recent unsucessful photo
                card access."
::= { photo-job 2 }


photo-default-num-copies OBJECT-TYPE
    SYNTAX      INTEGER(1..99)
    ACCESS      read-write
    STATUS      optional
       DESCRIPTION "Reads or writes the default number of copies to be printed
		during photo application print jobs. This value is saved over a
		power cycle.
                Additional information:
                Reads or writes the default number of copies to be
                printed during photo application print jobs.  This value is
                saved over a power cycle."
::= { settings-photo-job 1 }


photo-job-num-copies OBJECT-TYPE
    SYNTAX      INTEGER(1..99)
    ACCESS      read-write
    STATUS      optional
       DESCRIPTION "Reads or writes the number of copies to be printed during the
		next photo application print job. This value is not saved over
		power cycles.
                Additional information:
                Reads or writes the number of copies to be printed
                during the next photo application print job.  This value is
                not saved over a power cycle."
::= { settings-photo-job 2 }


photo-job-media-size OBJECT-TYPE
    SYNTAX      INTEGER {
                          eUSLetter(2),
                          eISOandJISA4(26),
                          ePhoto4x6(76)
		   }
    ACCESS      read-write
    STATUS      optional
       DESCRIPTION "Reads or writes the default media size to be used during the
		next photo application print job. This value is not saved over
		power cycles.
                Additional information:
                Reads or writes the default media size to be
                used during the next photo application print job.  This
                value is not saved over a power cycle."
::= { settings-photo-job 4 }


photo-job-media-name OBJECT-TYPE
    SYNTAX      OCTET STRING
    ACCESS      read-write
    STATUS      optional
       DESCRIPTION "Reads or writes the media type to be used on the next photo
		application print job. This value is not saved over power
		cycles.
                Additional information:
                Reads or writes the media type to be used on the next
                photo application print job. This value is not saved over a
                power cycle."
::= { settings-photo-job 6 }


photo-image-size OBJECT-TYPE
    SYNTAX      INTEGER {
                          eThumbnail(1),
                          eWallet(2),
                          e3halfx5in(3),
                          e3x4in(4),
                          e4x6in(5),
                          e5x7in(6),
                          e6x8in(7),
                          e8x10in(8),
                          e6x8cm(9),
                          e7x10cm(10),
                          e9x13cm(11),
                          e10x15cm(12),
                          e13x18cm(13),
                          e15x21cm(14),
                          e18x24cm(15),
                          e20x25cm(16),
                          eFullPage(17),
                          ePanoramic(18)
		   }
    ACCESS      read-write
    STATUS      optional
       DESCRIPTION "Reads or writes the default image size to be used during photo
		application print jobs. This value is saved over power cycles.
                Additional information:
                Reads or writes the default image size to be
                used during photo application print jobs. This value is
                saved over a power cycle. Valid image sizes are determined
                by the PHOTO-IMAGE-SIZE-SET pml object."
::= { settings-photo-job 7 }


photo-job-image-size OBJECT-TYPE
    SYNTAX      INTEGER {
                          eThumbnail(1),
                          eWallet(2),
                          e3halfx5in(3),
                          e3x4in(4),
                          e4x6in(5),
                          e5x7in(6),
                          e6x8in(7),
                          e8x10in(8),
                          e6x8cm(9),
                          e7x10cm(10),
                          e9x13cm(11),
                          e10x15cm(12),
                          e13x18cm(13),
                          e15x21cm(14),
                          e18x24cm(15),
                          e20x25cm(16),
                          eFullPage(17),
                          ePanoramic(18)
		   }
    ACCESS      read-write
    STATUS      optional
       DESCRIPTION "Reads or writes the image size to be used during the next photo
		application print job. This value is not saved over power
		cycles.
                Additional information:
                Reads or writes the image size to be used during
                the next photo application print job. This value is not
                saved over a power cycle. Valid image sizes are determined
                by the PHOTO-IMAGE-SIZE-SET pml object."
::= { settings-photo-job 8 }


photo-select-images OBJECT-TYPE
    SYNTAX      OCTET STRING
    ACCESS      read-write
    STATUS      optional
       DESCRIPTION "Reads or writes the list of images to print during the next
		photo application print job. Each image number or number range
		must be separated by a comma. The image number corresponds to
		the location of the file on the image card. For example, if
		there are 10 images on the photo card, then you could select
		'1-10' or '1,2,3,4,5' or '1,2,3,4-9'. The same image number can
		also appear multiple times in the list. i.e.
		'1,2,2,2,3,3,4,4,5'. This value is not saved over power cycles
		and only applies to the next job.
                Additional information:
                Reads or writes the list of images to print
                during the next photo application print job. Each image
                number or number range must be separated by a comma.  The
                image number corresponds to the location of the file on
                the image card.  For example, if there are 10 images on
                the photo card, then you could select 1-10 or 1,2,3,4,5 or
                1,2,3,4-9.  The same image number can also appear multiple
                times in the list. i.e. 1,2,2,2,3,3,4,4,5.  This value is
                not saved over a power cycle, and only applies to the next
                job."
::= { settings-photo-job 9 }


photo-images-on-card OBJECT-TYPE
    SYNTAX      INTEGER
    ACCESS      read-only
    STATUS      optional
       DESCRIPTION "Reads the number of printable photo images found on the
		inserted memory card. If 0, then no images were found, or the
		card was not properly inserted.
                Additional information:
                Reads the number of printable photo images found
                on the inserted memory card.  If 0, then no images were
                found, or the card was not properly inserted."
::= { settings-photo-job 10 }


photo-job-source OBJECT-TYPE
    SYNTAX      INTEGER {
                          ePhotoPrintProofSheet(1),
                          ePhotoScanProofSheet(2),
                          ePhotoPrintColorJob(3),
                          ePhotoPrintMonochromeJob(4),
                          ePhotoPrintIndexPrint(5)
		   }
    ACCESS      write-only
    STATUS      optional
       DESCRIPTION "Controls initiating photo application features.
                Additional information:
                Controls initiating photo application features."
::= { settings-photo-job 11 }


photo-color-page-count OBJECT-TYPE
    SYNTAX      INTEGER
    ACCESS      read-write
    STATUS      optional
       DESCRIPTION "Reads or writes the page count for color pages printed by the
		photo application. This value is saved over power cycles.
                Additional information:
                Reads or writes the page count for color pages
                printed by the photo application. This value is saved over
                a power cycle."
::= { settings-photo-job 12 }


photo-mono-page-count OBJECT-TYPE
    SYNTAX      INTEGER
    ACCESS      read-write
    STATUS      optional
       DESCRIPTION "Reads or writes the page count for monochrome pages printed by
		the photo application. This value is saved over power cycles.
                Additional information:
                Reads or writes the page count for monochrome pages
                printed by the photo application. This value is saved over
                a power cycle."
::= { settings-photo-job 13 }


photo-image-size-set OBJECT-TYPE
    SYNTAX      INTEGER {
                          eImageSizeSetInch1(1),
                          eImageSizeSetInch2(2),
                          eImageSizeSetCentimeter1(3),
                          eImageSizeSetCentimeter2(4),
                          eImageSizeSetCentimeter3(5)
		   }
    ACCESS      read-write
    STATUS      optional
       DESCRIPTION "This is only writable in service mode. This object changes the
		set of valid image sizes for the device. The image sizes groups
		are as follows:
		    eImageSizeSetInch1: Wallet, 3x4in, 3 1/2 x 5in, 4x6in,
			5x7in, 8x10in, full page
		    eImageSizeSetInch2: Wallet, 3 1/2 x 5in, 4x6in, 5x7in,
			6x8in, 8x10in, full page
		    eImageSizeSetCentimeter1: 6x8cm, 7x10cm, 9x13cm, 10x15cm,
			13x18cm, 15x21cm, 20x25cm, full page
		    eImageSizeSetCentimeter2: 7x10cm, 9x13cm, 10x15cm, 13x18cm,
			20x25cm, full page
		eImageSizeSetCentimeter3: 6x8cm, 9x13cm, 10x15cm, 13x18cm,
		15x21cm, 18x24cm, 20x25cm, full page   .
                Additional information:
                This is only writable in service mode.  This object
                changes the set of valid image sizes for the device.  The image
                sizes groups are as follows:
                eImageSizeSetInch1:  Thumbnail, Wallet, 3x4in, 3 1/2 x 5in, 4x6in,
                5x7in, 8x10in, full page, panorama
                eImageSizeSetInch2:  Thumbnail, Wallet, 3 1/2 x 5in, 4x6in, 5x7in,
                6x8in, 8x10in, full page, panorama
                eImageSizeSetCentimeter1:  Thumbnail, 6x8cm, 7x10cm, 9x13cm, 10x15cm,
                13x18cm, 15x21cm, 20x25cm, full page, panorama
                eImageSizeSetCentimeter2:  Thumbnail, 7x10cm, 9x13cm, 10x15cm, 13x18cm,
                20x25cm, full page, panorama
                eImageSizeSetCentimeter3:  Thumbnail, 6x8cm, 9x13cm, 10x15cm, 13x18cm,
                15x21cm, 18x24cm, 20x25cm, full page, panorama"
::= { settings-photo-job 15 }


photo-clear-counts OBJECT-TYPE
    SYNTAX      INTEGER {
                          eClearPageCounts(1),
                          eClearInsertCounts(2),
                          eClearAllCounts(3)
		   }
    ACCESS      write-only
    STATUS      optional
       DESCRIPTION "writing this object causes the page counts, insert counts, or
		all photo counts to be cleared and reset to 0.
                Additional information:
                writing this object causes the page counts, insert counts, or all photo counts
                to be cleared and reset to 0."
::= { settings-photo-job 18 }


photo-compact-flash-insert-count OBJECT-TYPE
    SYNTAX      INTEGER
    ACCESS      read-write
    STATUS      optional
       DESCRIPTION "Reads or writes the count for the number of times a compact
		flash memory card has been inserted in the device. This value
		is saved over a power cycle.
                Additional information:
                reads or writes the count for the number of times a compact flash memory card
                has been inserted in the device.  This value is saved over a power cycle."
::= { settings-photo-job 19 }


photo-memory-stick-insert-count OBJECT-TYPE
    SYNTAX      INTEGER
    ACCESS      read-write
    STATUS      optional
       DESCRIPTION "Reads or writes the count for the number of times a memory
		stick memory card has been inserted in the device. This value
		is saved over a power cycle.
                Additional information:
                reads or writes the count for the number of times a memory stick memory card
                has been inserted in the device.  This value is saved over a power cycle."
::= { settings-photo-job 20 }


photo-memory-stick-pro-insert-count OBJECT-TYPE
    SYNTAX      INTEGER
    ACCESS      read-write
    STATUS      optional
       DESCRIPTION "Reads or writes the count for the number of times a memory
		stick pro memory card has been inserted in the device. This
		value is saved over a power cycle.
                Additional information:
                reads or writes the count for the number of times a memory stick pro memory card
                has been inserted in the device.  This value is saved over a power cycle."
::= { settings-photo-job 21 }


photo-smart-media-insert-count OBJECT-TYPE
    SYNTAX      INTEGER
    ACCESS      read-write
    STATUS      optional
       DESCRIPTION "Reads or writes the count for the number of times a smart media
		memory card has been inserted in the device. This value is
		saved over a power cycle.
                Additional information:
                reads or writes the count for the number of times a compact flash memory card
                has been inserted in the device.  This value is saved over a power cycle."
::= { settings-photo-job 22 }


photo-secure-digital-insert-count OBJECT-TYPE
    SYNTAX      INTEGER
    ACCESS      read-write
    STATUS      optional
       DESCRIPTION "Reads or writes the count for the number of times a secure
		digital memory card has been inserted in the device. This value
		is saved over a power cycle.
                Additional information:
                reads or writes the count for the number of times a compact flash memory card
                has been inserted in the device.  This value is saved over a power cycle."
::= { settings-photo-job 23 }


photo-mmc-insert-count OBJECT-TYPE
    SYNTAX      INTEGER
    ACCESS      read-write
    STATUS      optional
       DESCRIPTION "Reads or writes the count for the number of times a
		MultiMediaCard memory card has been inserted in the device.
		This value is saved over a power cycle.
                Additional information:
                reads or writes the count for the number of times a MultiMediaCard memory card
                has been inserted in the device.  This value is saved over a power cycle."
::= { settings-photo-job 24 }


photo-xd-insert-count OBJECT-TYPE
    SYNTAX      INTEGER
    ACCESS      read-write
    STATUS      optional
       DESCRIPTION "Reads or writes the count for the number of times an xD-Picture
		memory card has been inserted in the device. This value is
		saved over a power cycle.
                Additional information:
                reads or writes the count for the number of times an xD-Picture memory card
                has been inserted in the device.  This value is saved over a power cycle."
::= { settings-photo-job 25 }


pe-test-photocard-manufacturing-errors OBJECT-TYPE
    SYNTAX      INTEGER
    ACCESS      read-only
    STATUS      optional
       DESCRIPTION "Error status of the photocard manufacturing test.
                Additional information:
                Error status of the photocard manufacturing test."
::= { print-engine-test 90 }


pe-test-photocard-manufacturing-test-config OBJECT-TYPE
    SYNTAX      INTEGER {
                          eOff(1),
                          eOn(2)
		   }
    ACCESS      write-only
    STATUS      optional
       DESCRIPTION "Configures the device for photocard manufacturing test mode.
                Additional information:
                Configures the device for photocard manufacturing test mode."
::= { print-engine-test 91 }


pe-test-photocard-data-input OBJECT-TYPE
    SYNTAX      OCTET STRING
    ACCESS      write-only
    STATUS      optional
       DESCRIPTION "This object sets the value of the test string to be written to
		the photocard.
                Additional information:
                This object sets the value of the test string to be
                		    written to the photocard ."
::= { print-engine-test 95 }


pe-test-photocard-dir-input OBJECT-TYPE
    SYNTAX      OCTET STRING
    ACCESS      write-only
    STATUS      optional
       DESCRIPTION "This object creates or opens a directory with the string name
		on a photocard.
                Additional information:
                This object creates or opens a directory with the string
                name on a photocard."
::= { print-engine-test 96 }


pe-test-photocard-file-input OBJECT-TYPE
    SYNTAX      OCTET STRING
    ACCESS      write-only
    STATUS      optional
       DESCRIPTION "This object creates or opens a file with the string name on a
		photocard.
                Additional information:
                This object creates or opens a file with the string name on a
                photocard."
::= { print-engine-test 97 }


energy-star OBJECT-TYPE
    SYNTAX      INTEGER
    ACCESS      read-only
    STATUS      optional
       DESCRIPTION "Returns or changes the Energy Star sleep value. If the value
		is greater than zero, then the device will go into energy
		saving sleep mode after the print engine has been idle for the
		number of seconds specified by this object. A value of zero
		means Energy Star is disabled and the device will not go to
		sleep based on print engine idle time. The value must be
		non-negative.
                Additional information:
                The product will always be in
                sleep mode when not processing data.  This object will
                always return a value of 1."
::= { settings-system 1 }


sleep-mode OBJECT-TYPE
    SYNTAX      INTEGER {
                          eFalse(1),
                          eTrue(2)
		   }
    ACCESS      read-only
    STATUS      optional
       DESCRIPTION "Returns eTrue if the device is in energy saving sleep mode,
		otherwise returns eFalse. Setting SLEEP-MODE to eFalse causes
		the device to wake up, if it is in sleep mode. Setting
		SLEEP-MODE to eTrue causes the device to go into sleep mode.
                Additional information:
                The product will always be in
                sleep mode except when either processing a print job or
                in an error state."
::= { settings-system 2 }


service-password OBJECT-TYPE
    SYNTAX      INTEGER
    ACCESS      write-only
    STATUS      optional
       DESCRIPTION "When set to the password value, other service related objects
		become 'visible' (i.e readable) or become writable. When
		written with any other value, the service related objects
		become 'hidden' (i.e. are no longer readable) or are not longer
		writable. The objects that can be effected by the
		SERVICE-PASSWORD object include: SERIAL-NUMBER and
		TOTAL-ENGINE-PAGE-COUNT. The password value, and the list of
		objects effected by the SERVICE-PASSWORD being set to the
		correct value, should be documented in the device POS.
                Additional information:
                The objects that can be effected by the SERVICE-
                PASSWORD are:  SCANNER-JAM-PAGE-COUNT, SCANNER-ADF-PAGE
                -COUNT, SCAN-ADF-PAGE-COUNT, SCANNER-RETRIEVE-SCANLINE,
                SCANNER-MOTOR-CONTROL, COPIER-ADF-PAGE-COUNT, COPIER-
                PRINT-PAGE-COUNT, TOTAL-ENGINE-PAGE-COUNT, PRINT-ENGINE-
                JAM-COUNT, PRINT-ENGINE-MISPICK-COUNT, CLEAR-NVRAM"
::= { settings-system 9 }


fuser-pressure-release OBJECT-TYPE
    SYNTAX      INTEGER {
                          eDisengage(1)
		   }
    ACCESS      write-only
    STATUS      optional
       DESCRIPTION "This object is used to disengage the pressure on the fuser to
		prevent roller marks on the fuser, which can occur when the
		pressure is engaged for long periods of time.
                Additional information:
                This object is used to disengage the pressure on the
                	fuser to prevent roller marks on the fuser, which can occur when
                	the pressure is engaged for long periods of time."
::= { settings-system 53 }


device-configure-generic-language-prompt OBJECT-TYPE
    SYNTAX      INTEGER {
                          eDisabled(1),
                          eEnabled(2)
		   }
    ACCESS      read-write
    STATUS      optional
       DESCRIPTION "This object is used to determine whether to prompt the user to
		enter the appropriate language.
                Additional information:
                This object is used to determine whether to
                		     prompt the user to enter the appropriate language
                	   	     at boot."
::= { device-configure 10 }


device-configure-generic-country-prompt OBJECT-TYPE
    SYNTAX      INTEGER {
                          eDisabled(1),
                          eEnabled(2)
		   }
    ACCESS      read-write
    STATUS      optional
       DESCRIPTION " This object is used to determine whether to prompt the user to
		enter the appropriate country at boot.
                Additional information:
                This object is used to determine whether to
                	 	     prompt the user to enter the appropriate country
                	    	     at boot."
::= { device-configure 11 }


device-configure-generic-country OBJECT-TYPE
    SYNTAX      INTEGER {
                          eKorea(4),
                          eIndonesia(5),
                          eChina(6),
                          eTaiwan(7),
                          ePhilippines(8),
                          eThailand(9),
                          eSriLanka(10),
                          eBrazil(12),
                          eCanada(13),
                          eMexico(14),
                          eUnitedStates(15),
                          eArgentina(16),
                          eChile(17),
                          eNewZealand(19),
                          eIsrael(21),
                          eAustralia(23),
                          eIndia(25),
                          ePakistan(26),
                          eMalaysia(27),
                          eHongKong(29),
                          eSingapore(30),
                          eUnitedKingdom(31),
                          eAustria(34),
                          eNetherlands(35),
                          eGermany(39),
                          eDenmark(40),
                          eSweden(41),
                          eSouthAfrica(42),
                          eNorway(43),
                          eIreland(44),
                          eBelgium(45),
                          eFinland(46),
                          eFrance(47),
                          eTurkey(48),
                          eGreece(49),
                          ePortugal(50),
                          eItaly(51),
                          eSpain(55),
                          ePoland(56),
                          eBulgaria(57),
                          eCroatia(58),
                          eRomania(59),
                          eSlovakRepublic(60),
                          eCzechRepublic(61),
                          eHungary(62),
                          eRussia(64),
                          ePeru(70),
                          eJordan(78),
                          eLebanon(79),
                          eSwitzerland(82),
                          eVietnam(83),
                          eLuxemberg(85),
                          eNorthAfrica(86),
                          eBelarus(66),
                          eBrunei(33),
                          eCambodia(94),
                          eCyprus(95),
                          eEgypt(67),
                          eEstonia(54),
                          eIceland(96),
                          eLatvia(53),
                          eLiechtentstein(98),
                          eLithuania(52),
                          eMalta(99),
                          eMorocco(65),
                          eSaudiArabia(28),
                          eTunisia(32),
                          eUAE(88),
                          eUkraine(63)
		   }
    ACCESS      read-write
    STATUS      optional
       DESCRIPTION "Set the location configuration for the device. This affects
		parameters that vary per region like the default paper size,
		symbol set, supply reorder URL, and fax parameters if
		applicable."
::= { device-configure 16 }


device-configure-secure-nvram-items OBJECT-TYPE
    SYNTAX      OCTET STRING
    ACCESS      read-write
    STATUS      optional
       DESCRIPTION "This object is used to configure product settings that are
		stored in secure area of nvram. The object consists of a 16-bit
		variable in secure nvram. Bits 15-8 are product specific. Bits
		7-0 are system specific.
                Additional information:
                This object is used to configure product settings that are
                stored in secure area of nvram. The object consists of a 16-bit
                variable in secure nvram. Bits 15-8 are product specific. Bits
                7-0 are system specific."
::= { device-configure 17 }


device-configure-cpe-feature OBJECT-TYPE
    SYNTAX      OCTET STRING
    ACCESS      read-write
    STATUS      optional
       DESCRIPTION "This object allows CPE to enable specific bug fixes or
		enhancements in post-release products.
                Additional information:
                This object allows CPE to enable specific bug fixes or
                enhancements in post-release products."
::= { device-configure 18 }


device-configure-custom-product-number OBJECT-TYPE
    SYNTAX      OCTET STRING
    ACCESS      read-only
    STATUS      optional
       DESCRIPTION "This object allows manufacturing to change the product number
		to a pre-defined alternate after release. This feature will
		allow manufacturing to assign unique product numbers to custom
		product bundles when the device is unable to determine its
		product number in firmware. For example, A HP Color LaserJet
		CP1515n could be configured to display CP1516n to the customer.
		This product number must be defined prior to release.
                Additional information:
                This object allows manufacturing to change the product number
                to a pre-defined alternate after release. This feature will
                allow manufacturing to assign unique product numbers to custom
                product bundles when the device is unable to determine its
                product number in firmware. For example, A HP Color LaserJet
                CP1515n could be configured to display CP1516n to the customer.
                This product number must be defined prior to release."
::= { device-configure 19 }


device-configure-preferred-boot-localization-language OBJECT-TYPE
    SYNTAX      INTEGER {
                          eEnglish(1),
                          eFrench(2),
                          eGerman(3),
                          eSpanish(4),
                          eItalian(5),
                          eSwedish(6),
                          eDanish(7),
                          eNorwegian(8),
                          eDutch(9),
                          eFinnish(10),
                          ePortuguese(12),
                          ePolish(13),
                          eTurkish(14),
                          eTradChinese(16),
                          eSimpChinese(17),
                          eRussian(18),
                          eCzech(19),
                          eHungarian(20),
                          eKorean(21),
                          eThai(22),
                          eUnknownLanguage(44)
		   }
    ACCESS      read-write
    STATUS      optional
       DESCRIPTION "Preferred localization language used by the device at boot up
		time. Setting this object will instruct the device to boot up
		in that language. Setting this language does not impact device
		generated PML strings, control panel messages, and text
		contained in any of the printer generated printed pages. The
		order of these languages is the same order that is defined for
		LOCALIZATION-LANGUAGE.
                Additional information:
                Preferred localization language used by the device at
                boot up time.  Setting this object will instruct the device to boot
                up in that language.  This will allow the device to NOT show the
                generic prompt on the CP display, since the device already knows
                the language."
::= { device-configure 20 }


control-panel-button-press-delay OBJECT-TYPE
    SYNTAX      INTEGER
    ACCESS      read-write
    STATUS      optional
       DESCRIPTION "This object gives the number of seconds to wait before
		simulating the button press when CONTROL-PANEL-BUTTON-PRESS is
		next called.
                Additional information:
                This object gives the number of seconds to wait before
                simulating the button press when CONTROL-PANEL-BUTTON-PRESS is
                next called."
::= { settings-system 47 }


low-power OBJECT-TYPE
    SYNTAX      INTEGER
    ACCESS      read-write
    STATUS      optional
       DESCRIPTION "Returns or changes the Auto Low Power sleep value. The device
		will go into energy saving Auto Low Power mode after the print
		engine has been idle for the number of seconds specified by
		this object. Frida supports values of 300 until 14400 seconds.
		If the value is invalid then it will return status of
		PML_Status_ErrUnsupValue and will not issue command to the
		engine.
                Additional information:
                Returns or changes the Auto Low Power sleep value. The device
                will go into energy saving Auto Low Power mode after the print
                engine has been idle for the number of seconds specified by
                this object. The product supports values of 0 (Off), 60 (1
                minute), 900 (15 minutes), 1800 (30 minutes), 3600 (1 hour),
                and 7200 (2 hours).
                If the value is invalid then it will return a status of
                PML_ERROR_INVALID_OR_UNSUPPORTED_VALUE and will not issue
                a command to the engine."
::= { settings-system 49 }


control-panel-display-contrast OBJECT-TYPE
    SYNTAX      INTEGER {
                          eLightest(1),
                          eLight(2),
                          eMedium(3),
                          eDark(4),
                          eDarkest(5)
		   }
    ACCESS      read-write
    STATUS      optional
       DESCRIPTION "This object returns or sets the display contrast setting if the
		control panel has a display and it supports contrast
		adjustment. The setting Is stored in NVRAM, so the value is
		saved over power cycles.
                Additional information:
                This object returns or sets the display contrast setting
                			if the control panel has a display and it supports
                			contrast adjustment. The setting is stored in NVRAM,
                			so the value is saved over power cycles."
::= { settings-system 73 }


on-off-line OBJECT-TYPE
    SYNTAX      INTEGER {
                          eOnline(1),
                          eOffline(2)
		   }
    ACCESS      read-only
    STATUS      optional
       DESCRIPTION "To bring the PDL processing sub-system on or off line. If the
		device is a printer, then the printer does not process print
		job data when the printer is off line. PML communication
		persists.
                Additional information:
                The value of this object is eOnline
                whenever the printer is in the ready state.  This object
                will return eOffline only when an alert is active.  For
                example, the printer will go eOffline if the cover is
                open, if the toner cartridge is removed, or if the paper
                trays are all empty.  It is not possible to change the
                state of the printer with this object.  "
::= { status-system 5 }


continue OBJECT-TYPE
    SYNTAX      INTEGER {
                          eInitiateAction(1),
                          eRetry(2),
                          eRetryAndCheck(3),
                          eUseLoadedMedia(4),
                          eEjectAndWait(5),
                          eSelectMediaSize(6)
		   }
    ACCESS      write-only
    STATUS      optional
       DESCRIPTION "A device can support a class of errors called continuable
		errors. When a continuable error is encountered, the device
		requires a continue event to occur before the device will
		continue operation. One continue event is setting the CONTINUE
		object to eInitiateAction. Devices can support other continue
		events, like auto-continue. A continue event causes the
		continuable error to be acknowledged, thus allowing the device
		to continue. Each device needs to list the continuable errors.
		If the device doesn't currently have an unacknowledged
		continuable error, the response will contain
		<genErr>.
                Additional information:
                Consult the Control Panel ERS for a
                list of continuable errors."
::= { status-system 6 }


auto-continue OBJECT-TYPE
    SYNTAX      INTEGER {
                          eOff(1),
                          eOn(2)
		   }
    ACCESS      read-write
    STATUS      optional
       DESCRIPTION "Indicates if the device will automatically continue after
		encountering a continuable error. If AUTO-CONTINUE is set to
		eOn, the device will automatically generate continue event to
		acknowledge continuable errors. If AUTO-CONTINUE is set to
		eOff, then some other continue event will have to acknowledge
		the continuable error."
::= { status-system 7 }


install-date OBJECT-TYPE
    SYNTAX      OCTET STRING (SIZE(0..14))
    ACCESS      read-write
    STATUS      optional
       DESCRIPTION "Identifies the date that the device was installed. The format
		of the string is 'YYYYMMDDHHmmZ'. Where:
		    YYYY is the year.
		    MM is the month (1-12).
		    DD is the day (1-31).
		    HH is the hour of the day (0-23).
		    mm are the minutes (0-59).
		    'Z' designates Greenwich Mean Time; if 'Z' not specified,
			value is local time.
		Device POS must specify the conditions for setting this
		object.
                Additional information:
                Identifies the date that the device was installed. The
                format of the string is 'YYYYMMDDHHmmZ'. Where:
                YYYY is the year.
                MM is the month (1-12).
                DD is the day (1-31).
                HH is the hour of the day (0-23).
                mm are the minutes (0-59).
                'Z' designates Greenwich Mean Time; if 'Z' not specified,
                value is local time.

                On Products without a real-time clock this
                object has the inital value of 'INVALID'.  While in
                the invalid state the object may written to.  Once the
                initial install date has been written a new intall date
                can not be written without resetting the object to 'INVALID'.

                The behavior on products with real-time clocks is different.
                The object is set to the initial real-time clock value, usually
                this is '199000300000'.  Manufacturing sets the real-time
                clock to the correct date and sets the INSTALL-DATE to 'INVALID'.
                Then when the customer turns on the printer for the first time
                the install date is reset."
::= { status-system 8 }


ship-cartridge-installed-in-printer OBJECT-TYPE
    SYNTAX      INTEGER {
                          eFalse(1),
                          eTrue(2)
		   }
    ACCESS      read-write
    STATUS      optional
       DESCRIPTION "Set developer motor cams in the position needed for shipping
		the cartridges installed in the printer if set to eTrue.
                Additional information:
                Notifies the engine that it needs to change it's shipping state."
::= { status-system 97 }


show-address OBJECT-TYPE
    SYNTAX      INTEGER {
                          eAuto(3),
                          eOff(1)
		   }
    ACCESS      read-write
    STATUS      optional
       DESCRIPTION "If this object is set to eAuto, and the device has an IP
		address, the IP address of the device will be shown with the
		READY message. If this object is set to eOff, the IP address
		will not be shown."
::= { display-status 3 }


job-input-auto-continue-timeout OBJECT-TYPE
    SYNTAX      INTEGER
    ACCESS      read-write
    STATUS      optional
       DESCRIPTION "The number of seconds the device waits after a job related
		continuable error occurs before automatically continuing. An
		example job related continuable error is the job requesting a
		media size that is not available. After the timeout expires,
		the device will continue processing the job as if a continue
		event occurred, such as the front panel continue key being
		pressed. If the value is -1, the device does not automatically
		continue after a job related continuable error occurs. If the
		value is 0, the device immediately continues. If the value is
		greater than 0, the value represents the timeout value in
		seconds."
::= { status-system 35 }


job-input-auto-continue-mode OBJECT-TYPE
    SYNTAX      OCTET STRING
    ACCESS      read-write
    STATUS      optional
       DESCRIPTION "Returns or sets the device behavior when the desired media is
		not currently available.
		    cCancelJob - The device cancels the job. The device POS
			should explain what happens if this item is not the
			only item in the collection.
		    cAutoMediaSizeOverride - The device is allowed to
			substitute a different size media.
		    cAutoMediaNameOverride - The device is allowed to
			substitute a different media name.
		    cUSMediaSizeOverride - The device is allowed to substitute
			US media sizes (letter, etc.) for ISO media sizes (A4,
			etc.).
		    cISOMediaSizeOverride - The device is allowed to substitute
			ISO media sizes (A4, etc.) for US media sizes (letter,
			etc.).   "
::= { status-system 36 }


error-log-clear OBJECT-TYPE
    SYNTAX      INTEGER {
                          eClearErrorLog(1)
		   }
    ACCESS      write-only
    STATUS      optional
       DESCRIPTION "Setting this object clears all the entries in the error log
		sub-tree.
                Additional information:
                Setting this object removes all errors that
                have been stored in the printer's non-volatile memory."
::= { status-system 38 }


control-panel-button-press OBJECT-TYPE
    SYNTAX      INTEGER {
                          eGoButton(1),
                          eMenuPlusButton(2),
                          eMenuMinusButton(3),
                          eCancelJobButton(9),
                          eBackButton(13)
		   }
    ACCESS      write-only
    STATUS      optional
       DESCRIPTION "Writing this object simulates pressing a button on the control
		panel. Reading it will return the last key pressed either on
		the control panel or via PML. The device POS will specify which
		keys are supported.
                Additional information:
                Writing this object simulates pressing a
                		button on the control panel."
::= { status-system 60 }


device-mac-address OBJECT-TYPE
    SYNTAX      OCTET STRING
    ACCESS      read-only
    STATUS      optional
       DESCRIPTION "The device's MAC address.
                Additional information:
                The device's MAC address."
::= { status-system 120 }


extended-print-modes-modified OBJECT-TYPE
    SYNTAX      INTEGER {
                          eYes(1),
                          eNo(2)
		   }
    ACCESS      read-only
    STATUS      optional
       DESCRIPTION "This object allows the user to view whether the extended print
		modes have been modified from their default settings.
                Additional information:
                This object allows the user to view whether the extended print
                modes have been modified from their default settings."
::= { status-system 121 }


clear-nvram OBJECT-TYPE
    SYNTAX      INTEGER {
                          eClearUnprotectedNVRAM(1),
                          eClearProtectedNVRAM(2),
                          eClearCompleteNVRAM(3)
		   }
    ACCESS      write-only
    STATUS      optional
       DESCRIPTION "Writing this object causes the specified NVRAM init option to
		be performed. Depending on the option, some (or all) of the
		permanent storage area will be completely erased. This object
		is only writable when the SERVICE-PASSWORD has been set
		correctly. NOTE: This considerably more destructive than
		setting the prtGeneralReset object to ePresetToFactoryDefaults
		since it destroys page counts, serial number, and other items
		not normally affected by ePresetToFactoryDefaults.
		eClearUnprotectedNVRAM - clears unprotected NVRAM
		eClearProtectedNVRAM - clears protected NVRAM
		eClearCompleteNVRAM - clears both protected nd unprotected
		NVRAM."
::= { status-system 68 }


model-number OBJECT-TYPE
    SYNTAX      OCTET STRING
    ACCESS      read-only
    STATUS      optional
       DESCRIPTION "Identifies the device model number as listed in the HP
		corporate price list (e.g. C2121A for DeskJet 500C). The string
		is as specific as possible. Products should note in POS if the
		model number on the CPL changes but the device reports the
		previous model number. If the model number changes based on the
		installed options, the POS should indicate if only the base
		model number is returned, or if the device senses the installed
		options and returns the correct model number. If possible,
		encode the model number in a symbol set (like Roman-8) that
		matches the ASCII character set and limit the characters used
		to ASCII characters.
                Additional information:
                Identifies the device model number as listed in the HP
                corporate price list (e.g. C2121A for DeskJet 500C).
                Owl distinguishes between the three model numbers by
                the absence or presence of networking and/or a duplexor."
::= { id 1 }


model-name OBJECT-TYPE
    SYNTAX      OCTET STRING
    ACCESS      read-only
    STATUS      optional
       DESCRIPTION "Identifies the device model name (e.g. ''DeskJet 1200C''). The
		string is as specific as possible. Capitalization and spacing
		should match family naming conventions. Products should note in
		POS if the model name on the HP corporate price list changes
		but the device reports the previous device name. If the model
		name changes based on the installed options, the POS should
		indicate if only the base model name is returned, or if the
		device senses the installed options and returns the correct
		model name. If possible, encode the model name in a symbol set
		(like Roman-8) that matches the ASCII character set and limit
		the characters used to ASCII characters.
                Additional information:
                The value of this object changes based on the
                installed options.

                Since the value of this object is frequently used in
                displaying a list of printers, it is kept relatively
                short in case systems have limited width for their
                display area."
::= { id 2 }


serial-number OBJECT-TYPE
    SYNTAX      OCTET STRING (SIZE(0..10))
    ACCESS      read-write
    STATUS      optional
       DESCRIPTION "Identifies the serial number for the device. If the
		SERIAL-NUMBER object is set by the user, then setting the
		object does not need to be protected. If the SERIAL-NUMBER
		object is set at the factory, then the SERVICE-PASSWORD object
		must be set correctly before the SERIAL-NUMBER object is
		writable. If this is a writable object, the POS should indicate
		the maximum supported string length. If possible, encode the
		serial number in a symbol set (like Roman-8) that matches the
		ASCII character set and limit the characters used to ASCII
		characters.
                Additional information:
                This value is initially set to the default
                value of XXXXXXXXXX."
::= { id 3 }


fw-rom-datecode OBJECT-TYPE
    SYNTAX      OCTET STRING
    ACCESS      read-only
    STATUS      optional
       DESCRIPTION "Identifies the base system firmware date code. The date code
		will be encoded in the yyyymmdd format. There may be several
		versions of the base system firmware. The date code associated
		with the version of the base system firmware that is being used
		is reported. There may be other date code objects for other
		specific modules such as fonts, localization modules, etc.;
		these other datecode objects are device specific."
::= { id 5 }


device-name OBJECT-TYPE
    SYNTAX      OCTET STRING
    ACCESS      read-write
    STATUS      optional
       DESCRIPTION "User defined device name. The POS should indicate the maximum
		supported string length. If the user entered string is too
		long, the device will store as much as possible and will return
		the <OKNearestLegal ValueSubstituted>.Additional information:
                The maximum supported string length is 32
                characters.  If the user entered string is too long, the
                device will store the first 32 characters and will
                return the <noError> status."
::= { id 10 }


asset-number OBJECT-TYPE
    SYNTAX      OCTET STRING (SIZE(0..8))
    ACCESS      read-write
    STATUS      optional
       DESCRIPTION "User defined asset number. The POS should indicate the maximum
		supported string length. If the user entered string is too
		long, the device will store as much as possible and will return
		the <OKNearestLegal ValueSubstituted>.Additional information:
                The maximum supported string length is 8
                characters.  If the user entered string is too long, the
                device will store the first 8 characters and will return
                the <noError> status."
::= { id 12 }


simm1-type OBJECT-TYPE
    SYNTAX      INTEGER {
                          eEmpty(1),
                          eUnknown(2),
                          eUnSupported(3),
                          eReadOnlyMemory(4),
                          eVolatileRandomAccessMemory(5),
                          eRamRom(9)
		   }
    ACCESS      read-only
    STATUS      optional
       DESCRIPTION "Returns an indication of the type of option installed in SIMM
		slot 1.
		    eEmpty means the device did not detect any option installed
			in the interface slot.
		    eUnknown means the device doesn't recognize the installed
			option.
		    eUnSupported means the device recognizes the installed
			option, but does not support the option.
		    eReadOnlyMemory means the installed option contains ROM
			Ics.
		    eVolatileRandomAccessMemory means the installed option
			contains RAM ICs that loose data when the power is
			turned off.
		    eNonVolatileRandomAccessMemory means that the installed
			option contains RAM ICs that do not loose data when the
			power is turned off.
		    eFlashMemory means that the installed option contains a
			type of non-volatile RAM that needs to be erased before
			it can be written.
		    eDiskDrive means the installed option contains a disk
			drive.
		    eRamRom means the installed option contains both volatile
			random access memory and read only memory.
		    eInputPHD means the installed option is an input paper
			handling device.
		    eOutputPHD means the installed option is an output paper
			handling device. eIOCard means the installed option is
			an I/O card.
		    eVolatileRAMOnBoardMemory means the installed option
			contains on board RAM ICs that loose data when the
			power is turned off.
                Additional information:
                This object is used to describe DIMMs
                instead of SIMMs on the product.  eRamRom is
                used to denote a combo dimm."
::= { simm1 4 }


simm1-capacity OBJECT-TYPE
    SYNTAX      INTEGER
    ACCESS      read-only
    STATUS      optional
       DESCRIPTION "Returns an indication of the capacity of the SIMM installed in
		SIMM slot 1. The capacity is dependent on the type of option,
		as indicated by the SIMM1-TYPE object. This object has no
		meaning if the installed option type is eUnknown or
		eReadOnlyMemory. This object contains the size, in bytes, if
		the installed option type is eVolatileRandomAccessMemory,
		eNonVolatileRandomAccessMemory, eFlashMemory, or eDiskDrive. If
		the type of the installed option is eRamRom, this object
		contains the size, in bytes, of the random access memory. If
		the type of the installed option is eInputPHD, the capacity
		indicates the number of input trays supported by the installed
		option. If the type of the installed option is eOutputPHD, the
		capacity indicates the number of output bins supported by the
		installed option. If the type of the installed option is
		eIOCard, the capacity indicates the number of logical I/O ports
		supported by the I/O card.
                Additional information:
                Returns an indication of the capacity of
                the installed option in bytes.  This object is not
                supported unless the SIMM1-TYPE type is
                eVolatileRandomAccessMemory or eRamRom.  For eRamRom
                only the size of the Ram portion of the simm (dimm) is
                returned."
::= { simm1 5 }


usb-product-id OBJECT-TYPE
    SYNTAX      INTEGER
    ACCESS      read-only
    STATUS      optional
       DESCRIPTION "Returns the Product ID of a connected USB device as defined in
		the Standard Device Descriptor of the Universal Serial Bus
		Specification Version 2.0. The value will be in the range
		0..65535."
::= { usb 5 }


self-test OBJECT-TYPE
    SYNTAX      INTEGER {
                          eNotInASelfTest(1),
                          eNonDestructiveSelfTest(4)
		   }
    ACCESS      read-write
    STATUS      optional
       DESCRIPTION "Writing this object allows a device self test to be started.
		Reading this object provides an indication what self-test is
		currently executing, if any. Actual self-test operation is
		device specific. A self test may not be allowed at any
		arbitrary time. If the device supports the requested self test,
		but can not start the execution of the self test when
		requested, the device will respond with
		<genErr>. If a non-destructive self
		test is being started, the device will generate a response
		before the self test is completed. RECOMMENDATION: If the
		device is ready (i.e. the NOT-READY-PRINTER object does not
		contain any items, except maybe being off-line) and is idle
		(i.e. the NOT-IDLE object does not contain any items), this
		request should always succeed. This provides a mechanism for
		driver writers to always determine if the action will succeed
		or not.
                Additional information:
                The eNonDestructiveSelfTest performs
                limited testing on the printer and its attached paper
                handling devices.  After the self-test is complete a
                configuration page is printed.  The recommended way to
                cause a configuration page to be printed is to use the
                PRINT-INTERNAL-PAGE object.  A continuous self test
                cannot be started or terminated using this OID.

                When the printer is idle, setting this object to
                eNonDestructiveSelfTest results in a status of <noError> and
                a value of eNonDestructiveSelfTest being returned.  If
                the printer is not idle (whether printing an external
                job, printing an internal page or running self test), a
                status of <genErr> status will
                be returned with a value of eNotInASelfTest.

                When the printer is idle, setting this object to
                eNonDestructiveSelfTest causes the configuration page to
                be formatted and put in the printer's print queue.

                Attempting to set this object before the configuration
                page has completed being formatted and printed will
                cause <genErr> status to be
                returned with a value of eNotInASelfTest.

                After the configuration page is in the queue, a get on
                this object will return a value of eNotInASelfTest.

                Setting the value to eNotInASelfTest is not supported on
                the product.  Once the test has started, it
                will finish printing.

                Likewise, if the PRINT-INTERNAL-PAGE object is set to a
                valid value and that page has not printed when this
                object is set to eNonDestructiveSelfTest, a status of
                <genErr> status with a value of
                eNotInASelfTest will be returned until the internal page
                has printed."
::= { test 1 }


print-internal-page OBJECT-TYPE
    SYNTAX      INTEGER {
                          eNotPrintingAnInternalPage(1),
                          ePrintingAnUnknownInternalPage(2),
                          eDeviceDemoPage1ConfigurationPage(3),
                          eDeviceDemoPage2(4),
                          eDeviceDemoPage7MenuMap(9),
                          eServicePage(13),
                          eSuppliesPage(101),
                          eDeviceCleaningPage(253),
                          ePCLFontList1(350),
                          ePCLXLFontList1(353),
                          ePostScriptFontList1(450),
                          eNetworkConfigPage(1200),
                          ePrintQualityDiagnosticPage(1409),
                          eColorUsageLog(1412)
		   }
    ACCESS      read-write
    STATUS      optional
       DESCRIPTION "Writing this object to a value other than
		eNotPrintingAnInternalPage causes the device to attempt to
		print an internally generated page. Reading this object
		provides an indication what internally generated page is
		currently being printed, if any. The actual page is device
		specific. Some devices may support continuously printing an
		internally generated page. Setting this object to
		eNotPrintingAnInternalPage terminates continuously printing
		internally generated pages. An internally generated page may
		not be allowed to be printed at any arbitrary time; under what
		conditions it will succeed or fail is device specific. If the
		device supports the requested page, but can not start printing
		the page when requested, the device will respond with
		<genErr>. RECOMMENDATION: If the
		device is ready (i.e. the NOT-READY-PRINTER object does not
		contain any items, except maybe being off-line) and is idle
		(i.e. the NOT-IDLE object does not contain any items), this
		request should always succeed. This provides a mechanism for
		driver writers to always determine if the action will succeed
		or not.
                Additional information:
                eDeviceDemoPage2 is the printer demo page.
                ePCLFontList1 is the PCL typeface list,
                ePostScriptFontList1 is the PostScript font list, and
                eDeviceDemoPage1ConfigurationPage is the selftest page.

                The product does not support continuously
                printing a demo page.

                The printer will queue requests if it is currently busy.

                When this object is set to a valid value and the printer
                is idle, the status returned is <noError> and the value
                returned is ePrintingAnUnknownInternalPage.

                Setting this object to a valid value causes the desired
                page to be formatted and put in the printer's print
                queue.  While the page is being formatted, and the
                printer remains in a testing state, a get on this object
                will return the value ePrintingAnUnknownInternalPage.
                The return value will be eNotPrintingAnInternal page if
                the printer is not in a testing state, and the internal
                page is done being formatted.

                The user will not be able to set
                eNotPrintingAnInternalPage or
                ePrintingAnUnknownInternalPage, and the return status
                will be <badValue> with a return
                value of eNotPrintingAnInternalPage.

                ePostScriptFontList1 and ePCLFontList1 will not be
                		valid values unless postscript and PCL, respectively,
                		are installed in the printer.  If postscript (PCL)
                is not installed and the user attempts to set
                ePostScriptFontList1 (ePCLFontList1), the return status
                		will be <badValue> with a return
                		value of eNotPrintingAnInternalPage.

                Setting through DMCMD will cause a 15 second delay in
                printing."
::= { test 2 }


job-info-change-id OBJECT-TYPE
    SYNTAX      OCTET STRING (SIZE(16))
    ACCESS      read-only
    STATUS      optional
       DESCRIPTION "Returns the current value of an object in the job-info sub-tree
		whose value has changed. Define the object identifier for the
		object whose value has changed as
		job-info.required-field.optional-field.job-id. job-info
		represents the OID prefix of all objects in the job-info
		sub-tree. Required-field represents the OID field value that
		follows the job-info prefix. Since some objects in the job-info
		sub-tree have two OID fields between the job-info prefix and
		the job-id, the optional-field represents the OID field between
		the required-field and the job-id field, if present. Using this
		definition, the format for the JOB-INFO-CHANGE-ID binary value
		can be described as follows:
		    Bytes 0-3 : required-field
		    Bytes 4-7 : optional-field, or all zeros if there
		    is no optional field
		    Bytes 8-11: Job ID.
		    Bytes 12-n : The value of the object job-info.
			required-field.optional-field.job-id.
		All multi-byte values stored in Motorola (big-endian) format,
		where the most significant byte occurs first.
                Additional information:
                The product will use this object
                to report changes of the job-info-pages-printed and
                job-info-state objects.  The required-field (bytes 0
                through 3) will designate whether the change to be
                reported involves the pages printed (13) or job state
                (15).  The optional-field (bytes 4 through 7) will
                always be zeroes.  The value-field (bytes 12 through 15)
                will contain the new value for pages printed or job
                state cast to a 32-bit integer."
::= { settings-job 3 }


current-job-parsing-id OBJECT-TYPE
    SYNTAX      INTEGER(-1..32767)
    ACCESS      read-only
    STATUS      optional
       DESCRIPTION "Contains the printer assigned job identification for the job
		currently being processed by the processing PDL sub-system. The
		job ID is a monotonically increasing number. The job ID may be
		reset to zero at power-up and may roll over to zero after
		reaching some maximum value.
                Additional information:
                A value of -1 is returned when the printer
                is not parsing a job.

                When data for a new job is detected, this object is
                updated (the job may or may not turn out to be a Null
                Job).  (A job is considered to be a 'null job' if it has
                no name or job attribute, causes no pages to be printed,
                and consumes MIN_JOB_SIZE (9) or fewer bytes.)  See the
                Job Boundary ERS for details on what constitutes a job
                boundary.

                Some job-info- objects are created when the first data
                bytes are received.  If the printer determines that the
                job is a Null Job, the job-info- objects related to the
                Null Job are deleted.  The product retains
                the job-info- objects for the MAX_JOBS_IN_LIST (12) most
                recent jobs that are not Null Jobs.

                The first job received after power-up will have job ID 1,
                and the job ID will increment to 32767 before rolling
                to zero.  To distinguish whether a power cycle or a
                rollover causes a reduction in the job ID value, the
                object prtGeneralConfigChanges can be watched and if it
                increments at the same time as the drop is observed in
                the value of CURRENT-JOB-PARSING-ID, then a power cycle
                is the most likely cause."
::= { job-being-parsed 1 }


job-info-name1 OBJECT-TYPE
    SYNTAX      OCTET STRING
    ACCESS      read-only
    STATUS      optional
       DESCRIPTION "Contains the first part of this print job's name. The last OID
		field for this dynamic object contains the job ID.
                Additional information:
                The job name is the string specified by the
                NAME= parameter of the @PJL JOB command which allows a
                maximum of 80 characters.  The first 40 characters are
                in this object and the second 40 are in job-info-name2.
                The symbol set is Roman-8.

                When jobs are nested, the value assigned to this object
                is the name provided by the most recent @PJL JOB NAME=
                command.  If no name is provided, a null string is
                returned."
::= { job-info 1 }


job-info-name2 OBJECT-TYPE
    SYNTAX      OCTET STRING
    ACCESS      read-only
    STATUS      optional
       DESCRIPTION "Contains the second part of this print job's name. The last OID
		field for this dynamic object contains the job ID.
                Additional information:
                See job-info-name1-1."
::= { job-info 2 }


job-info-stage OBJECT-TYPE
    SYNTAX      OCTET STRING
    ACCESS      read-only
    STATUS      optional
       DESCRIPTION "Indicates what printer sub-systems are currently processing
		this print job. The last OID field for this dynamic object
		contains the job ID. cSourceSubsystem - some of the job is in
		the printer I/O subsystem. cProcessingSubsystem - some of the
		job is in the printer imaging processing subsystem.
		cDestinationSubsystem - some of the job is being printed.
                Additional information:
                For the product, cSourceSubsystem
                and cProcessingSubsystem will always be set and cleared
                together.  They are set when the beginning of the job is
                detected, and they are cleared when the end of the job
                is parsed.

                A non-printing job will never set
                cDestinationSubsystem.

                When a page is ready to be printed (the intermediate has
                been built and the page is 'closed' by the personality),
                cDestinationSubsystem will be set even if a page of a
                previous job is currently being printed.
                cDestinationSubsystem remains set until the last page of
                the job has finished printing.

                If a page requires extensive processing and allows all
                the previous pages of a job to complete printing
                cDestinationSubsystem will remain set until the last
                page of the job has finished printing."
::= { job-info 10 }


job-info-io-source OBJECT-TYPE
    SYNTAX      INTEGER
    ACCESS      read-only
    STATUS      optional
       DESCRIPTION "Indicates which I/O source, the print job was received over.
		The value maps to port numbering scheme supported in the
		DEVICE/SOURCE-SUBSYSTEM/IO/PORTS sub-tree.
                Additional information:
                The product does not
                support the DEVICE/SOURCE-SUBSYSTEM/IO/PORTS sub-tree."
::= { job-info 11 }


job-info-pages-processed OBJECT-TYPE
    SYNTAX      INTEGER
    ACCESS      read-only
    STATUS      optional
       DESCRIPTION "Indicates the number of pages processed by the processing
		subsystem. If neither the cSourceSubsystem or the
		cProcessingSubsystem items are in the associated JOB-INFO-STAGE
		object, then this object contains the total number of pages
		processed for this job. The last OID field for this dynamic
		object contains the job ID.
                Additional information:
                This object is incremented by one when a
                page is processed ('closed' by the personality),
                regardless of the number of pages that are printed as a
                result of the single page processed.  In other words, it
                does not matter how many identical copies of a page are
                printed, or no pages may be printed if operating in
                silent run mode, this count is incremented exactly once
                per page processed.

                A page is considered processed when all of the input
                data has been processed for a page (that is, when the
                intermediate has been produced and the personality has
                'closed' the page).  At this time, the image of the page
                is not necessarily completely formed."
::= { job-info 12 }


job-info-pages-printed OBJECT-TYPE
    SYNTAX      INTEGER
    ACCESS      read-only
    STATUS      optional
       DESCRIPTION "Indicates the number of pages printed by the destination
		subsystem. If none of the cSourceSubsystem,
		cProcessingSubsystem or cDestinationSubsystem items are in the
		associated JOB-INFO-STAGE object, then this object contains the
		total number of pages printed for this job. This value may
		increase by two each time for duplex jobs. The last OID field
		for this dynamic object contains the job ID.
                Additional information:
                If multiple copies of a page are printed,
                each copy is counted individually."
::= { job-info 13 }


job-info-size OBJECT-TYPE
    SYNTAX      INTEGER
    ACCESS      read-only
    STATUS      optional
       DESCRIPTION "Indicates the number of bytes of data processed by the
		processing subsystem. If neither of the cSourceSubsystem or
		cProcessingSubsystem items are in the associated JOB-INFO-STAGE
		object, then this object contains the size of this job, in
		bytes. The last OID field for this dynamic object contains the
		job ID.
                Additional information:
                This count may be incremented by values
                other than one as blocks of data are processed; blocks
                of data (which may be as large as 2K bytes) will be
                processed in a varying amount of time.

                During the processing of a job and even when a job
                completes, an exact count of the number of I/O bytes
                processed by teh job is not necessarily expected."
::= { job-info 14 }


job-info-state OBJECT-TYPE
    SYNTAX      INTEGER {
                          eAborted(3),
                          eWaitingForResources(4),
                          ePrinted(5),
                          eTerminating(7),
                          eCancelled(10),
                          eProcessing(11)
		   }
    ACCESS      read-only
    STATUS      optional
       DESCRIPTION "Indicates the state of the job. The last OID field for this
		dynamic object contains the job ID.
		    eAborted - the print job was aborted.
		    eWaitingForResources - the print job requires resources
			that are not currently available. Example resources
			that can cause the job to wait include the print engine
			or PDL processor being unavailable. The print engine
			could be unavailable due to paper out, paper jam,
			staple out, stapler jam, marking agent low, output bin
			full, etc. The PDL processor could be unavailable due
			to an off-line condition. Each printer specific object
			specification should state which conditions cause a job
			to be waiting for resources and also state which
			objects can be retrieved by an application to determine
			the exact cause of a resource being unavailable.
		    ePrinted - the job has printed. The related JOB-INFO-
			OUTCOME object indicates if any problems were
			encountered while the job was processed.
		    eRetained - the job can be reprinted.
		    eTerminating - the job was aborted or cancelled and is
			currently is terminating.
		    eInterrupted - the job has been interrupted. The job can be
			continued.
		    ePaused - the job has been paused. The job can be
			continuted.
		    eCancelled - the job has been cancelled.
		eProcessing - the job is currently being printed normally.
		eStored - The job is stored on the device and can be retrieved
		and printed at a later point in time."
::= { job-info 15 }


job-info-outcome OBJECT-TYPE
    SYNTAX      INTEGER {
                          eOk(3)
		   }
    ACCESS      read-only
    STATUS      optional
       DESCRIPTION "Indicates if any warning or error conditions were encountered
		while processing the assoicated job. The last OID field for
		this dynamic object contains the job ID.
                Additional information:
                In the product, warnings
                and errors are not recorded in this object.  Although no
                meaningful information can be obtained from this object,
                it is kept around for the compatibility needs of
                existing software."
::= { job-info 19 }


job-info-outbins-used OBJECT-TYPE
    SYNTAX      OCTET STRING
    ACCESS      read-only
    STATUS      optional
       DESCRIPTION "Indicates which output bins this job has delivered printed
		pages to. The last OID field for this dynamic object contains
		the job ID.
                Additional information:
                The product has only 1 output bin.
                cOutbin1 is the top/face-down bin."
::= { job-info 20 }


job-info-physical-outbins-used OBJECT-TYPE
    SYNTAX      OCTET STRING
    ACCESS      read-only
    STATUS      optional
       DESCRIPTION "Indicates which physical output bins this job has delivered
		printed pages to. The last OID field for this dynamic object
		contains the job ID.
                Additional information:
                The product only has one output
                bin so this will always be set to cOutbin1.
                cOutbin1--Face-up bin"
::= { job-info 22 }


job-info-attr-1 OBJECT-TYPE
    SYNTAX      OCTET STRING (SIZE(1..80))
    ACCESS      read-only
    STATUS      optional
       DESCRIPTION "Returns the value that was set in PJL via the SET JOBATTR=
		command. Attribute objects are saved sequentially, starting
		with 1, after the start of a job. If more attributes are set
		than there are objects to store them, the excess JOBATTR values
		are ignored. If the corresponding SET JOBATTR= command has not
		been received when a get is done for this object, a status of
		<noSuchName> will be returned."
::= { job-info-attribute 1 }


job-info-attr-2 OBJECT-TYPE
    SYNTAX      OCTET STRING (SIZE(1..80))
    ACCESS      read-only
    STATUS      optional
       DESCRIPTION "Returns the value that was set in PJL via the SET JOBATTR=
		command. See JOB-INFO-ATTR-1 for details."
::= { job-info-attribute 2 }


job-info-attr-3 OBJECT-TYPE
    SYNTAX      OCTET STRING (SIZE(1..80))
    ACCESS      read-only
    STATUS      optional
       DESCRIPTION "Returns the value that was set in PJL via the SET JOBATTR=
		command. See JOB-INFO-ATTR-1 for details."
::= { job-info-attribute 3 }


job-info-attr-4 OBJECT-TYPE
    SYNTAX      OCTET STRING (SIZE(1..80))
    ACCESS      read-only
    STATUS      optional
       DESCRIPTION "Returns the value that was set in PJL via the SET JOBATTR=
		command. See JOB-INFO-ATTR-1 for details."
::= { job-info-attribute 4 }


job-info-attr-5 OBJECT-TYPE
    SYNTAX      OCTET STRING (SIZE(1..80))
    ACCESS      read-only
    STATUS      optional
       DESCRIPTION "Returns the value that was set in PJL via the SET JOBATTR=
		command. See JOB-INFO-ATTR-1 for details."
::= { job-info-attribute 5 }


job-info-attr-6 OBJECT-TYPE
    SYNTAX      OCTET STRING (SIZE(1..80))
    ACCESS      read-only
    STATUS      optional
       DESCRIPTION "Returns the value that was set in PJL via the SET JOBATTR=
		command. See JOB-INFO-ATTR-1 for details."
::= { job-info-attribute 6 }


job-info-attr-7 OBJECT-TYPE
    SYNTAX      OCTET STRING (SIZE(1..80))
    ACCESS      read-only
    STATUS      optional
       DESCRIPTION "Returns the value that was set in PJL via the SET JOBATTR=
		command. See JOB-INFO-ATTR-1 for details."
::= { job-info-attribute 7 }


job-info-attr-8 OBJECT-TYPE
    SYNTAX      OCTET STRING (SIZE(1..80))
    ACCESS      read-only
    STATUS      optional
       DESCRIPTION "Returns the value that was set in PJL via the SET JOBATTR=
		command. See JOB-INFO-ATTR-1 for details."
::= { job-info-attribute 8 }


job-info-attr-9 OBJECT-TYPE
    SYNTAX      OCTET STRING (SIZE(1..80))
    ACCESS      read-only
    STATUS      optional
       DESCRIPTION "Returns the value that was set in PJL via the SET JOBATTR=
		command. See JOB-INFO-ATTR-1 for details."
::= { job-info-attribute 9 }


job-info-attr-10 OBJECT-TYPE
    SYNTAX      OCTET STRING (SIZE(1..80))
    ACCESS      read-only
    STATUS      optional
       DESCRIPTION "Returns the value that was set in PJL via the SET JOBATTR=
		command. See JOB-INFO-ATTR-1 for details."
::= { job-info-attribute 10 }


job-info-attr-11 OBJECT-TYPE
    SYNTAX      OCTET STRING (SIZE(1..80))
    ACCESS      read-only
    STATUS      optional
       DESCRIPTION "Returns the value that was set in PJL via the SET JOBATTR=
		command. See JOB-INFO-ATTR-1 for details."
::= { job-info-attribute 11 }


job-info-attr-12 OBJECT-TYPE
    SYNTAX      OCTET STRING (SIZE(1..80))
    ACCESS      read-only
    STATUS      optional
       DESCRIPTION "Returns the value that was set in PJL via the SET JOBATTR=
		command. See JOB-INFO-ATTR-1 for details."
::= { job-info-attribute 12 }


job-info-attr-13 OBJECT-TYPE
    SYNTAX      OCTET STRING (SIZE(1..80))
    ACCESS      read-only
    STATUS      optional
       DESCRIPTION "Returns the value that was set in PJL via the SET JOBATTR=
		command. See JOB-INFO-ATTR-1 for details."
::= { job-info-attribute 13 }


job-info-attr-14 OBJECT-TYPE
    SYNTAX      OCTET STRING (SIZE(1..80))
    ACCESS      read-only
    STATUS      optional
       DESCRIPTION "Returns the value that was set in PJL via the SET JOBATTR=
		command. See JOB-INFO-ATTR-1 for details."
::= { job-info-attribute 14 }


job-info-attr-15 OBJECT-TYPE
    SYNTAX      OCTET STRING (SIZE(1..80))
    ACCESS      read-only
    STATUS      optional
       DESCRIPTION "Returns the value that was set in PJL via the SET JOBATTR=
		command. See JOB-INFO-ATTR-1 for details."
::= { job-info-attribute 15 }


job-info-attr-16 OBJECT-TYPE
    SYNTAX      OCTET STRING (SIZE(1..80))
    ACCESS      read-only
    STATUS      optional
       DESCRIPTION "Returns the value that was set in PJL via the SET JOBATTR=
		command. See JOB-INFO-ATTR-1 for details."
::= { job-info-attribute 16 }


error1-time-stamp OBJECT-TYPE
    SYNTAX      INTEGER
    ACCESS      read-only
    STATUS      optional
       DESCRIPTION "Contains some sort of time stamp indicating when error 1
		occurred. Example time stamps include the actual time the error
		occurred (in seconds since Jan. 1, 1970), and the total engine
		page count. The device POS documents the meaning of the time
		stamp.
                Additional information:
                This item contains the engine page count
                when the error occurred.

                If there is currently no error entry for this object, a
                '0' will be returned.  If ERROR1-CODE object also
                returns '0', then an error has not yet been logged for
                this object

                See ERROR1-CODE for an explanation of the order used for
                storing errors."
::= { error1 1 }


error1-code OBJECT-TYPE
    SYNTAX      INTEGER
    ACCESS      read-only
    STATUS      optional
       DESCRIPTION "Contains a device specific error code. Each device POS should
		list what errors are logged to the error log and the meaning of
		each supported error code value.
                Additional information:
                Returns a device specific error code.  If
                the error code returned is '0', then the printer has not
                yet logged an error for this object.  When the maximum
                number of errors is reached (10 on the
                		product), and a new error occurs, the error in
                ERROR1-CODE will be replaced by the one in ERROR2-CODE,
                and so on until the last error object will be given the
                value of the new error.

                The error category is returned in the upper 16 bits,
                either 79 (for service) or 0 (for support).  The lower
                16 bits encodes the specific error.  If an error is not
                a 79 service error, the value of this object is the PJL
                USTATUS code.  If it is a 79 service error, the lower 16
                bits contain the PJL USTATUS code.

                The types of errors reported for the product are:
                49 Service Error
                50-67  Service Error
                69 Service Error
                70-72 Service Error
                79 Service Errors
                		  Access Error
                		  Address Error
                		  ASIC fault
                		  Asserts
                		  Bad Beam Detect
                		  Bad E-Label
                		  Bad Fan
                		  Bad Fuser
                		  Bad Malfunction
                		  Bad MIO
                		  Bad Scanner Motor
                		  Data Communication Error
                		  Engine Communication Error
                		  Format Error
                		  Genunine HP Supply Installed
                		  Illegal Instruction
                		  Insufficient Memory
                		  Invalid Personality
                		  Laser Malfunction
                		  MIO Buffer Overflow
                		  MIO Connection Break
                		  Missing E-Label
                		  Non-HP Supply Detected
                		  NVRAM Error
                		  NVRAM Service Error
                		  Parallel Buffer Overflow
                		  Print Page Punt
                		  Priviledge Violation
                		  Trace Fault
                		  Unimplemented Line-a Opcode
                		  Unimplemented Line-f Opcode
                		  Uninitialized Interrupt"
::= { error1 2 }


error2-time-stamp OBJECT-TYPE
    SYNTAX      INTEGER
    ACCESS      read-only
    STATUS      optional
       DESCRIPTION "Contains some sort of time stamp indicating when error 2
		occurred. Example time stamps include the actual time the error
		occurred (in seconds since Jan. 1, 1970), and the total engine
		page count. The device POS documents the meaning of the time
		stamp.
                Additional information:
                See ERROR1-TIME-STAMP."
::= { error2 1 }


error2-code OBJECT-TYPE
    SYNTAX      INTEGER
    ACCESS      read-only
    STATUS      optional
       DESCRIPTION "Contains a device specific error code. Each device POS should
		list what errors are logged to the error log and the meaning of
		each supported error code value.
                Additional information:
                See ERROR1-CODE."
::= { error2 2 }


error3-time-stamp OBJECT-TYPE
    SYNTAX      INTEGER
    ACCESS      read-only
    STATUS      optional
       DESCRIPTION "Contains some sort of time stamp indicating when error 3
		occurred. Example time stamps include the actual time the error
		occurred (in seconds since Jan. 1, 1970), and the total engine
		page count. The device POS documents the meaning of the time
		stamp.
                Additional information:
                See ERROR1-TIME-STAMP."
::= { error3 1 }


error3-code OBJECT-TYPE
    SYNTAX      INTEGER
    ACCESS      read-only
    STATUS      optional
       DESCRIPTION "Contains a device specific error code. Each device POS should
		list what errors are logged to the error log and the meaning of
		each supported error code value.
                Additional information:
                See ERROR1-CODE."
::= { error3 2 }


error4-time-stamp OBJECT-TYPE
    SYNTAX      INTEGER
    ACCESS      read-only
    STATUS      optional
       DESCRIPTION "Contains some sort of time stamp indicating when error 4
		occurred. Example time stamps include the actual time the error
		occurred (in seconds since Jan. 1, 1970), and the total engine
		page count. The device POS documents the meaning of the time
		stamp.
                Additional information:
                See ERROR1-TIME-STAMP."
::= { error4 1 }


error4-code OBJECT-TYPE
    SYNTAX      INTEGER
    ACCESS      read-only
    STATUS      optional
       DESCRIPTION "Contains a device specific error code. Each device POS should
		list what errors are logged to the error log and the meaning of
		each supported error code value.
                Additional information:
                See ERROR1-CODE."
::= { error4 2 }


error5-time-stamp OBJECT-TYPE
    SYNTAX      INTEGER
    ACCESS      read-only
    STATUS      optional
       DESCRIPTION "Contains some sort of time stamp indicating when error 5
		occurred. Example time stamps include the actual time the error
		occurred (in seconds since Jan. 1, 1970), and the total engine
		page count. The device POS documents the meaning of the time
		stamp.
                Additional information:
                See ERROR1-TIME-STAMP."
::= { error5 1 }


error5-code OBJECT-TYPE
    SYNTAX      INTEGER
    ACCESS      read-only
    STATUS      optional
       DESCRIPTION "Contains a device specific error code. Each device POS should
		list what errors are logged to the error log and the meaning of
		each supported error code value.
                Additional information:
                See ERROR1-CODE."
::= { error5 2 }


error6-time-stamp OBJECT-TYPE
    SYNTAX      INTEGER
    ACCESS      read-only
    STATUS      optional
       DESCRIPTION "Contains some sort of time stamp indicating when error 6
		occurred. Example time stamps include the actual time the error
		occurred (in seconds since Jan. 1, 1970), and the total engine
		page count. The device POS documents the meaning of the time
		stamp.
                Additional information:
                See ERROR1-TIME-STAMP."
::= { error6 1 }


error6-code OBJECT-TYPE
    SYNTAX      INTEGER
    ACCESS      read-only
    STATUS      optional
       DESCRIPTION "Contains a device specific error code. Each device POS should
		list what errors are logged to the error log and the meaning of
		each supported error code value.
                Additional information:
                See ERROR1-CODE."
::= { error6 2 }


error7-time-stamp OBJECT-TYPE
    SYNTAX      INTEGER
    ACCESS      read-only
    STATUS      optional
       DESCRIPTION "Contains some sort of time stamp indicating when error 7
		occurred. Example time stamps include the actual time the error
		occurred (in seconds since Jan. 1, 1970), and the total engine
		page count. The device POS documents the meaning of the time
		stamp.
                Additional information:
                See ERROR1-TIME-STAMP."
::= { error7 1 }


error7-code OBJECT-TYPE
    SYNTAX      INTEGER
    ACCESS      read-only
    STATUS      optional
       DESCRIPTION "Contains a device specific error code. Each device POS should
		list what errors are logged to the error log and the meaning of
		each supported error code value.
                Additional information:
                See ERROR1-CODE."
::= { error7 2 }


error8-time-stamp OBJECT-TYPE
    SYNTAX      INTEGER
    ACCESS      read-only
    STATUS      optional
       DESCRIPTION "Contains some sort of time stamp indicating when error 8
		occurred. Example time stamps include the actual time the error
		occurred (in seconds since Jan. 1, 1970), and the total engine
		page count. The device POS documents the meaning of the time
		stamp.
                Additional information:
                See ERROR1-TIME-STAMP."
::= { error8 1 }


error8-code OBJECT-TYPE
    SYNTAX      INTEGER
    ACCESS      read-only
    STATUS      optional
       DESCRIPTION "Contains a device specific error code. Each device POS should
		list what errors are logged to the error log and the meaning of
		each supported error code value.
                Additional information:
                See ERROR1-CODE."
::= { error8 2 }


error9-time-stamp OBJECT-TYPE
    SYNTAX      INTEGER
    ACCESS      read-only
    STATUS      optional
       DESCRIPTION "Contains some sort of time stamp indicating when error 9
		occurred. Example time stamps include the actual time the error
		occurred (in seconds since Jan. 1, 1970), and the total engine
		page count. The device POS documents the meaning of the time
		stamp.
                Additional information:
                See ERROR1-TIME-STAMP."
::= { error9 1 }


error9-code OBJECT-TYPE
    SYNTAX      INTEGER
    ACCESS      read-only
    STATUS      optional
       DESCRIPTION "Contains a device specific error code. Each device POS should
		list what errors are logged to the error log and the meaning of
		each supported error code value.
                Additional information:
                See ERROR1-CODE."
::= { error9 2 }


error10-time-stamp OBJECT-TYPE
    SYNTAX      INTEGER
    ACCESS      read-only
    STATUS      optional
       DESCRIPTION "Contains some sort of time stamp indicating when error 10
		occurred. Example time stamps include the actual time the error
		occurred (in seconds since Jan. 1, 1970), and the total engine
		page count. The device POS documents the meaning of the time
		stamp.
                Additional information:
                See ERROR1-TIME-STAMP."
::= { error10 1 }


error10-code OBJECT-TYPE
    SYNTAX      INTEGER
    ACCESS      read-only
    STATUS      optional
       DESCRIPTION "Contains a device specific error code. Each device POS should
		list what errors are logged to the error log and the meaning of
		each supported error code value.
                Additional information:
                See ERROR1-CODE."
::= { error10 2 }


firmware-download-name OBJECT-TYPE
    SYNTAX      OCTET STRING
    ACCESS      read-only
    STATUS      optional
       DESCRIPTION "This returns the name of the printer. This should match the
		name in the header of the upgrade image being sent to the flash
		part. If the name does not match with the name returned then
		the image that we are attempting to download does not upgrade
		the printer firmware.
                Additional information:
                This object returns the HP name of the printer.
                		This should match what is in the PJL header of the RFU job
                		Web Jet Admin uses this to ensure the printer is available
                		to be upgraded."
::= { firmware-download 6 }


firmware-download-version OBJECT-TYPE
    SYNTAX      OCTET STRING
    ACCESS      read-only
    STATUS      optional
       DESCRIPTION "This object will return a string value representing the current
		revision of firmware that the printer is operating with. This
		is used to determine if code needs to be upgraded when an
		firmware bundle comes in, in an upgrade job.
                Additional information:
                This object will return a string value representing the current
                revision of firmware that the printer is operating with. This
                is used to determine if code needs to be upgraded when an
                firmware bundle comes in, in an upgrade job."
::= { firmware-download 7 }


io-timeout OBJECT-TYPE
    SYNTAX      INTEGER(5..7200)
    ACCESS      read-write
    STATUS      optional
       DESCRIPTION "The amount of time, in seconds, to wait for more print job data
		to be received before an I/O timeout occurs. The I/O channel
		being timed is the I/O channel that received the data
		associated with the current print job. If an I/O timeout
		occurs, the PDL processing sub-system assumes all the data
		associated with the current print job has been received, and
		processes the end of job in a PDL specific manner. The POS
		specifies the supported values.
                Additional information:
                If an I/O timeout occurs,the PDL processing
                sub-system will consider it an end of job condition only
                if there is data from another I/O subsystem waiting to be
                processed.
                The supported values are 5 to 7200 seconds.  Setting to a
                value outside the supported range returns
                <badValue> status."
::= { settings-io 1 }


io-switch OBJECT-TYPE
    SYNTAX      INTEGER {
                          eYes(1)
		   }
    ACCESS      read-only
    STATUS      optional
       DESCRIPTION "Indicates if the device will switch between I/O channels when a
		job boundary is encountered and print job data is available on
		another I/O channel."
::= { settings-io 2 }


default-copies OBJECT-TYPE
    SYNTAX      INTEGER(1..999)
    ACCESS      read-write
    STATUS      optional
       DESCRIPTION "Returns or changes default copies. Default copies is the
		default values used by the PDL to control the number of copies
		of each page in the print job that are printed. The print job
		can override this value. The list of supported values should be
		documented in the device POS.
                Additional information:
                 The supported values are 1 through 999.
                Setting to an unsupported value causes the printer to
                substitute in a snap value and to return
                <noError> status.
                The snaps are as follows:
                <1 snaps to
                >999 snaps to 999"
::= { settings-pdl 4 }


default-vertical-black-resolution OBJECT-TYPE
    SYNTAX      INTEGER
    ACCESS      read-write
    STATUS      optional
       DESCRIPTION "Returns or changes the value of the default vertical black
		resolution. The units are dots per inch.
                Additional information:
                In the product, changing this OID
                also causes DEFAULT-HORIZONTAL-BLACK RESOLUTION to
                change.  DEFAULT-HORIZONTAL-BLACK-RESOLUTION and
                DEFAULT-VERTICAL-BLACK-RESOLUTION must always be the
                same.  The only supported value is 600.

                Setting to an unsupported value causes the printer to
                substitute in a snap value and to return
                <noError> status.

                All values snap to 600."
::= { settings-pdl 8 }


default-horizontal-black-resolution OBJECT-TYPE
    SYNTAX      INTEGER
    ACCESS      read-write
    STATUS      optional
       DESCRIPTION "Returns or changes the value of the default horizontal black
		resolution. The units are dots per inch.
                Additional information:
                In the product, changing this OID
                also causes DEFAULT-VERTICAL-BLACK RESOLUTION to change.
                DEFAULT-HORIZONTAL-BLACK-RESOLUTION and
                DEFAULT-VERTICAL-BLACK-RESOLUTION must always be the
                same.  The only supported value is 600.

                Setting to an unsupported value causes the printer to
                substitute in a snap value and to return
                <noError> status.

                All values snap to 600."
::= { settings-pdl 9 }


default-lines-per-page OBJECT-TYPE
    SYNTAX      INTEGER
    ACCESS      read-write
    STATUS      optional
       DESCRIPTION "Returns or changes the default number of lines per page. The
		POS indicates the supported values. An unsupported value causes
		the printer to use the closest supported value, causing the
		printer to return the <noError>.
                Additional information:
                The supported values in the product
                are 5 to 128.  Setting to an unsupported value
                causes the printer to substitute in a snap value and to
                return <noError> status.

                The snap values are as follows:
                <5 snaps to 5
                >128 snaps to 128"
::= { settings-pdl 11 }


default-vmi OBJECT-TYPE
    SYNTAX      INTEGER
    ACCESS      read-write
    STATUS      optional
       DESCRIPTION "Returns or changes the default vertical motion index. The unit
		of measure for VMI is centipoints per line. The POS indicates
		the supported values. An unsupported value causes the printer
		to use the closest supported value, causing the printer to
		return <noError>.
                Additional information:
                Setting this object may cause
                DEFAULT-LINES-PER-PAGE to change."
::= { settings-pdl 12 }


default-media-size OBJECT-TYPE
    SYNTAX      INTEGER {
                          eUSExecutive(1),
                          eUSLetter(2),
                          eUSLegal(3),
                          eFoolscap(10),
                          eROC16K(17),
                          eISOandJISA6(24),
                          eISOandJISA5(25),
                          eISOandJISA4(26),
                          ePRC16K195X270(34),
                          eJISB5(45),
                          eJapanesePostcardSingle(71),
                          eJapanesePostcardDouble(72),
                          eIndexCard5x8(75),
                          ePhoto4x6(76),
                          eMonarch(80),
                          eCommercial10(81),
                          eROC16K184X260(89),
                          eInternationalDL(90),
                          eInternationalC5(91),
                          eInternationalB5(100),
                          eCustom(101),
                          ePhoto10x15(118)
		   }
    ACCESS      read-write
    STATUS      optional
       DESCRIPTION "This indicates the default media size. A write of an
		unsupported value causes an <ErrorInvalidOrUnsupported Value>.		Complete list of supported media sizes along with their
		dimensions are listed in the ''Media Size Table'' near the end
		of this document. (for a full list of media size enums see the
		end of this file) "
::= { settings-pdl 13 }


cold-reset-media-size OBJECT-TYPE
    SYNTAX      INTEGER {
                          eUSLetter(2),
                          eISOandJISA4(26)
		   }
    ACCESS      read-write
    STATUS      optional
       DESCRIPTION "Returns or sets the media size that is used as the
		DEFAULT-MEDIA-SIZE when a cold reset occurs."
::= { settings-pdl 19 }


default-media-name OBJECT-TYPE
    SYNTAX      OCTET STRING
    ACCESS      read-write
    STATUS      optional
       DESCRIPTION "Returns or sets the media name that is used until the media
		name is changed by a print job command.
                Additional information:
                This string must be one of the MEDIAn-NAME
                objects, except it cannot be set to ANY.
                The value of this object is saved across
                		            a power cycle."
::= { settings-pdl 22 }


reprint OBJECT-TYPE
    SYNTAX      INTEGER {
                          eOff(1),
                          eOn(2),
                          eAuto(3)
		   }
    ACCESS      read-write
    STATUS      optional
       DESCRIPTION "Returns or changes the reprint (jam recovery) setting. If eOn,
		then the device will reprint pages jammed pages. If eOff, the
		device will not attempt to reprint jammed pages. If eAuto, a
		device dependent algorithm (which should be documented in the
		POS) will be used to determine if the page gets reprinted. This
		object controls all PDLs, unless a specific PDL supports its
		own reprint control mechanism. To date, only PostScript has a
		PDL reprint control mechanism.
                Additional information:
                Setting this object when the printer is not
                idle, may cause a status of <noError> to be returned, but
                the new value will not take effect until a job boundary
                is reached.  If a get is done on object before the job
                boundary is reached, the value last set will be
                returned.

                When the value is set to eOff, pages will not be stored
                in the printer, and in the event of a paper jam, will
                have to be reprinted.  When the value is set to eOn,
                pages will be stored until delivery, therefore, in the
                event of a paper jam, the page will be reprinted.

                When the value is set to eAuto, the printer will behave
                as though it is eOff when there is less than seven
                megabytes of memory installed in the printer.  When
                additional memory is installed, to total at least seven
                megabytes of RAM, the setting of eAuto will behave as
                though it was set to eOn."
::= { settings-pdl 36 }


wide-a4 OBJECT-TYPE
    SYNTAX      INTEGER {
                          eOff(1),
                          eOn(2)
		   }
    ACCESS      read-write
    STATUS      optional
       DESCRIPTION "Returns or changes the wide A4 logical page size setting. If
		eOn, then the margins/printable area of A4 paper will be
		changed to allow 80 10-pitch characters to be printed on a
		single line. If eOff then the industry standard A4 logical page
		size is used."
::= { settings-pdl 37 }


dark-courier OBJECT-TYPE
    SYNTAX      INTEGER {
                          eOff(1),
                          eOn(2)
		   }
    ACCESS      read-write
    STATUS      optional
       DESCRIPTION "Returns or changes the dark Courier setting. If eOn, then the
		Courier font used will approximate the same darkness as the
		LaserJet III printer. If eOff, then the Courier font used will
		approximate the same darkness as the LaserJet 4 printer."
::= { settings-pdl 38 }


default-bits-per-pixel OBJECT-TYPE
    SYNTAX      INTEGER
    ACCESS      read-write
    STATUS      optional
       DESCRIPTION "Controls the number of levels used (per pixel) when printing
		grayscale or color images."
::= { settings-pdl 39 }


pcl-total-page-count OBJECT-TYPE
    SYNTAX      INTEGER
    ACCESS      read-write
    STATUS      optional
       DESCRIPTION "Total number of PCL pages printed by the device."
::= { pdl-pcl 5 }


pcl-default-font-height OBJECT-TYPE
    SYNTAX      INTEGER
    ACCESS      read-write
    STATUS      optional
       DESCRIPTION "Returns or changes the default PCL height. Height is an
		approximate measure of the body of the type in centipoints. A
		centipoint is 1/7200 inch. Height applies only to proportional
		fonts. Point size, in points, can be converted to font height,
		in centipoints, by multiplying the point size by 100. The POS
		indicates the supported values. An unsupported value causes the
		printer to use the closest supported value, causing the printer
		to return <noError>. ''Closest'' means
		the smallest absolute difference.
                Additional information:
                This object refers to the font point size
                with 400 representing the smallest settable font (4) and
                99975 representing the largest settable font (999.75).
                The default of 1200 is a font point size of 12.

                Supported values range from 400 to 99975.  Setting to an
                unsupported value causes the printer to substitute in a
                snap value and to return
                <noError> status.

                The snap values are as follows:
                <=400 snaps to 400
                >=99975 snaps to 99975

                Fonts are settable to the nearest quarter point size
                (i.e.  10, 10.25, 10.50, 10.75).  Unsupported values in
                the range 401 to 99974 snap DOWN to the previous
                supported value (i.e 25293 snaps to 25275 or 75038 snaps
                to 75025)."
::= { pdl-pcl 13 }


pcl-default-font-source OBJECT-TYPE
    SYNTAX      INTEGER {
                          eInternal(1),
                          ePermanentSoft(2),
                          eRomSimm1(10)
		   }
    ACCESS      read-write
    STATUS      optional
       DESCRIPTION "Returns or changes the value of the default font source
		variable in NVRAM."
::= { pdl-pcl 14 }


pcl-default-font-number OBJECT-TYPE
    SYNTAX      INTEGER(0..255)
    ACCESS      read-write
    STATUS      optional
       DESCRIPTION "Returns or changes the value of the default font number
		variable in NVRAM. Writing an unsupported value causes the
		printer to generate an <badValue>.
                Additional information:
                Valid numbers or 0 - 255, but only font
                numbers that are included in the PCL FONT LIST are
                selectable."
::= { pdl-pcl 15 }


pcl-default-font-width OBJECT-TYPE
    SYNTAX      INTEGER
    ACCESS      read-write
    STATUS      optional
       DESCRIPTION "Returns or changes the default PCL font width. Width is
		expressed as the width of a character in centipoints. A
		centipoint is 1/7200 inch. Width applies only to fixed space
		fonts. Pitch, in character per inch, can be converted to font
		width, in centipoints, by dividing 7200 by the pitch. The POS
		indicates the supported values. An unsupported value causes the
		printer to use the closest supported value, causing the printer
		to return <noError>. ''Closest'' means
		the smallest absolute difference.
                Additional information:
                Setting to an unsupported value causes the
                printer to substitue in a snap value (listed below) and
                return <noError> status.

                The snap values for pitch are as follow:
                <=44 snaps to 44
                >=9999 snaps to 9999

                Unsupported values in the range 44 - 9999 (.44 - 99.99)
                snap DOWN to the next supported value."
::= { pdl-pcl 16 }


postscript-total-page-count OBJECT-TYPE
    SYNTAX      INTEGER
    ACCESS      read-write
    STATUS      optional
       DESCRIPTION "Total number of PostScript pages printed by the device."
::= { pdl-postscript 5 }


postscript-print-errors OBJECT-TYPE
    SYNTAX      INTEGER {
                          eOff(1),
                          eOn(2)
		   }
    ACCESS      read-write
    STATUS      optional
       DESCRIPTION "Returns or changes the value of the print PostScript errors
		setting. If eOn, PostScript prints an error page showing the
		error encountered and the stack at the time of the error.
                Additional information:
                Returns or changes the value of the print PostScript errors
                setting. If eOn, PostScript prints an error page showing the
                error encountered and the stack at the time of the error."
::= { pdl-postscript 11 }


pclxl-total-page-count OBJECT-TYPE
    SYNTAX      INTEGER
    ACCESS      read-write
    STATUS      optional
       DESCRIPTION "Total number of PCLXL pages printed by the device."
::= { pdl-pclxl 1 }


pjl-password OBJECT-TYPE
    SYNTAX      INTEGER
    ACCESS      read-only
    STATUS      optional
       DESCRIPTION "Returns PJL password, if the password is not set (zero). If the
		password is set, then attempting to retrieve the password
		causes an <genErr> to occur and will return
		the <NullValue>."
::= { pjl 1 }


print-density OBJECT-TYPE
    SYNTAX      INTEGER(1..5)
    ACCESS      read-write
    STATUS      optional
       DESCRIPTION "Returns or sets the print density setting. Print density is the
		instantaneous amount of marking agent applied to the paper
		while printing. A value of zero has the lowest print density,
		yielding a lighter page. A value of 10 has the highest print
		density, yielding a darker page. Each POS should document what
		values in the 0 to 10 range are supported.
                Additional information:
                When this value is written, the page
                pipeline will be flushed (all pages being printed are
                completed, no new ones are started), the new density
                setting is set and printing resumes.  The acutal change
                in print density may be gradual over several pages.

                The supported values are 1 through 5.  Setting to an
                unsupported value causes the printer to substitue in a
                a snap value and to return <noError>
                status.

                The snap values are as follows:
                <1 snaps to 1
                >5 snaps to 5."
::= { settings-prt-eng 5 }


invalid-personality-reports-enabled OBJECT-TYPE
    SYNTAX      INTEGER {
                          eDisabled(1),
                          eEnabled(2)
		   }
    ACCESS      read-write
    STATUS      optional
       DESCRIPTION "Read or configure wether invalid personality reports are
		enabled or disabled for a product."
::= { settings-prt-eng 18 }


supplies-at-very-low-setting OBJECT-TYPE
    SYNTAX      INTEGER {
                          eStopAtOut(2),
                          eOverrideAtOut(4),
                          ePromptAtOut(6),
                          ePrintBlack(7)
		   }
    ACCESS      read-write
    STATUS      optional
       DESCRIPTION "This object can be used to change the setting of menu item AT
		VERY LOW. The behavior of the printer when a supply reaches low
		changes in accordance with the setting of this PML Object. If
		the option eStopAtOut is selected then printer will stop when a
		supply reaches Estimated End of Life (EEOL). If the option
		eOverrideAtOut is selected then printer will continue past EEOL
		in override mode. If the option eOverrideAtOut is selected then
		printer will continue past EEOL in override mode. If the option
		ePromptAtOut is selected then printer will ask the user if they
		wish to continue printing past EEOL in override mode. If the
		option eAutoContinueBlack is selected then printer will
		continue printing in mono past EEOL. This may be subject to
		page limits. (Color only) NOTE: This object replaces
		SUPPLIES-REPLACE-ACTION-AT-SETTING"
::= { settings-prt-eng 38 }


total-engine-page-count OBJECT-TYPE
    SYNTAX      INTEGER
    ACCESS      read-write
    STATUS      optional
       DESCRIPTION "Total number of pages printed by the device. POS indicates if
		the total engine page count is kept in NVRAM, and the maximum
		supported value before the page count rolls over to zero.
                Additional information:
                This object is stored in NVRAM.  The maximum value of
                this count is 1000000 before it rolls over to zero."
::= { status-prt-eng 5 }


print-engine-jam-count OBJECT-TYPE
    SYNTAX      INTEGER
    ACCESS      read-write
    STATUS      optional
       DESCRIPTION "Total number of pages jammed in the print engine's life time.
		The POS indicates if the total jam count is kept in NVRAM and
		the maximum supported value before the jam count rolls over to
		zero.
                Additional information:
                This object is stored in NVRAM. The maximum value of
                this count is 65000 before it rolls over to zero."
::= { status-prt-eng 34 }


print-engine-mispick-count OBJECT-TYPE
    SYNTAX      INTEGER
    ACCESS      read-write
    STATUS      optional
       DESCRIPTION "Total number of pages mispicked in the print engine's life
		time. The POS indicates if the total mispick count is kept in
		NVRAM and the maximum supported value before the mispick count
		rolls over to zero.
                Additional information:
                This object is stored in NVRAM. The maximum value of
                this count is 65000 before it rolls over to zero."
::= { status-prt-eng 35 }


supply-out-device-state OBJECT-TYPE
    SYNTAX      INTEGER {
                          eNoSupplyOut(1),
                          eOffline(2),
                          eSupplyOutOverride(3),
                          eMonochromePrintingAfterColorCartridgeOut(4)
		   }
    ACCESS      read-only
    STATUS      optional
       DESCRIPTION "This PML object indicates the current behavior of the device if
		one or more supplies have reached out. If no supply has reached
		out, the value of this PML object is eNoSupplyOut. If one or
		more supplies have reached out, the value of this PML object
		will indicate if the printer is online and if so what mode is
		being used to continue printing.
                Additional information:
                This PML object indicates the current behavior of the device if
                one or more supplies have reached out. If no supply has reached
                out, the value of this PML object is eNoSupplyOut. If one or
                more supplies have reached out, the value of this PML object
                will indicate if the printer is online and if so what mode is
                being used to continue printing. If the printer is in both
                eSupplyOutOverride and eMonochromePrintingAfterColorCartridgeOut
                then eMonochromePrintingAfterColorCartridgeOut will be returned."
::= { status-prt-eng 49 }


print-engine-revision OBJECT-TYPE
    SYNTAX      OCTET STRING
    ACCESS      read-only
    STATUS      optional
       DESCRIPTION "Print engine revision string.
                Additional information:
                Print engine revision string."
::= { status-prt-eng 26 }


custom-paper-dim-unit OBJECT-TYPE
    SYNTAX      INTEGER {
                          eTenThousandthsOfInches(3),
                          eMicrometers(4)
		   }
    ACCESS      read-write
    STATUS      optional
       DESCRIPTION "The units of measure used to specify the width and height of
		the printer's custom paper. The unit of measure of
		eTenThousandthsOfInches is 0.0001 inches.
                Additional information:
                The only valid values for this object are
                eTenThousandthsOfInches (3), and eMicrometers (4).  The
                data for this object is stored in NVRAM."
::= { settings-intray 7 }


custom-paper-feed-dim OBJECT-TYPE
    SYNTAX      INTEGER(50000..140000)
    ACCESS      read-write
    STATUS      optional
       DESCRIPTION "Sets the printer's custom paper dimension in the feed direction
		(direction parallel to the direction of paper feeding). The
		value for this object is specified in micrometers or
		tenthousandths of an inch, depending upon the value of
		CUSTOM-PAPER-DIM-UNIT. The valid range is engine-dependent and
		should be documented in the POS for each product.
                Additional information:
                 The valid range is 50000 to 140000 if
                CUSTOM-PAPER_DIM_UNIT is eTenThousandthsOfInches or 127000 to
                355600 if CUSTOM-PAPER-DIM-UNIT is ePmicrometers.  Attempts
                to set this object outside the valid range will result in a
                return value of ERROR_INVALID_OR_UNSUPPORTED_VALUE."
::= { settings-intray 8 }


custom-paper-xfeed-dim OBJECT-TYPE
    SYNTAX      INTEGER(30000..85000)
    ACCESS      read-write
    STATUS      optional
       DESCRIPTION "Sets the printer's custom paper dimension in the cross-feed
		direction (direction ninety degrees relative to the direction
		of paper feeding). The value for this object is specified in
		micrometers or tenthousandths of an inch, depending upon the
		value of CUSTOM-PAPER-DIM-UNIT. The valid range is
		engine-dependent and should be documented in the POS for each
		product.
                Additional information:
                The valid range for the product
                		is 30000 to 85000 if CUSTOM-PAPER-DIM-UNIT is
                eTenThousandthsOfInches or 76200 to 215900 if
                CUSTOM-PAPER-DIM-UNIT is ePmicrometers.  Attempts to set
                this object outside the valid range will result in a
                return value of <badValue>."
::= { settings-intray 9 }


tray1-media-size-loaded OBJECT-TYPE
    SYNTAX      INTEGER {
                          eUSExecutive(1),
                          eUSLetter(2),
                          eUSLegal(3),
                          eFoolscap(10),
                          eROC16K(17),
                          eISOandJISA6(24),
                          eISOandJISA5(25),
                          eISOandJISA4(26),
                          eROC16K195X270(34),
                          eJISB5(45),
                          eJapansePostcardSingle(71),
                          eJapansePostcardDouble(72),
                          eIndexCard5x8(75),
                          ePhoto4x6(76),
                          eMonarch(80),
                          eCommercial10(81),
                          eROC16K184X260(89),
                          eInternationalDL(90),
                          eInternationalC5(91),
                          eInternationalB5(100),
                          eCustom(101),
                          ePhoto10x15(118),
                          eAnySize(32765)
		   }
    ACCESS      read-write
    STATUS      optional
       DESCRIPTION "Returns the media size that is currently configuredconfigured
		in tray #1. This object can be set to indicate the media size
		currently loaded, if the printer supports input trays that can
		not sense the media size. Complete list of supported media
		sizes along with their dimensions are listed in the ''Media
		Size Table'' near the end of this document."
::= { intray1 1 }


default-ret OBJECT-TYPE
    SYNTAX      INTEGER {
                          eOff(1),
                          eLight(2),
                          eMedium(3),
                          eDark(4)
		   }
    ACCESS      read-write
    STATUS      optional
       DESCRIPTION "Returns or changes the Resolution Enhancement Technology
		setting. Devices that only support eOff and eOn should map all
		other values to eOn and always return the same non-eOff value
		to indicate on. The list of supported values should be
		documented in the device POS."
::= { imaging 5 }


media-names-available OBJECT-TYPE
    SYNTAX      OCTET STRING
    ACCESS      read-only
    STATUS      optional
       DESCRIPTION "The value of this object controls which of the MEDIAx-NAME
		objects are supported. If a bit is set to zero, then attempting
		to get or set the corresponding MEDIAx-NAME objects will return
		<noSuchName>.
                Additional information:
                Since this object is read-only, the corresponding MEDIAx
                			objects will always be available.  The DEFAULTS below
                represent which MediaNameX is available on this product
                of the total possible available defined in SYNTAX, so the
                collection is like a bitfield. NOTE - this object is limited
                to only 32 media names - Please use MEDIA-NAMES-ENABLED
                to determine true number of media names on a given product."
::= { settings-print-media 1 }


media-names-enabled OBJECT-TYPE
    SYNTAX      OCTET STRING (SIZE(0..63))
    ACCESS      read-only
    STATUS      optional
       DESCRIPTION "The value of this object controls whish of the MEDIAx-NAME
		objects are supported. Of a bit is set to zero then the attempt
		to get or set the corresponding MEDIAx-NAME objects will return
		<noSuchName>
                Additional information:
                The value of this object controls which of the MEDIAx-NAME
                objects are supported. If a bit is set to zero then the attempt
                to get or set the corresponding MEDIAx-NAME objects will return
                <noSuchName>.  This replaces the MEDIA-NAMES-
                AVAILABLE object for a product that supports more than 32 types."
::= { settings-print-media 3 }


media1-name OBJECT-TYPE
    SYNTAX      OCTET STRING
    ACCESS      read-only
    STATUS      optional
       DESCRIPTION "Media 1 name.
                Additional information:
                The symbol set for this string is Roman-8."
::= { media1 1 }


media1-engine-media-mode OBJECT-TYPE
    SYNTAX      INTEGER
    ACCESS      read-only
    STATUS      optional
       DESCRIPTION "The engine processing characteristics that are to be applied to
		this media. The processing characteristics are device
		specific.
                Additional information:
                The engine processing characteristics that are to
                be applied to this media type. Currently, 'engine
                processing characteristics' denotes changes to
                fusing temperature and/or transfer roller voltage."
::= { media1 4 }


media2-name OBJECT-TYPE
    SYNTAX      OCTET STRING
    ACCESS      read-only
    STATUS      optional
       DESCRIPTION "Media 2 name.
                Additional information:
                The symbol set for this string is Roman-8."
::= { media2 1 }


media2-engine-media-mode OBJECT-TYPE
    SYNTAX      INTEGER
    ACCESS      read-write
    STATUS      optional
       DESCRIPTION "The engine processing characteristics that are to be applied to
		this media. The processing characteristics are device
		specific.
                Additional information:
                See the description for MEDIA1-ENGINE-MEDIA-MODE."
::= { media2 4 }


media3-name OBJECT-TYPE
    SYNTAX      OCTET STRING
    ACCESS      read-only
    STATUS      optional
       DESCRIPTION "Media 3 name.
                Additional information:
                The symbol set for this string is Roman-8."
::= { media3 1 }


media3-engine-media-mode OBJECT-TYPE
    SYNTAX      INTEGER
    ACCESS      read-write
    STATUS      optional
       DESCRIPTION "The engine processing characteristics that are to be applied to
		this media. The processing characteristics are device
		specific.
                Additional information:
                See the description for MEDIA1-ENGINE-MEDIA-MODE."
::= { media3 4 }


media4-name OBJECT-TYPE
    SYNTAX      OCTET STRING
    ACCESS      read-only
    STATUS      optional
       DESCRIPTION "Media 4 name.
                Additional information:
                The symbol set for this string is Roman-8."
::= { media4 1 }


media4-engine-media-mode OBJECT-TYPE
    SYNTAX      INTEGER
    ACCESS      read-write
    STATUS      optional
       DESCRIPTION "The engine processing characteristics that are to be applied to
		this media. The processing characteristics are device
		specific.
                Additional information:
                See the description for MEDIA1-ENGINE-MEDIA-MODE."
::= { media4 4 }


media5-name OBJECT-TYPE
    SYNTAX      OCTET STRING
    ACCESS      read-only
    STATUS      optional
       DESCRIPTION "Media 5 name.
                Additional information:
                The symbol set for this string is Roman-8."
::= { media5 1 }


media5-engine-media-mode OBJECT-TYPE
    SYNTAX      INTEGER
    ACCESS      read-write
    STATUS      optional
       DESCRIPTION "The engine processing characteristics that are to be applied to
		this media. The processing characteristics are device
		specific.
                Additional information:
                See the description for MEDIA1-ENGINE-MEDIA-MODE."
::= { media5 4 }


media6-name OBJECT-TYPE
    SYNTAX      OCTET STRING
    ACCESS      read-only
    STATUS      optional
       DESCRIPTION "Media 6 name.
                Additional information:
                The symbol set for this string is Roman-8."
::= { media6 1 }


media6-engine-media-mode OBJECT-TYPE
    SYNTAX      INTEGER
    ACCESS      read-write
    STATUS      optional
       DESCRIPTION "The engine processing characteristics that are to be applied to
		this media. The processing characteristics are device
		specific.
                Additional information:
                See the description for MEDIA1-ENGINE-MEDIA-MODE."
::= { media6 4 }


media7-name OBJECT-TYPE
    SYNTAX      OCTET STRING
    ACCESS      read-only
    STATUS      optional
       DESCRIPTION "Media 7 name.
                Additional information:
                The symbol set for this string is Roman-8."
::= { media7 1 }


media7-engine-media-mode OBJECT-TYPE
    SYNTAX      INTEGER
    ACCESS      read-write
    STATUS      optional
       DESCRIPTION "The engine processing characteristics that are to be applied to
		this media. The processing characteristics are device
		specific.
                Additional information:
                See the description for MEDIA1-ENGINE-MEDIA-MODE."
::= { media7 4 }


media8-name OBJECT-TYPE
    SYNTAX      OCTET STRING
    ACCESS      read-only
    STATUS      optional
       DESCRIPTION "Media 8 name.
                Additional information:
                The symbol set for this string is Roman-8."
::= { media8 1 }


media8-engine-media-mode OBJECT-TYPE
    SYNTAX      INTEGER
    ACCESS      read-write
    STATUS      optional
       DESCRIPTION "The engine processing characteristics that are to be applied to
		this media. The processing characteristics are device
		specific.
                Additional information:
                See the description for MEDIA1-ENGINE-MEDIA-MODE."
::= { media8 4 }


media9-name OBJECT-TYPE
    SYNTAX      OCTET STRING
    ACCESS      read-only
    STATUS      optional
       DESCRIPTION "Media 9 name.
                Additional information:
                The symbol set for this string is Roman-8."
::= { media9 1 }


media9-engine-media-mode OBJECT-TYPE
    SYNTAX      INTEGER
    ACCESS      read-write
    STATUS      optional
       DESCRIPTION "The engine processing characteristics that are to be applied to
		this media. The processing characteristics are device
		specific.
                Additional information:
                See the description for MEDIA1-ENGINE-MEDIA-MODE."
::= { media9 4 }


media10-name OBJECT-TYPE
    SYNTAX      OCTET STRING
    ACCESS      read-only
    STATUS      optional
       DESCRIPTION "Media 10 name.
                Additional information:
                The symbol set for this string is Roman-8."
::= { media10 1 }


media10-engine-media-mode OBJECT-TYPE
    SYNTAX      INTEGER
    ACCESS      read-write
    STATUS      optional
       DESCRIPTION "The engine processing characteristics that are to be applied to
		this media. The processing characteristics are device
		specific.
                Additional information:
                See the description for MEDIA1-ENGINE-MEDIA-MODE."
::= { media10 4 }


media11-name OBJECT-TYPE
    SYNTAX      OCTET STRING
    ACCESS      read-only
    STATUS      optional
       DESCRIPTION "Media 11 name.
                Additional information:
                The symbol set for this string is Roman-8."
::= { media11 1 }


media11-engine-media-mode OBJECT-TYPE
    SYNTAX      INTEGER
    ACCESS      read-write
    STATUS      optional
       DESCRIPTION "The engine processing characteristics that are to be applied to
		this media. The processing characteristics are device
		specific.
                Additional information:
                See the description for MEDIA1-ENGINE-MEDIA-MODE."
::= { media11 4 }


media12-name OBJECT-TYPE
    SYNTAX      OCTET STRING
    ACCESS      read-only
    STATUS      optional
       DESCRIPTION "Media 12 name.
                Additional information:
                The symbol set for this string is Roman-8."
::= { media12 1 }


media12-engine-media-mode OBJECT-TYPE
    SYNTAX      INTEGER
    ACCESS      read-write
    STATUS      optional
       DESCRIPTION "The engine processing characteristics that are to be applied to
		this media. The processing characteristics are device
		specific.
                Additional information:
                See the description for MEDIA1-ENGINE-MEDIA-MODE."
::= { media12 4 }


media13-name OBJECT-TYPE
    SYNTAX      OCTET STRING
    ACCESS      read-only
    STATUS      optional
       DESCRIPTION "Media 13 name.
                Additional information:
                The symbol set for this string is Roman-8."
::= { media13 1 }


media13-engine-media-mode OBJECT-TYPE
    SYNTAX      INTEGER
    ACCESS      read-write
    STATUS      optional
       DESCRIPTION "The engine processing characteristics that are to be applied to
		this media. The processing characteristics are device
		specific.
                Additional information:
                See the description for MEDIA1-ENGINE-MEDIA-MODE."
::= { media13 4 }


media14-name OBJECT-TYPE
    SYNTAX      OCTET STRING
    ACCESS      read-only
    STATUS      optional
       DESCRIPTION "Media 14 name.
                Additional information:
                The symbol set for this string is Roman-8."
::= { media14 1 }


media14-engine-media-mode OBJECT-TYPE
    SYNTAX      INTEGER
    ACCESS      read-write
    STATUS      optional
       DESCRIPTION "The engine processing characteristics that are to be applied to
		this media. The processing characteristics are device
		specific.
                Additional information:
                See the description for MEDIA1-ENGINE-MEDIA-MODE."
::= { media14 4 }


media15-name OBJECT-TYPE
    SYNTAX      OCTET STRING
    ACCESS      read-only
    STATUS      optional
       DESCRIPTION "Media 15 name.
                Additional information:
                The symbol set for this string is Roman-8."
::= { media15 1 }


media15-engine-media-mode OBJECT-TYPE
    SYNTAX      INTEGER
    ACCESS      read-write
    STATUS      optional
       DESCRIPTION "The engine processing characteristics that are to be applied to
		this media. The processing characteristics are device
		specific.
                Additional information:
                See the description for MEDIA1-ENGINE-MEDIA-MODE."
::= { media15 4 }


media16-name OBJECT-TYPE
    SYNTAX      OCTET STRING
    ACCESS      read-only
    STATUS      optional
       DESCRIPTION "Media 16 name.
                Additional information:
                The symbol set for this string is Roman-8."
::= { media16 1 }


media16-engine-media-mode OBJECT-TYPE
    SYNTAX      INTEGER
    ACCESS      read-write
    STATUS      optional
       DESCRIPTION "The engine processing characteristics that are to be applied to
		this media. The processing characteristics are device
		specific.
                Additional information:
                See the description for MEDIA1-ENGINE-MEDIA-MODE."
::= { media16 4 }


media17-name OBJECT-TYPE
    SYNTAX      OCTET STRING
    ACCESS      read-only
    STATUS      optional
       DESCRIPTION "Media 17 name.
                Additional information:
                The symbol set for this string is Roman-8."
::= { media17 1 }


media17-engine-media-mode OBJECT-TYPE
    SYNTAX      INTEGER
    ACCESS      read-write
    STATUS      optional
       DESCRIPTION "The engine processing characteristics that are to be applied to
		this media. The processing characteristics are device
		specific.
                Additional information:
                See the description for MEDIA1-ENGINE-MEDIA-MODE."
::= { media17 4 }


media18-name OBJECT-TYPE
    SYNTAX      OCTET STRING
    ACCESS      read-only
    STATUS      optional
       DESCRIPTION "Media 18 name.
                Additional information:
                The symbol set for this string is Roman-8."
::= { media18 1 }


media18-engine-media-mode OBJECT-TYPE
    SYNTAX      INTEGER
    ACCESS      read-write
    STATUS      optional
       DESCRIPTION "The engine processing characteristics that are to be applied to
		this media. The processing characteristics are device
		specific.
                Additional information:
                See the description for MEDIA1-ENGINE-MEDIA-MODE."
::= { media18 4 }


media19-name OBJECT-TYPE
    SYNTAX      OCTET STRING
    ACCESS      read-only
    STATUS      optional
       DESCRIPTION "Media 19 name.
                Additional information:
                The symbol set for this string is Roman-8."
::= { media19 1 }


media19-engine-media-mode OBJECT-TYPE
    SYNTAX      INTEGER
    ACCESS      read-write
    STATUS      optional
       DESCRIPTION "The engine processing characteristics that are to be applied to
		this media. The processing characteristics are device
		specific.
                Additional information:
                See the description for MEDIA1-ENGINE-MEDIA-MODE."
::= { media19 4 }


media20-name OBJECT-TYPE
    SYNTAX      OCTET STRING
    ACCESS      read-only
    STATUS      optional
       DESCRIPTION "Media 20 name.
                Additional information:
                The symbol set for this string is Roman-8."
::= { media20 1 }


media20-engine-media-mode OBJECT-TYPE
    SYNTAX      INTEGER
    ACCESS      read-write
    STATUS      optional
       DESCRIPTION "The engine processing characteristics that are to be applied to
		this media. The processing characteristics are device
		specific.
                Additional information:
                See the description for MEDIA1-ENGINE-MEDIA-MODE."
::= { media20 4 }


media21-name OBJECT-TYPE
    SYNTAX      OCTET STRING
    ACCESS      read-only
    STATUS      optional
       DESCRIPTION "Media 21 name.
                Additional information:
                The symbol set for this string is Roman-8."
::= { media21 1 }


media21-engine-media-mode OBJECT-TYPE
    SYNTAX      INTEGER
    ACCESS      read-write
    STATUS      optional
       DESCRIPTION "The engine processing characteristics that are to be applied to
		this media. The processing characteristics are device
		specific.
                Additional information:
                See the description for MEDIA1-ENGINE-MEDIA-MODE."
::= { media21 4 }


media22-name OBJECT-TYPE
    SYNTAX      OCTET STRING
    ACCESS      read-only
    STATUS      optional
       DESCRIPTION "Media 22 name.
                Additional information:
                The symbol set for this string is Roman-8."
::= { media22 1 }


media22-engine-media-mode OBJECT-TYPE
    SYNTAX      INTEGER
    ACCESS      read-write
    STATUS      optional
       DESCRIPTION "The engine processing characteristics that are to be applied to
		this media. The processing characteristics are device
		specific.
                Additional information:
                See the description for MEDIA1-ENGINE-MEDIA-MODE."
::= { media22 4 }


media23-name OBJECT-TYPE
    SYNTAX      OCTET STRING
    ACCESS      read-only
    STATUS      optional
       DESCRIPTION "Media 23 name.
                Additional information:
                The symbol set for this string is Roman-8."
::= { media23 1 }


media23-engine-media-mode OBJECT-TYPE
    SYNTAX      INTEGER
    ACCESS      read-write
    STATUS      optional
       DESCRIPTION "The engine processing characteristics that are to be applied to
		this media. The processing characteristics are device
		specific.
                Additional information:
                See the description for MEDIA1-ENGINE-MEDIA-MODE."
::= { media23 4 }


media24-name OBJECT-TYPE
    SYNTAX      OCTET STRING
    ACCESS      read-only
    STATUS      optional
       DESCRIPTION "Media 24 name.
                Additional information:
                The symbol set for this string is Roman-8."
::= { media24 1 }


media24-engine-media-mode OBJECT-TYPE
    SYNTAX      INTEGER
    ACCESS      read-write
    STATUS      optional
       DESCRIPTION "The engine processing characteristics that are to be applied to
		this media. The processing characteristics are device
		specific.
                Additional information:
                See the description for MEDIA1-ENGINE-MEDIA-MODE."
::= { media24 4 }


media25-name OBJECT-TYPE
    SYNTAX      OCTET STRING
    ACCESS      read-only
    STATUS      optional
       DESCRIPTION "Media 25 name.
                Additional information:
                The symbol set for this string is Roman-8."
::= { media25 1 }


media25-engine-media-mode OBJECT-TYPE
    SYNTAX      INTEGER
    ACCESS      read-write
    STATUS      optional
       DESCRIPTION "The engine processing characteristics that are to be applied to
		this media. The processing characteristics are device
		specific.
                Additional information:
                See the description for MEDIA1-ENGINE-MEDIA-MODE."
::= { media25 4 }


media26-name OBJECT-TYPE
    SYNTAX      OCTET STRING
    ACCESS      read-only
    STATUS      optional
       DESCRIPTION "Media 26 name.
                Additional information:
                The symbol set for this string is Roman-8."
::= { media26 1 }


media26-engine-media-mode OBJECT-TYPE
    SYNTAX      INTEGER
    ACCESS      read-write
    STATUS      optional
       DESCRIPTION "The engine processing characteristics that are to be applied to
		this media. The processing characteristics are device
		specific.
                Additional information:
                See the description for MEDIA1-ENGINE-MEDIA-MODE."
::= { media26 4 }


media27-name OBJECT-TYPE
    SYNTAX      OCTET STRING
    ACCESS      read-only
    STATUS      optional
       DESCRIPTION "Media 27 name.
                Additional information:
                The symbol set for this string is Roman-8."
::= { media27 1 }


media27-engine-media-mode OBJECT-TYPE
    SYNTAX      INTEGER
    ACCESS      read-write
    STATUS      optional
       DESCRIPTION "The engine processing characteristics that are to be applied to
		this media. The processing characteristics are device
		specific.
                Additional information:
                See the description for MEDIA1-ENGINE-MEDIA-MODE."
::= { media27 4 }


media28-name OBJECT-TYPE
    SYNTAX      OCTET STRING
    ACCESS      read-only
    STATUS      optional
       DESCRIPTION "Media 28 name.
                Additional information:
                The symbol set for this string is Roman-8."
::= { media28 1 }


media28-engine-media-mode OBJECT-TYPE
    SYNTAX      INTEGER
    ACCESS      read-write
    STATUS      optional
       DESCRIPTION "The engine processing characteristics that are to be applied to
		this media. The processing characteristics are device
		specific.
                Additional information:
                See the description for MEDIA1-ENGINE-MEDIA-MODE."
::= { media28 4 }


media29-name OBJECT-TYPE
    SYNTAX      OCTET STRING
    ACCESS      read-only
    STATUS      optional
       DESCRIPTION "Media 29 name.
                Additional information:
                The symbol set for this string is Roman-8."
::= { media29 1 }


media29-engine-media-mode OBJECT-TYPE
    SYNTAX      INTEGER
    ACCESS      read-write
    STATUS      optional
       DESCRIPTION "The engine processing characteristics that are to be applied to
		this media. The processing characteristics are device
		specific.
                Additional information:
                See the description for MEDIA1-ENGINE-MEDIA-MODE."
::= { media29 4 }


media30-name OBJECT-TYPE
    SYNTAX      OCTET STRING
    ACCESS      read-only
    STATUS      optional
       DESCRIPTION "Media 30 name.
                Additional information:
                The symbol set for this string is Roman-8."
::= { media30 1 }


media30-engine-media-mode OBJECT-TYPE
    SYNTAX      INTEGER
    ACCESS      read-write
    STATUS      optional
       DESCRIPTION "The engine processing characteristics that are to be applied to
		this media. The processing characteristics are device
		specific.
                Additional information:
                See the description for MEDIA1-ENGINE-MEDIA-MODE."
::= { media30 4 }


media31-name OBJECT-TYPE
    SYNTAX      OCTET STRING
    ACCESS      read-only
    STATUS      optional
       DESCRIPTION "Media 31 name.
                Additional information:
                The symbol set for this string is Roman-8."
::= { media31 1 }


media31-engine-media-mode OBJECT-TYPE
    SYNTAX      INTEGER
    ACCESS      read-write
    STATUS      optional
       DESCRIPTION "The engine processing characteristics that are to be applied to
		this media. The processing characteristics are device
		specific.
                Additional information:
                See the description for MEDIA1-ENGINE-MEDIA-MODE."
::= { media31 4 }


media32-name OBJECT-TYPE
    SYNTAX      OCTET STRING
    ACCESS      read-only
    STATUS      optional
       DESCRIPTION "Media 32 name.
                Additional information:
                The symbol set for this string is Roman-8."
::= { media32 1 }


media32-engine-media-mode OBJECT-TYPE
    SYNTAX      INTEGER
    ACCESS      read-write
    STATUS      optional
       DESCRIPTION "The engine processing characteristics that are to be applied to
		this media. The processing characteristics are device
		specific.
                Additional information:
                See the description for MEDIA1-ENGINE-MEDIA-MODE."
::= { media32 4 }


media33-name OBJECT-TYPE
    SYNTAX      OCTET STRING
    ACCESS      read-only
    STATUS      optional
       DESCRIPTION "Media 3 name.
                Additional information:
                The symbol set for this string is Roman-8."
::= { media33 1 }


media33-engine-media-mode OBJECT-TYPE
    SYNTAX      INTEGER
    ACCESS      read-write
    STATUS      optional
       DESCRIPTION "The engine processing characteristics that are to be applied to
		this media. The processing characteristics are device
		specific.
                Additional information:
                See the description for MEDIA1-ENGINE-MEDIA-MODE."
::= { media33 4 }


media34-name OBJECT-TYPE
    SYNTAX      OCTET STRING
    ACCESS      read-only
    STATUS      optional
       DESCRIPTION "Media 3 name.
                Additional information:
                The symbol set for this string is Roman-8."
::= { media34 1 }


media34-engine-media-mode OBJECT-TYPE
    SYNTAX      INTEGER
    ACCESS      read-write
    STATUS      optional
       DESCRIPTION "The engine processing characteristics that are to be applied to
		this media. The processing characteristics are device
		specific.
                Additional information:
                See the description for MEDIA1-ENGINE-MEDIA-MODE."
::= { media34 4 }


engine-media-modes-supported1 OBJECT-TYPE
    SYNTAX      OCTET STRING
    ACCESS      read-only
    STATUS      optional
       DESCRIPTION "The list of engine media modes supported by the device. The
		modes are each separated by a comma character. An example
		string would be: 'Normal,Rough,Low,Vellum'."
::= { media-modes 1 }


pe-test-cause-assert OBJECT-TYPE
    SYNTAX      INTEGER {
                          e49DEAD(1),
                          e494C02(2),
                          e4900FF(3),
                          e80DEAD(4),
                          e81DEAD(5)
		   }
    ACCESS      write-only
    STATUS      optional
       DESCRIPTION "This object allows the user to cause a 49 Error.
                Additional information:
                This object allows the user to cause a 49 Error."
::= { print-engine-test 111 }


pe-test-cause-79error OBJECT-TYPE
    SYNTAX      INTEGER {
                          e79DEAD(1)
		   }
    ACCESS      write-only
    STATUS      optional
       DESCRIPTION "This object allows the user to cause a 79 Error.
                Additional information:
                This object allows the user to cause a 79 Error."
::= { print-engine-test 116 }


consumable-status-serial-number OBJECT-TYPE
    SYNTAX      OCTET STRING
    ACCESS      read-only
    STATUS      optional
       DESCRIPTION "This object is used to report the serial number for this
		consumable."
::= { consumable-status 3 }


consumable-status-partnumber OBJECT-TYPE
    SYNTAX      OCTET STRING
    ACCESS      read-only
    STATUS      optional
       DESCRIPTION "This object will have one sub-array for the consumable and will
		will hold the consumable's part number.
                Additional information:
                This object will have one sub-array for the consumable and will
                will hold the consumable's part number."
::= { consumable-status 56 }


consumable-reorder-url OBJECT-TYPE
    SYNTAX      OCTET STRING (SIZE(0..64))
    ACCESS      read-write
    STATUS      optional
       DESCRIPTION "This object is used to read and write the URL that can be used
		to reorder consumables for this device. This URL is set at the
		factory but can be updated by a reseller or third party.
                Additional information:
                The URL can be up to 64 characters long."
::= { consumables 2 }


consumable-pages-printed-with-supply OBJECT-TYPE
    SYNTAX      INTEGER
    ACCESS      read-only
    STATUS      optional
       DESCRIPTION "This PML object returns the number of pages printed with a
		cartridge consumable. This PML object returns the value that
		should be displayed under 'Pages Printed With This Supply' for
		cartridges in color products."
::= { consumables 11 }


consumable-life-usage-units-remaining OBJECT-TYPE
    SYNTAX      INTEGER
    ACCESS      read-only
    STATUS      optional
       DESCRIPTION "This object reports the current estimate of the number of usage
		units that remain before this supply is depleted. An installed
		supply that cannot report such a number will return a value of
		-2. It is the reponsibility of the host application to query
		each supply in order to determine an overall device
		USAGE-UNITS-REMAINING number - the lowest value returned. The
		unit of measure for this life estimate is determined by reading
		the corresponding CONSUMABLE-LIFE-USAGE-UNITS object.
                Additional information:
                This object reports the approximate number of pages remaining
                before this supply reaches very low. An installed cartridge that
                cannot report such a number (because supply status is not
                available) will return a value of -2. If the supply life is above
                80% then this object will return ErrorActionCanNotBePerformedNow
                (or genErr if queried through SNMP)."
::= { consumables-life 1 }


consumable-life-low-threshold OBJECT-TYPE
    SYNTAX      INTEGER
    ACCESS      read-write
    STATUS      optional
       DESCRIPTION "This object is used to report and modify a threshold value
		indicating the point in the life of a consumable or supply at
		which a transition to a LOW state will occur."
::= { consumables-life 3 }


consumable-test-password OBJECT-TYPE
    SYNTAX      INTEGER
    ACCESS      write-only
    STATUS      optional
       DESCRIPTION "When set with the correct integer password value this object is
		used to enable certain device specific test capabilities. When
		set with any incorrect integer value, this object is used to
		disable any device specific features previously enabled by this
		object. This object will return a response of
		<noSuchName> whenever an attempt is made to
		query the object rather than
		<noSuchName> so as to hide the
		existence of this object from external host applications."
::= { consumables-test 1 }


prtGeneralConfigChanges OBJECT-TYPE
    SYNTAX      INTEGER
    ACCESS      read-only
    STATUS      optional
       DESCRIPTION "Counts configuration changes that change the capabilities of
        a printer, such as the addition/deletion of input/output bins,
        the addition/deletion of interpreters, or changes in media
        size.  Such changes will often affect the capability of the
        printer to service certain types of print jobs.
        Management applications may cache infrequently changed
        configuration  information about sub-units on the printer.
        This object should be incremented whenever the agent wishes
        such applications to invalidate that cache and re-download
        all of this configuration information, thereby signaling a
        change in the printer's configuration.
        For example, if an input tray that contained paper of
        different dimensions was added, this counter would be
        incremented.
        As an additional example, this counter would not be
        incremented when an input tray is removed or the level of an
		input device changes.
                Additional information:
                This is a 32 bit counter (unsigned).  When it
                reaches its maximum value, it will roll to zero."
::= { prtGeneralEntry 1 }


prtGeneralCurrentLocalization OBJECT-TYPE
    SYNTAX      INTEGER
    ACCESS      read-write
    STATUS      optional
       DESCRIPTION "The value of the prtLocalizationIndex corresponding to the
        current language, country, and character set to be used for
        localized string values that are identified as being dependent
        on the value of this object.  Note that this object does not
        apply to localized strings in the prtConsole group or to any
        object that is not explicitly identified as being localized
        according to prtGeneralCurrentLocalization."
::= { prtGeneralEntry 2 }


prtGeneralReset OBJECT-TYPE
    SYNTAX      INTEGER {
                          ePnotResetting(3),
                          ePpowerCycleReset(4),
                          ePresetToNVRAM(5),
                          ePresetToFactoryDefaults(6)
		   }
    ACCESS      read-write
    STATUS      optional
       DESCRIPTION "Setting this value to `powerCycleReset', `resetToNVRAM', or
        `resetToFactoryDefaults' will result in the resetting of the
        printer.  When read, this object will always have the value
        `notResetting(3)', and a SET of the value `notResetting' shall
        have no effect on the printer.  Some of the defined values are
        optional.  However, every implementation must support at least
        the values `notResetting' and 'resetToNVRAM'.
                Additional information:
                Setting this object to ePnotResetting causes the
                	   printer to not reset.

                Setting this object to ePpowerCycleReset causes this device
                to do a reset.

                Setting this object to 'resetToNVRAM' does NOT perform an NVRAM
                init on the product.  It causes the device to perform its power
                on initialization routines.  All I/O buffers are reset and tests
                normally run at power on time are executed.

                Setting the object to 'resetToFactoryDefaults, causes the
                device to perform its reset to factory defaults routines.
                Also, the device will perform a power cycle, which is required
                to set all variables to their factory defaults."
::= { prtGeneralEntry 3 }


prtGeneralCurrentOperator OBJECT-TYPE
    SYNTAX      OCTET STRING (SIZE(0..26))
    ACCESS      read-write
    STATUS      optional
       DESCRIPTION "The name of the person who is responsible for operating
          this printer. It is suggested that this string include
          information that would enable other humans to reach the operator,
          such as a phone number. As a convention to facilitate automatic
          notification of the operator by the agent or the network
          management station, the phone number, fax number or email address
          should be placed on a separate line starting with ASCII LF (hex
          0x0A) and the ASCII text string (without the quotes): 'phone: ',
          'fax: ', and 'email: ', respectively. Phone numbers may contain
          digits, whitespace and parentheses, which shall be ignored. Phone
          numbers may also include ASCII comma characters(hex 2C) that are
          used to indicate a two-second pause during the dialing sequence.
          If either the phone, fax, or email information is not available,
          then a line should not be included for this information.
          NOTE: For interoperability purposes, it is advisable to use email
          addresses formatted according to RFC 822 requirements.
                Additional information:
                The maximum supported string length is 26
                characters.

                If the user entered string is too long, the device will store
                as much as possible and will return the
                <noError> status."
::= { prtGeneralEntry 4 }


prtGeneralServicePerson OBJECT-TYPE
    SYNTAX      OCTET STRING (SIZE(0..28))
    ACCESS      read-write
    STATUS      optional
       DESCRIPTION "The name of the person responsible for servicing this
          printer. It is suggested that this string include information
          that would enable other humans to reach the service person, such
          as a phone number. As a convention to facilitate automatic
          notification of the service person by the agent or a network
          management station, the phone number, fax number or email address
          should be placed on a separate line starting with ASCII LF (hex
          0x0A) and the ASCII text string (without the quotes): 'phone: ',
          'fax: ', and 'email: ', respectively. Phone numbers may contain
          digits, whitespace and parentheses, which shall be ignored. Phone
          numbers can also include one or more ASCII comma characters(hex
          2C) to indicate a two-second pause during the dialing sequence.
          If either the phone,fax, or email information is not available,
          then a line should not included for this information.
          NOTE: For interoperability purposes, it is advisable to use email
          addresses formatted according to RFC 822 requirements.
                Additional information:
                The maximum supported string length is 28
                characters.

                If the user entered string is too long, the device will store
                as much as possible and will return the
                <noError> status."
::= { prtGeneralEntry 5 }


prtInputDefaultIndex OBJECT-TYPE
    SYNTAX      INTEGER
    ACCESS      read-only
    STATUS      optional
       DESCRIPTION "The value of prtInputIndex corresponding to the default input
        sub-unit: that is, this object selects the default source of
        input media.
   This value shall be -1 if there is no default input subunit specified
   for the printer as a whole.  In this case, the actual default
   input subunit may be specified by means outside the scope of this
   MIB, such as by each interpreter in a printer with multiple
   interpreters.
                Additional information:
                The default input tray is determined by the
                printer based on DEFAULT-MEDIA-SIZE, what trays are locked
                (if any), and whether or not Tray 2 is installed.

                This object always returns -1, unknown."
::= { prtGeneralEntry 6 }


prtOutputDefaultIndex OBJECT-TYPE
    SYNTAX      INTEGER
    ACCESS      read-only
    STATUS      optional
       DESCRIPTION "The  value of prtOutputIndex  corresponding to the default
        output sub-unit; that is, this object selects the default
        output destination.
   This value shall be -1 if there is no default output subunit specified
   for the printer as a whole.  In this case, the actual default
   output subunit may be specified by means outside the scope of this
   MIB, such as by each interpreter in a printer with multiple
   interpreters.
                Additional information:
                The product has only one output bin, a
                face-down bin located at the top of the printer."
::= { prtGeneralEntry 7 }


prtMarkerDefaultIndex OBJECT-TYPE
    SYNTAX      INTEGER(1..65535)
    ACCESS      read-only
    STATUS      optional
       DESCRIPTION "The value of prtMarkerIndex corresponding to the
        default marker sub-unit; that is, this object selects the
        default marker.
                Additional information:
                The product only has one marker subunit."
::= { prtGeneralEntry 8 }


prtMediaPathDefaultIndex OBJECT-TYPE
    SYNTAX      INTEGER(1..3)
    ACCESS      read-only
    STATUS      optional
       DESCRIPTION "The value of prtMediaPathIndex corresponding to
        the default media path; that is, the selection of the
        default media path.
                Additional information:
                The only valid value for this object is 1
                (simplex)."
::= { prtGeneralEntry 9 }


prtConsoleLocalization OBJECT-TYPE
    SYNTAX      INTEGER
    ACCESS      read-write
    STATUS      optional
       DESCRIPTION "The value of the prtLocalizationIndex corresponding to
        the language, country, and character set to be used for the
        console.  This localization applies both to the actual display
        on the console as well as the encoding of these console
        objects in management operations."
::= { prtGeneralEntry 10 }


prtConsoleNumberOfDisplayLines OBJECT-TYPE
    SYNTAX      INTEGER(0..65535)
    ACCESS      read-only
    STATUS      optional
       DESCRIPTION "The number of lines on the printer's physical
        display.  This value is 0 if there are no lines on the
        physical display or if there is no physical display."
::= { prtGeneralEntry 11 }


prtConsoleNumberOfDisplayChars OBJECT-TYPE
    SYNTAX      INTEGER(0..65535)
    ACCESS      read-only
    STATUS      optional
       DESCRIPTION "The number of characters per line displayed on the physical
        display.  This value is 0 if there are no lines on the
        physical display or if there is no physical display.
                Additional information:
                The device has a 16 character by 2 line display."
::= { prtGeneralEntry 12 }


prtConsoleDisable OBJECT-TYPE
    SYNTAX      INTEGER {
                          ePoperatorConsoleEnabled(3)
		   }
    ACCESS      read-only
    STATUS      optional
       DESCRIPTION "If the object prtConsoleDisable has value
          'operatorConsoleDisabled' then input is not accepted from the
          operator console. If the object prtConsoleDisable has the value
          'operatorConsoleEnabled' then input is accepted from the
          operator console. If the object prtConsoleDisable has the value
          'operatorConsoleEnabledLevel1','operatorConsoleEnabledLevel2' or
          'operatorConsoleEnabledLevel3' then limited input is accepted
          from the operator console; the limitations are product specific,
          however, the limitations are generally less restrictive for
          operatorConsoleEnabledLevel1 than for
          operatorConsoleEnabledLeve2, which is less restrictive than
          operatorConsoleEnabledLevel3.
          The value of the prtConsoleDisable object is a type-2
          enumeration."
::= { prtGeneralEntry 13 }


prtGeneralPrinterName OBJECT-TYPE
    SYNTAX      OCTET STRING (SIZE(0..32))
    ACCESS      read-write
    STATUS      optional
       DESCRIPTION "An administrator-specified name for this printer.
          Depending upon implementation of this printer, the value of this
          object may or may not be same as the value for the MIB-II
          'SysName' object.
                Additional information:
                The maximum supported string length is 32
                characters.  Length of 32 was chosen so a phone number could
                be included with the name.
                If the user-entered string is too long, the device will store
                as much as possible and will return the
                <noError> status.  The value of this
                object is saved over a power cycle."
::= { prtGeneralEntry 16 }


prtGeneralSerialNumber OBJECT-TYPE
    SYNTAX      OCTET STRING (SIZE(0..11))
    ACCESS      read-only
    STATUS      optional
       DESCRIPTION "A recorded serial number for this device that indexes some type
		 device catalog or inventory. This value is usually set by the
		 device manufacturer but the MIB supports the option of
		 writeability for this object for site-specific administration of
		 device inventory or tracking."
::= { prtGeneralEntry 17 }


prtAlertCriticalEvents OBJECT-TYPE
    SYNTAX      INTEGER
    ACCESS      read-only
    STATUS      optional
       DESCRIPTION "A running counter of the number of critical alert events
          that have been recorded in the alert table. The value of this
          object is RESET in the event of a power cycle operation (i.e.,
          the value is not persistent.
                Additional information:
                This object is set to zero every time the
                printer is turned on."
::= { prtGeneralEntry 18 }


prtAlertAllEvents OBJECT-TYPE
    SYNTAX      INTEGER
    ACCESS      read-only
    STATUS      optional
       DESCRIPTION "A running counter of the total number of alert event entries
     (critical and non-critical) that have been recorded in the
     alert table
                Additional information:
                This object is set to zero every time the
                printer is turned on.  (It is not persistent through a
                power-cycle.)"
::= { prtGeneralEntry 19 }


prtCoverDescription OBJECT-TYPE
    SYNTAX      OCTET STRING (SIZE(0..255))
    ACCESS      read-only
    STATUS      optional
       DESCRIPTION "The manufacturer provided cover sub-mechanism  name in the
        localization specified by prtGeneralCurrentLocalization."
::= { prtCoverEntry 2 }


prtCoverStatus OBJECT-TYPE
    SYNTAX      INTEGER {
                          ePdoorOpen(3),
                          ePdoorClosed(4)
		   }
    ACCESS      read-only
    STATUS      optional
       DESCRIPTION "The status of this cover sub-unit."
::= { prtCoverEntry 3 }


prtLocalizationLanguage OBJECT-TYPE
    SYNTAX      OCTET STRING (SIZE(0..2))
    ACCESS      read-only
    STATUS      optional
       DESCRIPTION "A two character language code from ISO 639.  Examples
          en, gb, ca, fr, de."
::= { prtLocalizationEntry 2 }


prtLocalizationCountry OBJECT-TYPE
    SYNTAX      OCTET STRING (SIZE(0..2))
    ACCESS      read-only
    STATUS      optional
       DESCRIPTION "A two character country code from ISO 3166, a blank string
        (two space characters) shall indicate that the country is
        not defined.  Examples: US, FR, DE, ..."
::= { prtLocalizationEntry 3 }


prtLocalizationCharacterSet OBJECT-TYPE
    SYNTAX      INTEGER {
                          ePcsHPRoman8(2004),
                          ePcsISOLatin2(5),
                          ePcsISOLatinCyrillic(8),
                          ePcsISOLatin5(12),
                          ePcsISOLatinGreek(10),
                          ePcsISOLatinHebrew(11),
                          ePcsISOLatinArabic(9),
                          ePcsUnicode(2000)
		   }
    ACCESS      read-only
    STATUS      optional
       DESCRIPTION "The coded character set used for this localization."
::= { prtLocalizationEntry 4 }


prtStorageRefIndex OBJECT-TYPE
    SYNTAX      INTEGER(1..65535)
    ACCESS      read-only
    STATUS      optional
       DESCRIPTION "The value of the hrDeviceIndex of the printer device that this
        storageEntry is associated with."
::= { prtStorageRefEntry 2 }


prtDeviceRefIndex OBJECT-TYPE
    SYNTAX      INTEGER(1..65535)
    ACCESS      read-only
    STATUS      optional
       DESCRIPTION "The value of the hrDeviceIndex of the printer device that this
        deviceEntry is associated with."
::= { prtDeviceRefEntry 2 }


prtInputType OBJECT-TYPE
    SYNTAX      INTEGER {
                          ePsheetFeedAutoRemovableTray(3),
                          ePsheetFeedAutoNonRemovableTray(4)
		   }
    ACCESS      read-only
    STATUS      optional
       DESCRIPTION "The type of technology (discriminated primarily according to
        feeder mechanism type) employed by the input sub-unit.  Note,
        the Optional Input Class provides for a descriptor field to
        further qualify the other choice.
                Additional information:
                Tray 1 is the multi-purpose tray and is always
                present.  It supports both sheets and envelopes.  Its type is
                ePsheetFeedAutoNonRemovableTray. The tray 3 object does not
                	   exist when the tray is NOT installed."
::= { prtInputEntry 2 }


prtInputDimUnit OBJECT-TYPE
    SYNTAX      INTEGER {
                          ePtenThousandthsOfInches(3),
                          ePmicrometers(4)
		   }
    ACCESS      read-only
    STATUS      optional
       DESCRIPTION "The unit of measurement for use calculating and relaying
         dimensional values for this input sub-unit.
                Additional information:
                Following is a table of paper sizes and
                dimensions for each paper size supported by
                the product:

                Size....................Inches(ten-thousandths)...Micrometers
                -----------------------------------------------------------------
                eUSExecutive............72500 x 105000............184150 x 266700
                eUSLetter...............85000 x 110000............215900 x 279400
                eUSLegal................85000 x 140000............215900 x 355600
                eFoolscap...............85000 x 130000............215900 x 330200
                eROC16K.................77500 x 107500............196850 x 273050
                eISOandJISA4............82677 x 116929............210000 x 297000
                eISOandJISA5............58286 x 82677.............148000 x 210000
                eJISB5..................71654 x 101181............182000 x 257000
                eIOSB5..................69300 x 98400.............176000 x 250000
                eJapanesePostcardSingle.39370 x 58267.............100000 x 148000
                eJapanesePostcardDouble.58267 x 78740.............148000 x 200000
                eMonarch................38750 x 75000.............98425  x 190500
                eCommercial10...........41250 x 95000.............104775 x 241300
                eInternationalDL........43307 x 86614.............110000 x 220000
                eInternationalC5........63780 x 90157.............162000 x 229000
                eInternationalB5........69291 x 98425.............176000 x 250000
                eCustom.................30000 x 140000(max).......76000 x 355600(max)"
::= { prtInputEntry 3 }


prtInputMediaDimFeedDirDeclared OBJECT-TYPE
    SYNTAX      INTEGER
    ACCESS      read-only
    STATUS      optional
       DESCRIPTION "This object provides the value of the declared dimension, in
        the feed direction, of the media that is (or, if empty, was or
        will be) in this input sub-unit.  The feed direction is the
        direction in which the media is fed on this sub-unit.  This
        dimension is measured in input sub-unit dimensional units
        (prtInputDimUnit).  If this input sub-unit can reliably sense
        this value, the value is sensed by the printer and may not be
        changed by management requests.  Otherwise, the value may be
        changed. The value (-1) means other and specifically means
        that this sub-unit places no restriction on this parameter.
        The value (-2) indicates unknown.
                Additional information:
                The default values assume the trays are
                configured for letter size paper.  For tray 1 the value is
                the dimension for the media size currently declared.

                Valid values are 50000 to 140000 if prtInputDimUnit is
                ePtenThousandthsOfInches and 127000 to 355600 if
                prtInputDimUnit is ePmicrometers."
::= { prtInputEntry 4 }


prtInputMediaDimXFeedDirDeclared OBJECT-TYPE
    SYNTAX      INTEGER
    ACCESS      read-only
    STATUS      optional
       DESCRIPTION "This object provides the value of the declared dimension, in
        the cross feed direction, of the media that is (or, if empty,
        was or will be) in this input sub-unit.  The cross  feed
        direction is ninety degrees relative to the feed direction
        associated with this sub-unit. This dimension is measured in
        input sub-unit dimensional units (prtInputDimUnit).  If this
        input sub-unit can reliably sense this value, the value is
        sensed by the printer and may not be changed by management
        requests. Otherwise, the value may be changed. The value (-1)
        means other and specifically means that this sub-unit places
        no restriction on this parameter. The value (-2) indicates
        unknown.
                Additional information:
                The default values assume the trays are
                configured for letter size paper.  For trays 1 & 2, the value
                is the dimension for the media size currently declared.

                Valid values are 30000 to 85000 if prtInputDimUnit is
                ePtenThousandthsOfInches and 76000 to 216000 if
                prtInputDimUnit is ePmicrometers.  The minimum
                value for tray 2 is 72500 (tenthousandsinch)
                and 191000(micrometers)."
::= { prtInputEntry 5 }


prtInputMediaDimFeedDirChosen OBJECT-TYPE
    SYNTAX      INTEGER
    ACCESS      read-only
    STATUS      optional
       DESCRIPTION "The printer will act as if media of the chosen dimension (in
        the feed direction) is present in this input source.  Note
        that this value will be used even if the input tray is empty.
        Feed dimension measurements are taken relative to the feed
        direction associated with that sub-unit and are in input sub-unit
        dimensional units (MediaUnit). If the printer supports the
        declared dimension, the granted dimension is the same as
        the declared dimension. If not, the granted dimension is
        set to the closest dimension that the printer supports
        when the declared dimension is set. The value (-1) means
        other and specifically indicates that this sub-unit
        places no restriction on this parameter. The value (-2)
        indicates unknown.
                Additional information:
                The default value assumes the trays are configured
                for letter size paper.  The objects for the trays
                return the value of the media size for which the trays
                are currently configured because it cannot sense what size
                media they contain."
::= { prtInputEntry 6 }


prtInputMediaDimXFeedDirChosen OBJECT-TYPE
    SYNTAX      INTEGER
    ACCESS      read-only
    STATUS      optional
       DESCRIPTION "The printer will act as if media of the chosen dimension (in
        the cross feed direction) is present in this input source.
        Note that this value will be used even if the input tray is
        empty.  The cross feed direction is ninety degrees relative
        to the feed direction associated with this sub-unit. This
        dimension is measured in input sub-unit dimensional units
        (MediaUnit).  If the printer supports the declared
        dimension, the granted dimension is the same as the
        declared dimension. If not, the granted dimension is set
        to the closest dimension that the printer supports when
        the declared dimension is set. The value (-1) means other
        and specifically indicates that this sub-unit places no
        restriction on this parameter.  The value (-2) indicates
        unknown.
                Additional information:
                The default value assumes the trays are configured
                for letter size paper.  The object for the trays
                return the value of the media size for which the trays
                are currently configured because it cannot sense what size
                media it contains."
::= { prtInputEntry 7 }


prtInputCapacityUnit OBJECT-TYPE
    SYNTAX      INTEGER {
                          ePsheets(8)
		   }
    ACCESS      read-only
    STATUS      optional
       DESCRIPTION "The unit of measurement for use in calculating and relaying
        capacity values for this input sub-unit.
                Additional information:
                A sheet is a single piece of 20 pound paper. "
::= { prtInputEntry 8 }


prtInputMaxCapacity OBJECT-TYPE
    SYNTAX      INTEGER
    ACCESS      read-only
    STATUS      optional
       DESCRIPTION "The maximum capacity of the input sub-unit in input
        sub-unit capacity units (PrtCapacityUnitTC).  There is no
        convention associated with the media itself so this value
        reflects claimed capacity. If this input sub-unit can
        reliably sense this value, the value is sensed by the
        printer and may not be changed by management requests;
        otherwise, the value may be written (by a Remote
        Control Panel or a Management Application).
        The value (-1) means other and specifically
        indicates that the sub-unit places no restrictions
        on this parameter.  The value (-2) means unknown.
                Additional information:
                This is specified assuming 20 pound paper for
                the paper trays."
::= { prtInputEntry 9 }


prtInputCurrentLevel OBJECT-TYPE
    SYNTAX      INTEGER
    ACCESS      read-only
    STATUS      optional
       DESCRIPTION "The current capacity of the input sub-unit in input
        sub-unit capacity units (PrtCapacityUnitTC). If this input
        sub-unit can reliably sense this value, the value is
        sensed by the printer and may not be changed by
        management requests; otherwise, the value may
        be written (by a Remote Contol Panel or a
        Management Application).  The value (-1) means other and
        specifically indicates that the sub-unit places no
        restrictions on this parameter. The value (-2) means unknown.
        The value (-3) means that the printer knows that at least one
        unit remains.
                Additional information:
                The product can only detect
                empty/not empty in its trays.  It returns -3 for not empty
                and -2 (unknown) for any other condition (e.g.  tray is empty
                or tray is removed)."
::= { prtInputEntry 10 }


prtInputStatus OBJECT-TYPE
    SYNTAX      INTEGER
    ACCESS      read-only
    STATUS      optional
       DESCRIPTION "The current status of this input sub-unit.
                Additional information:
                The default value assumes that media is loaded
                in the tray.  When there is not media loaded in the tray it
                returns 9 instead of 0 (the default).

                Default - 0 (Available and Idle)
                paper motion - 6 (Available and Busy)
                paper out in this tray - 9 (Non-Critical Alert(8) + Unavailable and OnRequest(1))
                paper mount in this tray - 48 (Critical Alert (16) + OffLine (32))
                manual feed prompt (PaperMount) - 48 (Critical Alert (16) + OffLine (32))"
::= { prtInputEntry 11 }


prtInputMediaName OBJECT-TYPE
    SYNTAX      OCTET STRING (SIZE(0..63))
    ACCESS      read-write
    STATUS      optional
       DESCRIPTION "A description of the media contained in this input sub-unit;
        This description is intended for display to a human operator.
        This description is not processed by the printer.  It is used
        to provide information not expressible in terms of the other
        media attributes (e.g. prtInputMediaDimFeedDirChosen,
        prtInputMediaDimXFeedDirChosen, prtInputMediaWeight,
        prtInputMediaType). An example would be `legal tender bond
        paper'.
                Additional information:
                The product supports the
                concept of named media types. The values for this
                			object will always match one of the MEDIAn-NAME objects."
::= { prtInputEntry 12 }


prtInputName OBJECT-TYPE
    SYNTAX      OCTET STRING (SIZE(0..63))
    ACCESS      read-only
    STATUS      optional
       DESCRIPTION "The name assigned to this input sub-unit."
::= { prtInputEntry 13 }


prtInputVendorName OBJECT-TYPE
    SYNTAX      OCTET STRING (SIZE(0..63))
    ACCESS      read-only
    STATUS      optional
       DESCRIPTION "The vendor name of this input sub-unit."
::= { prtInputEntry 14 }


prtInputModel OBJECT-TYPE
    SYNTAX      OCTET STRING (SIZE(0..63))
    ACCESS      read-only
    STATUS      optional
       DESCRIPTION "The model name of this input sub-unit.
                Additional information:
                The product does not specify model
                names for the input trays."
::= { prtInputEntry 15 }


prtInputVersion OBJECT-TYPE
    SYNTAX      OCTET STRING (SIZE(0..63))
    ACCESS      read-only
    STATUS      optional
       DESCRIPTION "The version of this input sub-unit.
                Additional information:
                The product does not specify version
                numbers for the input trays."
::= { prtInputEntry 16 }


prtInputSerialNumber OBJECT-TYPE
    SYNTAX      OCTET STRING (SIZE(0..63))
    ACCESS      read-only
    STATUS      optional
       DESCRIPTION "The serial number assigned to this input sub-unit.
                Additional information:
                The product does not specify serial
                numbers for the input trays."
::= { prtInputEntry 17 }


prtInputDescription OBJECT-TYPE
    SYNTAX      OCTET STRING (SIZE(0..255))
    ACCESS      read-only
    STATUS      optional
       DESCRIPTION "A free-form text description of this input
        sub-unit in the localization specified by
        prtGeneralCurrentLocalization."
::= { prtInputEntry 18 }


prtInputSecurity OBJECT-TYPE
    SYNTAX      INTEGER {
                          ePother(1),
                          ePon(3),
                          ePoff(4),
                          ePnotPresent(5)
		   }
    ACCESS      read-only
    STATUS      optional
       DESCRIPTION "Indicates if this input sub-unit has some security
        associated with it.
                Additional information:
                No security mechanism provided."
::= { prtInputEntry 19 }


prtOutputType OBJECT-TYPE
    SYNTAX      INTEGER {
                          ePother(1),
                          ePunknown(2),
                          ePremovableBin(3),
                          ePunRemovableBin(4),
                          ePcontinuousRollDevice(5),
                          ePmailBox(6),
                          ePcontinousFanFold(7)
		   }
    ACCESS      read-only
    STATUS      optional
       DESCRIPTION "The type of technology supported by this output sub-unit.
                Additional information:
                The product has only one output bin, a
                face-down bin located at the top of the printer."
::= { prtOutputEntry 2 }


prtOutputCapacityUnit OBJECT-TYPE
    SYNTAX      INTEGER {
                          ePtenThousandthsOfInches(3),
                          ePmicrometers(4),
                          ePsheets(8),
                          ePfeet(16),
                          ePmeters(17)
		   }
    ACCESS      read-only
    STATUS      optional
       DESCRIPTION "The unit of measurement for use in calculating and relaying
        capacity values for this output sub-unit.
                Additional information:
                A sheet is a single piece of 20 pound paper."
::= { prtOutputEntry 3 }


prtOutputMaxCapacity OBJECT-TYPE
    SYNTAX      INTEGER
    ACCESS      read-only
    STATUS      optional
       DESCRIPTION "The maximum capacity of this output sub-unit in output
        sub-unit capacity units (PrtCapacityUnitTC). There is no
        convention associated with the media itself so this value
        essentially reflects claimed capacity. If this output
        sub-unit can reliably sense this value, the value is
        sensed by the printer and may not be changed by management
        requests; otherwise, the value may be written
        (by a Remote Control Panel or a Management Application).
        The value (-1) means other and specifically indicates
        that the sub-unit places no restrictions on this parameter.
        The value (-2) means unknown.
                Additional information:
                Note:  The product cannot sense how
                much is in the output bin.  The output bin can hold 125
                sheets."
::= { prtOutputEntry 4 }


prtOutputRemainingCapacity OBJECT-TYPE
    SYNTAX      INTEGER
    ACCESS      read-only
    STATUS      optional
       DESCRIPTION "The remaining capacity of the possible output sub-unit
        capacity in output sub-unit capacity units (PrtCapacityUnitTC)
        of this output sub-unit. If this output sub-unit can
        reliably sense this value, the value is sensed by the
        printer and may not be modified by management requests;
        otherwise, the value may be written (by
        a Remote Control Panel or a Management
        Application).  The value (-1) means other and
        specifically indicates that the sub-unit places no
        restrictions on this parameter.  The value (-2) means
        unknown.  The value (-3) means that the printer knows that
        there remains capacity for at least one unit.
                Additional information:
                The product does not have any sensing
                on the output bin, so it will always report unknown (-2).
                Note that for the products, this object is read-only
                because any values written by a Remote Control Panel or a
                Management Application would be unreliable."
::= { prtOutputEntry 5 }


prtOutputStatus OBJECT-TYPE
    SYNTAX      INTEGER
    ACCESS      read-only
    STATUS      optional
       DESCRIPTION "The current status of this output sub-unit.
                Additional information:
                The product cannot sense the output
                tray so this object will always return 5 (Unknown Status)."
::= { prtOutputEntry 6 }


prtMarkerMarkTech OBJECT-TYPE
    SYNTAX      INTEGER {
                          ePelectrophotographicLaser(4)
		   }
    ACCESS      read-only
    STATUS      optional
       DESCRIPTION "The type of marking technology used for this marking sub-unit."
::= { prtMarkerEntry 2 }


prtMarkerCounterUnit OBJECT-TYPE
    SYNTAX      INTEGER {
                          ePimpressions(7)
		   }
    ACCESS      read-only
    STATUS      optional
       DESCRIPTION "The unit that will be used by the printer when reporting
        counter values for this marking sub-unit.  The
        time units of measure are provided for a device like a
        strip recorder that does not or cannot track the physical
        dimensions of the media and does not use characters,
        lines or sheets.
                Additional information:
                Since the product keeps track of pages
                printed, the counter unit will be defined as ePimpressions
                which would be like saying pages printed.  (The term
                'impressions' is used instead of 'pages' to avoid confusion
                between 'sheets' and 'pages' on a duplexing printer.)"
::= { prtMarkerEntry 3 }


prtMarkerLifeCount OBJECT-TYPE
    SYNTAX      INTEGER
    ACCESS      read-only
    STATUS      optional
       DESCRIPTION "The count of the number of units of measure counted during
        the life of printer using units of measure as specified by
        prtMarkerCounterUnit.
                Additional information:
                In the product, the total engine page
                count is kept in NVRAM, however the NVRAM value is only
                updated every 10 impressions.

                NOTE:  The value returned by this OID will be incremented
                every page but if power is lost between NVRAM updates, up to
                9 impressions of the page count may be lost.  The counter
                will be reset to zero after 999999 pages.

                The page count is incremented when a sheet of media is pulled
                from an input tray."
::= { prtMarkerEntry 4 }


prtMarkerPowerOnCount OBJECT-TYPE
    SYNTAX      INTEGER
    ACCESS      read-only
    STATUS      optional
       DESCRIPTION "The count of the number of units of measure counted since the
        equipment was most recently powered on using units of measure as
        specified by prtMarkerCounterUnit."
::= { prtMarkerEntry 5 }


prtMarkerProcessColorants OBJECT-TYPE
    SYNTAX      INTEGER(0..65535)
    ACCESS      read-only
    STATUS      optional
       DESCRIPTION "The number of process colors supported by this marker.  A
        process color of 1 implies monochrome.  The value of this
        object and prtMarkerSpotColorants cannot both be 0.  The value of
        prtMarkerProcessColorants must be 0 or greater."
::= { prtMarkerEntry 6 }


prtMarkerSpotColorants OBJECT-TYPE
    SYNTAX      INTEGER(0..65535)
    ACCESS      read-only
    STATUS      optional
       DESCRIPTION "The number of spot colors supported by this marker.  The
        value of this object and prtMarkerProcessColorants cannot
        both be 0.  Must be 0 or greater."
::= { prtMarkerEntry 7 }


prtMarkerAddressabilityUnit OBJECT-TYPE
    SYNTAX      INTEGER {
                          ePtenThousandthsOfInches(3)
		   }
    ACCESS      read-only
    STATUS      optional
       DESCRIPTION "The unit of measure of distances, as applied to the marker's
         resolution.
                Additional information:
                This will always be ePtenThousandthsOfInches, no
                matter what COLD-RESET-MEDIA-SIZE is because we are talking
                about resolution and toner addressability, which is always
                dpi."
::= { prtMarkerEntry 8 }


prtMarkerAddressabilityFeedDir OBJECT-TYPE
    SYNTAX      INTEGER
    ACCESS      read-only
    STATUS      optional
       DESCRIPTION "The maximum number of addressable marking positions in the feed
        direction per 10000 units of measure specified by
        prtMarkerAddressabilityUnit.  A value of (-1) implies 'other' or
        'infinite' while a value of (-2) implies 'unknown'.
                Additional information:
                Use this object to specify resolution.  The
                product supports 600 dots per inch."
::= { prtMarkerEntry 9 }


prtMarkerAddressabilityXFeedDir OBJECT-TYPE
    SYNTAX      INTEGER
    ACCESS      read-only
    STATUS      optional
       DESCRIPTION "The maximum number of addressable marking positions in the cross
        feed direction in 10000 units of measure specified by
        prtMarkerAddressabilityUnit.  A value of (-1) implies 'other' or
        'infinite' while a value of (-2) implies 'unknown'.
                Additional information:
                Use this object to specify resolution.  The
                product support 600 dots per inch."
::= { prtMarkerEntry 10 }


prtMarkerNorthMargin OBJECT-TYPE
    SYNTAX      INTEGER
    ACCESS      read-only
    STATUS      optional
       DESCRIPTION "The margin, in units identified by prtMarkerAddressabilityUnit,
        from the leading edge of the medium as the medium flows
        through the marking engine with the side to be imaged
        facing the observer. The leading edge is the North edge
        and the other edges are defined by the normal compass
        layout of  directions with the compass facing the
        observer.  Printing within the area bounded by all four
        margins is guaranteed for all interpreters.   The value
        (-2) means unknown."
::= { prtMarkerEntry 11 }


prtMarkerSouthMargin OBJECT-TYPE
    SYNTAX      INTEGER
    ACCESS      read-only
    STATUS      optional
       DESCRIPTION "The margin from the South edge  (see prtMarkerNorthMargin)
        of the medium in units identified by
        prtMarkerAddressabilityUnit.  Printing within the area bounded by
        all four margins  is guaranteed for all interpreters.
        The value (-2) means unknown."
::= { prtMarkerEntry 12 }


prtMarkerWestMargin OBJECT-TYPE
    SYNTAX      INTEGER
    ACCESS      read-only
    STATUS      optional
       DESCRIPTION "The margin from the West edge (see prtMarkerNorthMargin) of the
        medium in units identified by prtMarkerAddressabilityUnit.
        Printing within the area bounded by all four margins is
        guaranteed for all interpreters.   The value (-2) means
        unknown."
::= { prtMarkerEntry 13 }


prtMarkerEastMargin OBJECT-TYPE
    SYNTAX      INTEGER
    ACCESS      read-only
    STATUS      optional
       DESCRIPTION "The margin from the East edge (see prtMarkerNorthMargin) of the
        medium in units identified by prtMarkerAddressabilityUnit.
        Printing within the area bounded by all four margins is
        guaranteed for all interpreters. The value (-2) means
        unknown."
::= { prtMarkerEntry 14 }


prtMarkerStatus OBJECT-TYPE
    SYNTAX      INTEGER
    ACCESS      read-only
    STATUS      optional
       DESCRIPTION "The current status of this marker sub-unit.
                Additional information:
                The default value assumes the printer is idle
                and has no malfunctions.

                Default - 0 (Available and Idle)
                no toner cartridge - 51 (UnAvailable because Broken (3) + Critical Alert (16) + OffLine (32))"
::= { prtMarkerEntry 15 }


prtMarkerSuppliesMarkerIndex OBJECT-TYPE
    SYNTAX      INTEGER(0..65535)
    ACCESS      read-only
    STATUS      optional
       DESCRIPTION "The value of prtMarkerIndex corresponding to the
        marking sub-unit with which this marker supply
        sub-unit is associated."
::= { prtMarkerSuppliesEntry 2 }


prtMarkerSuppliesColorantIndex OBJECT-TYPE
    SYNTAX      INTEGER(0..65535)
    ACCESS      read-only
    STATUS      optional
       DESCRIPTION "The value of prtMarkerColorantIndex
        corresponding to the colorant with which this
        marker supply sub-unit is associated.  This value
        shall be 0 if there is no colorant table."
::= { prtMarkerSuppliesEntry 3 }


prtMarkerSuppliesClass OBJECT-TYPE
    SYNTAX      INTEGER {
                          ePother(1),
                          ePsupplyThatIsConsumed(3),
                          ePreceptacleThatIsFilled(4)
		   }
    ACCESS      read-only
    STATUS      optional
       DESCRIPTION "Indicates whether this supply entity represents a supply
        that is consumed or a receptacle that is filled."
::= { prtMarkerSuppliesEntry 4 }


prtMarkerSuppliesType OBJECT-TYPE
    SYNTAX      INTEGER {
                          ePtoner(3),
                          ePtransferUnit(20),
                          ePtonerCartridge(21),
                          ePfuser(15),
                          ePdeveloper(10),
                          ePfuserCleaingPad(19),
                          ePopc(9)
		   }
    ACCESS      read-only
    STATUS      optional
       DESCRIPTION "The type of this supply."
::= { prtMarkerSuppliesEntry 5 }


prtMarkerSuppliesDescription OBJECT-TYPE
    SYNTAX      OCTET STRING (SIZE(0..255))
    ACCESS      read-only
    STATUS      optional
       DESCRIPTION "The description of this supply container/receptacle in the
        localization specified by prtGeneralCurrentLocalization.
                Additional information:
                "
::= { prtMarkerSuppliesEntry 6 }


prtMarkerSuppliesSupplyUnit OBJECT-TYPE
    SYNTAX      INTEGER {
                          ePtenThousandthsOfInches(3),
                          ePmicrometers(4),
                          ePimpressions(7),
                          ePsheets(8),
                          ePthousandthsOfOunces(12),
                          ePhours(11),
                          ePtenthsOfGrams(13),
                          ePhundrethsOfFluidOunces(14),
                          ePtenthsOfMilliliters(15),
                          ePfeet(16),
                          ePmeters(17),
                          ePpercent(19)
		   }
    ACCESS      read-only
    STATUS      optional
       DESCRIPTION "Unit of measure of this marker supply container/receptacle."
::= { prtMarkerSuppliesEntry 7 }


prtMarkerSuppliesMaxCapacity OBJECT-TYPE
    SYNTAX      INTEGER
    ACCESS      read-only
    STATUS      optional
       DESCRIPTION "The maximum capacity of this supply container/receptacle
        expressed in prtMarkerSuppliesSupplyUnit. If this supply
        container/receptacle can reliably sense this value, the
        value is reported by the printer and is read-only;
        otherwise, the value may be written (by a Remote Control
        Panel or a Management Application). The value (-1) means
        other and specifically indicates that the sub-unit places
        no restrictions on this parameter. The value (-2) means
        unknown.
                Additional information:
                This object reports the rated life of the Print Cartridge
                based on tenths of grams of toner."
::= { prtMarkerSuppliesEntry 8 }


prtMarkerSuppliesLevel OBJECT-TYPE
    SYNTAX      INTEGER
    ACCESS      read-only
    STATUS      optional
       DESCRIPTION "The current level if this supply is a container; the
        remaining space if this supply is a receptacle. If this
        supply container/receptacle can reliably sense this
        value, the value is reported by the printer and is
        read-only; otherwise, the value may be written (by a
        Remote Control Panel or a Management Application). The
        value (-1) means other and specifically indicates that
        the sub-unit places no restrictions on this parameter.
        The value (-2) means unknown.  A value of (-3) means that the
        printer knows that there is some supply/remaining space,
        respectively.
                Additional information:
                Print Cartridges measure life based on the three
                components: toner, developer and drum.  These Print
                Cartridge objects (1..4) report the lowest of these
                three factors in units of tenths of grams.  Print
                Cartridges that are not installed will return a value
                of 100."
::= { prtMarkerSuppliesEntry 9 }


prtMarkerColorantMarkerIndex OBJECT-TYPE
    SYNTAX      INTEGER(0..65535)
    ACCESS      read-only
    STATUS      optional
       DESCRIPTION "The value of prtMarkerIndex corresponding to the
        marker sub-unit with which this colorant entry is
        associated."
::= { prtMarkerColorantEntry 2 }


prtMarkerColorantRole OBJECT-TYPE
    SYNTAX      INTEGER {
                          ePother(1),
                          ePprocess(3),
                          ePspot(4)
		   }
    ACCESS      read-only
    STATUS      optional
       DESCRIPTION "The role played by this colorant."
::= { prtMarkerColorantEntry 3 }


prtMarkerColorantValue OBJECT-TYPE
    SYNTAX      OCTET STRING (SIZE(0..255))
    ACCESS      read-only
    STATUS      optional
       DESCRIPTION "The name of the color of this
        colorant using standardized string names from ISO 10175 (DPA)
        and ISO 10180 (SPDL) which are:
          other
          unknown
          white
          red
          green
          blue
          cyan
          magenta
          yellow
          black
        Implementors may add additional string values. The naming
        conventions in ISO 9070 are recommended in order to avoid
        potential name clashes.
                Additional information:
                "
::= { prtMarkerColorantEntry 4 }


prtMarkerColorantTonality OBJECT-TYPE
    SYNTAX      INTEGER
    ACCESS      read-only
    STATUS      optional
       DESCRIPTION "The distinct levels of tonality realizable by a marking
        sub-unit when using this colorant.  This value does not
        include the number of levels of tonal difference that an
        interpreter can obtain by techniques such as half toning.
        This value must be at least 2."
::= { prtMarkerColorantEntry 5 }


prtMediaPathMaxSpeedPrintUnit OBJECT-TYPE
    SYNTAX      INTEGER {
                          ePimpressionsPerHour(7)
		   }
    ACCESS      read-only
    STATUS      optional
       DESCRIPTION "The unit of measure used in specifying the speed of all media
        paths in the printer.
                Additional information:
                ePimpressionsPerHour is the value that will
                always be returned for this object.  (Print Speed is measured
                in pages-per-minute (impressions per minute), so
                ePimpressionsPerHour is a natural extension.)"
::= { prtMediaPathEntry 2 }


prtMediaPathMediaSizeUnit OBJECT-TYPE
    SYNTAX      INTEGER {
                          ePtenThousandthsOfInches(3),
                          ePmicrometers(4)
		   }
    ACCESS      read-only
    STATUS      optional
       DESCRIPTION "The units of measure of media size for use in calculating and
        relaying dimensional values for all media paths in the printer."
::= { prtMediaPathEntry 3 }


prtMediaPathMaxSpeed OBJECT-TYPE
    SYNTAX      INTEGER
    ACCESS      read-only
    STATUS      optional
       DESCRIPTION "The maximum printing speed of this media path expressed in
        prtMediaPathMaxSpeedUnit's.  A value of (-1) implies
        'other'.
                Additional information:
                The page size for this performance is 8.5 x 11. For
                	    the product, this value is (20ppm * 60)."
::= { prtMediaPathEntry 4 }


prtMediaPathMaxMediaFeedDir OBJECT-TYPE
    SYNTAX      INTEGER
    ACCESS      read-only
    STATUS      optional
       DESCRIPTION "The maximum physical media size in the feed direction of this
        media path expressed in units of measure specified by
        PrtMediaPathMediaSizeUnit.  A value of (-1) implies 'unlimited',
        a value of (-2) implies 'unknown'.
                Additional information:
                The value returned by this object depends on the
                value of prtMediaPathMediaSizeUnit.  It is 140000 if
                prtInputDimUnit is ePtenThousandthsOfInches or 355600 if
                prtInputDimUnit is ePmicrometers.  (140000 is the value
                arrived at because legal paper is the longest allowable on
                the product.)"
::= { prtMediaPathEntry 5 }


prtMediaPathMaxMediaXFeedDir OBJECT-TYPE
    SYNTAX      INTEGER
    ACCESS      read-only
    STATUS      optional
       DESCRIPTION "The maximum physical media size across the feed direction of
        this media path expressed in units of measure specified by
        prtMediaPathMediaSizeUnit.  A value of (-2) implies 'unknown'.
                Additional information:
                The value returned by this object depends on the
                value of prtMediaPathMediaSizeUnit.  It is 85000 if
                prtInputDimUnit is ePtenThousandthsOfInches or 216000 if
                prtInputDimUnit is ePmicrometers."
::= { prtMediaPathEntry 6 }


prtMediaPathMinMediaFeedDir OBJECT-TYPE
    SYNTAX      INTEGER
    ACCESS      read-only
    STATUS      optional
       DESCRIPTION "The minimum physical media size in the feed direction of this
        media path expressed in units of measure specified by
        prtMediaPathMediaSizeUnit. A value of (-2) implies 'unknown'.
                Additional information:
                The value returned by this object depends on the
                value of prtMediaPathMediaSizeUnit.  It is 50000 if
                prtInputDimUnit is ePtenThousandthsOfInches or 127000 if
                prtInputDimUnit is ePmicrometers."
::= { prtMediaPathEntry 7 }


prtMediaPathMinMediaXFeedDir OBJECT-TYPE
    SYNTAX      INTEGER
    ACCESS      read-only
    STATUS      optional
       DESCRIPTION "The minimum physical media size across the feed direction of
        this media path expressed in units of measure specified by
        prtMediaPathMediaSizeUnit.  A value of (-2) implies 'unknown'.
                Additional information:
                The value returned by this object depends on the
                value of prtMediaPathMediaSizeUnit.  It is 30000 if
                prtInputDimUnit is ePtenThousandthsOfInches or 76200 if
                prtInputDimUnit is ePmicrometers.  This size corresponds to a
                Monarch envelope.  "
::= { prtMediaPathEntry 8 }


prtMediaPathType OBJECT-TYPE
    SYNTAX      INTEGER {
                          ePsimplex(5)
		   }
    ACCESS      read-only
    STATUS      optional
       DESCRIPTION "The type of the media path for this media path.
                Additional information:
                This object describes how many paths there are
                through the engine disregarding the paper source (tray 1, 2,
                or 3)."
::= { prtMediaPathEntry 9 }


prtMediaPathDescription OBJECT-TYPE
    SYNTAX      OCTET STRING (SIZE(0..255))
    ACCESS      read-only
    STATUS      optional
       DESCRIPTION "The manufacturer-provided description of this media path in
        the localization specified by prtGeneralCurrentLocalization."
::= { prtMediaPathEntry 10 }


prtMediaPathStatus OBJECT-TYPE
    SYNTAX      INTEGER
    ACCESS      read-only
    STATUS      optional
       DESCRIPTION "The current status of this media path.
                Additional information:
                The default values assume the printer is idle.

                Default - 0 (Available and Idle)
                paper motion - 6 (Available and Busy)
                paper out in all trays - 9 (Non-Critical Alert(8) + Unavailable and OnRequest(1))
                paper mount (any tray) - 0 (Available and Idle)
                manual feed prompt (PaperMount) - 48 (Critical Alert (16) + OffLine (32))"
::= { prtMediaPathEntry 11 }


prtInterpreterLangFamily OBJECT-TYPE
    SYNTAX      INTEGER {
                          ePother(1),
                          ePlangPCL(3),
                          ePlangPJL(5),
                          ePlangPS(6),
                          ePlangAutomatic(37),
                          ePlangPCLXL(47)
		   }
    ACCESS      read-only
    STATUS      optional
       DESCRIPTION "The family name of a Page Description Language (PDL) or
        control language which this interpreter in the printer can
		interpret or emulate.
                Additional information:
                ePlangAutomatic refers to the 'super-language'
                made available by implicit language switching."
::= { prtInterpreterEntry 2 }


prtInterpreterLangLevel OBJECT-TYPE
    SYNTAX      OCTET STRING (SIZE(0..31))
    ACCESS      read-only
    STATUS      optional
       DESCRIPTION "The level of the language which this interpreter is
        interpreting or emulating.  This might contain a value like
        '5e' for an interpreter which is emulating level 5e of the PCL
        language.  It might contain '2' for an interpreter which is
        emulating level 2 of the PostScript language.  Similarly it
        might contain '2' for an interpreter which is emulating level
        2 of the HPGL language."
::= { prtInterpreterEntry 3 }


prtInterpreterLangVersion OBJECT-TYPE
    SYNTAX      OCTET STRING (SIZE(0..31))
    ACCESS      read-only
    STATUS      optional
       DESCRIPTION "The date code or version of the language which this interpreter
        is interpreting or emulating.
                Additional information:
                These values are derived from the dateCode field
                of the personality entities.  (ePlangautomatic uses the PJL
                dateCode.)  For PostScript, this is more detailed revision
                information."
::= { prtInterpreterEntry 4 }


prtInterpreterDescription OBJECT-TYPE
    SYNTAX      OCTET STRING (SIZE(0..255))
    ACCESS      read-only
    STATUS      optional
       DESCRIPTION "A string to identify this interpreter in the localization
        specified by prtGeneralCurrentLocalization as opposed to the
        language which is being interpreted.  It is anticipated that
        this string will allow manufacturers to unambiguously identify
        their interpreters.
                Additional information:
                None of these strings are localized."
::= { prtInterpreterEntry 5 }


prtInterpreterVersion OBJECT-TYPE
    SYNTAX      OCTET STRING (SIZE(0..31))
    ACCESS      read-only
    STATUS      optional
       DESCRIPTION "The date code, version number, or other product specific
        information tied to this interpreter.  This value is
        associated with the interpreter, rather than with the version
        of the language which is being interpreted or emulated.
                Additional information:
                Same as prtInterpreterLangVersion."
::= { prtInterpreterEntry 6 }


prtInterpreterDefaultOrientation OBJECT-TYPE
    SYNTAX      INTEGER {
                          ePportrait(3),
                          ePlandscape(4)
		   }
    ACCESS      read-write
    STATUS      optional
       DESCRIPTION "The current orientation default for this interpreter.  This
        value may be overridden for a particular job (e.g., by a
        command in the input data stream).
                Additional information:
                Interpreters 1 and 2 ignore the value of this
                object.

                The values for PCL and PostScript are either ePportrait or
                ePlandscape; attempting to set them to a different value will
                cause <badValue> to be returned.
                Setting this object for one interpreter will change it for
                all installed interpreters."
::= { prtInterpreterEntry 7 }


prtInterpreterFeedAddressability OBJECT-TYPE
    SYNTAX      INTEGER
    ACCESS      read-only
    STATUS      optional
       DESCRIPTION "The maximum interpreter addressability in the feed
        direction in 10000 prtMarkerAddressabilityUnits (see
        prtMarkerAddressabilityFeedDir ) for this interpreter.
        The value (-1) means other and specifically indicates
        that the sub-unit places no restrictions on this parameter."
::= { prtInterpreterEntry 8 }


prtInterpreterXFeedAddressability OBJECT-TYPE
    SYNTAX      INTEGER
    ACCESS      read-only
    STATUS      optional
       DESCRIPTION "The maximum interpreter addressability in the cross feed
        direction in 10000 prtMarkerAddressabilityUnits (see
        prtMarkerAddressabilityXFeedDir) for this interpreter.
        The value (-1) means other and specifically indicates
        that the sub-unit places no restrictions on this
        parameter."
::= { prtInterpreterEntry 9 }


prtInterpreterDefaultCharSetIn OBJECT-TYPE
    SYNTAX      INTEGER {
                          ePother(1),
                          ePcsASCII(3),
                          ePcsISOLatin1(4),
                          ePcsISOLatin2(5),
                          ePcsISOLatin5(12),
                          ePcsISOLatin6(13),
                          ePcsISOLatin9(2090),
                          ePcsISO4UnitedKingdom(20),
                          ePcsISO11SwedishforNames(21),
                          ePcsISO15Italian(22),
                          ePcsISO17Spanish(23),
                          ePcsISO21German(24),
                          ePcsISO60DanishNorwegian(25),
                          ePcsISO69French(26),
                          ePcsUnicodeIBM2039(1004),
                          ePcsWindows30Latin1(2000),
                          ePcsWindows31Latin1(2001),
                          ePcsWindows31Latin2(2002),
                          ePcsWindows31Latin5(2003),
                          ePcsHPRoman8(2004),
                          ePcsAdobeStandardEncoding(2005),
                          ePcsPC850Multilingual(2009),
                          ePcsPC858Multilingual(2089),
                          ePcsPCp852(2010),
                          ePcsPC8CodePage437(2011),
                          ePcsPC8DNDanishNorwegian(2012),
                          ePcsHPPC8Turkish(2014),
                          ePcsHPLegal(2017),
                          ePcsHPDeskTop(2021),
                          ePcsMacintosh(2027),
                          ePcsPC77Baltic(2087),
                          ePcsWindows1257Baltic(2257)
		   }
    ACCESS      read-write
    STATUS      optional
       DESCRIPTION "The default coded character set for input octets
        encountered outside a context in which the Page
        Description Language established the interpretation
        of the octets. (Input octets are presented to the
        interpreter through a path defined in the channel group.)
        This value shall be (2) if there is no default.
                Additional information:
                ePcsAdobeStandardEncoding is the same as PSText(10J).

                The object corresponding to PCL has read-write access;
                all others are read-only.

                Note: To determine which languages correspond to which subarrays refer
                to the object prtInterpreterLangFamily.

                The above list corresponds to the following symbol sets as they appear
                on the Control Panel:

                ePother( 1) - used if designated coded char. set not in list
                ePcsASCII( 3) - ISO-6
                ePcsISOLatin1( 4) - ISO L1
                ePcsISOLatin2( 5) - IS L2
                ePcsISOLatin5( 12) - ISO L5
                ePcsISOLatin6( 13) - ISO L6
                ePcsISOLatin9( 2090) - ISO L9
                ePcsISO4UnitedKingdom( 20) - ISO-4
                ePcsISO11SwedishforNames( 21) - ISO-11
                ePcsISO15Italian( 22) - ISO-15
                ePcsISO17Spanish( 23) - ISO-17
                ePcsISO21German( 24) - ISO-21
                ePcsISO60DanishNorwegian( 25) - ISO-60
                ePcsISO69French( 26) - ISO-69
                ePcsUnicodeIBM2039(1004) - PC-1004
                ePcsWindows30Latin1( 2000) - WIN 3.0
                ePcsWindows31Latin1( 2001) - WIN L1
                ePcsWindows31Latin2( 2002) - WIN L2
                ePcsWindows31Latin5( 2003) - WIN L5
                ePcsHPRoman8( 2004) - ROMAN-8
                ePcsAdobeStandardEncoding( 2005) - PS TEXT
                ePcsPC850Multilingual( 2009) - PC-850
                ePcsPC858Multilingual( 2089) - PC-858
                ePcsPCp852( 2010) - PC-852
                ePcsPC8CodePage437( 2011) - PC-8
                ePcsPC8DNDanishNorwegian( 2012) - PC-8DN
                ePcsHPPC8Turkish( 2014) - PC-8 TK
                ePcsHPLegal( 2017) - LEGAL
                ePcsHPDeskTop( 2021) - DESKTOP
                ePcsMacintosh( 2027) - MC TEXT
                ePcsPC77Baltic( 2087) - PC-775
                ePcsWindows1257Baltic( 2257) - WINBALT"
::= { prtInterpreterEntry 10 }


prtInterpreterDefaultCharSetOut OBJECT-TYPE
    SYNTAX      INTEGER {
                          ePcsNoDefault(2),
                          ePcsASCII(3),
                          ePcsHPRoman8(2004),
                          ePcsAdobeStandardEncoding(2005)
		   }
    ACCESS      read-only
    STATUS      optional
       DESCRIPTION "The default character set for data coming from this interpreter
        through the printer's output channel (i.e. the 'backchannel').
        This value shall be (2) if there is no default."
::= { prtInterpreterEntry 11 }


prtInterpreterTwoWay OBJECT-TYPE
    SYNTAX      INTEGER {
                          ePyes(3),
                          ePno(4)
		   }
    ACCESS      read-only
    STATUS      optional
       DESCRIPTION "Indicates whether or not this interpreter returns information
        back to the host."
::= { prtInterpreterEntry 12 }


prtConsoleDisplayBufferText OBJECT-TYPE
    SYNTAX      OCTET STRING (SIZE(0..255))
    ACCESS      read-only
    STATUS      optional
       DESCRIPTION "The content of a line in the logical display buffer of
        the operator's console of the printer.  When a write
        operation occurs, normally a critical message, to one of
        the LineText strings, the agent should make that line
        displayable if a physical display is present.  Writing
        a zero length string clears the line.  It is an
        implementation-specific matter as to whether the agent allows
        a line to be overwritten before it has been cleared.
        Printer generated strings shall be in the localization
        specified by prtConsoleLocalization.  Management Application
        generated strings should be localized by the Management
        Application.
                Additional information:
                In the case of a 2-line display message,
                prtConsoleDisplayBufferText.1 maps to the first
                line and prtConsoleDisplayBufferText.2 maps to
                the second.  In the case of a 1-line display
                message, prtConsoleDisplayBufferText.1 maps to
                the first line and prtConsoleDisplayBufferText.2
                return NULL."
::= { prtConsoleDisplayBufferEntry 2 }


prtConsoleOnTime OBJECT-TYPE
    SYNTAX      INTEGER
    ACCESS      read-only
    STATUS      optional
       DESCRIPTION "This object, in conjunction with prtConsoleOffTime, defines
        the current status of the light.  If both prtConsoleOnTime and
        prtConsoleOffTime are non-zero, the lamp is blinking and the
        values presented define the on time and off time, respectively,
        in milliseconds.  If prtConsoleOnTime is zero and
        prtConsoleOffTime is non-zero, the lamp is off.  If
        prtConsoleOffTime is zero and prtConsoleOnTime is non-zero,
        the lamp is on.  If both values are zero the status of the
        lamp is undefined.
                Additional information:
                There are two control panel LEDs: Attention
                and Ready.   When an LED blinks, it is on for one half
                second and off for one half second.  The value used for this
                object is 500 when the LED is on or blinking, otherwise it is
                zero.

                When the LEDs are in a cycling state the value of this object
                for all LEDs is zero and the value for prtConsoleOffTime for
                all LEDs is zero."
::= { prtConsoleLightEntry 2 }


prtConsoleOffTime OBJECT-TYPE
    SYNTAX      INTEGER
    ACCESS      read-only
    STATUS      optional
       DESCRIPTION "This object, in conjunction with prtConsoleOnTime, defines
        the current status of the light.  If both prtConsoleOnTime and
        prtConsoleOffTime are non-zero, the lamp is blinking and the
        values presented define the on time and off time, respectively,
        in milliseconds.  If prtConsoleOnTime is zero and
        prtConsoleOffTime is non-zero, the lamp is off.  If
        prtConsoleOffTime is zero and prtConsoleOnTime is non-zero,
        the lamp is on.  If both values are zero the status of the
        lamp is undefined.
                Additional information:
                There are 2 control panel LEDs: Attention
                and Ready.  When an LED blinks, it is on for one half
                second and off for one half second.  The value used for this
                object is 500 when the LED is off or blinking, otherwise it
                is
                zero.

                When the LEDs are in a cycling state the value of this object
                for all LEDs is zero and the value for prtConsoleOnTime for
                all LEDs is zero."
::= { prtConsoleLightEntry 3 }


prtConsoleColor OBJECT-TYPE
    SYNTAX      INTEGER {
                          ePother(1),
                          ePunknown(2),
                          ePwhite(3),
                          ePred(4),
                          ePgreen(5),
                          ePblue(6),
                          ePcyan(7),
                          ePmagenta(8),
                          ePyellow(9),
                          ePorange(10)
		   }
    ACCESS      read-only
    STATUS      optional
       DESCRIPTION "The color of this light."
::= { prtConsoleLightEntry 4 }


prtConsoleDescription OBJECT-TYPE
    SYNTAX      OCTET STRING (SIZE(0..255))
    ACCESS      read-only
    STATUS      optional
       DESCRIPTION "The vendor description or label of this light in the
        localization specified by prtConsoleLocalization."
::= { prtConsoleLightEntry 5 }


END
