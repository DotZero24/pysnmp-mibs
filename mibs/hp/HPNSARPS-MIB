-- ****************************************************************************
-- HP NSA RPS MIB
-- March 19, 1996
--
-- Copyright Hewlett-Packard Company 1994-1996
-- All rights reserved.
--
-- The information in this document is subject to change without notice.
--
-- The HP enterprise number is 11. The ASN.1 prefix to, and including,
-- the HP enterprise ID is 1.3.6.1.4.1.11.
--

HPNSARPS-MIB DEFINITIONS ::= BEGIN
   IMPORTS
      enterprises    FROM RFC1155-SMI
      DisplayString  FROM RFC1213-MIB
      OBJECT-TYPE    FROM RFC-1212;

   hp                  OBJECT IDENTIFIER ::= { enterprises 11 }
   nm                  OBJECT IDENTIFIER ::= { hp 2 }
   hpnsa               OBJECT IDENTIFIER ::= { nm 23 }
   hpnsaRPS            OBJECT IDENTIFIER ::= { hpnsa 22 }
   hpnsaRPSMibRev      OBJECT IDENTIFIER ::= { hpnsaRPS 1 }

-- *************************************************************************
-- HP NSA RPS MIB
-- ===================================
--
-- hp                                           (1.3.6.1.4.1.11)
--    nm                                        (hp.2)
--       hpnsa                                  (nm.23)
--          hpnsaRPS Group                      (hpnsa.22)
--             hpnsaRPSMibRev Group             (hpnsa.22.1)
--                hpnsaRPSMibRevMajor           (hpnsa.22.1.1)
--                hpnsaRPSMibRevMinor           (hpnsa.22.1.2)
--
-- Implementation of the MibRev group is mandatory for all HPNSA Agents
-- supporting the HP RPS MIB.
--
-- An HPNSA Agent conforming to this document will return a
-- hpnsaRPSMibRevMajor of 1 and a hpnsaRPSMibRevMinor of 0.
--
-- *************************************************************************

   hpnsaRPSMibRevMajor OBJECT-TYPE
      SYNTAX INTEGER (1..65535)
      ACCESS read-only
      STATUS mandatory
      DESCRIPTION
	 "The major revision level of the MIB."
   ::= { hpnsaRPSMibRev 1 }

   hpnsaRPSMibRevMinor OBJECT-TYPE
      SYNTAX INTEGER (0..65535)
      ACCESS read-only
      STATUS mandatory
      DESCRIPTION
	 "The minor revision level of the MIB."
   ::= { hpnsaRPSMibRev 2 }
END
