LEFTHAND-NETWORKS-NUS-COMMON-NTP-MIB DEFINITIONS ::= BEGIN

-- IMPORTS: Include definitions from other mibs here, which is always
-- the first item in a MIB file.
IMPORTS
	MODULE-IDENTITY, OBJECT-TYPE, IpAddress FROM SNMPv2-SMI
	RowStatus, TruthValue                      FROM SNMPv2-TC
	lhnModules                                 FROM LEFTHAND-NETWORKS-GLOBAL-REG
	lhnNusCommonNTP                            FROM LEFTHAND-NETWORKS-NUS-COMMON-MIB;

--
-- A brief description and update information about this mib.
--
lhnNusCommonNTPModule MODULE-IDENTITY
    LAST-UPDATED "0106010000Z"
	 ORGANIZATION "LeftHand Networks, Inc."
    CONTACT-INFO "
                  Author:     Jose Faria
                              LeftHand Networks
                  postal:     6185 Arapahoe Rd.
                              Boulder, CO 80301
                              USA
                  email:      jfaria@lefthandnetworks.com
                  phone:      +1 303 449-4100
                 "
    DESCRIPTION  "NTP items for NUS Devices"
    ::= { lhnModules 7 }

-- *********************************************************************************
--
-- NTP Module Objects
--
-- *********************************************************************************

ntpCount OBJECT-TYPE
    SYNTAX           INTEGER
    MAX-ACCESS       read-only
    STATUS           current
    DESCRIPTION      "count of NTP settings"
    ::= { lhnNusCommonNTP 1 }

ntpTable OBJECT-TYPE
    SYNTAX           SEQUENCE OF NtpEntry
    MAX-ACCESS       not-accessible
    STATUS           current
    DESCRIPTION      "Table of NTP settings for NUS"
    ::= { lhnNusCommonNTP 2 }

ntpStart OBJECT-TYPE
    SYNTAX           TruthValue
    MAX-ACCESS       read-write
    STATUS           current
    DESCRIPTION      "start NTP when set to true"
    ::= { lhnNusCommonNTP 3 }

ntpStop OBJECT-TYPE
    SYNTAX           TruthValue
    MAX-ACCESS       read-write
    STATUS           current
    DESCRIPTION      "stop NTP when set to true"
    ::= { lhnNusCommonNTP 4 }

ntpRestart OBJECT-TYPE
    SYNTAX           TruthValue
    MAX-ACCESS       read-write
    STATUS           current
    DESCRIPTION      "restart NTP when set to true"
    ::= { lhnNusCommonNTP 5 }

ntpCheck OBJECT-TYPE
    SYNTAX           TruthValue
    MAX-ACCESS       read-write
    STATUS           current
    DESCRIPTION      "check NTP when set to true"
    ::= { lhnNusCommonNTP 6 }

timeGMTTime OBJECT-TYPE
    SYNTAX      OCTET STRING
    MAX-ACCESS  read-write
    STATUS      current
    DESCRIPTION "GMT Time"
    ::= { lhnNusCommonNTP 7 }

timeTimeZone OBJECT-TYPE
    SYNTAX      OCTET STRING
    MAX-ACCESS  read-write
    STATUS      current
    DESCRIPTION "Local Time Zone"
    ::= { lhnNusCommonNTP 8 }

ntpEntry OBJECT-TYPE
    SYNTAX           NtpEntry
    MAX-ACCESS       not-accessible
    STATUS           current
    DESCRIPTION      "row of NTP settings"
    INDEX            { ntpIndex }
    ::= { ntpTable 1 }

NtpEntry ::= SEQUENCE
{
    ntpIndex        INTEGER,
    ntpPreferred    TruthValue,
    ntpServer       OCTET STRING,
    ntpRowStatus    RowStatus
}

ntpIndex OBJECT-TYPE
    SYNTAX          INTEGER
    MAX-ACCESS      read-create
    STATUS          current
    DESCRIPTION     "index to NTP Table"
    ::= { ntpEntry 1 }

ntpPreferred OBJECT-TYPE
    SYNTAX          TruthValue
    MAX-ACCESS      read-write
    STATUS          current
    DESCRIPTION     "true if preferred, false otherwise"
    ::= { ntpEntry 2 }

ntpServer OBJECT-TYPE
    SYNTAX           OCTET STRING
    MAX-ACCESS       read-write
    STATUS           current
    DESCRIPTION      "server name or ip address for a NTP entry"
    ::= { ntpEntry 3 }

ntpRowStatus OBJECT-TYPE
    SYNTAX      RowStatus
    MAX-ACCESS  read-create
    STATUS      current
    DESCRIPTION "The row status"
    ::= { ntpEntry 4 }

END
