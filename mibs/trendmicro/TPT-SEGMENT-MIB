-- - - - - - - - - - - - - - - - - - - - - - - - - - - - - - - - - - - - - - -
--
-- Trend Micro, Inc.
-- Copyright information is in the DESCRIPTION section of the MODULE-IDENTITY.
--
-- - - - - - - - - - - - - - - - - - - - - - - - - - - - - - - - - - - - - - -

TPT-SEGMENT-MIB

DEFINITIONS ::= BEGIN

IMPORTS
  MODULE-IDENTITY, OBJECT-TYPE, Unsigned32
    FROM SNMPv2-SMI

  TEXTUAL-CONVENTION
    FROM SNMPv2-TC

  tpt-tpa-objs
    FROM TPT-TPAMIBS-MIB
  ;

tpt-segment-objs MODULE-IDENTITY
  LAST-UPDATED "201605251854Z" -- May 25, 2016
  ORGANIZATION "Trend Micro, Inc."
  CONTACT-INFO "www.trendmicro.com"
  DESCRIPTION
    "Details of segments on the device.

     Copyright (C) 2016 Trend Micro Incorporated. All Rights Reserved.

     Trend Micro makes no warranty of any kind with regard to this material,
     including, but not limited to, the implied warranties of merchantability
     and fitness for a particular purpose. Trend Micro shall not be liable for
     errors contained herein or for incidental or consequential damages in
     connection with the furnishing, performance, or use of this material. This
     document contains proprietary information, which is protected by copyright. No
     part of this document may be photocopied, reproduced, or translated into
     another language without the prior written consent of Trend Micro. The
     information is provided 'as is' without warranty of any kind and is subject to
     change without notice. The only warranties for Trend Micro products and
     services are set forth in the express warranty statements accompanying such
     products and services. Nothing herein should be construed as constituting an
     additional warranty. Trend Micro shall not be liable for technical or editorial
     errors or omissions contained herein. TippingPoint(R), the TippingPoint logo, and
     Digital Vaccine(R) are registered trademarks of Trend Micro. All other company
     and product names may be trademarks of their respective holders. All rights
     reserved. This document contains confidential information, trade secrets or
     both, which are the property of Trend Micro. No part of this documentation may
     be reproduced in any form or by any means or used to make any derivative work
     (such as translation, transformation, or adaptation) without written permission
     from Trend Micro or one of its subsidiaries. All other company and product
     names may be trademarks of their respective holders.
    "

  REVISION "201605251854Z" -- May 25, 2016
  DESCRIPTION "Updated copyright information. Minor MIB syntax fixes."

  ::= { tpt-tpa-objs 19 }

-- - - - - - - - - - - - - - - - - - - - - - - - - - - - - - - - - - - - - - -
--
-- Textual conventions for slot  MIB objects
--
-- - - - - - - - - - - - - - - - - - - - - - - - - - - - - - - - - - - - - - -

SegmentSflowStatus ::= TEXTUAL-CONVENTION
  STATUS      current
  DESCRIPTION
    "An indication of sFlow enable/disable/applicable status for a segment"
  SYNTAX      INTEGER { disable(0), enable(1),  error(2), not-applicable(3) }





-- - - - - - - - - - - - - - - - - - - - - - - - - - - - - - - - - - - - - - -
--
-- Segment level sFlow status and divisor value
--
-- - - - - - - - - - - - - - - - - - - - - - - - - - - - - - - - - - - - - - -

segmentTable OBJECT-TYPE
  SYNTAX      SEQUENCE OF SegmentEntry
  MAX-ACCESS  not-accessible
  STATUS      current
  DESCRIPTION
    "Table of segment-related information."
  ::= { tpt-segment-objs 1 }


segmentEntry OBJECT-TYPE
  SYNTAX      SegmentEntry
  MAX-ACCESS  not-accessible
  STATUS      current
  DESCRIPTION
    "An entry in the segment table.
     Rows cannot be created or deleted.
    "

  INDEX       { slotIndex, segmentIndex }
  ::= { segmentTable 1 }

SegmentEntry ::= SEQUENCE {
  slotIndex                  Unsigned32,
  segmentIndex               Unsigned32,
  segmentSflowStatus         SegmentSflowStatus,
  sFlowDivisor               Unsigned32
}

slotIndex OBJECT-TYPE
  SYNTAX      Unsigned32
  MAX-ACCESS  read-only
  STATUS      current
  DESCRIPTION
    "The slot index, starting with 1.
     For older platforms like N-platforms and Lowball,
     all the segments are assumed to be on slot 1.
    "
  ::= { segmentEntry 1 }

segmentIndex OBJECT-TYPE
  SYNTAX      Unsigned32
  MAX-ACCESS  read-only
  STATUS      current
  DESCRIPTION
    "The segment index, starting with 1."
  ::= { segmentEntry 2 }


segmentSflowStatus  OBJECT-TYPE
  SYNTAX      SegmentSflowStatus
  MAX-ACCESS  read-only
  STATUS      current
  DESCRIPTION
    "sFlow status of the segment.
     Not applicable on Lowball platforms (10/110/330).
     For those platforms, the value will be set to not-applicable.
    "
  ::= { segmentEntry 3 }

sFlowDivisor OBJECT-TYPE
  SYNTAX      Unsigned32
  MAX-ACCESS  read-only
  STATUS      current
  DESCRIPTION
    "The sFlow divisor value of the segment.
     Not applicable on the Lowball platforms (10/110/330).
     For those platforms, the value will be set to 0.
    "
  ::= { segmentEntry 4 }


END
