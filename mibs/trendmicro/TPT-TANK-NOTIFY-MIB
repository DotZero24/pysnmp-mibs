-- - - - - - - - - - - - - - - - - - - - - - - - - - - - - - - - - - - - - - -
--
-- Trend Micro, Inc.
-- Copyright information is in the DESCRIPTION section of the MODULE-IDENTITY.
--
-- - - - - - - - - - - - - - - - - - - - - - - - - - - - - - - - - - - - - - -

TPT-TANK-NOTIFY-MIB

DEFINITIONS ::= BEGIN

IMPORTS
  MODULE-IDENTITY, OBJECT-TYPE, NOTIFICATION-TYPE
    FROM SNMPv2-SMI

  TEXTUAL-CONVENTION
    FROM SNMPv2-TC

  tpt-tpa-objs, tpt-tpa-eventsV2, tpt-tpa-unkparams
    FROM TPT-TPAMIBS-MIB

  tptMiscNotifyDeviceID
    FROM TPT-MISC-NOTIFY-MIB
  ;

tpt-tank-notify MODULE-IDENTITY
  LAST-UPDATED "201605251854Z" -- May 25, 2016
  ORGANIZATION "Trend Micro, Inc."
  CONTACT-INFO "www.trendmicro.com"
  DESCRIPTION
    "Notification definitions for X-Series.

     Copyright (C) 2016 Trend Micro Incorporated. All Rights Reserved.

     Trend Micro makes no warranty of any kind with regard to this material,
     including, but not limited to, the implied warranties of merchantability
     and fitness for a particular purpose. Trend Micro shall not be liable for
     errors contained herein or for incidental or consequential damages in
     connection with the furnishing, performance, or use of this material. This
     document contains proprietary information, which is protected by copyright. No
     part of this document may be photocopied, reproduced, or translated into
     another language without the prior written consent of Trend Micro. The
     information is provided 'as is' without warranty of any kind and is subject to
     change without notice. The only warranties for Trend Micro products and
     services are set forth in the express warranty statements accompanying such
     products and services. Nothing herein should be construed as constituting an
     additional warranty. Trend Micro shall not be liable for technical or editorial
     errors or omissions contained herein. TippingPoint(R), the TippingPoint logo, and
     Digital Vaccine(R) are registered trademarks of Trend Micro. All other company
     and product names may be trademarks of their respective holders. All rights
     reserved. This document contains confidential information, trade secrets or
     both, which are the property of Trend Micro. No part of this documentation may
     be reproduced in any form or by any means or used to make any derivative work
     (such as translation, transformation, or adaptation) without written permission
     from Trend Micro or one of its subsidiaries. All other company and product
     names may be trademarks of their respective holders.
    "

  REVISION "201605251854Z" -- May 25, 2016
  DESCRIPTION "Updated copyright information. Minor MIB syntax fixes."

  ::= { tpt-tpa-objs 11 }

-- - - - - - - - - - - - - - - - - - - - - - - - - - - - - - - - - - - - - - -
--
-- Textual convention for TANK notifications
--
-- - - - - - - - - - - - - - - - - - - - - - - - - - - - - - - - - - - - - - -

ExternalVIStatus ::= TEXTUAL-CONVENTION
  STATUS      current
  DESCRIPTION
    "An indication of whether external virtual interface is up or down."
  SYNTAX      INTEGER { up(1), down(2) }

WebFilterStatus ::= TEXTUAL-CONVENTION
  STATUS      current
  DESCRIPTION
    "An indication of the web filtering status."
  SYNTAX      INTEGER { uninitialized(1), success(2), timeout(3), failure(4) }

-- - - - - - - - - - - - - - - - - - - - - - - - - - - - - - - - - - - - - - -
--
-- TANK notifications
--
-- - - - - - - - - - - - - - - - - - - - - - - - - - - - - - - - - - - - - - -

tptTankNotifyExternalVIStatus OBJECT-TYPE
  SYNTAX      ExternalVIStatus
  MAX-ACCESS  read-only
  STATUS      current
  DESCRIPTION
    "Whether the external virtual interface is up or down."
  ::= { tpt-tpa-unkparams 151 }

tptTankNotifyWebFilterStatus OBJECT-TYPE
  SYNTAX      WebFilterStatus
  MAX-ACCESS  read-only
  STATUS      current
  DESCRIPTION
    "Status of web filtering status."
  ::= { tpt-tpa-unkparams 152 }

tptTankNotifyExternalVI NOTIFICATION-TYPE
  OBJECTS     { tptMiscNotifyDeviceID,        tptTankNotifyExternalVIStatus}
  STATUS      current
  DESCRIPTION
    "Notification: Used to inform the management station that external
     virtual interface came up or went down."
  ::= { tpt-tpa-eventsV2 22 }

tptTankNotifyWebFilter NOTIFICATION-TYPE
  OBJECTS     { tptMiscNotifyDeviceID,        tptTankNotifyWebFilterStatus}
  STATUS      current
  DESCRIPTION
    "Notification: Used to inform the management station of the web filtering
     status."
  ::= { tpt-tpa-eventsV2 23 }


END
