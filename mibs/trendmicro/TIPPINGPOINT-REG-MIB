-- - - - - - - - - - - - - - - - - - - - - - - - - - - - - - - - - - - - - - -
--
-- Trend Micro, Inc.
-- Copyright information is in the DESCRIPTION section of the MODULE-IDENTITY.
--
-- - - - - - - - - - - - - - - - - - - - - - - - - - - - - - - - - - - - - - -

TIPPINGPOINT-REG-MIB

DEFINITIONS ::= BEGIN

IMPORTS
  MODULE-IDENTITY, OBJECT-IDENTITY
    FROM SNMPv2-SMI

  enterprises
    FROM SNMPv2-SMI
  ;

tippingpoint MODULE-IDENTITY
  LAST-UPDATED "201605251854Z" -- May 25, 2016
  ORGANIZATION "Trend Micro, Inc."
  CONTACT-INFO "www.trendmicro.com"
  DESCRIPTION
    "Definitions of registration identities for all TPT modules.

     Copyright (C) 2016 Trend Micro Incorporated. All Rights Reserved.

     Trend Micro makes no warranty of any kind with regard to this material,
     including, but not limited to, the implied warranties of merchantability
     and fitness for a particular purpose. Trend Micro shall not be liable for
     errors contained herein or for incidental or consequential damages in
     connection with the furnishing, performance, or use of this material. This
     document contains proprietary information, which is protected by copyright. No
     part of this document may be photocopied, reproduced, or translated into
     another language without the prior written consent of Trend Micro. The
     information is provided 'as is' without warranty of any kind and is subject to
     change without notice. The only warranties for Trend Micro products and
     services are set forth in the express warranty statements accompanying such
     products and services. Nothing herein should be construed as constituting an
     additional warranty. Trend Micro shall not be liable for technical or editorial
     errors or omissions contained herein. TippingPoint(R), the TippingPoint logo, and
     Digital Vaccine(R) are registered trademarks of Trend Micro. All other company
     and product names may be trademarks of their respective holders. All rights
     reserved. This document contains confidential information, trade secrets or
     both, which are the property of Trend Micro. No part of this documentation may
     be reproduced in any form or by any means or used to make any derivative work
     (such as translation, transformation, or adaptation) without written permission
     from Trend Micro or one of its subsidiaries. All other company and product
     names may be trademarks of their respective holders.
    "

  REVISION "201605251854Z" -- May 25, 2016
  DESCRIPTION "Updated copyright information. Minor MIB syntax fixes."

  ::= { enterprises 10734 }  --assigned by IANA

-- -- -- -- -- -- -- -- -- -- -- -- -- -- -- -- -- -- -- -- -- -- -- -- -- --
-- -- -- -- -- -- -- -- -- -- -- -- -- -- -- -- -- -- -- -- -- -- -- -- -- --

tpt-reg OBJECT-IDENTITY
  STATUS         current
  DESCRIPTION    "Sub-tree for the registered modules for TippingPoint
                  Technologies."
  ::= { tippingpoint 1 }

tpt-generic OBJECT-IDENTITY
  STATUS         current
  DESCRIPTION    "Sub-tree for common object and event definitions."
  ::= { tippingpoint 2 }

tpt-products OBJECT-IDENTITY
  STATUS         current
  DESCRIPTION    "Sub-tree for specific object and event definitions."
  ::= { tippingpoint 3 }

tpt-caps OBJECT-IDENTITY
  STATUS         current
  DESCRIPTION    "Sub-tree for agent profiles."
  ::= { tippingpoint 4 }

tpt-reqs OBJECT-IDENTITY
  STATUS         current
  DESCRIPTION    "Sub-tree for management application requirements."
  ::= { tippingpoint 5 }

tpt-expr OBJECT-IDENTITY
  STATUS         current
  DESCRIPTION    "Sub-tree for experimental definitions."
  ::= { tippingpoint 6 }

-- -- -- -- -- -- -- -- -- -- -- -- -- -- -- -- -- -- -- -- -- -- -- -- -- --
-- -- -- -- -- -- -- -- -- -- -- -- -- -- -- -- -- -- -- -- -- -- -- -- -- --

END
