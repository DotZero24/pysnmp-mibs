-- - - - - - - - - - - - - - - - - - - - - - - - - - - - - - - - - - - - - - -
--
-- Trend Micro, Inc.
-- Copyright information is in the DESCRIPTION section of the MODULE-IDENTITY.
--
-- - - - - - - - - - - - - - - - - - - - - - - - - - - - - - - - - - - - - - -

TPT-MULTIDV-MIB

DEFINITIONS ::= BEGIN

IMPORTS
  MODULE-IDENTITY, OBJECT-TYPE,
  Unsigned32, Integer32
    FROM SNMPv2-SMI

  TEXTUAL-CONVENTION
    FROM SNMPv2-TC

  policyDVObjs
    FROM TPT-POLICY-MIB
  ;

tpt-multidv-objs MODULE-IDENTITY
  LAST-UPDATED "201605251854Z" -- May 25, 2016
  ORGANIZATION "Trend Micro, Inc."
  CONTACT-INFO "www.trendmicro.com"
  DESCRIPTION
    "Multiple Digital Vaccine support.

     Copyright (C) 2016 Trend Micro Incorporated. All Rights Reserved.

     Trend Micro makes no warranty of any kind with regard to this material,
     including, but not limited to, the implied warranties of merchantability
     and fitness for a particular purpose. Trend Micro shall not be liable for
     errors contained herein or for incidental or consequential damages in
     connection with the furnishing, performance, or use of this material. This
     document contains proprietary information, which is protected by copyright. No
     part of this document may be photocopied, reproduced, or translated into
     another language without the prior written consent of Trend Micro. The
     information is provided 'as is' without warranty of any kind and is subject to
     change without notice. The only warranties for Trend Micro products and
     services are set forth in the express warranty statements accompanying such
     products and services. Nothing herein should be construed as constituting an
     additional warranty. Trend Micro shall not be liable for technical or editorial
     errors or omissions contained herein. TippingPoint(R), the TippingPoint logo, and
     Digital Vaccine(R) are registered trademarks of Trend Micro. All other company
     and product names may be trademarks of their respective holders. All rights
     reserved. This document contains confidential information, trade secrets or
     both, which are the property of Trend Micro. No part of this documentation may
     be reproduced in any form or by any means or used to make any derivative work
     (such as translation, transformation, or adaptation) without written permission
     from Trend Micro or one of its subsidiaries. All other company and product
     names may be trademarks of their respective holders.
    "

  REVISION "201605251854Z" -- May 25, 2016
  DESCRIPTION "Updated copyright information. Minor MIB syntax fixes."

  ::= { policyDVObjs 2 }

-- - - - - - - - - - - - - - - - - - - - - - - - - - - - - - - - - - - - - - -
--
-- Textual conventions for multi-DV objects
--
-- - - - - - - - - - - - - - - - - - - - - - - - - - - - - - - - - - - - - - -

DVIsActive ::= TEXTUAL-CONVENTION
  STATUS      current
  DESCRIPTION
    "An indicator of whether a DV is active."
  SYNTAX      INTEGER { inactive(0), active(1) }

-- - - - - - - - - - - - - - - - - - - - - - - - - - - - - - - - - - - - - - -
--
-- Table of installed DVs
--
-- - - - - - - - - - - - - - - - - - - - - - - - - - - - - - - - - - - - - - -

installedDVTable OBJECT-TYPE
  SYNTAX      SEQUENCE OF InstalledDVEntry
  MAX-ACCESS  not-accessible
  STATUS      current
  DESCRIPTION
    "Table of installed digital vaccine packages."
  ::= { tpt-multidv-objs 1 }

installedDVEntry OBJECT-TYPE
  SYNTAX      InstalledDVEntry
  MAX-ACCESS  not-accessible
  STATUS      current
  DESCRIPTION
    "An entry in the installed DV table.
     Rows cannot be created or deleted."
  INDEX       { installedDVIndex }
  ::= { installedDVTable 1 }

InstalledDVEntry ::= SEQUENCE {
  installedDVIndex           Unsigned32,
  installedDVVersion         OCTET STRING (SIZE (0..31)),
  installedDVIsActive        DVIsActive
}

installedDVIndex OBJECT-TYPE
  SYNTAX      Unsigned32
  MAX-ACCESS  not-accessible
  STATUS      current
  DESCRIPTION
    "Index into the installed DV table, starting with 1."
  ::= { installedDVEntry 1 }

installedDVVersion OBJECT-TYPE
  SYNTAX      OCTET STRING (SIZE (0..31))
  MAX-ACCESS  read-only
  STATUS      current
  DESCRIPTION
    "The installed DV version in string format (major.minor.patch.build)."
  ::= { installedDVEntry 2 }

installedDVIsActive OBJECT-TYPE
  SYNTAX      DVIsActive
  MAX-ACCESS  read-only
  STATUS      current
  DESCRIPTION
    "Whether this installed DV is active."
  ::= { installedDVEntry 3 }

-- - - - - - - - - - - - - - - - - - - - - - - - - - - - - - - - - - - - - - -
--
-- Table of auxiliary DVs
--
-- - - - - - - - - - - - - - - - - - - - - - - - - - - - - - - - - - - - - - -

auxiliaryDVTable OBJECT-TYPE
  SYNTAX      SEQUENCE OF AuxiliaryDVEntry
  MAX-ACCESS  not-accessible
  STATUS      current
  DESCRIPTION
    "Table of auxiliary digital vaccine packages."
  ::= { tpt-multidv-objs 2 }

auxiliaryDVEntry OBJECT-TYPE
  SYNTAX      AuxiliaryDVEntry
  MAX-ACCESS  not-accessible
  STATUS      current
  DESCRIPTION
    "An entry in the auxiliary DV table.
     Rows cannot be created or deleted."
  INDEX       { auxiliaryDVIndex }
  ::= { auxiliaryDVTable 1 }

AuxiliaryDVEntry ::= SEQUENCE {
  auxiliaryDVIndex           Unsigned32,
  auxiliaryDVType            OCTET STRING (SIZE (0..49)),
  auxiliaryDVName            OCTET STRING (SIZE (0..255)),
  auxiliaryDVVersion         Integer32,
  auxiliaryDVPackage         OCTET STRING (SIZE (0..31))
}

auxiliaryDVIndex OBJECT-TYPE
  SYNTAX      Unsigned32
  MAX-ACCESS  not-accessible
  STATUS      current
  DESCRIPTION
    "Index into the auxiliary DV table, starting with 1."
  ::= { auxiliaryDVEntry 1 }

auxiliaryDVType OBJECT-TYPE
  SYNTAX      OCTET STRING (SIZE (0..49))
  MAX-ACCESS  read-only
  STATUS      current
  DESCRIPTION
    "The type of the auxiliary DV."
  ::= { auxiliaryDVEntry 2 }

auxiliaryDVName OBJECT-TYPE
  SYNTAX      OCTET STRING (SIZE (0..255))
  MAX-ACCESS  read-only
  STATUS      current
  DESCRIPTION
    "The name of the auxiliary DV."
  ::= { auxiliaryDVEntry 3 }

auxiliaryDVVersion OBJECT-TYPE
  SYNTAX      Integer32
  MAX-ACCESS  read-only
  STATUS      current
  DESCRIPTION
    "The auxiliary DV version number."
  ::= { auxiliaryDVEntry 4 }

auxiliaryDVPackage OBJECT-TYPE
  SYNTAX      OCTET STRING (SIZE (0..31))
  MAX-ACCESS  read-only
  STATUS      current
  DESCRIPTION
    "The auxiliary DV version in string format (major.minor.patch.build)."
  ::= { auxiliaryDVEntry 5 }



END
