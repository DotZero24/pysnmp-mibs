-- - - - - - - - - - - - - - - - - - - - - - - - - - - - - - - - - - - - - - -
--
-- Trend Micro, Inc.
-- Copyright information is in the DESCRIPTION section of the MODULE-IDENTITY.
--
-- - - - - - - - - - - - - - - - - - - - - - - - - - - - - - - - - - - - - - -

TPT-BAY-MIB

DEFINITIONS ::= BEGIN

IMPORTS
  MODULE-IDENTITY, OBJECT-TYPE, NOTIFICATION-TYPE, Unsigned32
    FROM SNMPv2-SMI

  TEXTUAL-CONVENTION
    FROM SNMPv2-TC

  tpt-tpa-objs, tpt-tpa-eventsV2, tpt-tpa-unkparams
    FROM TPT-TPAMIBS-MIB
  ;

tpt-slot-objs MODULE-IDENTITY
  LAST-UPDATED "201605251854Z" -- May 25, 2016
  ORGANIZATION "Trend Micro, Inc."
  CONTACT-INFO "www.trendmicro.com"
  DESCRIPTION
    "Slot details on the device.

     Copyright (C) 2016 Trend Micro Incorporated. All Rights Reserved.

     Trend Micro makes no warranty of any kind with regard to this material,
     including, but not limited to, the implied warranties of merchantability
     and fitness for a particular purpose. Trend Micro shall not be liable for
     errors contained herein or for incidental or consequential damages in
     connection with the furnishing, performance, or use of this material. This
     document contains proprietary information, which is protected by copyright. No
     part of this document may be photocopied, reproduced, or translated into
     another language without the prior written consent of Trend Micro. The
     information is provided 'as is' without warranty of any kind and is subject to
     change without notice. The only warranties for Trend Micro products and
     services are set forth in the express warranty statements accompanying such
     products and services. Nothing herein should be construed as constituting an
     additional warranty. Trend Micro shall not be liable for technical or editorial
     errors or omissions contained herein. TippingPoint(R), the TippingPoint logo, and
     Digital Vaccine(R) are registered trademarks of Trend Micro. All other company
     and product names may be trademarks of their respective holders. All rights
     reserved. This document contains confidential information, trade secrets or
     both, which are the property of Trend Micro. No part of this documentation may
     be reproduced in any form or by any means or used to make any derivative work
     (such as translation, transformation, or adaptation) without written permission
     from Trend Micro or one of its subsidiaries. All other company and product
     names may be trademarks of their respective holders.
    "

  REVISION "201605251854Z" -- May 25, 2016
  DESCRIPTION "Updated copyright information. Minor MIB syntax fixes."

  ::= { tpt-tpa-objs 17 }

-- - - - - - - - - - - - - - - - - - - - - - - - - - - - - - - - - - - - - - -
--
-- Textual conventions for slot  MIB objects
--
-- - - - - - - - - - - - - - - - - - - - - - - - - - - - - - - - - - - - - - -

SlotStatus ::= TEXTUAL-CONVENTION
  STATUS      current
  DESCRIPTION
    "An indication of slot status"
  SYNTAX      INTEGER { empty(0), active(1), error(2) }

SlotEvent ::= TEXTUAL-CONVENTION
  STATUS      current
  DESCRIPTION
    "An indication of events occuring in slot"
  SYNTAX      INTEGER { insert(0), remove(1) }


SlotModuleType ::= TEXTUAL-CONVENTION
  STATUS      current
  DESCRIPTION
    "Type of module present in the slot. "
  SYNTAX      INTEGER { type-12-port-1g-copper(1), type-12-port-1g-sfp(2),
                        type-8-port-10g-sfp(3), type-2-port-40g-sfp(4),
                        type-6100(5), type-5100(6), type-2500(7), type-1400(8),
                        type-660(9), type-330(10), type-110(11), type-10(12),
                        type-empty(13), type-8-port-1g-copper-bypass(14),
                        type-4-port-1g-sfp-sr-bypass(15),
                        type-4-port-1g-sfp-lr-bypass(16),
                        type-4-port-10g-sfp-sr-bypass(17),
                        type-4-port-10g-sfp-lr-bypass(18) }


-- - - - - - - - - - - - - - - - - - - - - - - - - - - - - - - - - - - - - - -
--
-- slot  data
--
-- - - - - - - - - - - - - - - - - - - - - - - - - - - - - - - - - - - - - - -

slotTempTable OBJECT-TYPE
  SYNTAX      SEQUENCE OF SlotTempEntry
  MAX-ACCESS  not-accessible
  STATUS      current
  DESCRIPTION
    "Table of slots on the device."
  ::= { tpt-slot-objs 1 }

slotTempEntry OBJECT-TYPE
  SYNTAX      SlotTempEntry
  MAX-ACCESS  not-accessible
  STATUS      current
  DESCRIPTION
    "An entry in the slot table.
     Rows cannot be created or deleted."
  INDEX       { slotTempIndex }
  ::= { slotTempTable 1 }

SlotTempEntry ::= SEQUENCE {
  slotTempIndex          Unsigned32,
  slotName               OCTET STRING (SIZE (0..64)),
  slotModuleName         OCTET STRING (SIZE (0..64)),
  slotStatus             SlotStatus,
  slotModuleSerialNum    OCTET STRING (SIZE (0..64)),
  slotModuleType         SlotModuleType
}

slotTempIndex OBJECT-TYPE
  SYNTAX      Unsigned32
  MAX-ACCESS  not-accessible
  STATUS      current
  DESCRIPTION
    "Index into the slot table, starting with 1."
  ::= { slotTempEntry 1 }


slotName         OBJECT-TYPE
  SYNTAX      OCTET STRING (SIZE (0..64))
  MAX-ACCESS  read-only
  STATUS      current
  DESCRIPTION
    "String description of the name of slot."
  ::= {slotTempEntry   2 }

slotModuleName          OBJECT-TYPE
  SYNTAX      OCTET STRING (SIZE (0..64))
  MAX-ACCESS  read-only
  STATUS      current
  DESCRIPTION
    "String description of the type of module in slot."
  ::= {slotTempEntry   3 }

slotStatus OBJECT-TYPE
  SYNTAX      SlotStatus
  MAX-ACCESS  read-only
  STATUS      current
  DESCRIPTION
    "status of this slot"
  ::= { slotTempEntry 4 }

slotModuleSerialNum  OBJECT-TYPE
  SYNTAX      OCTET STRING (SIZE (0..64))
  MAX-ACCESS  read-only
  STATUS      current
  DESCRIPTION
    "String description of the serial number of the module in the slot."
  ::= {slotTempEntry   5 }


slotModuleType OBJECT-TYPE
  SYNTAX      SlotModuleType
  MAX-ACCESS  read-only
  STATUS      current
  DESCRIPTION
    "Type of module present in the slot. This is applicable mainly for the
     newer devices like 6100 and above, which have multiple I/O slots. For
     older systems like 5100 which don't have slots, the module type would be
     the device model number."
  ::= { slotTempEntry 6 }

-- - - - - - - - - - - - - - - - - - - - - - - - - - - - - - - - - - - - - - -
--
-- slot module  notification
--
-- - - - - - - - - - - - - - - - - - - - - - - - - - - - - - - - - - - - - - -

tptSlotDeviceID OBJECT-TYPE
SYNTAX      OCTET STRING (SIZE (0..40))
MAX-ACCESS  read-only
STATUS      current
DESCRIPTION
"The unique identifier of the device sending this notification."
::= { tpt-tpa-unkparams 281 }

tptSlotID OBJECT-TYPE
SYNTAX     Unsigned32
MAX-ACCESS  read-only
STATUS      current
DESCRIPTION
"The slot index which is  sending this notification."
::= { tpt-tpa-unkparams 282 }


tptSlotEvent OBJECT-TYPE
SYNTAX    SlotEvent
MAX-ACCESS  read-only
STATUS      current
DESCRIPTION
"The event occuring in the slot  which is  sending this notification."
::= { tpt-tpa-unkparams 283 }


tptSlotChangeNotify NOTIFICATION-TYPE
OBJECTS     { tptSlotDeviceID, tptSlotID, tptSlotEvent }
STATUS      current
DESCRIPTION
"Notification: Module was inserted on this device"
::= { tpt-tpa-eventsV2 54 }


END
