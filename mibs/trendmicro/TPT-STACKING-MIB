-- - - - - - - - - - - - - - - - - - - - - - - - - - - - - - - - - - - - - - -
--
-- TippingPoint Technologies, Inc
-- Copyright information is in the DESCRIPTION section of the MODULE-IDENTITY.
--
-- - - - - - - - - - - - - - - - - - - - - - - - - - - - - - - - - - - - - - -

TPT-STACKING-MIB

DEFINITIONS ::= BEGIN

IMPORTS
  MODULE-IDENTITY, OBJECT-TYPE, NOTIFICATION-TYPE,
  Unsigned32
    FROM SNMPv2-SMI

  TEXTUAL-CONVENTION
    FROM SNMPv2-TC

  FaultCause
    FROM TPT-HIGH-AVAIL-MIB

  tpt-products
    FROM TIPPINGPOINT-REG-MIB

  EnabledOrNot
    FROM TPT-PORT-CONFIG-MIB

  tpt-tpa-objs, tpt-tpa-eventsV2, tpt-tpa-unkparams
    FROM TPT-TPAMIBS-MIB
  ;

tpt-stack-objs MODULE-IDENTITY
  LAST-UPDATED "201104191200Z"
  ORGANIZATION "Trend Micro, Inc."
  CONTACT-INFO "www.tippingpoint.com"
  DESCRIPTION
    "Device information related to stacking ultralight.

     Copyright 2016 Trend Micro, Inc  All rights reserved.
     This document contains confidential and proprietary information to
     Trend Micro, Inc. Use of this document is subject to the
     terms and conditions of Trend Micro's Non-Disclosure Agreement.
    "
  ::= { tpt-tpa-objs 20 }



-- - - - - - - - - - - - - - - - - - - - - - - - - - - - - - - - - - - - - - -
--
-- Textual convention(s) specific to stacking ultralight
--
-- - - - - - - - - - - - - - - - - - - - - - - - - - - - - - - - - - - - - - -
DeviceRti ::= TEXTUAL-CONVENTION
  STATUS      current
  DESCRIPTION
    "The current device RTI state."
  SYNTAX      INTEGER { unknown(0),
                        rebooting(5),
                        rlinferior(16),
                        recoverable(21),
                        unrecoverable(32),
                        rtipending(48),
                        rtinormal(64) }

StackRti ::= TEXTUAL-CONVENTION
  STATUS      current
  DESCRIPTION
    "The current stack RTI state."
  SYNTAX      INTEGER { unknown(0),
                        rlinferior(16),
                        invalid(48),
                        rebooting(64),
                        recoverable(80),
                        unrecoverable(96),
                        rtipending(112),
                        rtinormal(128) }

-- - - - - - - - - - - - - - - - - - - - - - - - - - - - - - - - - - - - - - -
--
-- stacking ultralight objects
--
-- - - - - - - - - - - - - - - - - - - - - - - - - - - - - - - - - - - - - - -

stackingStackRtiTimeStamp OBJECT-TYPE
  SYNTAX      Unsigned32
  MAX-ACCESS  read-only
  STATUS      current
  DESCRIPTION
  "The time of the last stack RTI state change (in seconds since
   January 1, 1970).  This value is zero if the stack RTI state has not changed
   since the last reboot."
  ::= {  tpt-stack-objs 1 }

stackingDeviceRTI OBJECT-TYPE
  SYNTAX      DeviceRti
  MAX-ACCESS  read-only
  STATUS      current
  DESCRIPTION
    "The current device RTI state"
  ::= {  tpt-stack-objs 2 }

stackingPrevDeviceRTI OBJECT-TYPE
  SYNTAX      DeviceRti
  MAX-ACCESS  read-only
  STATUS      current
  DESCRIPTION
    "The previous device RTI state"
  ::= {  tpt-stack-objs 3 }

stackingDeviceFaultCause OBJECT-TYPE
  SYNTAX      FaultCause
  MAX-ACCESS  read-only
  STATUS      current
  DESCRIPTION
    "Device fault cause if in L2FB"
  ::= {  tpt-stack-objs 4 }

stackingStackRTI OBJECT-TYPE
  SYNTAX      StackRti
  MAX-ACCESS  read-only
  STATUS      current
  DESCRIPTION
    "The current stack RTI state"
  ::= {  tpt-stack-objs 5 }

stackingPrevStackRTI OBJECT-TYPE
  SYNTAX      StackRti
  MAX-ACCESS  read-only
  STATUS      current
  DESCRIPTION
    "The previous stack RTI state"
  ::= {  tpt-stack-objs 6 }

-- - - - - - - - - - - - - - - - - - - - - - - - - - - - - - - - - - - - - - -
--
-- stacking ultralight notifications
--
-- - - - - - - - - - - - - - - - - - - - - - - - - - - - - - - - - - - - - - -
tptStackingNotifyDeviceID OBJECT-TYPE
  SYNTAX      OCTET STRING (SIZE (0..40))
  MAX-ACCESS  read-only
  STATUS      current
  DESCRIPTION
    "The unique device identifier sending this notification."
  ::= { tpt-tpa-unkparams 324 }

tptStackingNotifyKey OBJECT-TYPE
  SYNTAX      OCTET STRING (SIZE (0..12))
  MAX-ACCESS  read-only
  STATUS      current
  DESCRIPTION
    "The unique stack member identifier sending this notification."
  ::= { tpt-tpa-unkparams 328 }

tptStackingNotifyTimeStamp OBJECT-TYPE
  SYNTAX      Unsigned32
  MAX-ACCESS  read-only
  STATUS      current
  DESCRIPTION
    "The time of this notification (in seconds since January 1, 1970)."
  ::= {  tpt-tpa-unkparams 332 }

tptStackingNotifyDeviceRTI OBJECT-TYPE
  SYNTAX      DeviceRti
  MAX-ACCESS  read-only
  STATUS      current
  DESCRIPTION
    "The current device RTI state"
  ::= { tpt-tpa-unkparams 336 }

tptStackingNotifyPrevDeviceRTI OBJECT-TYPE
  SYNTAX      DeviceRti
  MAX-ACCESS  read-only
  STATUS      current
  DESCRIPTION
    "the previous device RTI state"
  ::= {  tpt-tpa-unkparams 340 }

tptStackingNotifyDeviceFaultCause OBJECT-TYPE
  SYNTAX      FaultCause
  MAX-ACCESS  read-only
  STATUS      current
  DESCRIPTION
    "Device fault cause if in L2FB"
  ::= {  tpt-tpa-unkparams 344 }

tptStackingNotifyStackRTI OBJECT-TYPE
  SYNTAX      StackRti
  MAX-ACCESS  read-only
  STATUS      current
  DESCRIPTION
    "The current stack RTI state"
  ::= {  tpt-tpa-unkparams 348 }

tptStackingNotifyPrevStackRTI OBJECT-TYPE
  SYNTAX      StackRti
  MAX-ACCESS  read-only
  STATUS      current
  DESCRIPTION
    "The previous tack RTI state"
  ::= {  tpt-tpa-unkparams 352 }

tptStackingNotifyMissedHeartbeatKey OBJECT-TYPE
  SYNTAX      OCTET STRING (SIZE (0..12))
  MAX-ACCESS  read-only
  STATUS      current
  DESCRIPTION
    "The unique stack member identifier of the device that is missing heartbeats"
  ::= { tpt-tpa-unkparams 356 }

tptStackingDeviceRTINotify NOTIFICATION-TYPE
  OBJECTS     { tptStackingNotifyDeviceID,
                tptStackingNotifyKey,
                tptStackingNotifyTimeStamp,
                tptStackingNotifyDeviceRTI,
                tptStackingNotifyPrevDeviceRTI,
                tptStackingNotifyDeviceFaultCause}
  STATUS      current
  DESCRIPTION
    "Notification: Used to inform the management station of changes in
     device RTI state."
  ::= {  tpt-tpa-eventsV2 70 }

tptStackingStackRTINotify NOTIFICATION-TYPE
  OBJECTS     { tptStackingNotifyDeviceID,
                tptStackingNotifyKey,
                tptStackingNotifyTimeStamp,
                tptStackingNotifyStackRTI,
                tptStackingNotifyPrevStackRTI }
  STATUS      current
  DESCRIPTION
    "Notification: Used to inform the management station of changes in
     stack RTI state."
  ::= { tpt-tpa-eventsV2 71 }

tptStackingMissedHeartbeatNotify NOTIFICATION-TYPE
  OBJECTS     { tptStackingNotifyDeviceID,
                tptStackingNotifyKey,
                tptStackingNotifyTimeStamp,
                tptStackingNotifyMissedHeartbeatKey}
  STATUS      current
  DESCRIPTION
    "Notification: Used to inform the management station of missed
     heartbeats."
  ::= { tpt-tpa-eventsV2 72 }

END
