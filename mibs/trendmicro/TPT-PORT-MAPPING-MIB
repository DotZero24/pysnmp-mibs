-- - - - - - - - - - - - - - - - - - - - - - - - - - - - - - - - - - - - - - -
--
-- Trend Micro, Inc.
-- Copyright information is in the DESCRIPTION section of the MODULE-IDENTITY.
--
-- - - - - - - - - - - - - - - - - - - - - - - - - - - - - - - - - - - - - - -

TPT-PORT-MAPPING-MIB

DEFINITIONS ::= BEGIN

IMPORTS
  MODULE-IDENTITY, OBJECT-TYPE, Integer32, Unsigned32
    FROM SNMPv2-SMI

  InterfaceIndex
    FROM IF-MIB

  tpt-tpa-objs
    FROM TPT-TPAMIBS-MIB
  ;

tpt-port-mapping-objs MODULE-IDENTITY
  LAST-UPDATED "201610031200Z" -- Oct 3, 2016
  ORGANIZATION "Trend Micro, Inc."
  CONTACT-INFO "www.trendmicro.com"
  DESCRIPTION
    "Configurable logical to physical port mapping on a device.

     Copyright (C) 2016 Trend Micro Incorporated. All Rights Reserved.

     Trend Micro makes no warranty of any kind with regard to this material,
     including, but not limited to, the implied warranties of merchantability
     and fitness for a particular purpose. Trend Micro shall not be liable for
     errors contained herein or for incidental or consequential damages in
     connection with the furnishing, performance, or use of this material. This
     document contains proprietary information, which is protected by copyright. No
     part of this document may be photocopied, reproduced, or translated into
     another language without the prior written consent of Trend Micro. The
     information is provided 'as is' without warranty of any kind and is subject to
     change without notice. The only warranties for Trend Micro products and
     services are set forth in the express warranty statements accompanying such
     products and services. Nothing herein should be construed as constituting an
     additional warranty. Trend Micro shall not be liable for technical or editorial
     errors or omissions contained herein. TippingPoint(R), the TippingPoint logo, and
     Digital Vaccine(R) are registered trademarks of Trend Micro. All other company
     and product names may be trademarks of their respective holders. All rights
     reserved. This document contains confidential information, trade secrets or
     both, which are the property of Trend Micro. No part of this documentation may
     be reproduced in any form or by any means or used to make any derivative work
     (such as translation, transformation, or adaptation) without written permission
     from Trend Micro or one of its subsidiaries. All other company and product
     names may be trademarks of their respective holders.
    "

  REVISION "201610031200Z" -- Oct 3, 2016
  DESCRIPTION "Fixed portMappingPhysicalVlanId to use Integer32 instead of INTEGER."

  REVISION "201605251854Z" -- May 25, 2016
  DESCRIPTION "Updated copyright information. Minor MIB syntax fixes."

  ::= { tpt-tpa-objs 16 }


-- - - - - - - - - - - - - - - - - - - - - - - - - - - - - - - - - - - - - - -
--
-- Table of port mapping settings on the device
--
-- - - - - - - - - - - - - - - - - - - - - - - - - - - - - - - - - - - - - - -

portMappingTable OBJECT-TYPE
  SYNTAX      SEQUENCE OF PortMappingEntry
  MAX-ACCESS  not-accessible
  STATUS      current
  DESCRIPTION
    "Table of logical slots/ports on the device and their mapping to the physical ports."
  ::= { tpt-port-mapping-objs 1 }

portMappingEntry OBJECT-TYPE
  SYNTAX      PortMappingEntry
  MAX-ACCESS  not-accessible
  STATUS      current
  DESCRIPTION
    "An entry in the slot/port table.
     Rows cannot be created or deleted."
  INDEX       { portMappingLogicalSlot, portMappingLogicalPort }
  ::= { portMappingTable 1 }

PortMappingEntry ::= SEQUENCE {
  portMappingLogicalSlot        Unsigned32,
  portMappingLogicalPort        Unsigned32,
  portMappingLogicalIfIndex     InterfaceIndex,
  portMappingPhysicalSlot       Unsigned32,
  portMappingPhysicalPort       Unsigned32,
  portMappingPhysicalIfIndex    InterfaceIndex,
  portMappingSegmentName        OCTET STRING (SIZE (0..128)),
  portMappingPhysicalVlanId     Integer32 (0..4094)
}

portMappingLogicalSlot OBJECT-TYPE
  SYNTAX      Unsigned32
  MAX-ACCESS  read-only
  STATUS      current
  DESCRIPTION
    "Slot number for this logical port."
  ::= { portMappingEntry 1 }

portMappingLogicalPort OBJECT-TYPE
  SYNTAX      Unsigned32
  MAX-ACCESS  read-only
  STATUS      current
  DESCRIPTION
    "Port number for this logical port."
  ::= { portMappingEntry 2 }

portMappingLogicalIfIndex OBJECT-TYPE
  SYNTAX      InterfaceIndex
  MAX-ACCESS  read-only
  STATUS      current
  DESCRIPTION
    "The entry in the IF-MIB interface table that corresponds to this logical port."
  ::= { portMappingEntry 3 }

portMappingPhysicalSlot OBJECT-TYPE
  SYNTAX      Unsigned32
  MAX-ACCESS  read-only
  STATUS      current
  DESCRIPTION
    "Slot number for the mapped physical port."
  ::= { portMappingEntry 4 }

portMappingPhysicalPort OBJECT-TYPE
  SYNTAX      Unsigned32
  MAX-ACCESS  read-only
  STATUS      current
  DESCRIPTION
    "Port number for the mapped physical port."
  ::= { portMappingEntry 5 }

portMappingPhysicalIfIndex OBJECT-TYPE
  SYNTAX      InterfaceIndex
  MAX-ACCESS  read-only
  STATUS      current
  DESCRIPTION
    "The entry in the IF-MIB interface table that corresponds to the mapped physical port."
  ::= { portMappingEntry 6 }

portMappingSegmentName OBJECT-TYPE
  SYNTAX      OCTET STRING (SIZE (0..128))
  MAX-ACCESS  read-only
  STATUS      obsolete
  DESCRIPTION
    "The name of the segment pertaining to this logical port."
  ::= { portMappingEntry 7 }

portMappingPhysicalVlanId OBJECT-TYPE
  SYNTAX      Integer32 (0..4094)
  MAX-ACCESS  read-only
  STATUS      current
  DESCRIPTION
    "The VLAN ID used on the physical port. 0 indicates the traffic is untagged or not applicable for this port."
  ::= { portMappingEntry 8 }

END
