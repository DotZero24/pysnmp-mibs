-- - - - - - - - - - - - - - - - - - - - - - - - - - - - - - - - - - - - - - -
--
-- Trend Micro, Inc.
-- Copyright information is in the DESCRIPTION section of the MODULE-IDENTITY.
--
-- - - - - - - - - - - - - - - - - - - - - - - - - - - - - - - - - - - - - - -

TPT-LICENSE-MIB

DEFINITIONS ::= BEGIN

IMPORTS
  MODULE-IDENTITY, OBJECT-TYPE, Unsigned32
    FROM SNMPv2-SMI

  TEXTUAL-CONVENTION
    FROM SNMPv2-TC

  tpt-tpa-objs
    FROM TPT-TPAMIBS-MIB
  ;

tpt-license-objs MODULE-IDENTITY
  LAST-UPDATED "201605251854Z" -- May 25, 2016
  ORGANIZATION "Trend Micro, Inc."
  CONTACT-INFO "www.trendmicro.com"
  DESCRIPTION
    "License Package support.

     Copyright (C) 2016 Trend Micro Incorporated. All Rights Reserved.

     Trend Micro makes no warranty of any kind with regard to this material,
     including, but not limited to, the implied warranties of merchantability
     and fitness for a particular purpose. Trend Micro shall not be liable for
     errors contained herein or for incidental or consequential damages in
     connection with the furnishing, performance, or use of this material. This
     document contains proprietary information, which is protected by copyright. No
     part of this document may be photocopied, reproduced, or translated into
     another language without the prior written consent of Trend Micro. The
     information is provided 'as is' without warranty of any kind and is subject to
     change without notice. The only warranties for Trend Micro products and
     services are set forth in the express warranty statements accompanying such
     products and services. Nothing herein should be construed as constituting an
     additional warranty. Trend Micro shall not be liable for technical or editorial
     errors or omissions contained herein. TippingPoint(R), the TippingPoint logo, and
     Digital Vaccine(R) are registered trademarks of Trend Micro. All other company
     and product names may be trademarks of their respective holders. All rights
     reserved. This document contains confidential information, trade secrets or
     both, which are the property of Trend Micro. No part of this documentation may
     be reproduced in any form or by any means or used to make any derivative work
     (such as translation, transformation, or adaptation) without written permission
     from Trend Micro or one of its subsidiaries. All other company and product
     names may be trademarks of their respective holders.
    "

  REVISION "201605251854Z" -- May 25, 2016
  DESCRIPTION "Updated copyright information. Minor MIB syntax fixes."

  ::= { tpt-tpa-objs 15 }

-- - - - - - - - - - - - - - - - - - - - - - - - - - - - - - - - - - - - - - -
--
-- Textual conventions for license objects
--
-- - - - - - - - - - - - - - - - - - - - - - - - - - - - - - - - - - - - - - -

LicenseStatus ::= TEXTUAL-CONVENTION
  STATUS      current
  DESCRIPTION
    "An indicator of the status for a licensed feature."
  SYNTAX      INTEGER { info(0), ok(1), warning(2), error(3) }

LicenseAction ::= TEXTUAL-CONVENTION
  STATUS      current
  DESCRIPTION
    "The action to take for a licensed feature."
  SYNTAX      INTEGER { allow(0), deny(1) }

-- - - - - - - - - - - - - - - - - - - - - - - - - - - - - - - - - - - - - - -
--
-- Table of licensed objects
--
-- - - - - - - - - - - - - - - - - - - - - - - - - - - - - - - - - - - - - - -

licenseTable OBJECT-TYPE
  SYNTAX      SEQUENCE OF LicenseEntry
  MAX-ACCESS  not-accessible
  STATUS      current
  DESCRIPTION
    "Table of licensed features."
  ::= { tpt-license-objs 1 }

licenseEntry OBJECT-TYPE
  SYNTAX      LicenseEntry
  MAX-ACCESS  not-accessible
  STATUS      current
  DESCRIPTION
    "An entry in the licensed feature table.
     Rows cannot be created or deleted."
  INDEX       { licenseEntryIndex }
  ::= { licenseTable 1 }

LicenseEntry ::= SEQUENCE {
  licenseEntryIndex          Unsigned32,
  licenseEntryFeature        OCTET STRING (SIZE (0..63)),
  licenseEntryStatus         LicenseStatus,
  licenseEntryAction         LicenseAction,
  licenseEntryExpiry         OCTET STRING (SIZE (0..31)),
  licenseEntryDetails        OCTET STRING (SIZE (0..255))
}

licenseEntryIndex OBJECT-TYPE
  SYNTAX      Unsigned32
  MAX-ACCESS  not-accessible
  STATUS      current
  DESCRIPTION
    "Index into the licensed feature table, starting with 1."
  ::= { licenseEntry 1 }

licenseEntryFeature OBJECT-TYPE
  SYNTAX      OCTET STRING (SIZE (0..63))
  MAX-ACCESS  read-only
  STATUS      current
  DESCRIPTION
    "The name of the licensed feature."
  ::= { licenseEntry 2 }

licenseEntryStatus OBJECT-TYPE
  SYNTAX      LicenseStatus
  MAX-ACCESS  read-only
  STATUS      current
  DESCRIPTION
    "Status of this licensed feature."
  ::= { licenseEntry 3 }

licenseEntryAction OBJECT-TYPE
  SYNTAX      LicenseAction
  MAX-ACCESS  read-only
  STATUS      current
  DESCRIPTION
    "Action to take for this licensed feature."
  ::= { licenseEntry 4 }

licenseEntryExpiry OBJECT-TYPE
  SYNTAX      OCTET STRING (SIZE (0..31))
  MAX-ACCESS  read-only
  STATUS      current
  DESCRIPTION
    "The date on which this licensed feature will expire."
  ::= { licenseEntry 5 }

licenseEntryDetails OBJECT-TYPE
  SYNTAX      OCTET STRING (SIZE (0..255))
  MAX-ACCESS  read-only
  STATUS      current
  DESCRIPTION
    "Any additional information about this licensed feature."
  ::= { licenseEntry 6 }

END
