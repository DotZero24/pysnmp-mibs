-- - - - - - - - - - - - - - - - - - - - - - - - - - - - - - - - - - - - - - -
--
-- Trend Micro, Inc.
-- Copyright information is in the DESCRIPTION section of the MODULE-IDENTITY.
--
-- - - - - - - - - - - - - - - - - - - - - - - - - - - - - - - - - - - - - - -

TPT-COMPACT-FLASH-MIB

DEFINITIONS ::= BEGIN

IMPORTS
  MODULE-IDENTITY, OBJECT-IDENTITY,OBJECT-TYPE,NOTIFICATION-TYPE,
  Unsigned32
    FROM SNMPv2-SMI

  TEXTUAL-CONVENTION
    FROM SNMPv2-TC

  tpt-tpa-objs, tpt-tpa-eventsV2, tpt-tpa-unkparams
    FROM TPT-TPAMIBS-MIB

  ;

tpt-compact-flash MODULE-IDENTITY
  LAST-UPDATED "201605251854Z" -- May 25, 2016
  ORGANIZATION "Trend Micro, Inc."
  CONTACT-INFO "www.trendmicro.com"
  DESCRIPTION
    "Compact flash details on the device.

     Copyright (C) 2016 Trend Micro Incorporated. All Rights Reserved.

     Trend Micro makes no warranty of any kind with regard to this material,
     including, but not limited to, the implied warranties of merchantability
     and fitness for a particular purpose. Trend Micro shall not be liable for
     errors contained herein or for incidental or consequential damages in
     connection with the furnishing, performance, or use of this material. This
     document contains proprietary information, which is protected by copyright. No
     part of this document may be photocopied, reproduced, or translated into
     another language without the prior written consent of Trend Micro. The
     information is provided 'as is' without warranty of any kind and is subject to
     change without notice. The only warranties for Trend Micro products and
     services are set forth in the express warranty statements accompanying such
     products and services. Nothing herein should be construed as constituting an
     additional warranty. Trend Micro shall not be liable for technical or editorial
     errors or omissions contained herein. TippingPoint(R), the TippingPoint logo, and
     Digital Vaccine(R) are registered trademarks of Trend Micro. All other company
     and product names may be trademarks of their respective holders. All rights
     reserved. This document contains confidential information, trade secrets or
     both, which are the property of Trend Micro. No part of this documentation may
     be reproduced in any form or by any means or used to make any derivative work
     (such as translation, transformation, or adaptation) without written permission
     from Trend Micro or one of its subsidiaries. All other company and product
     names may be trademarks of their respective holders.
    "

  REVISION "201605251854Z" -- May 25, 2016
  DESCRIPTION "Updated copyright information. Minor MIB syntax fixes."

  ::= { tpt-tpa-objs 14 }

-- - - - - - - - - - - - - - - - - - - - - - - - - - - - - - - - - - - - - - -
--
-- Textual conventions for CF  MIB objects
--
-- - - - - - - - - - - - - - - - - - - - - - - - - - - - - - - - - - - - - - -

MountedOrNot ::= TEXTUAL-CONVENTION
  STATUS      current
  DESCRIPTION
    "An indication of compact flash  mount status - mounted or unmounted."
  SYNTAX      INTEGER { mounted(0), unmounted(1) }

OperationMode ::= TEXTUAL-CONVENTION
  STATUS      current
  DESCRIPTION
    "An indication of compact flash operation mode - auto-mount or secure."
  SYNTAX      INTEGER { secure(0), auto-mount(1) }

FormattedOrNot ::= TEXTUAL-CONVENTION
  STATUS      current
  DESCRIPTION
    "An indication of compact flash format status - formatted or not."
  SYNTAX      INTEGER { formatted(0), unformatted(1) }

PresentOrNot ::= TEXTUAL-CONVENTION
  STATUS      current
  DESCRIPTION
    "An indication of compact flash  presence - present  or not."
  SYNTAX      INTEGER { present(0), absent(1) }



-- - - - - - - - - - - - - - - - - - - - - - - - - - - - - - - - - - - - - - -
--
-- CF data
--
-- - - - - - - - - - - - - - - - - - - - - - - - - - - - - - - - - - - - - - -

compactFlashPresent  OBJECT-TYPE
  SYNTAX      PresentOrNot
  MAX-ACCESS  read-only
  STATUS      current
  DESCRIPTION
    "Compact flash presence"
  ::= { tpt-compact-flash 1 }

compactFlashMounted  OBJECT-TYPE
  SYNTAX      MountedOrNot
  MAX-ACCESS  read-only
  STATUS      current
  DESCRIPTION
    "Compact flash mount status"
  ::= { tpt-compact-flash 2 }

compactFlashFormatted  OBJECT-TYPE
  SYNTAX      FormattedOrNot
  MAX-ACCESS  read-only
  STATUS      current
  DESCRIPTION
    "Compact flash format status"
  ::= { tpt-compact-flash 3 }

compactFlashOperationMode  OBJECT-TYPE
  SYNTAX      OperationMode
  MAX-ACCESS  read-only
  STATUS      current
  DESCRIPTION
    "Compact flash operation mode"
  ::= { tpt-compact-flash 4 }

vendorInformation OBJECT-IDENTITY
  STATUS      current
  DESCRIPTION
    "Sub-tree of compact flash details"
   ::= { tpt-compact-flash 5 }


serialNumber OBJECT-TYPE
  SYNTAX       OCTET STRING (SIZE (0..80))
  MAX-ACCESS  read-only
  STATUS      current
  DESCRIPTION
    "Serial number"
  ::= { vendorInformation 1 }

model    OBJECT-TYPE
  SYNTAX      OCTET STRING (SIZE (0..80))
  MAX-ACCESS  read-only
  STATUS      current
  DESCRIPTION
    "Model Name."
  ::= { vendorInformation  2 }

capacity OBJECT-TYPE
  SYNTAX      Unsigned32
  MAX-ACCESS  read-only
  STATUS      current
  DESCRIPTION
    "Capacity "
  ::= { vendorInformation 3 }

revision    OBJECT-TYPE
  SYNTAX      OCTET STRING (SIZE (0..80))
  MAX-ACCESS  read-only
  STATUS      current
  DESCRIPTION
    "Firmware revision"
  ::= { vendorInformation  4 }

-- - - - - - - - - - - - - - - - - - - - - - - - - - - - - - - - - - - - - - -
--
-- Device ID: first payload parameter of all notifications in this module.
--
-- - - - - - - - - - - - - - - - - - - - - - - - - - - - - - - - - - - - - - -

tptCompactFlashDeviceID OBJECT-TYPE
  SYNTAX      OCTET STRING (SIZE (0..40))
  MAX-ACCESS  read-only
  STATUS      current
  DESCRIPTION
    "The unique identifier of the device sending this notification."
  ::= { tpt-tpa-unkparams 261 }


tptCompactFlashDeviceStatus OBJECT-TYPE
  SYNTAX      PresentOrNot
  MAX-ACCESS  read-only
  STATUS      current
  DESCRIPTION
    "Compact flash status notification."
  ::= { tpt-tpa-unkparams 262 }

-- - - - - - - - - - - - - - - - - - - - - - - - - - - - - - - - - - - - - - -

-- - - - - - - - - - - - - - - - - - - - - - - - - - - - - - - - - - - - - - -
--
-- Mounted notification
--
-- - - - - - - - - - - - - - - - - - - - - - - - - - - - - - - - - - - - - - -

tptCFInsertedNotify NOTIFICATION-TYPE
  OBJECTS     { tptCompactFlashDeviceID, tptCompactFlashDeviceStatus }
  STATUS      current
  DESCRIPTION
    "Notification: Compact Flash was inserted on this device"
  ::= { tpt-tpa-eventsV2 51 }

-- - - - - - - - - - - - - - - - - - - - - - - - - - - - - - - - - - - - - - -
--
-- Unmanaged notification
--
-- - - - - - - - - - - - - - - - - - - - - - - - - - - - - - - - - - - - - - -

tptCFEjectedNotify NOTIFICATION-TYPE
  OBJECTS     { tptCompactFlashDeviceID, tptCompactFlashDeviceStatus }
  STATUS      current
  DESCRIPTION
    "Notification: Compact flash was ejected on this device"
  ::= { tpt-tpa-eventsV2 52 }


END
