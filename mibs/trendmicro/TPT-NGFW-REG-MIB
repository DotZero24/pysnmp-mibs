-- - - - - - - - - - - - - - - - - - - - - - - - - - - - - - - - - - - - - - -
--
-- Trend Micro, Inc.
-- Copyright information is in the DESCRIPTION section of the MODULE-IDENTITY.
--
-- - - - - - - - - - - - - - - - - - - - - - - - - - - - - - - - - - - - - - -

TPT-NGFW-REG-MIB

DEFINITIONS ::= BEGIN

IMPORTS
  MODULE-IDENTITY,
  OBJECT-IDENTITY,
  OBJECT-TYPE
    FROM SNMPv2-SMI

  tpt-products, tpt-reg
    FROM TIPPINGPOINT-REG-MIB

  TEXTUAL-CONVENTION
    FROM SNMPv2-TC

  MODULE-COMPLIANCE,
  OBJECT-GROUP
    FROM SNMPv2-CONF
;

tpt-ngfwMIBs MODULE-IDENTITY
  LAST-UPDATED "201606081721Z" -- June 8, 2016
  ORGANIZATION "Trend Micro, Inc."
  CONTACT-INFO "www.trendmicro.com"
  DESCRIPTION
    "Sub-tree for next-generation firewall objects.

     Copyright (C) 2016 Trend Micro Incorporated. All Rights Reserved.

     Trend Micro makes no warranty of any kind with regard to this material,
     including, but not limited to, the implied warranties of merchantability
     and fitness for a particular purpose. Trend Micro shall not be liable for
     errors contained herein or for incidental or consequential damages in
     connection with the furnishing, performance, or use of this material. This
     document contains proprietary information, which is protected by copyright. No
     part of this document may be photocopied, reproduced, or translated into
     another language without the prior written consent of Trend Micro. The
     information is provided 'as is' without warranty of any kind and is subject to
     change without notice. The only warranties for Trend Micro products and
     services are set forth in the express warranty statements accompanying such
     products and services. Nothing herein should be construed as constituting an
     additional warranty. Trend Micro shall not be liable for technical or editorial
     errors or omissions contained herein. TippingPoint(R), the TippingPoint logo, and
     Digital Vaccine(R) are registered trademarks of Trend Micro. All other company
     and product names may be trademarks of their respective holders. All rights
     reserved. This document contains confidential information, trade secrets or
     both, which are the property of Trend Micro. No part of this documentation may
     be reproduced in any form or by any means or used to make any derivative work
     (such as translation, transformation, or adaptation) without written permission
     from Trend Micro or one of its subsidiaries. All other company and product
     names may be trademarks of their respective holders.
    "

  REVISION "201606081721Z" -- June 8, 2016
  DESCRIPTION "Updated with vTPS SysOIds."

  REVISION "201605251854Z" -- May 25, 2016
  DESCRIPTION "Updated copyright information. Minor MIB syntax fixes."

  REVISION "201301031739Z" -- January 3, 2013
  DESCRIPTION "Initial version."

::= { tpt-products 9 }

-- - - - - - - - - - - - - - - - - - - - - - - - - - - - - - - - - - - - - - -
--
-- NGFW Common Textual Conventions
--
-- - - - - - - - - - - - - - - - - - - - - - - - - - - - - - - - - - - - - - -

Severity ::= TEXTUAL-CONVENTION
  STATUS      current
  DESCRIPTION "This indicates the severity of some type of event. The values are based
               on standard log severities.
              "
  SYNTAX      INTEGER { emergency(1), alert(2), critical(3), error(4), warning(5),
                        notice(6), info(7), debug(8) }

-- - - - - - - - - - - - - - - - - - - - - - - - - - - - - - - - - - - - - - -
--
-- NGFW Top Level MIBs
--
-- - - - - - - - - - - - - - - - - - - - - - - - - - - - - - - - - - - - - - -

tpt-ngfw-family OBJECT-IDENTITY
  STATUS         current
  DESCRIPTION    "Registration for the TippingPoint's family of next-generation firewall devices."
  ::= { tpt-reg 9 }

tpt-ngfw-conf OBJECT-IDENTITY
  STATUS         current
  DESCRIPTION    "This sub-tree is for conformance groups.
		  (OBJECT-GROUP, NOTIFICATION-GROUP, MODULE-COMPLIANCE)"
  ::= { tpt-ngfwMIBs 1 }

tpt-ngfw-objs OBJECT-IDENTITY
  STATUS         current
  DESCRIPTION    "This sub-tree is for all next-generation firewall managed objects"
  ::= { tpt-ngfwMIBs 2 }

tpt-ngfw-events OBJECT-IDENTITY
  STATUS         current
  DESCRIPTION    "This sub-tree is for all events (NOTIFICATION-TYPE) and
                  associated objects describing the notification."
  ::= { tpt-ngfwMIBs 3 }

-- - - - - - - - - - - - - - - - - - - - - - - - - - - - - - - - - - - - - - -
--
-- Conformance Top Level MIBs
--
-- - - - - - - - - - - - - - - - - - - - - - - - - - - - - - - - - - - - - - -

tpt-ngfw-groups OBJECT-IDENTITY
  STATUS         current
  DESCRIPTION    "This sub-tree is for all groups.
		  (OBJECT-GROUP, NOTIFICATION-GROUP)"
  ::= { tpt-ngfw-conf 1 }

tpt-ngfw-compls OBJECT-IDENTITY
  STATUS         current
  DESCRIPTION    "This sub-tree is for all compliance MIBs.
		  (MODULE-COMPLIANCE)"
  ::= { tpt-ngfw-conf 2 }

-- - - - - - - - - - - - - - - - - - - - - - - - - - - - - - - - - - - - - - -
--
-- Notification Top Level MIBs
--
-- - - - - - - - - - - - - - - - - - - - - - - - - - - - - - - - - - - - - - -

tpt-ngfw-eventsV2 OBJECT-IDENTITY
  STATUS         current
  DESCRIPTION    "This sub-tree is for all notifications."
  ::= { tpt-ngfw-events 0 }

tpt-ngfw-params OBJECT-IDENTITY
  STATUS         current
  DESCRIPTION    "This sub-tree is for all variables sent as part of a
                  notifications."
  ::= { tpt-ngfw-events 1 }

-- - - - - - - - - - - - - - - - - - - - - - - - - - - - - - - - - - - - - - -
--
-- Common Notification Parameters
--
-- - - - - - - - - - - - - - - - - - - - - - - - - - - - - - - - - - - - - - -

tptNgfwNotifySeverity OBJECT-TYPE
  SYNTAX      Severity
  MAX-ACCESS  accessible-for-notify
  STATUS      current
  DESCRIPTION    "The severity of a NGFW trap."
  ::= { tpt-ngfw-params 79 }

-- - - - - - - - - - - - - - - - - - - - - - - - - - - - - - - - - - - - - - -
--
-- Model Numbers
--
-- - - - - - - - - - - - - - - - - - - - - - - - - - - - - - - - - - - - - - -

tpt-model-S1020F OBJECT-IDENTITY
  STATUS         current
  DESCRIPTION    "Registration for the TippingPoint S1020F Next Generation Firewall."
  ::= { tpt-ngfw-family 1 }

tpt-model-S1050F OBJECT-IDENTITY
  STATUS         current
  DESCRIPTION    "Registration for the TippingPoint S1050F Next Generation Firewall."
  ::= { tpt-ngfw-family 2 }

tpt-model-S3010F OBJECT-IDENTITY
  STATUS         current
  DESCRIPTION    "Registration for the TippingPoint S3010F Next Generation Firewall."
  ::= { tpt-ngfw-family 3 }

tpt-model-S3020F OBJECT-IDENTITY
  STATUS         current
  DESCRIPTION    "Registration for the TippingPoint S3020F Next Generation Firewall."
  ::= { tpt-ngfw-family 4 }

tpt-model-S8005F OBJECT-IDENTITY
  STATUS         current
  DESCRIPTION    "Registration for the TippingPoint S8005F Next Generation Firewall."
  ::= { tpt-ngfw-family 5 }

tpt-model-S8010F OBJECT-IDENTITY
  STATUS         current
  DESCRIPTION    "Registration for the TippingPoint S8010F Next Generation Firewall."
  ::= { tpt-ngfw-family 6 }

tpt-model-S8020F OBJECT-IDENTITY
  STATUS         current
  DESCRIPTION    "Registration for the TippingPoint S8020F Next Generation Firewall."
  ::= { tpt-ngfw-family 7 }

tpt-model-440T-NGFW OBJECT-IDENTITY
  STATUS         current
  DESCRIPTION    "Registration for the TippingPoint 440T Threat Protection System (NGFW)."
  ::= { tpt-ngfw-family 8 }

tpt-model-2200T-NGFW OBJECT-IDENTITY
  STATUS         current
  DESCRIPTION    "Registration for the TippingPoint 2200T Threat Protection System (NGFW)."
  ::= { tpt-ngfw-family 9 }

tpt-model-VTPS-Standard-NGFW OBJECT-IDENTITY
  STATUS         current
  DESCRIPTION    "Registration for the HP vTPS Standard Virtual Threat Protection System."
  ::= { tpt-ngfw-family 10 }

tpt-model-VTPS-Trial-NGFW OBJECT-IDENTITY
  STATUS         current
  DESCRIPTION    "Registration for the HP vTPS Trial Virtual Threat Protection System."
  ::= { tpt-ngfw-family 11 }

tptNgfwNotificationGroup OBJECT-GROUP
  OBJECTS     {
                tptNgfwNotifySeverity
              }

  STATUS      current
  DESCRIPTION "Group consisting of common NGFW notification parameter objects.
              "
::= { tpt-ngfw-groups 13 }

tptNgfwCompl MODULE-COMPLIANCE
    STATUS      current
    DESCRIPTION "Compliance for common objects across all TippingPoint Next-generation
                 Firewall MIBs.
                "
    MODULE
      MANDATORY-GROUPS { tptNgfwNotificationGroup }
::= { tpt-ngfw-compls 6 }

END
