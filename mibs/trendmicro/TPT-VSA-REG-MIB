-- - - - - - - - - - - - - - - - - - - - - - - - - - - - - - - - - - - - - - -
--
-- Trend Micro, Inc.
-- Copyright information is in the DESCRIPTION section of the MODULE-IDENTITY.
--
-- - - - - - - - - - - - - - - - - - - - - - - - - - - - - - - - - - - - - - -

TPT-VSA-REG-MIB

DEFINITIONS ::= BEGIN

IMPORTS
  MODULE-IDENTITY,
  OBJECT-IDENTITY
    FROM SNMPv2-SMI

  tpt-products, tpt-reg
    FROM TIPPINGPOINT-REG-MIB
;

tpt-vsaMIBs MODULE-IDENTITY
  LAST-UPDATED "201605251854Z" -- May 25, 2016
  ORGANIZATION "Trend Micro, Inc."
  CONTACT-INFO "www.trendmicro.com"
  DESCRIPTION
    "Sub-tree for TippingPoint Virtual Security Appliance (VSA) objects.

     Copyright (C) 2016 Trend Micro Incorporated. All Rights Reserved.

     Trend Micro makes no warranty of any kind with regard to this material,
     including, but not limited to, the implied warranties of merchantability
     and fitness for a particular purpose. Trend Micro shall not be liable for
     errors contained herein or for incidental or consequential damages in
     connection with the furnishing, performance, or use of this material. This
     document contains proprietary information, which is protected by copyright. No
     part of this document may be photocopied, reproduced, or translated into
     another language without the prior written consent of Trend Micro. The
     information is provided 'as is' without warranty of any kind and is subject to
     change without notice. The only warranties for Trend Micro products and
     services are set forth in the express warranty statements accompanying such
     products and services. Nothing herein should be construed as constituting an
     additional warranty. Trend Micro shall not be liable for technical or editorial
     errors or omissions contained herein. TippingPoint(R), the TippingPoint logo, and
     Digital Vaccine(R) are registered trademarks of Trend Micro. All other company
     and product names may be trademarks of their respective holders. All rights
     reserved. This document contains confidential information, trade secrets or
     both, which are the property of Trend Micro. No part of this documentation may
     be reproduced in any form or by any means or used to make any derivative work
     (such as translation, transformation, or adaptation) without written permission
     from Trend Micro or one of its subsidiaries. All other company and product
     names may be trademarks of their respective holders.
    "

  REVISION "201605251854Z" -- May 25, 2016
  DESCRIPTION "Updated copyright information. Minor MIB syntax fixes."

  REVISION "201411111937Z" -- November 11, 2014
  DESCRIPTION "Initial version."

::= { tpt-products 10 }

-- - - - - - - - - - - - - - - - - - - - - - - - - - - - - - - - - - - - - - -
--
-- NGFW Top Level MIBs
--
-- - - - - - - - - - - - - - - - - - - - - - - - - - - - - - - - - - - - - - -

tpt-vsa-family OBJECT-IDENTITY
  STATUS         current
  DESCRIPTION    "Registration of TippingPoint's Virtual Security Appliance (VSA) product family."
  ::= { tpt-reg 10 }

-- - - - - - - - - - - - - - - - - - - - - - - - - - - - - - - - - - - - - - -
--
-- Model Numbers
--
-- - - - - - - - - - - - - - - - - - - - - - - - - - - - - - - - - - - - - - -

tpt-model-V10F OBJECT-IDENTITY
  STATUS         current
  DESCRIPTION    "Registration for TippingPoint V10F vCloudSecure Virtual Appliance."
  ::= { tpt-vsa-family 1 }

tpt-model-V1000F OBJECT-IDENTITY
  STATUS         current
  DESCRIPTION    "Registration for TippingPoint V1000F vCloudSecure Virtual Appliance."
  ::= { tpt-vsa-family 2 }

tpt-model-V2000F OBJECT-IDENTITY
  STATUS         current
  DESCRIPTION    "Registration for TippingPoint V2000F vCloudSecure Virtual Appliance."
  ::= { tpt-vsa-family 3 }

tpt-model-V5000F OBJECT-IDENTITY
  STATUS         current
  DESCRIPTION    "Registration for TippingPoint V5000F vCloudSecure Virtual Appliance."
  ::= { tpt-vsa-family 4 }

END
