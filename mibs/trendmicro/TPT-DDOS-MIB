-- - - - - - - - - - - - - - - - - - - - - - - - - - - - - - - - - - - - - - -
--
-- Trend Micro, Inc.
-- Copyright information is in the DESCRIPTION section of the MODULE-IDENTITY.
--
-- - - - - - - - - - - - - - - - - - - - - - - - - - - - - - - - - - - - - - -

TPT-DDOS-MIB

DEFINITIONS ::= BEGIN

IMPORTS
  MODULE-IDENTITY, OBJECT-TYPE,
  Unsigned32, Counter64
    FROM SNMPv2-SMI

  tpt-tpa-objs
    FROM TPT-TPAMIBS-MIB
  ;

tpt-ddos MODULE-IDENTITY
  LAST-UPDATED "201605251854Z" -- May 25, 2016
  ORGANIZATION "Trend Micro, Inc."
  CONTACT-INFO "www.trendmicro.com"
  DESCRIPTION
    "DDoS management (statistics).

     Copyright (C) 2016 Trend Micro Incorporated. All Rights Reserved.

     Trend Micro makes no warranty of any kind with regard to this material,
     including, but not limited to, the implied warranties of merchantability
     and fitness for a particular purpose. Trend Micro shall not be liable for
     errors contained herein or for incidental or consequential damages in
     connection with the furnishing, performance, or use of this material. This
     document contains proprietary information, which is protected by copyright. No
     part of this document may be photocopied, reproduced, or translated into
     another language without the prior written consent of Trend Micro. The
     information is provided 'as is' without warranty of any kind and is subject to
     change without notice. The only warranties for Trend Micro products and
     services are set forth in the express warranty statements accompanying such
     products and services. Nothing herein should be construed as constituting an
     additional warranty. Trend Micro shall not be liable for technical or editorial
     errors or omissions contained herein. TippingPoint(R), the TippingPoint logo, and
     Digital Vaccine(R) are registered trademarks of Trend Micro. All other company
     and product names may be trademarks of their respective holders. All rights
     reserved. This document contains confidential information, trade secrets or
     both, which are the property of Trend Micro. No part of this documentation may
     be reproduced in any form or by any means or used to make any derivative work
     (such as translation, transformation, or adaptation) without written permission
     from Trend Micro or one of its subsidiaries. All other company and product
     names may be trademarks of their respective holders.
    "

  REVISION "201605251854Z" -- May 25, 2016
  DESCRIPTION "Updated copyright information. Minor MIB syntax fixes."

  ::= { tpt-tpa-objs 9 }

-- - - - - - - - - - - - - - - - - - - - - - - - - - - - - - - - - - - - - - -
--
--  Variable definitions
--
-- - - - - - - - - - - - - - - - - - - - - - - - - - - - - - - - - - - - - - -


-- - - - - - - - - - - - - - - - - - - - - - - - - - - - - - - - - - - - - - -
--
-- SYN Proxy filter statistics
--
-- - - - - - - - - - - - - - - - - - - - - - - - - - - - - - - - - - - - - - -

-- Rejected SYNs per second history seconds

rejectSynHistSecondsTable OBJECT-TYPE
  SYNTAX      SEQUENCE OF RejectSynHistSecondsEntry
  MAX-ACCESS  not-accessible
  STATUS      current
  DESCRIPTION
    "Historical (sampled) data every second for a minute."
  ::= { tpt-ddos 5 }

rejectSynHistSecondsEntry OBJECT-TYPE
  SYNTAX      RejectSynHistSecondsEntry
  MAX-ACCESS  not-accessible
  STATUS      current
  DESCRIPTION
    "An entry in the rejected SYNs per second history seconds table.
     Rows cannot be created or deleted.
    "
  INDEX       { rejectSynHistSecondsGlobalID, rejectSynHistSecondsIndex }
  ::= { rejectSynHistSecondsTable 1 }

RejectSynHistSecondsEntry ::= SEQUENCE {
  rejectSynHistSecondsGlobalID   OCTET STRING (SIZE (0..40)),
  rejectSynHistSecondsIndex      Unsigned32,
  rejectSynHistSecondsUnitCount  Counter64,
  rejectSynHistSecondsTimestamp  Unsigned32
}

rejectSynHistSecondsGlobalID OBJECT-TYPE
  SYNTAX      OCTET STRING (SIZE (0..40))
  MAX-ACCESS  not-accessible
  STATUS      current
  DESCRIPTION
    "The global identifier of a DDoS filter group."
  ::= { rejectSynHistSecondsEntry 1 }

rejectSynHistSecondsIndex OBJECT-TYPE
  SYNTAX      Unsigned32
  MAX-ACCESS  not-accessible
  STATUS      current
  DESCRIPTION
    "The index (0-59) of the second."
  ::= { rejectSynHistSecondsEntry 2 }

rejectSynHistSecondsUnitCount OBJECT-TYPE
  SYNTAX      Counter64
  MAX-ACCESS  read-only
  STATUS      current
  DESCRIPTION
    "The count of filter-specific units matching the criteria for
     this filter in the specified second."
  ::= { rejectSynHistSecondsEntry 3 }

rejectSynHistSecondsTimestamp OBJECT-TYPE
  SYNTAX      Unsigned32
  MAX-ACCESS  read-only
  STATUS      current
  DESCRIPTION
    "The time SecondsUnitCount was updated (in seconds since January 1, 1970)."
  ::= { rejectSynHistSecondsEntry 4 }


-- Rejected SYNs per second history minutes

rejectSynHistMinutesTable OBJECT-TYPE
  SYNTAX      SEQUENCE OF RejectSynHistMinutesEntry
  MAX-ACCESS  not-accessible
  STATUS      current
  DESCRIPTION
    "Historical (sampled) data every minute for an hour."
  ::= { tpt-ddos 6 }

rejectSynHistMinutesEntry OBJECT-TYPE
  SYNTAX      RejectSynHistMinutesEntry
  MAX-ACCESS  not-accessible
  STATUS      current
  DESCRIPTION
    "An entry in the rejected SYNs per second history minutes table.
     Rows cannot be created or deleted.
    "
  INDEX       { rejectSynHistMinutesGlobalID, rejectSynHistMinutesIndex }
  ::= { rejectSynHistMinutesTable 1 }

RejectSynHistMinutesEntry ::= SEQUENCE {
  rejectSynHistMinutesGlobalID   OCTET STRING (SIZE (0..40)),
  rejectSynHistMinutesIndex      Unsigned32,
  rejectSynHistMinutesUnitCount  Counter64,
  rejectSynHistMinutesTimestamp  Unsigned32
}

rejectSynHistMinutesGlobalID OBJECT-TYPE
  SYNTAX      OCTET STRING (SIZE (0..40))
  MAX-ACCESS  not-accessible
  STATUS      current
  DESCRIPTION
    "The global identifier of a DDoS filter group."
  ::= { rejectSynHistMinutesEntry 1 }

rejectSynHistMinutesIndex OBJECT-TYPE
  SYNTAX      Unsigned32
  MAX-ACCESS  not-accessible
  STATUS      current
  DESCRIPTION
    "The index (0-59) of the minute."
  ::= { rejectSynHistMinutesEntry 2 }

rejectSynHistMinutesUnitCount OBJECT-TYPE
  SYNTAX      Counter64
  MAX-ACCESS  read-only
  STATUS      current
  DESCRIPTION
    "The average of the SecondsUnitCount values corresponding to this minute."
  ::= { rejectSynHistMinutesEntry 3 }

rejectSynHistMinutesTimestamp OBJECT-TYPE
  SYNTAX      Unsigned32
  MAX-ACCESS  read-only
  STATUS      current
  DESCRIPTION
    "The time MinutesUnitCount was updated (in seconds since January 1, 1970)."
  ::= { rejectSynHistMinutesEntry 4 }


-- Rejected SYNs per second history hours

rejectSynHistHoursTable OBJECT-TYPE
  SYNTAX      SEQUENCE OF RejectSynHistHoursEntry
  MAX-ACCESS  not-accessible
  STATUS      current
  DESCRIPTION
    "Historical (sampled) data every hour for a day."
  ::= { tpt-ddos 7 }

rejectSynHistHoursEntry OBJECT-TYPE
  SYNTAX      RejectSynHistHoursEntry
  MAX-ACCESS  not-accessible
  STATUS      current
  DESCRIPTION
    "An entry in the rejected SYNs per second history hours table.
     Rows cannot be created or deleted.
    "
  INDEX       { rejectSynHistHoursGlobalID, rejectSynHistHoursIndex }
  ::= { rejectSynHistHoursTable 1 }

RejectSynHistHoursEntry ::= SEQUENCE {
  rejectSynHistHoursGlobalID   OCTET STRING (SIZE (0..40)),
  rejectSynHistHoursIndex      Unsigned32,
  rejectSynHistHoursUnitCount  Counter64,
  rejectSynHistHoursTimestamp  Unsigned32
}

rejectSynHistHoursGlobalID OBJECT-TYPE
  SYNTAX      OCTET STRING (SIZE (0..40))
  MAX-ACCESS  not-accessible
  STATUS      current
  DESCRIPTION
    "The global identifier of a DDoS filter group."
  ::= { rejectSynHistHoursEntry 1 }

rejectSynHistHoursIndex OBJECT-TYPE
  SYNTAX      Unsigned32
  MAX-ACCESS  not-accessible
  STATUS      current
  DESCRIPTION
    "The index (0-23) of the hour."
  ::= { rejectSynHistHoursEntry 2 }

rejectSynHistHoursUnitCount OBJECT-TYPE
  SYNTAX      Counter64
  MAX-ACCESS  read-only
  STATUS      current
  DESCRIPTION
    "The average of the MinutesUnitCount values corresponding to this hour."
  ::= { rejectSynHistHoursEntry 3 }

rejectSynHistHoursTimestamp OBJECT-TYPE
  SYNTAX      Unsigned32
  MAX-ACCESS  read-only
  STATUS      current
  DESCRIPTION
    "The time HoursUnitCount was updated (in seconds since January 1, 1970)."
  ::= { rejectSynHistHoursEntry 4 }


-- Rejected SYNs per second history days

rejectSynHistDaysTable OBJECT-TYPE
  SYNTAX      SEQUENCE OF RejectSynHistDaysEntry
  MAX-ACCESS  not-accessible
  STATUS      current
  DESCRIPTION
    "Historical (sampled) data every day for 35 days."
  ::= { tpt-ddos 8 }

rejectSynHistDaysEntry OBJECT-TYPE
  SYNTAX      RejectSynHistDaysEntry
  MAX-ACCESS  not-accessible
  STATUS      current
  DESCRIPTION
    "An entry in the rejected SYNs per second history days table.
     Rows cannot be created or deleted.
    "
  INDEX       { rejectSynHistDaysGlobalID, rejectSynHistDaysIndex }
  ::= { rejectSynHistDaysTable 1 }

RejectSynHistDaysEntry ::= SEQUENCE {
  rejectSynHistDaysGlobalID   OCTET STRING (SIZE (0..40)),
  rejectSynHistDaysIndex      Unsigned32,
  rejectSynHistDaysUnitCount  Counter64,
  rejectSynHistDaysTimestamp  Unsigned32
}

rejectSynHistDaysGlobalID OBJECT-TYPE
  SYNTAX      OCTET STRING (SIZE (0..40))
  MAX-ACCESS  not-accessible
  STATUS      current
  DESCRIPTION
    "The global identifier of a DDoS filter group."
  ::= { rejectSynHistDaysEntry 1 }

rejectSynHistDaysIndex OBJECT-TYPE
  SYNTAX      Unsigned32
  MAX-ACCESS  not-accessible
  STATUS      current
  DESCRIPTION
    "The index (0-34) of the day."
  ::= { rejectSynHistDaysEntry 2 }

rejectSynHistDaysUnitCount OBJECT-TYPE
  SYNTAX      Counter64
  MAX-ACCESS  read-only
  STATUS      current
  DESCRIPTION
    "The average of the HoursUnitCount values corresponding to this day."
  ::= { rejectSynHistDaysEntry 3 }

rejectSynHistDaysTimestamp OBJECT-TYPE
  SYNTAX      Unsigned32
  MAX-ACCESS  read-only
  STATUS      current
  DESCRIPTION
    "The time DaysUnitCount was updated (in seconds since January 1, 1970)."
  ::= { rejectSynHistDaysEntry 4 }


-- Proxied connections per second history seconds

proxyConnHistSecondsTable OBJECT-TYPE
  SYNTAX      SEQUENCE OF ProxyConnHistSecondsEntry
  MAX-ACCESS  not-accessible
  STATUS      current
  DESCRIPTION
    "Historical (sampled) data every second for a minute."
  ::= { tpt-ddos 9 }

proxyConnHistSecondsEntry OBJECT-TYPE
  SYNTAX      ProxyConnHistSecondsEntry
  MAX-ACCESS  not-accessible
  STATUS      current
  DESCRIPTION
    "An entry in the proxied connections per second history seconds table.
     Rows cannot be created or deleted.
    "
  INDEX       { proxyConnHistSecondsGlobalID, proxyConnHistSecondsIndex }
  ::= { proxyConnHistSecondsTable 1 }

ProxyConnHistSecondsEntry ::= SEQUENCE {
  proxyConnHistSecondsGlobalID   OCTET STRING (SIZE (0..40)),
  proxyConnHistSecondsIndex      Unsigned32,
  proxyConnHistSecondsUnitCount  Counter64,
  proxyConnHistSecondsTimestamp  Unsigned32
}

proxyConnHistSecondsGlobalID OBJECT-TYPE
  SYNTAX      OCTET STRING (SIZE (0..40))
  MAX-ACCESS  not-accessible
  STATUS      current
  DESCRIPTION
    "The global identifier of a DDoS filter group."
  ::= { proxyConnHistSecondsEntry 1 }

proxyConnHistSecondsIndex OBJECT-TYPE
  SYNTAX      Unsigned32
  MAX-ACCESS  not-accessible
  STATUS      current
  DESCRIPTION
    "The index (0-59) of the second."
  ::= { proxyConnHistSecondsEntry 2 }

proxyConnHistSecondsUnitCount OBJECT-TYPE
  SYNTAX      Counter64
  MAX-ACCESS  read-only
  STATUS      current
  DESCRIPTION
    "The count of filter-specific units matching the traffic criteria for
     this filter in the specified second."
  ::= { proxyConnHistSecondsEntry 3 }

proxyConnHistSecondsTimestamp OBJECT-TYPE
  SYNTAX      Unsigned32
  MAX-ACCESS  read-only
  STATUS      current
  DESCRIPTION
    "The time SecondsUnitCount was updated (in seconds since January 1, 1970)."
  ::= { proxyConnHistSecondsEntry 4 }


-- Proxied connections per second history minutes

proxyConnHistMinutesTable OBJECT-TYPE
  SYNTAX      SEQUENCE OF ProxyConnHistMinutesEntry
  MAX-ACCESS  not-accessible
  STATUS      current
  DESCRIPTION
    "Historical (sampled) data every minute for an hour."
  ::= { tpt-ddos 10 }

proxyConnHistMinutesEntry OBJECT-TYPE
  SYNTAX      ProxyConnHistMinutesEntry
  MAX-ACCESS  not-accessible
  STATUS      current
  DESCRIPTION
    "An entry in the proxied connections per second history minutes table.
     Rows cannot be created or deleted.
    "
  INDEX       { proxyConnHistMinutesGlobalID, proxyConnHistMinutesIndex }
  ::= { proxyConnHistMinutesTable 1 }

ProxyConnHistMinutesEntry ::= SEQUENCE {
  proxyConnHistMinutesGlobalID   OCTET STRING (SIZE (0..40)),
  proxyConnHistMinutesIndex      Unsigned32,
  proxyConnHistMinutesUnitCount  Counter64,
  proxyConnHistMinutesTimestamp  Unsigned32
}

proxyConnHistMinutesGlobalID OBJECT-TYPE
  SYNTAX      OCTET STRING (SIZE (0..40))
  MAX-ACCESS  not-accessible
  STATUS      current
  DESCRIPTION
    "The global identifier of a DDoS filter group."
  ::= { proxyConnHistMinutesEntry 1 }

proxyConnHistMinutesIndex OBJECT-TYPE
  SYNTAX      Unsigned32
  MAX-ACCESS  not-accessible
  STATUS      current
  DESCRIPTION
    "The index (0-59) of the minute."
  ::= { proxyConnHistMinutesEntry 2 }

proxyConnHistMinutesUnitCount OBJECT-TYPE
  SYNTAX      Counter64
  MAX-ACCESS  read-only
  STATUS      current
  DESCRIPTION
    "The average of the SecondsUnitCount values corresponding to this minute."
  ::= { proxyConnHistMinutesEntry 3 }

proxyConnHistMinutesTimestamp OBJECT-TYPE
  SYNTAX      Unsigned32
  MAX-ACCESS  read-only
  STATUS      current
  DESCRIPTION
    "The time MinutesUnitCount was updated (in seconds since January 1, 1970)."
  ::= { proxyConnHistMinutesEntry 4 }


-- Proxied connections per second history hours

proxyConnHistHoursTable OBJECT-TYPE
  SYNTAX      SEQUENCE OF ProxyConnHistHoursEntry
  MAX-ACCESS  not-accessible
  STATUS      current
  DESCRIPTION
    "Historical (sampled) data every hour for a day."
  ::= { tpt-ddos 11 }

proxyConnHistHoursEntry OBJECT-TYPE
  SYNTAX      ProxyConnHistHoursEntry
  MAX-ACCESS  not-accessible
  STATUS      current
  DESCRIPTION
    "An entry in the proxied connections per second history hours table.
     Rows cannot be created or deleted.
    "
  INDEX       { proxyConnHistHoursGlobalID, proxyConnHistHoursIndex }
  ::= { proxyConnHistHoursTable 1 }

ProxyConnHistHoursEntry ::= SEQUENCE {
  proxyConnHistHoursGlobalID   OCTET STRING (SIZE (0..40)),
  proxyConnHistHoursIndex      Unsigned32,
  proxyConnHistHoursUnitCount  Counter64,
  proxyConnHistHoursTimestamp  Unsigned32
}

proxyConnHistHoursGlobalID OBJECT-TYPE
  SYNTAX      OCTET STRING (SIZE (0..40))
  MAX-ACCESS  not-accessible
  STATUS      current
  DESCRIPTION
    "The global identifier of a DDoS filter group."
  ::= { proxyConnHistHoursEntry 1 }

proxyConnHistHoursIndex OBJECT-TYPE
  SYNTAX      Unsigned32
  MAX-ACCESS  not-accessible
  STATUS      current
  DESCRIPTION
    "The index (0-23) of the hour."
  ::= { proxyConnHistHoursEntry 2 }

proxyConnHistHoursUnitCount OBJECT-TYPE
  SYNTAX      Counter64
  MAX-ACCESS  read-only
  STATUS      current
  DESCRIPTION
    "The average of the MinutesUnitCount values corresponding to this hour."
  ::= { proxyConnHistHoursEntry 3 }

proxyConnHistHoursTimestamp OBJECT-TYPE
  SYNTAX      Unsigned32
  MAX-ACCESS  read-only
  STATUS      current
  DESCRIPTION
    "The time HoursUnitCount was updated (in seconds since January 1, 1970)."
  ::= { proxyConnHistHoursEntry 4 }


-- Proxied connections per second history days

proxyConnHistDaysTable OBJECT-TYPE
  SYNTAX      SEQUENCE OF ProxyConnHistDaysEntry
  MAX-ACCESS  not-accessible
  STATUS      current
  DESCRIPTION
    "Historical (sampled) data every day for 35 days."
  ::= { tpt-ddos 12 }

proxyConnHistDaysEntry OBJECT-TYPE
  SYNTAX      ProxyConnHistDaysEntry
  MAX-ACCESS  not-accessible
  STATUS      current
  DESCRIPTION
    "An entry in the proxied connections per second history days table.
     Rows cannot be created or deleted.
    "
  INDEX       { proxyConnHistDaysGlobalID, proxyConnHistDaysIndex }
  ::= { proxyConnHistDaysTable 1 }

ProxyConnHistDaysEntry ::= SEQUENCE {
  proxyConnHistDaysGlobalID   OCTET STRING (SIZE (0..40)),
  proxyConnHistDaysIndex      Unsigned32,
  proxyConnHistDaysUnitCount  Counter64,
  proxyConnHistDaysTimestamp  Unsigned32
}

proxyConnHistDaysGlobalID OBJECT-TYPE
  SYNTAX      OCTET STRING (SIZE (0..40))
  MAX-ACCESS  not-accessible
  STATUS      current
  DESCRIPTION
    "The global identifier of a DDoS filter group."
  ::= { proxyConnHistDaysEntry 1 }

proxyConnHistDaysIndex OBJECT-TYPE
  SYNTAX      Unsigned32
  MAX-ACCESS  not-accessible
  STATUS      current
  DESCRIPTION
    "The index (0-34) of the day."
  ::= { proxyConnHistDaysEntry 2 }

proxyConnHistDaysUnitCount OBJECT-TYPE
  SYNTAX      Counter64
  MAX-ACCESS  read-only
  STATUS      current
  DESCRIPTION
    "The average of the HoursUnitCount values corresponding to this day."
  ::= { proxyConnHistDaysEntry 3 }

proxyConnHistDaysTimestamp OBJECT-TYPE
  SYNTAX      Unsigned32
  MAX-ACCESS  read-only
  STATUS      current
  DESCRIPTION
    "The time DaysUnitCount was updated (in seconds since January 1, 1970)."
  ::= { proxyConnHistDaysEntry 4 }


-- - - - - - - - - - - - - - - - - - - - - - - - - - - - - - - - - - - - - - -
--
-- CPS filter statistics
--
-- - - - - - - - - - - - - - - - - - - - - - - - - - - - - - - - - - - - - - -

-- Rejected connections per second (CPS) history seconds

rejectCpsHistSecondsTable OBJECT-TYPE
  SYNTAX      SEQUENCE OF RejectCpsHistSecondsEntry
  MAX-ACCESS  not-accessible
  STATUS      current
  DESCRIPTION
    "Historical (sampled) data every second for a minute."
  ::= { tpt-ddos 15 }

rejectCpsHistSecondsEntry OBJECT-TYPE
  SYNTAX      RejectCpsHistSecondsEntry
  MAX-ACCESS  not-accessible
  STATUS      current
  DESCRIPTION
    "An entry in the rejected connections per sec (CPS) history seconds table.
     Rows cannot be created or deleted.
    "
  INDEX       { rejectCpsHistSecondsGlobalID, rejectCpsHistSecondsIndex }
  ::= { rejectCpsHistSecondsTable 1 }

RejectCpsHistSecondsEntry ::= SEQUENCE {
  rejectCpsHistSecondsGlobalID   OCTET STRING (SIZE (0..40)),
  rejectCpsHistSecondsIndex      Unsigned32,
  rejectCpsHistSecondsUnitCount  Counter64,
  rejectCpsHistSecondsTimestamp  Unsigned32
}

rejectCpsHistSecondsGlobalID OBJECT-TYPE
  SYNTAX      OCTET STRING (SIZE (0..40))
  MAX-ACCESS  not-accessible
  STATUS      current
  DESCRIPTION
    "The global identifier of a DDoS filter group."
  ::= { rejectCpsHistSecondsEntry 1 }

rejectCpsHistSecondsIndex OBJECT-TYPE
  SYNTAX      Unsigned32
  MAX-ACCESS  not-accessible
  STATUS      current
  DESCRIPTION
    "The index (0-59) of the second."
  ::= { rejectCpsHistSecondsEntry 2 }

rejectCpsHistSecondsUnitCount OBJECT-TYPE
  SYNTAX      Counter64
  MAX-ACCESS  read-only
  STATUS      current
  DESCRIPTION
    "The count of filter-specific units matching the criteria for
     this filter in the specified second."
  ::= { rejectCpsHistSecondsEntry 3 }

rejectCpsHistSecondsTimestamp OBJECT-TYPE
  SYNTAX      Unsigned32
  MAX-ACCESS  read-only
  STATUS      current
  DESCRIPTION
    "The time SecondsUnitCount was updated (in seconds since January 1, 1970)."
  ::= { rejectCpsHistSecondsEntry 4 }


-- Rejected connections per second (CPS) history minutes

rejectCpsHistMinutesTable OBJECT-TYPE
  SYNTAX      SEQUENCE OF RejectCpsHistMinutesEntry
  MAX-ACCESS  not-accessible
  STATUS      current
  DESCRIPTION
    "Historical (sampled) data every minute for an hour."
  ::= { tpt-ddos 16 }

rejectCpsHistMinutesEntry OBJECT-TYPE
  SYNTAX      RejectCpsHistMinutesEntry
  MAX-ACCESS  not-accessible
  STATUS      current
  DESCRIPTION
    "An entry in the rejected connections per sec (CPS) history minutes table.
     Rows cannot be created or deleted.
    "
  INDEX       { rejectCpsHistMinutesGlobalID, rejectCpsHistMinutesIndex }
  ::= { rejectCpsHistMinutesTable 1 }

RejectCpsHistMinutesEntry ::= SEQUENCE {
  rejectCpsHistMinutesGlobalID   OCTET STRING (SIZE (0..40)),
  rejectCpsHistMinutesIndex      Unsigned32,
  rejectCpsHistMinutesUnitCount  Counter64,
  rejectCpsHistMinutesTimestamp  Unsigned32
}

rejectCpsHistMinutesGlobalID OBJECT-TYPE
  SYNTAX      OCTET STRING (SIZE (0..40))
  MAX-ACCESS  not-accessible
  STATUS      current
  DESCRIPTION
    "The global identifier of a DDoS filter group."
  ::= { rejectCpsHistMinutesEntry 1 }

rejectCpsHistMinutesIndex OBJECT-TYPE
  SYNTAX      Unsigned32
  MAX-ACCESS  not-accessible
  STATUS      current
  DESCRIPTION
    "The index (0-59) of the minute."
  ::= { rejectCpsHistMinutesEntry 2 }

rejectCpsHistMinutesUnitCount OBJECT-TYPE
  SYNTAX      Counter64
  MAX-ACCESS  read-only
  STATUS      current
  DESCRIPTION
    "The average of the SecondsUnitCount values corresponding to this minute."
  ::= { rejectCpsHistMinutesEntry 3 }

rejectCpsHistMinutesTimestamp OBJECT-TYPE
  SYNTAX      Unsigned32
  MAX-ACCESS  read-only
  STATUS      current
  DESCRIPTION
    "The time MinutesUnitCount was updated (in seconds since January 1, 1970)."
  ::= { rejectCpsHistMinutesEntry 4 }


-- Rejected connections per second (CPS) history hours

rejectCpsHistHoursTable OBJECT-TYPE
  SYNTAX      SEQUENCE OF RejectCpsHistHoursEntry
  MAX-ACCESS  not-accessible
  STATUS      current
  DESCRIPTION
    "Historical (sampled) data every hour for a day."
  ::= { tpt-ddos 17 }

rejectCpsHistHoursEntry OBJECT-TYPE
  SYNTAX      RejectCpsHistHoursEntry
  MAX-ACCESS  not-accessible
  STATUS      current
  DESCRIPTION
    "An entry in the rejected connections per sec (CPS) history hours table.
     Rows cannot be created or deleted.
    "
  INDEX       { rejectCpsHistHoursGlobalID, rejectCpsHistHoursIndex }
  ::= { rejectCpsHistHoursTable 1 }

RejectCpsHistHoursEntry ::= SEQUENCE {
  rejectCpsHistHoursGlobalID   OCTET STRING (SIZE (0..40)),
  rejectCpsHistHoursIndex      Unsigned32,
  rejectCpsHistHoursUnitCount  Counter64,
  rejectCpsHistHoursTimestamp  Unsigned32
}

rejectCpsHistHoursGlobalID OBJECT-TYPE
  SYNTAX      OCTET STRING (SIZE (0..40))
  MAX-ACCESS  not-accessible
  STATUS      current
  DESCRIPTION
    "The global identifier of a DDoS filter group."
  ::= { rejectCpsHistHoursEntry 1 }

rejectCpsHistHoursIndex OBJECT-TYPE
  SYNTAX      Unsigned32
  MAX-ACCESS  not-accessible
  STATUS      current
  DESCRIPTION
    "The index (0-23) of the hour."
  ::= { rejectCpsHistHoursEntry 2 }

rejectCpsHistHoursUnitCount OBJECT-TYPE
  SYNTAX      Counter64
  MAX-ACCESS  read-only
  STATUS      current
  DESCRIPTION
    "The average of the MinutesUnitCount values corresponding to this hour."
  ::= { rejectCpsHistHoursEntry 3 }

rejectCpsHistHoursTimestamp OBJECT-TYPE
  SYNTAX      Unsigned32
  MAX-ACCESS  read-only
  STATUS      current
  DESCRIPTION
    "The time HoursUnitCount was updated (in seconds since January 1, 1970)."
  ::= { rejectCpsHistHoursEntry 4 }


-- Rejected connections per second (CPS) history days

rejectCpsHistDaysTable OBJECT-TYPE
  SYNTAX      SEQUENCE OF RejectCpsHistDaysEntry
  MAX-ACCESS  not-accessible
  STATUS      current
  DESCRIPTION
    "Historical (sampled) data every day for 35 days."
  ::= { tpt-ddos 18 }

rejectCpsHistDaysEntry OBJECT-TYPE
  SYNTAX      RejectCpsHistDaysEntry
  MAX-ACCESS  not-accessible
  STATUS      current
  DESCRIPTION
    "An entry in the rejected connections per sec (CPS) history days table.
     Rows cannot be created or deleted.
    "
  INDEX       { rejectCpsHistDaysGlobalID, rejectCpsHistDaysIndex }
  ::= { rejectCpsHistDaysTable 1 }

RejectCpsHistDaysEntry ::= SEQUENCE {
  rejectCpsHistDaysGlobalID   OCTET STRING (SIZE (0..40)),
  rejectCpsHistDaysIndex      Unsigned32,
  rejectCpsHistDaysUnitCount  Counter64,
  rejectCpsHistDaysTimestamp  Unsigned32
}

rejectCpsHistDaysGlobalID OBJECT-TYPE
  SYNTAX      OCTET STRING (SIZE (0..40))
  MAX-ACCESS  not-accessible
  STATUS      current
  DESCRIPTION
    "The global identifier of a DDoS filter group."
  ::= { rejectCpsHistDaysEntry 1 }

rejectCpsHistDaysIndex OBJECT-TYPE
  SYNTAX      Unsigned32
  MAX-ACCESS  not-accessible
  STATUS      current
  DESCRIPTION
    "The index (0-34) of the day."
  ::= { rejectCpsHistDaysEntry 2 }

rejectCpsHistDaysUnitCount OBJECT-TYPE
  SYNTAX      Counter64
  MAX-ACCESS  read-only
  STATUS      current
  DESCRIPTION
    "The average of the HoursUnitCount values corresponding to this day."
  ::= { rejectCpsHistDaysEntry 3 }

rejectCpsHistDaysTimestamp OBJECT-TYPE
  SYNTAX      Unsigned32
  MAX-ACCESS  read-only
  STATUS      current
  DESCRIPTION
    "The time DaysUnitCount was updated (in seconds since January 1, 1970)."
  ::= { rejectCpsHistDaysEntry 4 }

-- Accepted connections per second (CPS) history seconds

acceptCpsHistSecondsTable OBJECT-TYPE
  SYNTAX      SEQUENCE OF AcceptCpsHistSecondsEntry
  MAX-ACCESS  not-accessible
  STATUS      current
  DESCRIPTION
    "Historical (sampled) data every second for a minute."
  ::= { tpt-ddos 19 }

acceptCpsHistSecondsEntry OBJECT-TYPE
  SYNTAX      AcceptCpsHistSecondsEntry
  MAX-ACCESS  not-accessible
  STATUS      current
  DESCRIPTION
    "An entry in the accepted connections per sec (CPS) history seconds table.
     Rows cannot be created or deleted.
    "
  INDEX       { acceptCpsHistSecondsGlobalID, acceptCpsHistSecondsIndex }
  ::= { acceptCpsHistSecondsTable 1 }

AcceptCpsHistSecondsEntry ::= SEQUENCE {
  acceptCpsHistSecondsGlobalID   OCTET STRING (SIZE (0..40)),
  acceptCpsHistSecondsIndex      Unsigned32,
  acceptCpsHistSecondsUnitCount  Counter64,
  acceptCpsHistSecondsTimestamp  Unsigned32
}

acceptCpsHistSecondsGlobalID OBJECT-TYPE
  SYNTAX      OCTET STRING (SIZE (0..40))
  MAX-ACCESS  not-accessible
  STATUS      current
  DESCRIPTION
    "The global identifier of a DDoS filter group."
  ::= { acceptCpsHistSecondsEntry 1 }

acceptCpsHistSecondsIndex OBJECT-TYPE
  SYNTAX      Unsigned32
  MAX-ACCESS  not-accessible
  STATUS      current
  DESCRIPTION
    "The index (0-59) of the second."
  ::= { acceptCpsHistSecondsEntry 2 }

acceptCpsHistSecondsUnitCount OBJECT-TYPE
  SYNTAX      Counter64
  MAX-ACCESS  read-only
  STATUS      current
  DESCRIPTION
    "The count of filter-specific units matching the criteria for
     this filter in the specified second."
  ::= { acceptCpsHistSecondsEntry 3 }

acceptCpsHistSecondsTimestamp OBJECT-TYPE
  SYNTAX      Unsigned32
  MAX-ACCESS  read-only
  STATUS      current
  DESCRIPTION
    "The time SecondsUnitCount was updated (in seconds since January 1, 1970)."
  ::= { acceptCpsHistSecondsEntry 4 }


-- Accepted connections per second (CPS) history minutes

acceptCpsHistMinutesTable OBJECT-TYPE
  SYNTAX      SEQUENCE OF AcceptCpsHistMinutesEntry
  MAX-ACCESS  not-accessible
  STATUS      current
  DESCRIPTION
    "Historical (sampled) data every minute for an hour."
  ::= { tpt-ddos 20 }

acceptCpsHistMinutesEntry OBJECT-TYPE
  SYNTAX      AcceptCpsHistMinutesEntry
  MAX-ACCESS  not-accessible
  STATUS      current
  DESCRIPTION
    "An entry in the accepted connections per sec (CPS) history minutes table.
     Rows cannot be created or deleted.
    "
  INDEX       { acceptCpsHistMinutesGlobalID, acceptCpsHistMinutesIndex }
  ::= { acceptCpsHistMinutesTable 1 }

AcceptCpsHistMinutesEntry ::= SEQUENCE {
  acceptCpsHistMinutesGlobalID   OCTET STRING (SIZE (0..40)),
  acceptCpsHistMinutesIndex      Unsigned32,
  acceptCpsHistMinutesUnitCount  Counter64,
  acceptCpsHistMinutesTimestamp  Unsigned32
}

acceptCpsHistMinutesGlobalID OBJECT-TYPE
  SYNTAX      OCTET STRING (SIZE (0..40))
  MAX-ACCESS  not-accessible
  STATUS      current
  DESCRIPTION
    "The global identifier of a DDoS filter group."
  ::= { acceptCpsHistMinutesEntry 1 }

acceptCpsHistMinutesIndex OBJECT-TYPE
  SYNTAX      Unsigned32
  MAX-ACCESS  not-accessible
  STATUS      current
  DESCRIPTION
    "The index (0-59) of the minute."
  ::= { acceptCpsHistMinutesEntry 2 }

acceptCpsHistMinutesUnitCount OBJECT-TYPE
  SYNTAX      Counter64
  MAX-ACCESS  read-only
  STATUS      current
  DESCRIPTION
    "The average of the SecondsUnitCount values corresponding to this minute."
  ::= { acceptCpsHistMinutesEntry 3 }

acceptCpsHistMinutesTimestamp OBJECT-TYPE
  SYNTAX      Unsigned32
  MAX-ACCESS  read-only
  STATUS      current
  DESCRIPTION
    "The time MinutesUnitCount was updated (in seconds since January 1, 1970)."
  ::= { acceptCpsHistMinutesEntry 4 }


-- Accepted connections per second (CPS) history hours

acceptCpsHistHoursTable OBJECT-TYPE
  SYNTAX      SEQUENCE OF AcceptCpsHistHoursEntry
  MAX-ACCESS  not-accessible
  STATUS      current
  DESCRIPTION
    "Historical (sampled) data every hour for a day."
  ::= { tpt-ddos 21 }

acceptCpsHistHoursEntry OBJECT-TYPE
  SYNTAX      AcceptCpsHistHoursEntry
  MAX-ACCESS  not-accessible
  STATUS      current
  DESCRIPTION
    "An entry in the accepted connections per sec (CPS) history hours table.
     Rows cannot be created or deleted.
    "
  INDEX       { acceptCpsHistHoursGlobalID, acceptCpsHistHoursIndex }
  ::= { acceptCpsHistHoursTable 1 }

AcceptCpsHistHoursEntry ::= SEQUENCE {
  acceptCpsHistHoursGlobalID   OCTET STRING (SIZE (0..40)),
  acceptCpsHistHoursIndex      Unsigned32,
  acceptCpsHistHoursUnitCount  Counter64,
  acceptCpsHistHoursTimestamp  Unsigned32
}

acceptCpsHistHoursGlobalID OBJECT-TYPE
  SYNTAX      OCTET STRING (SIZE (0..40))
  MAX-ACCESS  not-accessible
  STATUS      current
  DESCRIPTION
    "The global identifier of a DDoS filter group."
  ::= { acceptCpsHistHoursEntry 1 }

acceptCpsHistHoursIndex OBJECT-TYPE
  SYNTAX      Unsigned32
  MAX-ACCESS  not-accessible
  STATUS      current
  DESCRIPTION
    "The index (0-23) of the hour."
  ::= { acceptCpsHistHoursEntry 2 }

acceptCpsHistHoursUnitCount OBJECT-TYPE
  SYNTAX      Counter64
  MAX-ACCESS  read-only
  STATUS      current
  DESCRIPTION
    "The average of the MinutesUnitCount values corresponding to this hour."
  ::= { acceptCpsHistHoursEntry 3 }

acceptCpsHistHoursTimestamp OBJECT-TYPE
  SYNTAX      Unsigned32
  MAX-ACCESS  read-only
  STATUS      current
  DESCRIPTION
    "The time HoursUnitCount was updated (in seconds since January 1, 1970)."
  ::= { acceptCpsHistHoursEntry 4 }


-- Accepted connections per second (CPS) history days

acceptCpsHistDaysTable OBJECT-TYPE
  SYNTAX      SEQUENCE OF AcceptCpsHistDaysEntry
  MAX-ACCESS  not-accessible
  STATUS      current
  DESCRIPTION
    "Historical (sampled) data every day for 35 days."
  ::= { tpt-ddos 22 }

acceptCpsHistDaysEntry OBJECT-TYPE
  SYNTAX      AcceptCpsHistDaysEntry
  MAX-ACCESS  not-accessible
  STATUS      current
  DESCRIPTION
    "An entry in the accepted connections per sec (CPS) history days table.
     Rows cannot be created or deleted.
    "
  INDEX       { acceptCpsHistDaysGlobalID, acceptCpsHistDaysIndex }
  ::= { acceptCpsHistDaysTable 1 }

AcceptCpsHistDaysEntry ::= SEQUENCE {
  acceptCpsHistDaysGlobalID   OCTET STRING (SIZE (0..40)),
  acceptCpsHistDaysIndex      Unsigned32,
  acceptCpsHistDaysUnitCount  Counter64,
  acceptCpsHistDaysTimestamp  Unsigned32
}

acceptCpsHistDaysGlobalID OBJECT-TYPE
  SYNTAX      OCTET STRING (SIZE (0..40))
  MAX-ACCESS  not-accessible
  STATUS      current
  DESCRIPTION
    "The global identifier of a DDoS filter group."
  ::= { acceptCpsHistDaysEntry 1 }

acceptCpsHistDaysIndex OBJECT-TYPE
  SYNTAX      Unsigned32
  MAX-ACCESS  not-accessible
  STATUS      current
  DESCRIPTION
    "The index (0-34) of the day."
  ::= { acceptCpsHistDaysEntry 2 }

acceptCpsHistDaysUnitCount OBJECT-TYPE
  SYNTAX      Counter64
  MAX-ACCESS  read-only
  STATUS      current
  DESCRIPTION
    "The average of the HoursUnitCount values corresponding to this day."
  ::= { acceptCpsHistDaysEntry 3 }

acceptCpsHistDaysTimestamp OBJECT-TYPE
  SYNTAX      Unsigned32
  MAX-ACCESS  read-only
  STATUS      current
  DESCRIPTION
    "The time DaysUnitCount was updated (in seconds since January 1, 1970)."
  ::= { acceptCpsHistDaysEntry 4 }


-- - - - - - - - - - - - - - - - - - - - - - - - - - - - - - - - - - - - - - -
--
-- EST filter statistics
--
-- - - - - - - - - - - - - - - - - - - - - - - - - - - - - - - - - - - - - - -

-- Rejected connections per second (EST) history seconds

rejectEstHistSecondsTable OBJECT-TYPE
  SYNTAX      SEQUENCE OF RejectEstHistSecondsEntry
  MAX-ACCESS  not-accessible
  STATUS      current
  DESCRIPTION
    "Historical (sampled) data every second for a minute."
  ::= { tpt-ddos 25 }

rejectEstHistSecondsEntry OBJECT-TYPE
  SYNTAX      RejectEstHistSecondsEntry
  MAX-ACCESS  not-accessible
  STATUS      current
  DESCRIPTION
    "An entry in the rejected connections per sec (EST) history seconds table.
     Rows cannot be created or deleted.
    "
  INDEX       { rejectEstHistSecondsGlobalID, rejectEstHistSecondsIndex }
  ::= { rejectEstHistSecondsTable 1 }

RejectEstHistSecondsEntry ::= SEQUENCE {
  rejectEstHistSecondsGlobalID   OCTET STRING (SIZE (0..40)),
  rejectEstHistSecondsIndex      Unsigned32,
  rejectEstHistSecondsUnitCount  Counter64,
  rejectEstHistSecondsTimestamp  Unsigned32
}

rejectEstHistSecondsGlobalID OBJECT-TYPE
  SYNTAX      OCTET STRING (SIZE (0..40))
  MAX-ACCESS  not-accessible
  STATUS      current
  DESCRIPTION
    "The global identifier of a DDoS filter group."
  ::= { rejectEstHistSecondsEntry 1 }

rejectEstHistSecondsIndex OBJECT-TYPE
  SYNTAX      Unsigned32
  MAX-ACCESS  not-accessible
  STATUS      current
  DESCRIPTION
    "The index (0-59) of the second."
  ::= { rejectEstHistSecondsEntry 2 }

rejectEstHistSecondsUnitCount OBJECT-TYPE
  SYNTAX      Counter64
  MAX-ACCESS  read-only
  STATUS      current
  DESCRIPTION
    "The count of filter-specific units matching the criteria for
     this filter in the specified second."
  ::= { rejectEstHistSecondsEntry 3 }

rejectEstHistSecondsTimestamp OBJECT-TYPE
  SYNTAX      Unsigned32
  MAX-ACCESS  read-only
  STATUS      current
  DESCRIPTION
    "The time SecondsUnitCount was updated (in seconds since January 1, 1970)."
  ::= { rejectEstHistSecondsEntry 4 }


-- Rejected connections per second (EST) history minutes

rejectEstHistMinutesTable OBJECT-TYPE
  SYNTAX      SEQUENCE OF RejectEstHistMinutesEntry
  MAX-ACCESS  not-accessible
  STATUS      current
  DESCRIPTION
    "Historical (sampled) data every minute for an hour."
  ::= { tpt-ddos 26 }

rejectEstHistMinutesEntry OBJECT-TYPE
  SYNTAX      RejectEstHistMinutesEntry
  MAX-ACCESS  not-accessible
  STATUS      current
  DESCRIPTION
    "An entry in the rejected connections per sec (EST) history minutes table.
     Rows cannot be created or deleted.
    "
  INDEX       { rejectEstHistMinutesGlobalID, rejectEstHistMinutesIndex }
  ::= { rejectEstHistMinutesTable 1 }

RejectEstHistMinutesEntry ::= SEQUENCE {
  rejectEstHistMinutesGlobalID   OCTET STRING (SIZE (0..40)),
  rejectEstHistMinutesIndex      Unsigned32,
  rejectEstHistMinutesUnitCount  Counter64,
  rejectEstHistMinutesTimestamp  Unsigned32
}

rejectEstHistMinutesGlobalID OBJECT-TYPE
  SYNTAX      OCTET STRING (SIZE (0..40))
  MAX-ACCESS  not-accessible
  STATUS      current
  DESCRIPTION
    "The global identifier of a DDoS filter group."
  ::= { rejectEstHistMinutesEntry 1 }

rejectEstHistMinutesIndex OBJECT-TYPE
  SYNTAX      Unsigned32
  MAX-ACCESS  not-accessible
  STATUS      current
  DESCRIPTION
    "The index (0-59) of the minute."
  ::= { rejectEstHistMinutesEntry 2 }

rejectEstHistMinutesUnitCount OBJECT-TYPE
  SYNTAX      Counter64
  MAX-ACCESS  read-only
  STATUS      current
  DESCRIPTION
    "The average of the SecondsUnitCount values corresponding to this minute."
  ::= { rejectEstHistMinutesEntry 3 }

rejectEstHistMinutesTimestamp OBJECT-TYPE
  SYNTAX      Unsigned32
  MAX-ACCESS  read-only
  STATUS      current
  DESCRIPTION
    "The time MinutesUnitCount was updated (in seconds since January 1, 1970)."
  ::= { rejectEstHistMinutesEntry 4 }


-- Rejected connections per second (EST) history hours

rejectEstHistHoursTable OBJECT-TYPE
  SYNTAX      SEQUENCE OF RejectEstHistHoursEntry
  MAX-ACCESS  not-accessible
  STATUS      current
  DESCRIPTION
    "Historical (sampled) data every hour for a day."
  ::= { tpt-ddos 27 }

rejectEstHistHoursEntry OBJECT-TYPE
  SYNTAX      RejectEstHistHoursEntry
  MAX-ACCESS  not-accessible
  STATUS      current
  DESCRIPTION
    "An entry in the rejected connections per sec (EST) history hours table.
     Rows cannot be created or deleted.
    "
  INDEX       { rejectEstHistHoursGlobalID, rejectEstHistHoursIndex }
  ::= { rejectEstHistHoursTable 1 }

RejectEstHistHoursEntry ::= SEQUENCE {
  rejectEstHistHoursGlobalID   OCTET STRING (SIZE (0..40)),
  rejectEstHistHoursIndex      Unsigned32,
  rejectEstHistHoursUnitCount  Counter64,
  rejectEstHistHoursTimestamp  Unsigned32
}

rejectEstHistHoursGlobalID OBJECT-TYPE
  SYNTAX      OCTET STRING (SIZE (0..40))
  MAX-ACCESS  not-accessible
  STATUS      current
  DESCRIPTION
    "The global identifier of a DDoS filter group."
  ::= { rejectEstHistHoursEntry 1 }

rejectEstHistHoursIndex OBJECT-TYPE
  SYNTAX      Unsigned32
  MAX-ACCESS  not-accessible
  STATUS      current
  DESCRIPTION
    "The index (0-23) of the hour."
  ::= { rejectEstHistHoursEntry 2 }

rejectEstHistHoursUnitCount OBJECT-TYPE
  SYNTAX      Counter64
  MAX-ACCESS  read-only
  STATUS      current
  DESCRIPTION
    "The average of the MinutesUnitCount values corresponding to this hour."
  ::= { rejectEstHistHoursEntry 3 }

rejectEstHistHoursTimestamp OBJECT-TYPE
  SYNTAX      Unsigned32
  MAX-ACCESS  read-only
  STATUS      current
  DESCRIPTION
    "The time HoursUnitCount was updated (in seconds since January 1, 1970)."
  ::= { rejectEstHistHoursEntry 4 }


-- Rejected connections per second (EST) history days

rejectEstHistDaysTable OBJECT-TYPE
  SYNTAX      SEQUENCE OF RejectEstHistDaysEntry
  MAX-ACCESS  not-accessible
  STATUS      current
  DESCRIPTION
    "Historical (sampled) data every day for 35 days."
  ::= { tpt-ddos 28 }

rejectEstHistDaysEntry OBJECT-TYPE
  SYNTAX      RejectEstHistDaysEntry
  MAX-ACCESS  not-accessible
  STATUS      current
  DESCRIPTION
    "An entry in the rejected connections per sec (EST) history days table.
     Rows cannot be created or deleted.
    "
  INDEX       { rejectEstHistDaysGlobalID, rejectEstHistDaysIndex }
  ::= { rejectEstHistDaysTable 1 }

RejectEstHistDaysEntry ::= SEQUENCE {
  rejectEstHistDaysGlobalID   OCTET STRING (SIZE (0..40)),
  rejectEstHistDaysIndex      Unsigned32,
  rejectEstHistDaysUnitCount  Counter64,
  rejectEstHistDaysTimestamp  Unsigned32
}

rejectEstHistDaysGlobalID OBJECT-TYPE
  SYNTAX      OCTET STRING (SIZE (0..40))
  MAX-ACCESS  not-accessible
  STATUS      current
  DESCRIPTION
    "The global identifier of a DDoS filter group."
  ::= { rejectEstHistDaysEntry 1 }

rejectEstHistDaysIndex OBJECT-TYPE
  SYNTAX      Unsigned32
  MAX-ACCESS  not-accessible
  STATUS      current
  DESCRIPTION
    "The index (0-34) of the day."
  ::= { rejectEstHistDaysEntry 2 }

rejectEstHistDaysUnitCount OBJECT-TYPE
  SYNTAX      Counter64
  MAX-ACCESS  read-only
  STATUS      current
  DESCRIPTION
    "The average of the HoursUnitCount values corresponding to this day."
  ::= { rejectEstHistDaysEntry 3 }

rejectEstHistDaysTimestamp OBJECT-TYPE
  SYNTAX      Unsigned32
  MAX-ACCESS  read-only
  STATUS      current
  DESCRIPTION
    "The time DaysUnitCount was updated (in seconds since January 1, 1970)."
  ::= { rejectEstHistDaysEntry 4 }

-- Accepted connections per second (EST) history seconds

acceptEstHistSecondsTable OBJECT-TYPE
  SYNTAX      SEQUENCE OF AcceptEstHistSecondsEntry
  MAX-ACCESS  not-accessible
  STATUS      current
  DESCRIPTION
    "Historical (sampled) data every second for a minute."
  ::= { tpt-ddos 29 }

acceptEstHistSecondsEntry OBJECT-TYPE
  SYNTAX      AcceptEstHistSecondsEntry
  MAX-ACCESS  not-accessible
  STATUS      current
  DESCRIPTION
    "An entry in the accepted connections per sec (EST) history seconds table.
     Rows cannot be created or deleted.
    "
  INDEX       { acceptEstHistSecondsGlobalID, acceptEstHistSecondsIndex }
  ::= { acceptEstHistSecondsTable 1 }

AcceptEstHistSecondsEntry ::= SEQUENCE {
  acceptEstHistSecondsGlobalID   OCTET STRING (SIZE (0..40)),
  acceptEstHistSecondsIndex      Unsigned32,
  acceptEstHistSecondsUnitCount  Counter64,
  acceptEstHistSecondsTimestamp  Unsigned32
}

acceptEstHistSecondsGlobalID OBJECT-TYPE
  SYNTAX      OCTET STRING (SIZE (0..40))
  MAX-ACCESS  not-accessible
  STATUS      current
  DESCRIPTION
    "The global identifier of a DDoS filter group."
  ::= { acceptEstHistSecondsEntry 1 }

acceptEstHistSecondsIndex OBJECT-TYPE
  SYNTAX      Unsigned32
  MAX-ACCESS  not-accessible
  STATUS      current
  DESCRIPTION
    "The index (0-59) of the second."
  ::= { acceptEstHistSecondsEntry 2 }

acceptEstHistSecondsUnitCount OBJECT-TYPE
  SYNTAX      Counter64
  MAX-ACCESS  read-only
  STATUS      current
  DESCRIPTION
    "The count of filter-specific units matching the criteria for
     this filter in the specified second."
  ::= { acceptEstHistSecondsEntry 3 }

acceptEstHistSecondsTimestamp OBJECT-TYPE
  SYNTAX      Unsigned32
  MAX-ACCESS  read-only
  STATUS      current
  DESCRIPTION
    "The time SecondsUnitCount was updated (in seconds since January 1, 1970)."
  ::= { acceptEstHistSecondsEntry 4 }


-- Accepted connections per second (EST) history minutes

acceptEstHistMinutesTable OBJECT-TYPE
  SYNTAX      SEQUENCE OF AcceptEstHistMinutesEntry
  MAX-ACCESS  not-accessible
  STATUS      current
  DESCRIPTION
    "Historical (sampled) data every minute for an hour."
  ::= { tpt-ddos 30 }

acceptEstHistMinutesEntry OBJECT-TYPE
  SYNTAX      AcceptEstHistMinutesEntry
  MAX-ACCESS  not-accessible
  STATUS      current
  DESCRIPTION
    "An entry in the accepted connections per sec (EST) history minutes table.
     Rows cannot be created or deleted.
    "
  INDEX       { acceptEstHistMinutesGlobalID, acceptEstHistMinutesIndex }
  ::= { acceptEstHistMinutesTable 1 }

AcceptEstHistMinutesEntry ::= SEQUENCE {
  acceptEstHistMinutesGlobalID   OCTET STRING (SIZE (0..40)),
  acceptEstHistMinutesIndex      Unsigned32,
  acceptEstHistMinutesUnitCount  Counter64,
  acceptEstHistMinutesTimestamp  Unsigned32
}

acceptEstHistMinutesGlobalID OBJECT-TYPE
  SYNTAX      OCTET STRING (SIZE (0..40))
  MAX-ACCESS  not-accessible
  STATUS      current
  DESCRIPTION
    "The global identifier of a DDoS filter group."
  ::= { acceptEstHistMinutesEntry 1 }

acceptEstHistMinutesIndex OBJECT-TYPE
  SYNTAX      Unsigned32
  MAX-ACCESS  not-accessible
  STATUS      current
  DESCRIPTION
    "The index (0-59) of the minute."
  ::= { acceptEstHistMinutesEntry 2 }

acceptEstHistMinutesUnitCount OBJECT-TYPE
  SYNTAX      Counter64
  MAX-ACCESS  read-only
  STATUS      current
  DESCRIPTION
    "The average of the SecondsUnitCount values corresponding to this minute."
  ::= { acceptEstHistMinutesEntry 3 }

acceptEstHistMinutesTimestamp OBJECT-TYPE
  SYNTAX      Unsigned32
  MAX-ACCESS  read-only
  STATUS      current
  DESCRIPTION
    "The time MinutesUnitCount was updated (in seconds since January 1, 1970)."
  ::= { acceptEstHistMinutesEntry 4 }


-- Accepted connections per second (EST) history hours

acceptEstHistHoursTable OBJECT-TYPE
  SYNTAX      SEQUENCE OF AcceptEstHistHoursEntry
  MAX-ACCESS  not-accessible
  STATUS      current
  DESCRIPTION
    "Historical (sampled) data every hour for a day."
  ::= { tpt-ddos 31 }

acceptEstHistHoursEntry OBJECT-TYPE
  SYNTAX      AcceptEstHistHoursEntry
  MAX-ACCESS  not-accessible
  STATUS      current
  DESCRIPTION
    "An entry in the accepted connections per sec (EST) history hours table.
     Rows cannot be created or deleted.
    "
  INDEX       { acceptEstHistHoursGlobalID, acceptEstHistHoursIndex }
  ::= { acceptEstHistHoursTable 1 }

AcceptEstHistHoursEntry ::= SEQUENCE {
  acceptEstHistHoursGlobalID   OCTET STRING (SIZE (0..40)),
  acceptEstHistHoursIndex      Unsigned32,
  acceptEstHistHoursUnitCount  Counter64,
  acceptEstHistHoursTimestamp  Unsigned32
}

acceptEstHistHoursGlobalID OBJECT-TYPE
  SYNTAX      OCTET STRING (SIZE (0..40))
  MAX-ACCESS  not-accessible
  STATUS      current
  DESCRIPTION
    "The global identifier of a DDoS filter group."
  ::= { acceptEstHistHoursEntry 1 }

acceptEstHistHoursIndex OBJECT-TYPE
  SYNTAX      Unsigned32
  MAX-ACCESS  not-accessible
  STATUS      current
  DESCRIPTION
    "The index (0-23) of the hour."
  ::= { acceptEstHistHoursEntry 2 }

acceptEstHistHoursUnitCount OBJECT-TYPE
  SYNTAX      Counter64
  MAX-ACCESS  read-only
  STATUS      current
  DESCRIPTION
    "The average of the MinutesUnitCount values corresponding to this hour."
  ::= { acceptEstHistHoursEntry 3 }

acceptEstHistHoursTimestamp OBJECT-TYPE
  SYNTAX      Unsigned32
  MAX-ACCESS  read-only
  STATUS      current
  DESCRIPTION
    "The time HoursUnitCount was updated (in seconds since January 1, 1970)."
  ::= { acceptEstHistHoursEntry 4 }


-- Accepted connections per second (EST) history days

acceptEstHistDaysTable OBJECT-TYPE
  SYNTAX      SEQUENCE OF AcceptEstHistDaysEntry
  MAX-ACCESS  not-accessible
  STATUS      current
  DESCRIPTION
    "Historical (sampled) data every day for 35 days."
  ::= { tpt-ddos 32 }

acceptEstHistDaysEntry OBJECT-TYPE
  SYNTAX      AcceptEstHistDaysEntry
  MAX-ACCESS  not-accessible
  STATUS      current
  DESCRIPTION
    "An entry in the accepted connections per sec (EST) history days table.
     Rows cannot be created or deleted.
    "
  INDEX       { acceptEstHistDaysGlobalID, acceptEstHistDaysIndex }
  ::= { acceptEstHistDaysTable 1 }

AcceptEstHistDaysEntry ::= SEQUENCE {
  acceptEstHistDaysGlobalID   OCTET STRING (SIZE (0..40)),
  acceptEstHistDaysIndex      Unsigned32,
  acceptEstHistDaysUnitCount  Counter64,
  acceptEstHistDaysTimestamp  Unsigned32
}

acceptEstHistDaysGlobalID OBJECT-TYPE
  SYNTAX      OCTET STRING (SIZE (0..40))
  MAX-ACCESS  not-accessible
  STATUS      current
  DESCRIPTION
    "The global identifier of a DDoS filter group."
  ::= { acceptEstHistDaysEntry 1 }

acceptEstHistDaysIndex OBJECT-TYPE
  SYNTAX      Unsigned32
  MAX-ACCESS  not-accessible
  STATUS      current
  DESCRIPTION
    "The index (0-34) of the day."
  ::= { acceptEstHistDaysEntry 2 }

acceptEstHistDaysUnitCount OBJECT-TYPE
  SYNTAX      Counter64
  MAX-ACCESS  read-only
  STATUS      current
  DESCRIPTION
    "The average of the HoursUnitCount values corresponding to this day."
  ::= { acceptEstHistDaysEntry 3 }

acceptEstHistDaysTimestamp OBJECT-TYPE
  SYNTAX      Unsigned32
  MAX-ACCESS  read-only
  STATUS      current
  DESCRIPTION
    "The time DaysUnitCount was updated (in seconds since January 1, 1970)."
  ::= { acceptEstHistDaysEntry 4 }


END
