-- - - - - - - - - - - - - - - - - - - - - - - - - - - - - - - - - - - - - - -
--
-- Trend Micro, Inc.
-- Copyright information is in the DESCRIPTION section of the MODULE-IDENTITY.
--
-- - - - - - - - - - - - - - - - - - - - - - - - - - - - - - - - - - - - - - -

TPT-NPSTATS-MIB

DEFINITIONS ::= BEGIN

IMPORTS
  MODULE-IDENTITY, OBJECT-TYPE, OBJECT-IDENTITY,
  Unsigned32, Integer32, Counter64
    FROM SNMPv2-SMI

  DisplayString
    FROM SNMPv2-TC

  tpt-tpa-objs
    FROM TPT-TPAMIBS-MIB
  ;

tpt-npstats MODULE-IDENTITY
  LAST-UPDATED "201605251854Z" -- May 25, 2016
  ORGANIZATION "Trend Micro, Inc."
  CONTACT-INFO "www.trendmicro.com"
  DESCRIPTION
    "Network processor statistics.

     Copyright (C) 2016 Trend Micro Incorporated. All Rights Reserved.

     Trend Micro makes no warranty of any kind with regard to this material,
     including, but not limited to, the implied warranties of merchantability
     and fitness for a particular purpose. Trend Micro shall not be liable for
     errors contained herein or for incidental or consequential damages in
     connection with the furnishing, performance, or use of this material. This
     document contains proprietary information, which is protected by copyright. No
     part of this document may be photocopied, reproduced, or translated into
     another language without the prior written consent of Trend Micro. The
     information is provided 'as is' without warranty of any kind and is subject to
     change without notice. The only warranties for Trend Micro products and
     services are set forth in the express warranty statements accompanying such
     products and services. Nothing herein should be construed as constituting an
     additional warranty. Trend Micro shall not be liable for technical or editorial
     errors or omissions contained herein. TippingPoint(R), the TippingPoint logo, and
     Digital Vaccine(R) are registered trademarks of Trend Micro. All other company
     and product names may be trademarks of their respective holders. All rights
     reserved. This document contains confidential information, trade secrets or
     both, which are the property of Trend Micro. No part of this documentation may
     be reproduced in any form or by any means or used to make any derivative work
     (such as translation, transformation, or adaptation) without written permission
     from Trend Micro or one of its subsidiaries. All other company and product
     names may be trademarks of their respective holders.
    "

  REVISION "201605251854Z" -- May 25, 2016
  DESCRIPTION "Updated copyright information. Minor MIB syntax fixes."

  REVISION    "201605031726Z" -- May 03, 2016
  DESCRIPTION "Updated npstatsSslInspCurrentSessions and npstatsSslInspConnectionRate object
               descriptions correcting for misplaced connection rate calculation statement."

  ::= { tpt-tpa-objs 10 }

-- - - - - - - - - - - - - - - - - - - - - - - - - - - - - - - - - - - - - - -
--
--  Variable definitions
--
-- - - - - - - - - - - - - - - - - - - - - - - - - - - - - - - - - - - - - - -

-- - - - - - - - - - - - - - - - - - - - - - - - - - - - - - - - - - - - - - -
--
-- Network processor statistics rules table
--
-- - - - - - - - - - - - - - - - - - - - - - - - - - - - - - - - - - - - - - -

npstatsRulesTable OBJECT-TYPE
  SYNTAX      SEQUENCE OF NpstatsRulesEntry
  MAX-ACCESS  not-accessible
  STATUS      current
  DESCRIPTION
    "Statistical information pertaining to network processor rules.
     Entries in the table are sorted in descending order of number of flows."
  ::= { tpt-npstats 1 }

npstatsRulesEntry OBJECT-TYPE
  SYNTAX      NpstatsRulesEntry
  MAX-ACCESS  not-accessible
  STATUS      current
  DESCRIPTION
    "An entry in the network processor statistics rules table.
     Rows cannot be created or deleted.
    "
  INDEX       { npstatsRulesRank }
  ::= { npstatsRulesTable 1 }

NpstatsRulesEntry ::= SEQUENCE {
  npstatsRulesRank            Unsigned32,
  npstatsRulesFilter          Unsigned32,
  npstatsRulesFlows           Unsigned32,
  npstatsRulesSuccess         Unsigned32,
  npstatsRulesTotalPercent    Unsigned32,
  npstatsRulesSuccessPer10K   Unsigned32
}

npstatsRulesRank OBJECT-TYPE
  SYNTAX      Unsigned32
  MAX-ACCESS  not-accessible
  STATUS      current
  DESCRIPTION
    "The numerical ranking in the network processor statistics rules table."
  ::= { npstatsRulesEntry 1 }

npstatsRulesFilter OBJECT-TYPE
  SYNTAX      Unsigned32
  MAX-ACCESS  read-only
  STATUS      current
  DESCRIPTION
    "The filter number."
  ::= { npstatsRulesEntry 2 }

npstatsRulesFlows OBJECT-TYPE
  SYNTAX      Unsigned32
  MAX-ACCESS  read-only
  STATUS      current
  DESCRIPTION
    "The number of flows that have triggered this filter."
  ::= { npstatsRulesEntry 3 }

npstatsRulesSuccess OBJECT-TYPE
  SYNTAX      Unsigned32
  MAX-ACCESS  read-only
  STATUS      current
  DESCRIPTION
    "The number of times this filter has been successfully matched."
  ::= { npstatsRulesEntry 4 }

npstatsRulesTotalPercent OBJECT-TYPE
  SYNTAX      Unsigned32
  MAX-ACCESS  read-only
  STATUS      current
  DESCRIPTION
    "The number of flows for this filter as a percentage of all flows."
  ::= { npstatsRulesEntry 5 }

npstatsRulesSuccessPer10K OBJECT-TYPE
  SYNTAX      Unsigned32
  MAX-ACCESS  read-only
  STATUS      current
  DESCRIPTION
    "The number of matches for every 10000 flows triggered."
  ::= { npstatsRulesEntry 6 }

-- - - - - - - - - - - - - - - - - - - - - - - - - - - - - - - - - - - - - - -
--
-- Network processor tier statistics
--
-- - - - - - - - - - - - - - - - - - - - - - - - - - - - - - - - - - - - - - -

npstatsTiersTable OBJECT-TYPE
  SYNTAX      SEQUENCE OF NpstatsTiersEntry
  MAX-ACCESS  not-accessible
  STATUS      current
  DESCRIPTION
    "Statistical information pertaining to network processor tiers."
  ::= { tpt-npstats 2 }

npstatsTiersEntry OBJECT-TYPE
  SYNTAX      NpstatsTiersEntry
  MAX-ACCESS  not-accessible
  STATUS      current
  DESCRIPTION
    "An entry in the network processor statistics tiers table.
     Rows cannot be created or deleted.
    "
  INDEX       { npstatsTierNumber }
  ::= { npstatsTiersTable 1 }

NpstatsTiersEntry ::= SEQUENCE {
  npstatsTierNumber              Unsigned32,
  npstatsTiersReceiveMbps        Unsigned32,
  npstatsTiersTransmitMbps       Unsigned32,
  npstatsTiersRxPktsPerSec       Unsigned32,
  npstatsTiersMaxPktsPerSec      Unsigned32,
  npstatsTiersAvgBytesPerPkt     Unsigned32,
  npstatsTiersUtilizationPercent Integer32,
  npstatsTiersRatioToNextPer10K  Unsigned32,
  npstatsTiersMaxReceiveMbps     Unsigned32,
  npstatsTiersMaxTransmitMbps    Unsigned32,
  npstatsTiersMaxUtilizationPercent Integer32,
  npstatsTiersMaxRatioToNextPer10K  Unsigned32
}

npstatsTierNumber OBJECT-TYPE
  SYNTAX      Unsigned32
  MAX-ACCESS  not-accessible
  STATUS      current
  DESCRIPTION
    "The network processor statistics tier number."
  ::= { npstatsTiersEntry 1 }

npstatsTiersReceiveMbps OBJECT-TYPE
  SYNTAX      Unsigned32
  MAX-ACCESS  read-only
  STATUS      current
  DESCRIPTION
    "The current receive rate in Mbps."
  ::= { npstatsTiersEntry 2 }

npstatsTiersTransmitMbps OBJECT-TYPE
  SYNTAX      Unsigned32
  MAX-ACCESS  read-only
  STATUS      current
  DESCRIPTION
    "The current transmit rate in Mbps."
  ::= { npstatsTiersEntry 3 }

npstatsTiersRxPktsPerSec OBJECT-TYPE
  SYNTAX      Unsigned32
  MAX-ACCESS  read-only
  STATUS      current
  DESCRIPTION
    "The current receive rate in packets per sec."
  ::= { npstatsTiersEntry 4 }

npstatsTiersMaxPktsPerSec OBJECT-TYPE
  SYNTAX      Unsigned32
  MAX-ACCESS  read-only
  STATUS      current
  DESCRIPTION
    "The maximum receive rate in packets per sec."
  ::= { npstatsTiersEntry 5 }

npstatsTiersAvgBytesPerPkt OBJECT-TYPE
  SYNTAX      Unsigned32
  MAX-ACCESS  read-only
  STATUS      current
  DESCRIPTION
    "The average packet size in bytes."
  ::= { npstatsTiersEntry 6 }

npstatsTiersUtilizationPercent OBJECT-TYPE
  SYNTAX      Integer32
  MAX-ACCESS  read-only
  STATUS      current
  DESCRIPTION
    "The percent utilization of this tier."
  ::= { npstatsTiersEntry 7 }

npstatsTiersRatioToNextPer10K OBJECT-TYPE
  SYNTAX      Unsigned32
  MAX-ACCESS  read-only
  STATUS      current
  DESCRIPTION
    "The ratio of this tier's throughput to the next per 10K (percent * 100)."
  ::= { npstatsTiersEntry 8 }

npstatsTiersMaxReceiveMbps OBJECT-TYPE
  SYNTAX      Unsigned32
  MAX-ACCESS  read-only
  STATUS      current
  DESCRIPTION
    "The maximum receive rate in Mbps."
  ::= { npstatsTiersEntry 9 }

npstatsTiersMaxTransmitMbps OBJECT-TYPE
  SYNTAX      Unsigned32
  MAX-ACCESS  read-only
  STATUS      current
  DESCRIPTION
    "The maximum transmit rate in Mbps."
  ::= { npstatsTiersEntry 10 }

npstatsTiersMaxUtilizationPercent OBJECT-TYPE
  SYNTAX      Integer32
  MAX-ACCESS  read-only
  STATUS      current
  DESCRIPTION
    "The maximum percent utilization of this tier."
  ::= { npstatsTiersEntry 11 }

npstatsTiersMaxRatioToNextPer10K OBJECT-TYPE
  SYNTAX      Unsigned32
  MAX-ACCESS  read-only
  STATUS      current
  DESCRIPTION
    "The maximum ratio of this tier's throughput to the next per 10K (percent * 100)."
  ::= { npstatsTiersEntry 12 }


-- End of tiers table; extra information follows

npstatsTiersExtra OBJECT-IDENTITY
  STATUS      current
  DESCRIPTION
    "Additional statistical information pertaining to network processor tiers."
  ::= { tpt-npstats 3 }

npstatsTier1BypassMbps OBJECT-TYPE
  SYNTAX      Unsigned32
  MAX-ACCESS  read-only
  STATUS      current
  DESCRIPTION
    "The current bypass rate in Mbps."
  ::= { npstatsTiersExtra 1 }

npstatsTier1Balance OBJECT-TYPE
  SYNTAX      Unsigned32
  MAX-ACCESS  read-only
  STATUS      current
  DESCRIPTION
    "The load balance among network processors
     (1000 = exactly balanced, 0 = all to one processor)."
  ::= { npstatsTiersExtra 2 }

npstatsTier1MaxPktsPerSecA OBJECT-TYPE
  SYNTAX      Unsigned32
  MAX-ACCESS  read-only
  STATUS      current
  DESCRIPTION
    "The maximum processor A receive rate in packets per second."
  ::= { npstatsTiersExtra 3 }

npstatsTier1MaxPktsPerSecB OBJECT-TYPE
  SYNTAX      Unsigned32
  MAX-ACCESS  read-only
  STATUS      current
  DESCRIPTION
    "The maximum processor B receive rate in packets per second."
  ::= { npstatsTiersExtra 4 }

npstatsTier1TxPktsPerSec OBJECT-TYPE
  SYNTAX      Unsigned32
  MAX-ACCESS  read-only
  STATUS      current
  DESCRIPTION
    "The transmit rate in packets per second."
  ::= { npstatsTiersExtra 8 }

npstatsTier1MaxTxPktsPerSec OBJECT-TYPE
  SYNTAX      Unsigned32
  MAX-ACCESS  read-only
  STATUS      current
  DESCRIPTION
    "The maximum transmit rate in packets per second."
  ::= { npstatsTiersExtra 9 }

npstatsTier4TriggerMatchPer1000 OBJECT-TYPE
  SYNTAX      Unsigned32
  MAX-ACCESS  read-only
  STATUS      current
  DESCRIPTION
    "Proportion of traffic inspected because of trigger match (percent * 10)."
  ::= { npstatsTiersExtra 5 }

npstatsTier4ReroutePer1000 OBJECT-TYPE
  SYNTAX      Unsigned32
  MAX-ACCESS  read-only
  STATUS      current
  DESCRIPTION
    "Proportion of traffic inspected because of reroute (percent * 10)."
  ::= { npstatsTiersExtra 6 }

npstatsTier4TcpSequencePer1000 OBJECT-TYPE
  SYNTAX      Unsigned32
  MAX-ACCESS  read-only
  STATUS      current
  DESCRIPTION
    "Proportion of traffic inspected because of TCP sequence (percent * 10)."
  ::= { npstatsTiersExtra 7 }

npstatsTier1MaxPktsPerSecC OBJECT-TYPE
  SYNTAX      Unsigned32
  MAX-ACCESS  read-only
  STATUS      current
  DESCRIPTION
    "The maximum processor C receive rate in packets per second."
  ::= { npstatsTiersExtra 10 }

npstatsTier4ProtoDcdPer1000 OBJECT-TYPE
  SYNTAX      Unsigned32
  MAX-ACCESS  read-only
  STATUS      current
  DESCRIPTION
    "Proportion of reroute traffic inspected because of protocol decode (percent * 10)."
  ::= { npstatsTiersExtra 11 }

npstatsTier2TxTrustedPktsPerSec OBJECT-TYPE
  SYNTAX      Unsigned32
  MAX-ACCESS  read-only
  STATUS      current
  DESCRIPTION
    "The Tier 2 Trusted packets transmit rate in packets per second."
  ::= { npstatsTiersExtra 12 }

npstatsTier3TxTrustedPktsPerSec OBJECT-TYPE
  SYNTAX      Unsigned32
  MAX-ACCESS  read-only
  STATUS      current
  DESCRIPTION
    "The Tier 3 Trusted packets transmit rate in packets per second."
  ::= { npstatsTiersExtra 13 }

npstatsTier4TxTrustedPktsPerSec OBJECT-TYPE
  SYNTAX      Unsigned32
  MAX-ACCESS  read-only
  STATUS      current
  DESCRIPTION
    "The Tier 4 Trusted packets transmit rate in packets per second."
  ::= { npstatsTiersExtra 14 }

npstatsTier1BypassPktsPerSec OBJECT-TYPE
  SYNTAX      Unsigned32
  MAX-ACCESS  read-only
  STATUS      current
  DESCRIPTION
    "The inspection bypass rate in packets per second."
  ::= { npstatsTiersExtra 15 }

npstatsTier1MaxBypassPktsPerSec OBJECT-TYPE
  SYNTAX      Unsigned32
  MAX-ACCESS  read-only
  STATUS      current
  DESCRIPTION
    "The maximum inspection bypass rate in packets per second."
  ::= { npstatsTiersExtra 16 }

npstatsTier1BypassToRxPktsPerSecRatio OBJECT-TYPE
  SYNTAX      Unsigned32
  MAX-ACCESS  read-only
  STATUS      current
  DESCRIPTION
    "The ratio of inspection bypass packets per second to Rx packets per second."
  ::= { npstatsTiersExtra 17 }

npstatsTier1VlanTransPktsPerSec OBJECT-TYPE
  SYNTAX      Unsigned32
  MAX-ACCESS  read-only
  STATUS      current
  DESCRIPTION
    "The VLAN translation rate in packets per second."
  ::= { npstatsTiersExtra 18 }

npstatsTier1MaxVlanTransPktsPerSec OBJECT-TYPE
  SYNTAX      Unsigned32
  MAX-ACCESS  read-only
  STATUS      current
  DESCRIPTION
    "The maximum VLAN translation rate in packets per second."
  ::= { npstatsTiersExtra 19 }

npstatsTier1VlanTransToRxPktsPerSecRatio OBJECT-TYPE
  SYNTAX      Unsigned32
  MAX-ACCESS  read-only
  STATUS      current
  DESCRIPTION
    "The ratio of VLAN translation packets per second to Rx packets per second."
  ::= { npstatsTiersExtra 20 }

npstatsTier1PatternMatchToRxPktsPerSecRatio OBJECT-TYPE
  SYNTAX      Unsigned32
  MAX-ACCESS  read-only
  STATUS      current
  DESCRIPTION
    "The ratio of pattern match packets per second to Rx packets per second."
  ::= { npstatsTiersExtra 21 }

npstatsTier1MaxPatternMatchToRxPktsPerSecRatio OBJECT-TYPE
  SYNTAX      Unsigned32
  MAX-ACCESS  read-only
  STATUS      current
  DESCRIPTION
    "The maximum ratio of pattern match packets per second to Rx packets per second."
  ::= { npstatsTiersExtra 22 }

npstatsTier2MaxTxTrustedPktsPerSec OBJECT-TYPE
  SYNTAX      Unsigned32
  MAX-ACCESS  read-only
  STATUS      current
  DESCRIPTION
    "The maximum Tier 2 Trusted packets transmit rate in packets per second."
  ::= { npstatsTiersExtra 23 }

npstatsTier3MaxTxTrustedPktsPerSec OBJECT-TYPE
  SYNTAX      Unsigned32
  MAX-ACCESS  read-only
  STATUS      current
  DESCRIPTION
    "The maximum Tier 3 Trusted packets transmit rate in packets per second."
  ::= { npstatsTiersExtra 24 }

npstatsTier4MaxTxTrustedPktsPerSec OBJECT-TYPE
  SYNTAX      Unsigned32
  MAX-ACCESS  read-only
  STATUS      current
  DESCRIPTION
    "The maximum Tier 4 Trusted packets transmit rate in packets per second."
  ::= { npstatsTiersExtra 25 }

npstatsTier4MaxTriggerMatchPer1000 OBJECT-TYPE
  SYNTAX      Unsigned32
  MAX-ACCESS  read-only
  STATUS      current
  DESCRIPTION
    "Maximum proportion of traffic inspected because of trigger match (percent * 10)."
  ::= { npstatsTiersExtra 26 }

npstatsTier4MaxReroutePer1000 OBJECT-TYPE
  SYNTAX      Unsigned32
  MAX-ACCESS  read-only
  STATUS      current
  DESCRIPTION
    "Maximum proportion of traffic inspected because of reroute (percent * 10)."
  ::= { npstatsTiersExtra 27 }

npstatsTier4MaxTcpSequencePer1000 OBJECT-TYPE
  SYNTAX      Unsigned32
  MAX-ACCESS  read-only
  STATUS      current
  DESCRIPTION
    "Maximum proportion of traffic inspected because of TCP sequence (percent * 10)."
  ::= { npstatsTiersExtra 28 }

npstatsTier4MaxProtoDcdPer1000 OBJECT-TYPE
  SYNTAX      Unsigned32
  MAX-ACCESS  read-only
  STATUS      current
  DESCRIPTION
    "Maximum proportion of reroute traffic inspected because of protocol decode (percent * 10)."
  ::= { npstatsTiersExtra 29 }

-- - - - - - - - - - - - - - - - - - - - - - - - - - - - - - - - - - - - - - -
--
-- Miscellaneous network processor statistics
--
-- - - - - - - - - - - - - - - - - - - - - - - - - - - - - - - - - - - - - - -

npstatsMisc OBJECT-IDENTITY
  STATUS      current
  DESCRIPTION
    "Miscellaneous network processor statistical information."
  ::= { tpt-npstats 4 }

npstatsMiscTxPktsBestEffort OBJECT-TYPE
  SYNTAX      Counter64
  MAX-ACCESS  read-only
  STATUS      current
  DESCRIPTION
    "The number of packets transmitted due to best effort mode."
  ::= { npstatsMisc 1 }

-- - - - - - - - - - - - - - - - - - - - - - - - - - - - - - - - - - - - - - -
--
-- SSL Inspection Statistics
--
-- - - - - - - - - - - - - - - - - - - - - - - - - - - - - - - - - - - - - - -

npstatsSslInsp OBJECT-IDENTITY
  STATUS      current
  DESCRIPTION "Sub-tree for all SSL inspection statistics."
  ::= { tpt-npstats 5 }

npstatsSslInspCurrentSessions OBJECT-TYPE
  SYNTAX      Counter64
  MAX-ACCESS  read-only
  STATUS      current
  DESCRIPTION
    "The current number of active SSL sessions."
  ::= { npstatsSslInsp 1 }

npstatsSslInspConnectionRate OBJECT-TYPE
  SYNTAX      DisplayString (SIZE(0..40))
  MAX-ACCESS  read-only
  STATUS      current
  DESCRIPTION
    "The average SSL connection rate in connections per second. This value is not real-time and will
     lag approximately 2 minutes from actual due to the time interval for calculating the rate."
  ::= { npstatsSslInsp 2 }

npstatsSslInspBlockedMaxConns OBJECT-TYPE
  SYNTAX      Counter64
  MAX-ACCESS  read-only
  STATUS      current
  DESCRIPTION
    "The number of blocked SSL sessions due to maximum connection limit."
  ::= { npstatsSslInsp 3 }

npstatsSslInspPassedMaxConns OBJECT-TYPE
  SYNTAX      Counter64
  MAX-ACCESS  read-only
  STATUS      current
  DESCRIPTION
    "The number of passed (not inspected) SSL sessions due to maximum connection limit."
  ::= { npstatsSslInsp 4 }

npstatsSslInspTotalBytesIn OBJECT-TYPE
  SYNTAX      Counter64
  MAX-ACCESS  read-only
  STATUS      current
  DESCRIPTION
    "The number of inspected inbound SSL bytes."
  ::= { npstatsSslInsp 5 }

npstatsSslInspTotalBytesOut OBJECT-TYPE
  SYNTAX      Counter64
  MAX-ACCESS  read-only
  STATUS      current
  DESCRIPTION
    "The number of inspected outbound SSL bytes."
  ::= { npstatsSslInsp 6 }

-- - - - - - - - - - - - - - - - - - - - - - - - - - - - - - - - - - - - - - -
--
-- stacking tier stats
--
-- - - - - - - - - - - - - - - - - - - - - - - - - - - - - - - - - - - - - - -
npstatsStackSegmentPorts OBJECT-IDENTITY
  STATUS      current
  DESCRIPTION
    "Statistical information pertaining to customer-facing segment ports
     for a stack configuration."
  ::= { tpt-npstats 10 }

npstatsStackSegmentRecieveMbps OBJECT-TYPE
  SYNTAX      Unsigned32
  MAX-ACCESS  read-only
  STATUS      current
  DESCRIPTION
    "Aggregate rx rate in Mbps from all customer facing segment ports."
  ::= { npstatsStackSegmentPorts 1}

npstatsStackSegmentMaxRecieveMbps OBJECT-TYPE
  SYNTAX      Unsigned32
  MAX-ACCESS  read-only
  STATUS      current
  DESCRIPTION
    "Maximum rx rate in Mbps from all customer facing segment ports."
  ::= { npstatsStackSegmentPorts 2}

npstatsStackSegmentTransmitMbps OBJECT-TYPE
  SYNTAX      Unsigned32
  MAX-ACCESS  read-only
  STATUS      current
  DESCRIPTION
    "Aggregate tx rate in Mbps to all customer facing segment ports."
  ::= { npstatsStackSegmentPorts 3}

npstatsStackSegmentMaxTransmitMbps OBJECT-TYPE
  SYNTAX      Unsigned32
  MAX-ACCESS  read-only
  STATUS      current
  DESCRIPTION
    "Maximum tx rate in Mbps to all customer facing segment ports."
  ::= { npstatsStackSegmentPorts 4}

npstatsStackBalance OBJECT-TYPE
  SYNTAX      Unsigned32
  MAX-ACCESS  read-only
  STATUS      current
  DESCRIPTION
    "The load balance percent accross all stack members"
  ::= { npstatsStackSegmentPorts 5}

npstatsStackMinBalance OBJECT-TYPE
  SYNTAX      Unsigned32
  MAX-ACCESS  read-only
  STATUS      current
  DESCRIPTION
    "The minimum, non-zero load balance percent accross all stack members"
  ::= { npstatsStackSegmentPorts 6}

npstatsStackSegmentRatioToTier1Per10K OBJECT-TYPE
  SYNTAX      Unsigned32
  MAX-ACCESS  read-only
  STATUS      current
  DESCRIPTION
    "The ratio of this tier's throughput to tier 1 per 10K (percent * 100)."
  ::= { npstatsStackSegmentPorts 7 }

npstatsStackSegmentMaxRatioToTier1Per10K OBJECT-TYPE
  SYNTAX      Unsigned32
  MAX-ACCESS  read-only
  STATUS      current
  DESCRIPTION
    "The maximum ratio of this tier's throughput to tier 1 per 10K (percent * 100)."
  ::= { npstatsStackSegmentPorts 8 }

npstatsStackSegmentPortTable OBJECT-TYPE
  SYNTAX      SEQUENCE OF NpstatsStackSegmentPortEntry
  MAX-ACCESS  not-accessible
  STATUS      current
  DESCRIPTION
    "Statistical information related to customer-facing segment ports for
     each stack member"
  ::= { npstatsStackSegmentPorts 9 }

npstatsStackSegmentPortEntry OBJECT-TYPE
  SYNTAX      NpstatsStackSegmentPortEntry
  MAX-ACCESS  not-accessible
  STATUS      current
  DESCRIPTION
    "An entry in the stacking port table."
  INDEX       { npstatsStackMemberIndex }
  ::= { npstatsStackSegmentPortTable 1 }

NpstatsStackSegmentPortEntry ::= SEQUENCE {
  npstatsStackMemberIndex                   Unsigned32,
  npstatsStackMemberKey                     OCTET STRING,
  npstatsStackMemberHostname                OCTET STRING,
  npstatsStackMemberSegmentReceiveMbps      Unsigned32,
  npstatsStackMemberMaxSegmentReceiveMbps   Unsigned32
}

npstatsStackMemberIndex OBJECT-TYPE
  SYNTAX      Unsigned32
  MAX-ACCESS  read-only
  STATUS      current
  DESCRIPTION
    "Stack member index"
  ::= { npstatsStackSegmentPortEntry 1 }

npstatsStackMemberKey OBJECT-TYPE
  SYNTAX      OCTET STRING (SIZE (0..12))
  MAX-ACCESS  read-only
  STATUS      current
  DESCRIPTION
    "Unique stack member identifier."
  ::= { npstatsStackSegmentPortEntry 2 }

npstatsStackMemberHostname OBJECT-TYPE
  SYNTAX      OCTET STRING (SIZE (0..64))
  MAX-ACCESS  read-only
  STATUS      current
  DESCRIPTION
    "The stack member hostname"
  ::= { npstatsStackSegmentPortEntry 3 }

npstatsStackMemberSegmentReceiveMbps OBJECT-TYPE
  SYNTAX      Unsigned32
  MAX-ACCESS  read-only
  STATUS      current
  DESCRIPTION
    "The current segment rx rate in Mbps for a stack member."
  ::= { npstatsStackSegmentPortEntry 4 }

npstatsStackMemberMaxSegmentReceiveMbps OBJECT-TYPE
  SYNTAX      Unsigned32
  MAX-ACCESS  read-only
  STATUS      current
  DESCRIPTION
    "The maximum segment rx rate in Mbps for a stack member."
  ::= { npstatsStackSegmentPortEntry 5 }

npstatsStackPorts OBJECT-IDENTITY
  STATUS      current
  DESCRIPTION
    "Statistical information pertaining to stacking ports in a stack configuration."
  ::= { tpt-npstats 11 }

npstatsStackPortsRecieveMbps OBJECT-TYPE
  SYNTAX      Unsigned32
  MAX-ACCESS  read-only
  STATUS      current
  DESCRIPTION
    "Aggregate rx rate in Mbps from all stacking ports."
  ::= { npstatsStackPorts 1}

npstatsStackPortsMaxRecieveMbps OBJECT-TYPE
  SYNTAX      Unsigned32
  MAX-ACCESS  read-only
  STATUS      current
  DESCRIPTION
    "Maximum rx rate in Mbps from all stacking ports."
  ::= { npstatsStackPorts 2}

npstatsStackPortsTransmitMbps OBJECT-TYPE
  SYNTAX      Unsigned32
  MAX-ACCESS  read-only
  STATUS      current
  DESCRIPTION
    "Aggregate tx rate in Mbps for all stacking ports."
  ::= { npstatsStackPorts 3}

npstatsStackPortsMaxTransmitMbps OBJECT-TYPE
  SYNTAX      Unsigned32
  MAX-ACCESS  read-only
  STATUS      current
  DESCRIPTION
    "Maximum tx rate in Mbps for all stacking ports."
  ::= { npstatsStackPorts 4}

npstatsStackRxToStackTxMbps OBJECT-TYPE
  SYNTAX      Unsigned32
  MAX-ACCESS  read-only
  STATUS      current
  DESCRIPTION
    "Aggregate through traffic rate from segment ports to stacking ports"
  ::= { npstatsStackPorts 5}

npstatsStackMaxRxToStackTxMbps OBJECT-TYPE
  SYNTAX      Unsigned32
  MAX-ACCESS  read-only
  STATUS      current
  DESCRIPTION
    "The maximum through traffic rate from segment ports to stacking ports"
  ::= { npstatsStackPorts 6}

npstatsStackRxToSegmentTxMbps OBJECT-TYPE
  SYNTAX      Unsigned32
  MAX-ACCESS  read-only
  STATUS      current
  DESCRIPTION
    "Return rate in Mbps for traffic coming in on the
     stacking ports and transmitted to the segment ports"
  ::= { npstatsStackPorts 7}

npstatsStackMaxRxToSegmentTxMbps OBJECT-TYPE
  SYNTAX      Unsigned32
  MAX-ACCESS  read-only
  STATUS      current
  DESCRIPTION
    "Maximum return rate in Mbps for traffic coming in on the
     stacking ports and transmitted to the segment ports"
  ::= { npstatsStackPorts 8}

npstatsStackRxToTier1 OBJECT-TYPE
  SYNTAX      Unsigned32
  MAX-ACCESS  read-only
  STATUS      current
  DESCRIPTION
    "Aggregate receive rate from stacking ports to tier one"
  ::= { npstatsStackPorts 9}

npstatsStackMaxRxToTier1 OBJECT-TYPE
  SYNTAX      Unsigned32
  MAX-ACCESS  read-only
  STATUS      current
  DESCRIPTION
    "Maximnum receive rate from stacking ports to tier one"
  ::= { npstatsStackPorts 10}

END
