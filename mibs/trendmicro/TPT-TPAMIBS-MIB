-- - - - - - - - - - - - - - - - - - - - - - - - - - - - - - - - - - - - - - -
--
-- Trend Micro, Inc.
-- Copyright information is in the DESCRIPTION section of the MODULE-IDENTITY.
--
-- - - - - - - - - - - - - - - - - - - - - - - - - - - - - - - - - - - - - - -

TPT-TPAMIBS-MIB

DEFINITIONS ::= BEGIN

IMPORTS
  MODULE-IDENTITY, OBJECT-IDENTITY
    FROM SNMPv2-SMI

  tpt-products, tpt-reg
    FROM TIPPINGPOINT-REG-MIB
  ;

tpt-tpaMIBs MODULE-IDENTITY
  LAST-UPDATED "201606081724Z" -- June 8, 2016
  ORGANIZATION "Trend Micro, Inc."
  CONTACT-INFO "www.trendmicro.com"
  DESCRIPTION
    "Sub-tree for objects and events on the TPA.

     Copyright (C) 2016 Trend Micro Incorporated. All Rights Reserved.

     Trend Micro makes no warranty of any kind with regard to this material,
     including, but not limited to, the implied warranties of merchantability
     and fitness for a particular purpose. Trend Micro shall not be liable for
     errors contained herein or for incidental or consequential damages in
     connection with the furnishing, performance, or use of this material. This
     document contains proprietary information, which is protected by copyright. No
     part of this document may be photocopied, reproduced, or translated into
     another language without the prior written consent of Trend Micro. The
     information is provided 'as is' without warranty of any kind and is subject to
     change without notice. The only warranties for Trend Micro products and
     services are set forth in the express warranty statements accompanying such
     products and services. Nothing herein should be construed as constituting an
     additional warranty. Trend Micro shall not be liable for technical or editorial
     errors or omissions contained herein. TippingPoint(R), the TippingPoint logo, and
     Digital Vaccine(R) are registered trademarks of Trend Micro. All other company
     and product names may be trademarks of their respective holders. All rights
     reserved. This document contains confidential information, trade secrets or
     both, which are the property of Trend Micro. No part of this documentation may
     be reproduced in any form or by any means or used to make any derivative work
     (such as translation, transformation, or adaptation) without written permission
     from Trend Micro or one of its subsidiaries. All other company and product
     names may be trademarks of their respective holders.
    "

  REVISION "201606081724Z" -- June 8, 2016
  DESCRIPTION "Added vTPS models."

  REVISION "201605251854Z" -- May 25, 2016
  DESCRIPTION "Updated copyright information. Minor MIB syntax fixes."

  ::= { tpt-products 3 }

-- - - - - - - - - - - - - - - - - - - - - - - - - - - - - - - - - - - - - - -
--
-- TPA top level MIBs
--
-- - - - - - - - - - - - - - - - - - - - - - - - - - - - - - - - - - - - - - -

tpt-tpa-conf OBJECT-IDENTITY
  STATUS         current
  DESCRIPTION    "This sub-tree is for conformance.
		  (OBJECT-GROUP, NOTIFICATION-GROUP, MODULE-COMPLIANCE)"
  ::= { tpt-tpaMIBs 1 }

tpt-tpa-objs OBJECT-IDENTITY
  STATUS         current
  DESCRIPTION    "This sub-tree is for all managed objects on the TPA."
  ::= { tpt-tpaMIBs 2 }

tpt-tpa-events OBJECT-IDENTITY
  STATUS         current
  DESCRIPTION    "This sub-tree is for all events (NOTIFICATION-TYPE) and
                  payload variables that are needed for notifications."
  ::= { tpt-tpaMIBs 3 }

-- - - - - - - - - - - - - - - - - - - - - - - - - - - - - - - - - - - - - - -
--
-- Conformance top level MIBS
--
-- - - - - - - - - - - - - - - - - - - - - - - - - - - - - - - - - - - - - - -

tpt-tpa-groups OBJECT-IDENTITY
  STATUS         current
  DESCRIPTION    "This sub-tree is for all groups.
		  (OBJECT-GROUP, NOTIFICATION-GROUP)"
  ::= { tpt-tpa-conf 1 }

tpt-tpa-compls OBJECT-IDENTITY
  STATUS         current
  DESCRIPTION    "This sub-tree is for all compliance MIBs.
		  (MODULE-COMPLIANCE)"
  ::= { tpt-tpa-conf 2 }

-- - - - - - - - - - - - - - - - - - - - - - - - - - - - - - - - - - - - - - -
--
-- Notification top level MIBs
--
-- - - - - - - - - - - - - - - - - - - - - - - - - - - - - - - - - - - - - - -

tpt-tpa-eventsV2 OBJECT-IDENTITY
  STATUS         current
  DESCRIPTION    "This sub-tree is for all notification MIBs for a TPA."
  ::= { tpt-tpa-events 0 }

tpt-tpa-unkparams OBJECT-IDENTITY
  STATUS         current
  DESCRIPTION    "This sub-tree is for all MIB variables sent as part of a
                  notification payload sent by a TPA."
  ::= { tpt-tpa-events 1 }

-- - - - - - - - - - - - - - - - - - - - - - - - - - - - - - - - - - - - - - -
--
-- Model numbers
--
-- - - - - - - - - - - - - - - - - - - - - - - - - - - - - - - - - - - - - - -

tpt-tpa-family OBJECT-IDENTITY
  STATUS         current
  DESCRIPTION    "Registration for the TPT family of network security devices."
  ::= { tpt-reg 3 }

tpt-model-2000 OBJECT-IDENTITY
  STATUS         current
  DESCRIPTION    "Registration for the TPT model 2000."
  ::= { tpt-tpa-family 1 }

tpt-model-600 OBJECT-IDENTITY
  STATUS         current
  DESCRIPTION    "Registration for the TPT model 600."
  ::= { tpt-tpa-family 2 }

tpt-model-600A OBJECT-IDENTITY
  STATUS         current
  DESCRIPTION    "Registration for the TPT model 600A."
  ::= { tpt-tpa-family 4 }

tpt-model-400 OBJECT-IDENTITY
  STATUS         current
  DESCRIPTION    "Registration for the TPT model 400."
  ::= { tpt-tpa-family 5 }

tpt-model-50 OBJECT-IDENTITY
  STATUS         current
  DESCRIPTION    "Registration for the TPT model 50."
  ::= { tpt-tpa-family 6 }

tpt-model-1200 OBJECT-IDENTITY
  STATUS         current
  DESCRIPTION    "Registration for the TPT model 1200."
  ::= { tpt-tpa-family 7 }

tpt-model-2400 OBJECT-IDENTITY
  STATUS         current
  DESCRIPTION    "Registration for the TPT model 2400."
  ::= { tpt-tpa-family 8 }

tpt-model-5000 OBJECT-IDENTITY
  STATUS         current
  DESCRIPTION    "Registration for the TPT model 5000."
  ::= { tpt-tpa-family 9 }

tpt-model-200 OBJECT-IDENTITY
  STATUS         current
  DESCRIPTION    "Registration for the TPT model 200."
  ::= { tpt-tpa-family 10 }

tpt-model-10 OBJECT-IDENTITY
  STATUS         current
  DESCRIPTION    "Registration for the TPT model 10."
  ::= { tpt-tpa-family 11 }

tpt-model-100 OBJECT-IDENTITY
  STATUS         current
  DESCRIPTION    "Registration for the TPT model 100."
  ::= { tpt-tpa-family 12 }

tpt-model-X505 OBJECT-IDENTITY
  STATUS         current
  DESCRIPTION    "Registration for the TPT model X505."
  ::= { tpt-tpa-family 13 }

tpt-model-X5 OBJECT-IDENTITY
  STATUS         current
  DESCRIPTION    "Registration for the TPT model X5."
  ::= { tpt-tpa-family 14 }

tpt-model-T200 OBJECT-IDENTITY
  STATUS         current
  DESCRIPTION    "Registration for the TPT model T200."
  ::= { tpt-tpa-family 15 }

tpt-model-X506 OBJECT-IDENTITY
  STATUS         current
  DESCRIPTION    "Registration for the TPT model X506."
  ::= { tpt-tpa-family 16 }

tpt-model-X5-25 OBJECT-IDENTITY
  STATUS         current
  DESCRIPTION    "Registration for the TPT model X5-25."
  ::= { tpt-tpa-family 17 }

tpt-model-X710 OBJECT-IDENTITY
  STATUS         current
  DESCRIPTION    "Registration for the TPT model X710."
  ::= { tpt-tpa-family 18 }

tpt-model-T210E OBJECT-IDENTITY
  STATUS         current
  DESCRIPTION    "Registration for the TPT model T210E."
  ::= { tpt-tpa-family 19 }

tpt-model-T600E OBJECT-IDENTITY
  STATUS         current
  DESCRIPTION    "Registration for the TPT model T600E."
  ::= { tpt-tpa-family 20 }

tpt-model-T1000E OBJECT-IDENTITY
  STATUS         current
  DESCRIPTION    "Registration for the TPT model T1000E."
  ::= { tpt-tpa-family 21 }

tpt-model-T2000E OBJECT-IDENTITY
  STATUS         current
  DESCRIPTION    "Registration for the TPT model T2000E."
  ::= { tpt-tpa-family 22 }

tpt-model-T5000E OBJECT-IDENTITY
  STATUS         current
  DESCRIPTION    "Registration for the TPT model T5000E."
  ::= { tpt-tpa-family 23 }

tpt-model-660N OBJECT-IDENTITY
  STATUS         current
  DESCRIPTION    "Registration for the TPT model 660N."
  ::= { tpt-tpa-family 27 }

tpt-model-1400N OBJECT-IDENTITY
  STATUS         current
  DESCRIPTION    "Registration for the TPT model 1400N."
  ::= { tpt-tpa-family 28 }

tpt-model-2500N OBJECT-IDENTITY
  STATUS         current
  DESCRIPTION    "Registration for the TPT model 2500N."
  ::= { tpt-tpa-family 29 }

tpt-model-5100N OBJECT-IDENTITY
  STATUS         current
  DESCRIPTION    "Registration for the TPT model 5100N."
  ::= { tpt-tpa-family 30 }

tpt-model-110 OBJECT-IDENTITY
  STATUS         current
  DESCRIPTION    "Registration for the TPT model 110."
  ::= { tpt-tpa-family 31 }

tpt-model-330 OBJECT-IDENTITY
  STATUS         current
  DESCRIPTION    "Registration for the TPT model 330."
  ::= { tpt-tpa-family 32 }

tpt-model-SB1200N OBJECT-IDENTITY
  STATUS         current
  DESCRIPTION    "Registration for the TPT SecBlade model 1200N."
  ::= { tpt-tpa-family 33}

tpt-model-6100N OBJECT-IDENTITY
  STATUS         current
  DESCRIPTION    "Registration for the TPT model 6100N."
  ::= { tpt-tpa-family 34}

tpt-model-7100NX OBJECT-IDENTITY
  STATUS         current
  DESCRIPTION    "Registration for the TPT model 7100NX."
  ::= { tpt-tpa-family 35}

tpt-model-5200NX OBJECT-IDENTITY
  STATUS         current
  DESCRIPTION    "Registration for the TPT model 5200NX."
  ::= { tpt-tpa-family 36}

tpt-model-2600NX OBJECT-IDENTITY
  STATUS         current
  DESCRIPTION    "Registration for the TPT model 2600NX."
  ::= { tpt-tpa-family 44}

tpt-model-6200NX OBJECT-IDENTITY
  STATUS         current
  DESCRIPTION    "Registration for the TPT model 6200NX."
  ::= { tpt-tpa-family 45}

tpt-model-7500NX OBJECT-IDENTITY
  STATUS         current
  DESCRIPTION    "Registration for the TPT model 7500NX."
  ::= { tpt-tpa-family 46}

tpt-model-440T-IPS OBJECT-IDENTITY
  STATUS         current
  DESCRIPTION    "Registration for the TippingPoint 440T Threat Protection System (IPS)."
  ::= { tpt-tpa-family 47 }

tpt-model-2200T-IPS OBJECT-IDENTITY
  STATUS         current
  DESCRIPTION    "Registration for the TippingPoint 2200T Threat Protection System (IPS)."
  ::= { tpt-tpa-family 48 }

tpt-model-VTPS-Standard-IPS OBJECT-IDENTITY
  STATUS         current
  DESCRIPTION    "Registration for the HP vTPS Standard Threat Protection System (IPS)."
  ::= { tpt-tpa-family 49 }

tpt-model-VTPS-Trial-IPS OBJECT-IDENTITY
  STATUS         current
  DESCRIPTION    "Registration for the HP vTPS Standard Trial Threat Protection System (IPS)."
  ::= { tpt-tpa-family 50 }

END
