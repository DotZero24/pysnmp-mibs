-- *****************************************************************************
-- Bachmann GmbH, Stuttgart
-- BACHMANN-BLUENET2-MIB Version 1.0
--
-- Management Information Base for SNMP Network Management
--
-- Copyright 2013 Bachmann GmbH.
-- All Rights Reserved.
--
-- *****************************************************************************
-- File   : $RCSfile: BACHMANN-BLUENET2-MIB.txt,v $
-- Rev.   : $Revision: 1.17 $
-- Date   : $Date: 2015/09/22 16:45:34 $
-- Author : $Author: fis $
-- Id     : $Id: BACHMANN-BLUENET2-MIB.txt,v 1.17 2015/09/22 16:45:34 fis Exp $
-- *****************************************************************************

BACHMANN-BLUENET2-MIB DEFINITIONS ::= BEGIN

        IMPORTS
                                MODULE-IDENTITY,
                                NOTIFICATION-TYPE,
                                OBJECT-TYPE,
                                Integer32,
                                Unsigned32,
                                TimeTicks
        FROM                SNMPv2-SMI
                                MODULE-COMPLIANCE,
                                NOTIFICATION-GROUP,
                                OBJECT-GROUP
        FROM                SNMPv2-CONF
                                DateAndTime,
                                DisplayString,
                                RowStatus,
                                TEXTUAL-CONVENTION
        FROM                SNMPv2-TC
                                sysObjectID
        FROM                SNMPv2-MIB
                                bachmann
        FROM                BACHMANN-SMI-MIB;


blueNet2Mib MODULE-IDENTITY
        LAST-UPDATED        "201507010000Z"
        ORGANIZATION        "Bachmann GmbH"
        CONTACT-INFO        "www.bachmann.com

                            Bachmann GmbH
                            Ernsthaldenstrasse 33
                            D-70565 Stuttgart
                            Germany, Europe

                            Tel. +49 711 86602-0
                            Fax  +49 711 86602-34
                            info@bachmann.com"
        DESCRIPTION         "The MIB module for representing BlueNet2 PDU SNMP agent implementation version v1.01.00."
        REVISION            "201507010000Z"
        DESCRIPTION         "The MIB module for representing BlueNet2 PDU SNMP agent implementation version v1.00.00."
        REVISION            "201506010000Z"
        DESCRIPTION         "Version 10100 of BlueNet2 PDU MIB."
        REVISION            "201502010000Z"
        DESCRIPTION         "Initial Version of BlueNet2 PDU MIB."
--      ::=                 { iso(1) org(3) dod(6) internet(1) private(4) enterprises(1) bachmann(31770) blueNet2Mib(2) }
        ::=                 { bachmann          2 }

-- *****************************************************************************

--  bachmann                OBJECT IDENTIFIER ::= { enterprises          31770       }
--  blueNet2Mib             OBJECT IDENTIFIER ::= {   bachmann                 2     }
    blueNet2Notifications   OBJECT IDENTIFIER ::= {     blueNet2Mib              0   }
    blueNet2Products        OBJECT IDENTIFIER ::= {     blueNet2Mib              1   }
    blueNet2Objects         OBJECT IDENTIFIER ::= {     blueNet2Mib              2   }
    blueNet2Identification  OBJECT IDENTIFIER ::= {       blueNet2Objects          1 }
    blueNet2Information     OBJECT IDENTIFIER ::= {       blueNet2Objects          2 }
    blueNet2Configuration   OBJECT IDENTIFIER ::= {       blueNet2Objects          3 }
    blueNet2Devices         OBJECT IDENTIFIER ::= {       blueNet2Objects          4 }
    blueNet2Sensors         OBJECT IDENTIFIER ::= {       blueNet2Objects          5 }
    blueNet2Circuits        OBJECT IDENTIFIER ::= {       blueNet2Objects          6 }
    blueNet2SocketGroups    OBJECT IDENTIFIER ::= {       blueNet2Objects          7 }
    blueNet2Variables       OBJECT IDENTIFIER ::= {       blueNet2Objects          8 }
    blueNet2MPStates        OBJECT IDENTIFIER ::= {       blueNet2Objects          9 }
    blueNet2Traps           OBJECT IDENTIFIER ::= {     blueNet2Mib              3   }
    blueNet2Conformance     OBJECT IDENTIFIER ::= {     blueNet2Mib              4   }
--  blueNet2Capabilities    OBJECT IDENTIFIER ::= {     blueNet2Mib              5   }

-- *****************************************************************************

    BlueNet2ComponentStates ::=  TEXTUAL-CONVENTION
        STATUS              current
        DESCRIPTION         "Represents the possible values of component states."
        SYNTAX              INTEGER {
                                ok              (1),
                                warning         (2),
                                alarm           (3)
                            }

    BlueNet2EntitySources   ::=  TEXTUAL-CONVENTION
        STATUS              current
        DESCRIPTION         "Represents the possible source of entity variables."
        SYNTAX              INTEGER {
                                other           (1),
                                device          (2),
                                sensor          (3),
                                circuit         (4),
                                phase           (5),
                                fuse            (6),
                                socket          (7),
                                socketgroup     (8),
                                rcm             (9)
                            }

    BlueNet2EntityStates    ::=  TEXTUAL-CONVENTION
        STATUS              current
        DESCRIPTION         "Represents the possible values of entity states."
        SYNTAX              INTEGER {
                                expected        (0),
                                undefined       (1),
                                ok              (2),
                                errorHigh       (3),
                                errorLow        (4),
                                warningHigh     (5),
                                warningLow      (6),
                                lost            (7),
                                deactivate      (8),
                                onAlarmIdentidy (9),
                                offAlarmIdentify(10),
                                onAlarm         (11),
                                offAlarm        (12),
                                onWarningIdentify  (13),
                                offWarningIdentify (14),
                                onWarning       (15),
                                offWarning      (16),
                                onIdentify      (17),
                                offIdentify     (18),
                                on              (19),
                                off             (20),
                                onChildAlarm    (21),
                                offChildAlarm   (22),
                                onChildWarning  (23),
                                offChildWarning (24),
                                childAlarm      (25),
                                childWarning    (26),
                                lostChild       (27),
                                updateInProgress    (36),
                                updateError     (37),
                                onGoingSwitch   (38),
                                high            (39),
                                low             (40),
                                alarm           (41),
                                warning         (42),
                                ok              (43),
                                disabled        (44),
                                fwVersionTooNew (45)
                            }

    BlueNet2EntityBits      ::=  TEXTUAL-CONVENTION
        DISPLAY-HINT        "1x:"
        STATUS              current
        DESCRIPTION         "Each octet within this value specifies a set of
                            eight BlueNet2EntityStates, with the first octet
                            specifying 0 through 7, the second octet
                            specifying states 8 through 15, etc.
                            Within each octet, the most significant bit
                            represents the lowest numbered state, and the least
                            significant bit represents the highest numbered
                            state. Thus, each state is represented by a single
                            bit within the value of this object. If that bit
                            has a value of '1' then that state is included in
                            the set of states; the states is not included if
                            its bit has a value of '0'."
        SYNTAX              OCTET STRING        (SIZE (8..8))

    BlueNet2DataSourceTypes ::=  TEXTUAL-CONVENTION
        STATUS              current
        DESCRIPTION         "Represents the possible values of data sources.

                            (1) voltage
                            (2) peak voltage, can be reset by user
                            (4) current
                            (5) peak current, can be reset by user
                            (7) differential current AC
                            (8) differential current DC
                            (9) neutral current if more than one phase is present
                            (16) phase angle
                            (17) power factor
                            (18) apparent power
                            (19) active power
                            (20) peak active power
                            (21) peak active power, can be reset by user
                            (22) reactive power
                            (23) frequency
                            (24) peak neutral current
                            (32) apparent energy accumulated
                            (33) apparent energy delta
                            (34) reactive energy accumulated
                            (35) reactive energy delta
                            (36) active energy accumulated
                            (37) active energy delta
                            (38) active energy accumulated, can be reset by the user
                            (39) active energy runtime
                            (40) custom energy runtime, can be reset by the user
                            (48) fuse state (on, off etc)
                            (49) orientation as calculated by the gyro sensor
                            (50) usb
                            (51) socket state
                            (52) pdu state
                            (53) state of an external i2c sensor
                            (54) circuit state
                            (55) phase state
                            (56) rcd state
                            (57) socketGroup state
                            (58) global state
                            (64) (external) sensor type
                            (65) circuit type
                            (66) fuse type
                            (67) socket type
                            (68) socket color
                            (69) phase type
                            (70) pdu type
                            (71) rcm type
                            (80) delta voltage 12
                            (81) delta voltage 23
                            (82) delta voltage 31
                            (83) rcm AC peak value
                            (84) rcm DC peak value
                            (256) temperature
                            (257) humidity
                            (258) general purpose i/o input  channel 1
                            (259) general purpose i/o input  channel 2
                            (260) general purpose i/o input  channel 3
                            (261) general purpose i/o input  channel 4
                            (262) general purpose i/o output channel 1
                            (263) general purpose i/o output channel 2
                            (264) general purpose i/o output channel 3
                            (265) general purpose i/o output channel 4
							(266) dew point
							(267) pressure
							(268) differential pressure
							(269) co2 equivalent (air quality)
							(270) total volatile organic components (air quality)
                            (65535) Unspecified"
        SYNTAX              INTEGER {
                                voltage         (1),
                                peakVoltage     (2),
                                current         (4),
                                peakCurrent     (5),
                                differentialCurrentAc(7),
                                differentialCurrentDc(8),
                                neutralCurrent  (9),
                                phaseAngle      (16),
                                powerFactor     (17),
                                apparentPower   (18),
                                activePower     (19),
                                peakActivePower (20),
                                peakActivePowerUser(21),
                                reactivePower   (22),
                                frequency       (23),
                                peakNeutralCurrent(24),
                                apparentEnergyAccumulated(32),
                                apparentEnergyDelta(33),
                                reactiveEnergyAccumulated(34),
                                reactiveEnergyDelta(35),
                                activeEnergyAccumulated(36),
                                activeEnergyDelta(37),
                                activeEnergyAccumulatedUser(38),
                                activeEnergyRuntime(39),
                                customEnergyRuntimeUser(40),
                                fuseState       (48),
                                orientation     (49),
                                usb             (50),
                                socketState     (51),
                                pduState        (52),
                                sensorState     (53),
                                circuitState    (54),
                                phaseState      (55),
                                rcdState        (56),
                                socketGroupState (57),
                                globalState     (58),
                                sensorType      (64),
                                circuitType     (65),
                                fuseType        (66),
                                socketType      (67),
                                socketColor     (68),
                                phaseType       (69),
                                pduType         (70),
                                rcmType         (71),
                                deltaVoltage12  (80),
                                deltaVoltage23  (81),
                                deltaVoltage31  (82),
                                rcmACPeak       (83),
                                rcmDCPeak       (84),
                                temperature     (256),
                                humidity        (257),
                                ioInputChannel1 (258),
                                ioInputChannel2 (259),
                                ioInputChannel3 (260),
                                ioInputChannel4 (261),
                                ioOutputChannel1(262),
                                ioOutputChannel2(263),
                                ioOutputChannel3(264),
                                ioOutputChannel4(265),
								dewPoint        (266),
								pressure        (267),
								diffPressure    (268),
								co2Equivalent   (269),
								tvoc            (270),
                                unspecified     (65535)
                            }

    BlueNet2DataSourceUnits ::=  TEXTUAL-CONVENTION
        STATUS              current
        DESCRIPTION         "Represents the possible units of data sources.
                            Definitions according to CiA 2006."
        SYNTAX              INTEGER {
                                metre           (1),
                                kilogram        (2),
                                second          (3),
                                ampere          (4),
                                kelvin          (5),
                                mole            (6),
                                candela         (7),
                                radian          (16),
                                steradian       (17),
                                hertz           (32),
                                newton          (33),
                                pascal          (34),
                                joule           (35),
                                watt            (36),
                                coulomb         (37),
                                volt            (38),
                                farad           (39),
                                ohm             (40),
                                siemens         (41),
                                weber           (42),
                                tesla           (43),
                                henry           (44),
                                celsius         (45),
                                lumen           (46),
                                lux             (47),
                                becquerel       (48),
                                gray            (49),
                                sievert         (50),
                                katal           (51),
                                grade           (64),
                                degree          (65),
                                aMinuteAngle    (66),
                                aSecondAngle    (67),
                                litre           (68),
                                are             (69),
                                hectare         (70),
                                minute          (71),
                                hour            (72),
                                day             (73),
                                year            (74),
                                gram            (75),
                                tonne           (76),
                                bar             (78),
                                poise           (79),
                                stokes          (80),
                                electronvolt    (81),
                                atomicMass      (82),
                                astronomic      (83),
                                parsec          (84),
                                metrePerS2      (85),
                                newtonMetre     (86),
                                s2              (87),
                                m2              (88),
                                m3              (89),
                                pascalSecond    (90),
                                jPerKgK         (91),
                                wPerMK          (92),
                                jPerMoleK       (93),
                                wPerM2Sr        (94),
                                katPerM3        (95),
                                kiloWattHour    (240),
                                percentage      (241),
                                va              (242),
                                var             (243),
                                kiloVaHour      (244),
                                kiloVarHour     (245),
                                milliAmpere     (246),
                                unit            (255)
                            }

    BlueNet2InfoMessageSources ::=  TEXTUAL-CONVENTION
        STATUS              current
        DESCRIPTION         "Represents the source of a message."
        SYNTAX              INTEGER {
                                other           (1),
                                device          (2),
                                sensor          (3),
                                variable        (4)
                            }

    BlueNet2SocketModes     ::=  TEXTUAL-CONVENTION
        STATUS              current
        DESCRIPTION         "Represents the mode of a socket or socket group or its LEDs.
                            A socket or socket group can be notSwitchable or switchedOn/Off.
                            A socket group may also have different sockets switchedOnAndOff.
                            A socket or socket group can be set using switchedOn/Off only.
                            A socket group without any socket at all has mode notAvailable."
        SYNTAX              INTEGER {
                                switchedOn      (1),
                                switchedOff     (2),
                                switchedOnAndOff(3),
                                notAvailable    (4),
                                notSwitchable   (5)
                            }

    BlueNet2SocketMembers   ::= TEXTUAL-CONVENTION
        DISPLAY-HINT        "1x:"
        STATUS              current
        DESCRIPTION         "Each octet within this value specifies a set of eight
                            sockets, with the first octet specifying sockets 1 through
                            8, the second octet specifying sockets 9 through 16, etc.
                            Within each octet, the most significant bit represents
                            the lowest numbered socket, and the least significant bit
                            represents the highest numbered socket.  Thus, each socket
                            of the pdu is represented by a single bit within the
                            value of this object.  If that bit has a value of '1'
                            then that socket is included in the set of sockets; the
                            socket is not included if its bit has a value of '0'."
        SYNTAX              OCTET STRING        (SIZE (1..255))


    BlueNet2GPIOModes     ::=  TEXTUAL-CONVENTION
        STATUS              current
        DESCRIPTION         "Represents the mode of GPIO input or output."
        SYNTAX              INTEGER {
                                disabled      (0),
                                enabled       (2),
                                s0            (6),
                                undefined     (7)
                            }


    BlueNet2GPIOSwitch     ::=  TEXTUAL-CONVENTION
        STATUS              current
        DESCRIPTION         "Represents the state to switch on/off GPIO output."
        SYNTAX              INTEGER {
                                undefined     (0),
                                switchable    (3),
                                notSwitchable (5),
                                on            (1),
                                off           (2)
                            }


    BlueNet2RcmSelftestCommand     ::=  TEXTUAL-CONVENTION
        STATUS              current
        DESCRIPTION         "Represents RCM self-test commands with or without alarm or selftest notifications."
        SYNTAX              INTEGER {
        						selftestWithoutAnyNotification      (0),
                                selftestWithAlarmNotifyOnly         (1),
                                selftestWithSelftestNotifyOnly      (2),
                                selftestWithAlarmAndSelftestNotify  (3),
                                selftestCommand                     (4)
                            }

    BlueNet2RcmSelftestResult     ::=  TEXTUAL-CONVENTION
        STATUS              current
        DESCRIPTION         "Represents RCM self-test result values."
        SYNTAX              INTEGER {
        						notRun         (0),
                                notReachable   (1),
                                success        (2),
                                failure        (3),
                                partialSuccess (4),
                                cancelled      (5),
                                notApplicable  (255)
                            }


-- *****************************************************************************

--  Notifications  --

	blueNet2NotificationPrefix      OBJECT IDENTIFIER ::= { blueNet2Notifications                  0 }
    blueNet2PduStatusOkNotification NOTIFICATION-TYPE
        OBJECTS             {
                                blueNet2DeviceGuid,
                                blueNet2DeviceStatus,
                                blueNet2DeviceAlarm
                            }
        STATUS              current
        DESCRIPTION         "PDU status ok."
--
--            #CATEGORY     "Status Events."
--            #TYPE         "PDU status ok."
--            #SUMMARY      "Guid %x device status is %i: %s."
--            #ARGUMENTS    {0,1,2}
--            #SEVERITY     INFORMATIONAL
--            #STATE        OPERATIONAL
--
        ::=                 { blueNet2NotificationPrefix 1 }

    blueNet2PduStatusWarningNotification NOTIFICATION-TYPE
        OBJECTS             {
                                blueNet2DeviceGuid,
                                blueNet2DeviceStatus,
                                blueNet2DeviceAlarm
                            }
        STATUS              current
        DESCRIPTION         "PDU status warning."
--
--            #CATEGORY     "Status Events."
--            #TYPE         "PDU status warning."
--            #SUMMARY      "Guid %x device status is %i: %s."
--            #ARGUMENTS    {0,1,2}
--            #SEVERITY     MINOR
--            #STATE        OPERATIONAL
--
        ::=                 { blueNet2NotificationPrefix 2 }

    blueNet2PduStatusAlarmNotification NOTIFICATION-TYPE
        OBJECTS             {
                                blueNet2DeviceGuid,
                                blueNet2DeviceStatus,
                                blueNet2DeviceAlarm
                            }
        STATUS              current
        DESCRIPTION         "PDU status alarm."
--
--            #CATEGORY     "Status Events."
--            #TYPE         "PDU status alarm."
--            #SUMMARY      "Guid %x device status is %i: %s."
--            #ARGUMENTS    {0,1,2}
--            #SEVERITY     MAJOR
--            #STATE        OPERATIONAL
--
        ::=                 { blueNet2NotificationPrefix 3 }

    blueNet2SensorStatusOkNotification NOTIFICATION-TYPE
        OBJECTS             {
                                blueNet2SensorGuid,
                                blueNet2SensorStatus,
                                blueNet2SensorAlarm
                            }
        STATUS              current
        DESCRIPTION         "Sensor status ok."
--
--            #CATEGORY     "Status Events."
--            #TYPE         "Sensor status ok."
--            #SUMMARY      "Guid %x sensor status is %i: %s."
--            #ARGUMENTS    {0,1,2}
--            #SEVERITY     INFORMATIONAL
--            #STATE        OPERATIONAL
--
        ::=                 { blueNet2NotificationPrefix 4 }

    blueNet2SensorStatusWarningNotification NOTIFICATION-TYPE
        OBJECTS             {
                                blueNet2SensorGuid,
                                blueNet2SensorStatus,
                                blueNet2SensorAlarm
                            }
        STATUS              current
        DESCRIPTION         "Sensor status warning."
--
--            #CATEGORY     "Status Events."
--            #TYPE         "Sensor status warning."
--            #SUMMARY      "Guid %x sensor status is %i: %s."
--            #ARGUMENTS    {0,1,2}
--            #SEVERITY     MINOR
--            #STATE        OPERATIONAL
--
        ::=                 { blueNet2NotificationPrefix 5 }

    blueNet2SensorStatusAlarmNotification NOTIFICATION-TYPE
        OBJECTS             {
                                blueNet2SensorGuid,
                                blueNet2SensorStatus,
                                blueNet2SensorAlarm
                            }
        STATUS              current
        DESCRIPTION         "Sensor status alarm."
--
--            #CATEGORY     "Status Events."
--            #TYPE         "Sensor status alarm."
--            #SUMMARY      "Guid %x sensor status is %i: %s."
--            #ARGUMENTS    {0,1,2}
--            #SEVERITY     INFORMATIONAL
--            #STATE        OPERATIONAL
--
        ::=                 { blueNet2NotificationPrefix 6 }

    blueNet2VariableStatusOkNotification NOTIFICATION-TYPE
        OBJECTS             {
                                blueNet2VariableDataGuid,
                                blueNet2VariableDataStatus,
                                blueNet2VariableDataValue,
                                blueNet2VariableAlarm
                            }
        STATUS              current
        DESCRIPTION         "Variable status ok."
--
--            #CATEGORY     "Threshold Events."
--            #TYPE         "Variable status ok."
--            #SUMMARY      "Guid %x variable value %i is ok (%i), %s."
--            #ARGUMENTS    {0,1,2,3}
--            #SEVERITY     INFORMATIONAL
--            #STATE        OPERATIONAL
--
        ::=                 { blueNet2NotificationPrefix 7 }

    blueNet2VariableLowerWarningNotification NOTIFICATION-TYPE
        OBJECTS             {
                                blueNet2VariableDataGuid,
                                blueNet2VariableDataStatus,
                                blueNet2VariableDataValue,
                                blueNet2VariableSetPointLowerAlarm,
                                blueNet2VariableAlarm
                            }
        STATUS              current
        DESCRIPTION         "Variable status lower warning."
--
--            #CATEGORY     "Threshold Events."
--            #TYPE         "Variable status lower warning."
--            #SUMMARY      "Guid %x variable value %i deceeds %i (%i), %s."
--            #ARGUMENTS    {0,2,1,3,4}
--            #SEVERITY     MINOR
--            #STATE        OPERATIONAL
--
        ::=                 { blueNet2NotificationPrefix 8 }

    blueNet2VariableUpperWarningNotification NOTIFICATION-TYPE
        OBJECTS             {
                                blueNet2VariableDataGuid,
                                blueNet2VariableDataStatus,
                                blueNet2VariableDataValue,
                                blueNet2VariableSetPointUpperWarning,
                                blueNet2VariableAlarm
                            }
        STATUS              current
        DESCRIPTION         "Variable status upper warning."
--
--            #CATEGORY     "Threshold Events."
--            #TYPE         "Variable status upper warning."
--            #SUMMARY      "Guid %x variable value %i exceeds %i (%i), %s."
--            #ARGUMENTS    {0,2,1,3,4}
--            #SEVERITY     MINOR
--            #STATE        OPERATIONAL
--
        ::=                 { blueNet2NotificationPrefix 9 }

    blueNet2VariableLowerAlarmNotification NOTIFICATION-TYPE
        OBJECTS             {
                                blueNet2VariableDataGuid,
                                blueNet2VariableDataStatus,
                                blueNet2VariableDataValue,
                                blueNet2VariableSetPointLowerAlarm,
                                blueNet2VariableAlarm
                            }
        STATUS              current
        DESCRIPTION         "Variable status lower alarm."
--
--            #CATEGORY     "Threshold Events."
--            #TYPE         "Variable status lower alarm."
--            #SUMMARY      "Guid %x variable value %i deceeds %i (%i), %s."
--            #ARGUMENTS    {0,2,1,3,4}
--            #SEVERITY     MAJOR
--            #STATE        OPERATIONAL
--
        ::=                 { blueNet2NotificationPrefix 10 }

    blueNet2VariableUpperAlarmNotification NOTIFICATION-TYPE
        OBJECTS             {
                                blueNet2VariableDataGuid,
                                blueNet2VariableDataStatus,
                                blueNet2VariableDataValue,
                                blueNet2VariableSetPointUpperAlarm,
                                blueNet2VariableAlarm
                            }
        STATUS              current
        DESCRIPTION         "Variable status upper alarm."
--
--            #CATEGORY     "Threshold Events."
--            #TYPE         "Variable status upper alarm."
--            #SUMMARY      "Guid %x variable value %i exceeds %i (%i), %s."
--            #ARGUMENTS    {0,2,1,3,4}
--            #SEVERITY     MAJOR
--            #STATE        OPERATIONAL
--
        ::=                 { blueNet2NotificationPrefix 11 }

    blueNet2ReconfigAgentNotification NOTIFICATION-TYPE
        OBJECTS             {
                                sysObjectID
                            }
        STATUS              current
        DESCRIPTION         "Agent reconfiguration."
--
--            #CATEGORY     "Status Events."
--            #TYPE         "Agent status."
--            #SUMMARY      "Agent type: %s, Status: configuration has changed."
--            #ARGUMENTS    {0}
--            #SEVERITY     INFORMATIONAL
--            #TIMEINDEX    6
--            #STATE        OPERATIONAL
--
        ::=                 { blueNet2NotificationPrefix 98 }

    blueNet2ShutdownAgentNotification NOTIFICATION-TYPE
        OBJECTS             {
                                sysObjectID
                            }
        STATUS              current
        DESCRIPTION         "Agent shutdown."
--
--            #CATEGORY     "Status Events."
--            #TYPE         "Agent status."
--            #SUMMARY      "Agent type: %s, Status: shutdown."
--            #ARGUMENTS    {0}
--            #SEVERITY     SEVERE
--            #TIMEINDEX    6
--            #STATE        NONOPERATIONAL
--
        ::=                 { blueNet2NotificationPrefix 99 }

-- *****************************************************************************

--  Products --

--  please refer to BACHMANN-BLUENET2-PRODUCTS-MIB definitions

-- *****************************************************************************

--  Objects --

-- =============================================================================
--  blueNet2Identification: global BlueNet2 PDU product identification --

    blueNet2IdProductVendor OBJECT-TYPE
        SYNTAX              DisplayString       (SIZE (0..32))
        MAX-ACCESS          read-only
        STATUS              current
        DESCRIPTION         "BlueNet2 vendor name."
        ::=                 { blueNet2Identification 1 }

    blueNet2IdProductName   OBJECT-TYPE
        SYNTAX              DisplayString       (SIZE (0..32))
        MAX-ACCESS          read-only
        STATUS              current
        DESCRIPTION         "BlueNet2 product name."
        ::=                 { blueNet2Identification 2 }

    blueNet2IdProductURI    OBJECT-TYPE
        SYNTAX              DisplayString       (SIZE (0..32))
        MAX-ACCESS          read-only
        STATUS              current
        DESCRIPTION         "URI of BlueNet2 PDU product."
        ::=                 { blueNet2Identification 3 }

    blueNet2IdProductPartNr OBJECT-TYPE
        SYNTAX              DisplayString       (SIZE (0..32))
        MAX-ACCESS          read-only
        STATUS              current
        DESCRIPTION         "Part number of BlueNet2 PDU product."
        ::=                 { blueNet2Identification 4 }

    blueNet2IdProductSNr    OBJECT-TYPE
        SYNTAX              DisplayString       (SIZE (0..32))
        MAX-ACCESS          read-only
        STATUS              current
        DESCRIPTION         "Unique serial number of BlueNet2 PDU product."
        ::=                 { blueNet2Identification 5 }

    blueNet2IdProductDate   OBJECT-TYPE
        SYNTAX              DisplayString       (SIZE (0..32))
        MAX-ACCESS          read-only
        STATUS              current
        DESCRIPTION         "Production date of BlueNet2 PDU product."
        ::=                 { blueNet2Identification 6 }

    blueNet2IdProductFacility OBJECT-TYPE
        SYNTAX              INTEGER {
                                neutralCurrent  (0),
                                fuse            (1),
                                rcd             (2),
                                identify        (3),
                                switch          (4),
                                oneInlet        (5),
                                monitoredPerOutlet(6),
                                monitoredPerPhase(7),
                                spd             (8)
                            }
        MAX-ACCESS          read-only
        STATUS              current
        DESCRIPTION         "Functional product facility of BlueNet2 PDU product.
                            0 : number of phases is 3
                            1 : has real fuses
                            2 : has any RCMs
                            3 : has sockets
                            4 : sockets can be switched
                            5 : has one inlet
                            6 : measurement is done on socket layer
                            7 : measurement is done on phase layer
                            8 : has any SPDs"
        ::=                 { blueNet2Identification 7 }

    blueNet2IdProductCaps   OBJECT-TYPE
        SYNTAX              Unsigned32
        MAX-ACCESS          read-only
        STATUS              current
        DESCRIPTION         "Capabilities of BlueNet2 PDU product as referred in
                            BACHMANN-BLUENET2-CAPABILITY-MIB blueNet2Capabilities.
                            e.g. read 10203 as 01 02 03 to get version 1.2.3."
        ::=                 { blueNet2Identification 8 }

    blueNet2IdProductFwV    OBJECT-TYPE
        SYNTAX              DisplayString       (SIZE (0..32))
        MAX-ACCESS          read-only
        STATUS              current
        DESCRIPTION         "Hardware revision of BlueNet2 PDU."
        ::=                 { blueNet2Identification 9 }

    blueNet2IdProductHwV    OBJECT-TYPE
        SYNTAX              DisplayString       (SIZE (0..32))
        MAX-ACCESS          read-only
        STATUS              current
        DESCRIPTION         "Hardware revision of BlueNet2 PDU."
        ::=                 { blueNet2Identification 10 }

    blueNet2IdProductSwV    OBJECT-TYPE
        SYNTAX              DisplayString       (SIZE (0..32))
        MAX-ACCESS          read-only
        STATUS              current
        DESCRIPTION         "Software revision of BlueNet2 PDU."
        ::=                 { blueNet2Identification 11 }

    blueNet2IdProductOsV    OBJECT-TYPE
        SYNTAX              DisplayString       (SIZE (0..255))
        MAX-ACCESS          read-only
        STATUS              current
        DESCRIPTION         "Operating system revision of BlueNet2 PDU."
        ::=                 { blueNet2Identification 12 }

    blueNet2IdProductArch   OBJECT-TYPE
        SYNTAX              DisplayString       (SIZE (0..32))
        MAX-ACCESS          read-only
        STATUS              current
        DESCRIPTION         "Operating system cpu architecture of BlueNet2 PDU."
        ::=                 { blueNet2Identification 13 }

    blueNet2IdProductMAC    OBJECT-TYPE
        SYNTAX              DisplayString       (SIZE (0..32))
        MAX-ACCESS          read-only
        STATUS              current
        DESCRIPTION         "Ethernet MAC address of BlueNet2 PDU."
        ::=                 { blueNet2Identification 14 }


-- =============================================================================
--  blueNet2Information: global BlueNet2 PDU information  --

    blueNet2InfoUpTime      OBJECT-TYPE
        SYNTAX              Unsigned32
        MAX-ACCESS          read-only
        STATUS              current
        DESCRIPTION         "Uptime of the BlueNet2 PDU operating system in seconds.
                            This is different to the sysUpTime since agent (re-)start."
        ::=                 { blueNet2Information 1 }

    blueNet2InfoOverallStatus OBJECT-TYPE
        SYNTAX              BlueNet2ComponentStates
        MAX-ACCESS          read-only
        STATUS              current
        DESCRIPTION         "General hadware status of BlueNet2 PDU."
        ::=                 { blueNet2Information 2 }

    blueNet2InfoNumberOfChanges OBJECT-TYPE
        SYNTAX              Unsigned32
        MAX-ACCESS          read-only
        STATUS              current
        DESCRIPTION         "The number of global configuration changes."
        ::=                 { blueNet2Information 3 }

    blueNet2InfoLastChange  OBJECT-TYPE
        SYNTAX              TimeTicks
        MAX-ACCESS          read-only
        STATUS              current
        DESCRIPTION         "The value of the sysUpTime object at which the
                            last change in global configuration happened."
        ::=                 { blueNet2Information 4 }

    blueNet2InfoAccumulatedStatus OBJECT-TYPE
        SYNTAX              BlueNet2EntityBits
        MAX-ACCESS          read-only
        STATUS              current
        DESCRIPTION         "A bit field of all current states."
        ::=                 { blueNet2Information 5 }

    blueNet2InfoLoadTable   OBJECT-TYPE
        SYNTAX              SEQUENCE OF BlueNet2InfoLoadEntry
        MAX-ACCESS          not-accessible
        STATUS              current
        DESCRIPTION         "A list of system load entries."
        ::=                 { blueNet2Information 6 }

    blueNet2InfoLoadEntry   OBJECT-TYPE
        SYNTAX              BlueNet2InfoLoadEntry
        MAX-ACCESS          not-accessible
        STATUS              current
        DESCRIPTION         "Entries of system load table."
        INDEX               { blueNet2InfoLoadIndex }
        ::=                 { blueNet2InfoLoadTable 1 }

    BlueNet2InfoLoadEntry   ::= SEQUENCE            {
                                blueNet2InfoLoadIndex       Unsigned32,
                                blueNet2InfoLoadAverage     Unsigned32
                            }

    blueNet2InfoLoadIndex   OBJECT-TYPE
        SYNTAX              Unsigned32          (1..10)
        MAX-ACCESS          not-accessible
        STATUS              current
        DESCRIPTION         "Index for the system load table.
                            These are the past minutes the load is given for."
        ::=                 { blueNet2InfoLoadEntry 1 }

    blueNet2InfoLoadAverage OBJECT-TYPE
        SYNTAX              Unsigned32
        MAX-ACCESS          read-only
        STATUS              current
        DESCRIPTION         "System load average multiplied by 100."
        ::=                 { blueNet2InfoLoadEntry 2 }


    blueNet2InfoMessageTable OBJECT-TYPE
        SYNTAX              SEQUENCE OF BlueNet2InfoMessageEntry
        MAX-ACCESS          not-accessible
        STATUS              current
        DESCRIPTION         "A table of the last text message per source."
        ::=                 { blueNet2Information 7 }

    blueNet2InfoMessageEntry OBJECT-TYPE
        SYNTAX              BlueNet2InfoMessageEntry
        MAX-ACCESS          not-accessible
        STATUS              current
        DESCRIPTION         "Entries of last message table."
        INDEX               { blueNet2InfoMessageSource }
        ::=                 { blueNet2InfoMessageTable 1 }

    BlueNet2InfoMessageEntry ::= SEQUENCE            {
                                blueNet2InfoMessageSource   BlueNet2InfoMessageSources,
                                blueNet2InfoMessageStatus   BlueNet2ComponentStates,
                                blueNet2InfoMessageTime     TimeTicks,
                                blueNet2InfoMessageText     DisplayString,
                                blueNet2InfoMessageNumberOfOks Unsigned32,
                                blueNet2InfoMessageNumberOfWarnings Unsigned32,
                                blueNet2InfoMessageNumberOfErrors Unsigned32
                            }

    blueNet2InfoMessageSource OBJECT-TYPE
        SYNTAX              BlueNet2InfoMessageSources
        MAX-ACCESS          not-accessible
        STATUS              current
        DESCRIPTION         "Source of the text message."
        ::=                 { blueNet2InfoMessageEntry 1 }

    blueNet2InfoMessageStatus OBJECT-TYPE
        SYNTAX              BlueNet2ComponentStates
        MAX-ACCESS          read-only
        STATUS              current
        DESCRIPTION         "Status of the text message source."
        ::=                 { blueNet2InfoMessageEntry 2 }

    blueNet2InfoMessageTime OBJECT-TYPE
        SYNTAX              TimeTicks
        MAX-ACCESS          read-only
        STATUS              current
        DESCRIPTION         "Timestamp of last received text message
                            according to operating time sysUpTime."
        ::=                 { blueNet2InfoMessageEntry 3 }

    blueNet2InfoMessageText OBJECT-TYPE
        SYNTAX              DisplayString       (SIZE (0..255))
        MAX-ACCESS          read-only
        STATUS              current
        DESCRIPTION         "Last text message of a source."
        ::=                 { blueNet2InfoMessageEntry 4 }

    blueNet2InfoMessageNumberOfOks OBJECT-TYPE
        SYNTAX              Unsigned32
        MAX-ACCESS          read-only
        STATUS              current
        DESCRIPTION         "The accumulated number of ok messages."
        ::=                 { blueNet2InfoMessageEntry 5 }

    blueNet2InfoMessageNumberOfWarnings OBJECT-TYPE
        SYNTAX              Unsigned32
        MAX-ACCESS          read-only
        STATUS              current
        DESCRIPTION         "The accumulated number of warning messages."
        ::=                 { blueNet2InfoMessageEntry 6 }

    blueNet2InfoMessageNumberOfErrors OBJECT-TYPE
        SYNTAX              Unsigned32
        MAX-ACCESS          read-only
        STATUS              current
        DESCRIPTION         "The accumulated number of error messages."
        ::=                 { blueNet2InfoMessageEntry 7 }

-- =============================================================================
--  blueNet2Configuration: global BlueNet2 PDU configuration  --

    blueNet2Alias           OBJECT-TYPE
        SYNTAX              DisplayString       (SIZE (0..255))
        MAX-ACCESS          read-write
        STATUS              current
        DESCRIPTION         "BlueNet2 product alias.
                            This object should be set by the administrator."
        ::=                 { blueNet2Configuration 1 }

    blueNet2Language        OBJECT-TYPE
        SYNTAX              INTEGER {
                                other           (1),
                                english         (2),
                                german          (3),
                                french          (4)
                            }
        MAX-ACCESS          read-write
        STATUS              deprecated
        DESCRIPTION         "Supported display language."
        DEFVAL              { english }
        ::=                 { blueNet2Configuration 2 }

    blueNet2DateTime        OBJECT-TYPE
        SYNTAX              DateAndTime
--      DISPLAY-HINT        "2d-1d-1d,1d:1d:1d.1d,1a1d:1d"
        MAX-ACCESS          read-write
        STATUS              current
        DESCRIPTION         "Date and time of day as set manually or by NTP."
        ::=                 { blueNet2Configuration 3 }

    blueNet2Protocols       OBJECT IDENTIFIER ::= { blueNet2Configuration          4 }

    blueNet2FtpAccess       OBJECT-TYPE
        SYNTAX              INTEGER {
                                disabled        (1),
                                enabled         (2)
                            }
        MAX-ACCESS          read-write
        STATUS              current
        DESCRIPTION         "Ftp access status."
        DEFVAL              { disabled }
        ::=                 { blueNet2Protocols 1 }

    blueNet2FtpPort         OBJECT-TYPE
        SYNTAX              Unsigned32          (1..65535)
        MAX-ACCESS          read-write
        STATUS              current
        DESCRIPTION         "TCP/IP port of FTP daemon."
        DEFVAL              { 21 }
        ::=                 { blueNet2Protocols 2 }

    blueNet2HttpAccess      OBJECT-TYPE
        SYNTAX              BITS {
                                httpEnabled     (0),
                                httpsEnabled    (1)
                            }
        MAX-ACCESS          read-write
        STATUS              current
        DESCRIPTION         "HTTP/HTTPS access status."
        DEFVAL              { { httpsEnabled } }
        ::=                 { blueNet2Protocols 3 }

    blueNet2HttpPort        OBJECT-TYPE
        SYNTAX              Unsigned32          (1..65535)
        MAX-ACCESS          read-write
        STATUS              current
        DESCRIPTION         "TCP/IP port of HTTP daemon."
        DEFVAL              { 80 }
        ::=                 { blueNet2Protocols 4 }

    blueNet2HttpsPort       OBJECT-TYPE
        SYNTAX              Unsigned32          (1..65535)
        MAX-ACCESS          read-write
        STATUS              current
        DESCRIPTION         "TCP/IP port of HTTPS daemon."
        DEFVAL              { 443 }
        ::=                 { blueNet2Protocols 5 }

    blueNet2SftpAccess      OBJECT-TYPE
        SYNTAX              INTEGER {
                                disabled        (1),
                                enabled         (2)
                            }
        MAX-ACCESS          read-write
        STATUS              deprecated
        DESCRIPTION         "Sftp access status."
        DEFVAL              { disabled }
        ::=                 { blueNet2Protocols 6 }

    blueNet2SftpPort        OBJECT-TYPE
        SYNTAX              Unsigned32          (1..65535)
        MAX-ACCESS          read-write
        STATUS              deprecated
        DESCRIPTION         "TCP/IP port of SFTP daemon."
        DEFVAL              { 115 }
        ::=                 { blueNet2Protocols 7 }

    blueNet2SshAccess       OBJECT-TYPE
        SYNTAX              INTEGER {
                                disabled        (1),
                                enabled         (2)
                            }
        MAX-ACCESS          read-write
        STATUS              current
        DESCRIPTION         "Ssh access status."
        DEFVAL              { enabled }
        ::=                 { blueNet2Protocols 8 }

    blueNet2SshPort         OBJECT-TYPE
        SYNTAX              Unsigned32          (1..65535)
        MAX-ACCESS          read-write
        STATUS              current
        DESCRIPTION         "TCP/IP port of SSH daemon."
        DEFVAL              { 22 }
        ::=                 { blueNet2Protocols 9 }

    blueNet2TelnetAccess    OBJECT-TYPE
        SYNTAX              INTEGER {
                                disabled        (1),
                                enabled         (2)
                            }
        MAX-ACCESS          read-write
        STATUS              deprecated
        DESCRIPTION         "Telnet access status."
        DEFVAL              { disabled }
        ::=                 { blueNet2Protocols 10 }

    blueNet2TelnetPort      OBJECT-TYPE
        SYNTAX              Unsigned32          (1..65535)
        MAX-ACCESS          read-write
        STATUS              deprecated
        DESCRIPTION         "TCP/IP port of telnet daemon."
        DEFVAL              { 23 }
        ::=                 { blueNet2Protocols 11 }

-- -----------------------------------------------------------------------------

    blueNet2Snmp            OBJECT IDENTIFIER ::= { blueNet2Protocols             12 }

    blueNet2SnmpVersions    OBJECT-TYPE
        SYNTAX              BITS {
                                snmpv1          (0),
                                snmpv2c         (1),
                                snmpv3          (2)
                            }
        MAX-ACCESS          read-only
        STATUS              current
        DESCRIPTION         "Supported and enabled SNMP versions."
        DEFVAL              { { snmpv1, snmpv2c, snmpv3 } }
        ::=                 { blueNet2Snmp      1 }

    blueNet2MaxTrapReceivers OBJECT-TYPE
        SYNTAX              Unsigned32          (1..256)
        MAX-ACCESS          read-only
        STATUS              current
        DESCRIPTION         "The maximum number of entries in blueNet2TrapReceiverTable."
        ::=                 { blueNet2Snmp      2 }

    blueNet2TrapReceiverTable OBJECT-TYPE
        SYNTAX              SEQUENCE OF BlueNet2TrapReceiverEntry
        MAX-ACCESS          not-accessible
        STATUS              current
        DESCRIPTION         "A list of trap receiver entries."
        ::=                 { blueNet2Snmp      3 }

    blueNet2TrapReceiverEntry OBJECT-TYPE
        SYNTAX              BlueNet2TrapReceiverEntry
        MAX-ACCESS          not-accessible
        STATUS              current
        DESCRIPTION         "Entries of trapTable."
        INDEX               { blueNet2TrapReceiverIndex }
        ::=                 { blueNet2TrapReceiverTable 1 }

    BlueNet2TrapReceiverEntry ::= SEQUENCE            {
                                blueNet2TrapReceiverIndex   Unsigned32,
                                blueNet2TrapReceiverRowStatus RowStatus,
                                blueNet2TrapReceiverProtocol INTEGER,
                                blueNet2TrapReceiverAddress DisplayString,
                                blueNet2TrapReceiverFriendlyName DisplayString,
                                blueNet2TrapReceiverDescription DisplayString,
                                blueNet2TrapReceiverCommunity DisplayString,
                                blueNet2TrapReceiverUsername DisplayString
                            }

    blueNet2TrapReceiverIndex OBJECT-TYPE
        SYNTAX              Unsigned32          (1..256)
        MAX-ACCESS          not-accessible
        STATUS              current
        DESCRIPTION         "Index of the trap receiver table."
        ::=                 { blueNet2TrapReceiverEntry 1 }

    blueNet2TrapReceiverRowStatus OBJECT-TYPE
        SYNTAX              RowStatus
        MAX-ACCESS          read-create
        STATUS              current
        DESCRIPTION         "Activate/create/destroy/disable a trap receiver entry."
        ::=                 { blueNet2TrapReceiverEntry 2 }

    blueNet2TrapReceiverProtocol OBJECT-TYPE
        SYNTAX              INTEGER {
                                snmpv1Trap      (1),
                                snmpv2cTrap     (2),
                                snmpv2cInform   (3),
                                snmpv3Trap      (4),
                                snmpv3Inform    (5)
                            }
        MAX-ACCESS          read-only
        STATUS              current
        DESCRIPTION         "Set trap/inform version."
        DEFVAL              { snmpv1Trap }
        ::=                 { blueNet2TrapReceiverEntry 3 }

    blueNet2TrapReceiverAddress OBJECT-TYPE
        SYNTAX              DisplayString       (SIZE (0..64))
        MAX-ACCESS          read-only
        STATUS              current
        DESCRIPTION         "IPv4/IPv6 address or host name of trap receiver."
        ::=                 { blueNet2TrapReceiverEntry 4 }

    blueNet2TrapReceiverFriendlyName OBJECT-TYPE
        SYNTAX              DisplayString       (SIZE (0..128))
        MAX-ACCESS          read-only
        STATUS              deprecated
        DESCRIPTION         "User friendly name to identify a trap receiver.
                            This is a mnemonic only and will not be used to send traps."
        ::=                 { blueNet2TrapReceiverEntry 5 }

    blueNet2TrapReceiverDescription OBJECT-TYPE
        SYNTAX              DisplayString       (SIZE (0..255))
        MAX-ACCESS          read-only
        STATUS              deprecated
        DESCRIPTION         "Description to identify a trap receiver.
                            This is a mnemonic only and will not be used to send traps."
        ::=                 { blueNet2TrapReceiverEntry 6 }

    blueNet2TrapReceiverCommunity OBJECT-TYPE
        SYNTAX              DisplayString       (SIZE (0..64))
        MAX-ACCESS          read-only
        STATUS              current
        DESCRIPTION         "Community used by SNMPv1 and SNMPv2c to identify at trap receiver address."
        ::=                 { blueNet2TrapReceiverEntry 7 }

    blueNet2TrapReceiverUsername OBJECT-TYPE
        SYNTAX              DisplayString       (SIZE (0..64))
        MAX-ACCESS          read-only
        STATUS              current
        DESCRIPTION         "Username used by SNMPv3 to identify at trap receiver address."
        ::=                 { blueNet2TrapReceiverEntry 8 }


-- -----------------------------------------------------------------------------

    blueNet2Modbus          OBJECT IDENTIFIER ::= { blueNet2Protocols             13 }

    blueNet2ModbusVersions  OBJECT-TYPE
        SYNTAX              BITS {
                                rtu             (0),
                                tcp             (1)
                            }
        MAX-ACCESS          read-write
        STATUS              current
        DESCRIPTION         "Supported and enabled modbus version(s)."
        DEFVAL              { { tcp } }
        ::=                 { blueNet2Modbus    1 }

    blueNet2ModbusService   OBJECT-TYPE
        SYNTAX              INTEGER {
                                disabled        (1),
                                readonly        (2),
                                writeonly       (3),
                                readwrite       (4)
                            }
        MAX-ACCESS          read-write
        STATUS              deprecated
        DESCRIPTION         "Modbus service status."
        DEFVAL              { disabled }
        ::=                 { blueNet2Modbus    2 }

    blueNet2ModbusTcpPort   OBJECT-TYPE
        SYNTAX              Unsigned32          (1..65535)
        MAX-ACCESS          read-write
        STATUS              current
        DESCRIPTION         "TCP/IP port of modbus daemon."
        DEFVAL              { 502 }
        ::=                 { blueNet2Modbus    3 }

    blueNet2ModbusSerialMode OBJECT-TYPE
        SYNTAX              DisplayString       (SIZE (0..32))
        MAX-ACCESS          read-write
        STATUS              deprecated
        DESCRIPTION         "Serial mode configuration parameters (baud,data,parity,stop) of modbus daemon."
        DEFVAL              { "115200,8,N,1" }
        ::=                 { blueNet2Modbus    4 }

    blueNet2MaxModbusTcpMasters OBJECT-TYPE
        SYNTAX              Unsigned32          (1..256)
        MAX-ACCESS          read-only
        STATUS              current
        DESCRIPTION         "The maximum number of entries in blueNet2ModbusTcpTable."
        ::=                 { blueNet2Modbus    5 }

    blueNet2ModbusTcpTable  OBJECT-TYPE
        SYNTAX              SEQUENCE OF BlueNet2ModbusTcpEntry
        MAX-ACCESS          not-accessible
        STATUS              deprecated
        DESCRIPTION         "A list of modbus entries."
        ::=                 { blueNet2Modbus    6 }

    blueNet2ModbusTcpEntry  OBJECT-TYPE
        SYNTAX              BlueNet2ModbusTcpEntry
        MAX-ACCESS          not-accessible
        STATUS              deprecated
        DESCRIPTION         "Entries of modbus table."
        INDEX               { blueNet2ModbusTcpIndex }
        ::=                 { blueNet2ModbusTcpTable 1 }

    BlueNet2ModbusTcpEntry  ::=
        SEQUENCE            {
                                blueNet2ModbusTcpIndex      Unsigned32,
                                blueNet2ModbusTcpRowStatus  RowStatus,
                                blueNet2ModbusTcpAccess     INTEGER,
                                blueNet2ModbusTcpMaster     DisplayString,
                                blueNet2ModbusTcpFriendlyName DisplayString,
                                blueNet2ModbusTcpDescription DisplayString
                            }

    blueNet2ModbusTcpIndex  OBJECT-TYPE
        SYNTAX              Unsigned32          (1..256)
        MAX-ACCESS          not-accessible
        STATUS              deprecated
        DESCRIPTION         "Index of the modbus TCP access table."
        ::=                 { blueNet2ModbusTcpEntry 1 }

    blueNet2ModbusTcpRowStatus OBJECT-TYPE
        SYNTAX              RowStatus
        MAX-ACCESS          read-create
        STATUS              deprecated
        DESCRIPTION         "Activate/create/destroy/disable a modbus TCP entry."
        ::=                 { blueNet2ModbusTcpEntry 2 }

    blueNet2ModbusTcpAccess OBJECT-TYPE
        SYNTAX              INTEGER {
                                noaccess        (1),
                                readonly        (2),
                                writeonly       (3),
                                readwrite       (4)
                            }
        MAX-ACCESS          read-write
        STATUS              deprecated
        DESCRIPTION         "Modbus access for this master entry.
                            This access is inferior to blueNet2ModbusService, e.g.
                            readwrite access also requires readwrite status."
--  DEFVAL              { noaccess }
        ::=                 { blueNet2ModbusTcpEntry 3 }

    blueNet2ModbusTcpMaster OBJECT-TYPE
        SYNTAX              DisplayString       (SIZE (0..64))
        MAX-ACCESS          read-write
        STATUS              deprecated
        DESCRIPTION         "Source to restrict modbus access.

                            It can either be a specific hostname,
                            IP address, or a subnet represented as
                            IP/MASK (e.g. 10.10.10.0/255.255.255.0),
                            or IP/BITS (e.g. 10.10.10.0/24),
                            or the IPv6 equivalents.

                            The same master can be specified in several separate
                            entries presumably with different access tokens.
                            The first combination matching an incoming request
                            will be selected."
        ::=                 { blueNet2ModbusTcpEntry 4 }

    blueNet2ModbusTcpFriendlyName OBJECT-TYPE
        SYNTAX              DisplayString       (SIZE (0..128))
        MAX-ACCESS          read-write
        STATUS              deprecated
        DESCRIPTION         "User friendly name to identify a modbus master.
                            This is a mnemonic only and will not be used to query data."
        ::=                 { blueNet2ModbusTcpEntry 5 }

    blueNet2ModbusTcpDescription OBJECT-TYPE
        SYNTAX              DisplayString       (SIZE (0..255))
        MAX-ACCESS          read-write
        STATUS              deprecated
        DESCRIPTION         "Description to identify a modbus master.
                            This is a mnemonic only and will not be used to query data."
        ::=                 { blueNet2ModbusTcpEntry 6 }


-- -----------------------------------------------------------------------------

    blueNet2Ntp             OBJECT IDENTIFIER ::= { blueNet2Protocols             14 }

    blueNet2NtpService      OBJECT-TYPE
        SYNTAX              INTEGER {
                                disabled        (1),
                                enabled         (2)
                            }
        MAX-ACCESS          read-write
        STATUS              current
        DESCRIPTION         "NTP service status."
        DEFVAL              { disabled }
        ::=                 { blueNet2Ntp       1 }

    blueNet2NtpPort         OBJECT-TYPE
        SYNTAX              Unsigned32          (1..65535)
        MAX-ACCESS          read-write
        STATUS              current
        DESCRIPTION         "TCP/IP port of NTP server."
        DEFVAL              { 123 }
        ::=                 { blueNet2Ntp       2 }

    blueNet2NtpTimeZone     OBJECT-TYPE
        SYNTAX              Integer32           (1..107)
        MAX-ACCESS          read-write
        STATUS              current
        DESCRIPTION         "Time Zone, list is sorted once by time offset and once by index

                            24  : (GMT-12:00) International Date Line West
                            99  : (GMT-11:00) Coordinated Universal Time-11
                            39  : (GMT-10:00) Hawaii
                            2   : (GMT-09:00) Alaska
                            58  : (GMT-08:00) Pacific Time (US & Canada)
                            59  : (GMT-08:00) Tijuana, Baja California
                            75  : (GMT-07:00) Arizona
                            47  : (GMT-07:00) Mountain Time (US & Canada)
                            48  : (GMT-07:00) Chihuahua, La Paz, Mazatlan
                            15  : (GMT-06:00) Central America
                            21  : (GMT-06:00) Central Time (US & Canada)
                            22  : (GMT-06:00) Guadalajara, Mexico City, Monterrey
                            11  : (GMT-06:00) Saskatchewan
                            106 : (GMT-05:30) Pacific Marquesas
                            63  : (GMT-05:00) Bogota, Lima, Quito, Rio Branco
                            29  : (GMT-05:00) Eastern Time (US & Canada)
                            74  : (GMT-05:00) Indiana (East)
                            85  : (GMT-04:00) Caracas
                            95  : (GMT-04:00) Asuncion
                            6   : (GMT-04:00) Atlantic Time (Canada)
                            64  : (GMT-04:00) La Paz
                            17  : (GMT-04:00) Manaus
                            57  : (GMT-04:00) Santiago
                            54  : (GMT-03:30) Newfoundland
                            28  : (GMT-03:00) Brasilia
                            86  : (GMT-03:00) Buenos Aires
                            62  : (GMT-03:00) Buenos Aires, Georgetown
                            36  : (GMT-03:00) Greenland
                            83  : (GMT-03:00) Montevideo
                            87  : (GMT-03:00) Salvador
                            45  : (GMT-02:00) Mid-Atlantic
                            10  : (GMT-01:00) Azores
                            12  : (GMT-01:00) Cape Verde Is.
                            93  : (GMT) Casablanca
                            89  : (GMT) Coordinated Universal Time
                            37  : (GMT) Casablanca, Monrovia, Reykjavik
                            35  : (GMT) Greenwich Mean Time : Dublin, Edinburgh, Lisbon, London
                            79  : (GMT+01:00) Amsterdam, Berlin, Bern, Rome, Stockholm, Vienna
                            18  : (GMT+01:00) Belgrade, Bratislava, Budapest, Ljubljana, Prague
                            60  : (GMT+01:00) Brussels, Copenhagen, Madrid, Paris
                            19  : (GMT+01:00) Sarajevo, Skopje, Warsaw, Zagreb
                            101 : (GMT+01:00) Tripoli
                            78  : (GMT+01:00) West Central Africa
                            43  : (GMT+02:00) Amman
                            38  : (GMT+02:00) Athens, Bucharest, Istanbul
                            46  : (GMT+02:00) Beirut
                            27  : (GMT+02:00) Minsk
                            30  : (GMT+02:00) Cairo
                            96  : (GMT+02:00) Damascus
                            68  : (GMT+02:00) Harare, Pretoria
                            33  : (GMT+02:00) Helsinki, Kyiv, Riga, Sofia, Tallinn, Vilnius
                            98  : (GMT+02:00) Istanbul
                            42  : (GMT+02:00) Jerusalem
                            51  : (GMT+02:00) Windhoek
                            5   : (GMT+03:00) Baghdad
                            90  : (GMT+03:00) Kaliningrad, Minsk
                            3   : (GMT+03:00) Kuwait, Riyadh
                            61  : (GMT+04:00) Moscow, St. Petersburg, Volgograd
                            92  : (GMT+04:00) Port Louis
                            25  : (GMT+03:00) Nairobi
                            34  : (GMT+03:00) Tbilisi
                            41  : (GMT+03:30) Tehran
                            4   : (GMT+04:00) Abu Dhabi, Muscat
                            9   : (GMT+04:00) Baku
                            84  : (GMT+04:00) Yerevan
                            13  : (GMT+04:00) Yerevan (Do not use)
                            1   : (GMT+04:30) Kabul
                            31  : (GMT+05:00) Ekaterinburg
                            94  : (GMT+05:00) Islamabad, Karachi
                            80  : (GMT+05:00) Tashkent
                            40  : (GMT+05:30) Chennai, Kolkata, Mumbai, New Delhi
                            69  : (GMT+05:30) Sri Jayawardenepura
                            52  : (GMT+05:45) Kathmandu
                            50  : (GMT+06:00) Almaty, Novosibirsk
                            16  : (GMT+06:00) Astana, Dhaka
                            88  : (GMT+06:00) Dhaka
                            49  : (GMT+06:30) Yangon (Rangoon)
                            66  : (GMT+07:00) Bangkok, Hanoi, Jakarta
                            56  : (GMT+07:00) Krasnoyarsk
                            23  : (GMT+08:00) Beijing, Chongqing, Hong Kong, Urumqi
                            55  : (GMT+08:00) Irkutsk, Ulaan Bataar
                            97  : (GMT+08:00) Ulaanbaatar
                            67  : (GMT+08:00) Kuala Lumpur, Singapore
                            77  : (GMT+08:00) Perth
                            70  : (GMT+08:00) Taipei
                            102 : (GMT+08:45) Australia, Eucla
                            72  : (GMT+09:00) Osaka, Sapporo, Tokyo
                            44  : (GMT+09:00) Seoul
                            82  : (GMT+09:00) Yakutsk
                            14  : (GMT+09:30) Adelaide
                            7   : (GMT+09:30) Darwin
                            26  : (GMT+10:00) Brisbane
                            8   : (GMT+10:00) Canberra, Melbourne, Sydney
                            81  : (GMT+10:00) Guam, Port Moresby
                            71  : (GMT+10:00) Hobart
                            76  : (GMT+10:00) Vladivostok
                            103 : (GMT+10:30) Australia, Lord Howe
                            104 : (GMT+11:30) Pacific, Norfolk
                            91  : (GMT+12:00) Magadan
                            20  : (GMT+11:00) Magadan, Solomon Is., New Caledonia
                            53  : (GMT+12:00) Auckland, Wellington
                            100 : (GMT+12:00) Coordinated Universal Time+12
                            32  : (GMT+12:00) Fiji, Kamchatka, Marshall Is.
                            105 : (GMT+12:45) Pacific, Chatham
                            65  : (GMT+13:00) Samoa
                            73  : (GMT+13:00) Nuku'alofa
                            107 : (GMT+14:00) Line Island


                            1   : (GMT+04:30) Kabul
                            2   : (GMT-09:00) Alaska
                            3   : (GMT+03:00) Kuwait, Riyadh
                            4   : (GMT+04:00) Abu Dhabi, Muscat
                            5   : (GMT+03:00) Baghdad
                            6   : (GMT-04:00) Atlantic Time (Canada)
                            7   : (GMT+09:30) Darwin
                            8   : (GMT+10:00) Canberra, Melbourne, Sydney
                            9   : (GMT+04:00) Baku
                            10  : (GMT-01:00) Azores
                            11  : (GMT-06:00) Saskatchewan
                            12  : (GMT-01:00) Cape Verde Is.
                            13  : (GMT+04:00) Yerevan (Do not use)
                            14  : (GMT+09:30) Adelaide
                            15  : (GMT-06:00) Central America
                            16  : (GMT+06:00) Astana, Dhaka
                            17  : (GMT-04:00) Manaus
                            18  : (GMT+01:00) Belgrade, Bratislava, Budapest, Ljubljana, Prague
                            19  : (GMT+01:00) Sarajevo, Skopje, Warsaw, Zagreb
                            20  : (GMT+11:00) Magadan, Solomon Is., New Caledonia
                            21  : (GMT-06:00) Central Time (US & Canada)
                            22  : (GMT-06:00) Guadalajara, Mexico City, Monterrey
                            23  : (GMT+08:00) Beijing, Chongqing, Hong Kong, Urumqi
                            24  : (GMT-12:00) International Date Line West
                            25  : (GMT+03:00) Nairobi
                            26  : (GMT+10:00) Brisbane
                            27  : (GMT+02:00) Minsk
                            28  : (GMT-03:00) Brasilia
                            29  : (GMT-05:00) Eastern Time (US & Canada)
                            30  : (GMT+02:00) Cairo
                            31  : (GMT+05:00) Ekaterinburg
                            32  : (GMT+12:00) Fiji, Kamchatka, Marshall Is.
                            33  : (GMT+02:00) Helsinki, Kyiv, Riga, Sofia, Tallinn, Vilnius
                            34  : (GMT+03:00) Tbilisi
                            35  : (GMT) Greenwich Mean Time : Dublin, Edinburgh, Lisbon, London
                            36  : (GMT-03:00) Greenland
                            37  : (GMT) Casablanca, Monrovia, Reykjavik
                            38  : (GMT+02:00) Athens, Bucharest, Istanbul
                            39  : (GMT-10:00) Hawaii
                            40  : (GMT+05:30) Chennai, Kolkata, Mumbai, New Delhi
                            41  : (GMT+03:30) Tehran
                            42  : (GMT+02:00) Jerusalem
                            43  : (GMT+02:00) Amman
                            44  : (GMT+09:00) Seoul
                            45  : (GMT-02:00) Mid-Atlantic
                            46  : (GMT+02:00) Beirut
                            47  : (GMT-07:00) Mountain Time (US & Canada)
                            48  : (GMT-07:00) Chihuahua, La Paz, Mazatlan
                            49  : (GMT+06:30) Yangon (Rangoon)
                            50  : (GMT+06:00) Almaty, Novosibirsk
                            51  : (GMT+02:00) Windhoek
                            52  : (GMT+05:45) Kathmandu
                            53  : (GMT+12:00) Auckland, Wellington
                            54  : (GMT-03:30) Newfoundland
                            55  : (GMT+08:00) Irkutsk, Ulaan Bataar
                            56  : (GMT+07:00) Krasnoyarsk
                            57  : (GMT-04:00) Santiago
                            58  : (GMT-08:00) Pacific Time (US & Canada)
                            59  : (GMT-08:00) Tijuana, Baja California
                            60  : (GMT+01:00) Brussels, Copenhagen, Madrid, Paris
                            61  : (GMT+04:00) Moscow, St. Petersburg, Volgograd
                            62  : (GMT-03:00) Buenos Aires, Georgetown
                            63  : (GMT-05:00) Bogota, Lima, Quito, Rio Branco
                            64  : (GMT-04:00) La Paz
                            65  : (GMT+13:00) Samoa
                            66  : (GMT+07:00) Bangkok, Hanoi, Jakarta
                            67  : (GMT+08:00) Kuala Lumpur, Singapore
                            68  : (GMT+02:00) Harare, Pretoria
                            69  : (GMT+05:30) Sri Jayawardenepura
                            70  : (GMT+08:00) Taipei
                            71  : (GMT+10:00) Hobart
                            72  : (GMT+09:00) Osaka, Sapporo, Tokyo
                            73  : (GMT+13:00) Nuku'alofa
                            74  : (GMT-05:00) Indiana (East)
                            75  : (GMT-07:00) Arizona
                            76  : (GMT+10:00) Vladivostok
                            77  : (GMT+08:00) Perth
                            78  : (GMT+01:00) West Central Africa
                            79  : (GMT+01:00) Amsterdam, Berlin, Bern, Rome, Stockholm, Vienna
                            80  : (GMT+05:00) Tashkent
                            81  : (GMT+10:00) Guam, Port Moresby
                            82  : (GMT+09:00) Yakutsk
                            83  : (GMT-03:00) Montevideo
                            84  : (GMT+04:00) Yerevan
                            85  : (GMT-04:00) Caracas
                            86  : (GMT-03:00) Buenos Aires
                            87  : (GMT-03:00) Salvador
                            88  : (GMT+06:00) Dhaka
                            89  : (GMT) Coordinated Universal Time
                            90  : (GMT+03:00) Kaliningrad, Minsk
                            91  : (GMT+12:00) Magadan
                            92  : (GMT+04:00) Port Louis
                            93  : (GMT) Casablanca
                            94  : (GMT+05:00) Islamabad, Karachi
                            95  : (GMT-04:00) Asuncion
                            96  : (GMT+02:00) Damascus
                            97  : (GMT+08:00) Ulaanbaatar
                            98  : (GMT+02:00) Istanbul
                            99  : (GMT-11:00) Coordinated Universal Time-11
                            100 : (GMT+12:00) Coordinated Universal Time+12
                            101 : (GMT+01:00) Tripoli
                            102 : (GMT+08:45) Australia, Eucla
                            103 : (GMT+10:30) Australia, Lord Howe
                            104 : (GMT+11:30) Pacific, Norfolk
                            105 : (GMT+12:45) Pacific, Chatham
                            106 : (GMT-09:30) Pacific Marquesas
                            107 : (GMT+14:00) Line Island

                            The operating system may reject any unknown/unsupported timezone.
                            The timezone may also change to another timezone with the same offset."
        DEFVAL              { 79 }
        ::=                 { blueNet2Ntp       3 }

    blueNet2MaxNtpServers   OBJECT-TYPE
        SYNTAX              Unsigned32          (1..3)
        MAX-ACCESS          read-only
        STATUS              current
        DESCRIPTION         "The maximum number of entries in blueNet2NtpServerTable."
        ::=                 { blueNet2Ntp       4 }

    blueNet2NtpServerTable  OBJECT-TYPE
        SYNTAX              SEQUENCE OF BlueNet2NtpServerEntry
        MAX-ACCESS          not-accessible
        STATUS              current
        DESCRIPTION         "A list of NTP server entries."
        ::=                 { blueNet2Ntp       5 }

    blueNet2NtpServerEntry  OBJECT-TYPE
        SYNTAX              BlueNet2NtpServerEntry
        MAX-ACCESS          not-accessible
        STATUS              current
        DESCRIPTION         "Entries of NTP server table."
        INDEX               { blueNet2NtpServerIndex }
        ::=                 { blueNet2NtpServerTable 1 }

    BlueNet2NtpServerEntry  ::=
        SEQUENCE            {
                                blueNet2NtpServerIndex      Unsigned32,
                                blueNet2NtpServerRowStatus  RowStatus,
                                blueNet2NtpServerAddress    DisplayString,
                                blueNet2NtpServerFriendlyName DisplayString,
                                blueNet2NtpServerDescription DisplayString
                            }

    blueNet2NtpServerIndex  OBJECT-TYPE
        SYNTAX              Unsigned32          (1..3)
        MAX-ACCESS          not-accessible
        STATUS              current
        DESCRIPTION         "Index of the NTP server table."
        ::=                 { blueNet2NtpServerEntry 1 }

    blueNet2NtpServerRowStatus OBJECT-TYPE
        SYNTAX              RowStatus
        MAX-ACCESS          read-create
        STATUS              current
        DESCRIPTION         "Activate/create/destroy/disable a NTP server entry."
        ::=                 { blueNet2NtpServerEntry 2 }

    blueNet2NtpServerAddress OBJECT-TYPE
        SYNTAX              DisplayString       (SIZE (0..64))
        MAX-ACCESS          read-write
        STATUS              current
        DESCRIPTION         "IP address or name of NTP server."
        ::=                 { blueNet2NtpServerEntry 3 }

    blueNet2NtpServerFriendlyName OBJECT-TYPE
        SYNTAX              DisplayString       (SIZE (0..128))
        MAX-ACCESS          read-only
        STATUS              deprecated
        DESCRIPTION         "User friendly name to identify a ntp server.
                            This is a mnemonic only and will not be used to query data."
        ::=                 { blueNet2NtpServerEntry 4 }

    blueNet2NtpServerDescription OBJECT-TYPE
        SYNTAX              DisplayString       (SIZE (0..255))
        MAX-ACCESS          read-only
        STATUS              deprecated
        DESCRIPTION         "Description to identify a ntp server.
                            This is a mnemonic only and will not be used to query data."
        ::=                 { blueNet2NtpServerEntry 5 }


-- -----------------------------------------------------------------------------

    blueNet2Smtp            OBJECT IDENTIFIER ::= { blueNet2Protocols             15 }

    blueNet2SmtpService     OBJECT-TYPE
        SYNTAX              INTEGER {
                                disabled        (1),
                                enabled         (2)
                            }
        MAX-ACCESS          read-write
        STATUS              current
        DESCRIPTION         "SMTP service status."
        DEFVAL              { disabled }
        ::=                 { blueNet2Smtp      1 }

    blueNet2SmtpPort        OBJECT-TYPE
        SYNTAX              Unsigned32          (1..65535)
        MAX-ACCESS          read-write
        STATUS              current
        DESCRIPTION         "TCP/IP port of SMTP server."
        DEFVAL              { 25 }
        ::=                 { blueNet2Smtp      2 }

    blueNet2SmtpServer      OBJECT-TYPE
        SYNTAX              DisplayString       (SIZE (0..64))
        MAX-ACCESS          read-write
        STATUS              current
        DESCRIPTION         "IP address or name of SMTP server."
        ::=                 { blueNet2Smtp      3 }

    blueNet2SmtpAuth        OBJECT-TYPE
        SYNTAX              INTEGER {
                                disabled        (1),
                                enabled         (2)
                            }
        MAX-ACCESS          read-write
        STATUS              current
        DESCRIPTION         "SMTP authentication mode."
        DEFVAL              { disabled }
        ::=                 { blueNet2Smtp      4 }

    blueNet2SmtpUsername    OBJECT-TYPE
        SYNTAX              DisplayString       (SIZE (0..20))
        MAX-ACCESS          read-write
        STATUS              current
        DESCRIPTION         "Username required to authenticate at the SMTP server."
        ::=                 { blueNet2Smtp      5 }

    blueNet2SmtpPassword    OBJECT-TYPE
        SYNTAX              DisplayString       (SIZE (0..20))
        MAX-ACCESS          read-write
        STATUS              current
        DESCRIPTION         "Password required to authenticate at the SMTP server."
        ::=                 { blueNet2Smtp      6 }

    blueNet2SmtpFrom        OBJECT-TYPE
        SYNTAX              DisplayString       (SIZE (0..64))
        MAX-ACCESS          read-write
        STATUS              current
        DESCRIPTION         "Sender address of the SMTP message."
        ::=                 { blueNet2Smtp      7 }

    blueNet2SmtpReply       OBJECT-TYPE
        SYNTAX              DisplayString       (SIZE (0..64))
        MAX-ACCESS          read-write
        STATUS              current
        DESCRIPTION         "Reply address of the SMTP message."
        ::=                 { blueNet2Smtp      8 }

    blueNet2MaxSmtpReceivers OBJECT-TYPE
        SYNTAX              Unsigned32          (1..256)
        MAX-ACCESS          read-only
        STATUS              current
        DESCRIPTION         "The maximum number of entries in blueNet2SmtpReceiverTable."
        ::=                 { blueNet2Smtp      9 }

    blueNet2SmtpReceiverTable OBJECT-TYPE
        SYNTAX              SEQUENCE OF BlueNet2SmtpReceiverEntry
        MAX-ACCESS          not-accessible
        STATUS              deprecated
        DESCRIPTION         "A list of SMTP receiver entries."
        ::=                 { blueNet2Smtp      10 }

    blueNet2SmtpReceiverEntry OBJECT-TYPE
        SYNTAX              BlueNet2SmtpReceiverEntry
        MAX-ACCESS          not-accessible
        STATUS              deprecated
        DESCRIPTION         "Entries of SMTP receiver table."
        INDEX               { blueNet2SmtpReceiverIndex }
        ::=                 { blueNet2SmtpReceiverTable 1 }

    BlueNet2SmtpReceiverEntry ::=
        SEQUENCE            {
                                blueNet2SmtpReceiverIndex   Unsigned32,
                                blueNet2SmtpReceiverRowStatus RowStatus,
                                blueNet2SmtpReceiverAddress DisplayString,
                                blueNet2SmtpReceiverFriendlyName DisplayString,
                                blueNet2SmtpReceiverDescription DisplayString
                            }

    blueNet2SmtpReceiverIndex OBJECT-TYPE
        SYNTAX              Unsigned32          (1..256)
        MAX-ACCESS          not-accessible
        STATUS              deprecated
        DESCRIPTION         "Index of the SMTP receiver table."
        ::=                 { blueNet2SmtpReceiverEntry 1 }

    blueNet2SmtpReceiverRowStatus OBJECT-TYPE
        SYNTAX              RowStatus
        MAX-ACCESS          read-create
        STATUS              deprecated
        DESCRIPTION         "Activate/create/destroy/disable a SMTP receiver entry."
        ::=                 { blueNet2SmtpReceiverEntry 2 }

    blueNet2SmtpReceiverAddress OBJECT-TYPE
        SYNTAX              DisplayString       (SIZE (0..64))
        MAX-ACCESS          read-write
        STATUS              deprecated
        DESCRIPTION         "IP address or name of SMTP receiver."
        ::=                 { blueNet2SmtpReceiverEntry 3 }

    blueNet2SmtpReceiverFriendlyName OBJECT-TYPE
        SYNTAX              DisplayString       (SIZE (0..128))
        MAX-ACCESS          read-write
        STATUS              deprecated
        DESCRIPTION         "User friendly name to identify a smtp server.
                            This is a mnemonic only and will not be used to send data."
        ::=                 { blueNet2SmtpReceiverEntry 4 }

    blueNet2SmtpReceiverDescription OBJECT-TYPE
        SYNTAX              DisplayString       (SIZE (0..255))
        MAX-ACCESS          read-write
        STATUS              deprecated
        DESCRIPTION         "Description to identify a smtp server.
                            This is a mnemonic only and will not be used to send data."
        ::=                 { blueNet2SmtpReceiverEntry 5 }


-- -----------------------------------------------------------------------------

    blueNet2Syslog          OBJECT IDENTIFIER ::= { blueNet2Protocols             16 }

    blueNet2SyslogService   OBJECT-TYPE
        SYNTAX              INTEGER {
                                disabled        (1),
                                enabled         (2)
                            }
        MAX-ACCESS          read-write
        STATUS              current
        DESCRIPTION         "Syslog service status."
        DEFVAL              { disabled }
        ::=                 { blueNet2Syslog    1 }

    blueNet2SyslogFacility  OBJECT-TYPE
        SYNTAX              INTEGER {
                                local0          (1),
                                local1          (2),
                                local2          (3),
                                local3          (4),
                                local4          (5),
                                local5          (6),
                                local6          (7),
                                local7          (8)
                            }
        MAX-ACCESS          read-write
        STATUS              current
        DESCRIPTION         "Syslog facility local0 .. local7."
        DEFVAL              { local0 }
        ::=                 { blueNet2Syslog    2 }

    blueNet2MaxSyslogServers OBJECT-TYPE
        SYNTAX              Unsigned32          (1..3)
        MAX-ACCESS          read-only
        STATUS              current
        DESCRIPTION         "The maximum number of entries in blueNet2SyslogServerTable."
        ::=                 { blueNet2Syslog    3 }

    blueNet2SyslogServerTable OBJECT-TYPE
        SYNTAX              SEQUENCE OF BlueNet2SyslogServerEntry
        MAX-ACCESS          not-accessible
        STATUS              current
        DESCRIPTION         "A list of syslog server entries."
        ::=                 { blueNet2Syslog    4 }

    blueNet2SyslogServerEntry OBJECT-TYPE
        SYNTAX              BlueNet2SyslogServerEntry
        MAX-ACCESS          not-accessible
        STATUS              current
        DESCRIPTION         "Entries of syslog server table."
        INDEX               { blueNet2SyslogServerIndex }
        ::=                 { blueNet2SyslogServerTable 1 }

    BlueNet2SyslogServerEntry ::=
        SEQUENCE            {
                                blueNet2SyslogServerIndex   Unsigned32,
                                blueNet2SyslogServerRowStatus RowStatus,
                                blueNet2SyslogServerAddress DisplayString,
                                blueNet2SyslogServerPort    Unsigned32,
                                blueNet2SyslogServerFriendlyName DisplayString,
                                blueNet2SyslogServerDescription DisplayString,
                                blueNet2SyslogServerProtocol INTEGER
                            }

    blueNet2SyslogServerIndex OBJECT-TYPE
        SYNTAX              Unsigned32          (1..3)
        MAX-ACCESS          not-accessible
        STATUS              current
        DESCRIPTION         "Index of the syslog server table."
        ::=                 { blueNet2SyslogServerEntry 1 }

    blueNet2SyslogServerRowStatus OBJECT-TYPE
        SYNTAX              RowStatus
        MAX-ACCESS          read-create
        STATUS              current
        DESCRIPTION         "Activate/create/destroy/disable a syslog server entry."
        ::=                 { blueNet2SyslogServerEntry 2 }

    blueNet2SyslogServerAddress OBJECT-TYPE
        SYNTAX              DisplayString       (SIZE (0..64))
        MAX-ACCESS          read-write
        STATUS              current
        DESCRIPTION         "IP address or name of syslog server."
        ::=                 { blueNet2SyslogServerEntry 3 }

    blueNet2SyslogServerPort OBJECT-TYPE
        SYNTAX              Unsigned32          (1..65535)
        MAX-ACCESS          read-write
        STATUS              current
        DESCRIPTION         "TCP/IP port of syslog server."
        DEFVAL              { 514 }
        ::=                 { blueNet2SyslogServerEntry 4 }

    blueNet2SyslogServerFriendlyName OBJECT-TYPE
        SYNTAX              DisplayString       (SIZE (0..128))
        MAX-ACCESS          read-only
        STATUS              deprecated
        DESCRIPTION         "User friendly name to identify a syslog server.
                            This is a mnemonic only and will not be used to send data."
        ::=                 { blueNet2SyslogServerEntry 5 }

    blueNet2SyslogServerDescription OBJECT-TYPE
        SYNTAX              DisplayString       (SIZE (0..255))
        MAX-ACCESS          read-only
        STATUS              deprecated
        DESCRIPTION         "Description to identify a syslog server.
                            This is a mnemonic only and will not be used to send data."
        ::=                 { blueNet2SyslogServerEntry 6 }

    blueNet2SyslogServerProtocol OBJECT-TYPE
        SYNTAX              INTEGER {
                                udp             (1),
                                tcp             (2),
                                relp            (3)
                            }
        MAX-ACCESS          read-write
        STATUS              current
        DESCRIPTION         "Set TCP/IP protocol of syslog server."
        DEFVAL              { udp }
        ::=                 { blueNet2SyslogServerEntry 7 }


-- =============================================================================
--  blueNet2Devices: global BlueNet2 PDU devices --

    blueNet2DeviceInfo      OBJECT IDENTIFIER ::= { blueNet2Devices                1 }

    blueNet2OverallDeviceStatus OBJECT-TYPE
        SYNTAX              BlueNet2ComponentStates
        MAX-ACCESS          read-only
        STATUS              current
        DESCRIPTION         "Overall status of all devices."
        ::=                 { blueNet2DeviceInfo 1 }

    blueNet2NumberOfDevices OBJECT-TYPE
        SYNTAX              Unsigned32
        MAX-ACCESS          read-only
        STATUS              current
        DESCRIPTION         "Number of devices available."
        ::=                 { blueNet2DeviceInfo 2 }

    blueNet2LastChangeOverallDeviceStatus OBJECT-TYPE
        SYNTAX              TimeTicks
        MAX-ACCESS          read-only
        STATUS              current
        DESCRIPTION         "Timestamp of last status change of any device connected to BlueNet2 PDU
                            according to operating time sysUpTime."
        ::=                 { blueNet2DeviceInfo 3 }

    blueNet2LastChangeNumberOfDevices OBJECT-TYPE
        SYNTAX              TimeTicks
        MAX-ACCESS          read-only
        STATUS              current
        DESCRIPTION         "Timestamp of last device number change
                            according to operating time sysUpTime."
        ::=                 { blueNet2DeviceInfo 4 }

    blueNet2LastChangeDeviceSettings OBJECT-TYPE
        SYNTAX              TimeTicks
        MAX-ACCESS          read-only
        STATUS              current
        DESCRIPTION         "Timestamp of last setting change of any device connected to BlueNet2 PDU
                            according to operating time sysUpTime.
                            This timestamp will be affected by SNMP settings only!"
        ::=                 { blueNet2DeviceInfo 5 }

    blueNet2LastChangeDevices OBJECT-TYPE
        SYNTAX              TimeTicks
        MAX-ACCESS          read-only
        STATUS              current
        DESCRIPTION         "Timestamp of last device change
                            according to operating time sysUpTime."
        ::=                 { blueNet2DeviceInfo 6 }

    blueNet2DevicesAccumulatedStatus OBJECT-TYPE
        SYNTAX              BlueNet2EntityBits
        MAX-ACCESS          read-only
        STATUS              current
        DESCRIPTION         "A bit field of all current device states."
        ::=                 { blueNet2DeviceInfo 7 }


-- -----------------------------------------------------------------------------

    blueNet2DeviceTable     OBJECT-TYPE
        SYNTAX              SEQUENCE OF BlueNet2DeviceEntry
        MAX-ACCESS          not-accessible
        STATUS              current
        DESCRIPTION         "Headline of device table."
        ::=                 { blueNet2Devices   2 }

    blueNet2DeviceEntry     OBJECT-TYPE
        SYNTAX              BlueNet2DeviceEntry
        MAX-ACCESS          not-accessible
        STATUS              current
        DESCRIPTION         "Entries of device table."
        INDEX               { blueNet2DeviceIndex }
        ::=                 { blueNet2DeviceTable 1 }


    BlueNet2DeviceEntry     ::=
        SEQUENCE            {
                                blueNet2DeviceIndex         Unsigned32,
                                blueNet2DeviceGuid          OCTET STRING,
                                blueNet2DeviceName          DisplayString,
                                blueNet2DeviceFriendlyName  DisplayString,
                                blueNet2DeviceDescription   DisplayString,
                                blueNet2DeviceType          OBJECT IDENTIFIER,
                                blueNet2DeviceStatus        BlueNet2EntityStates,
                                blueNet2DeviceAlarm         DisplayString,
                                blueNet2DeviceLastChange    TimeTicks,
                                blueNet2DeviceEntPhysicalIndex Unsigned32,
                                blueNet2DevicePartNr        DisplayString,
                                blueNet2DeviceSNr           DisplayString,
                                blueNet2DeviceFwV           DisplayString,
                                blueNet2DeviceHwV           DisplayString,
                                blueNet2DeviceSwV           DisplayString,
                                blueNet2DeviceOsV           DisplayString,
                                blueNet2DeviceMAC           DisplayString,
                                blueNet2DeviceNumberOfSensors Unsigned32,
                                blueNet2DeviceNumberOfCircuits Unsigned32,
                                blueNet2DeviceNumberOfPhases Unsigned32,
                                blueNet2DeviceNumberOfFuses Unsigned32,
                                blueNet2DeviceNumberOfSockets Unsigned32,
                                blueNet2DeviceNumberOfRCMs  Unsigned32,
                                blueNet2DeviceNumberOfVars  Unsigned32,
                                blueNet2DeviceLocation      DisplayString,
                                blueNet2DeviceProductDate   DisplayString,
                                blueNet2DeviceModbusAddr    Integer32,
                                blueNet2DeviceNumberOfSPDs  Unsigned32
                            }

    blueNet2DeviceIndex     OBJECT-TYPE
        SYNTAX              Unsigned32          (1..11)
        MAX-ACCESS          not-accessible
        STATUS              current
        DESCRIPTION         "Index of device connected to BlueNet2 PDU."
        ::=                 { blueNet2DeviceEntry 1 }

    blueNet2DeviceGuid      OBJECT-TYPE
        SYNTAX              OCTET STRING        (SIZE (8..8))
        MAX-ACCESS          read-only
        STATUS              current
        DESCRIPTION         "GUID of device connected to BlueNet2 PDU."
        ::=                 { blueNet2DeviceEntry 2 }

    blueNet2DeviceName      OBJECT-TYPE
        SYNTAX              DisplayString       (SIZE (0..40))
        MAX-ACCESS          read-only
        STATUS              current
        DESCRIPTION         "Name of the device connected to BlueNet2 PDU."
        ::=                 { blueNet2DeviceEntry 3 }

    blueNet2DeviceFriendlyName OBJECT-TYPE
        SYNTAX              DisplayString       (SIZE (0..128))
        MAX-ACCESS          read-write
        STATUS              current
        DESCRIPTION         "User friendlyname of the device connected to BlueNet2 PDU."
        ::=                 { blueNet2DeviceEntry 4 }

    blueNet2DeviceDescription OBJECT-TYPE
        SYNTAX              DisplayString       (SIZE (0..255))
        MAX-ACCESS          read-write
        STATUS              current
        DESCRIPTION         "Description of the device connected to BlueNet2 PDU."
        ::=                 { blueNet2DeviceEntry 5 }

    blueNet2DeviceType      OBJECT-TYPE
        SYNTAX              OBJECT IDENTIFIER
        MAX-ACCESS          read-only
        STATUS              current
        DESCRIPTION         "Type of device connected to BlueNet2 PDU."
        ::=                 { blueNet2DeviceEntry 6 }

    blueNet2DeviceStatus    OBJECT-TYPE
        SYNTAX              BlueNet2EntityStates
        MAX-ACCESS          read-only
        STATUS              current
        DESCRIPTION         "General status of device connected to BlueNet2 PDU."
        ::=                 { blueNet2DeviceEntry 7 }

    blueNet2DeviceAlarm     OBJECT-TYPE
        SYNTAX              DisplayString       (SIZE (0..255))
        MAX-ACCESS          read-only
        STATUS              deprecated
        DESCRIPTION         "Alarm text of device connected to BlueNet2 PDU.
        					This field is deprecated and is not filled."
        ::=                 { blueNet2DeviceEntry 8 }

    blueNet2DeviceLastChange OBJECT-TYPE
        SYNTAX              TimeTicks
        MAX-ACCESS          read-only
        STATUS              current
        DESCRIPTION         "Timestamp of last change of device connected to BlueNet2 PDU
                            according to operating time sysUpTime."
        ::=                 { blueNet2DeviceEntry 9 }

    blueNet2DeviceEntPhysicalIndex OBJECT-TYPE
        SYNTAX              Unsigned32
        MAX-ACCESS          read-only
        STATUS              current
        DESCRIPTION         "Corresponding entPhysicalIndex of this device. 0 if none exists."
        ::=                 { blueNet2DeviceEntry 10 }

    blueNet2DevicePartNr    OBJECT-TYPE
        SYNTAX              DisplayString       (SIZE (0..32))
        MAX-ACCESS          read-only
        STATUS              current
        DESCRIPTION         "Article part number of device connected to BlueNet2 PDU."
        ::=                 { blueNet2DeviceEntry 11 }

    blueNet2DeviceSNr       OBJECT-TYPE
        SYNTAX              DisplayString       (SIZE (0..32))
        MAX-ACCESS          read-only
        STATUS              current
        DESCRIPTION         "Serial number of device connected to BlueNet2 PDU."
        ::=                 { blueNet2DeviceEntry 12 }

    blueNet2DeviceFwV       OBJECT-TYPE
        SYNTAX              DisplayString       (SIZE (0..32))
        MAX-ACCESS          read-only
        STATUS              current
        DESCRIPTION         "Firmware version of device connected to BlueNet2 PDU."
        ::=                 { blueNet2DeviceEntry 13 }

    blueNet2DeviceHwV       OBJECT-TYPE
        SYNTAX              DisplayString       (SIZE (0..32))
        MAX-ACCESS          read-only
        STATUS              current
        DESCRIPTION         "Hardware version of device connected to BlueNet2 PDU."
        ::=                 { blueNet2DeviceEntry 14 }

    blueNet2DeviceSwV       OBJECT-TYPE
        SYNTAX              DisplayString       (SIZE (0..32))
        MAX-ACCESS          read-only
        STATUS              current
        DESCRIPTION         "Software version of device connected to BlueNet2 PDU."
        ::=                 { blueNet2DeviceEntry 15 }

    blueNet2DeviceOsV       OBJECT-TYPE
        SYNTAX              DisplayString       (SIZE (0..255))
        MAX-ACCESS          read-only
        STATUS              current
        DESCRIPTION         "Operating system version of device connected to BlueNet2 PDU."
        ::=                 { blueNet2DeviceEntry 16 }

    blueNet2DeviceMAC       OBJECT-TYPE
        SYNTAX              DisplayString       (SIZE (0..32))
        MAX-ACCESS          read-only
        STATUS              current
        DESCRIPTION         "MAC address of device connected to BlueNet2 PDU."
        ::=                 { blueNet2DeviceEntry 17 }

    blueNet2DeviceNumberOfSensors OBJECT-TYPE
        SYNTAX              Unsigned32
        MAX-ACCESS          read-only
        STATUS              current
        DESCRIPTION         "Number of sensors available on this device.
                            This variable will give the number of rows of the
                            sensor table blueNet2SensorTable belonging to this device."
        ::=                 { blueNet2DeviceEntry 18 }

    blueNet2DeviceNumberOfCircuits OBJECT-TYPE
        SYNTAX              Unsigned32
        MAX-ACCESS          read-only
        STATUS              current
        DESCRIPTION         "Number of circuits available in this device.
                            This variable will give the number of rows of the circuit
                            table blueNet2CircuitTable belonging to this device."
        ::=                 { blueNet2DeviceEntry 19 }

    blueNet2DeviceNumberOfPhases OBJECT-TYPE
        SYNTAX              Unsigned32
        MAX-ACCESS          read-only
        STATUS              current
        DESCRIPTION         "Number of phases available in this device.
                            This variable will give the number of rows of the phases
                            table blueNet2PhaseTable belonging to this device."
        ::=                 { blueNet2DeviceEntry 20 }

    blueNet2DeviceNumberOfFuses OBJECT-TYPE
        SYNTAX              Unsigned32
        MAX-ACCESS          read-only
        STATUS              current
        DESCRIPTION         "Number of fuses available in this device.
                            This variable will give the number of rows of the fuse
                            table blueNet2FuseTable belonging to this device."
        ::=                 { blueNet2DeviceEntry 21 }

    blueNet2DeviceNumberOfSockets OBJECT-TYPE
        SYNTAX              Unsigned32
        MAX-ACCESS          read-only
        STATUS              current
        DESCRIPTION         "Number of sockets available in this device.
                            This variable will give the number of rows of the socket
                            table blueNet2SocketTable belonging to this device."
        ::=                 { blueNet2DeviceEntry 22 }

    blueNet2DeviceNumberOfRCMs OBJECT-TYPE
        SYNTAX              Unsigned32
        MAX-ACCESS          read-only
        STATUS              current
        DESCRIPTION         "Number of RCMs available in this device.
                            This variable will give the number of rows of the RCM
                            table blueNet2RcmTable belonging to this device."
        ::=                 { blueNet2DeviceEntry 23 }

    blueNet2DeviceNumberOfVars OBJECT-TYPE
        SYNTAX              Unsigned32
        MAX-ACCESS          read-only
        STATUS              current
        DESCRIPTION         "Number of variables available in this device.
                            This variable will give the number of rows of the variable
                            table blueNet2VariableTable belonging to this device."
        ::=                 { blueNet2DeviceEntry 24 }

    blueNet2DeviceLocation  OBJECT-TYPE
        SYNTAX              DisplayString       (SIZE (0..255))
        MAX-ACCESS          read-write
        STATUS              current
        DESCRIPTION         "Location of device connected to BlueNet2 PDU."
        ::=                 { blueNet2DeviceEntry 25 }

    blueNet2DeviceProductDate  OBJECT-TYPE
        SYNTAX              DisplayString       (SIZE (0..255))
        MAX-ACCESS          read-only
        STATUS              current
        DESCRIPTION         "Device Production Date."
        ::=                 { blueNet2DeviceEntry 26 }

    blueNet2DeviceModbusAddr  OBJECT-TYPE
        SYNTAX              Integer32
        MAX-ACCESS          read-only
        STATUS              current
        DESCRIPTION         "Device Modbus Address."
        ::=                 { blueNet2DeviceEntry 27 }

    blueNet2DeviceNumberOfSPDs OBJECT-TYPE
        SYNTAX              Unsigned32
        MAX-ACCESS          read-only
        STATUS              current
        DESCRIPTION         "Number of SPDs available in this device.
                            This variable will give the number of rows of the SPD
                            table blueNet2SpdTable belonging to this device."
        ::=                 { blueNet2DeviceEntry 28 }

-- =============================================================================
--  blueNet2Sensors: BlueNet2 PDU sensors --

    blueNet2SensorInfo      OBJECT IDENTIFIER ::= { blueNet2Sensors                1 }

    blueNet2OverallSensorStatus OBJECT-TYPE
        SYNTAX              BlueNet2ComponentStates
        MAX-ACCESS          read-only
        STATUS              current
        DESCRIPTION         "Overall status of all sensors."
        ::=                 { blueNet2SensorInfo 1 }

    blueNet2NumberOfSensors OBJECT-TYPE
        SYNTAX              Unsigned32
        MAX-ACCESS          read-only
        STATUS              current
        DESCRIPTION         "Number of sensors available."
        ::=                 { blueNet2SensorInfo 2 }

    blueNet2LastChangeOverallSensorStatus OBJECT-TYPE
        SYNTAX              TimeTicks
        MAX-ACCESS          read-only
        STATUS              current
        DESCRIPTION         "Timestamp of last status change of any sensor connected to BlueNet2 PDU
                            according to operating time sysUpTime."
        ::=                 { blueNet2SensorInfo 3 }

    blueNet2LastChangeNumberOfSensors OBJECT-TYPE
        SYNTAX              TimeTicks
        MAX-ACCESS          read-only
        STATUS              current
        DESCRIPTION         "Timestamp of last sensor number change
                            according to operating time sysUpTime."
        ::=                 { blueNet2SensorInfo 4 }

    blueNet2LastChangeSensorSettings OBJECT-TYPE
        SYNTAX              TimeTicks
        MAX-ACCESS          read-only
        STATUS              current
        DESCRIPTION         "Timestamp of last setting change of any sensor connected to BlueNet2 PDU
                            according to operating time sysUpTime.
                            This timestamp will be affected by SNMP settings only!"
        ::=                 { blueNet2SensorInfo 5 }

    blueNet2LastChangeSensors OBJECT-TYPE
        SYNTAX              TimeTicks
        MAX-ACCESS          read-only
        STATUS              current
        DESCRIPTION         "Timestamp of last sensor change
                            according to operating time sysUpTime."
        ::=                 { blueNet2SensorInfo 6 }

    blueNet2SensorsAccumulatedStatus OBJECT-TYPE
        SYNTAX              BlueNet2EntityBits
        MAX-ACCESS          read-only
        STATUS              current
        DESCRIPTION         "A bit field of all current sensor states."
        ::=                 { blueNet2SensorInfo 7 }

-- -----------------------------------------------------------------------------

    blueNet2SensorTable     OBJECT-TYPE
        SYNTAX              SEQUENCE OF BlueNet2SensorEntry
        MAX-ACCESS          not-accessible
        STATUS              current
        DESCRIPTION         "Headline of sensor table."
        ::=                 { blueNet2Sensors   2 }

    blueNet2SensorEntry     OBJECT-TYPE
        SYNTAX              BlueNet2SensorEntry
        MAX-ACCESS          not-accessible
        STATUS              current
        DESCRIPTION         "Entries of sensor table."
        INDEX               { blueNet2SensorDevice,blueNet2SensorIndex }
        ::=                 { blueNet2SensorTable 1 }


    BlueNet2SensorEntry     ::=
        SEQUENCE            {
                                blueNet2SensorDevice        Unsigned32,
                                blueNet2SensorIndex         Unsigned32,
                                blueNet2SensorGuid          OCTET STRING,
                                blueNet2SensorName          DisplayString,
                                blueNet2SensorFriendlyName  DisplayString,
                                blueNet2SensorDescription   DisplayString,
                                blueNet2SensorType          OBJECT IDENTIFIER,
                                blueNet2SensorStatus        BlueNet2EntityStates,
                                blueNet2SensorAlarm         DisplayString,
                                blueNet2SensorLastChange    TimeTicks,
                                blueNet2SensorEntPhysicalIndex Unsigned32,
                                blueNet2SensorNumberOfVars  Unsigned32,
                                blueNet2SensorHwV           DisplayString,
                                blueNet2SensorFwV           DisplayString,
                                blueNet2SensorSNr           DisplayString
                            }

    blueNet2SensorDevice    OBJECT-TYPE
        SYNTAX              Unsigned32          (1..11)
        MAX-ACCESS          not-accessible
        STATUS              current
        DESCRIPTION         "Index of device connected to BlueNet2 PDU."
        ::=                 { blueNet2SensorEntry 1 }

    blueNet2SensorIndex     OBJECT-TYPE
        SYNTAX              Unsigned32          (1..8)
        MAX-ACCESS          not-accessible
        STATUS              current
        DESCRIPTION         "Index of sensor connected to BlueNet2 PDU."
        ::=                 { blueNet2SensorEntry 2 }

    blueNet2SensorGuid      OBJECT-TYPE
        SYNTAX              OCTET STRING        (SIZE (8..8))
        MAX-ACCESS          read-only
        STATUS              current
        DESCRIPTION         "GUID of sensor connected to BlueNet2 PDU."
        ::=                 { blueNet2SensorEntry 3 }

    blueNet2SensorName      OBJECT-TYPE
        SYNTAX              DisplayString       (SIZE (0..40))
        MAX-ACCESS          read-only
        STATUS              current
        DESCRIPTION         "Name of the sensor connected to BlueNet2 PDU."
        ::=                 { blueNet2SensorEntry 4 }

    blueNet2SensorFriendlyName OBJECT-TYPE
        SYNTAX              DisplayString       (SIZE (0..128))
        MAX-ACCESS          read-write
        STATUS              current
        DESCRIPTION         "User friendlyname of the sensor connected to BlueNet2 PDU."
        ::=                 { blueNet2SensorEntry 5 }

    blueNet2SensorDescription OBJECT-TYPE
        SYNTAX              DisplayString       (SIZE (0..255))
        MAX-ACCESS          read-write
        STATUS              current
        DESCRIPTION         "Description of the sensor connected to BlueNet2 PDU."
        ::=                 { blueNet2SensorEntry 6 }

    blueNet2SensorType      OBJECT-TYPE
        SYNTAX              OBJECT IDENTIFIER
        MAX-ACCESS          read-only
        STATUS              current
        DESCRIPTION         "Type of of sensor connected to BlueNet2 PDU."
        ::=                 { blueNet2SensorEntry 7 }

    blueNet2SensorStatus    OBJECT-TYPE
        SYNTAX              BlueNet2EntityStates
        MAX-ACCESS          read-only
        STATUS              current
        DESCRIPTION         "General Status of sensor connected to BlueNet2 PDU."
        ::=                 { blueNet2SensorEntry 8 }

    blueNet2SensorAlarm     OBJECT-TYPE
        SYNTAX              DisplayString       (SIZE (0..255))
        MAX-ACCESS          read-only
        STATUS              current
        DESCRIPTION         "Alarm text of sensor connected to BlueNet2 PDU."
        ::=                 { blueNet2SensorEntry 9 }

    blueNet2SensorLastChange OBJECT-TYPE
        SYNTAX              TimeTicks
        MAX-ACCESS          read-only
        STATUS              current
        DESCRIPTION         "Timestamp of last change of sensor connected to BlueNet2 PDU
                            according to operating time sysUpTime."
        ::=                 { blueNet2SensorEntry 10 }

    blueNet2SensorEntPhysicalIndex OBJECT-TYPE
        SYNTAX              Unsigned32
        MAX-ACCESS          read-only
        STATUS              current
        DESCRIPTION         "Corresponding entPhysicalIndex of this sensor. 0 if none exists."
        ::=                 { blueNet2SensorEntry 11 }

    blueNet2SensorNumberOfVars OBJECT-TYPE
        SYNTAX              Unsigned32
        MAX-ACCESS          read-only
        STATUS              current
        DESCRIPTION         "Number of variables available on this sensor.
                            This variable will give the number of rows of the
                            variable table blueNet2SensorVarTable belonging to this sensor."
        ::=                 { blueNet2SensorEntry 12 }

    blueNet2SensorHwV       OBJECT-TYPE
        SYNTAX              DisplayString       (SIZE (0..32))
        MAX-ACCESS          read-only
        STATUS              current
        DESCRIPTION         "Hardware version of the sensor."
        ::=                 { blueNet2SensorEntry 13 }

    blueNet2SensorFwV       OBJECT-TYPE
        SYNTAX              DisplayString       (SIZE (0..32))
        MAX-ACCESS          read-only
        STATUS              current
        DESCRIPTION         "Firmware version of the sensor."
        ::=                 { blueNet2SensorEntry 14 }

    blueNet2SensorSNr       OBJECT-TYPE
        SYNTAX              DisplayString       (SIZE (0..64))
        MAX-ACCESS          read-only
        STATUS              current
        DESCRIPTION         "Serial number of the sensor."
        ::=                 { blueNet2SensorEntry 15 }

-- -----------------------------------------------------------------------------

    blueNet2SensorVariableTable OBJECT-TYPE
        SYNTAX              SEQUENCE OF BlueNet2SensorVariableEntry
        MAX-ACCESS          not-accessible
        STATUS              current
        DESCRIPTION         "Headline of sensor variable table."
        ::=                 { blueNet2Sensors   3 }

    blueNet2SensorVariableEntry OBJECT-TYPE
        SYNTAX              BlueNet2SensorVariableEntry
        MAX-ACCESS          not-accessible
        STATUS              current
        DESCRIPTION         "Entries of sensor variable table."
        INDEX               { blueNet2SensorDeviceIndex,blueNet2SensorSensorIndex,blueNet2SensorVariableIndex }
        ::=                 { blueNet2SensorVariableTable 1 }


    BlueNet2SensorVariableEntry ::=
        SEQUENCE            {
                                blueNet2SensorDeviceIndex   Unsigned32,
                                blueNet2SensorSensorIndex   Unsigned32,
                                blueNet2SensorVariableIndex Unsigned32,
                                blueNet2SensorVariableGuid  OCTET STRING,
                                blueNet2SensorVariableName  DisplayString,
                                blueNet2SensorVariableFriendlyName DisplayString,
                                blueNet2SensorVariableDescription DisplayString,
                                blueNet2SensorVariableGPIOMode    BlueNet2GPIOModes,
                                blueNet2SensorVariableGPIOSwitch  BlueNet2GPIOSwitch,
                                blueNet2SensorVariableGPIOState   BlueNet2EntityStates
                            }

    blueNet2SensorDeviceIndex OBJECT-TYPE
        SYNTAX              Unsigned32          (1..11)
        MAX-ACCESS          not-accessible
        STATUS              current
        DESCRIPTION         "Index of sensor connected."
        ::=                 { blueNet2SensorVariableEntry 1 }

    blueNet2SensorSensorIndex OBJECT-TYPE
        SYNTAX              Unsigned32          (1..8)
        MAX-ACCESS          not-accessible
        STATUS              current
        DESCRIPTION         "Index of sensor connected."
        ::=                 { blueNet2SensorVariableEntry 2 }

    blueNet2SensorVariableIndex OBJECT-TYPE
        SYNTAX              Unsigned32          (1..8)
        MAX-ACCESS          not-accessible
        STATUS              current
        DESCRIPTION         "Index of sensor variable."
        ::=                 { blueNet2SensorVariableEntry 3 }

    blueNet2SensorVariableGuid OBJECT-TYPE
        SYNTAX              OCTET STRING        (SIZE (8..8))
        MAX-ACCESS          read-only
        STATUS              current
        DESCRIPTION         "GUID of sensor connected to BlueNet2 PDU."
        ::=                 { blueNet2SensorVariableEntry 4 }

    blueNet2SensorVariableName OBJECT-TYPE
        SYNTAX              DisplayString       (SIZE (0..40))
        MAX-ACCESS          read-only
        STATUS              current
        DESCRIPTION         "Name of the sensor variable."
        ::=                 { blueNet2SensorVariableEntry 5 }

    blueNet2SensorVariableFriendlyName OBJECT-TYPE
        SYNTAX              DisplayString       (SIZE (0..128))
        MAX-ACCESS          read-only
        STATUS              current
        DESCRIPTION         "User friendlyname of the sensor variable."
        ::=                 { blueNet2SensorVariableEntry 6 }

    blueNet2SensorVariableDescription OBJECT-TYPE
        SYNTAX              DisplayString       (SIZE (0..255))
        MAX-ACCESS          read-only
        STATUS              current
        DESCRIPTION         "Description of the sensor variable."
        ::=                 { blueNet2SensorVariableEntry 7 }

    blueNet2SensorVariableGPIOMode      OBJECT-TYPE
        SYNTAX              BlueNet2GPIOModes
        MAX-ACCESS          read-write
        STATUS              current
        DESCRIPTION         "Mode of the GPIO sensor connected to BlueNet2 PDU."
        ::=                 { blueNet2SensorVariableEntry 8 }

    blueNet2SensorVariableGPIOSwitch      OBJECT-TYPE
        SYNTAX              BlueNet2GPIOSwitch
        MAX-ACCESS          read-write
        STATUS              current
        DESCRIPTION         "Switch on/off the GPIO Outputs."
        ::=                 { blueNet2SensorVariableEntry 9 }

    blueNet2SensorVariableGPIOState   OBJECT-TYPE
        SYNTAX              BlueNet2EntityStates
        MAX-ACCESS          read-only
        STATUS              current
        DESCRIPTION         "State of GPIO inputs/outputs"
        ::=                 { blueNet2SensorVariableEntry 10 }

-- =============================================================================
--  blueNet2Circuits: BlueNet2 PDU Circuits --

    blueNet2CircuitInfo     OBJECT IDENTIFIER ::= { blueNet2Circuits               1 }

    blueNet2OverallCircuitStatus OBJECT-TYPE
        SYNTAX              BlueNet2ComponentStates
        MAX-ACCESS          read-only
        STATUS              current
        DESCRIPTION         "Overall status of all circuits."
        ::=                 { blueNet2CircuitInfo 1 }

    blueNet2NumberOfCircuits OBJECT-TYPE
        SYNTAX              Unsigned32
        MAX-ACCESS          read-only
        STATUS              current
        DESCRIPTION         "Number of circuits available."
        ::=                 { blueNet2CircuitInfo 2 }

    blueNet2LastChangeOverallCircuitStatus OBJECT-TYPE
        SYNTAX              TimeTicks
        MAX-ACCESS          read-only
        STATUS              current
        DESCRIPTION         "Timestamp of last status change of any circuit connected to BlueNet2 PDU
                            according to operating time sysUpTime."
        ::=                 { blueNet2CircuitInfo 3 }

    blueNet2LastChangeNumberOfCircuits OBJECT-TYPE
        SYNTAX              TimeTicks
        MAX-ACCESS          read-only
        STATUS              current
        DESCRIPTION         "Timestamp of last circuit number change
                            according to operating time sysUpTime."
        ::=                 { blueNet2CircuitInfo 4 }

    blueNet2LastChangeCircuitSettings OBJECT-TYPE
        SYNTAX              TimeTicks
        MAX-ACCESS          read-only
        STATUS              current
        DESCRIPTION         "Timestamp of last setting change of any circuit connected to BlueNet2 PDU
                            according to operating time sysUpTime.
                            This timestamp will be affected by SNMP settings only!"
        ::=                 { blueNet2CircuitInfo 5 }

    blueNet2LastChangeCircuits OBJECT-TYPE
        SYNTAX              TimeTicks
        MAX-ACCESS          read-only
        STATUS              current
        DESCRIPTION         "Timestamp of last circuit change
                            according to operating time sysUpTime."
        ::=                 { blueNet2CircuitInfo 6 }

-- -----------------------------------------------------------------------------

    blueNet2CircuitTable    OBJECT-TYPE
        SYNTAX              SEQUENCE OF BlueNet2CircuitEntry
        MAX-ACCESS          not-accessible
        STATUS              current
        DESCRIPTION         "Headline of circuit table."
        ::=                 { blueNet2Circuits  2 }

    blueNet2CircuitEntry    OBJECT-TYPE
        SYNTAX              BlueNet2CircuitEntry
        MAX-ACCESS          not-accessible
        STATUS              current
        DESCRIPTION         "Entries of circuit table."
        INDEX               { blueNet2CircuitDevice,blueNet2CircuitIndex }
        ::=                 { blueNet2CircuitTable 1 }

    BlueNet2CircuitEntry    ::=
        SEQUENCE            {
                                blueNet2CircuitDevice       Unsigned32,
                                blueNet2CircuitIndex        Unsigned32,
                                blueNet2CircuitGuid         OCTET STRING,
                                blueNet2CircuitName         DisplayString,
                                blueNet2CircuitFriendlyName DisplayString,
                                blueNet2CircuitDescription  DisplayString,
                                blueNet2CircuitType         OBJECT IDENTIFIER,
                                blueNet2CircuitStatus       BlueNet2EntityStates,
                                blueNet2CircuitNumberOfPhases Unsigned32
                            }

    blueNet2CircuitDevice   OBJECT-TYPE
        SYNTAX              Unsigned32          (1..11)
        MAX-ACCESS          not-accessible
        STATUS              current
        DESCRIPTION         "Index of device connected to BlueNet2 PDU."
        ::=                 { blueNet2CircuitEntry 1 }

    blueNet2CircuitIndex    OBJECT-TYPE
        SYNTAX              Unsigned32          (1..2)
        MAX-ACCESS          not-accessible
        STATUS              current
        DESCRIPTION         "Index of circuit connected to BlueNet2 PDU."
        ::=                 { blueNet2CircuitEntry 2 }

    blueNet2CircuitGuid     OBJECT-TYPE
        SYNTAX              OCTET STRING        (SIZE (8..8))
        MAX-ACCESS          read-only
        STATUS              current
        DESCRIPTION         "GUID of circuit connected to BlueNet2 PDU."
        ::=                 { blueNet2CircuitEntry 3 }

    blueNet2CircuitName     OBJECT-TYPE
        SYNTAX              DisplayString       (SIZE (0..40))
        MAX-ACCESS          read-only
        STATUS              current
        DESCRIPTION         "Name of the circuit connected to BlueNet2 PDU."
        ::=                 { blueNet2CircuitEntry 4 }

    blueNet2CircuitFriendlyName OBJECT-TYPE
        SYNTAX              DisplayString       (SIZE (0..128))
        MAX-ACCESS          read-write
        STATUS              current
        DESCRIPTION         "User friendlyname of the circuit connected to BlueNet2 PDU."
        ::=                 { blueNet2CircuitEntry 5 }

    blueNet2CircuitDescription OBJECT-TYPE
        SYNTAX              DisplayString       (SIZE (0..255))
        MAX-ACCESS          read-write
        STATUS              current
        DESCRIPTION         "Description of the circuit connected to BlueNet2 PDU."
        ::=                 { blueNet2CircuitEntry 6 }

    blueNet2CircuitType     OBJECT-TYPE
        SYNTAX              OBJECT IDENTIFIER
        MAX-ACCESS          read-only
        STATUS              current
        DESCRIPTION         "Type of circuit connected to BlueNet2 PDU."
        ::=                 { blueNet2CircuitEntry 7 }

    blueNet2CircuitStatus   OBJECT-TYPE
        SYNTAX              BlueNet2EntityStates
        MAX-ACCESS          read-only
        STATUS              current
        DESCRIPTION         "General status of the entity providing the status of a
                            circuit connected to BlueNet2 PDU in blueNet2VariableStatus."
        ::=                 { blueNet2CircuitEntry 8 }

    blueNet2CircuitNumberOfPhases OBJECT-TYPE
        SYNTAX              Unsigned32

        MAX-ACCESS          read-only
        STATUS              current
        DESCRIPTION         "Number of phases of circuit connected to BlueNet2 PDU."
        ::=                 { blueNet2CircuitEntry 9 }

-- -----------------------------------------------------------------------------

    blueNet2PhaseTable      OBJECT-TYPE
        SYNTAX              SEQUENCE OF BlueNet2PhaseEntry
        MAX-ACCESS          not-accessible
        STATUS              current
        DESCRIPTION         "Headline of phase table."
        ::=                 { blueNet2Circuits  3 }

    blueNet2PhaseEntry      OBJECT-TYPE
        SYNTAX              BlueNet2PhaseEntry
        MAX-ACCESS          not-accessible
        STATUS              current
        DESCRIPTION         "Entries of phase table."
        INDEX               { blueNet2PhaseDevice,blueNet2PhaseCircuit,blueNet2PhaseIndex }
        ::=                 { blueNet2PhaseTable 1 }

    BlueNet2PhaseEntry      ::=
        SEQUENCE            {
                                blueNet2PhaseDevice         Unsigned32,
                                blueNet2PhaseCircuit        Unsigned32,
                                blueNet2PhaseIndex          Unsigned32,
                                blueNet2PhaseGuid           OCTET STRING,
                                blueNet2PhaseName           DisplayString,
                                blueNet2PhaseFriendlyName   DisplayString,
                                blueNet2PhaseDescription    DisplayString,
                                blueNet2PhaseStatus         BlueNet2EntityStates,
                                blueNet2PhaseNumberOfFuses  Unsigned32
                            }

    blueNet2PhaseDevice     OBJECT-TYPE
        SYNTAX              Unsigned32          (1..11)
        MAX-ACCESS          not-accessible
        STATUS              current
        DESCRIPTION         "Index of device connected to BlueNet2 PDU."
        ::=                 { blueNet2PhaseEntry 1 }

    blueNet2PhaseCircuit    OBJECT-TYPE
        SYNTAX              Unsigned32          (1..2)
        MAX-ACCESS          not-accessible
        STATUS              current
        DESCRIPTION         "Index of circuit connected to BlueNet2 PDU."
        ::=                 { blueNet2PhaseEntry 2 }

    blueNet2PhaseIndex      OBJECT-TYPE
        SYNTAX              Unsigned32          (1..3)
        MAX-ACCESS          not-accessible
        STATUS              current
        DESCRIPTION         "Index of phase connected to BlueNet2 PDU."
        ::=                 { blueNet2PhaseEntry 3 }

    blueNet2PhaseGuid       OBJECT-TYPE
        SYNTAX              OCTET STRING        (SIZE (8..8))
        MAX-ACCESS          read-only
        STATUS              current
        DESCRIPTION         "GUID of phase connected to BlueNet2 PDU."
        ::=                 { blueNet2PhaseEntry 4 }

    blueNet2PhaseName       OBJECT-TYPE
        SYNTAX              DisplayString       (SIZE (0..40))
        MAX-ACCESS          read-only
        STATUS              current
        DESCRIPTION         "Name of the phase connected to BlueNet2 PDU."
        ::=                 { blueNet2PhaseEntry 5 }

    blueNet2PhaseFriendlyName OBJECT-TYPE
        SYNTAX              DisplayString       (SIZE (0..128))
        MAX-ACCESS          read-write
        STATUS              current
        DESCRIPTION         "User friendlyname of the phase connected to BlueNet2 PDU."
        ::=                 { blueNet2PhaseEntry 6 }

    blueNet2PhaseDescription OBJECT-TYPE
        SYNTAX              DisplayString       (SIZE (0..255))
        MAX-ACCESS          read-write
        STATUS              current
        DESCRIPTION         "Description of the phase connected to BlueNet2 PDU."
        ::=                 { blueNet2PhaseEntry 7 }

    blueNet2PhaseStatus     OBJECT-TYPE
        SYNTAX              BlueNet2EntityStates
        MAX-ACCESS          read-only
        STATUS              current
        DESCRIPTION         "General status of the entity providing the status of a
                            phase connected to BlueNet2 PDU in blueNet2VariableStatus."
        ::=                 { blueNet2PhaseEntry 8 }

    blueNet2PhaseNumberOfFuses OBJECT-TYPE
        SYNTAX              Unsigned32
        MAX-ACCESS          read-only
        STATUS              current
        DESCRIPTION         "Number of fuses of phase connected to BlueNet2 PDU."
        ::=                 { blueNet2PhaseEntry 9 }


-- -----------------------------------------------------------------------------

    blueNet2FuseTable       OBJECT-TYPE
        SYNTAX              SEQUENCE OF BlueNet2FuseEntry
        MAX-ACCESS          not-accessible
        STATUS              current
        DESCRIPTION         "Headline of fuse table."
        ::=                 { blueNet2Circuits  4 }

    blueNet2FuseEntry       OBJECT-TYPE
        SYNTAX              BlueNet2FuseEntry
        MAX-ACCESS          not-accessible
        STATUS              current
        DESCRIPTION         "Entries of fuse table."
        INDEX               { blueNet2FuseDevice,blueNet2FuseCircuit,blueNet2FusePhase,blueNet2FuseIndex }
        ::=                 { blueNet2FuseTable 1 }

    BlueNet2FuseEntry       ::=
        SEQUENCE            {
                                blueNet2FuseDevice          Unsigned32,
                                blueNet2FuseCircuit         Unsigned32,
                                blueNet2FusePhase           Unsigned32,
                                blueNet2FuseIndex           Unsigned32,
                                blueNet2FuseGuid            OCTET STRING,
                                blueNet2FuseName            DisplayString,
                                blueNet2FuseFriendlyName    DisplayString,
                                blueNet2FuseDescription     DisplayString,
                                blueNet2FuseType            OBJECT IDENTIFIER,
                                blueNet2FuseStatus          BlueNet2EntityStates,
                                blueNet2FuseNumberOfSockets Unsigned32
                            }

    blueNet2FuseDevice      OBJECT-TYPE
        SYNTAX              Unsigned32          (1..11)
        MAX-ACCESS          not-accessible
        STATUS              current
        DESCRIPTION         "Index of device connected to BlueNet2 PDU."
        ::=                 { blueNet2FuseEntry 1 }

    blueNet2FuseCircuit     OBJECT-TYPE
        SYNTAX              Unsigned32          (1..2)
        MAX-ACCESS          not-accessible
        STATUS              current
        DESCRIPTION         "Index of circuit connected to BlueNet2 PDU."
        ::=                 { blueNet2FuseEntry 2 }

    blueNet2FusePhase       OBJECT-TYPE
        SYNTAX              Unsigned32          (1..3)
        MAX-ACCESS          not-accessible
        STATUS              current
        DESCRIPTION         "Index of phase connected to BlueNet2 PDU."
        ::=                 { blueNet2FuseEntry 3 }

    blueNet2FuseIndex       OBJECT-TYPE
        SYNTAX              Unsigned32          (1..4)
        MAX-ACCESS          not-accessible
        STATUS              current
        DESCRIPTION         "Index of phase connected to BlueNet2 PDU."
        ::=                 { blueNet2FuseEntry 4 }

    blueNet2FuseGuid        OBJECT-TYPE
        SYNTAX              OCTET STRING        (SIZE (8..8))
        MAX-ACCESS          read-only
        STATUS              current
        DESCRIPTION         "GUID of fuse connected to BlueNet2 PDU."
        ::=                 { blueNet2FuseEntry 5 }

    blueNet2FuseName        OBJECT-TYPE
        SYNTAX              DisplayString       (SIZE (0..40))
        MAX-ACCESS          read-only
        STATUS              current
        DESCRIPTION         "Name of the fuse connected to BlueNet2 PDU."
        ::=                 { blueNet2FuseEntry 6 }

    blueNet2FuseFriendlyName OBJECT-TYPE
        SYNTAX              DisplayString       (SIZE (0..128))
        MAX-ACCESS          read-write
        STATUS              current
        DESCRIPTION         "User friendlyname of the fuse connected to BlueNet2 PDU."
        ::=                 { blueNet2FuseEntry 7 }

    blueNet2FuseDescription OBJECT-TYPE
        SYNTAX              DisplayString       (SIZE (0..255))
        MAX-ACCESS          read-write
        STATUS              current
        DESCRIPTION         "Description of the fuse connected to BlueNet2 PDU."
        ::=                 { blueNet2FuseEntry 8 }

    blueNet2FuseType        OBJECT-TYPE
        SYNTAX              OBJECT IDENTIFIER
        MAX-ACCESS          read-only
        STATUS              current
        DESCRIPTION         "Type of the fuse connected to BlueNet2 PDU."
        ::=                 { blueNet2FuseEntry 9 }

    blueNet2FuseStatus      OBJECT-TYPE
        SYNTAX              BlueNet2EntityStates
        MAX-ACCESS          read-only
        STATUS              current
        DESCRIPTION         "General status of the entity providing the status of a
                            fuse connected to BlueNet2 PDU in blueNet2VariableStatus."
        ::=                 { blueNet2FuseEntry 10 }

    blueNet2FuseNumberOfSockets OBJECT-TYPE
        SYNTAX              Unsigned32
        MAX-ACCESS          read-only
        STATUS              current
        DESCRIPTION         "Number of sockets of fuse connected to BlueNet2 PDU."
        ::=                 { blueNet2FuseEntry 11 }

-- -----------------------------------------------------------------------------

    blueNet2SocketTable     OBJECT-TYPE
        SYNTAX              SEQUENCE OF BlueNet2SocketEntry
        MAX-ACCESS          not-accessible
        STATUS              current
        DESCRIPTION         "Headline of socket table."
        ::=                 { blueNet2Circuits  5 }

    blueNet2SocketEntry     OBJECT-TYPE
        SYNTAX              BlueNet2SocketEntry
        MAX-ACCESS          not-accessible
        STATUS              current
        DESCRIPTION         "Entries of socket table."
        INDEX               { blueNet2SocketDevice,blueNet2SocketCircuit,blueNet2SocketPhase,blueNet2SocketIndex }
        ::=                 { blueNet2SocketTable 1 }

    BlueNet2SocketEntry     ::=
        SEQUENCE            {
                                blueNet2SocketDevice        Unsigned32,
                                blueNet2SocketCircuit       Unsigned32,
                                blueNet2SocketPhase         Unsigned32,
                                blueNet2SocketFuse          Unsigned32,
                                blueNet2SocketIndex         Unsigned32,
                                blueNet2SocketGuid          OCTET STRING,
                                blueNet2SocketName          DisplayString,
                                blueNet2SocketFriendlyName  DisplayString,
                                blueNet2SocketDescription   DisplayString,
                                blueNet2SocketType          OBJECT IDENTIFIER,
                                blueNet2SocketStatus        BlueNet2EntityStates,
                                blueNet2SocketMode          BlueNet2SocketModes,
                                blueNet2SocketIdentify      BlueNet2SocketModes,
                                blueNet2SocketMemberIndex   Unsigned32
                            }

    blueNet2SocketDevice    OBJECT-TYPE
        SYNTAX              Unsigned32          (1..11)
        MAX-ACCESS          not-accessible
        STATUS              current
        DESCRIPTION         "Index of device connected to BlueNet2 PDU."
        ::=                 { blueNet2SocketEntry 1 }

    blueNet2SocketCircuit   OBJECT-TYPE
        SYNTAX              Unsigned32          (1..2)
        MAX-ACCESS          not-accessible
        STATUS              current
        DESCRIPTION         "Index of circuit connected to BlueNet2 PDU."
        ::=                 { blueNet2SocketEntry 2 }

    blueNet2SocketPhase     OBJECT-TYPE
        SYNTAX              Unsigned32          (0..3)
        MAX-ACCESS          not-accessible
        STATUS              current
        DESCRIPTION         "Index of phase connected to BlueNet2 PDU."
        ::=                 { blueNet2SocketEntry 3 }

    blueNet2SocketFuse      OBJECT-TYPE
        SYNTAX              Unsigned32          (1..4)
        MAX-ACCESS          not-accessible
        STATUS              current
        DESCRIPTION         "Index of fuse connected to BlueNet2 PDU."
        ::=                 { blueNet2SocketEntry 4 }

    blueNet2SocketIndex     OBJECT-TYPE
        SYNTAX              Unsigned32          (0..24)
        MAX-ACCESS          not-accessible
        STATUS              current
        DESCRIPTION         "Index of socket connected to BlueNet2 PDU."
        ::=                 { blueNet2SocketEntry 5 }

    blueNet2SocketGuid      OBJECT-TYPE
        SYNTAX              OCTET STRING        (SIZE (8..8))
        MAX-ACCESS          read-only
        STATUS              current
        DESCRIPTION         "GUID of socket connected to BlueNet2 PDU."
        ::=                 { blueNet2SocketEntry 6 }

    blueNet2SocketName      OBJECT-TYPE
        SYNTAX              DisplayString       (SIZE (0..40))
        MAX-ACCESS          read-only
        STATUS              current
        DESCRIPTION         "Name of the socket connected to BlueNet2 PDU."
        ::=                 { blueNet2SocketEntry 7 }

    blueNet2SocketFriendlyName OBJECT-TYPE
        SYNTAX              DisplayString       (SIZE (0..128))
        MAX-ACCESS          read-write
        STATUS              current
        DESCRIPTION         "User friendlyname of the socket connected to BlueNet2 PDU."
        ::=                 { blueNet2SocketEntry 8 }

    blueNet2SocketDescription OBJECT-TYPE
        SYNTAX              DisplayString       (SIZE (0..255))
        MAX-ACCESS          read-write
        STATUS              current
        DESCRIPTION         "Description of the socket connected to BlueNet2 PDU."
        ::=                 { blueNet2SocketEntry 9 }

    blueNet2SocketType      OBJECT-TYPE
        SYNTAX              OBJECT IDENTIFIER
        MAX-ACCESS          read-only
        STATUS              current
        DESCRIPTION         "Type of the socket connected to BlueNet2 PDU."
        ::=                 { blueNet2SocketEntry 10 }

    blueNet2SocketStatus    OBJECT-TYPE
        SYNTAX              BlueNet2EntityStates
        MAX-ACCESS          read-only
        STATUS              current
        DESCRIPTION         "General status of the entity providing the status of a
                            socket connected to BlueNet2 PDU in blueNet2VariableStatus."
        ::=                 { blueNet2SocketEntry 11 }

    blueNet2SocketMode      OBJECT-TYPE
        SYNTAX              BlueNet2SocketModes
        MAX-ACCESS          read-write
        STATUS              current
        DESCRIPTION         "Mode of the socket connected to BlueNet2 PDU."
        ::=                 { blueNet2SocketEntry 12 }

    blueNet2SocketIdentify  OBJECT-TYPE
        SYNTAX              BlueNet2SocketModes
        MAX-ACCESS          read-write
        STATUS              current
        DESCRIPTION         "Mode of the sockets LED connected to BlueNet2 PDU."
        ::=                 { blueNet2SocketEntry 13 }

    blueNet2SocketMemberIndex OBJECT-TYPE
        SYNTAX              Unsigned32          (1..2048)
        MAX-ACCESS          read-only
        STATUS              current
        DESCRIPTION         "Index of this socket to be used in blueNet2SocketGroupMembers."
        ::=                 { blueNet2SocketEntry 14 }


-- -----------------------------------------------------------------------------

    blueNet2RcmTable        OBJECT-TYPE
        SYNTAX              SEQUENCE OF BlueNet2RCMEntry
        MAX-ACCESS          not-accessible
        STATUS              current
        DESCRIPTION         "Headline of rcm table."
        ::=                 { blueNet2Circuits  6 }

    blueNet2RcmEntry        OBJECT-TYPE
        SYNTAX              BlueNet2RCMEntry
        MAX-ACCESS          not-accessible
        STATUS              current
        DESCRIPTION         "Entries of rcm table."
        INDEX               { blueNet2RcmDevice,blueNet2RcmCircuit,blueNet2RcmPhase,blueNet2RcmFuse,blueNet2RcmSocket,blueNet2RcmIndex }
        ::=                 { blueNet2RcmTable  1 }

    BlueNet2RCMEntry        ::=
        SEQUENCE            {
                                blueNet2RcmDevice                  Unsigned32,
                                blueNet2RcmCircuit                 Unsigned32,
                                blueNet2RcmPhase                   Unsigned32,
                                blueNet2RcmFuse                    Unsigned32,
                                blueNet2RcmSocket                  Unsigned32,
                                blueNet2RcmIndex                   Unsigned32,
                                blueNet2RcmGuid                    OCTET STRING,
                                blueNet2RcmName                    DisplayString,
                                blueNet2RcmFriendlyName            DisplayString,
                                blueNet2RcmDescription             DisplayString,
                                blueNet2RcmType                    OBJECT IDENTIFIER,
                                blueNet2RcmStatus                  BlueNet2EntityStates,
                                blueNet2RcmSelftestCommand         BlueNet2RcmSelftestCommand,
                                blueNet2RcmSelftestResultValue     BlueNet2RcmSelftestResult,
                                blueNet2RcmSelftestResultACvalue   BlueNet2RcmSelftestResult,
                                blueNet2RcmSelftestResultDCvalue   BlueNet2RcmSelftestResult,
                                blueNet2RcmSelftestTimeStamp       DateAndTime,
                                blueNet2RcmSelftestResultStr       DisplayString
                            }

    blueNet2RcmDevice       OBJECT-TYPE
        SYNTAX              Unsigned32          (0..11)
        MAX-ACCESS          not-accessible
        STATUS              current
        DESCRIPTION         "Index of device connected to BlueNet2 PDU."
        ::=                 { blueNet2RcmEntry  1 }

    blueNet2RcmCircuit      OBJECT-TYPE
        SYNTAX              Unsigned32          (0..2)
        MAX-ACCESS          not-accessible
        STATUS              current
        DESCRIPTION         "Index of circuit connected to BlueNet2 PDU."
        ::=                 { blueNet2RcmEntry  2 }

    blueNet2RcmPhase        OBJECT-TYPE
        SYNTAX              Unsigned32          (0..3)
        MAX-ACCESS          not-accessible
        STATUS              current
        DESCRIPTION         "Index of phase connected to BlueNet2 PDU."
        ::=                 { blueNet2RcmEntry  3 }

    blueNet2RcmFuse         OBJECT-TYPE
        SYNTAX              Unsigned32          (0..4)
        MAX-ACCESS          not-accessible
        STATUS              current
        DESCRIPTION         "Index of fuse connected to BlueNet2 PDU."
        ::=                 { blueNet2RcmEntry  4 }

    blueNet2RcmSocket       OBJECT-TYPE
        SYNTAX              Unsigned32          (0..24)
        MAX-ACCESS          not-accessible
        STATUS              current
        DESCRIPTION         "Index of socket connected to BlueNet2 PDU."
        ::=                 { blueNet2RcmEntry  5 }

    blueNet2RcmIndex        OBJECT-TYPE
        SYNTAX              Unsigned32          (0..24)
        MAX-ACCESS          not-accessible
        STATUS              current
        DESCRIPTION         "Index of RCM connected to BlueNet2 PDU."
        ::=                 { blueNet2RcmEntry  6 }

    blueNet2RcmGuid         OBJECT-TYPE
        SYNTAX              OCTET STRING        (SIZE (8..8))
        MAX-ACCESS          read-only
        STATUS              current
        DESCRIPTION         "GUID of RCM connected to BlueNet2 PDU."
        ::=                 { blueNet2RcmEntry  7 }

    blueNet2RcmName         OBJECT-TYPE
        SYNTAX              DisplayString       (SIZE (0..40))
        MAX-ACCESS          read-only
        STATUS              current
        DESCRIPTION         "Name of the RCM connected to BlueNet2 PDU."
        ::=                 { blueNet2RcmEntry  8 }

    blueNet2RcmFriendlyName OBJECT-TYPE
        SYNTAX              DisplayString       (SIZE (0..128))
        MAX-ACCESS          read-write
        STATUS              current
        DESCRIPTION         "User friendlyname of the RCM connected to BlueNet2 PDU."
        ::=                 { blueNet2RcmEntry  9 }

    blueNet2RcmDescription  OBJECT-TYPE
        SYNTAX              DisplayString       (SIZE (0..255))
        MAX-ACCESS          read-write
        STATUS              current
        DESCRIPTION         "Description of the RCM connected to BlueNet2 PDU."
        ::=                 { blueNet2RcmEntry  10 }

    blueNet2RcmType         OBJECT-TYPE
        SYNTAX              OBJECT IDENTIFIER
        MAX-ACCESS          read-only
        STATUS              current
        DESCRIPTION         "Type of the rcm connected to BlueNet2 PDU."
        ::=                 { blueNet2RcmEntry  11 }

    blueNet2RcmStatus       OBJECT-TYPE
        SYNTAX              BlueNet2EntityStates
        MAX-ACCESS          read-only
        STATUS              current
        DESCRIPTION         "General status of the entity providing the status of a
                            Rcm connected to BlueNet2 PDU in blueNet2VariableStatus."
        ::=                 { blueNet2RcmEntry  12 }

    blueNet2RcmSelftestCommand       OBJECT-TYPE
        SYNTAX              BlueNet2RcmSelftestCommand
        MAX-ACCESS          read-write
        STATUS              current
        DESCRIPTION         "RCM self-test commands."
        ::=                 { blueNet2RcmEntry  13 }

    blueNet2RcmSelftestResultValue       OBJECT-TYPE
        SYNTAX              BlueNet2RcmSelftestResult
        MAX-ACCESS          read-only
        STATUS              current
        DESCRIPTION         "RCM self-test result value."
        ::=                 { blueNet2RcmEntry  14 }

    blueNet2RcmSelftestResultACvalue       OBJECT-TYPE
        SYNTAX              BlueNet2RcmSelftestResult
        MAX-ACCESS          read-only
        STATUS              current
        DESCRIPTION         "RCM self-test AC result value."
        ::=                 { blueNet2RcmEntry  15 }

    blueNet2RcmSelftestResultDCvalue       OBJECT-TYPE
        SYNTAX              BlueNet2RcmSelftestResult
        MAX-ACCESS          read-only
        STATUS              current
        DESCRIPTION         "RCM self-test DC result value."
        ::=                 { blueNet2RcmEntry  16 }

	blueNet2RcmSelftestTimeStamp OBJECT-TYPE
		SYNTAX              DateAndTime
		MAX-ACCESS          read-only
		STATUS              current
		DESCRIPTION         "Timestamp of RCM self-test."
		::=                 { blueNet2RcmEntry 17 }

    blueNet2RcmSelftestResultStr OBJECT-TYPE
        SYNTAX              DisplayString       (SIZE (0..255))
        MAX-ACCESS          read-only
        STATUS              current
        DESCRIPTION         "RCM Selftest result as string."
        ::=                 { blueNet2RcmEntry  18 }

-- -----------------------------------------------------------------------------

    blueNet2SpdTable        OBJECT-TYPE
        SYNTAX              SEQUENCE OF BlueNet2SpdEntry
        MAX-ACCESS          not-accessible
        STATUS              current
        DESCRIPTION         "Headline of SPD table."
        ::=                 { blueNet2Circuits  7 }

    blueNet2SpdEntry        OBJECT-TYPE
        SYNTAX              BlueNet2SpdEntry
        MAX-ACCESS          not-accessible
        STATUS              current
        DESCRIPTION         "Entries of spd table."
        INDEX               { blueNet2SpdDevice,blueNet2SpdCircuit,blueNet2SpdPhase,blueNet2SpdFuse,blueNet2SpdSocket,blueNet2SpdIndex }
        ::=                 { blueNet2SpdTable  1 }

    BlueNet2SpdEntry        ::=
        SEQUENCE            {
                                blueNet2SpdDevice           Unsigned32,
                                blueNet2SpdCircuit          Unsigned32,
                                blueNet2SpdPhase            Unsigned32,
                                blueNet2SpdFuse             Unsigned32,
                                blueNet2SpdSocket           Unsigned32,
                                blueNet2SpdIndex            Unsigned32,
                                blueNet2SpdGuid             OCTET STRING,
                                blueNet2SpdName             DisplayString,
                                blueNet2SpdFriendlyName     DisplayString,
                                blueNet2SpdDescription      DisplayString,
                                blueNet2SpdType             OBJECT IDENTIFIER,
                                blueNet2SpdStatus           BlueNet2EntityStates
                            }

    blueNet2SpdDevice       OBJECT-TYPE
        SYNTAX              Unsigned32          (1..11)
        MAX-ACCESS          not-accessible
        STATUS              current
        DESCRIPTION         "Index of device connected to BlueNet2 PDU."
        ::=                 { blueNet2SpdEntry  1 }

    blueNet2SpdCircuit      OBJECT-TYPE
        SYNTAX              Unsigned32          (1..2)
        MAX-ACCESS          not-accessible
        STATUS              current
        DESCRIPTION         "Index of circuit connected to BlueNet2 PDU."
        ::=                 { blueNet2SpdEntry  2 }

    blueNet2SpdPhase        OBJECT-TYPE
        SYNTAX              Unsigned32          (0..3)
        MAX-ACCESS          not-accessible
        STATUS              current
        DESCRIPTION         "Index of phase connected to BlueNet2 PDU."
        ::=                 { blueNet2SpdEntry  3 }

    blueNet2SpdFuse         OBJECT-TYPE
        SYNTAX              Unsigned32          (0..4)
        MAX-ACCESS          not-accessible
        STATUS              current
        DESCRIPTION         "Index of fuse connected to BlueNet2 PDU."
        ::=                 { blueNet2SpdEntry  4 }

    blueNet2SpdSocket       OBJECT-TYPE
        SYNTAX              Unsigned32          (0..48)
        MAX-ACCESS          not-accessible
        STATUS              current
        DESCRIPTION         "Index of socket connected to BlueNet2 PDU."
        ::=                 { blueNet2SpdEntry  5 }

    blueNet2SpdIndex        OBJECT-TYPE
        SYNTAX              Unsigned32          (1..3)
        MAX-ACCESS          not-accessible
        STATUS              current
        DESCRIPTION         "Index of SPD connected to BlueNet2 PDU."
        ::=                 { blueNet2SpdEntry  6 }

    blueNet2SpdGuid         OBJECT-TYPE
        SYNTAX              OCTET STRING        (SIZE (8..8))
        MAX-ACCESS          read-only
        STATUS              current
        DESCRIPTION         "GUID of SPD connected to BlueNet2 PDU."
        ::=                 { blueNet2SpdEntry  7 }

    blueNet2SpdName         OBJECT-TYPE
        SYNTAX              DisplayString       (SIZE (0..40))
        MAX-ACCESS          read-only
        STATUS              current
        DESCRIPTION         "Name of the SPD connected to BlueNet2 PDU."
        ::=                 { blueNet2SpdEntry  8 }

    blueNet2SpdFriendlyName OBJECT-TYPE
        SYNTAX              DisplayString       (SIZE (0..128))
        MAX-ACCESS          read-write
        STATUS              current
        DESCRIPTION         "User friendlyname of the SPD connected to BlueNet2 PDU."
        ::=                 { blueNet2SpdEntry  9 }

    blueNet2SpdDescription  OBJECT-TYPE
        SYNTAX              DisplayString       (SIZE (0..255))
        MAX-ACCESS          read-write
        STATUS              current
        DESCRIPTION         "Description of the SPD connected to BlueNet2 PDU."
        ::=                 { blueNet2SpdEntry  10 }

    blueNet2SpdType         OBJECT-TYPE
        SYNTAX              OBJECT IDENTIFIER
        MAX-ACCESS          read-only
        STATUS              current
        DESCRIPTION         "Type of the spd connected to BlueNet2 PDU."
        ::=                 { blueNet2SpdEntry  11 }

    blueNet2SpdStatus       OBJECT-TYPE
        SYNTAX              BlueNet2EntityStates
        MAX-ACCESS          read-only
        STATUS              current
        DESCRIPTION         "General status of the entity providing the status of an
                            SPD connected to BlueNet2 PDU."
        ::=                 { blueNet2SpdEntry  12 }


-- =============================================================================
--  blueNet2SocketGroups: global BlueNet2 PDU SocketGroups --

    blueNet2SocketGroupInfo OBJECT IDENTIFIER ::= { blueNet2SocketGroups           1 }

    blueNet2OverallSocketGroupStatus OBJECT-TYPE
        SYNTAX              BlueNet2ComponentStates
        MAX-ACCESS          read-only
        STATUS              current
        DESCRIPTION         "Overall status of all socket groups."
        ::=                 { blueNet2SocketGroupInfo 1 }

    blueNet2NumberOfSocketGroups OBJECT-TYPE
        SYNTAX              Unsigned32          (1..128)
        MAX-ACCESS          read-only
        STATUS              current
        DESCRIPTION         "Number of socket groups available."
        ::=                 { blueNet2SocketGroupInfo 2 }

    blueNet2LastChangeOverallSocketGroupStatus OBJECT-TYPE
        SYNTAX              TimeTicks
        MAX-ACCESS          read-only
        STATUS              current
        DESCRIPTION         "Timestamp of last status change of any socket group connected to BlueNet2 PDU
                            according to operating time sysUpTime."
        ::=                 { blueNet2SocketGroupInfo 3 }

    blueNet2LastChangeNumberOfSocketGroups OBJECT-TYPE
        SYNTAX              TimeTicks
        MAX-ACCESS          read-only
        STATUS              current
        DESCRIPTION         "Timestamp of last socket group number change
                            according to operating time sysUpTime."
        ::=                 { blueNet2SocketGroupInfo 4 }

    blueNet2LastChangeSocketGroupSettings OBJECT-TYPE
        SYNTAX              TimeTicks
        MAX-ACCESS          read-only
        STATUS              current
        DESCRIPTION         "Timestamp of last setting change of any socket group connected to BlueNet2 PDU
                            according to operating time sysUpTime.
                            This timestamp will be affected by SNMP settings only!"
        ::=                 { blueNet2SocketGroupInfo 5 }

    blueNet2LastChangeSocketGroups OBJECT-TYPE
        SYNTAX              TimeTicks
        MAX-ACCESS          read-only
        STATUS              current
        DESCRIPTION         "Timestamp of last socket group change
                            according to operating time sysUpTime."
        ::=                 { blueNet2SocketGroupInfo 6 }

    blueNet2SocketGroupsAccumulatedStatus OBJECT-TYPE
        SYNTAX              BlueNet2EntityBits
        MAX-ACCESS          read-only
        STATUS              current
        DESCRIPTION         "A bit field of all current socket group states."
        ::=                 { blueNet2SocketGroupInfo 7 }

    blueNet2SocketGroupsInUse OBJECT-TYPE
        SYNTAX              Unsigned32          (1..128)
        MAX-ACCESS          read-only
        STATUS              current
        DESCRIPTION         "Number of socket groups in use."
        ::=                 { blueNet2SocketGroupInfo 8 }

    blueNet2MaxSocketGroups OBJECT-TYPE
        SYNTAX              Unsigned32          (1..128)
        MAX-ACCESS          read-only
        STATUS              current
        DESCRIPTION         "The maximum number of entries in blueNet2SocketGroupTable."
        ::=                 { blueNet2SocketGroupInfo 9 }

-- -----------------------------------------------------------------------------

    blueNet2SocketGroupTable OBJECT-TYPE
        SYNTAX              SEQUENCE OF BlueNet2SocketGroupEntry
        MAX-ACCESS          not-accessible
        STATUS              current
        DESCRIPTION         "Headline of socket group table."
        ::=                 { blueNet2SocketGroups 2 }

    blueNet2SocketGroupEntry OBJECT-TYPE
        SYNTAX              BlueNet2SocketGroupEntry
        MAX-ACCESS          not-accessible
        STATUS              current
        DESCRIPTION         "Entries of socket group table."
        INDEX               { blueNet2SocketGroupIndex }
        ::=                 { blueNet2SocketGroupTable 1 }

    BlueNet2SocketGroupEntry ::=
        SEQUENCE            {
                                blueNet2SocketGroupIndex    Unsigned32,
                                blueNet2SocketGroupRowStatus RowStatus,
                                blueNet2SocketGroupGuid     OCTET STRING,
                                blueNet2SocketGroupName     DisplayString,
                                blueNet2SocketGroupFriendlyName DisplayString,
                                blueNet2SocketGroupDescription DisplayString,
                                blueNet2SocketGroupStatus   INTEGER,
                                blueNet2SocketGroupMode     BlueNet2SocketModes,
                                blueNet2SocketGroupIdentify BlueNet2SocketModes,
                                blueNet2SocketGroupEntPhysicalIndex Unsigned32,
                                blueNet2SocketGroupAccumulatedStatus BlueNet2EntityBits,
                                blueNet2SocketGroupMembers  BlueNet2SocketMembers
                            }

    blueNet2SocketGroupIndex OBJECT-TYPE
        SYNTAX              Unsigned32          (1..128)
        MAX-ACCESS          not-accessible
        STATUS              current
        DESCRIPTION         "Index of socket group available on BlueNet2 PDU."
        ::=                 { blueNet2SocketGroupEntry 1 }

    blueNet2SocketGroupRowStatus OBJECT-TYPE
        SYNTAX              RowStatus
        MAX-ACCESS          read-create
        STATUS              current
        DESCRIPTION         "Activate/create/destroy/disable a socket group entry."
        ::=                 { blueNet2SocketGroupEntry 2 }

    blueNet2SocketGroupGuid OBJECT-TYPE
        SYNTAX              OCTET STRING        (SIZE (8..8))
        MAX-ACCESS          read-only
        STATUS              current
        DESCRIPTION         "GUID of socket group on BlueNet2 PDU."
        ::=                 { blueNet2SocketGroupEntry 3 }

    blueNet2SocketGroupName OBJECT-TYPE
        SYNTAX              DisplayString       (SIZE (0..40))
        MAX-ACCESS          read-only
        STATUS              current
        DESCRIPTION         "Name of the socket group connected to BlueNet2 PDU."
        ::=                 { blueNet2SocketGroupEntry 4 }

    blueNet2SocketGroupFriendlyName OBJECT-TYPE
        SYNTAX              DisplayString       (SIZE (0..128))
        MAX-ACCESS          read-write
        STATUS              current
        DESCRIPTION         "User friendlyname of the socket group connected to BlueNet2 PDU."
        ::=                 { blueNet2SocketGroupEntry 5 }

    blueNet2SocketGroupDescription OBJECT-TYPE
        SYNTAX              DisplayString       (SIZE (0..255))
        MAX-ACCESS          read-write
        STATUS              current
        DESCRIPTION         "Description of the socket group connected to BlueNet2 PDU."
        ::=                 { blueNet2SocketGroupEntry 6 }

    blueNet2SocketGroupStatus OBJECT-TYPE
        SYNTAX              BlueNet2EntityStates
        MAX-ACCESS          read-only
        STATUS              current
        DESCRIPTION         "Status of socket group."
        ::=                 { blueNet2SocketGroupEntry 7 }

    blueNet2SocketGroupMode OBJECT-TYPE
        SYNTAX              BlueNet2SocketModes
        MAX-ACCESS          read-write
        STATUS              current
        DESCRIPTION         "Mode of all the sockets of a socket group connected to BlueNet2 PDU."
        ::=                 { blueNet2SocketGroupEntry 8 }

    blueNet2SocketGroupIdentify OBJECT-TYPE
        SYNTAX              BlueNet2SocketModes
        MAX-ACCESS          read-write
        STATUS              current
        DESCRIPTION         "Mode of all the socket leds of a socket group connected to BlueNet2 PDU."
        ::=                 { blueNet2SocketGroupEntry 9 }

    blueNet2SocketGroupEntPhysicalIndex OBJECT-TYPE
        SYNTAX              Unsigned32
        MAX-ACCESS          read-only
        STATUS              current
        DESCRIPTION         "Corresponding entPhysicalIndex of this socketgroup. 0 if none exists."
        ::=                 { blueNet2SocketGroupEntry 10 }

    blueNet2SocketGroupAccumulatedStatus OBJECT-TYPE
        SYNTAX              BlueNet2EntityBits
        MAX-ACCESS          read-only
        STATUS              current
        DESCRIPTION         "A bit field of all current socket group members states."
        ::=                 { blueNet2SocketGroupEntry 11 }

    blueNet2SocketGroupMembers OBJECT-TYPE
        SYNTAX              BlueNet2SocketMembers
        MAX-ACCESS          read-write
        STATUS              current
        DESCRIPTION         "The set of sockets which are members of this socket group."
        ::=                 { blueNet2SocketGroupEntry 12 }


--- =============================================================================
--  blueNet2Variables: global BlueNet2 PDU Variables --

    blueNet2VariableInfo    OBJECT IDENTIFIER ::= { blueNet2Variables              1 }

    blueNet2OverallVariableStatus OBJECT-TYPE
        SYNTAX              BlueNet2ComponentStates
        MAX-ACCESS          read-only
        STATUS              current
        DESCRIPTION         "Overall status of all variables."
        ::=                 { blueNet2VariableInfo 1 }

    blueNet2NumberOfVariables OBJECT-TYPE
        SYNTAX              Unsigned32          (1..128)
        MAX-ACCESS          read-only
        STATUS              current
        DESCRIPTION         "Number of variables available."
        ::=                 { blueNet2VariableInfo 2 }

    blueNet2LastChangeOverallVariableStatus OBJECT-TYPE
        SYNTAX              TimeTicks
        MAX-ACCESS          read-only
        STATUS              current
        DESCRIPTION         "Timestamp of last status change of any variables connected to BlueNet2 PDU
                            according to operating time sysUpTime."
        ::=                 { blueNet2VariableInfo 3 }

    blueNet2LastChangeNumberOfVariables OBJECT-TYPE
        SYNTAX              TimeTicks
        MAX-ACCESS          read-only
        STATUS              current
        DESCRIPTION         "Timestamp of last variables number change
                            according to operating time sysUpTime."
        ::=                 { blueNet2VariableInfo 4 }

    blueNet2LastChangeVariableSettings OBJECT-TYPE
        SYNTAX              TimeTicks
        MAX-ACCESS          read-only
        STATUS              current
        DESCRIPTION         "Timestamp of last setting change of any variables connected to BlueNet2 PDU
                            according to operating time sysUpTime.
                            This timestamp will be affected by SNMP settings only!"
        ::=                 { blueNet2VariableInfo 5 }

    blueNet2LastChangeVariableStatus OBJECT-TYPE
        SYNTAX              TimeTicks
        MAX-ACCESS          read-only
        STATUS              current
        DESCRIPTION         "Timestamp of last variable status change
                            according to operating time sysUpTime."
        ::=                 { blueNet2VariableInfo 6 }

    blueNet2VariablesAccumulatedStatus OBJECT-TYPE
        SYNTAX              BlueNet2EntityBits
        MAX-ACCESS          read-only
        STATUS              current
        DESCRIPTION         "A bit field of all current variable states."
        ::=                 { blueNet2VariableInfo 7 }

    blueNet2NumberOfChangesVariableScaling OBJECT-TYPE
        SYNTAX              Unsigned32
        MAX-ACCESS          read-only
        STATUS              current
        DESCRIPTION         "Number of changes in variable scaling due to overrun or reset.
                            Variables are given most accurate, each using its own scaling.
                            But some variables are accumulated and may overrun time by time.
                            In case of overrun or manually reset of a variable its scaling
                            will be changed and this counter gets incremented."
        ::=                 { blueNet2VariableInfo 8 }

    blueNet2LastChangeVariableScaling OBJECT-TYPE
        SYNTAX              TimeTicks
        MAX-ACCESS          read-only
        STATUS              current
        DESCRIPTION         "Timestamp of last variable scaling change
                            according to operating time sysUpTime."
        ::=                 { blueNet2VariableInfo 9 }

    blueNet2LastChangeVariableReset OBJECT-TYPE
        SYNTAX              TimeTicks
        MAX-ACCESS          read-only
        STATUS              current
        DESCRIPTION         "Timestamp of last manually reset of a variable
                            according to operating time sysUpTime."
        ::=                 { blueNet2VariableInfo 10 }


-- -----------------------------------------------------------------------------

    blueNet2VariableTable   OBJECT-TYPE
        SYNTAX              SEQUENCE OF BlueNet2VariableEntry
        MAX-ACCESS          not-accessible
        STATUS              current
        DESCRIPTION         "Headline of variable table."
        ::=                 { blueNet2Variables 2 }

    blueNet2VariableEntry   OBJECT-TYPE
        SYNTAX              BlueNet2VariableEntry
        MAX-ACCESS          not-accessible
        STATUS              current
        DESCRIPTION         "Entries of variable table."
        INDEX               { blueNet2VariableId }
        ::=                 { blueNet2VariableTable 1 }

    BlueNet2VariableEntry   ::=
        SEQUENCE            {
                                blueNet2VariableId          OCTET STRING,
                                blueNet2VariableGuid        OCTET STRING,
                                blueNet2VariableName        DisplayString,
                                blueNet2VariableFriendlyName DisplayString,
                                blueNet2VariableDescription DisplayString,
                                blueNet2VariableType        BlueNet2DataSourceTypes,
                                blueNet2VariableStatus      BlueNet2EntityStates,
                                blueNet2VariableAlarm       DisplayString,
                                blueNet2VariableScaling     Integer32,
                                blueNet2VariableUnit        BlueNet2DataSourceUnits,
                                blueNet2VariableSetPoint    INTEGER,
                                blueNet2VariableMode        INTEGER,
                                blueNet2VariableEntPhysicalIndex Unsigned32
                            }

    blueNet2VariableId      OBJECT-TYPE
        SYNTAX              OCTET STRING        (SIZE (8..8))
        MAX-ACCESS          not-accessible
        STATUS              current
        DESCRIPTION         "GUID of variable."
        ::=                 { blueNet2VariableEntry 1 }

    blueNet2VariableGuid    OBJECT-TYPE
        SYNTAX              OCTET STRING        (SIZE (8..8))
        MAX-ACCESS          read-only
        STATUS              current
        DESCRIPTION         "GUID of variable."
        ::=                 { blueNet2VariableEntry 2 }

    blueNet2VariableName    OBJECT-TYPE
        SYNTAX              DisplayString       (SIZE (0..40))
        MAX-ACCESS          read-only
        STATUS              current
        DESCRIPTION         "Name of the variable connected to BlueNet2 PDU."
        ::=                 { blueNet2VariableEntry 3 }

    blueNet2VariableFriendlyName OBJECT-TYPE
        SYNTAX              DisplayString       (SIZE (0..128))
        MAX-ACCESS          read-only
        STATUS              current
        DESCRIPTION         "User friendlyname of the variable connected to BlueNet2 PDU."
        ::=                 { blueNet2VariableEntry 4 }

    blueNet2VariableDescription OBJECT-TYPE
        SYNTAX              DisplayString       (SIZE (0..255))
        MAX-ACCESS          read-only
        STATUS              current
        DESCRIPTION         "Description of the variable connected to BlueNet2 PDU."
        ::=                 { blueNet2VariableEntry 5 }

    blueNet2VariableType    OBJECT-TYPE
        SYNTAX              BlueNet2DataSourceTypes
        MAX-ACCESS          read-only
        STATUS              current
        DESCRIPTION         "Type of variable."
        ::=                 { blueNet2VariableEntry 6 }

    blueNet2VariableStatus  OBJECT-TYPE
        SYNTAX              BlueNet2EntityStates
        MAX-ACCESS          read-only
        STATUS              current
        DESCRIPTION         "General status of variable connected to BlueNet2 PDU."
        ::=                 { blueNet2VariableEntry 7 }

    blueNet2VariableAlarm   OBJECT-TYPE
        SYNTAX              DisplayString       (SIZE (0..255))
        MAX-ACCESS          read-only
        STATUS              current
        DESCRIPTION         "Alarm text of variable connected to BlueNet2 PDU."
        ::=                 { blueNet2VariableEntry 8 }

    blueNet2VariableScaling OBJECT-TYPE
        SYNTAX              Integer32
        MAX-ACCESS          read-only
        STATUS              current
        DESCRIPTION         "Scaling of variable as 10^x."
        ::=                 { blueNet2VariableEntry 9 }

    blueNet2VariableUnit    OBJECT-TYPE
        SYNTAX              BlueNet2DataSourceUnits
        MAX-ACCESS          read-only
        STATUS              current
        DESCRIPTION         "Unit of variable."
        ::=                 { blueNet2VariableEntry 10 }

    blueNet2VariableSetPoint OBJECT-TYPE
        SYNTAX              INTEGER {
                                notAvailable    (1),
                                available       (2)
                            }
        MAX-ACCESS          read-only
        STATUS              current
        DESCRIPTION         "Set point supported for this variable."
        ::=                 { blueNet2VariableEntry 11 }

    blueNet2VariableMode    OBJECT-TYPE
        SYNTAX              INTEGER {
        						resettable      (0),
                                reset           (1),
                                noReset         (2)
                            }
        MAX-ACCESS          read-write
        STATUS              current
        DESCRIPTION         "Reset mode of a variable.
                            Variables in mode reset(1) can by reset by writing reset(1).
                            No other values than reset(1) can be written."
        ::=                 { blueNet2VariableEntry 12 }

    blueNet2VariableEntPhysicalIndex OBJECT-TYPE
        SYNTAX              Unsigned32
        MAX-ACCESS          read-only
        STATUS              current
        DESCRIPTION         "Corresponding entPhysicalIndex of this variable. 0 if none exists."
        ::=                 { blueNet2VariableEntry 13 }

-- -----------------------------------------------------------------------------

    blueNet2VariableSetPointTable OBJECT-TYPE
        SYNTAX              SEQUENCE OF BlueNet2VariableSetPointEntry
        MAX-ACCESS          not-accessible
        STATUS              current
        DESCRIPTION         "Headline of variable set point table."
        ::=                 { blueNet2Variables 3 }

    blueNet2VariableSetPointEntry OBJECT-TYPE
        SYNTAX              BlueNet2VariableSetPointEntry
        MAX-ACCESS          not-accessible
        STATUS              current
        DESCRIPTION         "Entries of variable set point table."
        INDEX               { blueNet2VariableSetPointGuid }
        ::=                 { blueNet2VariableSetPointTable 1 }

    BlueNet2VariableSetPointEntry ::=
        SEQUENCE            {
                                blueNet2VariableSetPointGuid OCTET STRING,
                                blueNet2VariableSetPointType BITS,
                                blueNet2VariableSetPointMinValue Integer32,
                                blueNet2VariableSetPointMaxValue Integer32,
                                blueNet2VariableSetPointLowerAlarm Integer32,
                                blueNet2VariableSetPointLowerWarning Integer32,
                                blueNet2VariableSetPointUpperWarning Integer32,
                                blueNet2VariableSetPointUpperAlarm Integer32,
                                blueNet2VariableSetPointHysteresis Unsigned32,
                                blueNet2VariableSetPointRcmACUpperAlarmThreshold DisplayString,
                                blueNet2VariableSetPointRcmACUpperAlarmGradient DisplayString,
                                blueNet2VariableSetPointRcmACUpperWarningThreshold DisplayString,
                                blueNet2VariableSetPointRcmACUpperWarningGradient DisplayString

                            }

    blueNet2VariableSetPointGuid OBJECT-TYPE
        SYNTAX              OCTET STRING        (SIZE (8..8))
        MAX-ACCESS          not-accessible
        STATUS              current
        DESCRIPTION         "GUID of set point."
        ::=                 { blueNet2VariableSetPointEntry 1 }

    blueNet2VariableSetPointType OBJECT-TYPE
        SYNTAX              BITS {
                                highAlarm       (0),
                                lowAlarm        (1),
                                highWarning     (2),
                                lowWarning      (3)
                            }
        MAX-ACCESS          read-only
        STATUS              current
        DESCRIPTION         "Type of setpoint."
        ::=                 { blueNet2VariableSetPointEntry 2 }

    blueNet2VariableSetPointMinValue OBJECT-TYPE
        SYNTAX              Integer32
        MAX-ACCESS          read-only
        STATUS              current
        DESCRIPTION         "Minimum value of setpoint."
        ::=                 { blueNet2VariableSetPointEntry 3 }

    blueNet2VariableSetPointMaxValue OBJECT-TYPE
        SYNTAX              Integer32
        MAX-ACCESS          read-only
        STATUS              current
        DESCRIPTION         "Maximum value of setpoint."
        ::=                 { blueNet2VariableSetPointEntry 4 }

    blueNet2VariableSetPointLowerAlarm OBJECT-TYPE
        SYNTAX              Integer32
        MAX-ACCESS          read-write
        STATUS              current
        DESCRIPTION         "Lower threshold of variable."
        ::=                 { blueNet2VariableSetPointEntry 5 }

    blueNet2VariableSetPointLowerWarning OBJECT-TYPE
        SYNTAX              Integer32
        MAX-ACCESS          read-write
        STATUS              current
        DESCRIPTION         "Lower Warning of variable."
        ::=                 { blueNet2VariableSetPointEntry 6 }

    blueNet2VariableSetPointUpperWarning OBJECT-TYPE
        SYNTAX              Integer32
        MAX-ACCESS          read-write
        STATUS              current
        DESCRIPTION         "Upper warning of variable."
        ::=                 { blueNet2VariableSetPointEntry 7 }

    blueNet2VariableSetPointUpperAlarm OBJECT-TYPE
        SYNTAX              Integer32
        MAX-ACCESS          read-write
        STATUS              current
        DESCRIPTION         "Upper threshold of variable."
        ::=                 { blueNet2VariableSetPointEntry 8 }

    blueNet2VariableSetPointHysteresis OBJECT-TYPE
        SYNTAX              Unsigned32          (0..100)
        MAX-ACCESS          read-write
        STATUS              current
        DESCRIPTION         "Hysteresis of variable."
        ::=                 { blueNet2VariableSetPointEntry 9 }

    blueNet2VariableSetPointRcmACUpperAlarmThreshold OBJECT-TYPE
        SYNTAX              DisplayString       (SIZE (0..20))
        MAX-ACCESS          read-write
        STATUS              current
        DESCRIPTION         "Upper Alarm threshold of RCM AC."
        ::=                 { blueNet2VariableSetPointEntry 10 }

    blueNet2VariableSetPointRcmACUpperAlarmGradient    OBJECT-TYPE
        SYNTAX              DisplayString       (SIZE (0..20))
        MAX-ACCESS          read-write
        STATUS              current
        DESCRIPTION         "Upper Alarm gradient of RCM AC."
        ::=                 { blueNet2VariableSetPointEntry 11 }

    blueNet2VariableSetPointRcmACUpperWarningThreshold OBJECT-TYPE
        SYNTAX              DisplayString       (SIZE (0..20))
        MAX-ACCESS          read-write
        STATUS              current
        DESCRIPTION         "Upper Warning threshold of RCM AC."
        ::=                 { blueNet2VariableSetPointEntry 12 }

    blueNet2VariableSetPointRcmACUpperWarningGradient    OBJECT-TYPE
        SYNTAX              DisplayString       (SIZE (0..20))
        MAX-ACCESS          read-write
        STATUS              current
        DESCRIPTION         "Upper Warning gradient of RCM AC."
        ::=                 { blueNet2VariableSetPointEntry 13 }

-- -----------------------------------------------------------------------------

    blueNet2VariableDataTable OBJECT-TYPE
        SYNTAX              SEQUENCE OF BlueNet2VariableDataEntry
        MAX-ACCESS          not-accessible
        STATUS              current
        DESCRIPTION         "Headline of variable data table.
                            This table contains a subset of frequently changing variables as
                            in blueNet2VariableDataTable, like measured values and status."
        ::=                 { blueNet2Variables 4 }

    blueNet2VariableDataEntry OBJECT-TYPE
        SYNTAX              BlueNet2VariableDataEntry
        MAX-ACCESS          not-accessible
        STATUS              current
        DESCRIPTION         "Entries of variable date table."
        INDEX               { blueNet2VariableGuid }
        ::=                 { blueNet2VariableDataTable 1 }

    BlueNet2VariableDataEntry ::=
        SEQUENCE            {
                                blueNet2VariableDataId      OCTET STRING,
                                blueNet2VariableDataGuid    OCTET STRING,
                                blueNet2VariableDataType    BlueNet2DataSourceTypes,
                                blueNet2VariableDataStatus  BlueNet2EntityStates,
                                blueNet2VariableDataValue   Integer32,
                                blueNet2VariableDataDateTime DateAndTime
                            }

    blueNet2VariableDataId  OBJECT-TYPE
        SYNTAX              OCTET STRING        (SIZE (8..8))
        MAX-ACCESS          not-accessible
        STATUS              current
        DESCRIPTION         "GUID of variable."
        ::=                 { blueNet2VariableDataEntry 1 }

    blueNet2VariableDataGuid OBJECT-TYPE
        SYNTAX              OCTET STRING        (SIZE (8..8))
        MAX-ACCESS          read-only
        STATUS              current
        DESCRIPTION         "GUID of variable."
        ::=                 { blueNet2VariableDataEntry 2 }

    blueNet2VariableDataType OBJECT-TYPE
        SYNTAX              BlueNet2DataSourceTypes
        MAX-ACCESS          read-only
        STATUS              current
        DESCRIPTION         "Type of variable."
        ::=                 { blueNet2VariableDataEntry 3 }

    blueNet2VariableDataStatus OBJECT-TYPE
        SYNTAX              BlueNet2EntityStates
        MAX-ACCESS          read-only
        STATUS              current
        DESCRIPTION         "Status of variable."
        ::=                 { blueNet2VariableDataEntry 4 }

    blueNet2VariableDataValue OBJECT-TYPE
        SYNTAX              Integer32
        MAX-ACCESS          read-only
        STATUS              current
        DESCRIPTION         "Value of variable."
        ::=                 { blueNet2VariableDataEntry 5 }

    blueNet2VariableDataDateTime OBJECT-TYPE
        SYNTAX              DateAndTime
        MAX-ACCESS          read-only
        STATUS              current
        DESCRIPTION         "Timestamp of variable."
        ::=                 { blueNet2VariableDataEntry 6 }

-- -----------------------------------------------------------------------------

    blueNet2VariableDataByTypeTable OBJECT-TYPE
        SYNTAX              SEQUENCE OF BlueNet2VariableDataByTypeEntry
        MAX-ACCESS          not-accessible
        STATUS              current
        DESCRIPTION         "Headline of variable data by type table.
                            This table contains a subset of frequently changing variables as
                            in blueNet2VariableDataByTypeTable, like measured values and status.
                            This table is ordered by type of measurement source."
        ::=                 { blueNet2Variables 5 }

    blueNet2VariableDataByTypeEntry OBJECT-TYPE
        SYNTAX              BlueNet2VariableDataByTypeEntry
        MAX-ACCESS          not-accessible
        STATUS              current
        DESCRIPTION         "Entries of variable data by type table."
        INDEX               { blueNet2VariableDataByType,blueNet2VariableDataByTypeGuid }
        ::=                 { blueNet2VariableDataByTypeTable 1 }

    BlueNet2VariableDataByTypeEntry ::=
        SEQUENCE            {
                                blueNet2VariableDataByType  BlueNet2DataSourceTypes,
                                blueNet2VariableDataByTypeGuid OCTET STRING,
                                blueNet2VariableDataByTypeType BlueNet2DataSourceTypes,
                                blueNet2VariableDataByTypeStatus BlueNet2EntityStates,
                                blueNet2VariableDataByTypeValue Integer32,
                                blueNet2VariableDataByTypeDateTime DateAndTime
                            }

    blueNet2VariableDataByType OBJECT-TYPE
        SYNTAX              BlueNet2DataSourceTypes
        MAX-ACCESS          not-accessible
        STATUS              current
        DESCRIPTION         "Type of variable."
        ::=                 { blueNet2VariableDataByTypeEntry 1 }

    blueNet2VariableDataByTypeGuid OBJECT-TYPE
        SYNTAX              OCTET STRING        (SIZE (8..8))
        MAX-ACCESS          not-accessible
        STATUS              current
        DESCRIPTION         "GUID of variable."
        ::=                 { blueNet2VariableDataByTypeEntry 2 }

    blueNet2VariableDataByTypeType OBJECT-TYPE
        SYNTAX              BlueNet2DataSourceTypes
        MAX-ACCESS          read-only
        STATUS              current
        DESCRIPTION         "Type of variable."
        ::=                 { blueNet2VariableDataByTypeEntry 3 }

    blueNet2VariableDataByTypeStatus OBJECT-TYPE
        SYNTAX              BlueNet2EntityStates
        MAX-ACCESS          read-only
        STATUS              current
        DESCRIPTION         "Status of variable."
        ::=                 { blueNet2VariableDataByTypeEntry 4 }

    blueNet2VariableDataByTypeValue OBJECT-TYPE
        SYNTAX              Integer32
        MAX-ACCESS          read-only
        STATUS              current
        DESCRIPTION         "Value of variable."
        ::=                 { blueNet2VariableDataByTypeEntry 5 }

    blueNet2VariableDataByTypeDateTime OBJECT-TYPE
        SYNTAX              DateAndTime
        MAX-ACCESS          read-only
        STATUS              current
        DESCRIPTION         "Timestamp of variable."
        ::=                 { blueNet2VariableDataByTypeEntry 6 }

-- -----------------------------------------------------------------------------

    blueNet2VariableDataByStateTable OBJECT-TYPE
        SYNTAX              SEQUENCE OF BlueNet2VariableDataByStateEntry
        MAX-ACCESS          not-accessible
        STATUS              deprecated
        DESCRIPTION         "Headline of variable data by state table.
                            This table contains a subset of frequently changing variables as
                            in blueNet2VariableDataByStateTable, like measured values and status.
                            This table is ordered by the state of variable.

                            This table is updated periodically in a 15 seconds intervall!
                            Therefore a variable state may temporarily not reflect the current state!"
        ::=                 { blueNet2Variables 6 }

    blueNet2VariableDataByStateEntry OBJECT-TYPE
        SYNTAX              BlueNet2VariableDataByStateEntry
        MAX-ACCESS          not-accessible
        STATUS              deprecated
        DESCRIPTION         "Entries of variable data by state table."
        INDEX               { blueNet2VariableDataByState,blueNet2VariableDataByStateGuid }
        ::=                 { blueNet2VariableDataByStateTable 1 }

    BlueNet2VariableDataByStateEntry ::=
        SEQUENCE            {
                                blueNet2VariableDataByState BlueNet2EntityStates,
                                blueNet2VariableDataByStateGuid OCTET STRING,
                                blueNet2VariableDataByStateType BlueNet2DataSourceTypes,
                                blueNet2VariableDataByStateStatus BlueNet2EntityStates,
                                blueNet2VariableDataByStateValue Integer32,
                                blueNet2VariableDataByStateDateTime DateAndTime
                            }

    blueNet2VariableDataByState OBJECT-TYPE
        SYNTAX              BlueNet2EntityStates
        MAX-ACCESS          not-accessible
        STATUS              deprecated
        DESCRIPTION         "Status of variable."
        ::=                 { blueNet2VariableDataByStateEntry 1 }

    blueNet2VariableDataByStateGuid OBJECT-TYPE
        SYNTAX              OCTET STRING        (SIZE (8..8))
        MAX-ACCESS          not-accessible
        STATUS              deprecated
        DESCRIPTION         "GUID of variable."
        ::=                 { blueNet2VariableDataByStateEntry 2 }

    blueNet2VariableDataByStateType OBJECT-TYPE
        SYNTAX              BlueNet2DataSourceTypes
        MAX-ACCESS          read-only
        STATUS              deprecated
        DESCRIPTION         "Type of variable."
        ::=                 { blueNet2VariableDataByStateEntry 3 }

    blueNet2VariableDataByStateStatus OBJECT-TYPE
        SYNTAX              BlueNet2EntityStates
        MAX-ACCESS          read-only
        STATUS              deprecated
        DESCRIPTION         "Status of variable."
        ::=                 { blueNet2VariableDataByStateEntry 4 }

    blueNet2VariableDataByStateValue OBJECT-TYPE
        SYNTAX              Integer32
        MAX-ACCESS          read-only
        STATUS              deprecated
        DESCRIPTION         "Value of variable."
        ::=                 { blueNet2VariableDataByStateEntry 5 }

    blueNet2VariableDataByStateDateTime OBJECT-TYPE
        SYNTAX              DateAndTime
        MAX-ACCESS          read-only
        STATUS              deprecated
        DESCRIPTION         "Timestamp of variable."
        ::=                 { blueNet2VariableDataByStateEntry 6 }

-- -----------------------------------------------------------------------------

    blueNet2VariableDataBySourceTable OBJECT-TYPE
        SYNTAX              SEQUENCE OF BlueNet2VariableDataBySourceEntry
        MAX-ACCESS          not-accessible
        STATUS              current
        DESCRIPTION         "Headline of variable data by state table.
                            This table contains a subset of frequently changing variables as
                            in blueNet2VariableDataBySourceTable, like measured values and status.
                            This table is ordered by the source of variable."
        ::=                 { blueNet2Variables 7 }

    blueNet2VariableDataBySourceEntry OBJECT-TYPE
        SYNTAX              BlueNet2VariableDataBySourceEntry
        MAX-ACCESS          not-accessible
        STATUS              current
        DESCRIPTION         "Entries of variable data by source table."
        INDEX               { blueNet2VariableDataBySource,blueNet2VariableDataBySourceGuid }
        ::=                 { blueNet2VariableDataBySourceTable 1 }

    BlueNet2VariableDataBySourceEntry ::=
        SEQUENCE            {
                                blueNet2VariableDataBySource BlueNet2EntitySources,
                                blueNet2VariableDataBySourceGuid OCTET STRING,
                                blueNet2VariableDataBySourceType BlueNet2DataSourceTypes,
                                blueNet2VariableDataBySourceStatus BlueNet2EntityStates,
                                blueNet2VariableDataBySourceValue Integer32,
                                blueNet2VariableDataBySourceDateTime DateAndTime
                            }

    blueNet2VariableDataBySource OBJECT-TYPE
        SYNTAX              BlueNet2EntitySources
        MAX-ACCESS          not-accessible
        STATUS              current
        DESCRIPTION         "Source of variable."
        ::=                 { blueNet2VariableDataBySourceEntry 1 }

    blueNet2VariableDataBySourceGuid OBJECT-TYPE
        SYNTAX              OCTET STRING        (SIZE (8..8))
        MAX-ACCESS          not-accessible
        STATUS              current
        DESCRIPTION         "GUID of variable."
        ::=                 { blueNet2VariableDataBySourceEntry 2 }

    blueNet2VariableDataBySourceType OBJECT-TYPE
        SYNTAX              BlueNet2DataSourceTypes
        MAX-ACCESS          read-only
        STATUS              current
        DESCRIPTION         "Type of variable."
        ::=                 { blueNet2VariableDataBySourceEntry 3 }

    blueNet2VariableDataBySourceStatus OBJECT-TYPE
        SYNTAX              BlueNet2EntityStates
        MAX-ACCESS          read-only
        STATUS              current
        DESCRIPTION         "Status of variable."
        ::=                 { blueNet2VariableDataBySourceEntry 4 }

    blueNet2VariableDataBySourceValue OBJECT-TYPE
        SYNTAX              Integer32
        MAX-ACCESS          read-only
        STATUS              current
        DESCRIPTION         "Value of variable."
        ::=                 { blueNet2VariableDataBySourceEntry 5 }

    blueNet2VariableDataBySourceDateTime OBJECT-TYPE
        SYNTAX              DateAndTime
        MAX-ACCESS          read-only
        STATUS              current
        DESCRIPTION         "Timestamp of variable."
        ::=                 { blueNet2VariableDataBySourceEntry 6 }


--- =============================================================================
--  blueNet2MPStates: global BlueNet2 Overview of Measurement Point States --

    blueNet2MPTable         OBJECT-TYPE
        SYNTAX              SEQUENCE OF BlueNet2MPEntry
        MAX-ACCESS          not-accessible
        STATUS              current
        DESCRIPTION         "Headline of MP (Measurement Point) table."
        ::=                 { blueNet2MPStates  1 }

    blueNet2MPEntry         OBJECT-TYPE
        SYNTAX              BlueNet2MPEntry
        MAX-ACCESS          not-accessible
        STATUS              current
        DESCRIPTION         "Entries of Measurement Point table."
        INDEX               { blueNet2MPID }
        ::=                 { blueNet2MPTable 1 }

    BlueNet2MPEntry    ::=
        SEQUENCE            {
                                blueNet2MPID           OCTET STRING,
                                blueNet2MPGuid         OCTET STRING,
                                blueNet2MPName         DisplayString,
                                blueNet2MPFriendlyName DisplayString,
                                blueNet2MPState        BlueNet2EntityStates,
                                blueNet2MPTimeStamp    DateAndTime
                            }

    blueNet2MPID            OBJECT-TYPE
        SYNTAX              OCTET STRING        (SIZE (8..8))
        MAX-ACCESS          not-accessible
        STATUS              current
        DESCRIPTION         "GUID of a Measurement Point."
        ::=                 { blueNet2MPEntry 1 }

    blueNet2MPGuid          OBJECT-TYPE
        SYNTAX              OCTET STRING        (SIZE (8..8))
        MAX-ACCESS          read-only
        STATUS              current
        DESCRIPTION         "GUID of a Measurement Point."
        ::=                 { blueNet2MPEntry 2 }

    blueNet2MPName          OBJECT-TYPE
        SYNTAX              DisplayString       (SIZE (0..40))
        MAX-ACCESS          read-only
        STATUS              current
        DESCRIPTION         "Name of a Measurement Point."
        ::=                 { blueNet2MPEntry 3 }

    blueNet2MPFriendlyName  OBJECT-TYPE
        SYNTAX              DisplayString       (SIZE (0..128))
        MAX-ACCESS          read-only
        STATUS              current
        DESCRIPTION         "User friendlyname of a Measurement Point."
        ::=                 { blueNet2MPEntry 4 }

    blueNet2MPState         OBJECT-TYPE
        SYNTAX              BlueNet2EntityStates
        MAX-ACCESS          read-only
        STATUS              current
        DESCRIPTION         "Status of a Measurement Point."
        ::=                 { blueNet2MPEntry 5 }

     blueNet2MPTimeStamp    OBJECT-TYPE
        SYNTAX              DateAndTime
        MAX-ACCESS          read-only
        STATUS              current
        DESCRIPTION         "Timestamp of the last change of a Measurement Point."
        ::=                 { blueNet2MPEntry 6 }


-- *****************************************************************************

--  Traps  --

    blueNet2TrapPrefix      OBJECT IDENTIFIER ::= { blueNet2Traps                  0 }

    blueNet2PduStatusOkTrap NOTIFICATION-TYPE
        OBJECTS             {
                                blueNet2DeviceGuid,
                                blueNet2DeviceStatus,
                                blueNet2DeviceAlarm
                            }
        STATUS              current
        DESCRIPTION         "PDU status ok."
--
--            #CATEGORY     "Status Events."
--            #TYPE         "PDU status ok."
--            #SUMMARY      "Guid %x device status is %i: %s."
--            #ARGUMENTS    {0,1,2}
--            #SEVERITY     INFORMATIONAL
--            #STATE        OPERATIONAL
--
        ::=                 { blueNet2TrapPrefix 1 }

    blueNet2PduStatusWarningTrap NOTIFICATION-TYPE
        OBJECTS             {
                                blueNet2DeviceGuid,
                                blueNet2DeviceStatus,
                                blueNet2DeviceAlarm
                            }
        STATUS              current
        DESCRIPTION         "PDU status warning."
--
--            #CATEGORY     "Status Events."
--            #TYPE         "PDU status warning."
--            #SUMMARY      "Guid %x device status is %i: %s."
--            #ARGUMENTS    {0,1,2}
--            #SEVERITY     MINOR
--            #STATE        OPERATIONAL
--
        ::=                 { blueNet2TrapPrefix 2 }

    blueNet2PduStatusAlarmTrap NOTIFICATION-TYPE
        OBJECTS             {
                                blueNet2DeviceGuid,
                                blueNet2DeviceStatus,
                                blueNet2DeviceAlarm
                            }
        STATUS              current
        DESCRIPTION         "PDU status alarm."
--
--            #CATEGORY     "Status Events."
--            #TYPE         "PDU status alarm."
--            #SUMMARY      "Guid %x device status is %i: %s."
--            #ARGUMENTS    {0,1,2}
--            #SEVERITY     MAJOR
--            #STATE        OPERATIONAL
--
        ::=                 { blueNet2TrapPrefix 3 }

    blueNet2SensorStatusOkTrap NOTIFICATION-TYPE
        OBJECTS             {
                                blueNet2SensorGuid,
                                blueNet2SensorStatus,
                                blueNet2SensorAlarm
                            }
        STATUS              current
        DESCRIPTION         "Sensor status change."
--
--            #CATEGORY     "Status Events."
--            #TYPE         "Sensor status ok."
--            #SUMMARY      "Guid %x sensor status is %i: %s."
--            #ARGUMENTS    {0,1,2}
--            #SEVERITY     INFORMATIONAL
--            #STATE        OPERATIONAL
--
        ::=                 { blueNet2TrapPrefix 4 }

    blueNet2SensorStatusWarningTrap NOTIFICATION-TYPE
        OBJECTS             {
                                blueNet2SensorGuid,
                                blueNet2SensorStatus,
                                blueNet2SensorAlarm
                            }
        STATUS              current
        DESCRIPTION         "Sensor status change."
--
--            #CATEGORY     "Status Events."
--            #TYPE         "Sensor status warning."
--            #SUMMARY      "Guid %x sensor status is %i: %s."
--            #ARGUMENTS    {0,1,2}
--            #SEVERITY     MINOR
--            #STATE        OPERATIONAL
--
        ::=                 { blueNet2TrapPrefix 5 }

    blueNet2SensorStatusAlarmTrap NOTIFICATION-TYPE
        OBJECTS             {
                                blueNet2SensorGuid,
                                blueNet2SensorStatus,
                                blueNet2SensorAlarm
                            }
        STATUS              current
        DESCRIPTION         "Sensor status change."
--
--            #CATEGORY     "Status Events."
--            #TYPE         "Sensor status alarm."
--            #SUMMARY      "Guid %x sensor status is %i: %s."
--            #ARGUMENTS    {0,1,2}
--            #SEVERITY     MAJOR
--            #STATE        OPERATIONAL
--
        ::=                 { blueNet2TrapPrefix 6 }

    blueNet2VariableStatusOkTrap NOTIFICATION-TYPE
        OBJECTS             {
                                blueNet2VariableDataGuid,
                                blueNet2VariableDataStatus,
                                blueNet2VariableDataValue,
                                blueNet2VariableAlarm
                            }
        STATUS              current
        DESCRIPTION         "Variable status is ok."
--
--            #CATEGORY     "Threshold Events."
--            #TYPE         "Variable status is ok."
--            #SUMMARY      "Guid %x variable value %i is ok (%i), %s."
--            #ARGUMENTS    {0,1,2,3}
--            #SEVERITY     INFORMATIONAL
--            #STATE        OPERATIONAL
--
        ::=                 { blueNet2TrapPrefix 7 }

    blueNet2VariableLowerWarningTrap NOTIFICATION-TYPE
        OBJECTS             {
                                blueNet2VariableDataGuid,
                                blueNet2VariableDataStatus,
                                blueNet2VariableDataValue,
                                blueNet2VariableSetPointLowerAlarm,
                                blueNet2VariableAlarm
                            }
        STATUS              current
        DESCRIPTION         "Variable status lower warning."
--
--            #CATEGORY     "Threshold Events."
--            #TYPE         "Variable status lower warning."
--            #SUMMARY      "Guid %x variable value %i deceeds %i (%i), %s."
--            #ARGUMENTS    {0,2,1,3,4}
--            #SEVERITY     MINOR
--            #STATE        OPERATIONAL
--
        ::=                 { blueNet2TrapPrefix 8 }

    blueNet2VariableUpperWarningTrap NOTIFICATION-TYPE
        OBJECTS             {
                                blueNet2VariableDataGuid,
                                blueNet2VariableDataStatus,
                                blueNet2VariableDataValue,
                                blueNet2VariableSetPointUpperWarning,
                                blueNet2VariableAlarm
                            }
        STATUS              current
        DESCRIPTION         "Variable status upper warning."
--
--            #CATEGORY     "Threshold Events."
--            #TYPE         "Variable status upper warning."
--            #SUMMARY      "Guid %x variable value %i exceeds %i (%i), %s."
--            #ARGUMENTS    {0,2,1,3,4}
--            #SEVERITY     MINOR
--            #STATE        OPERATIONAL
--
        ::=                 { blueNet2TrapPrefix 9 }

    blueNet2VariableLowerAlarmTrap NOTIFICATION-TYPE
        OBJECTS             {
                                blueNet2VariableDataGuid,
                                blueNet2VariableDataStatus,
                                blueNet2VariableDataValue,
                                blueNet2VariableSetPointLowerAlarm,
                                blueNet2VariableAlarm
                            }
        STATUS              current
        DESCRIPTION         "Variable status lower alarm."
--
--            #CATEGORY     "Threshold Events."
--            #TYPE         "Variable status lower alarm."
--            #SUMMARY      "Guid %x variable value %i deceeds %i (%i), %s."
--            #ARGUMENTS    {0,2,1,3,4}
--            #SEVERITY     MAJOR
--            #STATE        OPERATIONAL
--
        ::=                 { blueNet2TrapPrefix 10 }

    blueNet2VariableUpperAlarmTrap NOTIFICATION-TYPE
        OBJECTS             {
                                blueNet2VariableDataGuid,
                                blueNet2VariableDataStatus,
                                blueNet2VariableDataValue,
                                blueNet2VariableSetPointUpperAlarm,
                                blueNet2VariableAlarm
                            }
        STATUS              current
        DESCRIPTION         "Variable status upper alarm."
--
--            #CATEGORY     "Threshold Events."
--            #TYPE         "Variable status upper alarm."
--            #SUMMARY      "Guid %x variable value %i exceeds %i (%i), %s."
--            #ARGUMENTS    {0,2,1,3,4}
--            #SEVERITY     MAJOR
--            #STATE        OPERATIONAL
--
        ::=                 { blueNet2TrapPrefix 11 }

    blueNet2RCMSelftestResultTrap NOTIFICATION-TYPE
        OBJECTS             {
                                blueNet2RcmSelftestResultStr
                            }
        STATUS              current
        DESCRIPTION         "RCM Selftest result."
--
--            #CATEGORY     "Status Events."
--            #TYPE         "RCM Selftest result."
--            #SUMMARY      "RCM Selftest result: %s."
--            #ARGUMENTS    {0}
--            #SEVERITY     INFORMATIONAL
--            #STATE        OPERATIONAL
--
        ::=                 { blueNet2TrapPrefix 12 }

    blueNet2ReconfigAgentTrap NOTIFICATION-TYPE
        OBJECTS             {
                                sysObjectID
                            }
        STATUS              current
        DESCRIPTION         "Agent reconfiguration."
--
--            #CATEGORY     "Status Events."
--            #TYPE         "Agent status."
--            #SUMMARY      "Agent type: %s, Status: configuration has changed."
--            #ARGUMENTS    {0}
--            #SEVERITY     INFORMATIONAL
--            #TIMEINDEX    6
--            #STATE        OPERATIONAL
--
        ::=                 { blueNet2TrapPrefix 98 }

    blueNet2ShutdownAgentTrap NOTIFICATION-TYPE
        OBJECTS             {
                                sysObjectID
                            }
        STATUS              current
        DESCRIPTION         "Agent shutdown."
--
--            #CATEGORY     "Status Events."
--            #TYPE         "Agent status."
--            #SUMMARY      "Agent type: %s, Status: shutdown."
--            #ARGUMENTS    {0}
--            #SEVERITY     SEVERE
--            #TIMEINDEX    6
--            #STATE        NONOPERATIONAL
--
        ::=                 { blueNet2TrapPrefix 99 }


-- *****************************************************************************

--  Compliance Statements  --

    blueNet2Compliances     OBJECT IDENTIFIER ::= { blueNet2Conformance            1 }
    blueNet2Groups          OBJECT IDENTIFIER ::= { blueNet2Conformance            2 }

    blueNet2Compliance      MODULE-COMPLIANCE
        STATUS              current
        DESCRIPTION         "The core compliance statement for all BlueNet2 PDU implementations."
        MODULE              MANDATORY-GROUPS {
                                blueNet2NotificationGroup,
                                blueNet2TrapGroup,
                                blueNet2IdentificationGroup,
                                blueNet2InformationGroup,
                                blueNet2ConfigurationGroup,
                                blueNet2RcmGroup,
                                blueNet2SpdGroup,
                                blueNet2SmtpGroup,
                                blueNet2SnmpGroup,
                                blueNet2NtpGroup,
                                blueNet2ModbusGroup,
                                blueNet2DeviceGroup,
                                blueNet2SensorGroup,
                                blueNet2CircuitGroup,
                                blueNet2SocketGroup,
                                blueNet2VariableGroup,
                                blueNet2MPGroup
                            }

        GROUP               blueNet2NotificationGroup
        DESCRIPTION         "SNMP notification handling."

        GROUP               blueNet2TrapGroup
        DESCRIPTION         "SNMP trap handling."

        GROUP               blueNet2IdentificationGroup
        DESCRIPTION         "base identification handling."

        GROUP               blueNet2InformationGroup
        DESCRIPTION         "base information handling."

        GROUP               blueNet2ConfigurationGroup
        DESCRIPTION         "base configuration handling."

        GROUP               blueNet2NtpGroup
        DESCRIPTION         "Simple Network Time Protocol (NTP) handling."

        GROUP               blueNet2SyslogGroup
        DESCRIPTION         "System log handling."

        GROUP               blueNet2SmtpGroup
        DESCRIPTION         "Simple Mail Transfer Protocol (SMTP) handling."

        GROUP               blueNet2SnmpGroup
        DESCRIPTION         "Simple Network Management Protocol (SNMP) handling."

        GROUP               blueNet2ModbusGroup
        DESCRIPTION         "Modbus ASCII/RTU/TCP handling."

        GROUP               blueNet2DeviceGroup
        DESCRIPTION         "BlueNet2 PDU device handling."

        GROUP               blueNet2SensorGroup
        DESCRIPTION         "BlueNet2 PDU sensor handling."

        GROUP               blueNet2CircuitGroup
        DESCRIPTION         "BlueNet2 PDU circuit handling."

        GROUP               blueNet2PhaseGroup
        DESCRIPTION         "BlueNet2 PDU phase handling."

        GROUP               blueNet2FuseGroup
        DESCRIPTION         "BlueNet2 PDU fuse handling."

        GROUP               blueNet2SocketGroup
        DESCRIPTION         "BlueNet2 PDU socket handling."

        GROUP               blueNet2SocketGroupGroup
        DESCRIPTION         "BlueNet2 PDU socket group handling."

        GROUP               blueNet2VariableGroup
        DESCRIPTION         "BlueNet2 PDU variable handling."

        GROUP               blueNet2MPGroup
        DESCRIPTION         "BlueNet2 Measurement Point handling."

        ::=                 { blueNet2Compliances 1 }

-- *****************************************************************************

--  Conformance Groups  --

    blueNet2TrapGroup       OBJECT-GROUP
        OBJECTS             {
                                blueNet2DeviceGuid,
                                blueNet2DeviceStatus,
                                blueNet2DeviceAlarm,

                                blueNet2SensorGuid,
                                blueNet2SensorStatus,
                                blueNet2SensorAlarm,

                                blueNet2VariableDataGuid,
                                blueNet2VariableDataStatus,
                                blueNet2VariableDataValue,
                                blueNet2VariableSetPointLowerAlarm,
                                blueNet2VariableSetPointLowerWarning,
                                blueNet2VariableSetPointUpperWarning,
                                blueNet2VariableSetPointUpperAlarm,
                                blueNet2VariableAlarm
                            }
        STATUS              current
        DESCRIPTION         "Conformance group for all objects contained in BlueNet2 PDU traps."
        ::=                 { blueNet2Groups    1 }

    blueNet2NotificationGroup NOTIFICATION-GROUP
        NOTIFICATIONS       {
                                blueNet2PduStatusOkNotification,
                                blueNet2PduStatusWarningNotification,
                                blueNet2PduStatusAlarmNotification,

                                blueNet2SensorStatusOkNotification,
                                blueNet2SensorStatusWarningNotification,
                                blueNet2SensorStatusAlarmNotification,

                                blueNet2VariableStatusOkNotification,
                                blueNet2VariableLowerWarningNotification,
                                blueNet2VariableUpperWarningNotification,
                                blueNet2VariableLowerAlarmNotification,
                                blueNet2VariableUpperAlarmNotification,
                                blueNet2ReconfigAgentNotification,
                                blueNet2ShutdownAgentNotification,

                                blueNet2PduStatusOkTrap,
                                blueNet2PduStatusWarningTrap,
                                blueNet2PduStatusAlarmTrap,

                                blueNet2SensorStatusOkTrap,
                                blueNet2SensorStatusWarningTrap,
                                blueNet2SensorStatusAlarmTrap,

                                blueNet2VariableStatusOkTrap,
                                blueNet2VariableLowerWarningTrap,
                                blueNet2VariableUpperWarningTrap,
                                blueNet2VariableLowerAlarmTrap,
                                blueNet2VariableUpperAlarmTrap,

                                blueNet2RCMSelftestResultTrap,

                                blueNet2ReconfigAgentTrap,
                                blueNet2ShutdownAgentTrap
                            }
        STATUS              current
        DESCRIPTION         "Conformance group for BlueNet2 PDU notifications."
        ::=                 { blueNet2Groups    2 }

    blueNet2IdentificationGroup OBJECT-GROUP
        OBJECTS             {
                                blueNet2IdProductVendor,
                                blueNet2IdProductURI,
                                blueNet2IdProductName,
                                blueNet2IdProductPartNr,
                                blueNet2IdProductSNr,
                                blueNet2IdProductDate,
                                blueNet2IdProductFacility,
                                blueNet2IdProductCaps,
                                blueNet2IdProductFwV,
                                blueNet2IdProductHwV,
                                blueNet2IdProductSwV,
                                blueNet2IdProductOsV,
                                blueNet2IdProductArch,
                                blueNet2IdProductMAC
                            }
        STATUS              current
        DESCRIPTION         "Conformance group for BlueNet2 PDU base identfication."
        ::=                 { blueNet2Groups    3 }

    blueNet2InformationGroup OBJECT-GROUP
        OBJECTS             {
                                blueNet2InfoUpTime,
                                blueNet2InfoOverallStatus,
                                blueNet2InfoNumberOfChanges,
                                blueNet2InfoLastChange,
                                blueNet2InfoAccumulatedStatus,
                                blueNet2InfoLoadAverage,
                                blueNet2InfoMessageStatus,
                                blueNet2InfoMessageTime,
                                blueNet2InfoMessageText,
                                blueNet2InfoMessageNumberOfOks,
                                blueNet2InfoMessageNumberOfWarnings,
                                blueNet2InfoMessageNumberOfErrors
                            }
        STATUS              current
        DESCRIPTION         "Conformance group for BlueNet2 PDU base information."
        ::=                 { blueNet2Groups    4 }

    blueNet2ConfigurationGroup OBJECT-GROUP
        OBJECTS             {
                                blueNet2Alias,
                                blueNet2Language,
                                blueNet2FtpAccess,
                                blueNet2FtpPort,
                                blueNet2HttpAccess,
                                blueNet2HttpPort,
                                blueNet2HttpsPort,
                                blueNet2SftpAccess,
                                blueNet2SftpPort,
                                blueNet2SshAccess,
                                blueNet2SshPort,
                                blueNet2TelnetAccess,
                                blueNet2TelnetPort
                            }
        STATUS              current
        DESCRIPTION         "Conformance group for BlueNet2 PDU base configuration."
        ::=                 { blueNet2Groups    5 }

    blueNet2SnmpGroup       OBJECT-GROUP
        OBJECTS             {
                                blueNet2SnmpVersions,
                                blueNet2MaxTrapReceivers,

                                blueNet2TrapReceiverRowStatus,
                                blueNet2TrapReceiverProtocol,
                                blueNet2TrapReceiverAddress,
                                blueNet2TrapReceiverFriendlyName,
                                blueNet2TrapReceiverDescription,
                                blueNet2TrapReceiverCommunity,
                                blueNet2TrapReceiverUsername
                            }
        STATUS              current
        DESCRIPTION         "Conformance group for BlueNet2 PDU SNMP configuration."
        ::=                 { blueNet2Groups    6 }

    blueNet2ModbusGroup     OBJECT-GROUP
        OBJECTS             {
                                blueNet2ModbusVersions,
                                blueNet2ModbusService,
                                blueNet2ModbusTcpPort,
                                blueNet2ModbusSerialMode,
                                blueNet2MaxModbusTcpMasters,

                                blueNet2ModbusTcpRowStatus,
                                blueNet2ModbusTcpAccess,
                                blueNet2ModbusTcpMaster,
                                blueNet2ModbusTcpFriendlyName,
                                blueNet2ModbusTcpDescription
                            }
        STATUS              current
        DESCRIPTION         "Conformance group for blueNet2 PDU modbus configuration."
        ::=                 { blueNet2Groups    7 }

    blueNet2NtpGroup        OBJECT-GROUP
        OBJECTS             {
                                blueNet2DateTime,
                                blueNet2NtpService,
                                blueNet2NtpPort,
                                blueNet2NtpTimeZone,
                                blueNet2MaxNtpServers,

                                blueNet2NtpServerRowStatus,
                                blueNet2NtpServerAddress,
                                blueNet2NtpServerFriendlyName,
                                blueNet2NtpServerDescription
                            }
        STATUS              current
        DESCRIPTION         "Conformance group for BlueNet2 PDU NTP configuration."
        ::=                 { blueNet2Groups    8 }

    blueNet2SmtpGroup       OBJECT-GROUP
        OBJECTS             {
                                blueNet2SmtpService,
                                blueNet2SmtpPort,
                                blueNet2SmtpServer,
                                blueNet2SmtpAuth,
                                blueNet2SmtpUsername,
                                blueNet2SmtpPassword,
                                blueNet2SmtpFrom,
                                blueNet2SmtpReply,
                                blueNet2MaxSmtpReceivers,

                                blueNet2SmtpReceiverRowStatus,
                                blueNet2SmtpReceiverAddress,
                                blueNet2SmtpReceiverFriendlyName,
                                blueNet2SmtpReceiverDescription
                            }
        STATUS              current
        DESCRIPTION         "Conformance group for BlueNet2 PDU SMTP configuration."
        ::=                 { blueNet2Groups    9 }

    blueNet2SyslogGroup     OBJECT-GROUP
        OBJECTS             {
                                blueNet2SyslogService,
                                blueNet2SyslogFacility,
                                blueNet2MaxSyslogServers,

                                blueNet2SyslogServerRowStatus,
                                blueNet2SyslogServerAddress,
                                blueNet2SyslogServerPort,
                                blueNet2SyslogServerFriendlyName,
                                blueNet2SyslogServerDescription,
                                blueNet2SyslogServerProtocol
                            }
        STATUS              current
        DESCRIPTION         "Conformance group for BlueNet2 PDU syslog operations."
        ::=                 { blueNet2Groups    10 }

    blueNet2DeviceGroup     OBJECT-GROUP
        OBJECTS             {
                                blueNet2OverallDeviceStatus,
                                blueNet2NumberOfDevices,
                                blueNet2LastChangeOverallDeviceStatus,
                                blueNet2LastChangeNumberOfDevices,
                                blueNet2LastChangeDeviceSettings,
                                blueNet2LastChangeDevices,
                                blueNet2DevicesAccumulatedStatus,

                                blueNet2DeviceGuid,
                                blueNet2DeviceName,
                                blueNet2DeviceFriendlyName,
                                blueNet2DeviceDescription,
                                blueNet2DeviceType,
                                blueNet2DeviceStatus,
                                blueNet2DeviceAlarm,
                                blueNet2DeviceLastChange,
                                blueNet2DeviceEntPhysicalIndex,
                                blueNet2DevicePartNr,
                                blueNet2DeviceSNr,
                                blueNet2DeviceFwV,
                                blueNet2DeviceHwV,
                                blueNet2DeviceSwV,
                                blueNet2DeviceOsV,
                                blueNet2DeviceMAC,
                                blueNet2DeviceNumberOfSensors,
                                blueNet2DeviceNumberOfCircuits,
                                blueNet2DeviceNumberOfPhases,
                                blueNet2DeviceNumberOfFuses,
                                blueNet2DeviceNumberOfSockets,
                                blueNet2DeviceNumberOfRCMs,
                                blueNet2DeviceNumberOfVars,
                                blueNet2DeviceLocation,
                                blueNet2DeviceProductDate,
                                blueNet2DeviceModbusAddr
                            }
        STATUS              current
        DESCRIPTION         "Conformance group for BlueNet2 PDU device information."
        ::=                 { blueNet2Groups    11 }


    blueNet2SensorGroup     OBJECT-GROUP
        OBJECTS             {
                                blueNet2OverallSensorStatus,
                                blueNet2NumberOfSensors,
                                blueNet2LastChangeOverallSensorStatus,
                                blueNet2LastChangeNumberOfSensors,
                                blueNet2LastChangeSensorSettings,
                                blueNet2LastChangeSensors,
                                blueNet2SensorsAccumulatedStatus,

                                blueNet2SensorGuid,
                                blueNet2SensorName,
                                blueNet2SensorFriendlyName,
                                blueNet2SensorDescription,
                                blueNet2SensorType,
                                blueNet2SensorStatus,
                                blueNet2SensorAlarm,
                                blueNet2SensorLastChange,
                                blueNet2SensorEntPhysicalIndex,
                                blueNet2SensorNumberOfVars,
                                blueNet2SensorHwV,
                                blueNet2SensorFwV,
                                blueNet2SensorSNr,

                                blueNet2SensorVariableGuid,
                                blueNet2SensorVariableName,
                                blueNet2SensorVariableFriendlyName,
                                blueNet2SensorVariableDescription,
                                blueNet2SensorVariableGPIOMode,
                                blueNet2SensorVariableGPIOSwitch,
                                blueNet2SensorVariableGPIOState
                            }
        STATUS              current
        DESCRIPTION         "Conformance group for BlueNet2 PDU sensor information."
        ::=                 { blueNet2Groups    12 }


    blueNet2CircuitGroup    OBJECT-GROUP
        OBJECTS             {
                                blueNet2OverallCircuitStatus,
                                blueNet2NumberOfCircuits,
                                blueNet2LastChangeOverallCircuitStatus,
                                blueNet2LastChangeNumberOfCircuits,
                                blueNet2LastChangeCircuitSettings,
                                blueNet2LastChangeCircuits,

                                blueNet2CircuitGuid,
                                blueNet2CircuitName,
                                blueNet2CircuitFriendlyName,
                                blueNet2CircuitDescription,
                                blueNet2CircuitType,
                                blueNet2CircuitStatus,
                                blueNet2CircuitNumberOfPhases
                            }
        STATUS              current
        DESCRIPTION         "Conformance group for BlueNet2 PDU circuit information."
        ::=                 { blueNet2Groups    13 }


    blueNet2PhaseGroup      OBJECT-GROUP
        OBJECTS             {
                                blueNet2PhaseGuid,
                                blueNet2PhaseName,
                                blueNet2PhaseFriendlyName,
                                blueNet2PhaseDescription,
                                blueNet2PhaseStatus,
                                blueNet2PhaseNumberOfFuses
                            }
        STATUS              current
        DESCRIPTION         "Conformance group for BlueNet2 PDU phase information."
        ::=                 { blueNet2Groups    14 }


    blueNet2FuseGroup       OBJECT-GROUP
        OBJECTS             {
                                blueNet2FuseGuid,
                                blueNet2FuseName,
                                blueNet2FuseFriendlyName,
                                blueNet2FuseDescription,
                                blueNet2FuseType,
                                blueNet2FuseStatus,
                                blueNet2FuseNumberOfSockets
                            }
        STATUS              current
        DESCRIPTION         "Conformance group for BlueNet2 PDU fuse information."
        ::=                 { blueNet2Groups    15 }


    blueNet2SocketGroup     OBJECT-GROUP
        OBJECTS             {
                                blueNet2SocketGuid,
                                blueNet2SocketName,
                                blueNet2SocketFriendlyName,
                                blueNet2SocketDescription,
                                blueNet2SocketType,
                                blueNet2SocketStatus,
                                blueNet2SocketMode,
                                blueNet2SocketIdentify,
                                blueNet2SocketMemberIndex
                            }
        STATUS              current
        DESCRIPTION         "Conformance group for BlueNet2 PDU socket information."
        ::=                 { blueNet2Groups    16 }


    blueNet2RcmGroup        OBJECT-GROUP
        OBJECTS             {
                                blueNet2RcmGuid,
                                blueNet2RcmName,
                                blueNet2RcmFriendlyName,
                                blueNet2RcmDescription,
                                blueNet2RcmType,
                                blueNet2RcmStatus
                            }
        STATUS              current
        DESCRIPTION         "Conformance group for BlueNet2 PDU RCM information."
        ::=                 { blueNet2Groups    17 }


    blueNet2SocketGroupGroup OBJECT-GROUP
        OBJECTS             {
                                blueNet2OverallSocketGroupStatus,
                                blueNet2NumberOfSocketGroups,
                                blueNet2LastChangeOverallSocketGroupStatus,
                                blueNet2LastChangeNumberOfSocketGroups,
                                blueNet2LastChangeSocketGroupSettings,
                                blueNet2LastChangeSocketGroups,
                                blueNet2SocketGroupsAccumulatedStatus,
                                blueNet2SocketGroupsInUse,
                                blueNet2MaxSocketGroups,

                                blueNet2SocketGroupRowStatus,
                                blueNet2SocketGroupGuid,
                                blueNet2SocketGroupName,
                                blueNet2SocketGroupFriendlyName,
                                blueNet2SocketGroupDescription,
                                blueNet2SocketGroupStatus,
                                blueNet2SocketGroupMode,
                                blueNet2SocketGroupIdentify,
                                blueNet2SocketGroupEntPhysicalIndex,
                                blueNet2SocketGroupAccumulatedStatus,
                                blueNet2SocketGroupMembers
                            }
        STATUS              current
        DESCRIPTION         "Conformance group for BlueNet2 PDU socket groups."
        ::=                 { blueNet2Groups    18 }

    blueNet2VariableGroup   OBJECT-GROUP
        OBJECTS             {
                                blueNet2OverallVariableStatus,
                                blueNet2NumberOfVariables,
                                blueNet2LastChangeOverallVariableStatus,
                                blueNet2LastChangeNumberOfVariables,
                                blueNet2LastChangeVariableSettings,
                                blueNet2LastChangeVariableStatus,
                                blueNet2VariablesAccumulatedStatus,
                                blueNet2NumberOfChangesVariableScaling,
                                blueNet2LastChangeVariableScaling,
                                blueNet2LastChangeVariableReset,

                                blueNet2VariableGuid,
                                blueNet2VariableName,
                                blueNet2VariableFriendlyName,
                                blueNet2VariableDescription,
                                blueNet2VariableType,
                                blueNet2VariableStatus,
                                blueNet2VariableAlarm,
                                blueNet2VariableScaling,
                                blueNet2VariableUnit,
                                blueNet2VariableSetPoint,
                                blueNet2VariableMode,
                                blueNet2VariableEntPhysicalIndex,

                                blueNet2VariableSetPointType,
                                blueNet2VariableSetPointMinValue,
                                blueNet2VariableSetPointMaxValue,
                                blueNet2VariableSetPointLowerAlarm,
                                blueNet2VariableSetPointLowerWarning,
                                blueNet2VariableSetPointUpperWarning,
                                blueNet2VariableSetPointUpperAlarm,
                                blueNet2VariableSetPointHysteresis,
                                blueNet2VariableSetPointRcmACUpperAlarmThreshold,
                                blueNet2VariableSetPointRcmACUpperAlarmGradient,
                                blueNet2VariableSetPointRcmACUpperWarningThreshold,
                                blueNet2VariableSetPointRcmACUpperWarningGradient,

                                blueNet2VariableDataType,
                                blueNet2VariableDataStatus,
                                blueNet2VariableDataValue,
                                blueNet2VariableDataDateTime,

                                blueNet2VariableDataByTypeType,
                                blueNet2VariableDataByTypeStatus,
                                blueNet2VariableDataByTypeValue,
                                blueNet2VariableDataByTypeDateTime,

                                blueNet2VariableDataByStateType,
                                blueNet2VariableDataByStateStatus,
                                blueNet2VariableDataByStateValue,
                                blueNet2VariableDataByStateDateTime,

                                blueNet2VariableDataBySourceType,
                                blueNet2VariableDataBySourceStatus,
                                blueNet2VariableDataBySourceValue,
                                blueNet2VariableDataBySourceDateTime
                            }
        STATUS              current
        DESCRIPTION         "Conformance group for BlueNet2 PDU variable information."
        ::=                 { blueNet2Groups    19 }


    blueNet2MPGroup         OBJECT-GROUP
        OBJECTS             {
                                blueNet2MPGuid,
                                blueNet2MPName,
                                blueNet2MPFriendlyName,
                                blueNet2MPState,
                                blueNet2MPTimeStamp
                            }
        STATUS              current
        DESCRIPTION         "Conformance group for BlueNet2 Measurement Point information."
        ::=                 { blueNet2Groups    20 }

    blueNet2SpdGroup        OBJECT-GROUP
        OBJECTS             {
                                blueNet2SpdGuid,
                                blueNet2SpdName,
                                blueNet2SpdFriendlyName,
                                blueNet2SpdDescription,
                                blueNet2SpdType,
                                blueNet2SpdStatus
                            }
        STATUS              current
        DESCRIPTION         "Conformance group for BlueNet2 PDU SPD information."
        ::=                 { blueNet2Groups    21 }



-- *****************************************************************************

--  Capabilities --

--  please refer to BACHMANN-BLUENET2-CAPABILITY-MIB definitions --

-- *****************************************************************************
END
