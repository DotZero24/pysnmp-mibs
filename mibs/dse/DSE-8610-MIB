DSE-8610-MIB DEFINITIONS ::= BEGIN

IMPORTS
    OBJECT-TYPE, NOTIFICATION-TYPE, MODULE-IDENTITY,
    Integer32, Unsigned32, enterprises, Counter32, TimeTicks
        FROM SNMPv2-SMI
	TEXTUAL-CONVENTION
		FROM SNMPv2-TC

    MODULE-COMPLIANCE, OBJECT-GROUP, NOTIFICATION-GROUP
	FROM SNMPv2-CONF;

dseVendor MODULE-IDENTITY
    LAST-UPDATED "201708150000Z"
    ORGANIZATION "DEEP SEA ELECTRONICS PLC"
    CONTACT-INFO
	"DEEP SEA ELECTRONICS PLC contact info:
         post:  Highfield House,
         		Hunmanby Industrial Estate,
         		Hunmanby, North Yorkshire
         		YO14 0PH England

         email:    info@deepseaplc.com"

    DESCRIPTION
	"v1.7 Mib file for the DSE 8610 module"

    REVISION	 "201708150000Z"
    DESCRIPTION
	"Added missing Electrical Trip from 8660 alarm"

    REVISION	 "201708090000Z"
    DESCRIPTION
	"Fixed scaling for engOilPress instrument"

    REVISION	 "201706060000Z"
    DESCRIPTION
	"Fixed spelling mistakes for instrumentation descriptions"

    REVISION	 "201706060000Z"
    DESCRIPTION
	"Added additional MSC Named alarms"

    REVISION	 "201703150000Z"
    DESCRIPTION
	"Amended bus table id to 9"

    REVISION	 "201703130000Z"
    DESCRIPTION
	"Removed Mains instrumentation and added Bus Items"

    REVISION	 "201702170000Z"
    DESCRIPTION
	"Updates to fix conformity errors"

    REVISION	 "201702160000Z"
    DESCRIPTION
	"First draft MIB file for DSE 8610 MKII Auto Start Control Module"

    ::= { enterprises 41385 }


-- ************************************* Product ***************************************
dseProduct	OBJECT IDENTIFIER ::= { dseVendor 1 }
dse8610		OBJECT IDENTIFIER ::= { dseProduct 5 }


-- ************************************* Instrumentation Section *************************************
dseInstrumentsSection           OBJECT IDENTIFIER ::= { dse8610 1 }
dse8610Control 			        OBJECT IDENTIFIER ::= { dse8610 2 }


-- ************************************* TEXTUAL CONVENTIONS *************************************


ChargeVoltsDiv10 ::= TEXTUAL-CONVENTION
    DISPLAY-HINT "d-1"
    STATUS       current
    DESCRIPTION  "Charge Voltage. Fixed point, one decimal"
    SYNTAX       Unsigned32 (0..40)

FreqDiv10 ::= TEXTUAL-CONVENTION
    DISPLAY-HINT "d-1"
    STATUS       current
    DESCRIPTION  "Frequency. Fixed point, one decimal"
    SYNTAX       Unsigned32 (0..70)

VoltsLNDiv10 ::= TEXTUAL-CONVENTION
    DISPLAY-HINT "d-1"
    STATUS       current
    DESCRIPTION  "Phase to neutral Voltage. Fixed point, one decimal"
    SYNTAX       Unsigned32 (0..18000)

VoltsLLDiv10 ::= TEXTUAL-CONVENTION
    DISPLAY-HINT "d-1"
    STATUS       current
    DESCRIPTION  "Phase to phase Voltage. Fixed point, one decimal"
    SYNTAX       Unsigned32 (0..30000)

CurrentDiv10 ::= TEXTUAL-CONVENTION
    DISPLAY-HINT "d-1"
    STATUS       current
    DESCRIPTION  "Current. Fixed point, one decimal"
    SYNTAX       Unsigned32 (0..99999)

RPMDiv1000 ::= TEXTUAL-CONVENTION
    DISPLAY-HINT "d-3"
    STATUS       current
    DESCRIPTION  "Rev per minute. Fixed point, one decimal"
    SYNTAX       Unsigned32 (0..4211)

AirFilterDiv10 ::= TEXTUAL-CONVENTION
    DISPLAY-HINT "d-1"
    STATUS       current
    DESCRIPTION  "Air filter. Fixed point, one decimal"
    SYNTAX       Unsigned32 (0..125)

ElectricalPotentialDiv10 ::= TEXTUAL-CONVENTION
    DISPLAY-HINT "d-1"
    STATUS       current
    DESCRIPTION  "Electrical potential. Fixed point, one decimal"
    SYNTAX       Unsigned32

AverageFuelDiv100 ::= TEXTUAL-CONVENTION
    DISPLAY-HINT "d-2"
    STATUS       current
    DESCRIPTION  "Average Fuel. Fixed point, two decimals"
    SYNTAX       Unsigned32 (0..10000)

PowerFactorDiv100 ::= TEXTUAL-CONVENTION
    DISPLAY-HINT "d-2"
    STATUS       current
    DESCRIPTION  "Power factor. Fixed point, two decimals"
    SYNTAX       Integer32 (-100..100)

PowerPCDiv10 ::= TEXTUAL-CONVENTION
    DISPLAY-HINT "d-1"
    STATUS       current
    DESCRIPTION  "Power. Fixed point, one decimal"
    SYNTAX       Integer32 (-999..999)

VAPCDiv10 ::= TEXTUAL-CONVENTION
    DISPLAY-HINT "d-1"
    STATUS       current
    DESCRIPTION  "VPAC. Fixed point, one decimal"
    SYNTAX       Unsigned32 (0..999)

PowerPCDiv100 ::= TEXTUAL-CONVENTION
    DISPLAY-HINT "d-2"
    STATUS       current
    DESCRIPTION  "Power. Fixed point, two decimals"
    SYNTAX       Unsigned32 (0..99999)

CrankPressureDiv100 ::= TEXTUAL-CONVENTION
    DISPLAY-HINT "d-2"
    STATUS       current
    DESCRIPTION  "Pressure. Fixed point, two decimals"
    SYNTAX       Integer32 (-25000..25000)

InjectorRailPressureDiv100 ::= TEXTUAL-CONVENTION
    DISPLAY-HINT "d-2"
    STATUS       current
    DESCRIPTION  "Injector Rail Pressure. Fixed point, two decimals"
    SYNTAX       Unsigned32 (0..2509)

OilPressureDiv100 ::= TEXTUAL-CONVENTION
    DISPLAY-HINT "d-2"
    STATUS       current
    DESCRIPTION  "Pressure. Fixed point, two decimals"
    SYNTAX       Unsigned32 (0..10000)


-- ************************************* TRAP/NOTIFICATION MANAGEMENT SECTION *************************************

dse8610AlarmsMngr OBJECT IDENTIFIER ::= { dse8610 150 }

dse8610AlarmStateTable OBJECT-TYPE
	SYNTAX		SEQUENCE OF DSE8610AlarmStateSequence
	MAX-ACCESS	not-accessible
	STATUS		current
	DESCRIPTION
		"Alarms state table"
	::= { dse8610AlarmsMngr 1 }

DSE8610AlarmStateSequence ::= SEQUENCE {
	dse8610AlarmKeyID		Integer32,
	dse8610SeqNr			Counter32,
	dse8610TrapID			Integer32,
	dse8610TrapState		Integer32,
--	dse8610TrapOrigin		Integer32,
	dse8610TrapTimeStamp	TimeTicks
}

dse8610AlarmStateEntry OBJECT-TYPE
	SYNTAX		DSE8610AlarmStateSequence
	MAX-ACCESS	not-accessible
	STATUS		current
	DESCRIPTION
		"Entry in the alarms state table,
		indexed by Key ID (1..3)"
	INDEX
--		{ dse8610TrapID }
		{ dse8610AlarmKeyID }
	::= { dse8610AlarmStateTable 1 }

dse8610AlarmKeyID OBJECT-TYPE
  SYNTAX  Integer32 (1..100)
  MAX-ACCESS  not-accessible
  STATUS  current
  DESCRIPTION "Notification Key ID"
	::= { dse8610AlarmStateEntry 1 }

dse8610SeqNr  OBJECT-TYPE
	SYNTAX		Counter32
	MAX-ACCESS	read-only
	STATUS		current
	DESCRIPTION
		"Alarm sequence number"
--	::= { dse8610AlarmStateEntry 1 }
	::= { dse8610AlarmStateEntry 2 }

dse8610TrapID OBJECT-TYPE
--	SYNTAX		Integer32 (0x1000..0x6FFF)
	SYNTAX		Integer32 (4096..28671)
	MAX-ACCESS	read-only
	STATUS		current
	DESCRIPTION
		"Alarm identification number"
--	::= { dse8610AlarmStateEntry 2 }
	::= { dse8610AlarmStateEntry 3 }

dse8610TrapState OBJECT-TYPE
	SYNTAX		INTEGER {
				alarmNormal (1),
				alarmWarning (2),
				alarmElectricalTrip (3),
				alarmShutdown (4),
				modeStop (5),
				modeManual (6),
				modeTest (7),
				modeAuto (8),
				modeConfig (9),
				singleEventNotification (10),
				ecuLampOff (11),
				ecuLampFlashSlow (12),
				ecuLampFlashFast (13),
				ecuLampOnSteady (14),
				fuelLevelUsageNormal (15),
				fuelLevelEndFill (16),
				fuelLevelStartFill (17),
				fuelLevelUsageTheftAlarm (18),
				fuelLevelUsageLevelAlarm (19)
			}
	MAX-ACCESS	read-write
	STATUS		current
	DESCRIPTION
		"Alarm state. Trap 'alarmNormal' clears former alarms."
	::= { dse8610AlarmStateEntry 4 }

--dse8610TrapOrigin OBJECT-TYPE
--	SYNTAX		Integer32 (0..100)
--	MAX-ACCESS	read-only
--	STATUS		current
--	DESCRIPTION
--		"Alarm identification origin"
--	::= { dse8610AlarmStateEntry 4 }
--	::= { dse8610AlarmStateEntry 5 }

dse8610TrapTimeStamp OBJECT-TYPE
	SYNTAX		TimeTicks
	MAX-ACCESS	read-only
	STATUS		current
	DESCRIPTION
		"Trap timestamp in UNIX format - seconds since Jan 01 1970. (UTC)."
--	::= { dse8610AlarmStateEntry 5 }
	::= { dse8610AlarmStateEntry 6 }

--  ************************************* Control *************************************

dseKeypressTable  OBJECT-TYPE
    SYNTAX  SEQUENCE OF DseKeypressEntry
    MAX-ACCESS  not-accessible
    STATUS  current
    DESCRIPTION
     "Mains Table"
    ::= { dse8610Control 1 }

dseKeypressEntry OBJECT-TYPE
    SYNTAX  DseKeypressEntry
    MAX-ACCESS  not-accessible
    STATUS  current
    DESCRIPTION
     "Key Press Entry"
    INDEX { keypressKeyID }
    ::= { dseKeypressTable  1 }

DseKeypressEntry ::= SEQUENCE {
  keypressKeyID         INTEGER,
  keypress           OCTET STRING
  }

keypressKeyID OBJECT-TYPE
  SYNTAX  Integer32 (1..2147483647)
  MAX-ACCESS  not-accessible
  STATUS  current
  DESCRIPTION "Keypress Key ID"
  ::= { dseKeypressEntry 1 }


keypress OBJECT-TYPE
  SYNTAX  OCTET STRING
  MAX-ACCESS  read-write
  STATUS  current
  DESCRIPTION "Valid values: ACT_ON, ACT_MAN, ACT_TEST, ACT_AUTO, ACT_OFF, ACT_GEN, ACT_MAINS, ACT_BUZZ, ACT_AL_RESET, ACT_MANRESTORE, NO_ACT"
  ::= { dseKeypressEntry 2 }

--  ************************************* Instruments *************************************

generatorTable OBJECT-TYPE
    SYNTAX  SEQUENCE OF GeneratorEntry
    MAX-ACCESS  not-accessible
    STATUS  current
    DESCRIPTION
     "Generator Table"
    ::= { dseInstrumentsSection 2 }

engineTable OBJECT-TYPE
    SYNTAX  SEQUENCE OF EngineEntry
    MAX-ACCESS  not-accessible
    STATUS  current
    DESCRIPTION
     "Engine Table"
    ::= { dseInstrumentsSection 3 }

busTable OBJECT-TYPE
    SYNTAX  SEQUENCE OF BusTableEntry
    MAX-ACCESS  not-accessible
    STATUS  current
    DESCRIPTION
     "Bus Table"
    ::= { dseInstrumentsSection 9 }

gencommSection           OBJECT IDENTIFIER ::= { dseInstrumentsSection 4 }

gencommP166Table OBJECT-TYPE
    SYNTAX  SEQUENCE OF GencommP166Entry
    MAX-ACCESS  not-accessible
    STATUS  current
    DESCRIPTION
     "Gencomm Page 166 Table"
    ::= { gencommSection 1 }

gencommP167Table OBJECT-TYPE
    SYNTAX  SEQUENCE OF GencommP167Entry
    MAX-ACCESS  not-accessible
    STATUS  current
    DESCRIPTION
     "Gencomm Page 167 Table"
    ::= { gencommSection 2 }

gencommP168Table OBJECT-TYPE
    SYNTAX  SEQUENCE OF GencommP168Entry
    MAX-ACCESS  not-accessible
    STATUS  current
    DESCRIPTION
     "Gencomm Page 168 Table"
    ::= { gencommSection 3 }

gencommP169Table OBJECT-TYPE
    SYNTAX  SEQUENCE OF GencommP169Entry
    MAX-ACCESS  not-accessible
    STATUS  current
    DESCRIPTION
     "Gencomm Page 169 Table"
    ::= { gencommSection 4 }

generatorEntry OBJECT-TYPE
    SYNTAX  GeneratorEntry
    MAX-ACCESS  not-accessible
    STATUS  current
    DESCRIPTION
     "Generator Entry"
    INDEX { genKeyID }
    ::= { generatorTable   1 }

engineEntry OBJECT-TYPE
    SYNTAX  EngineEntry
    MAX-ACCESS  not-accessible
    STATUS  current
    DESCRIPTION
     "Engine Entry"
    INDEX { engKeyID }
    ::= { engineTable   1 }

busTableEntry OBJECT-TYPE
    SYNTAX  BusTableEntry
    MAX-ACCESS  not-accessible
    STATUS  current
    DESCRIPTION
     "Bus Table Entry"
    INDEX { busKeyId }
    ::= { busTable   1 }

gencommP166Entry OBJECT-TYPE
    SYNTAX  GencommP166Entry
    MAX-ACCESS  not-accessible
    STATUS  current
    DESCRIPTION
     "Gencomm Page 166 Entry"
    INDEX { gencommP166KeyID }
    ::= { gencommP166Table   1 }

gencommP167Entry OBJECT-TYPE
    SYNTAX  GencommP167Entry
    MAX-ACCESS  not-accessible
    STATUS  current
    DESCRIPTION
     "Gencomm Page 167 Entry"
    INDEX { gencommP167KeyID }
    ::= { gencommP167Table   1 }

gencommP168Entry OBJECT-TYPE
    SYNTAX  GencommP168Entry
    MAX-ACCESS  not-accessible
    STATUS  current
    DESCRIPTION
     "Gencomm Page 168 Entry"
    INDEX { gencommP168KeyID }
    ::= { gencommP168Table   1 }

gencommP169Entry OBJECT-TYPE
    SYNTAX  GencommP169Entry
    MAX-ACCESS  not-accessible
    STATUS  current
    DESCRIPTION
     "Gencomm Page 169 Entry"
    INDEX { gencommP169KeyID }
    ::= { gencommP169Table   1 }

GeneratorEntry ::= SEQUENCE {
	genKeyID            Integer32,			--
	genFreq             FreqDiv10,	        --
	genL1Volts          VoltsLNDiv10,	    --
	genL2Volts          VoltsLNDiv10,	    --
	genL3Volts          VoltsLNDiv10,	    --
	genL1L2Volts        VoltsLLDiv10,	    --
	genL2L3Volts        VoltsLLDiv10,	    --
	genL3L1Volts        VoltsLLDiv10,	    --
	genL1Current        CurrentDiv10,	    --
	genL2Current        CurrentDiv10,	    --
	genL3Current        CurrentDiv10,	    --
	genECurrent         CurrentDiv10,	    --
	genL1Watts          Integer32,	        --
	genL2Watts          Integer32,	        --
	genL3Watts          Integer32,	        --
	genRotation         Integer32,	        --
	genWattsTotal       Integer32,	        --
	genL1VA             Unsigned32,	        --
	genL2VA             Unsigned32,	        --
	genL3VA             Unsigned32,	        --
	genTotalVA          Unsigned32,	        --
	genL1VAr            Integer32,	        --
	genL2VAr            Integer32,	        --
	genL3VAr            Integer32,	        --
	genTotalVAr         Integer32,	        --
	genPowerFactorL1    PowerFactorDiv100,	--
	genPowerFactorL2    PowerFactorDiv100,	--
	genPowerFactorL3    PowerFactorDiv100,	--
	genAvgPowerFactor   PowerFactorDiv100,	--
	genPowerTotalPC     Integer32,	        --
	genVARTotalPC       Integer32,	        --
	genPhase1           Unsigned32,         --
	genPhase2           Unsigned32,         --
	genPhase3           Unsigned32,         --
	genPhaseTotal       Unsigned32,         --
	genPowerL1PC		Integer32,         	--
	genPowerL2PC		Integer32,         	--
	genPowerL3PC		Integer32,         	--
	genVoltageLNAvg     VoltsLNDiv10,	    --
	genVoltageLNDiff    VoltsLNDiv10,	    --
	genVoltageLNMin     VoltsLNDiv10,	    --
	genVoltageLNMax     VoltsLNDiv10,	    --
	genVoltageLLAvg     VoltsLLDiv10,	    --
	genVoltageLLDiff    VoltsLLDiv10,	    --
	genVoltageLLMin     VoltsLLDiv10,	    --
	genVoltageLLMax     VoltsLLDiv10,	    --
	genCurrentAve		CurrentDiv10,		--
	genCurrentDif		CurrentDiv10,		--
	genCurrentMin		CurrentDiv10,		--
	genCurrentMax		CurrentDiv10,		--
	genPowerTotalAvgPC  PowerPCDiv100,	    --
	genPowerTotalDiffPC PowerPCDiv10,	    --
	genPowerTotalMinPC  PowerPCDiv10,	    --
	genPowerTotalMaxPC  PowerPCDiv10,	    --
	genVATotalAvgPC     VAPCDiv10,	        --
	genVADiffPC         VAPCDiv10,	        --
	genVAMinPC          VAPCDiv10,	        --
	genVAMaxPC          VAPCDiv10,	        --
	genVARTotalAvgPC    PowerPCDiv10,	    --
	genVARDiffPC        PowerPCDiv10,	    --
	genVARMinPC         PowerPCDiv10,	    --
	genVARMaxPC         PowerPCDiv10,	    --
	genPFTotalAvgPC     PowerFactorDiv100,	--
	genPFDiffPC         PowerFactorDiv100,	--
	genPFMinPC          PowerFactorDiv100,	--
	genPFMaxPC          PowerFactorDiv100	--
}

EngineEntry ::= SEQUENCE {
	engKeyID                Integer32,					--
	engOilPress             OilPressureDiv100,   	            --
	engTemp         	    Integer32,		            --
	engOilTemp              Integer32,	                --
	engFuelLevel            Unsigned32,	                --
	engChargeAltVolts       ChargeVoltsDiv10,	        --
	engBatteryVolts       	ChargeVoltsDiv10,	        --
	engSpeedDisplay         Unsigned32,                 --
	engCoolantP1            Unsigned32,                 --
	engCoolantP2            Unsigned32,                 --
	engFuelP1               Unsigned32,                 --
	engFuelP2               Unsigned32,                 --
	engTurboP1              Unsigned32,                 --
	engTurboP2              Unsigned32,                 --
	engInMainfoldT1         Unsigned32,                 --
	engInMainfoldT2         Integer32,	                --
	engExhaustT1            Integer32,	                --
	engExhaustT2            Integer32,	                --
	engFuelConsumption      AverageFuelDiv100,	        --
	engWaterInFuel          Unsigned32,	                --
	engCANBitData           Unsigned32,	                --
	engAtmosphericP         Unsigned32,	                --
	engFuelT                Integer32,	                --
	engFuelLevelUnits       Unsigned32,	                --
	engTankFuelUnits        Unsigned32,	                --
	engAfttrt1FuelUSed      Unsigned32,	                --
	engAfttrt1ExGasT1       Integer32,	                --
	engAfttrt1ExGasT3       Integer32,	                --
	engRefTorque            Unsigned32,	                --
	engPerTorque            Integer32,	                --
	engDemandPerTorque      Integer32,	                --
	engPCLoadAtSpeed        Unsigned32,	                --
	engAccelPedalPos        Unsigned32,	                --
	engNomFricPerTorque     Integer32,	                --
	engOilLevel         	Unsigned32,	                --
	engCrankCasePress       CrankPressureDiv100,	    --
	engCoolantLevel         Integer32,	                --
	engInjectorRail1        InjectorRailPressureDiv100,	--
	engInjectorRail2        InjectorRailPressureDiv100,	--
	engEgrFlowRate          Unsigned32,	                --
	engPreFilOilPress       Unsigned32,	                --
	engInstBreakPower       Unsigned32,	                --
	engExhGasPort1Temp      Integer32,	                --
	engExhGasPort2Temp      Integer32,	                --
	engExhGasPort3Temp      Integer32,	                --
	engExhGasPort4Temp      Integer32,	                --
	engExhGasPort5Temp      Integer32,	                --
	engExhGasPort6Temp      Integer32,	                --
	engExhGasPort7Temp      Integer32,	                --
	engExhGasPort8Temp      Integer32,	                --
	engExhGasPort9Temp      Integer32,	                --
	engExhGasPort10Temp     Integer32,	                --
	engExhGasPort11Temp     Integer32,	                --
	engExhGasPort12Temp     Integer32,	                --
	engExhGasPort13Temp     Integer32,	                --
	engExhGasPort14Temp     Integer32,	                --
	engExhGasPort15Temp     Integer32,	                --
	engExhGasPort16Temp     Integer32,	                --
	engIntercoolerTemp      Integer32,	                --
	engTurboOilTemp         Unsigned32,	                --
	engECUTemp              Integer32,	                --
	engFanSpeed             Unsigned32,	                --
	engTotalRev             RPMDiv1000,	                --
	engAirInPress           Unsigned32,	                --
	engAirFilDiffPres       AirFilterDiv10,	        	--
	engTrapInPress          Unsigned32,	                --
	engTurboP3              Unsigned32,	                --
	engTurboP4              Unsigned32,	                --
	engInMainfoldT3         Integer32,	                --
	engInMainfoldT4         Integer32,	                --
	engInMainfoldT5         Integer32,	                --
	engInMainfoldT6         Integer32,	                --
	engTripFuel             Unsigned32,	                --
	engElectPotential       ElectricalPotentialDiv10,	--
	engPGIEngType           Unsigned32,	                --
	engPGIVerNum            Unsigned32,	                --
	engDPTCFilLampCmd       INTEGER,	                --
	engExhSysHighTemp       INTEGER,	                --
	engDPTCActRegFor        INTEGER,	                --
	engSDWNWaitStart        INTEGER,	                --
	engSDWNProtection       Unsigned32,	                --
	engSDWNApproaching      Unsigned32,	                --
	engOperatingState       Unsigned32,	                --
	engSDWNClOverride       Unsigned32,	                --
	engBattleshortOvr       Unsigned32,	                --
	engModHours             Unsigned32,	                --
	engModOilPress          Unsigned32,	                --
	engModCoolTemp          Unsigned32,	                --
	engModRPM               Unsigned32,	                --
	engModChargeAlt         Unsigned32,	                --
	engModSpeedFeed         Unsigned32,	                --
	engModFreqAdj           Unsigned32,	                --
	engAlarmWarn            Unsigned32,	                --
	engAlarmShdwn           Unsigned32,	                --
	engAlarmElectr          Unsigned32,	                --
	engAmberStopLamp        Unsigned32,	                --
	engAmberLampFlash       Unsigned32,	                --
	engRedStopLamp          Unsigned32,	                --
	engRedLampFlash         Unsigned32,	                --
	engProtLamp             Unsigned32,	                --
	engProtLampFlash        Unsigned32,	                --
	engMalfLamp             Unsigned32,	                --
	engMalfLampFlash        Unsigned32,	                --
	engBattSwitched         Unsigned32,	                --
	engChargPotential       Unsigned32,	                --
	engCharAltCurr          Unsigned32,	                --
	engBattCurr             Unsigned32,	                --
	engTorqueMode           Unsigned32,	                --
	engStarterMode          Unsigned32,	                --
	engCIStatus             Unsigned32,	                --
	engDemandedSpeed        Unsigned32,	                --
	engSpeedFBUp            Unsigned32,	                --
	engSpeedFBDown          Unsigned32,	                --
	engSpeedFailMode        Unsigned32,	                --
	engCurrSDSrc            Unsigned32,	                --
	engFbackSDCAN           Unsigned32,	                --
	engFbackSDAnalog        Unsigned32,	                --
	engFailureCodes         Unsigned32,	                --
	engActDrop              Unsigned32,	                --
	engStartStatus          Unsigned32,	                --
	engProtOrStatus         Unsigned32,	                --
	engMTURuniingState      Unsigned32,	                --
	engCylCutOff            Unsigned32,	                --
	engLoadGenStatus        Unsigned32,	                --
	engEtxStopState         Unsigned32,	                --
	engCurrOPMode           Unsigned32,	                --
	engMTUReqTorque         Unsigned32,	                --
	engTripAvgFuel          AverageFuelDiv100,	        --
	engECURatedPower        Unsigned32,	                --
	engECURatedSpeed        Unsigned32,	                --
	engECUIdleSpeed         Unsigned32,	                --
	engECUDesirSpeed        Unsigned32,	                --
	engECUPreheatStat       Unsigned32,	                --
	engManiFoldPres         Unsigned32,	                --
	engIntercoolerLevel     Unsigned32,	                --
	engCANLinkState         Unsigned32,	                --
	engAutoDFPRegInh        Unsigned32,	                --
	engDPTCActRegInhSwitch  Unsigned32,	                --
	engSootLoadPC           Unsigned32,	                --
	engAshLoadPC            Unsigned32,	                --
	engDefTankLevel         Unsigned32,	                --
	engDefTankTemp          Unsigned32,	                --
	engDefLevelWarn         Unsigned32,	                --
	engDefReagentCons       Unsigned32,	                --
	engDefInducReason       Unsigned32,	                --
	engDefInducSever        Unsigned32,	                --
	engDefCounterMin        Unsigned32,	                --
	engTLTTorqueReduc       Unsigned32,	                --
	engTLTVehspdReduc       Unsigned32,	                --
	engEGRPress             Unsigned32,	                --
	engEGRTemp              Unsigned32,	                --
	engAmbAirTemp           Unsigned32,	                --
	engAirIntakeTemp        Unsigned32,	                --
	engSRCOperatInduc       Unsigned32,	                --
	engTankLevLowLost       Unsigned32,	                --
	engMiscAltSpeedSel      Unsigned32,	                --
	engExhGasP17Temp        Integer32,	                --
	engExhGasP18Temp        Integer32,	                --
	engExhGasP19Temp        Integer32,	                --
	engExhGasP20Temp        Integer32,	                --
	engInstFuelRate         Unsigned32,	                --
	engDPTCFiltStat         Unsigned32,	                --
	engDPTCActRegInh        Unsigned32,	                --
	engDPTCActRegInhEt      Unsigned32,	                --
	engDefTankStat          Unsigned32,	                --
	engFuelGasPress         Unsigned32,	                --
	engThrotPos1            Unsigned32,	                --
	engThrotPos2            Unsigned32	                --
}

BusTableEntry ::= SEQUENCE {
	busKeyId            Integer32,	                --
	busFreq            FreqDiv10,	                -- Bus frequency
	busL1Volts            VoltsLNDiv10,	                -- Bus L1-N voltage
	busL2Volts            VoltsLNDiv10,	                -- Bus L2-N voltage
	busL3Volts            VoltsLNDiv10,	                -- Bus L3-N voltage
	busL1L2Volts            VoltsLLDiv10,	                -- Bus L1-L2 voltage
	busL2L3Volts            VoltsLLDiv10,	                -- Bus L2-L3 voltage
	busL3L1Volts            VoltsLLDiv10,	                -- Bus L3-L1 voltage
	busL1Current            CurrentDiv10,	                -- Bus L1 current
	busL2Current            CurrentDiv10,	                -- Bus L2 current
	busL3Current            CurrentDiv10,	                -- Bus L3 current
	busECurrent            CurrentDiv10,	                -- Bus earth current
	busL1Watts            Integer32,	                -- Bus L1 watts
	busL2Watts            Integer32,	                -- Bus L2 watts
	busL3Watts            Integer32,	                -- Bus L3 watts
	busRotations            Integer32,	                -- Bus phase rotation
	busWattsTotal            Integer32,	                -- Bus total watts
	busL1VA            Unsigned32,	                -- Bus L1 VA
	busL2VA            Unsigned32,	                -- Bus L2 VA
	busL3VA            Unsigned32,	                -- Bus L3 VA
	busTotalVA            Unsigned32,	                -- Bus total VA
	busL1VAr            Integer32,	                -- Bus L1 Var
	busL2VAr            Integer32,	                -- Bus L2 Var
	busL3VAr            Integer32,	                -- Bus L3 Var
	busTotalVAr            Integer32,	                -- Bus total Var
	busPowerFactorL1            PowerFactorDiv100,	                -- Bus power factor L1
	busPowerFactorL2            PowerFactorDiv100,	                -- Bus power factor L2
	busPowerFactorL3            PowerFactorDiv100,	                -- Bus power factor L3
	busAvgPowerFactor            PowerFactorDiv100,	                -- Bus average power factor
	busPowerTotalPC            PowerPCDiv10,	                -- Bus percentage of full power
	busVARTotalPC            PowerPCDiv10,	                -- Bus percentage of full Var
	busVoltageLNAvg            VoltsLNDiv10,	                -- Bus L-N voltage average
	busVoltageLNDiff            VoltsLNDiv10,	                -- Bus L-N voltage difference
	busVoltageLNMin            VoltsLNDiv10,	                -- Bus L-N voltage min
	busVoltageLNMax            VoltsLNDiv10,	                -- Bus L-N voltage max
	busVoltageLLAvg            VoltsLLDiv10,	                -- Bus L-L voltage average
	busVoltageLLDiff            VoltsLLDiv10,	                -- Bus L-L voltage difference
	busVoltageLLMin            VoltsLLDiv10,	                -- Bus L-L voltage min
	busVoltageLLMax            VoltsLLDiv10	                -- Bus L-L voltage max
}

GencommP166Entry ::= SEQUENCE {
	gencommP166KeyID            Integer32,					--
	gencommP166Reg-0-1      	Unsigned32,             	--
	gencommP166Reg-2-3          Unsigned32,             	--
	gencommP166Reg-4-5          Unsigned32,             	--
	gencommP166Reg-6-7          Unsigned32,             	--
	gencommP166Reg-8-9          Unsigned32,             	--
	gencommP166Reg-10-11        Unsigned32,             	--
	gencommP166Reg-12-13        Unsigned32,             	--
	gencommP166Reg-14-15        Unsigned32,             	--
	gencommP166Reg-16-17        Unsigned32,             	--
	gencommP166Reg-18-19        Unsigned32,             	--
	gencommP166Reg-20-21        Unsigned32,             	--
	gencommP166Reg-22-23        Unsigned32,             	--
	gencommP166Reg-24-25        Unsigned32,             	--
	gencommP166Reg-26-27        Unsigned32,             	--
	gencommP166Reg-28-29        Unsigned32,             	--
	gencommP166Reg-30-31        Unsigned32,             	--
	gencommP166Reg-32-33        Unsigned32,             	--
	gencommP166Reg-34-35        Unsigned32,             	--
	gencommP166Reg-36-37        Unsigned32,             	--
	gencommP166Reg-38-39        Unsigned32,             	--
	gencommP166Reg-40-41        Unsigned32,             	--
	gencommP166Reg-42-43        Unsigned32,             	--
	gencommP166Reg-44-45        Unsigned32,             	--
	gencommP166Reg-46-47        Unsigned32,             	--
	gencommP166Reg-48-49        Unsigned32,             	--
	gencommP166Reg-50-51        Unsigned32,             	--
	gencommP166Reg-52-53        Unsigned32,             	--
	gencommP166Reg-54-55        Unsigned32,             	--
	gencommP166Reg-56-57        Unsigned32,             	--
	gencommP166Reg-58-59        Unsigned32,             	--
	gencommP166Reg-60-61        Unsigned32,             	--
	gencommP166Reg-62-63        Unsigned32,             	--
	gencommP166Reg-64-65        Unsigned32,             	--
	gencommP166Reg-66-67        Unsigned32,             	--
	gencommP166Reg-68-69        Unsigned32,             	--
	gencommP166Reg-70-71        Unsigned32,             	--
	gencommP166Reg-72-73        Unsigned32,             	--
	gencommP166Reg-74-75        Unsigned32,             	--
	gencommP166Reg-76-77        Unsigned32,             	--
	gencommP166Reg-78-79        Unsigned32,             	--
	gencommP166Reg-80-81        Unsigned32,             	--
	gencommP166Reg-82-83        Unsigned32,             	--
	gencommP166Reg-84-85        Unsigned32,             	--
	gencommP166Reg-86-87        Unsigned32,             	--
	gencommP166Reg-88-89        Unsigned32,             	--
	gencommP166Reg-90-91        Unsigned32,             	--
	gencommP166Reg-92-93        Unsigned32,             	--
	gencommP166Reg-94-95        Unsigned32,             	--
	gencommP166Reg-96-97        Unsigned32,             	--
	gencommP166Reg-98-99        Unsigned32,             	--
	gencommP166Reg-100-101      Unsigned32,             	--
	gencommP166Reg-102-103      Unsigned32,             	--
	gencommP166Reg-104-105      Unsigned32,             	--
	gencommP166Reg-106-107      Unsigned32,             	--
	gencommP166Reg-108-109      Unsigned32,             	--
	gencommP166Reg-110-111      Unsigned32,             	--
	gencommP166Reg-112-113      Unsigned32,             	--
	gencommP166Reg-114-115      Unsigned32,             	--
	gencommP166Reg-116-117      Unsigned32,             	--
	gencommP166Reg-118-119      Unsigned32,             	--
	gencommP166Reg-120-121      Unsigned32,             	--
	gencommP166Reg-122-123      Unsigned32,             	--
	gencommP166Reg-124-125      Unsigned32,             	--
	gencommP166Reg-126-127      Unsigned32,             	--
	gencommP166Reg-128-129      Unsigned32,             	--
	gencommP166Reg-130-131      Unsigned32,             	--
	gencommP166Reg-132-133      Unsigned32,             	--
	gencommP166Reg-134-135      Unsigned32,             	--
	gencommP166Reg-136-137      Unsigned32,             	--
	gencommP166Reg-138-139      Unsigned32,             	--
	gencommP166Reg-140-141      Unsigned32,             	--
	gencommP166Reg-142-143      Unsigned32,             	--
	gencommP166Reg-144-145      Unsigned32,             	--
	gencommP166Reg-146-147      Unsigned32,             	--
	gencommP166Reg-148-149      Unsigned32,             	--
	gencommP166Reg-150-151      Unsigned32,             	--
	gencommP166Reg-152-153      Unsigned32,             	--
	gencommP166Reg-154-155      Unsigned32,             	--
	gencommP166Reg-156-157      Unsigned32,             	--
	gencommP166Reg-158-159      Unsigned32,             	--
	gencommP166Reg-160-161      Unsigned32,             	--
	gencommP166Reg-162-163      Unsigned32,             	--
	gencommP166Reg-164-165      Unsigned32,             	--
	gencommP166Reg-166-167      Unsigned32,             	--
	gencommP166Reg-168-169      Unsigned32,             	--
	gencommP166Reg-170-171      Unsigned32,             	--
	gencommP166Reg-172-173      Unsigned32,             	--
	gencommP166Reg-174-175      Unsigned32,             	--
	gencommP166Reg-176-177      Unsigned32,             	--
	gencommP166Reg-178-179      Unsigned32,             	--
	gencommP166Reg-180-181      Unsigned32,             	--
	gencommP166Reg-182-183      Unsigned32,             	--
	gencommP166Reg-184-185      Unsigned32,             	--
	gencommP166Reg-186-187      Unsigned32,             	--
	gencommP166Reg-188-189      Unsigned32,             	--
	gencommP166Reg-190-191      Unsigned32,             	--
	gencommP166Reg-192-193      Unsigned32,             	--
	gencommP166Reg-194-195      Unsigned32,             	--
	gencommP166Reg-196-197      Unsigned32,             	--
	gencommP166Reg-198-199      Unsigned32,             	--
	gencommP166Reg-200-201      Unsigned32,             	--
	gencommP166Reg-202-203      Unsigned32,             	--
	gencommP166Reg-204-205      Unsigned32,             	--
	gencommP166Reg-206-207      Unsigned32,             	--
	gencommP166Reg-208-209      Unsigned32,             	--
	gencommP166Reg-210-211      Unsigned32,             	--
	gencommP166Reg-212-213      Unsigned32,             	--
	gencommP166Reg-214-215      Unsigned32,             	--
	gencommP166Reg-216-217      Unsigned32,             	--
	gencommP166Reg-218-219      Unsigned32,             	--
	gencommP166Reg-220-221      Unsigned32,             	--
	gencommP166Reg-222-223      Unsigned32,             	--
	gencommP166Reg-224-225      Unsigned32,             	--
	gencommP166Reg-226-227      Unsigned32,             	--
	gencommP166Reg-228-229      Unsigned32,             	--
	gencommP166Reg-230-231      Unsigned32,             	--
	gencommP166Reg-232-233      Unsigned32,             	--
	gencommP166Reg-234-235      Unsigned32,             	--
	gencommP166Reg-236-237      Unsigned32,             	--
	gencommP166Reg-238-239      Unsigned32,             	--
	gencommP166Reg-240-241      Unsigned32,             	--
	gencommP166Reg-242-243      Unsigned32,             	--
	gencommP166Reg-244-245      Unsigned32,             	--
	gencommP166Reg-246-247      Unsigned32,             	--
	gencommP166Reg-248-249      Unsigned32,             	--
	gencommP166Reg-250-251      Unsigned32,             	--
	gencommP166Reg-252-253      Unsigned32,             	--
	gencommP166Reg-254-255      Unsigned32             		--
}

GencommP167Entry ::= SEQUENCE {
	gencommP167KeyID            Integer32,					--
	gencommP167Reg-0-1          Unsigned32,             	--
	gencommP167Reg-2-3          Unsigned32,             	--
	gencommP167Reg-4-5          Unsigned32,             	--
	gencommP167Reg-6-7          Unsigned32,             	--
	gencommP167Reg-8-9          Unsigned32,             	--
	gencommP167Reg-10-11        Unsigned32,             	--
	gencommP167Reg-12-13        Unsigned32,             	--
	gencommP167Reg-14-15        Unsigned32,             	--
	gencommP167Reg-16-17        Unsigned32,             	--
	gencommP167Reg-18-19        Unsigned32,             	--
	gencommP167Reg-20-21        Unsigned32,             	--
	gencommP167Reg-22-23        Unsigned32,             	--
	gencommP167Reg-24-25        Unsigned32,             	--
	gencommP167Reg-26-27        Unsigned32,             	--
	gencommP167Reg-28-29        Unsigned32,             	--
	gencommP167Reg-30-31        Unsigned32,             	--
	gencommP167Reg-32-33        Unsigned32,             	--
	gencommP167Reg-34-35        Unsigned32,             	--
	gencommP167Reg-36-37        Unsigned32,             	--
	gencommP167Reg-38-39        Unsigned32,             	--
	gencommP167Reg-40-41        Unsigned32,             	--
	gencommP167Reg-42-43        Unsigned32,             	--
	gencommP167Reg-44-45        Unsigned32,             	--
	gencommP167Reg-46-47        Unsigned32,             	--
	gencommP167Reg-48-49        Unsigned32,             	--
	gencommP167Reg-50-51        Unsigned32,             	--
	gencommP167Reg-52-53        Unsigned32,             	--
	gencommP167Reg-54-55        Unsigned32,             	--
	gencommP167Reg-56-57        Unsigned32,             	--
	gencommP167Reg-58-59        Unsigned32,             	--
	gencommP167Reg-60-61        Unsigned32,             	--
	gencommP167Reg-62-63        Unsigned32,             	--
	gencommP167Reg-64-65        Unsigned32,             	--
	gencommP167Reg-66-67        Unsigned32,             	--
	gencommP167Reg-68-69        Unsigned32,             	--
	gencommP167Reg-70-71        Unsigned32,             	--
	gencommP167Reg-72-73        Unsigned32,             	--
	gencommP167Reg-74-75        Unsigned32,             	--
	gencommP167Reg-76-77        Unsigned32,             	--
	gencommP167Reg-78-79        Unsigned32,             	--
	gencommP167Reg-80-81        Unsigned32,             	--
	gencommP167Reg-82-83        Unsigned32,             	--
	gencommP167Reg-84-85        Unsigned32,             	--
	gencommP167Reg-86-87        Unsigned32,             	--
	gencommP167Reg-88-89        Unsigned32,             	--
	gencommP167Reg-90-91        Unsigned32,             	--
	gencommP167Reg-92-93        Unsigned32,             	--
	gencommP167Reg-94-95        Unsigned32,             	--
	gencommP167Reg-96-97        Unsigned32,             	--
	gencommP167Reg-98-99        Unsigned32,             	--
	gencommP167Reg-100-101      Unsigned32,             	--
	gencommP167Reg-102-103      Unsigned32,             	--
	gencommP167Reg-104-105      Unsigned32,             	--
	gencommP167Reg-106-107      Unsigned32,             	--
	gencommP167Reg-108-109      Unsigned32,             	--
	gencommP167Reg-110-111      Unsigned32,             	--
	gencommP167Reg-112-113      Unsigned32,             	--
	gencommP167Reg-114-115      Unsigned32,             	--
	gencommP167Reg-116-117      Unsigned32,             	--
	gencommP167Reg-118-119      Unsigned32,             	--
	gencommP167Reg-120-121      Unsigned32,             	--
	gencommP167Reg-122-123      Unsigned32,             	--
	gencommP167Reg-124-125      Unsigned32,             	--
	gencommP167Reg-126-127      Unsigned32,             	--
	gencommP167Reg-128-129      Unsigned32,             	--
	gencommP167Reg-130-131      Unsigned32,             	--
	gencommP167Reg-132-133      Unsigned32,             	--
	gencommP167Reg-134-135      Unsigned32,             	--
	gencommP167Reg-136-137      Unsigned32,             	--
	gencommP167Reg-138-139      Unsigned32,             	--
	gencommP167Reg-140-141      Unsigned32,             	--
	gencommP167Reg-142-143      Unsigned32,             	--
	gencommP167Reg-144-145      Unsigned32,             	--
	gencommP167Reg-146-147      Unsigned32,             	--
	gencommP167Reg-148-149      Unsigned32,             	--
	gencommP167Reg-150-151      Unsigned32,             	--
	gencommP167Reg-152-153      Unsigned32,             	--
	gencommP167Reg-154-155      Unsigned32,             	--
	gencommP167Reg-156-157      Unsigned32,             	--
	gencommP167Reg-158-159      Unsigned32,             	--
	gencommP167Reg-160-161      Unsigned32,             	--
	gencommP167Reg-162-163      Unsigned32,             	--
	gencommP167Reg-164-165      Unsigned32,             	--
	gencommP167Reg-166-167      Unsigned32,             	--
	gencommP167Reg-168-169      Unsigned32,             	--
	gencommP167Reg-170-171      Unsigned32,             	--
	gencommP167Reg-172-173      Unsigned32,             	--
	gencommP167Reg-174-175      Unsigned32,             	--
	gencommP167Reg-176-177      Unsigned32,             	--
	gencommP167Reg-178-179      Unsigned32,             	--
	gencommP167Reg-180-181      Unsigned32,             	--
	gencommP167Reg-182-183      Unsigned32,             	--
	gencommP167Reg-184-185      Unsigned32,             	--
	gencommP167Reg-186-187      Unsigned32,             	--
	gencommP167Reg-188-189      Unsigned32,             	--
	gencommP167Reg-190-191      Unsigned32,             	--
	gencommP167Reg-192-193      Unsigned32,             	--
	gencommP167Reg-194-195      Unsigned32,             	--
	gencommP167Reg-196-197      Unsigned32,             	--
	gencommP167Reg-198-199      Unsigned32,             	--
	gencommP167Reg-200-201      Unsigned32,             	--
	gencommP167Reg-202-203      Unsigned32,             	--
	gencommP167Reg-204-205      Unsigned32,             	--
	gencommP167Reg-206-207      Unsigned32,             	--
	gencommP167Reg-208-209      Unsigned32,             	--
	gencommP167Reg-210-211      Unsigned32,             	--
	gencommP167Reg-212-213      Unsigned32,             	--
	gencommP167Reg-214-215      Unsigned32,             	--
	gencommP167Reg-216-217      Unsigned32,             	--
	gencommP167Reg-218-219      Unsigned32,             	--
	gencommP167Reg-220-221      Unsigned32,             	--
	gencommP167Reg-222-223      Unsigned32,             	--
	gencommP167Reg-224-225      Unsigned32,             	--
	gencommP167Reg-226-227      Unsigned32,             	--
	gencommP167Reg-228-229      Unsigned32,             	--
	gencommP167Reg-230-231      Unsigned32,             	--
	gencommP167Reg-232-233      Unsigned32,             	--
	gencommP167Reg-234-235      Unsigned32,             	--
	gencommP167Reg-236-237      Unsigned32,             	--
	gencommP167Reg-238-239      Unsigned32,             	--
	gencommP167Reg-240-241      Unsigned32,             	--
	gencommP167Reg-242-243      Unsigned32,             	--
	gencommP167Reg-244-245      Unsigned32,             	--
	gencommP167Reg-246-247      Unsigned32,             	--
	gencommP167Reg-248-249      Unsigned32,             	--
	gencommP167Reg-250-251      Unsigned32,             	--
	gencommP167Reg-252-253      Unsigned32,             	--
	gencommP167Reg-254-255      Unsigned32             		--
}

GencommP168Entry ::= SEQUENCE {
	gencommP168KeyID            Integer32,					--
	gencommP168Reg-0-1      	Unsigned32,             	--
	gencommP168Reg-2-3          Unsigned32,             	--
	gencommP168Reg-4-5          Unsigned32,             	--
	gencommP168Reg-6-7          Unsigned32,             	--
	gencommP168Reg-8-9          Unsigned32,             	--
	gencommP168Reg-10-11        Unsigned32,             	--
	gencommP168Reg-12-13        Unsigned32,             	--
	gencommP168Reg-14-15        Unsigned32,             	--
	gencommP168Reg-16-17        Unsigned32,             	--
	gencommP168Reg-18-19        Unsigned32,             	--
	gencommP168Reg-20-21        Unsigned32,             	--
	gencommP168Reg-22-23        Unsigned32,             	--
	gencommP168Reg-24-25        Unsigned32,             	--
	gencommP168Reg-26-27        Unsigned32,             	--
	gencommP168Reg-28-29        Unsigned32,             	--
	gencommP168Reg-30-31        Unsigned32,             	--
	gencommP168Reg-32-33        Unsigned32,             	--
	gencommP168Reg-34-35        Unsigned32,             	--
	gencommP168Reg-36-37        Unsigned32,             	--
	gencommP168Reg-38-39        Unsigned32,             	--
	gencommP168Reg-40-41        Unsigned32,             	--
	gencommP168Reg-42-43        Unsigned32,             	--
	gencommP168Reg-44-45        Unsigned32,             	--
	gencommP168Reg-46-47        Unsigned32,             	--
	gencommP168Reg-48-49        Unsigned32,             	--
	gencommP168Reg-50-51        Unsigned32,             	--
	gencommP168Reg-52-53        Unsigned32,             	--
	gencommP168Reg-54-55        Unsigned32,             	--
	gencommP168Reg-56-57        Unsigned32,             	--
	gencommP168Reg-58-59        Unsigned32,             	--
	gencommP168Reg-60-61        Unsigned32,             	--
	gencommP168Reg-62-63        Unsigned32,             	--
	gencommP168Reg-64-65        Unsigned32,             	--
	gencommP168Reg-66-67        Unsigned32,             	--
	gencommP168Reg-68-69        Unsigned32,             	--
	gencommP168Reg-70-71        Unsigned32,             	--
	gencommP168Reg-72-73        Unsigned32,             	--
	gencommP168Reg-74-75        Unsigned32,             	--
	gencommP168Reg-76-77        Unsigned32,             	--
	gencommP168Reg-78-79        Unsigned32,             	--
	gencommP168Reg-80-81        Unsigned32,             	--
	gencommP168Reg-82-83        Unsigned32,             	--
	gencommP168Reg-84-85        Unsigned32,             	--
	gencommP168Reg-86-87        Unsigned32,             	--
	gencommP168Reg-88-89        Unsigned32,             	--
	gencommP168Reg-90-91        Unsigned32,             	--
	gencommP168Reg-92-93        Unsigned32,             	--
	gencommP168Reg-94-95        Unsigned32,             	--
	gencommP168Reg-96-97        Unsigned32,             	--
	gencommP168Reg-98-99        Unsigned32,             	--
	gencommP168Reg-100-101      Unsigned32,             	--
	gencommP168Reg-102-103      Unsigned32,             	--
	gencommP168Reg-104-105      Unsigned32,             	--
	gencommP168Reg-106-107      Unsigned32,             	--
	gencommP168Reg-108-109      Unsigned32,             	--
	gencommP168Reg-110-111      Unsigned32,             	--
	gencommP168Reg-112-113      Unsigned32,             	--
	gencommP168Reg-114-115      Unsigned32,             	--
	gencommP168Reg-116-117      Unsigned32,             	--
	gencommP168Reg-118-119      Unsigned32,             	--
	gencommP168Reg-120-121      Unsigned32,             	--
	gencommP168Reg-122-123      Unsigned32,             	--
	gencommP168Reg-124-125      Unsigned32,             	--
	gencommP168Reg-126-127      Unsigned32,             	--
	gencommP168Reg-128-129      Unsigned32,             	--
	gencommP168Reg-130-131      Unsigned32,             	--
	gencommP168Reg-132-133      Unsigned32,             	--
	gencommP168Reg-134-135      Unsigned32,             	--
	gencommP168Reg-136-137      Unsigned32,             	--
	gencommP168Reg-138-139      Unsigned32,             	--
	gencommP168Reg-140-141      Unsigned32,             	--
	gencommP168Reg-142-143      Unsigned32,             	--
	gencommP168Reg-144-145      Unsigned32,             	--
	gencommP168Reg-146-147      Unsigned32,             	--
	gencommP168Reg-148-149      Unsigned32,             	--
	gencommP168Reg-150-151      Unsigned32,             	--
	gencommP168Reg-152-153      Unsigned32,             	--
	gencommP168Reg-154-155      Unsigned32,             	--
	gencommP168Reg-156-157      Unsigned32,             	--
	gencommP168Reg-158-159      Unsigned32,             	--
	gencommP168Reg-160-161      Unsigned32,             	--
	gencommP168Reg-162-163      Unsigned32,             	--
	gencommP168Reg-164-165      Unsigned32,             	--
	gencommP168Reg-166-167      Unsigned32,             	--
	gencommP168Reg-168-169      Unsigned32,             	--
	gencommP168Reg-170-171      Unsigned32,             	--
	gencommP168Reg-172-173      Unsigned32,             	--
	gencommP168Reg-174-175      Unsigned32,             	--
	gencommP168Reg-176-177      Unsigned32,             	--
	gencommP168Reg-178-179      Unsigned32,             	--
	gencommP168Reg-180-181      Unsigned32,             	--
	gencommP168Reg-182-183      Unsigned32,             	--
	gencommP168Reg-184-185      Unsigned32,             	--
	gencommP168Reg-186-187      Unsigned32,             	--
	gencommP168Reg-188-189      Unsigned32,             	--
	gencommP168Reg-190-191      Unsigned32,             	--
	gencommP168Reg-192-193      Unsigned32,             	--
	gencommP168Reg-194-195      Unsigned32,             	--
	gencommP168Reg-196-197      Unsigned32,             	--
	gencommP168Reg-198-199      Unsigned32,             	--
	gencommP168Reg-200-201      Unsigned32,             	--
	gencommP168Reg-202-203      Unsigned32,             	--
	gencommP168Reg-204-205      Unsigned32,             	--
	gencommP168Reg-206-207      Unsigned32,             	--
	gencommP168Reg-208-209      Unsigned32,             	--
	gencommP168Reg-210-211      Unsigned32,             	--
	gencommP168Reg-212-213      Unsigned32,             	--
	gencommP168Reg-214-215      Unsigned32,             	--
	gencommP168Reg-216-217      Unsigned32,             	--
	gencommP168Reg-218-219      Unsigned32,             	--
	gencommP168Reg-220-221      Unsigned32,             	--
	gencommP168Reg-222-223      Unsigned32,             	--
	gencommP168Reg-224-225      Unsigned32,             	--
	gencommP168Reg-226-227      Unsigned32,             	--
	gencommP168Reg-228-229      Unsigned32,             	--
	gencommP168Reg-230-231      Unsigned32,             	--
	gencommP168Reg-232-233      Unsigned32,             	--
	gencommP168Reg-234-235      Unsigned32,             	--
	gencommP168Reg-236-237      Unsigned32,             	--
	gencommP168Reg-238-239      Unsigned32,             	--
	gencommP168Reg-240-241      Unsigned32,             	--
	gencommP168Reg-242-243      Unsigned32,             	--
	gencommP168Reg-244-245      Unsigned32,             	--
	gencommP168Reg-246-247      Unsigned32,             	--
	gencommP168Reg-248-249      Unsigned32,             	--
	gencommP168Reg-250-251      Unsigned32,             	--
	gencommP168Reg-252-253      Unsigned32,             	--
	gencommP168Reg-254-255      Unsigned32         	    	--
}

GencommP169Entry ::= SEQUENCE {
	gencommP169KeyID            Integer32,					--
	gencommP169Reg-0-1      	Unsigned32,             	--
	gencommP169Reg-2-3          Unsigned32,             	--
	gencommP169Reg-4-5          Unsigned32,             	--
	gencommP169Reg-6-7          Unsigned32,             	--
	gencommP169Reg-8-9          Unsigned32,             	--
	gencommP169Reg-10-11        Unsigned32,             	--
	gencommP169Reg-12-13        Unsigned32,             	--
	gencommP169Reg-14-15        Unsigned32,             	--
	gencommP169Reg-16-17        Unsigned32,             	--
	gencommP169Reg-18-19        Unsigned32,             	--
	gencommP169Reg-20-21        Unsigned32,             	--
	gencommP169Reg-22-23        Unsigned32,             	--
	gencommP169Reg-24-25        Unsigned32,             	--
	gencommP169Reg-26-27        Unsigned32,             	--
	gencommP169Reg-28-29        Unsigned32,             	--
	gencommP169Reg-30-31        Unsigned32,             	--
	gencommP169Reg-32-33        Unsigned32,             	--
	gencommP169Reg-34-35        Unsigned32,             	--
	gencommP169Reg-36-37        Unsigned32,             	--
	gencommP169Reg-38-39        Unsigned32,             	--
	gencommP169Reg-40-41        Unsigned32,             	--
	gencommP169Reg-42-43        Unsigned32,             	--
	gencommP169Reg-44-45        Unsigned32,             	--
	gencommP169Reg-46-47        Unsigned32,             	--
	gencommP169Reg-48-49        Unsigned32,             	--
	gencommP169Reg-50-51        Unsigned32,             	--
	gencommP169Reg-52-53        Unsigned32,             	--
	gencommP169Reg-54-55        Unsigned32,             	--
	gencommP169Reg-56-57        Unsigned32,             	--
	gencommP169Reg-58-59        Unsigned32,             	--
	gencommP169Reg-60-61        Unsigned32,             	--
	gencommP169Reg-62-63        Unsigned32,             	--
	gencommP169Reg-64-65        Unsigned32,             	--
	gencommP169Reg-66-67        Unsigned32,             	--
	gencommP169Reg-68-69        Unsigned32,             	--
	gencommP169Reg-70-71        Unsigned32,             	--
	gencommP169Reg-72-73        Unsigned32,             	--
	gencommP169Reg-74-75        Unsigned32,             	--
	gencommP169Reg-76-77        Unsigned32,             	--
	gencommP169Reg-78-79        Unsigned32,             	--
	gencommP169Reg-80-81        Unsigned32,             	--
	gencommP169Reg-82-83        Unsigned32,             	--
	gencommP169Reg-84-85        Unsigned32,             	--
	gencommP169Reg-86-87        Unsigned32,             	--
	gencommP169Reg-88-89        Unsigned32,             	--
	gencommP169Reg-90-91        Unsigned32,             	--
	gencommP169Reg-92-93        Unsigned32,             	--
	gencommP169Reg-94-95        Unsigned32,             	--
	gencommP169Reg-96-97        Unsigned32,             	--
	gencommP169Reg-98-99        Unsigned32,             	--
	gencommP169Reg-100-101      Unsigned32,             	--
	gencommP169Reg-102-103      Unsigned32,             	--
	gencommP169Reg-104-105      Unsigned32,             	--
	gencommP169Reg-106-107      Unsigned32,             	--
	gencommP169Reg-108-109      Unsigned32,             	--
	gencommP169Reg-110-111      Unsigned32,             	--
	gencommP169Reg-112-113      Unsigned32,             	--
	gencommP169Reg-114-115      Unsigned32,             	--
	gencommP169Reg-116-117      Unsigned32,             	--
	gencommP169Reg-118-119      Unsigned32,             	--
	gencommP169Reg-120-121      Unsigned32,             	--
	gencommP169Reg-122-123      Unsigned32,             	--
	gencommP169Reg-124-125      Unsigned32,             	--
	gencommP169Reg-126-127      Unsigned32,             	--
	gencommP169Reg-128-129      Unsigned32,             	--
	gencommP169Reg-130-131      Unsigned32,             	--
	gencommP169Reg-132-133      Unsigned32,             	--
	gencommP169Reg-134-135      Unsigned32,             	--
	gencommP169Reg-136-137      Unsigned32,             	--
	gencommP169Reg-138-139      Unsigned32,             	--
	gencommP169Reg-140-141      Unsigned32,             	--
	gencommP169Reg-142-143      Unsigned32,             	--
	gencommP169Reg-144-145      Unsigned32,             	--
	gencommP169Reg-146-147      Unsigned32,             	--
	gencommP169Reg-148-149      Unsigned32,             	--
	gencommP169Reg-150-151      Unsigned32,             	--
	gencommP169Reg-152-153      Unsigned32,             	--
	gencommP169Reg-154-155      Unsigned32,             	--
	gencommP169Reg-156-157      Unsigned32,             	--
	gencommP169Reg-158-159      Unsigned32,             	--
	gencommP169Reg-160-161      Unsigned32,             	--
	gencommP169Reg-162-163      Unsigned32,             	--
	gencommP169Reg-164-165      Unsigned32,             	--
	gencommP169Reg-166-167      Unsigned32,             	--
	gencommP169Reg-168-169      Unsigned32,             	--
	gencommP169Reg-170-171      Unsigned32,             	--
	gencommP169Reg-172-173      Unsigned32,             	--
	gencommP169Reg-174-175      Unsigned32,             	--
	gencommP169Reg-176-177      Unsigned32,             	--
	gencommP169Reg-178-179      Unsigned32,             	--
	gencommP169Reg-180-181      Unsigned32,             	--
	gencommP169Reg-182-183      Unsigned32,             	--
	gencommP169Reg-184-185      Unsigned32,             	--
	gencommP169Reg-186-187      Unsigned32,             	--
	gencommP169Reg-188-189      Unsigned32,             	--
	gencommP169Reg-190-191      Unsigned32,             	--
	gencommP169Reg-192-193      Unsigned32,             	--
	gencommP169Reg-194-195      Unsigned32,             	--
	gencommP169Reg-196-197      Unsigned32,             	--
	gencommP169Reg-198-199      Unsigned32,             	--
	gencommP169Reg-200-201      Unsigned32,             	--
	gencommP169Reg-202-203      Unsigned32,             	--
	gencommP169Reg-204-205      Unsigned32,             	--
	gencommP169Reg-206-207      Unsigned32,             	--
	gencommP169Reg-208-209      Unsigned32,             	--
	gencommP169Reg-210-211      Unsigned32,             	--
	gencommP169Reg-212-213      Unsigned32,             	--
	gencommP169Reg-214-215      Unsigned32,             	--
	gencommP169Reg-216-217      Unsigned32,             	--
	gencommP169Reg-218-219      Unsigned32,             	--
	gencommP169Reg-220-221      Unsigned32,             	--
	gencommP169Reg-222-223      Unsigned32,             	--
	gencommP169Reg-224-225      Unsigned32,             	--
	gencommP169Reg-226-227      Unsigned32,             	--
	gencommP169Reg-228-229      Unsigned32,             	--
	gencommP169Reg-230-231      Unsigned32,             	--
	gencommP169Reg-232-233      Unsigned32,             	--
	gencommP169Reg-234-235      Unsigned32,             	--
	gencommP169Reg-236-237      Unsigned32,             	--
	gencommP169Reg-238-239      Unsigned32,             	--
	gencommP169Reg-240-241      Unsigned32,             	--
	gencommP169Reg-242-243      Unsigned32,             	--
	gencommP169Reg-244-245      Unsigned32,             	--
	gencommP169Reg-246-247      Unsigned32,             	--
	gencommP169Reg-248-249      Unsigned32,             	--
	gencommP169Reg-250-251      Unsigned32,             	--
	gencommP169Reg-252-253      Unsigned32,             	--
	gencommP169Reg-254-255      Unsigned32            	 	--
}

genKeyID OBJECT-TYPE
  SYNTAX  Integer32 (1..2147483647)
  MAX-ACCESS  not-accessible
  STATUS  current
  DESCRIPTION "Generator Key ID"
  ::= { generatorEntry 1 }

engKeyID OBJECT-TYPE
  SYNTAX  Integer32 (1..2147483647)
  MAX-ACCESS  not-accessible
  STATUS  current
  DESCRIPTION "Engine Key ID"
  ::= { engineEntry 1 }

busKeyId OBJECT-TYPE
  SYNTAX  Integer32 (1..2147483647)
  MAX-ACCESS  not-accessible
  STATUS  current
  DESCRIPTION "Bus Key ID"
  ::= { busTableEntry 1 }

gencommP166KeyID OBJECT-TYPE
  SYNTAX  Integer32 (1..2147483647)
  MAX-ACCESS  not-accessible
  STATUS  current
  DESCRIPTION "Gencomm Page 166 Key ID"
  ::= { gencommP166Entry 1 }

gencommP167KeyID OBJECT-TYPE
  SYNTAX  Integer32 (1..2147483647)
  MAX-ACCESS  not-accessible
  STATUS  current
  DESCRIPTION "Gencomm Page 167 Key ID"
  ::= { gencommP167Entry 1 }

gencommP168KeyID OBJECT-TYPE
  SYNTAX  Integer32 (1..2147483647)
  MAX-ACCESS  not-accessible
  STATUS  current
  DESCRIPTION "Gencomm Page 168 Key ID"
  ::= { gencommP168Entry 1 }

gencommP169KeyID OBJECT-TYPE
  SYNTAX  Integer32 (1..2147483647)
  MAX-ACCESS  not-accessible
  STATUS  current
  DESCRIPTION "Gencomm Page 169 Key ID"
  ::= { gencommP169Entry 1 }

genFreq OBJECT-TYPE
  SYNTAX  FreqDiv10
  MAX-ACCESS  read-only
  STATUS  current
  DESCRIPTION "Generator Frequency. Scaling factor 0.1"
  ::= { generatorEntry 2 }

genL1Volts OBJECT-TYPE
  SYNTAX  VoltsLNDiv10
  MAX-ACCESS  read-only
  STATUS  current
  DESCRIPTION "Generator L1-N voltage. Scaling factor 0.1"
  ::= { generatorEntry 3 }

genL2Volts OBJECT-TYPE
  SYNTAX  VoltsLNDiv10
  MAX-ACCESS  read-only
  STATUS  current
  DESCRIPTION "Generator L2-N voltage. Scaling factor 0.1"
  ::= { generatorEntry 4 }

genL3Volts OBJECT-TYPE
  SYNTAX  VoltsLNDiv10
  MAX-ACCESS  read-only
  STATUS  current
  DESCRIPTION "Generator L3-N voltage. Scaling factor 0.1"
  ::= { generatorEntry 5 }

genL1L2Volts OBJECT-TYPE
  SYNTAX  VoltsLLDiv10
  MAX-ACCESS  read-only
  STATUS  current
  DESCRIPTION "Generator L1-L2 voltage. Scaling factor 0.1"
  ::= { generatorEntry 6 }

genL2L3Volts OBJECT-TYPE
  SYNTAX  VoltsLLDiv10
  MAX-ACCESS  read-only
  STATUS  current
  DESCRIPTION "Generator L2-L3 voltage. Scaling factor 0.1"
  ::= { generatorEntry 7 }

genL3L1Volts OBJECT-TYPE
  SYNTAX  VoltsLLDiv10
  MAX-ACCESS  read-only
  STATUS  current
  DESCRIPTION "Generator L3-L1 voltage. Scaling factor 0.1"
  ::= { generatorEntry 8 }

genL1Current OBJECT-TYPE
  SYNTAX  CurrentDiv10
  MAX-ACCESS  read-only
  STATUS  current
  DESCRIPTION "Generator L1 current. Scaling factor 0.1"
  ::= { generatorEntry 9 }

genL2Current OBJECT-TYPE
  SYNTAX  CurrentDiv10
  MAX-ACCESS  read-only
  STATUS  current
  DESCRIPTION "Generator L2 current. Scaling factor 0.1"
  ::= { generatorEntry 10 }

genL3Current OBJECT-TYPE
  SYNTAX  CurrentDiv10
  MAX-ACCESS  read-only
  STATUS  current
  DESCRIPTION "Generator L3 current. Scaling factor 0.1"
  ::= { generatorEntry 11 }

genECurrent OBJECT-TYPE
  SYNTAX  CurrentDiv10
  MAX-ACCESS  read-only
  STATUS  current
  DESCRIPTION "Generator earth current. Scaling factor 0.1"
  ::= { generatorEntry 12 }

genL1Watts OBJECT-TYPE
  SYNTAX  Integer32 (-99999999..99999999)
  MAX-ACCESS  read-only
  STATUS  current
  DESCRIPTION "Generator L1 watts. Scaling factor 1"
  ::= { generatorEntry 13 }

genL2Watts OBJECT-TYPE
  SYNTAX  Integer32 (-99999999..99999999)
  MAX-ACCESS  read-only
  STATUS  current
  DESCRIPTION "Generator L2 watts. Scaling factor 1"
  ::= { generatorEntry 14 }

genL3Watts OBJECT-TYPE
  SYNTAX  Integer32 (-99999999..99999999)
  MAX-ACCESS  read-only
  STATUS  current
  DESCRIPTION "Generator L3 watts. Scaling factor 1"
  ::= { generatorEntry 15 }

genRotation OBJECT-TYPE
  SYNTAX  Integer32 (0..3)
  MAX-ACCESS  read-only
  STATUS  current
  DESCRIPTION "Generator phase rotation. Intermediate=0, L1_L2_L3=1, L3_L2_L1=2, Error=3"
  ::= { generatorEntry 16 }

genWattsTotal OBJECT-TYPE
  SYNTAX  Integer32 (-99999999..99999999)
  MAX-ACCESS  read-only
  STATUS  current
  DESCRIPTION "Generator total watts. Scaling factor 1"
  ::= { generatorEntry 17 }

genL1VA OBJECT-TYPE
  SYNTAX  Unsigned32 (0..99999999)
  MAX-ACCESS  read-only
  STATUS  current
  DESCRIPTION "Generator L1 VA. Scaling factor 1"
  ::= { generatorEntry 18 }

genL2VA OBJECT-TYPE
  SYNTAX  Unsigned32 (0..99999999)
  MAX-ACCESS  read-only
  STATUS  current
  DESCRIPTION "Generator L2 VA. Scaling factor 1"
  ::= { generatorEntry 19 }

genL3VA OBJECT-TYPE
  SYNTAX  Unsigned32 (0..99999999)
  MAX-ACCESS  read-only
  STATUS  current
  DESCRIPTION "Generator L3 VA. Scaling factor 1"
  ::= { generatorEntry 20 }

genTotalVA OBJECT-TYPE
  SYNTAX  Unsigned32 (0..99999999)
  MAX-ACCESS  read-only
  STATUS  current
  DESCRIPTION "Generator total VA. Scaling factor 1"
  ::= { generatorEntry 21 }

genL1VAr OBJECT-TYPE
  SYNTAX  Integer32 (-99999999..99999999)
  MAX-ACCESS  read-only
  STATUS  current
  DESCRIPTION "Generator L1 VAr. Scaling factor 1"
  ::= { generatorEntry 22 }

genL2VAr OBJECT-TYPE
  SYNTAX  Integer32 (-99999999..99999999)
  MAX-ACCESS  read-only
  STATUS  current
  DESCRIPTION "Generator L2 VAr. Scaling factor 1"
  ::= { generatorEntry 23 }

genL3VAr OBJECT-TYPE
  SYNTAX  Integer32 (-99999999..99999999)
  MAX-ACCESS  read-only
  STATUS  current
  DESCRIPTION "Generator L3 VAr. Scaling factor 1"
  ::= { generatorEntry 24 }

genTotalVAr OBJECT-TYPE
  SYNTAX  Integer32 (-99999999..99999999)
  MAX-ACCESS  read-only
  STATUS  current
  DESCRIPTION "Generator total VAr. Scaling factor 1"
  ::= { generatorEntry 25 }

genPowerFactorL1 OBJECT-TYPE
  SYNTAX  PowerFactorDiv100
  MAX-ACCESS  read-only
  STATUS  current
  DESCRIPTION "Generator power factor L1. Scaling factor 0.01"
  ::= { generatorEntry 26 }

genPowerFactorL2 OBJECT-TYPE
  SYNTAX  PowerFactorDiv100
  MAX-ACCESS  read-only
  STATUS  current
  DESCRIPTION "Generator power factor L2. Scaling factor 0.01"
  ::= { generatorEntry 27 }

genPowerFactorL3 OBJECT-TYPE
  SYNTAX  PowerFactorDiv100
  MAX-ACCESS  read-only
  STATUS  current
  DESCRIPTION "Generator power factor L3. Scaling factor 0.01"
  ::= { generatorEntry 28 }

genAvgPowerFactor OBJECT-TYPE
  SYNTAX  PowerFactorDiv100
  MAX-ACCESS  read-only
  STATUS  current
  DESCRIPTION "Generator average power factor. Scaling factor 0.01"
  ::= { generatorEntry 29 }

genPowerTotalPC OBJECT-TYPE
  SYNTAX  Integer32 (-9999..9999)
  MAX-ACCESS  read-only
  STATUS  current
  DESCRIPTION "Generator Total Percentage of Full Power. Scaling factor 0.1"
  ::= { generatorEntry 30 }

genVARTotalPC OBJECT-TYPE
  SYNTAX  Integer32 (-9999..9999)
  MAX-ACCESS  read-only
  STATUS  current
  DESCRIPTION "Generator Total Percentage of Full VAR. Scaling factor 0.1"
  ::= { generatorEntry 31 }

genPhase1 OBJECT-TYPE
  SYNTAX  Unsigned32 (0..2)
  MAX-ACCESS  read-only
  STATUS  current
  DESCRIPTION "Generator Phase L1 lead/lag. Lead=0, Undetermined=1, Lag=2"
  ::= { generatorEntry 32 }

genPhase2 OBJECT-TYPE
  SYNTAX  Unsigned32 (0..2)
  MAX-ACCESS  read-only
  STATUS  current
  DESCRIPTION "Generator Phase L2 lead/lag. Lead=0, Undetermined=1, Lag=2"
  ::= { generatorEntry 33 }

genPhase3 OBJECT-TYPE
  SYNTAX  Unsigned32 (0..2)
  MAX-ACCESS  read-only
  STATUS  current
  DESCRIPTION "Generator Phase L3 lead/lag. Lead=0, Undetermined=1, Lag=2"
  ::= { generatorEntry 34 }

genPhaseTotal OBJECT-TYPE
  SYNTAX  Unsigned32 (0..2)
  MAX-ACCESS  read-only
  STATUS  current
  DESCRIPTION "Generator Phase Total lead/lag. Lead=0, Undetermined=1, Lag=2"
  ::= { generatorEntry 35 }

genPowerL1PC OBJECT-TYPE
  SYNTAX  Integer32 (-9999..9999)
  MAX-ACCESS  read-only
  STATUS  current
  DESCRIPTION "Generator L1 Percentage of Full Power. Scaling factor 0.1"
  ::= { generatorEntry 36 }

genPowerL2PC OBJECT-TYPE
  SYNTAX  Integer32 (-9999..9999)
  MAX-ACCESS  read-only
  STATUS  current
  DESCRIPTION "Generator L2 Percentage of Full Power. Scaling factor 0.1"
  ::= { generatorEntry 37 }

genPowerL3PC OBJECT-TYPE
  SYNTAX  Integer32 (-9999..9999)
  MAX-ACCESS  read-only
  STATUS  current
  DESCRIPTION "Generator L3 Percentage of Full Power. Scaling factor 0.1"
  ::= { generatorEntry 38 }

genVoltageLNAvg OBJECT-TYPE
  SYNTAX  VoltsLNDiv10
  MAX-ACCESS  read-only
  STATUS  current
  DESCRIPTION "Generator L-N voltage average. Scaling factor 0.1"
  ::= { generatorEntry 39 }

genVoltageLNDiff OBJECT-TYPE
  SYNTAX  VoltsLNDiv10
  MAX-ACCESS  read-only
  STATUS  current
  DESCRIPTION "Generator L-N voltage difference. Scaling factor 0.1"
  ::= { generatorEntry 40 }

genVoltageLNMin OBJECT-TYPE
  SYNTAX  VoltsLNDiv10
  MAX-ACCESS  read-only
  STATUS  current
  DESCRIPTION "Generator L-N voltage min. Scaling factor 0.1"
  ::= { generatorEntry 41 }

genVoltageLNMax OBJECT-TYPE
  SYNTAX  VoltsLNDiv10
  MAX-ACCESS  read-only
  STATUS  current
  DESCRIPTION "Generator L-N voltage max. Scaling factor 0.1"
  ::= { generatorEntry 42 }

genVoltageLLAvg OBJECT-TYPE
  SYNTAX  VoltsLLDiv10
  MAX-ACCESS  read-only
  STATUS  current
  DESCRIPTION "Generator L-L voltage average. Scaling factor 0.1"
  ::= { generatorEntry 43 }

genVoltageLLDiff OBJECT-TYPE
  SYNTAX  VoltsLLDiv10
  MAX-ACCESS  read-only
  STATUS  current
  DESCRIPTION "Generator L-L voltage difference. Scaling factor 0.1"
  ::= { generatorEntry 44 }

genVoltageLLMin OBJECT-TYPE
  SYNTAX  VoltsLLDiv10
  MAX-ACCESS  read-only
  STATUS  current
  DESCRIPTION "Generator L-L voltage min. Scaling factor 0.1"
  ::= { generatorEntry 45 }

genVoltageLLMax OBJECT-TYPE
  SYNTAX  VoltsLLDiv10
  MAX-ACCESS  read-only
  STATUS  current
  DESCRIPTION "Generator L-L voltage max. Scaling factor 0.1"
  ::= { generatorEntry 46 }

genCurrentAve OBJECT-TYPE
  SYNTAX  CurrentDiv10
  MAX-ACCESS  read-only
  STATUS  current
  DESCRIPTION "Generator current average. Scaling factor 0.1"
  ::= { generatorEntry 47 }

genCurrentDif OBJECT-TYPE
  SYNTAX  CurrentDiv10
  MAX-ACCESS  read-only
  STATUS  current
  DESCRIPTION "Generator current difference. Scaling factor 0.1"
  ::= { generatorEntry 48 }

genCurrentMin OBJECT-TYPE
  SYNTAX  CurrentDiv10
  MAX-ACCESS  read-only
  STATUS  current
  DESCRIPTION "Generator current min. Scaling factor 0.1"
  ::= { generatorEntry 49 }

genCurrentMax OBJECT-TYPE
  SYNTAX  CurrentDiv10
  MAX-ACCESS  read-only
  STATUS  current
  DESCRIPTION "Generator current max. Scaling factor 0.1"
  ::= { generatorEntry 50 }

genPowerTotalAvgPC OBJECT-TYPE
  SYNTAX  PowerPCDiv100
  MAX-ACCESS  read-only
  STATUS  current
  DESCRIPTION "Generator watts average %. Scaling factor 0.1"
  ::= { generatorEntry 51 }

genPowerTotalDiffPC OBJECT-TYPE
  SYNTAX  PowerPCDiv10
  MAX-ACCESS  read-only
  STATUS  current
  DESCRIPTION "Generator watts difference %. Scaling factor 0.1"
  ::= { generatorEntry 52 }

genPowerTotalMinPC OBJECT-TYPE
  SYNTAX  PowerPCDiv10
  MAX-ACCESS  read-only
  STATUS  current
  DESCRIPTION "Generator watts Min %. Scaling factor 0.1"
  ::= { generatorEntry 53 }

genPowerTotalMaxPC OBJECT-TYPE
  SYNTAX  PowerPCDiv10
  MAX-ACCESS  read-only
  STATUS  current
  DESCRIPTION "Generator watts Max %. Scaling factor 0.1"
  ::= { generatorEntry 54 }

genVATotalAvgPC OBJECT-TYPE
  SYNTAX  VAPCDiv10
  MAX-ACCESS  read-only
  STATUS  current
  DESCRIPTION "Generator VA average %. Scaling factor 0.1"
  ::= { generatorEntry 55 }

genVADiffPC OBJECT-TYPE
  SYNTAX  VAPCDiv10
  MAX-ACCESS  read-only
  STATUS  current
  DESCRIPTION "Generator VA difference %. Scaling factor 0.1"
  ::= { generatorEntry 56 }

genVAMinPC OBJECT-TYPE
  SYNTAX  VAPCDiv10
  MAX-ACCESS  read-only
  STATUS  current
  DESCRIPTION "Generator VA Min %. Scaling factor 0.1"
  ::= { generatorEntry 57 }

genVAMaxPC OBJECT-TYPE
  SYNTAX  VAPCDiv10
  MAX-ACCESS  read-only
  STATUS  current
  DESCRIPTION "Generator VA Max %. Scaling factor 0.1"
  ::= { generatorEntry 58 }

genVARTotalAvgPC OBJECT-TYPE
  SYNTAX  PowerPCDiv10
  MAX-ACCESS  read-only
  STATUS  current
  DESCRIPTION "Generator VAR average %. Scaling factor 0.1"
  ::= { generatorEntry 59 }

genVARDiffPC OBJECT-TYPE
  SYNTAX  PowerPCDiv10
  MAX-ACCESS  read-only
  STATUS  current
  DESCRIPTION "Generator VAR difference %. Scaling factor 0.1"
  ::= { generatorEntry 60 }

genVARMinPC OBJECT-TYPE
  SYNTAX  PowerPCDiv10
  MAX-ACCESS  read-only
  STATUS  current
  DESCRIPTION "Generator VAR Min %. Scaling factor 0.1"
  ::= { generatorEntry 61 }

genVARMaxPC OBJECT-TYPE
  SYNTAX  PowerPCDiv10
  MAX-ACCESS  read-only
  STATUS  current
  DESCRIPTION "Generator VAR Max %. Scaling factor 0.1"
  ::= { generatorEntry 62 }

genPFTotalAvgPC OBJECT-TYPE
  SYNTAX  PowerFactorDiv100
  MAX-ACCESS  read-only
  STATUS  current
  DESCRIPTION "Generator PF average. Scaling factor 0.1"
  ::= { generatorEntry 63 }

genPFDiffPC OBJECT-TYPE
  SYNTAX  PowerFactorDiv100
  MAX-ACCESS  read-only
  STATUS  current
  DESCRIPTION "Generator PF difference. Scaling factor 0.1"
  ::= { generatorEntry 64 }

genPFMinPC OBJECT-TYPE
  SYNTAX  PowerFactorDiv100
  MAX-ACCESS  read-only
  STATUS  current
  DESCRIPTION "Generator PF Min. Scaling factor 0.1"
  ::= { generatorEntry 65 }

genPFMaxPC OBJECT-TYPE
  SYNTAX  PowerFactorDiv100
  MAX-ACCESS  read-only
  STATUS  current
  DESCRIPTION "Generator PF Max. Scaling factor 0.1"
  ::= { generatorEntry 66 }

engOilPress OBJECT-TYPE
  SYNTAX  OilPressureDiv100
  MAX-ACCESS  read-only
  STATUS  current
  DESCRIPTION "Engine Oil Pressure. Scaling factor 0.01 [bar]"
  ::= { engineEntry 2 }

engTemp OBJECT-TYPE
  SYNTAX  Integer32
  MAX-ACCESS  read-only
  STATUS  current
  DESCRIPTION "Engine Cooltant temperature. Scaling factor 1 [degrees Celsius]"
  ::= { engineEntry 3 }

engOilTemp OBJECT-TYPE
  SYNTAX  Integer32
  MAX-ACCESS  read-only
  STATUS  current
  DESCRIPTION "Engine Oil temperature. Scaling factor 1 [degrees Celsius]"
  ::= { engineEntry 4 }

engFuelLevel OBJECT-TYPE
  SYNTAX  Unsigned32 (0..130)
  MAX-ACCESS  read-only
  STATUS  current
  DESCRIPTION "Engine Fuel level"
  ::= { engineEntry 5 }

engChargeAltVolts OBJECT-TYPE
  SYNTAX  ChargeVoltsDiv10
  MAX-ACCESS  read-only
  STATUS  current
  DESCRIPTION "Engine Charge alternator voltage"
  ::= { engineEntry 6 }

engBatteryVolts OBJECT-TYPE
  SYNTAX  ChargeVoltsDiv10
  MAX-ACCESS  read-only
  STATUS  current
  DESCRIPTION "Engine Battery voltage"
  ::= { engineEntry 7 }

engSpeedDisplay OBJECT-TYPE
  SYNTAX  Unsigned32 (0..6000)
  MAX-ACCESS  read-only
  STATUS  current
  DESCRIPTION "Engine speed"
  ::= { engineEntry 8 }

engCoolantP1 OBJECT-TYPE
  SYNTAX  Unsigned32 (0..10000)
  MAX-ACCESS  read-only
  STATUS  current
  DESCRIPTION "Coolant Pressure 1"
  ::= { engineEntry 9 }

engCoolantP2 OBJECT-TYPE
  SYNTAX  Unsigned32 (0..10000)
  MAX-ACCESS  read-only
  STATUS  current
  DESCRIPTION "Coolant Pressure 2"
  ::= { engineEntry 10 }

engFuelP1 OBJECT-TYPE
  SYNTAX  Unsigned32 (0..10000)
  MAX-ACCESS  read-only
  STATUS  current
  DESCRIPTION "Fuel Pressure 1"
  ::= { engineEntry 11 }

engFuelP2 OBJECT-TYPE
  SYNTAX  Unsigned32 (0..10000)
  MAX-ACCESS  read-only
  STATUS  current
  DESCRIPTION "Fuel Pressure 2"
  ::= { engineEntry 12 }

engTurboP1 OBJECT-TYPE
  SYNTAX  Unsigned32 (0..10000)
  MAX-ACCESS  read-only
  STATUS  current
  DESCRIPTION "Fuel Pressure 1"
  ::= { engineEntry 13 }

engTurboP2 OBJECT-TYPE
  SYNTAX  Unsigned32 (0..10000)
  MAX-ACCESS  read-only
  STATUS  current
  DESCRIPTION "Fuel Pressure 2"
  ::= { engineEntry 14 }

engInMainfoldT1 OBJECT-TYPE
  SYNTAX  Unsigned32 (0..10000)
  MAX-ACCESS  read-only
  STATUS  current
  DESCRIPTION "Inlet Manifold Temperature 1. Scaling factor 1 [degrees Celsius]"
  ::= { engineEntry 15 }

engInMainfoldT2 OBJECT-TYPE
  SYNTAX  Integer32 (-50..10000)
  MAX-ACCESS  read-only
  STATUS  current
  DESCRIPTION "Inlet Manifold Temperature 2. Scaling factor 1 [degrees Celsius]"
  ::= { engineEntry 16 }

engExhaustT1 OBJECT-TYPE
  SYNTAX  Integer32 (-50..10000)
  MAX-ACCESS  read-only
  STATUS  current
  DESCRIPTION "Exhaust Temperature 1. Scaling factor 1 [degrees Celsius]"
  ::= { engineEntry 17 }

engExhaustT2 OBJECT-TYPE
  SYNTAX  Integer32 (-50..10000)
  MAX-ACCESS  read-only
  STATUS  current
  DESCRIPTION "Exhaust Temperature 2. Scaling factor 1 [degrees Celsius]"
  ::= { engineEntry 18 }

engFuelConsumption OBJECT-TYPE
  SYNTAX  AverageFuelDiv100
  MAX-ACCESS  read-only
  STATUS  current
  DESCRIPTION "Fuel consumption"
  ::= { engineEntry 19 }

engWaterInFuel OBJECT-TYPE
  SYNTAX  Unsigned32
  MAX-ACCESS  read-only
  STATUS  current
  DESCRIPTION "Water in Fuel"
  ::= { engineEntry 20 }

engCANBitData OBJECT-TYPE
  SYNTAX  Unsigned32
  MAX-ACCESS  read-only
  STATUS  current
  DESCRIPTION "CAN BIT data"
  ::= { engineEntry 21 }

engAtmosphericP OBJECT-TYPE
  SYNTAX  Unsigned32
  MAX-ACCESS  read-only
  STATUS  current
  DESCRIPTION "Atmospheric pressure"
  ::= { engineEntry 22 }

engFuelT OBJECT-TYPE
  SYNTAX  Integer32
  MAX-ACCESS  read-only
  STATUS  current
  DESCRIPTION "Fuel temperature. Scaling factor 1 [degrees Celsius]"
  ::= { engineEntry 23 }

engFuelLevelUnits OBJECT-TYPE
  SYNTAX  Unsigned32 (0..999999999)
  MAX-ACCESS  read-only
  STATUS  current
  DESCRIPTION "Fuel level (Units)"
  ::= { engineEntry 24 }

engTankFuelUnits OBJECT-TYPE
  SYNTAX  Unsigned32 (0..2)
  MAX-ACCESS  read-only
  STATUS  current
  DESCRIPTION "Selected units for fuel level"
  ::= { engineEntry 25 }

engAfttrt1FuelUSed OBJECT-TYPE
  SYNTAX  Unsigned32 (0..2105)
  MAX-ACCESS  read-only
  STATUS  current
  DESCRIPTION "Exhaust after treatment fuel used"
  ::= { engineEntry 26 }

engAfttrt1ExGasT1 OBJECT-TYPE
  SYNTAX  Integer32 (-273..1735)
  MAX-ACCESS  read-only
  STATUS  current
  DESCRIPTION "After treatment temperature T1"
  ::= { engineEntry 27 }

engAfttrt1ExGasT3 OBJECT-TYPE
  SYNTAX  Integer32 (-273..1735)
  MAX-ACCESS  read-only
  STATUS  current
  DESCRIPTION "After treatment temperature T3"
  ::= { engineEntry 28 }

engRefTorque OBJECT-TYPE
  SYNTAX  Unsigned32 (0..6425)
  MAX-ACCESS  read-only
  STATUS  current
  DESCRIPTION "Engine reference torque"
  ::= { engineEntry 29 }

engPerTorque OBJECT-TYPE
  SYNTAX  Integer32
  MAX-ACCESS  read-only
  STATUS  current
  DESCRIPTION "Engine percentage torque"
  ::= { engineEntry 30 }

engDemandPerTorque OBJECT-TYPE
  SYNTAX  Integer32
  MAX-ACCESS  read-only
  STATUS  current
  DESCRIPTION "Engine demand torque"
  ::= { engineEntry 31 }

engPCLoadAtSpeed OBJECT-TYPE
  SYNTAX  Unsigned32 (0..250)
  MAX-ACCESS  read-only
  STATUS  current
  DESCRIPTION "Percentage load at speed"
  ::= { engineEntry 32 }

engAccelPedalPos OBJECT-TYPE
  SYNTAX  Unsigned32 (0..100)
  MAX-ACCESS  read-only
  STATUS  current
  DESCRIPTION "Accelerator position"
  ::= { engineEntry 33 }

engNomFricPerTorque OBJECT-TYPE
  SYNTAX  Integer32 (-125..125)
  MAX-ACCESS  read-only
  STATUS  current
  DESCRIPTION "Nominal friction percentage torque"
  ::= { engineEntry 34 }

engOilLevel OBJECT-TYPE
  SYNTAX  Unsigned32
  MAX-ACCESS  read-only
  STATUS  current
  DESCRIPTION "Oil level"
  ::= { engineEntry 35 }

engCrankCasePress OBJECT-TYPE
  SYNTAX  CrankPressureDiv100
  MAX-ACCESS  read-only
  STATUS  current
  DESCRIPTION "Crank case pressure"
  ::= { engineEntry 36 }

engCoolantLevel OBJECT-TYPE
  SYNTAX  Integer32 (-25000..25000)
  MAX-ACCESS  read-only
  STATUS  current
  DESCRIPTION "Coolant level"
  ::= { engineEntry 37 }

engInjectorRail1 OBJECT-TYPE
  SYNTAX  InjectorRailPressureDiv100
  MAX-ACCESS  read-only
  STATUS  current
  DESCRIPTION "Injector Rail 1 pressure"
  ::= { engineEntry 38 }

engInjectorRail2 OBJECT-TYPE
  SYNTAX  InjectorRailPressureDiv100
  MAX-ACCESS  read-only
  STATUS  current
  DESCRIPTION "Injector Rail 2 pressure"
  ::= { engineEntry 39 }

engEgrFlowRate OBJECT-TYPE
  SYNTAX  Unsigned32 (0..3212)
  MAX-ACCESS  read-only
  STATUS  current
  DESCRIPTION "Engine EGR flow"
  ::= { engineEntry 40 }

engPreFilOilPress OBJECT-TYPE
  SYNTAX  Unsigned32 (0..1000)
  MAX-ACCESS  read-only
  STATUS  current
  DESCRIPTION "Pre filter oil pressure"
  ::= { engineEntry 41 }

engInstBreakPower OBJECT-TYPE
  SYNTAX  Unsigned32 (0..3212)
  MAX-ACCESS  read-only
  STATUS  current
  DESCRIPTION "Instantaious break power"
  ::= { engineEntry 42 }

engExhGasPort1Temp OBJECT-TYPE
  SYNTAX  Integer32 (-273..1735)
  MAX-ACCESS  read-only
  STATUS  current
  DESCRIPTION "Exhaust gas port 1 temperature. Scaling factor 1 [degrees Celsius]"
  ::= { engineEntry 43 }

engExhGasPort2Temp OBJECT-TYPE
  SYNTAX  Integer32 (-273..1735)
  MAX-ACCESS  read-only
  STATUS  current
  DESCRIPTION "Exhaust gas port 2 temperature. Scaling factor 1 [degrees Celsius]"
  ::= { engineEntry 44 }

engExhGasPort3Temp OBJECT-TYPE
  SYNTAX  Integer32 (-273..1735)
  MAX-ACCESS  read-only
  STATUS  current
  DESCRIPTION "Exhaust gas port 3 temperature. Scaling factor 1 [degrees Celsius]"
  ::= { engineEntry 45 }

engExhGasPort4Temp OBJECT-TYPE
  SYNTAX  Integer32 (-273..1735)
  MAX-ACCESS  read-only
  STATUS  current
  DESCRIPTION "Exhaust gas port 4 temperature. Scaling factor 1 [degrees Celsius]"
  ::= { engineEntry 46 }

engExhGasPort5Temp OBJECT-TYPE
  SYNTAX  Integer32 (-273..1735)
  MAX-ACCESS  read-only
  STATUS  current
  DESCRIPTION "Exhaust gas port 5 temperature. Scaling factor 1 [degrees Celsius]"
  ::= { engineEntry 47 }

engExhGasPort6Temp OBJECT-TYPE
  SYNTAX  Integer32 (-273..1735)
  MAX-ACCESS  read-only
  STATUS  current
  DESCRIPTION "Exhaust gas port 6 temperature. Scaling factor 1 [degrees Celsius]"
  ::= { engineEntry 48 }

engExhGasPort7Temp OBJECT-TYPE
  SYNTAX  Integer32 (-273..1735)
  MAX-ACCESS  read-only
  STATUS  current
  DESCRIPTION "Exhaust gas port 7 temperature. Scaling factor 1 [degrees Celsius]"
  ::= { engineEntry 49 }

engExhGasPort8Temp OBJECT-TYPE
  SYNTAX  Integer32 (-273..1735)
  MAX-ACCESS  read-only
  STATUS  current
  DESCRIPTION "Exhaust gas port 8 temperature. Scaling factor 1 [degrees Celsius]"
  ::= { engineEntry 50 }

engExhGasPort9Temp OBJECT-TYPE
  SYNTAX  Integer32 (-273..1735)
  MAX-ACCESS  read-only
  STATUS  current
  DESCRIPTION "Exhaust gas port 9 temperature. Scaling factor 1 [degrees Celsius]"
  ::= { engineEntry 51 }

engExhGasPort10Temp OBJECT-TYPE
  SYNTAX  Integer32 (-273..1735)
  MAX-ACCESS  read-only
  STATUS  current
  DESCRIPTION "Exhaust gas port 10 temperature. Scaling factor 1 [degrees Celsius]"
  ::= { engineEntry 52 }

engExhGasPort11Temp OBJECT-TYPE
  SYNTAX  Integer32 (-273..1735)
  MAX-ACCESS  read-only
  STATUS  current
  DESCRIPTION "Exhaust gas port 11 temperature. Scaling factor 1 [degrees Celsius]"
  ::= { engineEntry 53 }

engExhGasPort12Temp OBJECT-TYPE
  SYNTAX  Integer32 (-273..1735)
  MAX-ACCESS  read-only
  STATUS  current
  DESCRIPTION "Exhaust gas port 12 temperature. Scaling factor 1 [degrees Celsius]"
  ::= { engineEntry 54 }

engExhGasPort13Temp OBJECT-TYPE
  SYNTAX  Integer32 (-273..1735)
  MAX-ACCESS  read-only
  STATUS  current
  DESCRIPTION "Exhaust gas port 13 temperature. Scaling factor 1 [degrees Celsius]"
  ::= { engineEntry 55 }

engExhGasPort14Temp OBJECT-TYPE
  SYNTAX  Integer32 (-273..1735)
  MAX-ACCESS  read-only
  STATUS  current
  DESCRIPTION "Exhaust gas port 14 temperature. Scaling factor 1 [degrees Celsius]"
  ::= { engineEntry 56 }

engExhGasPort15Temp OBJECT-TYPE
  SYNTAX  Integer32 (-273..1735)
  MAX-ACCESS  read-only
  STATUS  current
  DESCRIPTION "Exhaust gas port 15 temperature. Scaling factor 1 [degrees Celsius]"
  ::= { engineEntry 57 }

engExhGasPort16Temp OBJECT-TYPE
  SYNTAX  Integer32 (-273..1735)
  MAX-ACCESS  read-only
  STATUS  current
  DESCRIPTION "Exhaust gas port 16 temperature. Scaling factor 1 [degrees Celsius]"
  ::= { engineEntry 58 }

engIntercoolerTemp OBJECT-TYPE
  SYNTAX  Integer32 (-40..210)
  MAX-ACCESS  read-only
  STATUS  current
  DESCRIPTION "Intercooler temperature. Scaling factor 1 [degrees Celsius]"
  ::= { engineEntry 59 }

engTurboOilTemp OBJECT-TYPE
  SYNTAX  Unsigned32 (0..8031)
  MAX-ACCESS  read-only
  STATUS  current
  DESCRIPTION "Turbo oil temperature. Scaling factor 1 [degrees Celsius]"
  ::= { engineEntry 60 }

engECUTemp OBJECT-TYPE
  SYNTAX  Integer32 (-273..1735)
  MAX-ACCESS  read-only
  STATUS  current
  DESCRIPTION "ECU temperature. Scaling factor 1 [degrees Celsius]"
  ::= { engineEntry 61 }

engFanSpeed OBJECT-TYPE
  SYNTAX  Unsigned32 (0..8031)
  MAX-ACCESS  read-only
  STATUS  current
  DESCRIPTION "Fan speed"
  ::= { engineEntry 62 }

engTotalRev OBJECT-TYPE
  SYNTAX  RPMDiv1000
  MAX-ACCESS  read-only
  STATUS  current
  DESCRIPTION "Total engine revolutions"
  ::= { engineEntry 63 }

engAirInPress OBJECT-TYPE
  SYNTAX  Unsigned32 (0..500)
  MAX-ACCESS  read-only
  STATUS  current
  DESCRIPTION "Air inlet pressure"
  ::= { engineEntry 64 }

engAirFilDiffPres OBJECT-TYPE
  SYNTAX  AirFilterDiv10
  MAX-ACCESS  read-only
  STATUS  current
  DESCRIPTION "Air filter differential pressure"
  ::= { engineEntry 65 }

engTrapInPress OBJECT-TYPE
  SYNTAX  Unsigned32 (0..125)
  MAX-ACCESS  read-only
  STATUS  current
  DESCRIPTION "Air trap inlet pressure"
  ::= { engineEntry 66 }

engTurboP3 OBJECT-TYPE
  SYNTAX  Unsigned32 (0..8031)
  MAX-ACCESS  read-only
  STATUS  current
  DESCRIPTION "Turbo pressure 3"
  ::= { engineEntry 67 }

engTurboP4 OBJECT-TYPE
  SYNTAX  Unsigned32 (0..8031)
  MAX-ACCESS  read-only
  STATUS  current
  DESCRIPTION "Turbo pressure 4"
  ::= { engineEntry 68 }

engInMainfoldT3 OBJECT-TYPE
  SYNTAX  Integer32 (-40..210)
  MAX-ACCESS  read-only
  STATUS  current
  DESCRIPTION "Inlet manifold temperature 3. Scaling factor 1 [degrees Celsius]"
  ::= { engineEntry 69 }

engInMainfoldT4 OBJECT-TYPE
  SYNTAX  Integer32 (-40..210)
  MAX-ACCESS  read-only
  STATUS  current
  DESCRIPTION "Inlet manifold temperature 4. Scaling factor 1 [degrees Celsius]"
  ::= { engineEntry 70 }

engInMainfoldT5 OBJECT-TYPE
  SYNTAX  Integer32 (-40..210)
  MAX-ACCESS  read-only
  STATUS  current
  DESCRIPTION "Inlet manifold temperature 5. Scaling factor 1 [degrees Celsius]"
  ::= { engineEntry 71 }

engInMainfoldT6 OBJECT-TYPE
  SYNTAX  Integer32 (-40..210)
  MAX-ACCESS  read-only
  STATUS  current
  DESCRIPTION "Inlet manifold temperature 6. Scaling factor 1 [degrees Celsius]"
  ::= { engineEntry 72 }

engTripFuel OBJECT-TYPE
  SYNTAX  Unsigned32
  MAX-ACCESS  read-only
  STATUS  current
  DESCRIPTION "Trip fuel"
  ::= { engineEntry 73 }

engElectPotential OBJECT-TYPE
  SYNTAX  ElectricalPotentialDiv10
  MAX-ACCESS  read-only
  STATUS  current
  DESCRIPTION "Electrical potential"
  ::= { engineEntry 74 }

engPGIEngType OBJECT-TYPE
  SYNTAX  Unsigned32
  MAX-ACCESS  read-only
  STATUS  current
  DESCRIPTION "PGI Engine type"
  ::= { engineEntry 75 }

engPGIVerNum OBJECT-TYPE
  SYNTAX  Unsigned32
  MAX-ACCESS  read-only
  STATUS  current
  DESCRIPTION "PGI Engine version number"
  ::= { engineEntry 76 }

engDPTCFilLampCmd OBJECT-TYPE
  SYNTAX	INTEGER {
				off (0),
				onSolid (1),
				reservedSAE1 (2),
				reservedSAE2 (3),
				fastBlink (4),
				reservedSAE3 (5),
				reservedSAE4 (6),
				notAvailable (7)
			}
  MAX-ACCESS  read-only
  STATUS  current
  DESCRIPTION "DPTC filter lamp command"
  ::= { engineEntry 77 }

engExhSysHighTemp OBJECT-TYPE
  SYNTAX	INTEGER {
				engineStopped (0),
				preStart (1),
				availableSAE5 (2),
				availableSAE6 (3),
				availableSAE7 (4),
				availableSAE8 (5),
				availableSAE9 (6)
			}
  MAX-ACCESS  read-only
  STATUS  current
  DESCRIPTION "Exhaust system high temperature lamp"
  ::= { engineEntry 78 }

engDPTCActRegFor OBJECT-TYPE
  SYNTAX	INTEGER {
				notActive (0),
				activeForcedBySwitch (1),
				activeForcedByServiceTool (2),
				notAvailable1 (3),
				notAvailable2 (4),
				notAvailable3 (5),
				notAvailable4 (6),
				notAvailable5 (7)
			}
  MAX-ACCESS  read-only
  STATUS  current
  DESCRIPTION "DPTC Action regeneration forced"
  ::= { engineEntry 79 }

engSDWNWaitStart OBJECT-TYPE
  SYNTAX	INTEGER {
				engineStopped2 (0),
				preStart2 (1),
				warnimgUp2 (2),
				running2 (3),
				coolingDown2 (4),
				engineStoped2 (5),
				postRun2 (6),
				unknown2 (7),
				availableSAE10 (8),
				availableSAE11 (9),
				availableSAE12 (10),
				availableSAE13 (11),
				availableSAE14 (12),
				availableSAE15 (13),
				availableSAE16 (14),
				availableSAE17 (15)
			}
  MAX-ACCESS  read-only
  STATUS  current
  DESCRIPTION "Shutdown wait to start - 0x57e"
  ::= { engineEntry 80 }

engSDWNProtection OBJECT-TYPE
  SYNTAX  Unsigned32
  MAX-ACCESS  read-only
  STATUS  current
  DESCRIPTION "Shutdown protection - 0x57f"
  ::= { engineEntry 81 }

engSDWNApproaching OBJECT-TYPE
  SYNTAX  Unsigned32
  MAX-ACCESS  read-only
  STATUS  current
  DESCRIPTION "Shutdown Approaching - 0x580"
  ::= { engineEntry 82 }

engOperatingState OBJECT-TYPE
  SYNTAX  Unsigned32
  MAX-ACCESS  read-only
  STATUS  current
  DESCRIPTION "Engine operating state - 0x581"
  ::= { engineEntry 83 }

engSDWNClOverride OBJECT-TYPE
  SYNTAX  Unsigned32
  MAX-ACCESS  read-only
  STATUS  current
  DESCRIPTION "Shutdown coolant override - 0x582"
  ::= { engineEntry 84 }

engBattleshortOvr OBJECT-TYPE
  SYNTAX  Unsigned32
  MAX-ACCESS  read-only
  STATUS  current
  DESCRIPTION "Battle short override - 0x583"
  ::= { engineEntry 85 }

engModHours OBJECT-TYPE
  SYNTAX  Unsigned32
  MAX-ACCESS  read-only
  STATUS  current
  DESCRIPTION "Module engine hours - 0x584"
  ::= { engineEntry 86 }

engModOilPress OBJECT-TYPE
  SYNTAX  Unsigned32
  MAX-ACCESS  read-only
  STATUS  current
  DESCRIPTION "Module oil pressure - 0x585"
  ::= { engineEntry 87 }

engModCoolTemp OBJECT-TYPE
  SYNTAX  Unsigned32
  MAX-ACCESS  read-only
  STATUS  current
  DESCRIPTION "Module coolant temperature - 0x586"
  ::= { engineEntry 88 }

engModRPM OBJECT-TYPE
  SYNTAX  Unsigned32
  MAX-ACCESS  read-only
  STATUS  current
  DESCRIPTION "Module engine RPM - 0x587"
  ::= { engineEntry 89 }

engModChargeAlt OBJECT-TYPE
  SYNTAX  Unsigned32
  MAX-ACCESS  read-only
  STATUS  current
  DESCRIPTION "Module charge alternator - 0x888"
  ::= { engineEntry 90 }

engModSpeedFeed OBJECT-TYPE
  SYNTAX  Unsigned32
  MAX-ACCESS  read-only
  STATUS  current
  DESCRIPTION "Module speed feed - 0x589"
  ::= { engineEntry 91 }

engModFreqAdj OBJECT-TYPE
  SYNTAX  Unsigned32
  MAX-ACCESS  read-only
  STATUS  current
  DESCRIPTION "Frequency adjust - 0x58a"
  ::= { engineEntry 92 }

engAlarmWarn OBJECT-TYPE
  SYNTAX  Unsigned32
  MAX-ACCESS  read-only
  STATUS  current
  DESCRIPTION "Engine alarm warning - 0x58c"
  ::= { engineEntry 93 }

engAlarmShdwn OBJECT-TYPE
  SYNTAX  Unsigned32
  MAX-ACCESS  read-only
  STATUS  current
  DESCRIPTION "Engine alarm shutdown - 0x58d"
  ::= { engineEntry 94 }

engAlarmElectr OBJECT-TYPE
  SYNTAX  Unsigned32
  MAX-ACCESS  read-only
  STATUS  current
  DESCRIPTION "Engine alarm electrical trip - 0x58e"
  ::= { engineEntry 95 }

engAmberStopLamp OBJECT-TYPE
  SYNTAX  Unsigned32
  MAX-ACCESS  read-only
  STATUS  current
  DESCRIPTION "CAN amber stop lamp - 0x58f"
  ::= { engineEntry 96 }

engAmberLampFlash OBJECT-TYPE
  SYNTAX  Unsigned32
  MAX-ACCESS  read-only
  STATUS  current
  DESCRIPTION "CAN amber lamp flash - 0x590 = 1"
  ::= { engineEntry 97 }

engRedStopLamp OBJECT-TYPE
  SYNTAX  Unsigned32
  MAX-ACCESS  read-only
  STATUS  current
  DESCRIPTION "CAN Red stop lamp - 0x591"
  ::= { engineEntry 98 }

engRedLampFlash OBJECT-TYPE
  SYNTAX  Unsigned32
  MAX-ACCESS  read-only
  STATUS  current
  DESCRIPTION "CAN red lamp flash - 0x592 = 3"
  ::= { engineEntry 99 }

engProtLamp OBJECT-TYPE
  SYNTAX  Unsigned32
  MAX-ACCESS  read-only
  STATUS  current
  DESCRIPTION "CAN protect lamp - 0x593"
  ::= { engineEntry 100 }

engProtLampFlash OBJECT-TYPE
  SYNTAX  Unsigned32
  MAX-ACCESS  read-only
  STATUS  current
  DESCRIPTION "CAN protect lamp flash - 594    = 3"
  ::= { engineEntry 101 }

engMalfLamp OBJECT-TYPE
  SYNTAX  Unsigned32
  MAX-ACCESS  read-only
  STATUS  current
  DESCRIPTION "Malfunction Lamp - 595"
  ::= { engineEntry 102 }

engMalfLampFlash OBJECT-TYPE
  SYNTAX  Unsigned32
  MAX-ACCESS  read-only
  STATUS  current
  DESCRIPTION "Malfunction lamp flash - 596    = 3"
  ::= { engineEntry 103 }

engBattSwitched OBJECT-TYPE
  SYNTAX  Unsigned32
  MAX-ACCESS  read-only
  STATUS  current
  DESCRIPTION "Battery potential - 0x598  = 0x78"
  ::= { engineEntry 104 }

engChargPotential OBJECT-TYPE
  SYNTAX  Unsigned32
  MAX-ACCESS  read-only
  STATUS  current
  DESCRIPTION "Charging potential - 599    = 0x82"
  ::= { engineEntry 105 }

engCharAltCurr OBJECT-TYPE
  SYNTAX  Unsigned32
  MAX-ACCESS  read-only
  STATUS  current
  DESCRIPTION "Charge alternator current - 59a    = 0x0f"
  ::= { engineEntry 106 }

engBattCurr OBJECT-TYPE
  SYNTAX  Unsigned32
  MAX-ACCESS  read-only
  STATUS  current
  DESCRIPTION "Battery current - 59b"
  ::= { engineEntry 107 }

engTorqueMode OBJECT-TYPE
  SYNTAX  Unsigned32
  MAX-ACCESS  read-only
  STATUS  current
  DESCRIPTION "Engine torque mode - 59c"
  ::= { engineEntry 108 }

engStarterMode OBJECT-TYPE
  SYNTAX  Unsigned32
  MAX-ACCESS  read-only
  STATUS  current
  DESCRIPTION "Engine starter mode - 0x59d"
  ::= { engineEntry 109 }

engCIStatus OBJECT-TYPE
  SYNTAX  Unsigned32
  MAX-ACCESS  read-only
  STATUS  current
  DESCRIPTION "CAN CI status - 59e    =  0"
  ::= { engineEntry 110 }

engDemandedSpeed OBJECT-TYPE
  SYNTAX  Unsigned32
  MAX-ACCESS  read-only
  STATUS  current
  DESCRIPTION "Demand speed - 59f  = ffff"
  ::= { engineEntry 111 }

engSpeedFBUp OBJECT-TYPE
  SYNTAX  Unsigned32
  MAX-ACCESS  read-only
  STATUS  current
  DESCRIPTION "Speed up - 5a0  = ffff"
  ::= { engineEntry 112 }

engSpeedFBDown OBJECT-TYPE
  SYNTAX  Unsigned32
  MAX-ACCESS  read-only
  STATUS  current
  DESCRIPTION "Speed down - 5a1  = ffff"
  ::= { engineEntry 113 }

engSpeedFailMode OBJECT-TYPE
  SYNTAX  Unsigned32
  MAX-ACCESS  read-only
  STATUS  current
  DESCRIPTION "Speed fail - 5a2  = ffff"
  ::= { engineEntry 114 }

engCurrSDSrc OBJECT-TYPE
  SYNTAX  Unsigned32
  MAX-ACCESS  read-only
  STATUS  current
  DESCRIPTION "Current SD source - 5a3  = ffff"
  ::= { engineEntry 115 }

engFbackSDCAN OBJECT-TYPE
  SYNTAX  Unsigned32
  MAX-ACCESS  read-only
  STATUS  current
  DESCRIPTION "Feedback SD CAN - 5a4 = fffb"
  ::= { engineEntry 116 }

engFbackSDAnalog OBJECT-TYPE
  SYNTAX  Unsigned32
  MAX-ACCESS  read-only
  STATUS  current
  DESCRIPTION "Feedback SD analogue - 5a5  = ffff"
  ::= { engineEntry 117 }

engFailureCodes OBJECT-TYPE
  SYNTAX  Unsigned32
  MAX-ACCESS  read-only
  STATUS  current
  DESCRIPTION "Failure codes - 5a6  = ffff"
  ::= { engineEntry 118 }

engActDrop OBJECT-TYPE
  SYNTAX  Unsigned32
  MAX-ACCESS  read-only
  STATUS  current
  DESCRIPTION "Actual droop - 5a7  = ffff"
  ::= { engineEntry 119 }

engStartStatus OBJECT-TYPE
  SYNTAX  Unsigned32
  MAX-ACCESS  read-only
  STATUS  current
  DESCRIPTION "Start status - 5a8 = fffb"
  ::= { engineEntry 120 }

engProtOrStatus OBJECT-TYPE
  SYNTAX  Unsigned32
  MAX-ACCESS  read-only
  STATUS  current
  DESCRIPTION "Protection override status - 5a9  = ffff"
  ::= { engineEntry 121 }

engMTURuniingState OBJECT-TYPE
  SYNTAX  Unsigned32
  MAX-ACCESS  read-only
  STATUS  current
  DESCRIPTION "MTU running state - 5aa  = ffff"
  ::= { engineEntry 122 }

engCylCutOff OBJECT-TYPE
  SYNTAX  Unsigned32
  MAX-ACCESS  read-only
  STATUS  current
  DESCRIPTION "Cylinder cut off - 5ab  = ffff"
  ::= { engineEntry 123 }

engLoadGenStatus OBJECT-TYPE
  SYNTAX  Unsigned32
  MAX-ACCESS  read-only
  STATUS  current
  DESCRIPTION "Load gen status - 5ac = fffb"
  ::= { engineEntry 124 }

engEtxStopState OBJECT-TYPE
  SYNTAX  Unsigned32
  MAX-ACCESS  read-only
  STATUS  current
  DESCRIPTION "Load gen status - 5ac = fffb"
  ::= { engineEntry 125 }

engCurrOPMode OBJECT-TYPE
  SYNTAX  Unsigned32
  MAX-ACCESS  read-only
  STATUS  current
  DESCRIPTION "Current operating mode - 5ae  = ffff"
  ::= { engineEntry 126 }

engMTUReqTorque OBJECT-TYPE
  SYNTAX  Unsigned32
  MAX-ACCESS  read-only
  STATUS  current
  DESCRIPTION "MTU required torque - 5af  = ffff"
  ::= { engineEntry 127 }

engTripAvgFuel OBJECT-TYPE
  SYNTAX  AverageFuelDiv100
  MAX-ACCESS  read-only
  STATUS  current
  DESCRIPTION "Trip average fuel - 5b0  = 0"
  ::= { engineEntry 128 }

engECURatedPower OBJECT-TYPE
  SYNTAX  Unsigned32
  MAX-ACCESS  read-only
  STATUS  current
  DESCRIPTION "ECU rated power - 5b1  = 0"
  ::= { engineEntry 129 }

engECURatedSpeed OBJECT-TYPE
  SYNTAX  Unsigned32
  MAX-ACCESS  read-only
  STATUS  current
  DESCRIPTION "ECU rated speed - 5b2  = 0"
  ::= { engineEntry 130 }

engECUIdleSpeed OBJECT-TYPE
  SYNTAX  Unsigned32
  MAX-ACCESS  read-only
  STATUS  current
  DESCRIPTION "ECU idle speed - 5b3  = fffb"
  ::= { engineEntry 131 }

engECUDesirSpeed OBJECT-TYPE
  SYNTAX  Unsigned32
  MAX-ACCESS  read-only
  STATUS  current
  DESCRIPTION "ECU desired speed - 5b4  = 0"
  ::= { engineEntry 132 }

engECUPreheatStat OBJECT-TYPE
  SYNTAX  Unsigned32
  MAX-ACCESS  read-only
  STATUS  current
  DESCRIPTION "ECU preheat status - 5b5  = 1"
  ::= { engineEntry 133 }

engManiFoldPres OBJECT-TYPE
  SYNTAX  Unsigned32
  MAX-ACCESS  read-only
  STATUS  current
  DESCRIPTION "Manifold pressure - 5b6  = 0"
  ::= { engineEntry 134 }

engIntercoolerLevel OBJECT-TYPE
  SYNTAX  Unsigned32
  MAX-ACCESS  read-only
  STATUS  current
  DESCRIPTION "Intercoller level - 5b7  = 0"
  ::= { engineEntry 135 }

engCANLinkState OBJECT-TYPE
  SYNTAX  Unsigned32
  MAX-ACCESS  read-only
  STATUS  current
  DESCRIPTION "CAN link status"
  ::= { engineEntry 136 }

engAutoDFPRegInh OBJECT-TYPE
  SYNTAX  Unsigned32
  MAX-ACCESS  read-only
  STATUS  current
  DESCRIPTION "Tier IV Auto DPF Regeneration Inhibit"
  ::= { engineEntry 137 }

engDPTCActRegInhSwitch OBJECT-TYPE
  SYNTAX  Unsigned32
  MAX-ACCESS  read-only
  STATUS  current
  DESCRIPTION "Tier IV DPTC Active Regeneration Inhibit Switch (received from engine) SPN 3703"
  ::= { engineEntry 138 }

engSootLoadPC OBJECT-TYPE
  SYNTAX  Unsigned32
  MAX-ACCESS  read-only
  STATUS  current
  DESCRIPTION "Soot Load"
  ::= { engineEntry 139 }

engAshLoadPC OBJECT-TYPE
  SYNTAX  Unsigned32
  MAX-ACCESS  read-only
  STATUS  current
  DESCRIPTION "Ash Load"
  ::= { engineEntry 140 }

engDefTankLevel OBJECT-TYPE
  SYNTAX  Unsigned32
  MAX-ACCESS  read-only
  STATUS  current
  DESCRIPTION "DEF Tank Level"
  ::= { engineEntry 141 }

engDefTankTemp OBJECT-TYPE
  SYNTAX  Unsigned32
  MAX-ACCESS  read-only
  STATUS  current
  DESCRIPTION "DEF Tank Temperature"
  ::= { engineEntry 142 }

engDefLevelWarn OBJECT-TYPE
  SYNTAX  Unsigned32
  MAX-ACCESS  read-only
  STATUS  current
  DESCRIPTION "DEF Level Status"
  ::= { engineEntry 143 }

engDefReagentCons OBJECT-TYPE
  SYNTAX  Unsigned32
  MAX-ACCESS  read-only
  STATUS  current
  DESCRIPTION "DEF Consumption"
  ::= { engineEntry 144 }

engDefInducReason OBJECT-TYPE
  SYNTAX  Unsigned32
  MAX-ACCESS  read-only
  STATUS  current
  DESCRIPTION "Aftertreatment Status Reason"
  ::= { engineEntry 145 }

engDefInducSever OBJECT-TYPE
  SYNTAX  Unsigned32
  MAX-ACCESS  read-only
  STATUS  current
  DESCRIPTION "Aftertreatment Status Severity"
  ::= { engineEntry 146 }

engDefCounterMin OBJECT-TYPE
  SYNTAX  Unsigned32
  MAX-ACCESS  read-only
  STATUS  current
  DESCRIPTION "Time left until action needed"
  ::= { engineEntry 147 }

engTLTTorqueReduc OBJECT-TYPE
  SYNTAX  Unsigned32
  MAX-ACCESS  read-only
  STATUS  current
  DESCRIPTION "Time until Torque Reduction"
  ::= { engineEntry 148 }

engTLTVehspdReduc OBJECT-TYPE
  SYNTAX  Unsigned32
  MAX-ACCESS  read-only
  STATUS  current
  DESCRIPTION "Time until Speed Reduction"
  ::= { engineEntry 149 }

engEGRPress OBJECT-TYPE
  SYNTAX  Unsigned32
  MAX-ACCESS  read-only
  STATUS  current
  DESCRIPTION "EGR Pressure"
  ::= { engineEntry 150 }

engEGRTemp OBJECT-TYPE
  SYNTAX  Unsigned32
  MAX-ACCESS  read-only
  STATUS  current
  DESCRIPTION "EGR Temperature"
  ::= { engineEntry 151 }

engAmbAirTemp OBJECT-TYPE
  SYNTAX  Unsigned32
  MAX-ACCESS  read-only
  STATUS  current
  DESCRIPTION "Ambient Air Temperature"
  ::= { engineEntry 152 }

engAirIntakeTemp OBJECT-TYPE
  SYNTAX  Unsigned32
  MAX-ACCESS  read-only
  STATUS  current
  DESCRIPTION "Air Intake Temperature"
  ::= { engineEntry 153 }

engSRCOperatInduc OBJECT-TYPE
  SYNTAX  Unsigned32 (0..15)
  MAX-ACCESS  read-only
  STATUS  current
  DESCRIPTION "DEF Lamps - SCR Inducement - Bit Field - 3 bit length"
  ::= { engineEntry 154 }

engTankLevLowLost OBJECT-TYPE
  SYNTAX  Unsigned32 (0..15)
  MAX-ACCESS  read-only
  STATUS  current
  DESCRIPTION "DEF Lamps - DEF Level Low - Bit Field - 3bit length"
  ::= { engineEntry 155 }

engMiscAltSpeedSel OBJECT-TYPE
  SYNTAX  Unsigned32 (0..1)
  MAX-ACCESS  read-only
  STATUS  current
  DESCRIPTION "CAN Alternate engine speed selected"
  ::= { engineEntry 156 }

engExhGasP17Temp OBJECT-TYPE
  SYNTAX  Integer32 (-273..1735)
  MAX-ACCESS  read-only
  STATUS  current
  DESCRIPTION "Exhaust gas port 17 temperature"
  ::= { engineEntry 157 }

engExhGasP18Temp OBJECT-TYPE
  SYNTAX  Integer32 (-273..1735)
  MAX-ACCESS  read-only
  STATUS  current
  DESCRIPTION "Exhaust gas port 18 temperature"
  ::= { engineEntry 158 }

engExhGasP19Temp OBJECT-TYPE
  SYNTAX  Integer32 (-273..1735)
  MAX-ACCESS  read-only
  STATUS  current
  DESCRIPTION "Exhaust gas port 19 temperature"
  ::= { engineEntry 159 }

engExhGasP20Temp OBJECT-TYPE
  SYNTAX  Integer32 (-273..1735)
  MAX-ACCESS  read-only
  STATUS  current
  DESCRIPTION "Exhaust gas port 20 temperature"
  ::= { engineEntry 160 }

engInstFuelRate OBJECT-TYPE
  SYNTAX  Unsigned32
  MAX-ACCESS  read-only
  STATUS  current
  DESCRIPTION "Instant Fuel Rate"
  ::= { engineEntry 161 }

engDPTCFiltStat OBJECT-TYPE
  SYNTAX  Unsigned32
  MAX-ACCESS  read-only
  STATUS  current
  DESCRIPTION "DPTC Filter Status"
  ::= { engineEntry 162 }

engDPTCActRegInh OBJECT-TYPE
  SYNTAX  Unsigned32
  MAX-ACCESS  read-only
  STATUS  current
  DESCRIPTION "DPTC Active Regeneration Inhibit"
  ::= { engineEntry 163 }

engDPTCActRegInhEt OBJECT-TYPE
  SYNTAX  Unsigned32
  MAX-ACCESS  read-only
  STATUS  current
  DESCRIPTION "DPTC Active Regeneration Inhibit ET"
  ::= { engineEntry 164 }

engDefTankStat OBJECT-TYPE
  SYNTAX  Unsigned32
  MAX-ACCESS  read-only
  STATUS  current
  DESCRIPTION "DEF Tank Status"
  ::= { engineEntry 165 }

engFuelGasPress OBJECT-TYPE
  SYNTAX  Unsigned32
  MAX-ACCESS  read-only
  STATUS  current
  DESCRIPTION "Gas Fuel Pressure"
  ::= { engineEntry 166 }

engThrotPos1 OBJECT-TYPE
  SYNTAX  Unsigned32
  MAX-ACCESS  read-only
  STATUS  current
  DESCRIPTION "Throttle Position 1"
  ::= { engineEntry 167 }

engThrotPos2 OBJECT-TYPE
  SYNTAX  Unsigned32
  MAX-ACCESS  read-only
  STATUS  current
  DESCRIPTION "Throttle Position 2"
  ::= { engineEntry 168 }

busFreq OBJECT-TYPE
  SYNTAX  FreqDiv10
  MAX-ACCESS  read-only
  STATUS  current
  DESCRIPTION "Bus frequency. Scaling Factor 0.1"
  ::= { busTableEntry 2 }

busL1Volts OBJECT-TYPE
  SYNTAX  VoltsLNDiv10
  MAX-ACCESS  read-only
  STATUS  current
  DESCRIPTION "Bus L1-N voltage. Scaling Factor 0.1"
  ::= { busTableEntry 3 }

busL2Volts OBJECT-TYPE
  SYNTAX  VoltsLNDiv10
  MAX-ACCESS  read-only
  STATUS  current
  DESCRIPTION "Bus L2-N voltage. Scaling Factor 0.1"
  ::= { busTableEntry 4 }

busL3Volts OBJECT-TYPE
  SYNTAX  VoltsLNDiv10
  MAX-ACCESS  read-only
  STATUS  current
  DESCRIPTION "Bus L3-N voltage. Scaling Factor 0.1"
  ::= { busTableEntry 5 }

busL1L2Volts OBJECT-TYPE
  SYNTAX  VoltsLLDiv10
  MAX-ACCESS  read-only
  STATUS  current
  DESCRIPTION "Bus L1-L2 voltage. Scaling Factor 0.1"
  ::= { busTableEntry 6 }

busL2L3Volts OBJECT-TYPE
  SYNTAX  VoltsLLDiv10
  MAX-ACCESS  read-only
  STATUS  current
  DESCRIPTION "Bus L2-L3 voltage. Scaling Factor 0.1"
  ::= { busTableEntry 7 }

busL3L1Volts OBJECT-TYPE
  SYNTAX  VoltsLLDiv10
  MAX-ACCESS  read-only
  STATUS  current
  DESCRIPTION "Bus L3-L1 voltage. Scaling Factor 0.1"
  ::= { busTableEntry 8 }

busL1Current OBJECT-TYPE
  SYNTAX  CurrentDiv10
  MAX-ACCESS  read-only
  STATUS  current
  DESCRIPTION "Bus L1 current. Scaling Factor 0.1"
  ::= { busTableEntry 9 }

busL2Current OBJECT-TYPE
  SYNTAX  CurrentDiv10
  MAX-ACCESS  read-only
  STATUS  current
  DESCRIPTION "Bus L2 current. Scaling Factor 0.1"
  ::= { busTableEntry 10 }

busL3Current OBJECT-TYPE
  SYNTAX  CurrentDiv10
  MAX-ACCESS  read-only
  STATUS  current
  DESCRIPTION "Bus L3 current. Scaling Factor 0.1"
  ::= { busTableEntry 11 }

busECurrent OBJECT-TYPE
  SYNTAX  CurrentDiv10
  MAX-ACCESS  read-only
  STATUS  current
  DESCRIPTION "Bus earth current. Scaling Factor 0.1"
  ::= { busTableEntry 12 }

busL1Watts OBJECT-TYPE
  SYNTAX  Integer32 (-999999999..999999999)
  MAX-ACCESS  read-only
  STATUS  current
  DESCRIPTION "Bus L1 watts. Scaling Factor 1"
  ::= { busTableEntry 13 }

busL2Watts OBJECT-TYPE
  SYNTAX  Integer32 (-999999999..999999999)
  MAX-ACCESS  read-only
  STATUS  current
  DESCRIPTION "Bus L2 watts. Scaling Factor 1"
  ::= { busTableEntry 14 }

busL3Watts OBJECT-TYPE
  SYNTAX  Integer32 (-999999999..999999999)
  MAX-ACCESS  read-only
  STATUS  current
  DESCRIPTION "Bus L3 watts. Scaling Factor 1"
  ::= { busTableEntry 15 }

busRotations OBJECT-TYPE
  SYNTAX  Integer32 (0..3)
  MAX-ACCESS  read-only
  STATUS  current
  DESCRIPTION "Bus phase rotation. Scaling Factor"
  ::= { busTableEntry 16 }

busWattsTotal OBJECT-TYPE
  SYNTAX  Integer32 (-999999999..999999999)
  MAX-ACCESS  read-only
  STATUS  current
  DESCRIPTION "Bus total watts. Scaling Factor 1"
  ::= { busTableEntry 17 }

busL1VA OBJECT-TYPE
  SYNTAX  Unsigned32 (0..99999999)
  MAX-ACCESS  read-only
  STATUS  current
  DESCRIPTION "Bus L1 VA. Scaling Factor 1"
  ::= { busTableEntry 18 }

busL2VA OBJECT-TYPE
  SYNTAX  Unsigned32 (0..99999999)
  MAX-ACCESS  read-only
  STATUS  current
  DESCRIPTION "Bus L2 VA. Scaling Factor 1"
  ::= { busTableEntry 19 }

busL3VA OBJECT-TYPE
  SYNTAX  Unsigned32 (0..99999999)
  MAX-ACCESS  read-only
  STATUS  current
  DESCRIPTION "Bus L3 VA. Scaling Factor 1"
  ::= { busTableEntry 20 }

busTotalVA OBJECT-TYPE
  SYNTAX  Unsigned32 (0..999999999)
  MAX-ACCESS  read-only
  STATUS  current
  DESCRIPTION "Bus total VA. Scaling Factor 1"
  ::= { busTableEntry 21 }

busL1VAr OBJECT-TYPE
  SYNTAX  Integer32 (-99999999..99999999)
  MAX-ACCESS  read-only
  STATUS  current
  DESCRIPTION "Bus L1 Var. Scaling Factor 1"
  ::= { busTableEntry 22 }

busL2VAr OBJECT-TYPE
  SYNTAX  Integer32 (-99999999..99999999)
  MAX-ACCESS  read-only
  STATUS  current
  DESCRIPTION "Bus L2 Var. Scaling Factor 1"
  ::= { busTableEntry 23 }

busL3VAr OBJECT-TYPE
  SYNTAX  Integer32 (-99999999..99999999)
  MAX-ACCESS  read-only
  STATUS  current
  DESCRIPTION "Bus L3 Var. Scaling Factor 1"
  ::= { busTableEntry 24 }

busTotalVAr OBJECT-TYPE
  SYNTAX  Integer32 (-999999999..999999999)
  MAX-ACCESS  read-only
  STATUS  current
  DESCRIPTION "Bus total Var. Scaling Factor 1"
  ::= { busTableEntry 25 }

busPowerFactorL1 OBJECT-TYPE
  SYNTAX  PowerFactorDiv100
  MAX-ACCESS  read-only
  STATUS  current
  DESCRIPTION "Bus power factor L1. Scaling Factor 0.01"
  ::= { busTableEntry 26 }

busPowerFactorL2 OBJECT-TYPE
  SYNTAX  PowerFactorDiv100
  MAX-ACCESS  read-only
  STATUS  current
  DESCRIPTION "Bus power factor L2. Scaling Factor 0.01"
  ::= { busTableEntry 27 }

busPowerFactorL3 OBJECT-TYPE
  SYNTAX  PowerFactorDiv100
  MAX-ACCESS  read-only
  STATUS  current
  DESCRIPTION "Bus power factor L3. Scaling Factor 0.01"
  ::= { busTableEntry 28 }

busAvgPowerFactor OBJECT-TYPE
  SYNTAX  PowerFactorDiv100
  MAX-ACCESS  read-only
  STATUS  current
  DESCRIPTION "Bus average power factor. Scaling Factor 0.01"
  ::= { busTableEntry 29 }

busPowerTotalPC OBJECT-TYPE
  SYNTAX  PowerPCDiv10
  MAX-ACCESS  read-only
  STATUS  current
  DESCRIPTION "Bus percentage of full power. Scaling Factor 0.1"
  ::= { busTableEntry 30 }

busVARTotalPC OBJECT-TYPE
  SYNTAX  PowerPCDiv10
  MAX-ACCESS  read-only
  STATUS  current
  DESCRIPTION "Bus percentage of full Var. Scaling Factor 0.1"
  ::= { busTableEntry 31 }

busVoltageLNAvg OBJECT-TYPE
  SYNTAX  VoltsLNDiv10
  MAX-ACCESS  read-only
  STATUS  current
  DESCRIPTION "Bus L-N voltage average. Scaling Factor 0.1"
  ::= { busTableEntry 32 }

busVoltageLNDiff OBJECT-TYPE
  SYNTAX  VoltsLNDiv10
  MAX-ACCESS  read-only
  STATUS  current
  DESCRIPTION "Bus L-N voltage difference. Scaling Factor 0.1"
  ::= { busTableEntry 33 }

busVoltageLNMin OBJECT-TYPE
  SYNTAX  VoltsLNDiv10
  MAX-ACCESS  read-only
  STATUS  current
  DESCRIPTION "Bus L-N voltage min. Scaling Factor 0.1"
  ::= { busTableEntry 34 }

busVoltageLNMax OBJECT-TYPE
  SYNTAX  VoltsLNDiv10
  MAX-ACCESS  read-only
  STATUS  current
  DESCRIPTION "Bus L-N voltage max. Scaling Factor 0.1"
  ::= { busTableEntry 35 }

busVoltageLLAvg OBJECT-TYPE
  SYNTAX  VoltsLLDiv10
  MAX-ACCESS  read-only
  STATUS  current
  DESCRIPTION "Bus L-L voltage average. Scaling Factor 0.1"
  ::= { busTableEntry 36 }

busVoltageLLDiff OBJECT-TYPE
  SYNTAX  VoltsLLDiv10
  MAX-ACCESS  read-only
  STATUS  current
  DESCRIPTION "Bus L-L voltage difference. Scaling Factor 0.1"
  ::= { busTableEntry 37 }

busVoltageLLMin OBJECT-TYPE
  SYNTAX  VoltsLLDiv10
  MAX-ACCESS  read-only
  STATUS  current
  DESCRIPTION "Bus L-L voltage min. Scaling Factor 0.1"
  ::= { busTableEntry 38 }

busVoltageLLMax OBJECT-TYPE
  SYNTAX  VoltsLLDiv10
  MAX-ACCESS  read-only
  STATUS  current
  DESCRIPTION "Bus L-L voltage max. Scaling Factor 0.1"
  ::= { busTableEntry 39 }

gencommP166Reg-0-1 OBJECT-TYPE
  SYNTAX  Unsigned32
  MAX-ACCESS  read-only
  STATUS  current
  DESCRIPTION "Gencomm Page 166 Register 0 to 1"
  ::= { gencommP166Entry 2 }

gencommP166Reg-2-3 OBJECT-TYPE
  SYNTAX  Unsigned32
  MAX-ACCESS  read-only
  STATUS  current
  DESCRIPTION "Gencomm Page 166  Register 2 to 3"
  ::= { gencommP166Entry 3 }

gencommP166Reg-4-5 OBJECT-TYPE
  SYNTAX  Unsigned32
  MAX-ACCESS  read-only
  STATUS  current
  DESCRIPTION "Gencomm Page 166  Register 4 to 5"
  ::= { gencommP166Entry 4 }

gencommP166Reg-6-7 OBJECT-TYPE
  SYNTAX  Unsigned32
  MAX-ACCESS  read-only
  STATUS  current
  DESCRIPTION "Gencomm Page 166  Register 6 to 7"
  ::= { gencommP166Entry 5 }

gencommP166Reg-8-9 OBJECT-TYPE
  SYNTAX  Unsigned32
  MAX-ACCESS  read-only
  STATUS  current
  DESCRIPTION "Gencomm Page 166 Register 8 to 9"
  ::= { gencommP166Entry 6 }

gencommP166Reg-10-11 OBJECT-TYPE
  SYNTAX  Unsigned32
  MAX-ACCESS  read-only
  STATUS  current
  DESCRIPTION "Gencomm Page 166 Register 10 to 11"
  ::= { gencommP166Entry 7 }

gencommP166Reg-12-13 OBJECT-TYPE
  SYNTAX  Unsigned32
  MAX-ACCESS  read-only
  STATUS  current
  DESCRIPTION "Gencomm Page 166 Register 12 to 13"
  ::= { gencommP166Entry 8 }

gencommP166Reg-14-15 OBJECT-TYPE
  SYNTAX  Unsigned32
  MAX-ACCESS  read-only
  STATUS  current
  DESCRIPTION "Gencomm Page 166 Register 14 to 15"
  ::= { gencommP166Entry 9 }

gencommP166Reg-16-17 OBJECT-TYPE
  SYNTAX  Unsigned32
  MAX-ACCESS  read-only
  STATUS  current
  DESCRIPTION "Gencomm Page 166 Register 16 to 17"
  ::= { gencommP166Entry 10 }

gencommP166Reg-18-19 OBJECT-TYPE
  SYNTAX  Unsigned32
  MAX-ACCESS  read-only
  STATUS  current
  DESCRIPTION "Gencomm Page 166 Register 18 to 19"
  ::= { gencommP166Entry 11 }

gencommP166Reg-20-21 OBJECT-TYPE
  SYNTAX  Unsigned32
  MAX-ACCESS  read-only
  STATUS  current
  DESCRIPTION "Gencomm Page 166 Register 20 to 21"
  ::= { gencommP166Entry 12 }

gencommP166Reg-22-23 OBJECT-TYPE
  SYNTAX  Unsigned32
  MAX-ACCESS  read-only
  STATUS  current
  DESCRIPTION "Gencomm Page 166 Register 22 to 23"
  ::= { gencommP166Entry 13 }

gencommP166Reg-24-25 OBJECT-TYPE
  SYNTAX  Unsigned32
  MAX-ACCESS  read-only
  STATUS  current
  DESCRIPTION "Gencomm Page 166 Register 24 to 25"
  ::= { gencommP166Entry 14 }

gencommP166Reg-26-27 OBJECT-TYPE
  SYNTAX  Unsigned32
  MAX-ACCESS  read-only
  STATUS  current
  DESCRIPTION "Gencomm Page 166 Register 26 to 27"
  ::= { gencommP166Entry 15 }

gencommP166Reg-28-29 OBJECT-TYPE
  SYNTAX  Unsigned32
  MAX-ACCESS  read-only
  STATUS  current
  DESCRIPTION "Gencomm Page 166 Register 28 to 29"
  ::= { gencommP166Entry 16 }

gencommP166Reg-30-31 OBJECT-TYPE
  SYNTAX  Unsigned32
  MAX-ACCESS  read-only
  STATUS  current
  DESCRIPTION "Gencomm Page 166 Register 30 to 31"
  ::= { gencommP166Entry 17 }

gencommP166Reg-32-33 OBJECT-TYPE
  SYNTAX  Unsigned32
  MAX-ACCESS  read-only
  STATUS  current
  DESCRIPTION "Gencomm Page 166 Register 32 to 33"
  ::= { gencommP166Entry 18 }

gencommP166Reg-34-35 OBJECT-TYPE
  SYNTAX  Unsigned32
  MAX-ACCESS  read-only
  STATUS  current
  DESCRIPTION "Gencomm Page 166 Register 34 to 35"
  ::= { gencommP166Entry 19 }

gencommP166Reg-36-37 OBJECT-TYPE
  SYNTAX  Unsigned32
  MAX-ACCESS  read-only
  STATUS  current
  DESCRIPTION "Gencomm Page 166 Register 36 to 37"
  ::= { gencommP166Entry 20 }

gencommP166Reg-38-39 OBJECT-TYPE
  SYNTAX  Unsigned32
  MAX-ACCESS  read-only
  STATUS  current
  DESCRIPTION "Gencomm Page 166 Register 38 to 39"
  ::= { gencommP166Entry 21 }

gencommP166Reg-40-41 OBJECT-TYPE
  SYNTAX  Unsigned32
  MAX-ACCESS  read-only
  STATUS  current
  DESCRIPTION "Gencomm Page 166 Register 40 to 41"
  ::= { gencommP166Entry 22 }

gencommP166Reg-42-43 OBJECT-TYPE
  SYNTAX  Unsigned32
  MAX-ACCESS  read-only
  STATUS  current
  DESCRIPTION "Gencomm Page 166 Register 42 to 43"
  ::= { gencommP166Entry 23 }

gencommP166Reg-44-45 OBJECT-TYPE
  SYNTAX  Unsigned32
  MAX-ACCESS  read-only
  STATUS  current
  DESCRIPTION "Gencomm Page 166 Register 44 to 45"
  ::= { gencommP166Entry 24 }

gencommP166Reg-46-47 OBJECT-TYPE
  SYNTAX  Unsigned32
  MAX-ACCESS  read-only
  STATUS  current
  DESCRIPTION "Gencomm Page 166 Register 46 to 47"
  ::= { gencommP166Entry 25 }

gencommP166Reg-48-49 OBJECT-TYPE
  SYNTAX  Unsigned32
  MAX-ACCESS  read-only
  STATUS  current
  DESCRIPTION "Gencomm Page 166 Register 48 to 49"
  ::= { gencommP166Entry 26 }

gencommP166Reg-50-51 OBJECT-TYPE
  SYNTAX  Unsigned32
  MAX-ACCESS  read-only
  STATUS  current
  DESCRIPTION "Gencomm Page 166 Register 50 to 51"
  ::= { gencommP166Entry 27 }

gencommP166Reg-52-53 OBJECT-TYPE
  SYNTAX  Unsigned32
  MAX-ACCESS  read-only
  STATUS  current
  DESCRIPTION "Gencomm Page 166 Register 52 to 53"
  ::= { gencommP166Entry 28 }

gencommP166Reg-54-55 OBJECT-TYPE
  SYNTAX  Unsigned32
  MAX-ACCESS  read-only
  STATUS  current
  DESCRIPTION "Gencomm Page 166 Register 54 to 55"
  ::= { gencommP166Entry 29 }

gencommP166Reg-56-57 OBJECT-TYPE
  SYNTAX  Unsigned32
  MAX-ACCESS  read-only
  STATUS  current
  DESCRIPTION "Gencomm Page 166 Register 56 to 57"
  ::= { gencommP166Entry 30 }

gencommP166Reg-58-59 OBJECT-TYPE
  SYNTAX  Unsigned32
  MAX-ACCESS  read-only
  STATUS  current
  DESCRIPTION "Gencomm Page 166 Register 58 to 59"
  ::= { gencommP166Entry 31 }

gencommP166Reg-60-61 OBJECT-TYPE
  SYNTAX  Unsigned32
  MAX-ACCESS  read-only
  STATUS  current
  DESCRIPTION "Gencomm Page 166 Register 60 to 61"
  ::= { gencommP166Entry 32 }

gencommP166Reg-62-63 OBJECT-TYPE
  SYNTAX  Unsigned32
  MAX-ACCESS  read-only
  STATUS  current
  DESCRIPTION "Gencomm Page 166 Register 62 to 63"
  ::= { gencommP166Entry 33 }

gencommP166Reg-64-65 OBJECT-TYPE
  SYNTAX  Unsigned32
  MAX-ACCESS  read-only
  STATUS  current
  DESCRIPTION "Gencomm Page 166 Register 64 to 65"
  ::= { gencommP166Entry 34 }

gencommP166Reg-66-67 OBJECT-TYPE
  SYNTAX  Unsigned32
  MAX-ACCESS  read-only
  STATUS  current
  DESCRIPTION "Gencomm Page 166 Register 66 to 67"
  ::= { gencommP166Entry 35 }

gencommP166Reg-68-69 OBJECT-TYPE
  SYNTAX  Unsigned32
  MAX-ACCESS  read-only
  STATUS  current
  DESCRIPTION "Gencomm Page 166 Register 68 to 69"
  ::= { gencommP166Entry 36 }

gencommP166Reg-70-71 OBJECT-TYPE
  SYNTAX  Unsigned32
  MAX-ACCESS  read-only
  STATUS  current
  DESCRIPTION "Gencomm Page 166 Register 70 to 71"
  ::= { gencommP166Entry 37 }

gencommP166Reg-72-73 OBJECT-TYPE
  SYNTAX  Unsigned32
  MAX-ACCESS  read-only
  STATUS  current
  DESCRIPTION "Gencomm Page 166 Register 72 to 73"
  ::= { gencommP166Entry 38 }

gencommP166Reg-74-75 OBJECT-TYPE
  SYNTAX  Unsigned32
  MAX-ACCESS  read-only
  STATUS  current
  DESCRIPTION "Gencomm Page 166 Register 74 to 75"
  ::= { gencommP166Entry 39 }

gencommP166Reg-76-77 OBJECT-TYPE
  SYNTAX  Unsigned32
  MAX-ACCESS  read-only
  STATUS  current
  DESCRIPTION "Gencomm Page 166 Register 76 to 77"
  ::= { gencommP166Entry 40 }

gencommP166Reg-78-79 OBJECT-TYPE
  SYNTAX  Unsigned32
  MAX-ACCESS  read-only
  STATUS  current
  DESCRIPTION "Gencomm Page 166 Register 78 to 79"
  ::= { gencommP166Entry 41 }

gencommP166Reg-80-81 OBJECT-TYPE
  SYNTAX  Unsigned32
  MAX-ACCESS  read-only
  STATUS  current
  DESCRIPTION "Gencomm Page 166 Register 80 to 81"
  ::= { gencommP166Entry 42 }

gencommP166Reg-82-83 OBJECT-TYPE
  SYNTAX  Unsigned32
  MAX-ACCESS  read-only
  STATUS  current
  DESCRIPTION "Gencomm Page 166 Register 82 to 83"
  ::= { gencommP166Entry 43 }

gencommP166Reg-84-85 OBJECT-TYPE
  SYNTAX  Unsigned32
  MAX-ACCESS  read-only
  STATUS  current
  DESCRIPTION "Gencomm Page 166 Register 84 to 85"
  ::= { gencommP166Entry 44 }

gencommP166Reg-86-87 OBJECT-TYPE
  SYNTAX  Unsigned32
  MAX-ACCESS  read-only
  STATUS  current
  DESCRIPTION "Gencomm Page 166 Register 86 to 87"
  ::= { gencommP166Entry 45 }

gencommP166Reg-88-89 OBJECT-TYPE
  SYNTAX  Unsigned32
  MAX-ACCESS  read-only
  STATUS  current
  DESCRIPTION "Gencomm Page 166 Register 88 to 89"
  ::= { gencommP166Entry 46 }

gencommP166Reg-90-91 OBJECT-TYPE
  SYNTAX  Unsigned32
  MAX-ACCESS  read-only
  STATUS  current
  DESCRIPTION "Gencomm Page 166 Register 90 to 91"
  ::= { gencommP166Entry 47 }

gencommP166Reg-92-93 OBJECT-TYPE
  SYNTAX  Unsigned32
  MAX-ACCESS  read-only
  STATUS  current
  DESCRIPTION "Gencomm Page 166 Register 92 to 93"
  ::= { gencommP166Entry 48 }

gencommP166Reg-94-95 OBJECT-TYPE
  SYNTAX  Unsigned32
  MAX-ACCESS  read-only
  STATUS  current
  DESCRIPTION "Gencomm Page 166 Register 94 to 95"
  ::= { gencommP166Entry 49 }

gencommP166Reg-96-97 OBJECT-TYPE
  SYNTAX  Unsigned32
  MAX-ACCESS  read-only
  STATUS  current
  DESCRIPTION "Gencomm Page 166 Register 96 to 97"
  ::= { gencommP166Entry 50 }

gencommP166Reg-98-99 OBJECT-TYPE
  SYNTAX  Unsigned32
  MAX-ACCESS  read-only
  STATUS  current
  DESCRIPTION "Gencomm Page 166 Register 98 to 99"
  ::= { gencommP166Entry 51 }

gencommP166Reg-100-101 OBJECT-TYPE
  SYNTAX  Unsigned32
  MAX-ACCESS  read-only
  STATUS  current
  DESCRIPTION "Gencomm Page 166 Register 100 to 101"
  ::= { gencommP166Entry 52 }

gencommP166Reg-102-103 OBJECT-TYPE
  SYNTAX  Unsigned32
  MAX-ACCESS  read-only
  STATUS  current
  DESCRIPTION "Gencomm Page 166 Register 102 to 103"
  ::= { gencommP166Entry 53 }

gencommP166Reg-104-105 OBJECT-TYPE
  SYNTAX  Unsigned32
  MAX-ACCESS  read-only
  STATUS  current
  DESCRIPTION "Gencomm Page 166 Register 104 to 105"
  ::= { gencommP166Entry 54 }

gencommP166Reg-106-107 OBJECT-TYPE
  SYNTAX  Unsigned32
  MAX-ACCESS  read-only
  STATUS  current
  DESCRIPTION "Gencomm Page 166 Register 106 to 107"
  ::= { gencommP166Entry 55 }

gencommP166Reg-108-109 OBJECT-TYPE
  SYNTAX  Unsigned32
  MAX-ACCESS  read-only
  STATUS  current
  DESCRIPTION "Gencomm Page 166 Register 108 to 109"
  ::= { gencommP166Entry 56 }

gencommP166Reg-110-111 OBJECT-TYPE
  SYNTAX  Unsigned32
  MAX-ACCESS  read-only
  STATUS  current
  DESCRIPTION "Gencomm Page 166 Register 110 to 111"
  ::= { gencommP166Entry 57 }

gencommP166Reg-112-113 OBJECT-TYPE
  SYNTAX  Unsigned32
  MAX-ACCESS  read-only
  STATUS  current
  DESCRIPTION "Gencomm Page 166 Register 112 to 113"
  ::= { gencommP166Entry 58 }

gencommP166Reg-114-115 OBJECT-TYPE
  SYNTAX  Unsigned32
  MAX-ACCESS  read-only
  STATUS  current
  DESCRIPTION "Gencomm Page 166 Register 114 to 115"
  ::= { gencommP166Entry 59 }

gencommP166Reg-116-117 OBJECT-TYPE
  SYNTAX  Unsigned32
  MAX-ACCESS  read-only
  STATUS  current
  DESCRIPTION "Gencomm Page 166 Register 116 to 117"
  ::= { gencommP166Entry 60 }

gencommP166Reg-118-119 OBJECT-TYPE
  SYNTAX  Unsigned32
  MAX-ACCESS  read-only
  STATUS  current
  DESCRIPTION "Gencomm Page 166 Register 118 to 119"
  ::= { gencommP166Entry 61 }

gencommP166Reg-120-121 OBJECT-TYPE
  SYNTAX  Unsigned32
  MAX-ACCESS  read-only
  STATUS  current
  DESCRIPTION "Gencomm Page 166 Register 120 to 121"
  ::= { gencommP166Entry 62 }

gencommP166Reg-122-123 OBJECT-TYPE
  SYNTAX  Unsigned32
  MAX-ACCESS  read-only
  STATUS  current
  DESCRIPTION "Gencomm Page 166 Register 122 to 123"
  ::= { gencommP166Entry 63 }

gencommP166Reg-124-125 OBJECT-TYPE
  SYNTAX  Unsigned32
  MAX-ACCESS  read-only
  STATUS  current
  DESCRIPTION "Gencomm Page 166 Register 124 to 125"
  ::= { gencommP166Entry 64 }

gencommP166Reg-126-127 OBJECT-TYPE
  SYNTAX  Unsigned32
  MAX-ACCESS  read-only
  STATUS  current
  DESCRIPTION "Gencomm Page 166 Register 126 to 127"
  ::= { gencommP166Entry 65 }

gencommP166Reg-128-129 OBJECT-TYPE
  SYNTAX  Unsigned32
  MAX-ACCESS  read-only
  STATUS  current
  DESCRIPTION "Gencomm Page 166 Register 128 to 129"
  ::= { gencommP166Entry 66 }

gencommP166Reg-130-131 OBJECT-TYPE
  SYNTAX  Unsigned32
  MAX-ACCESS  read-only
  STATUS  current
  DESCRIPTION "Gencomm Page 166 Register 130 to 131"
  ::= { gencommP166Entry 67 }

gencommP166Reg-132-133 OBJECT-TYPE
  SYNTAX  Unsigned32
  MAX-ACCESS  read-only
  STATUS  current
  DESCRIPTION "Gencomm Page 166 Register 132 to 133"
  ::= { gencommP166Entry 68 }

gencommP166Reg-134-135 OBJECT-TYPE
  SYNTAX  Unsigned32
  MAX-ACCESS  read-only
  STATUS  current
  DESCRIPTION "Gencomm Page 166 Register 134 to 135"
  ::= { gencommP166Entry 69 }

gencommP166Reg-136-137 OBJECT-TYPE
  SYNTAX  Unsigned32
  MAX-ACCESS  read-only
  STATUS  current
  DESCRIPTION "Gencomm Page 166 Register 136 to 137"
  ::= { gencommP166Entry 70 }

gencommP166Reg-138-139 OBJECT-TYPE
  SYNTAX  Unsigned32
  MAX-ACCESS  read-only
  STATUS  current
  DESCRIPTION "Gencomm Page 166 Register 138 to 139"
  ::= { gencommP166Entry 71 }

gencommP166Reg-140-141 OBJECT-TYPE
  SYNTAX  Unsigned32
  MAX-ACCESS  read-only
  STATUS  current
  DESCRIPTION "Gencomm Page 166 Register 140 to 141"
  ::= { gencommP166Entry 72 }

gencommP166Reg-142-143 OBJECT-TYPE
  SYNTAX  Unsigned32
  MAX-ACCESS  read-only
  STATUS  current
  DESCRIPTION "Gencomm Page 166 Register 142 to 143"
  ::= { gencommP166Entry 73 }

gencommP166Reg-144-145 OBJECT-TYPE
  SYNTAX  Unsigned32
  MAX-ACCESS  read-only
  STATUS  current
  DESCRIPTION "Gencomm Page 166 Register 144 to 145"
  ::= { gencommP166Entry 74 }

gencommP166Reg-146-147 OBJECT-TYPE
  SYNTAX  Unsigned32
  MAX-ACCESS  read-only
  STATUS  current
  DESCRIPTION "Gencomm Page 166 Register 146 to 147"
  ::= { gencommP166Entry 75 }

gencommP166Reg-148-149 OBJECT-TYPE
  SYNTAX  Unsigned32
  MAX-ACCESS  read-only
  STATUS  current
  DESCRIPTION "Gencomm Page 166 Register 148 to 149"
  ::= { gencommP166Entry 76 }

gencommP166Reg-150-151 OBJECT-TYPE
  SYNTAX  Unsigned32
  MAX-ACCESS  read-only
  STATUS  current
  DESCRIPTION "Gencomm Page 166 Register 150 to 151"
  ::= { gencommP166Entry 77 }

gencommP166Reg-152-153 OBJECT-TYPE
  SYNTAX  Unsigned32
  MAX-ACCESS  read-only
  STATUS  current
  DESCRIPTION "Gencomm Page 166 Register 152 to 153"
  ::= { gencommP166Entry 78 }

gencommP166Reg-154-155 OBJECT-TYPE
  SYNTAX  Unsigned32
  MAX-ACCESS  read-only
  STATUS  current
  DESCRIPTION "Gencomm Page 166 Register 154 to 155"
  ::= { gencommP166Entry 79 }

gencommP166Reg-156-157 OBJECT-TYPE
  SYNTAX  Unsigned32
  MAX-ACCESS  read-only
  STATUS  current
  DESCRIPTION "Gencomm Page 166 Register 156 to 157"
  ::= { gencommP166Entry 80 }

gencommP166Reg-158-159 OBJECT-TYPE
  SYNTAX  Unsigned32
  MAX-ACCESS  read-only
  STATUS  current
  DESCRIPTION "Gencomm Page 166 Register 158 to 159"
  ::= { gencommP166Entry 81 }

gencommP166Reg-160-161 OBJECT-TYPE
  SYNTAX  Unsigned32
  MAX-ACCESS  read-only
  STATUS  current
  DESCRIPTION "Gencomm Page 166 Register 160 to 161"
  ::= { gencommP166Entry 82 }

gencommP166Reg-162-163 OBJECT-TYPE
  SYNTAX  Unsigned32
  MAX-ACCESS  read-only
  STATUS  current
  DESCRIPTION "Gencomm Page 166 Register 162 to 163"
  ::= { gencommP166Entry 83 }

gencommP166Reg-164-165 OBJECT-TYPE
  SYNTAX  Unsigned32
  MAX-ACCESS  read-only
  STATUS  current
  DESCRIPTION "Gencomm Page 166 Register 164 to 165"
  ::= { gencommP166Entry 84 }

gencommP166Reg-166-167 OBJECT-TYPE
  SYNTAX  Unsigned32
  MAX-ACCESS  read-only
  STATUS  current
  DESCRIPTION "Gencomm Page 166 Register 166 to 167"
  ::= { gencommP166Entry 85 }

gencommP166Reg-168-169 OBJECT-TYPE
  SYNTAX  Unsigned32
  MAX-ACCESS  read-only
  STATUS  current
  DESCRIPTION "Gencomm Page 166 Register 168 to 169"
  ::= { gencommP166Entry 86 }

gencommP166Reg-170-171 OBJECT-TYPE
  SYNTAX  Unsigned32
  MAX-ACCESS  read-only
  STATUS  current
  DESCRIPTION "Gencomm Page 166 Register 170 to 171"
  ::= { gencommP166Entry 87 }

gencommP166Reg-172-173 OBJECT-TYPE
  SYNTAX  Unsigned32
  MAX-ACCESS  read-only
  STATUS  current
  DESCRIPTION "Gencomm Page 166 Register 172 to 173"
  ::= { gencommP166Entry 88 }

gencommP166Reg-174-175 OBJECT-TYPE
  SYNTAX  Unsigned32
  MAX-ACCESS  read-only
  STATUS  current
  DESCRIPTION "Gencomm Page 166 Register 174 to 175"
  ::= { gencommP166Entry 89 }

gencommP166Reg-176-177 OBJECT-TYPE
  SYNTAX  Unsigned32
  MAX-ACCESS  read-only
  STATUS  current
  DESCRIPTION "Gencomm Page 166 Register 176 to 177"
  ::= { gencommP166Entry 90 }

gencommP166Reg-178-179 OBJECT-TYPE
  SYNTAX  Unsigned32
  MAX-ACCESS  read-only
  STATUS  current
  DESCRIPTION "Gencomm Page 166 Register 178 to 179"
  ::= { gencommP166Entry 91 }

gencommP166Reg-180-181 OBJECT-TYPE
  SYNTAX  Unsigned32
  MAX-ACCESS  read-only
  STATUS  current
  DESCRIPTION "Gencomm Page 166 Register 180 to 181"
  ::= { gencommP166Entry 92 }

gencommP166Reg-182-183 OBJECT-TYPE
  SYNTAX  Unsigned32
  MAX-ACCESS  read-only
  STATUS  current
  DESCRIPTION "Gencomm Page 166 Register 182 to 183"
  ::= { gencommP166Entry 93 }

gencommP166Reg-184-185 OBJECT-TYPE
  SYNTAX  Unsigned32
  MAX-ACCESS  read-only
  STATUS  current
  DESCRIPTION "Gencomm Page 166 Register 184 to 185"
  ::= { gencommP166Entry 94 }

gencommP166Reg-186-187 OBJECT-TYPE
  SYNTAX  Unsigned32
  MAX-ACCESS  read-only
  STATUS  current
  DESCRIPTION "Gencomm Page 166 Register 186 to 187"
  ::= { gencommP166Entry 95 }

gencommP166Reg-188-189 OBJECT-TYPE
  SYNTAX  Unsigned32
  MAX-ACCESS  read-only
  STATUS  current
  DESCRIPTION "Gencomm Page 166 Register 188 to 189"
  ::= { gencommP166Entry 96 }

gencommP166Reg-190-191 OBJECT-TYPE
  SYNTAX  Unsigned32
  MAX-ACCESS  read-only
  STATUS  current
  DESCRIPTION "Gencomm Page 166 Register 190 to 191"
  ::= { gencommP166Entry 97 }

gencommP166Reg-192-193 OBJECT-TYPE
  SYNTAX  Unsigned32
  MAX-ACCESS  read-only
  STATUS  current
  DESCRIPTION "Gencomm Page 166 Register 192 to 193"
  ::= { gencommP166Entry 98 }

gencommP166Reg-194-195 OBJECT-TYPE
  SYNTAX  Unsigned32
  MAX-ACCESS  read-only
  STATUS  current
  DESCRIPTION "Gencomm Page 166 Register 184 to 195"
  ::= { gencommP166Entry 99 }

gencommP166Reg-196-197 OBJECT-TYPE
  SYNTAX  Unsigned32
  MAX-ACCESS  read-only
  STATUS  current
  DESCRIPTION "Gencomm Page 166 Register 196 to 197"
  ::= { gencommP166Entry 100 }

gencommP166Reg-198-199 OBJECT-TYPE
  SYNTAX  Unsigned32
  MAX-ACCESS  read-only
  STATUS  current
  DESCRIPTION "Gencomm Page 166 Register 198 to 199"
  ::= { gencommP166Entry 101 }

gencommP166Reg-200-201 OBJECT-TYPE
  SYNTAX  Unsigned32
  MAX-ACCESS  read-only
  STATUS  current
  DESCRIPTION "Gencomm Page 166 Register 200 to 201"
  ::= { gencommP166Entry 102 }

gencommP166Reg-202-203 OBJECT-TYPE
  SYNTAX  Unsigned32
  MAX-ACCESS  read-only
  STATUS  current
  DESCRIPTION "Gencomm Page 166 Register 202 to 203"
  ::= { gencommP166Entry 103 }

gencommP166Reg-204-205 OBJECT-TYPE
  SYNTAX  Unsigned32
  MAX-ACCESS  read-only
  STATUS  current
  DESCRIPTION "Gencomm Page 166 Register 204 to 205"
  ::= { gencommP166Entry 104 }

gencommP166Reg-206-207 OBJECT-TYPE
  SYNTAX  Unsigned32
  MAX-ACCESS  read-only
  STATUS  current
  DESCRIPTION "Gencomm Page 166 Register 206 to 207"
  ::= { gencommP166Entry 105 }

gencommP166Reg-208-209 OBJECT-TYPE
  SYNTAX  Unsigned32
  MAX-ACCESS  read-only
  STATUS  current
  DESCRIPTION "Gencomm Page 166 Register 208 to 209"
  ::= { gencommP166Entry 106 }

gencommP166Reg-210-211 OBJECT-TYPE
  SYNTAX  Unsigned32
  MAX-ACCESS  read-only
  STATUS  current
  DESCRIPTION "Gencomm Page 166 Register 210 to 211"
  ::= { gencommP166Entry 107 }

gencommP166Reg-212-213 OBJECT-TYPE
  SYNTAX  Unsigned32
  MAX-ACCESS  read-only
  STATUS  current
  DESCRIPTION "Gencomm Page 166 Register 212 to 213"
  ::= { gencommP166Entry 108 }

gencommP166Reg-214-215 OBJECT-TYPE
  SYNTAX  Unsigned32
  MAX-ACCESS  read-only
  STATUS  current
  DESCRIPTION "Gencomm Page 166 Register 214 to 215"
  ::= { gencommP166Entry 109 }

gencommP166Reg-216-217 OBJECT-TYPE
  SYNTAX  Unsigned32
  MAX-ACCESS  read-only
  STATUS  current
  DESCRIPTION "Gencomm Page 166 Register 216 to 217"
  ::= { gencommP166Entry 110 }

gencommP166Reg-218-219 OBJECT-TYPE
  SYNTAX  Unsigned32
  MAX-ACCESS  read-only
  STATUS  current
  DESCRIPTION "Gencomm Page 166 Register 218 to 219"
  ::= { gencommP166Entry 111 }

gencommP166Reg-220-221 OBJECT-TYPE
  SYNTAX  Unsigned32
  MAX-ACCESS  read-only
  STATUS  current
  DESCRIPTION "Gencomm Page 166 Register 220 to 221"
  ::= { gencommP166Entry 112 }

gencommP166Reg-222-223 OBJECT-TYPE
  SYNTAX  Unsigned32
  MAX-ACCESS  read-only
  STATUS  current
  DESCRIPTION "Gencomm Page 166 Register 222 to 223"
  ::= { gencommP166Entry 113 }

gencommP166Reg-224-225 OBJECT-TYPE
  SYNTAX  Unsigned32
  MAX-ACCESS  read-only
  STATUS  current
  DESCRIPTION "Gencomm Page 166 Register 224 to 225"
  ::= { gencommP166Entry 114 }

gencommP166Reg-226-227 OBJECT-TYPE
  SYNTAX  Unsigned32
  MAX-ACCESS  read-only
  STATUS  current
  DESCRIPTION "Gencomm Page 166 Register 226 to 227"
  ::= { gencommP166Entry 115 }

gencommP166Reg-228-229 OBJECT-TYPE
  SYNTAX  Unsigned32
  MAX-ACCESS  read-only
  STATUS  current
  DESCRIPTION "Gencomm Page 166 Register 228 to 229"
  ::= { gencommP166Entry 116 }

gencommP166Reg-230-231 OBJECT-TYPE
  SYNTAX  Unsigned32
  MAX-ACCESS  read-only
  STATUS  current
  DESCRIPTION "Gencomm Page 166 Register 230 to 231"
  ::= { gencommP166Entry 117 }

gencommP166Reg-232-233 OBJECT-TYPE
  SYNTAX  Unsigned32
  MAX-ACCESS  read-only
  STATUS  current
  DESCRIPTION "Gencomm Page 166 Register 232 to 233"
  ::= { gencommP166Entry 118 }

gencommP166Reg-234-235 OBJECT-TYPE
  SYNTAX  Unsigned32
  MAX-ACCESS  read-only
  STATUS  current
  DESCRIPTION "Gencomm Page 166 Register 234 to 235"
  ::= { gencommP166Entry 119 }

gencommP166Reg-236-237 OBJECT-TYPE
  SYNTAX  Unsigned32
  MAX-ACCESS  read-only
  STATUS  current
  DESCRIPTION "Gencomm Page 166 Register 236 to 237"
  ::= { gencommP166Entry 120 }

gencommP166Reg-238-239 OBJECT-TYPE
  SYNTAX  Unsigned32
  MAX-ACCESS  read-only
  STATUS  current
  DESCRIPTION "Gencomm Page 166 Register 238 to 239"
  ::= { gencommP166Entry 121 }

gencommP166Reg-240-241 OBJECT-TYPE
  SYNTAX  Unsigned32
  MAX-ACCESS  read-only
  STATUS  current
  DESCRIPTION "Gencomm Page 166 Register 240 to 241"
  ::= { gencommP166Entry 122 }

gencommP166Reg-242-243 OBJECT-TYPE
  SYNTAX  Unsigned32
  MAX-ACCESS  read-only
  STATUS  current
  DESCRIPTION "Gencomm Page 166 Register 242 to 243"
  ::= { gencommP166Entry 123 }

gencommP166Reg-244-245 OBJECT-TYPE
  SYNTAX  Unsigned32
  MAX-ACCESS  read-only
  STATUS  current
  DESCRIPTION "Gencomm Page 166 Register 244 to 245"
  ::= { gencommP166Entry 124 }

gencommP166Reg-246-247 OBJECT-TYPE
  SYNTAX  Unsigned32
  MAX-ACCESS  read-only
  STATUS  current
  DESCRIPTION "Gencomm Page 166 Register 246 to 247"
  ::= { gencommP166Entry 125 }

gencommP166Reg-248-249 OBJECT-TYPE
  SYNTAX  Unsigned32
  MAX-ACCESS  read-only
  STATUS  current
  DESCRIPTION "Gencomm Page 166 Register 248 to 249"
  ::= { gencommP166Entry 126 }

gencommP166Reg-250-251 OBJECT-TYPE
  SYNTAX  Unsigned32
  MAX-ACCESS  read-only
  STATUS  current
  DESCRIPTION "Gencomm Page 166 Register 250 to 251"
  ::= { gencommP166Entry 127 }

gencommP166Reg-252-253 OBJECT-TYPE
  SYNTAX  Unsigned32
  MAX-ACCESS  read-only
  STATUS  current
  DESCRIPTION "Gencomm Page 166 Register 252 to 253"
  ::= { gencommP166Entry 128 }

gencommP166Reg-254-255 OBJECT-TYPE
  SYNTAX  Unsigned32
  MAX-ACCESS  read-only
  STATUS  current
  DESCRIPTION "Gencomm Page 166 Register 254 to 255"
  ::= { gencommP166Entry 129 }

gencommP167Reg-0-1 OBJECT-TYPE
  SYNTAX  Unsigned32
  MAX-ACCESS  read-only
  STATUS  current
  DESCRIPTION "Gencomm Page 167 Register 0 to 1"
  ::= { gencommP167Entry 2 }

gencommP167Reg-2-3 OBJECT-TYPE
  SYNTAX  Unsigned32
  MAX-ACCESS  read-only
  STATUS  current
  DESCRIPTION "Gencomm Page 167 Register 2 to 3"
  ::= { gencommP167Entry 3 }

gencommP167Reg-4-5 OBJECT-TYPE
  SYNTAX  Unsigned32
  MAX-ACCESS  read-only
  STATUS  current
  DESCRIPTION "Gencomm Page 167 Register 4 to 5"
  ::= { gencommP167Entry 4 }

gencommP167Reg-6-7 OBJECT-TYPE
  SYNTAX  Unsigned32
  MAX-ACCESS  read-only
  STATUS  current
  DESCRIPTION "Gencomm Page 167 Register 6 to 7"
  ::= { gencommP167Entry 5 }

gencommP167Reg-8-9 OBJECT-TYPE
  SYNTAX  Unsigned32
  MAX-ACCESS  read-only
  STATUS  current
  DESCRIPTION "Gencomm Page 167 Register 8 to 9"
  ::= { gencommP167Entry 6 }

gencommP167Reg-10-11 OBJECT-TYPE
  SYNTAX  Unsigned32
  MAX-ACCESS  read-only
  STATUS  current
  DESCRIPTION "Gencomm Page 167 Register 10 to 11"
  ::= { gencommP167Entry 7 }

gencommP167Reg-12-13 OBJECT-TYPE
  SYNTAX  Unsigned32
  MAX-ACCESS  read-only
  STATUS  current
  DESCRIPTION "Gencomm Page 167 Register 12 to 13"
  ::= { gencommP167Entry 8 }

gencommP167Reg-14-15 OBJECT-TYPE
  SYNTAX  Unsigned32
  MAX-ACCESS  read-only
  STATUS  current
  DESCRIPTION "Gencomm Page 167 Register 14 to 15"
  ::= { gencommP167Entry 9 }

gencommP167Reg-16-17 OBJECT-TYPE
  SYNTAX  Unsigned32
  MAX-ACCESS  read-only
  STATUS  current
  DESCRIPTION "Gencomm Page 167 Register 16 to 17"
  ::= { gencommP167Entry 10 }

gencommP167Reg-18-19 OBJECT-TYPE
  SYNTAX  Unsigned32
  MAX-ACCESS  read-only
  STATUS  current
  DESCRIPTION "Gencomm Page 167 Register 18 to 19"
  ::= { gencommP167Entry 11 }

gencommP167Reg-20-21 OBJECT-TYPE
  SYNTAX  Unsigned32
  MAX-ACCESS  read-only
  STATUS  current
  DESCRIPTION "Gencomm Page 167 Register 20 to 21"
  ::= { gencommP167Entry 12 }

gencommP167Reg-22-23 OBJECT-TYPE
  SYNTAX  Unsigned32
  MAX-ACCESS  read-only
  STATUS  current
  DESCRIPTION "Gencomm Page 167 Register 22 to 23"
  ::= { gencommP167Entry 13 }

gencommP167Reg-24-25 OBJECT-TYPE
  SYNTAX  Unsigned32
  MAX-ACCESS  read-only
  STATUS  current
  DESCRIPTION "Gencomm Page 167 Register 24 to 25"
  ::= { gencommP167Entry 14 }

gencommP167Reg-26-27 OBJECT-TYPE
  SYNTAX  Unsigned32
  MAX-ACCESS  read-only
  STATUS  current
  DESCRIPTION "Gencomm Page 167 Register 26 to 27"
  ::= { gencommP167Entry 15 }

gencommP167Reg-28-29 OBJECT-TYPE
  SYNTAX  Unsigned32
  MAX-ACCESS  read-only
  STATUS  current
  DESCRIPTION "Gencomm Page 167 Register 28 to 29"
  ::= { gencommP167Entry 16 }

gencommP167Reg-30-31 OBJECT-TYPE
  SYNTAX  Unsigned32
  MAX-ACCESS  read-only
  STATUS  current
  DESCRIPTION "Gencomm Page 167 Register 30 to 31"
  ::= { gencommP167Entry 17 }

gencommP167Reg-32-33 OBJECT-TYPE
  SYNTAX  Unsigned32
  MAX-ACCESS  read-only
  STATUS  current
  DESCRIPTION "Gencomm Page 167 Register 32 to 33"
  ::= { gencommP167Entry 18 }

gencommP167Reg-34-35 OBJECT-TYPE
  SYNTAX  Unsigned32
  MAX-ACCESS  read-only
  STATUS  current
  DESCRIPTION "Gencomm Page 167 Register 34 to 35"
  ::= { gencommP167Entry 19 }

gencommP167Reg-36-37 OBJECT-TYPE
  SYNTAX  Unsigned32
  MAX-ACCESS  read-only
  STATUS  current
  DESCRIPTION "Gencomm Page 167 Register 36 to 37"
  ::= { gencommP167Entry 20 }

gencommP167Reg-38-39 OBJECT-TYPE
  SYNTAX  Unsigned32
  MAX-ACCESS  read-only
  STATUS  current
  DESCRIPTION "Gencomm Page 167 Register 38 to 39"
  ::= { gencommP167Entry 21 }

gencommP167Reg-40-41 OBJECT-TYPE
  SYNTAX  Unsigned32
  MAX-ACCESS  read-only
  STATUS  current
  DESCRIPTION "Gencomm Page 167 Register 40 to 41"
  ::= { gencommP167Entry 22 }

gencommP167Reg-42-43 OBJECT-TYPE
  SYNTAX  Unsigned32
  MAX-ACCESS  read-only
  STATUS  current
  DESCRIPTION "Gencomm Page 167 Register 42 to 43"
  ::= { gencommP167Entry 23 }

gencommP167Reg-44-45 OBJECT-TYPE
  SYNTAX  Unsigned32
  MAX-ACCESS  read-only
  STATUS  current
  DESCRIPTION "Gencomm Page 167 Register 44 to 45"
  ::= { gencommP167Entry 24 }

gencommP167Reg-46-47 OBJECT-TYPE
  SYNTAX  Unsigned32
  MAX-ACCESS  read-only
  STATUS  current
  DESCRIPTION "Gencomm Page 167 Register 46 to 47"
  ::= { gencommP167Entry 25 }

gencommP167Reg-48-49 OBJECT-TYPE
  SYNTAX  Unsigned32
  MAX-ACCESS  read-only
  STATUS  current
  DESCRIPTION "Gencomm Page 167 Register 48 to 49"
  ::= { gencommP167Entry 26 }

gencommP167Reg-50-51 OBJECT-TYPE
  SYNTAX  Unsigned32
  MAX-ACCESS  read-only
  STATUS  current
  DESCRIPTION "Gencomm Page 167 Register 50 to 51"
  ::= { gencommP167Entry 27 }

gencommP167Reg-52-53 OBJECT-TYPE
  SYNTAX  Unsigned32
  MAX-ACCESS  read-only
  STATUS  current
  DESCRIPTION "Gencomm Page 167 Register 52 to 53"
  ::= { gencommP167Entry 28 }

gencommP167Reg-54-55 OBJECT-TYPE
  SYNTAX  Unsigned32
  MAX-ACCESS  read-only
  STATUS  current
  DESCRIPTION "Gencomm Page 167 Register 54 to 55"
  ::= { gencommP167Entry 29 }

gencommP167Reg-56-57 OBJECT-TYPE
  SYNTAX  Unsigned32
  MAX-ACCESS  read-only
  STATUS  current
  DESCRIPTION "Gencomm Page 167 Register 56 to 57"
  ::= { gencommP167Entry 30 }

gencommP167Reg-58-59 OBJECT-TYPE
  SYNTAX  Unsigned32
  MAX-ACCESS  read-only
  STATUS  current
  DESCRIPTION "Gencomm Page 167 Register 58 to 59"
  ::= { gencommP167Entry 31 }

gencommP167Reg-60-61 OBJECT-TYPE
  SYNTAX  Unsigned32
  MAX-ACCESS  read-only
  STATUS  current
  DESCRIPTION "Gencomm Page 167 Register 60 to 61"
  ::= { gencommP167Entry 32 }

gencommP167Reg-62-63 OBJECT-TYPE
  SYNTAX  Unsigned32
  MAX-ACCESS  read-only
  STATUS  current
  DESCRIPTION "Gencomm Page 167 Register 62 to 63"
  ::= { gencommP167Entry 33 }

gencommP167Reg-64-65 OBJECT-TYPE
  SYNTAX  Unsigned32
  MAX-ACCESS  read-only
  STATUS  current
  DESCRIPTION "Gencomm Page 167 Register 64 to 65"
  ::= { gencommP167Entry 34 }

gencommP167Reg-66-67 OBJECT-TYPE
  SYNTAX  Unsigned32
  MAX-ACCESS  read-only
  STATUS  current
  DESCRIPTION "Gencomm Page 167 Register 66 to 67"
  ::= { gencommP167Entry 35 }

gencommP167Reg-68-69 OBJECT-TYPE
  SYNTAX  Unsigned32
  MAX-ACCESS  read-only
  STATUS  current
  DESCRIPTION "Gencomm Page 167 Register 68 to 69"
  ::= { gencommP167Entry 36 }

gencommP167Reg-70-71 OBJECT-TYPE
  SYNTAX  Unsigned32
  MAX-ACCESS  read-only
  STATUS  current
  DESCRIPTION "Gencomm Page 167 Register 70 to 71"
  ::= { gencommP167Entry 37 }

gencommP167Reg-72-73 OBJECT-TYPE
  SYNTAX  Unsigned32
  MAX-ACCESS  read-only
  STATUS  current
  DESCRIPTION "Gencomm Page 167 Register 72 to 73"
  ::= { gencommP167Entry 38 }

gencommP167Reg-74-75 OBJECT-TYPE
  SYNTAX  Unsigned32
  MAX-ACCESS  read-only
  STATUS  current
  DESCRIPTION "Gencomm Page 167 Register 74 to 75"
  ::= { gencommP167Entry 39 }

gencommP167Reg-76-77 OBJECT-TYPE
  SYNTAX  Unsigned32
  MAX-ACCESS  read-only
  STATUS  current
  DESCRIPTION "Gencomm Page 167 Register 76 to 77"
  ::= { gencommP167Entry 40 }

gencommP167Reg-78-79 OBJECT-TYPE
  SYNTAX  Unsigned32
  MAX-ACCESS  read-only
  STATUS  current
  DESCRIPTION "Gencomm Page 167 Register 78 to 79"
  ::= { gencommP167Entry 41 }

gencommP167Reg-80-81 OBJECT-TYPE
  SYNTAX  Unsigned32
  MAX-ACCESS  read-only
  STATUS  current
  DESCRIPTION "Gencomm Page 167 Register 80 to 81"
  ::= { gencommP167Entry 42 }

gencommP167Reg-82-83 OBJECT-TYPE
  SYNTAX  Unsigned32
  MAX-ACCESS  read-only
  STATUS  current
  DESCRIPTION "Gencomm Page 167 Register 82 to 83"
  ::= { gencommP167Entry 43 }

gencommP167Reg-84-85 OBJECT-TYPE
  SYNTAX  Unsigned32
  MAX-ACCESS  read-only
  STATUS  current
  DESCRIPTION "Gencomm Page 167 Register 84 to 85"
  ::= { gencommP167Entry 44 }

gencommP167Reg-86-87 OBJECT-TYPE
  SYNTAX  Unsigned32
  MAX-ACCESS  read-only
  STATUS  current
  DESCRIPTION "Gencomm Page 167 Register 86 to 87"
  ::= { gencommP167Entry 45 }

gencommP167Reg-88-89 OBJECT-TYPE
  SYNTAX  Unsigned32
  MAX-ACCESS  read-only
  STATUS  current
  DESCRIPTION "Gencomm Page 167 Register 88 to 89"
  ::= { gencommP167Entry 46 }

gencommP167Reg-90-91 OBJECT-TYPE
  SYNTAX  Unsigned32
  MAX-ACCESS  read-only
  STATUS  current
  DESCRIPTION "Gencomm Page 167 Register 90 to 91"
  ::= { gencommP167Entry 47 }

gencommP167Reg-92-93 OBJECT-TYPE
  SYNTAX  Unsigned32
  MAX-ACCESS  read-only
  STATUS  current
  DESCRIPTION "Gencomm Page 167 Register 92 to 93"
  ::= { gencommP167Entry 48 }

gencommP167Reg-94-95 OBJECT-TYPE
  SYNTAX  Unsigned32
  MAX-ACCESS  read-only
  STATUS  current
  DESCRIPTION "Gencomm Page 167 Register 94 to 95"
  ::= { gencommP167Entry 49 }

gencommP167Reg-96-97 OBJECT-TYPE
  SYNTAX  Unsigned32
  MAX-ACCESS  read-only
  STATUS  current
  DESCRIPTION "Gencomm Page 167 Register 96 to 97"
  ::= { gencommP167Entry 50 }

gencommP167Reg-98-99 OBJECT-TYPE
  SYNTAX  Unsigned32
  MAX-ACCESS  read-only
  STATUS  current
  DESCRIPTION "Gencomm Page 167 Register 98 to 99"
  ::= { gencommP167Entry 51 }

gencommP167Reg-100-101 OBJECT-TYPE
  SYNTAX  Unsigned32
  MAX-ACCESS  read-only
  STATUS  current
  DESCRIPTION "Gencomm Page 167 Register 100 to 101"
  ::= { gencommP167Entry 52 }

gencommP167Reg-102-103 OBJECT-TYPE
  SYNTAX  Unsigned32
  MAX-ACCESS  read-only
  STATUS  current
  DESCRIPTION "Gencomm Page 167 Register 102 to 103"
  ::= { gencommP167Entry 53 }

gencommP167Reg-104-105 OBJECT-TYPE
  SYNTAX  Unsigned32
  MAX-ACCESS  read-only
  STATUS  current
  DESCRIPTION "Gencomm Page 167 Register 104 to 105"
  ::= { gencommP167Entry 54 }

gencommP167Reg-106-107 OBJECT-TYPE
  SYNTAX  Unsigned32
  MAX-ACCESS  read-only
  STATUS  current
  DESCRIPTION "Gencomm Page 167 Register 106 to 107"
  ::= { gencommP167Entry 55 }

gencommP167Reg-108-109 OBJECT-TYPE
  SYNTAX  Unsigned32
  MAX-ACCESS  read-only
  STATUS  current
  DESCRIPTION "Gencomm Page 167 Register 108 to 109"
  ::= { gencommP167Entry 56 }

gencommP167Reg-110-111 OBJECT-TYPE
  SYNTAX  Unsigned32
  MAX-ACCESS  read-only
  STATUS  current
  DESCRIPTION "Gencomm Page 167 Register 110 to 111"
  ::= { gencommP167Entry 57 }

gencommP167Reg-112-113 OBJECT-TYPE
  SYNTAX  Unsigned32
  MAX-ACCESS  read-only
  STATUS  current
  DESCRIPTION "Gencomm Page 167 Register 112 to 113"
  ::= { gencommP167Entry 58 }

gencommP167Reg-114-115 OBJECT-TYPE
  SYNTAX  Unsigned32
  MAX-ACCESS  read-only
  STATUS  current
  DESCRIPTION "Gencomm Page 167 Register 114 to 115"
  ::= { gencommP167Entry 59 }

gencommP167Reg-116-117 OBJECT-TYPE
  SYNTAX  Unsigned32
  MAX-ACCESS  read-only
  STATUS  current
  DESCRIPTION "Gencomm Page 167 Register 116 to 117"
  ::= { gencommP167Entry 60 }

gencommP167Reg-118-119 OBJECT-TYPE
  SYNTAX  Unsigned32
  MAX-ACCESS  read-only
  STATUS  current
  DESCRIPTION "Gencomm Page 167 Register 118 to 119"
  ::= { gencommP167Entry 61 }

gencommP167Reg-120-121 OBJECT-TYPE
  SYNTAX  Unsigned32
  MAX-ACCESS  read-only
  STATUS  current
  DESCRIPTION "Gencomm Page 167 Register 120 to 121"
  ::= { gencommP167Entry 62 }

gencommP167Reg-122-123 OBJECT-TYPE
  SYNTAX  Unsigned32
  MAX-ACCESS  read-only
  STATUS  current
  DESCRIPTION "Gencomm Page 167 Register 122 to 123"
  ::= { gencommP167Entry 63 }

gencommP167Reg-124-125 OBJECT-TYPE
  SYNTAX  Unsigned32
  MAX-ACCESS  read-only
  STATUS  current
  DESCRIPTION "Gencomm Page 167 Register 124 to 125"
  ::= { gencommP167Entry 64 }

gencommP167Reg-126-127 OBJECT-TYPE
  SYNTAX  Unsigned32
  MAX-ACCESS  read-only
  STATUS  current
  DESCRIPTION "Gencomm Page 167 Register 126 to 127"
  ::= { gencommP167Entry 65 }

gencommP167Reg-128-129 OBJECT-TYPE
  SYNTAX  Unsigned32
  MAX-ACCESS  read-only
  STATUS  current
  DESCRIPTION "Gencomm Page 167 Register 128 to 129"
  ::= { gencommP167Entry 66 }

gencommP167Reg-130-131 OBJECT-TYPE
  SYNTAX  Unsigned32
  MAX-ACCESS  read-only
  STATUS  current
  DESCRIPTION "Gencomm Page 167 Register 130 to 131"
  ::= { gencommP167Entry 67 }

gencommP167Reg-132-133 OBJECT-TYPE
  SYNTAX  Unsigned32
  MAX-ACCESS  read-only
  STATUS  current
  DESCRIPTION "Gencomm Page 167 Register 132 to 133"
  ::= { gencommP167Entry 68 }

gencommP167Reg-134-135 OBJECT-TYPE
  SYNTAX  Unsigned32
  MAX-ACCESS  read-only
  STATUS  current
  DESCRIPTION "Gencomm Page 167 Register 134 to 135"
  ::= { gencommP167Entry 69 }

gencommP167Reg-136-137 OBJECT-TYPE
  SYNTAX  Unsigned32
  MAX-ACCESS  read-only
  STATUS  current
  DESCRIPTION "Gencomm Page 167 Register 136 to 137"
  ::= { gencommP167Entry 70 }

gencommP167Reg-138-139 OBJECT-TYPE
  SYNTAX  Unsigned32
  MAX-ACCESS  read-only
  STATUS  current
  DESCRIPTION "Gencomm Page 167 Register 138 to 139"
  ::= { gencommP167Entry 71 }

gencommP167Reg-140-141 OBJECT-TYPE
  SYNTAX  Unsigned32
  MAX-ACCESS  read-only
  STATUS  current
  DESCRIPTION "Gencomm Page 167 Register 140 to 141"
  ::= { gencommP167Entry 72 }

gencommP167Reg-142-143 OBJECT-TYPE
  SYNTAX  Unsigned32
  MAX-ACCESS  read-only
  STATUS  current
  DESCRIPTION "Gencomm Page 167 Register 142 to 143"
  ::= { gencommP167Entry 73 }

gencommP167Reg-144-145 OBJECT-TYPE
  SYNTAX  Unsigned32
  MAX-ACCESS  read-only
  STATUS  current
  DESCRIPTION "Gencomm Page 167 Register 144 to 145"
  ::= { gencommP167Entry 74 }

gencommP167Reg-146-147 OBJECT-TYPE
  SYNTAX  Unsigned32
  MAX-ACCESS  read-only
  STATUS  current
  DESCRIPTION "Gencomm Page 167 Register 146 to 147"
  ::= { gencommP167Entry 75 }

gencommP167Reg-148-149 OBJECT-TYPE
  SYNTAX  Unsigned32
  MAX-ACCESS  read-only
  STATUS  current
  DESCRIPTION "Gencomm Page 167 Register 148 to 149"
  ::= { gencommP167Entry 76 }

gencommP167Reg-150-151 OBJECT-TYPE
  SYNTAX  Unsigned32
  MAX-ACCESS  read-only
  STATUS  current
  DESCRIPTION "Gencomm Page 167 Register 150 to 151"
  ::= { gencommP167Entry 77 }

gencommP167Reg-152-153 OBJECT-TYPE
  SYNTAX  Unsigned32
  MAX-ACCESS  read-only
  STATUS  current
  DESCRIPTION "Gencomm Page 167 Register 152 to 153"
  ::= { gencommP167Entry 78 }

gencommP167Reg-154-155 OBJECT-TYPE
  SYNTAX  Unsigned32
  MAX-ACCESS  read-only
  STATUS  current
  DESCRIPTION "Gencomm Page 167 Register 154 to 155"
  ::= { gencommP167Entry 79 }

gencommP167Reg-156-157 OBJECT-TYPE
  SYNTAX  Unsigned32
  MAX-ACCESS  read-only
  STATUS  current
  DESCRIPTION "Gencomm Page 167 Register 156 to 157"
  ::= { gencommP167Entry 80 }

gencommP167Reg-158-159 OBJECT-TYPE
  SYNTAX  Unsigned32
  MAX-ACCESS  read-only
  STATUS  current
  DESCRIPTION "Gencomm Page 167 Register 158 to 159"
  ::= { gencommP167Entry 81 }

gencommP167Reg-160-161 OBJECT-TYPE
  SYNTAX  Unsigned32
  MAX-ACCESS  read-only
  STATUS  current
  DESCRIPTION "Gencomm Page 167 Register 160 to 161"
  ::= { gencommP167Entry 82 }

gencommP167Reg-162-163 OBJECT-TYPE
  SYNTAX  Unsigned32
  MAX-ACCESS  read-only
  STATUS  current
  DESCRIPTION "Gencomm Page 167 Register 162 to 163"
  ::= { gencommP167Entry 83 }

gencommP167Reg-164-165 OBJECT-TYPE
  SYNTAX  Unsigned32
  MAX-ACCESS  read-only
  STATUS  current
  DESCRIPTION "Gencomm Page 167 Register 164 to 165"
  ::= { gencommP167Entry 84 }

gencommP167Reg-166-167 OBJECT-TYPE
  SYNTAX  Unsigned32
  MAX-ACCESS  read-only
  STATUS  current
  DESCRIPTION "Gencomm Page 167 Register 166 to 167"
  ::= { gencommP167Entry 85 }

gencommP167Reg-168-169 OBJECT-TYPE
  SYNTAX  Unsigned32
  MAX-ACCESS  read-only
  STATUS  current
  DESCRIPTION "Gencomm Page 167 Register 168 to 169"
  ::= { gencommP167Entry 86 }

gencommP167Reg-170-171 OBJECT-TYPE
  SYNTAX  Unsigned32
  MAX-ACCESS  read-only
  STATUS  current
  DESCRIPTION "Gencomm Page 167 Register 170 to 171"
  ::= { gencommP167Entry 87 }

gencommP167Reg-172-173 OBJECT-TYPE
  SYNTAX  Unsigned32
  MAX-ACCESS  read-only
  STATUS  current
  DESCRIPTION "Gencomm Page 167 Register 172 to 173"
  ::= { gencommP167Entry 88 }

gencommP167Reg-174-175 OBJECT-TYPE
  SYNTAX  Unsigned32
  MAX-ACCESS  read-only
  STATUS  current
  DESCRIPTION "Gencomm Page 167 Register 174 to 175"
  ::= { gencommP167Entry 89 }

gencommP167Reg-176-177 OBJECT-TYPE
  SYNTAX  Unsigned32
  MAX-ACCESS  read-only
  STATUS  current
  DESCRIPTION "Gencomm Page 167 Register 176 to 177"
  ::= { gencommP167Entry 90 }

gencommP167Reg-178-179 OBJECT-TYPE
  SYNTAX  Unsigned32
  MAX-ACCESS  read-only
  STATUS  current
  DESCRIPTION "Gencomm Page 167 Register 178 to 179"
  ::= { gencommP167Entry 91 }

gencommP167Reg-180-181 OBJECT-TYPE
  SYNTAX  Unsigned32
  MAX-ACCESS  read-only
  STATUS  current
  DESCRIPTION "Gencomm Page 167 Register 180 to 181"
  ::= { gencommP167Entry 92 }

gencommP167Reg-182-183 OBJECT-TYPE
  SYNTAX  Unsigned32
  MAX-ACCESS  read-only
  STATUS  current
  DESCRIPTION "Gencomm Page 167 Register 182 to 183"
  ::= { gencommP167Entry 93 }

gencommP167Reg-184-185 OBJECT-TYPE
  SYNTAX  Unsigned32
  MAX-ACCESS  read-only
  STATUS  current
  DESCRIPTION "Gencomm Page 167 Register 184 to 185"
  ::= { gencommP167Entry 94 }

gencommP167Reg-186-187 OBJECT-TYPE
  SYNTAX  Unsigned32
  MAX-ACCESS  read-only
  STATUS  current
  DESCRIPTION "Gencomm Page 167 Register 186 to 187"
  ::= { gencommP167Entry 95 }

gencommP167Reg-188-189 OBJECT-TYPE
  SYNTAX  Unsigned32
  MAX-ACCESS  read-only
  STATUS  current
  DESCRIPTION "Gencomm Page 167 Register 188 to 189"
  ::= { gencommP167Entry 96 }

gencommP167Reg-190-191 OBJECT-TYPE
  SYNTAX  Unsigned32
  MAX-ACCESS  read-only
  STATUS  current
  DESCRIPTION "Gencomm Page 167 Register 190 to 191"
  ::= { gencommP167Entry 97 }

gencommP167Reg-192-193 OBJECT-TYPE
  SYNTAX  Unsigned32
  MAX-ACCESS  read-only
  STATUS  current
  DESCRIPTION "Gencomm Page 167 Register 192 to 193"
  ::= { gencommP167Entry 98 }

gencommP167Reg-194-195 OBJECT-TYPE
  SYNTAX  Unsigned32
  MAX-ACCESS  read-only
  STATUS  current
  DESCRIPTION "Gencomm Page 167 Register 194 to 195"
  ::= { gencommP167Entry 99 }

gencommP167Reg-196-197 OBJECT-TYPE
  SYNTAX  Unsigned32
  MAX-ACCESS  read-only
  STATUS  current
  DESCRIPTION "Gencomm Page 167 Register 196 to 197"
  ::= { gencommP167Entry 100 }

gencommP167Reg-198-199 OBJECT-TYPE
  SYNTAX  Unsigned32
  MAX-ACCESS  read-only
  STATUS  current
  DESCRIPTION "Gencomm Page 167 Register 198 to 199"
  ::= { gencommP167Entry 101 }

gencommP167Reg-200-201 OBJECT-TYPE
  SYNTAX  Unsigned32
  MAX-ACCESS  read-only
  STATUS  current
  DESCRIPTION "Gencomm Page 167 Register 200 to 201"
  ::= { gencommP167Entry 102 }

gencommP167Reg-202-203 OBJECT-TYPE
  SYNTAX  Unsigned32
  MAX-ACCESS  read-only
  STATUS  current
  DESCRIPTION "Gencomm Page 167 Register 202 to 203"
  ::= { gencommP167Entry 103 }

gencommP167Reg-204-205 OBJECT-TYPE
  SYNTAX  Unsigned32
  MAX-ACCESS  read-only
  STATUS  current
  DESCRIPTION "Gencomm Page 167 Register 204 to 205"
  ::= { gencommP167Entry 104 }

gencommP167Reg-206-207 OBJECT-TYPE
  SYNTAX  Unsigned32
  MAX-ACCESS  read-only
  STATUS  current
  DESCRIPTION "Gencomm Page 167 Register 206 to 207"
  ::= { gencommP167Entry 105 }

gencommP167Reg-208-209 OBJECT-TYPE
  SYNTAX  Unsigned32
  MAX-ACCESS  read-only
  STATUS  current
  DESCRIPTION "Gencomm Page 167 Register 208 to 209"
  ::= { gencommP167Entry 106 }

gencommP167Reg-210-211 OBJECT-TYPE
  SYNTAX  Unsigned32
  MAX-ACCESS  read-only
  STATUS  current
  DESCRIPTION "Gencomm Page 167 Register 210 to 211"
  ::= { gencommP167Entry 107 }

gencommP167Reg-212-213 OBJECT-TYPE
  SYNTAX  Unsigned32
  MAX-ACCESS  read-only
  STATUS  current
  DESCRIPTION "Gencomm Page 167 Register 212 to 213"
  ::= { gencommP167Entry 108 }

gencommP167Reg-214-215 OBJECT-TYPE
  SYNTAX  Unsigned32
  MAX-ACCESS  read-only
  STATUS  current
  DESCRIPTION "Gencomm Page 167 Register 214 to 215"
  ::= { gencommP167Entry 109 }

gencommP167Reg-216-217 OBJECT-TYPE
  SYNTAX  Unsigned32
  MAX-ACCESS  read-only
  STATUS  current
  DESCRIPTION "Gencomm Page 167 Register 216 to 217"
  ::= { gencommP167Entry 110 }

gencommP167Reg-218-219 OBJECT-TYPE
  SYNTAX  Unsigned32
  MAX-ACCESS  read-only
  STATUS  current
  DESCRIPTION "Gencomm Page 167 Register 218 to 219"
  ::= { gencommP167Entry 111 }

gencommP167Reg-220-221 OBJECT-TYPE
  SYNTAX  Unsigned32
  MAX-ACCESS  read-only
  STATUS  current
  DESCRIPTION "Gencomm Page 167 Register 220 to 221"
  ::= { gencommP167Entry 112 }

gencommP167Reg-222-223 OBJECT-TYPE
  SYNTAX  Unsigned32
  MAX-ACCESS  read-only
  STATUS  current
  DESCRIPTION "Gencomm Page 167 Register 222 to 223"
  ::= { gencommP167Entry 113 }

gencommP167Reg-224-225 OBJECT-TYPE
  SYNTAX  Unsigned32
  MAX-ACCESS  read-only
  STATUS  current
  DESCRIPTION "Gencomm Page 167 Register 224 to 225"
  ::= { gencommP167Entry 114 }

gencommP167Reg-226-227 OBJECT-TYPE
  SYNTAX  Unsigned32
  MAX-ACCESS  read-only
  STATUS  current
  DESCRIPTION "Gencomm Page 167 Register 226 to 227"
  ::= { gencommP167Entry 115 }

gencommP167Reg-228-229 OBJECT-TYPE
  SYNTAX  Unsigned32
  MAX-ACCESS  read-only
  STATUS  current
  DESCRIPTION "Gencomm Page 167 Register 228 to 229"
  ::= { gencommP167Entry 116 }

gencommP167Reg-230-231 OBJECT-TYPE
  SYNTAX  Unsigned32
  MAX-ACCESS  read-only
  STATUS  current
  DESCRIPTION "Gencomm Page 167 Register 230 to 231"
  ::= { gencommP167Entry 117 }

gencommP167Reg-232-233 OBJECT-TYPE
  SYNTAX  Unsigned32
  MAX-ACCESS  read-only
  STATUS  current
  DESCRIPTION "Gencomm Page 167 Register 232 to 233"
  ::= { gencommP167Entry 118 }

gencommP167Reg-234-235 OBJECT-TYPE
  SYNTAX  Unsigned32
  MAX-ACCESS  read-only
  STATUS  current
  DESCRIPTION "Gencomm Page 167 Register 234 to 235"
  ::= { gencommP167Entry 119 }

gencommP167Reg-236-237 OBJECT-TYPE
  SYNTAX  Unsigned32
  MAX-ACCESS  read-only
  STATUS  current
  DESCRIPTION "Gencomm Page 167 Register 236 to 237"
  ::= { gencommP167Entry 120 }

gencommP167Reg-238-239 OBJECT-TYPE
  SYNTAX  Unsigned32
  MAX-ACCESS  read-only
  STATUS  current
  DESCRIPTION "Gencomm Page 167 Register 238 to 239"
  ::= { gencommP167Entry 121 }

gencommP167Reg-240-241 OBJECT-TYPE
  SYNTAX  Unsigned32
  MAX-ACCESS  read-only
  STATUS  current
  DESCRIPTION "Gencomm Page 167 Register 240 to 241"
  ::= { gencommP167Entry 122 }

gencommP167Reg-242-243 OBJECT-TYPE
  SYNTAX  Unsigned32
  MAX-ACCESS  read-only
  STATUS  current
  DESCRIPTION "Gencomm Page 167 Register 242 to 243"
  ::= { gencommP167Entry 123 }

gencommP167Reg-244-245 OBJECT-TYPE
  SYNTAX  Unsigned32
  MAX-ACCESS  read-only
  STATUS  current
  DESCRIPTION "Gencomm Page 167 Register 244 to 245"
  ::= { gencommP167Entry 124 }

gencommP167Reg-246-247 OBJECT-TYPE
  SYNTAX  Unsigned32
  MAX-ACCESS  read-only
  STATUS  current
  DESCRIPTION "Gencomm Page 167 Register 246 to 247"
  ::= { gencommP167Entry 125 }

gencommP167Reg-248-249 OBJECT-TYPE
  SYNTAX  Unsigned32
  MAX-ACCESS  read-only
  STATUS  current
  DESCRIPTION "Gencomm Page 167 Register 248 to 249"
  ::= { gencommP167Entry 126 }

gencommP167Reg-250-251 OBJECT-TYPE
  SYNTAX  Unsigned32
  MAX-ACCESS  read-only
  STATUS  current
  DESCRIPTION "Gencomm Page 167 Register 250 to 251"
  ::= { gencommP167Entry 127 }

gencommP167Reg-252-253 OBJECT-TYPE
  SYNTAX  Unsigned32
  MAX-ACCESS  read-only
  STATUS  current
  DESCRIPTION "Gencomm Page 167 Register 252 to 253"
  ::= { gencommP167Entry 128 }

gencommP167Reg-254-255 OBJECT-TYPE
  SYNTAX  Unsigned32
  MAX-ACCESS  read-only
  STATUS  current
  DESCRIPTION "Gencomm Page 167 Register 254 to 255"
  ::= { gencommP167Entry 129 }

gencommP168Reg-0-1 OBJECT-TYPE
  SYNTAX  Unsigned32
  MAX-ACCESS  read-only
  STATUS  current
  DESCRIPTION "Gencomm Page 167 Register 0 to 1"
  ::= { gencommP168Entry 2 }

gencommP168Reg-2-3 OBJECT-TYPE
  SYNTAX  Unsigned32
  MAX-ACCESS  read-only
  STATUS  current
  DESCRIPTION "Gencomm Page 168 Register 2 to 3"
  ::= { gencommP168Entry 3 }

gencommP168Reg-4-5 OBJECT-TYPE
  SYNTAX  Unsigned32
  MAX-ACCESS  read-only
  STATUS  current
  DESCRIPTION "Gencomm Page 168 Register 4 to 5"
  ::= { gencommP168Entry 4 }

gencommP168Reg-6-7 OBJECT-TYPE
  SYNTAX  Unsigned32
  MAX-ACCESS  read-only
  STATUS  current
  DESCRIPTION "Gencomm Page 168 Register 6 to 7"
  ::= { gencommP168Entry 5 }

gencommP168Reg-8-9 OBJECT-TYPE
  SYNTAX  Unsigned32
  MAX-ACCESS  read-only
  STATUS  current
  DESCRIPTION "Gencomm Page 168 Register 8 to 9"
  ::= { gencommP168Entry 6 }

gencommP168Reg-10-11 OBJECT-TYPE
  SYNTAX  Unsigned32
  MAX-ACCESS  read-only
  STATUS  current
  DESCRIPTION "Gencomm Page 168 Register 10 to 11"
  ::= { gencommP168Entry 7 }

gencommP168Reg-12-13 OBJECT-TYPE
  SYNTAX  Unsigned32
  MAX-ACCESS  read-only
  STATUS  current
  DESCRIPTION "Gencomm Page 168 Register 12 to 13"
  ::= { gencommP168Entry 8 }

gencommP168Reg-14-15 OBJECT-TYPE
  SYNTAX  Unsigned32
  MAX-ACCESS  read-only
  STATUS  current
  DESCRIPTION "Gencomm Page 168 Register 14 to 15"
  ::= { gencommP168Entry 9 }

gencommP168Reg-16-17 OBJECT-TYPE
  SYNTAX  Unsigned32
  MAX-ACCESS  read-only
  STATUS  current
  DESCRIPTION "Gencomm Page 168 Register 16 to 17"
  ::= { gencommP168Entry 10 }

gencommP168Reg-18-19 OBJECT-TYPE
  SYNTAX  Unsigned32
  MAX-ACCESS  read-only
  STATUS  current
  DESCRIPTION "Gencomm Page 168 Register 18 to 19"
  ::= { gencommP168Entry 11 }

gencommP168Reg-20-21 OBJECT-TYPE
  SYNTAX  Unsigned32
  MAX-ACCESS  read-only
  STATUS  current
  DESCRIPTION "Gencomm Page 168 Register 20 to 21"
  ::= { gencommP168Entry 12 }

gencommP168Reg-22-23 OBJECT-TYPE
  SYNTAX  Unsigned32
  MAX-ACCESS  read-only
  STATUS  current
  DESCRIPTION "Gencomm Page 168 Register 22 to 23"
  ::= { gencommP168Entry 13 }

gencommP168Reg-24-25 OBJECT-TYPE
  SYNTAX  Unsigned32
  MAX-ACCESS  read-only
  STATUS  current
  DESCRIPTION "Gencomm Page 168 Register 24 to 25"
  ::= { gencommP168Entry 14 }

gencommP168Reg-26-27 OBJECT-TYPE
  SYNTAX  Unsigned32
  MAX-ACCESS  read-only
  STATUS  current
  DESCRIPTION "Gencomm Page 168 Register 26 to 27"
  ::= { gencommP168Entry 15 }

gencommP168Reg-28-29 OBJECT-TYPE
  SYNTAX  Unsigned32
  MAX-ACCESS  read-only
  STATUS  current
  DESCRIPTION "Gencomm Page 168 Register 28 to 29"
  ::= { gencommP168Entry 16 }

gencommP168Reg-30-31 OBJECT-TYPE
  SYNTAX  Unsigned32
  MAX-ACCESS  read-only
  STATUS  current
  DESCRIPTION "Gencomm Page 168 Register 30 to 31"
  ::= { gencommP168Entry 17 }

gencommP168Reg-32-33 OBJECT-TYPE
  SYNTAX  Unsigned32
  MAX-ACCESS  read-only
  STATUS  current
  DESCRIPTION "Gencomm Page 168 Register 32 to 33"
  ::= { gencommP168Entry 18 }

gencommP168Reg-34-35 OBJECT-TYPE
  SYNTAX  Unsigned32
  MAX-ACCESS  read-only
  STATUS  current
  DESCRIPTION "Gencomm Page 168 Register 34 to 35"
  ::= { gencommP168Entry 19 }

gencommP168Reg-36-37 OBJECT-TYPE
  SYNTAX  Unsigned32
  MAX-ACCESS  read-only
  STATUS  current
  DESCRIPTION "Gencomm Page 168 Register 36 to 37"
  ::= { gencommP168Entry 20 }

gencommP168Reg-38-39 OBJECT-TYPE
  SYNTAX  Unsigned32
  MAX-ACCESS  read-only
  STATUS  current
  DESCRIPTION "Gencomm Page 168 Register 38 to 39"
  ::= { gencommP168Entry 21 }

gencommP168Reg-40-41 OBJECT-TYPE
  SYNTAX  Unsigned32
  MAX-ACCESS  read-only
  STATUS  current
  DESCRIPTION "Gencomm Page 168 Register 40 to 41"
  ::= { gencommP168Entry 22 }

gencommP168Reg-42-43 OBJECT-TYPE
  SYNTAX  Unsigned32
  MAX-ACCESS  read-only
  STATUS  current
  DESCRIPTION "Gencomm Page 168 Register 42 to 43"
  ::= { gencommP168Entry 23 }

gencommP168Reg-44-45 OBJECT-TYPE
  SYNTAX  Unsigned32
  MAX-ACCESS  read-only
  STATUS  current
  DESCRIPTION "Gencomm Page 168 Register 44 to 45"
  ::= { gencommP168Entry 24 }

gencommP168Reg-46-47 OBJECT-TYPE
  SYNTAX  Unsigned32
  MAX-ACCESS  read-only
  STATUS  current
  DESCRIPTION "Gencomm Page 168 Register 46 to 47"
  ::= { gencommP168Entry 25 }

gencommP168Reg-48-49 OBJECT-TYPE
  SYNTAX  Unsigned32
  MAX-ACCESS  read-only
  STATUS  current
  DESCRIPTION "Gencomm Page 168 Register 48 to 49"
  ::= { gencommP168Entry 26 }

gencommP168Reg-50-51 OBJECT-TYPE
  SYNTAX  Unsigned32
  MAX-ACCESS  read-only
  STATUS  current
  DESCRIPTION "Gencomm Page 168 Register 50 to 51"
  ::= { gencommP168Entry 27 }

gencommP168Reg-52-53 OBJECT-TYPE
  SYNTAX  Unsigned32
  MAX-ACCESS  read-only
  STATUS  current
  DESCRIPTION "Gencomm Page 168 Register 52 to 53"
  ::= { gencommP168Entry 28 }

gencommP168Reg-54-55 OBJECT-TYPE
  SYNTAX  Unsigned32
  MAX-ACCESS  read-only
  STATUS  current
  DESCRIPTION "Gencomm Page 168 Register 54 to 55"
  ::= { gencommP168Entry 29 }

gencommP168Reg-56-57 OBJECT-TYPE
  SYNTAX  Unsigned32
  MAX-ACCESS  read-only
  STATUS  current
  DESCRIPTION "Gencomm Page 168 Register 56 to 57"
  ::= { gencommP168Entry 30 }

gencommP168Reg-58-59 OBJECT-TYPE
  SYNTAX  Unsigned32
  MAX-ACCESS  read-only
  STATUS  current
  DESCRIPTION "Gencomm Page 168 Register 58 to 59"
  ::= { gencommP168Entry 31 }

gencommP168Reg-60-61 OBJECT-TYPE
  SYNTAX  Unsigned32
  MAX-ACCESS  read-only
  STATUS  current
  DESCRIPTION "Gencomm Page 168 Register 60 to 61"
  ::= { gencommP168Entry 32 }

gencommP168Reg-62-63 OBJECT-TYPE
  SYNTAX  Unsigned32
  MAX-ACCESS  read-only
  STATUS  current
  DESCRIPTION "Gencomm Page 168 Register 62 to 63"
  ::= { gencommP168Entry 33 }

gencommP168Reg-64-65 OBJECT-TYPE
  SYNTAX  Unsigned32
  MAX-ACCESS  read-only
  STATUS  current
  DESCRIPTION "Gencomm Page 168 Register 64 to 65"
  ::= { gencommP168Entry 34 }

gencommP168Reg-66-67 OBJECT-TYPE
  SYNTAX  Unsigned32
  MAX-ACCESS  read-only
  STATUS  current
  DESCRIPTION "Gencomm Page 168 Register 66 to 67"
  ::= { gencommP168Entry 35 }

gencommP168Reg-68-69 OBJECT-TYPE
  SYNTAX  Unsigned32
  MAX-ACCESS  read-only
  STATUS  current
  DESCRIPTION "Gencomm Page 168 Register 68 to 69"
  ::= { gencommP168Entry 36 }

gencommP168Reg-70-71 OBJECT-TYPE
  SYNTAX  Unsigned32
  MAX-ACCESS  read-only
  STATUS  current
  DESCRIPTION "Gencomm Page 168 Register 70 to 71"
  ::= { gencommP168Entry 37 }

gencommP168Reg-72-73 OBJECT-TYPE
  SYNTAX  Unsigned32
  MAX-ACCESS  read-only
  STATUS  current
  DESCRIPTION "Gencomm Page 168 Register 72 to 73"
  ::= { gencommP168Entry 38 }

gencommP168Reg-74-75 OBJECT-TYPE
  SYNTAX  Unsigned32
  MAX-ACCESS  read-only
  STATUS  current
  DESCRIPTION "Gencomm Page 168 Register 74 to 75"
  ::= { gencommP168Entry 39 }

gencommP168Reg-76-77 OBJECT-TYPE
  SYNTAX  Unsigned32
  MAX-ACCESS  read-only
  STATUS  current
  DESCRIPTION "Gencomm Page 168 Register 76 to 77"
  ::= { gencommP168Entry 40 }

gencommP168Reg-78-79 OBJECT-TYPE
  SYNTAX  Unsigned32
  MAX-ACCESS  read-only
  STATUS  current
  DESCRIPTION "Gencomm Page 168 Register 78 to 79"
  ::= { gencommP168Entry 41 }

gencommP168Reg-80-81 OBJECT-TYPE
  SYNTAX  Unsigned32
  MAX-ACCESS  read-only
  STATUS  current
  DESCRIPTION "Gencomm Page 168 Register 80 to 81"
  ::= { gencommP168Entry 42 }

gencommP168Reg-82-83 OBJECT-TYPE
  SYNTAX  Unsigned32
  MAX-ACCESS  read-only
  STATUS  current
  DESCRIPTION "Gencomm Page 168 Register 82 to 83"
  ::= { gencommP168Entry 43 }

gencommP168Reg-84-85 OBJECT-TYPE
  SYNTAX  Unsigned32
  MAX-ACCESS  read-only
  STATUS  current
  DESCRIPTION "Gencomm Page 168 Register 84 to 85"
  ::= { gencommP168Entry 44 }

gencommP168Reg-86-87 OBJECT-TYPE
  SYNTAX  Unsigned32
  MAX-ACCESS  read-only
  STATUS  current
  DESCRIPTION "Gencomm Page 168 Register 86 to 87"
  ::= { gencommP168Entry 45 }

gencommP168Reg-88-89 OBJECT-TYPE
  SYNTAX  Unsigned32
  MAX-ACCESS  read-only
  STATUS  current
  DESCRIPTION "Gencomm Page 168 Register 88 to 89"
  ::= { gencommP168Entry 46 }

gencommP168Reg-90-91 OBJECT-TYPE
  SYNTAX  Unsigned32
  MAX-ACCESS  read-only
  STATUS  current
  DESCRIPTION "Gencomm Page 168 Register 90 to 91"
  ::= { gencommP168Entry 47 }

gencommP168Reg-92-93 OBJECT-TYPE
  SYNTAX  Unsigned32
  MAX-ACCESS  read-only
  STATUS  current
  DESCRIPTION "Gencomm Page 168 Register 92 to 93"
  ::= { gencommP168Entry 48 }

gencommP168Reg-94-95 OBJECT-TYPE
  SYNTAX  Unsigned32
  MAX-ACCESS  read-only
  STATUS  current
  DESCRIPTION "Gencomm Page 168 Register 94 to 95"
  ::= { gencommP168Entry 49 }

gencommP168Reg-96-97 OBJECT-TYPE
  SYNTAX  Unsigned32
  MAX-ACCESS  read-only
  STATUS  current
  DESCRIPTION "Gencomm Page 168 Register 96 to 97"
  ::= { gencommP168Entry 50 }

gencommP168Reg-98-99 OBJECT-TYPE
  SYNTAX  Unsigned32
  MAX-ACCESS  read-only
  STATUS  current
  DESCRIPTION "Gencomm Page 168 Register 98 to 99"
  ::= { gencommP168Entry 51 }

gencommP168Reg-100-101 OBJECT-TYPE
  SYNTAX  Unsigned32
  MAX-ACCESS  read-only
  STATUS  current
  DESCRIPTION "Gencomm Page 168 Register 100 to 101"
  ::= { gencommP168Entry 52 }

gencommP168Reg-102-103 OBJECT-TYPE
  SYNTAX  Unsigned32
  MAX-ACCESS  read-only
  STATUS  current
  DESCRIPTION "Gencomm Page 168 Register 102 to 103"
  ::= { gencommP168Entry 53 }

gencommP168Reg-104-105 OBJECT-TYPE
  SYNTAX  Unsigned32
  MAX-ACCESS  read-only
  STATUS  current
  DESCRIPTION "Gencomm Page 168 Register 104 to 105"
  ::= { gencommP168Entry 54 }

gencommP168Reg-106-107 OBJECT-TYPE
  SYNTAX  Unsigned32
  MAX-ACCESS  read-only
  STATUS  current
  DESCRIPTION "Gencomm Page 168 Register 106 to 107"
  ::= { gencommP168Entry 55 }

gencommP168Reg-108-109 OBJECT-TYPE
  SYNTAX  Unsigned32
  MAX-ACCESS  read-only
  STATUS  current
  DESCRIPTION "Gencomm Page 168 Register 108 to 109"
  ::= { gencommP168Entry 56 }

gencommP168Reg-110-111 OBJECT-TYPE
  SYNTAX  Unsigned32
  MAX-ACCESS  read-only
  STATUS  current
  DESCRIPTION "Gencomm Page 168 Register 110 to 111"
  ::= { gencommP168Entry 57 }

gencommP168Reg-112-113 OBJECT-TYPE
  SYNTAX  Unsigned32
  MAX-ACCESS  read-only
  STATUS  current
  DESCRIPTION "Gencomm Page 168 Register 112 to 113"
  ::= { gencommP168Entry 58 }

gencommP168Reg-114-115 OBJECT-TYPE
  SYNTAX  Unsigned32
  MAX-ACCESS  read-only
  STATUS  current
  DESCRIPTION "Gencomm Page 168 Register 114 to 115"
  ::= { gencommP168Entry 59 }

gencommP168Reg-116-117 OBJECT-TYPE
  SYNTAX  Unsigned32
  MAX-ACCESS  read-only
  STATUS  current
  DESCRIPTION "Gencomm Page 168 Register 116 to 117"
  ::= { gencommP168Entry 60 }

gencommP168Reg-118-119 OBJECT-TYPE
  SYNTAX  Unsigned32
  MAX-ACCESS  read-only
  STATUS  current
  DESCRIPTION "Gencomm Page 168 Register 118 to 119"
  ::= { gencommP168Entry 61 }

gencommP168Reg-120-121 OBJECT-TYPE
  SYNTAX  Unsigned32
  MAX-ACCESS  read-only
  STATUS  current
  DESCRIPTION "Gencomm Page 168 Register 120 to 121"
  ::= { gencommP168Entry 62 }

gencommP168Reg-122-123 OBJECT-TYPE
  SYNTAX  Unsigned32
  MAX-ACCESS  read-only
  STATUS  current
  DESCRIPTION "Gencomm Page 168 Register 122 to 123"
  ::= { gencommP168Entry 63 }

gencommP168Reg-124-125 OBJECT-TYPE
  SYNTAX  Unsigned32
  MAX-ACCESS  read-only
  STATUS  current
  DESCRIPTION "Gencomm Page 168 Register 124 to 125"
  ::= { gencommP168Entry 64 }

gencommP168Reg-126-127 OBJECT-TYPE
  SYNTAX  Unsigned32
  MAX-ACCESS  read-only
  STATUS  current
  DESCRIPTION "Gencomm Page 168 Register 126 to 127"
  ::= { gencommP168Entry 65 }

gencommP168Reg-128-129 OBJECT-TYPE
  SYNTAX  Unsigned32
  MAX-ACCESS  read-only
  STATUS  current
  DESCRIPTION "Gencomm Page 168 Register 128 to 129"
  ::= { gencommP168Entry 66 }

gencommP168Reg-130-131 OBJECT-TYPE
  SYNTAX  Unsigned32
  MAX-ACCESS  read-only
  STATUS  current
  DESCRIPTION "Gencomm Page 168 Register 130 to 131"
  ::= { gencommP168Entry 67 }

gencommP168Reg-132-133 OBJECT-TYPE
  SYNTAX  Unsigned32
  MAX-ACCESS  read-only
  STATUS  current
  DESCRIPTION "Gencomm Page 168 Register 132 to 133"
  ::= { gencommP168Entry 68 }

gencommP168Reg-134-135 OBJECT-TYPE
  SYNTAX  Unsigned32
  MAX-ACCESS  read-only
  STATUS  current
  DESCRIPTION "Gencomm Page 168 Register 134 to 135"
  ::= { gencommP168Entry 69 }

gencommP168Reg-136-137 OBJECT-TYPE
  SYNTAX  Unsigned32
  MAX-ACCESS  read-only
  STATUS  current
  DESCRIPTION "Gencomm Page 168 Register 136 to 137"
  ::= { gencommP168Entry 70 }

gencommP168Reg-138-139 OBJECT-TYPE
  SYNTAX  Unsigned32
  MAX-ACCESS  read-only
  STATUS  current
  DESCRIPTION "Gencomm Page 168 Register 138 to 139"
  ::= { gencommP168Entry 71 }

gencommP168Reg-140-141 OBJECT-TYPE
  SYNTAX  Unsigned32
  MAX-ACCESS  read-only
  STATUS  current
  DESCRIPTION "Gencomm Page 168 Register 140 to 141"
  ::= { gencommP168Entry 72 }

gencommP168Reg-142-143 OBJECT-TYPE
  SYNTAX  Unsigned32
  MAX-ACCESS  read-only
  STATUS  current
  DESCRIPTION "Gencomm Page 168 Register 142 to 143"
  ::= { gencommP168Entry 73 }

gencommP168Reg-144-145 OBJECT-TYPE
  SYNTAX  Unsigned32
  MAX-ACCESS  read-only
  STATUS  current
  DESCRIPTION "Gencomm Page 168 Register 144 to 145"
  ::= { gencommP168Entry 74 }

gencommP168Reg-146-147 OBJECT-TYPE
  SYNTAX  Unsigned32
  MAX-ACCESS  read-only
  STATUS  current
  DESCRIPTION "Gencomm Page 168 Register 146 to 147"
  ::= { gencommP168Entry 75 }

gencommP168Reg-148-149 OBJECT-TYPE
  SYNTAX  Unsigned32
  MAX-ACCESS  read-only
  STATUS  current
  DESCRIPTION "Gencomm Page 168 Register 148 to 149"
  ::= { gencommP168Entry 76 }

gencommP168Reg-150-151 OBJECT-TYPE
  SYNTAX  Unsigned32
  MAX-ACCESS  read-only
  STATUS  current
  DESCRIPTION "Gencomm Page 168 Register 150 to 151"
  ::= { gencommP168Entry 77 }

gencommP168Reg-152-153 OBJECT-TYPE
  SYNTAX  Unsigned32
  MAX-ACCESS  read-only
  STATUS  current
  DESCRIPTION "Gencomm Page 168 Register 152 to 153"
  ::= { gencommP168Entry 78 }

gencommP168Reg-154-155 OBJECT-TYPE
  SYNTAX  Unsigned32
  MAX-ACCESS  read-only
  STATUS  current
  DESCRIPTION "Gencomm Page 168 Register 154 to 155"
  ::= { gencommP168Entry 79 }

gencommP168Reg-156-157 OBJECT-TYPE
  SYNTAX  Unsigned32
  MAX-ACCESS  read-only
  STATUS  current
  DESCRIPTION "Gencomm Page 168 Register 156 to 157"
  ::= { gencommP168Entry 80 }

gencommP168Reg-158-159 OBJECT-TYPE
  SYNTAX  Unsigned32
  MAX-ACCESS  read-only
  STATUS  current
  DESCRIPTION "Gencomm Page 168 Register 158 to 159"
  ::= { gencommP168Entry 81 }

gencommP168Reg-160-161 OBJECT-TYPE
  SYNTAX  Unsigned32
  MAX-ACCESS  read-only
  STATUS  current
  DESCRIPTION "Gencomm Page 168 Register 160 to 161"
  ::= { gencommP168Entry 82 }

gencommP168Reg-162-163 OBJECT-TYPE
  SYNTAX  Unsigned32
  MAX-ACCESS  read-only
  STATUS  current
  DESCRIPTION "Gencomm Page 168 Register 162 to 163"
  ::= { gencommP168Entry 83 }

gencommP168Reg-164-165 OBJECT-TYPE
  SYNTAX  Unsigned32
  MAX-ACCESS  read-only
  STATUS  current
  DESCRIPTION "Gencomm Page 168 Register 164 to 165"
  ::= { gencommP168Entry 84 }

gencommP168Reg-166-167 OBJECT-TYPE
  SYNTAX  Unsigned32
  MAX-ACCESS  read-only
  STATUS  current
  DESCRIPTION "Gencomm Page 168 Register 166 to 167"
  ::= { gencommP168Entry 85 }

gencommP168Reg-168-169 OBJECT-TYPE
  SYNTAX  Unsigned32
  MAX-ACCESS  read-only
  STATUS  current
  DESCRIPTION "Gencomm Page 168 Register 168 to 169"
  ::= { gencommP168Entry 86 }

gencommP168Reg-170-171 OBJECT-TYPE
  SYNTAX  Unsigned32
  MAX-ACCESS  read-only
  STATUS  current
  DESCRIPTION "Gencomm Page 168 Register 170 to 171"
  ::= { gencommP168Entry 87 }

gencommP168Reg-172-173 OBJECT-TYPE
  SYNTAX  Unsigned32
  MAX-ACCESS  read-only
  STATUS  current
  DESCRIPTION "Gencomm Page 168 Register 172 to 173"
  ::= { gencommP168Entry 88 }

gencommP168Reg-174-175 OBJECT-TYPE
  SYNTAX  Unsigned32
  MAX-ACCESS  read-only
  STATUS  current
  DESCRIPTION "Gencomm Page 168 Register 174 to 175"
  ::= { gencommP168Entry 89 }

gencommP168Reg-176-177 OBJECT-TYPE
  SYNTAX  Unsigned32
  MAX-ACCESS  read-only
  STATUS  current
  DESCRIPTION "Gencomm Page 168 Register 176 to 177"
  ::= { gencommP168Entry 90 }

gencommP168Reg-178-179 OBJECT-TYPE
  SYNTAX  Unsigned32
  MAX-ACCESS  read-only
  STATUS  current
  DESCRIPTION "Gencomm Page 168 Register 178 to 179"
  ::= { gencommP168Entry 91 }

gencommP168Reg-180-181 OBJECT-TYPE
  SYNTAX  Unsigned32
  MAX-ACCESS  read-only
  STATUS  current
  DESCRIPTION "Gencomm Page 168 Register 180 to 181"
  ::= { gencommP168Entry 92 }

gencommP168Reg-182-183 OBJECT-TYPE
  SYNTAX  Unsigned32
  MAX-ACCESS  read-only
  STATUS  current
  DESCRIPTION "Gencomm Page 168 Register 182 to 183"
  ::= { gencommP168Entry 93 }

gencommP168Reg-184-185 OBJECT-TYPE
  SYNTAX  Unsigned32
  MAX-ACCESS  read-only
  STATUS  current
  DESCRIPTION "Gencomm Page 168 Register 184 to 185"
  ::= { gencommP168Entry 94 }

gencommP168Reg-186-187 OBJECT-TYPE
  SYNTAX  Unsigned32
  MAX-ACCESS  read-only
  STATUS  current
  DESCRIPTION "Gencomm Page 168 Register 186 to 187"
  ::= { gencommP168Entry 95 }

gencommP168Reg-188-189 OBJECT-TYPE
  SYNTAX  Unsigned32
  MAX-ACCESS  read-only
  STATUS  current
  DESCRIPTION "Gencomm Page 168 Register 188 to 189"
  ::= { gencommP168Entry 96 }

gencommP168Reg-190-191 OBJECT-TYPE
  SYNTAX  Unsigned32
  MAX-ACCESS  read-only
  STATUS  current
  DESCRIPTION "Gencomm Page 168 Register 190 to 191"
  ::= { gencommP168Entry 97 }

gencommP168Reg-192-193 OBJECT-TYPE
  SYNTAX  Unsigned32
  MAX-ACCESS  read-only
  STATUS  current
  DESCRIPTION "Gencomm Page 168 Register 192 to 193"
  ::= { gencommP168Entry 98 }

gencommP168Reg-194-195 OBJECT-TYPE
  SYNTAX  Unsigned32
  MAX-ACCESS  read-only
  STATUS  current
  DESCRIPTION "Gencomm Page 168 Register 194 to 195"
  ::= { gencommP168Entry 99 }

gencommP168Reg-196-197 OBJECT-TYPE
  SYNTAX  Unsigned32
  MAX-ACCESS  read-only
  STATUS  current
  DESCRIPTION "Gencomm Page 168 Register 196 to 197"
  ::= { gencommP168Entry 100 }

gencommP168Reg-198-199 OBJECT-TYPE
  SYNTAX  Unsigned32
  MAX-ACCESS  read-only
  STATUS  current
  DESCRIPTION "Gencomm Page 168 Register 198 to 199"
  ::= { gencommP168Entry 101 }

gencommP168Reg-200-201 OBJECT-TYPE
  SYNTAX  Unsigned32
  MAX-ACCESS  read-only
  STATUS  current
  DESCRIPTION "Gencomm Page 168 Register 200 to 201"
  ::= { gencommP168Entry 102 }

gencommP168Reg-202-203 OBJECT-TYPE
  SYNTAX  Unsigned32
  MAX-ACCESS  read-only
  STATUS  current
  DESCRIPTION "Gencomm Page 168 Register 202 to 203"
  ::= { gencommP168Entry 103 }

gencommP168Reg-204-205 OBJECT-TYPE
  SYNTAX  Unsigned32
  MAX-ACCESS  read-only
  STATUS  current
  DESCRIPTION "Gencomm Page 168 Register 204 to 205"
  ::= { gencommP168Entry 104 }

gencommP168Reg-206-207 OBJECT-TYPE
  SYNTAX  Unsigned32
  MAX-ACCESS  read-only
  STATUS  current
  DESCRIPTION "Gencomm Page 168 Register 206 to 207"
  ::= { gencommP168Entry 105 }

gencommP168Reg-208-209 OBJECT-TYPE
  SYNTAX  Unsigned32
  MAX-ACCESS  read-only
  STATUS  current
  DESCRIPTION "Gencomm Page 168 Register 208 to 209"
  ::= { gencommP168Entry 106 }

gencommP168Reg-210-211 OBJECT-TYPE
  SYNTAX  Unsigned32
  MAX-ACCESS  read-only
  STATUS  current
  DESCRIPTION "Gencomm Page 168 Register 210 to 211"
  ::= { gencommP168Entry 107 }

gencommP168Reg-212-213 OBJECT-TYPE
  SYNTAX  Unsigned32
  MAX-ACCESS  read-only
  STATUS  current
  DESCRIPTION "Gencomm Page 168 Register 212 to 213"
  ::= { gencommP168Entry 108 }

gencommP168Reg-214-215 OBJECT-TYPE
  SYNTAX  Unsigned32
  MAX-ACCESS  read-only
  STATUS  current
  DESCRIPTION "Gencomm Page 168 Register 214 to 215"
  ::= { gencommP168Entry 109 }

gencommP168Reg-216-217 OBJECT-TYPE
  SYNTAX  Unsigned32
  MAX-ACCESS  read-only
  STATUS  current
  DESCRIPTION "Gencomm Page 168 Register 216 to 217"
  ::= { gencommP168Entry 110 }

gencommP168Reg-218-219 OBJECT-TYPE
  SYNTAX  Unsigned32
  MAX-ACCESS  read-only
  STATUS  current
  DESCRIPTION "Gencomm Page 168 Register 218 to 219"
  ::= { gencommP168Entry 111 }

gencommP168Reg-220-221 OBJECT-TYPE
  SYNTAX  Unsigned32
  MAX-ACCESS  read-only
  STATUS  current
  DESCRIPTION "Gencomm Page 168 Register 220 to 221"
  ::= { gencommP168Entry 112 }

gencommP168Reg-222-223 OBJECT-TYPE
  SYNTAX  Unsigned32
  MAX-ACCESS  read-only
  STATUS  current
  DESCRIPTION "Gencomm Page 168 Register 222 to 223"
  ::= { gencommP168Entry 113 }

gencommP168Reg-224-225 OBJECT-TYPE
  SYNTAX  Unsigned32
  MAX-ACCESS  read-only
  STATUS  current
  DESCRIPTION "Gencomm Page 168 Register 224 to 225"
  ::= { gencommP168Entry 114 }

gencommP168Reg-226-227 OBJECT-TYPE
  SYNTAX  Unsigned32
  MAX-ACCESS  read-only
  STATUS  current
  DESCRIPTION "Gencomm Page 168 Register 226 to 227"
  ::= { gencommP168Entry 115 }

gencommP168Reg-228-229 OBJECT-TYPE
  SYNTAX  Unsigned32
  MAX-ACCESS  read-only
  STATUS  current
  DESCRIPTION "Gencomm Page 168 Register 228 to 229"
  ::= { gencommP168Entry 116 }

gencommP168Reg-230-231 OBJECT-TYPE
  SYNTAX  Unsigned32
  MAX-ACCESS  read-only
  STATUS  current
  DESCRIPTION "Gencomm Page 168 Register 230 to 231"
  ::= { gencommP168Entry 117 }

gencommP168Reg-232-233 OBJECT-TYPE
  SYNTAX  Unsigned32
  MAX-ACCESS  read-only
  STATUS  current
  DESCRIPTION "Gencomm Page 168 Register 232 to 233"
  ::= { gencommP168Entry 118 }

gencommP168Reg-234-235 OBJECT-TYPE
  SYNTAX  Unsigned32
  MAX-ACCESS  read-only
  STATUS  current
  DESCRIPTION "Gencomm Page 168 Register 234 to 235"
  ::= { gencommP168Entry 119 }

gencommP168Reg-236-237 OBJECT-TYPE
  SYNTAX  Unsigned32
  MAX-ACCESS  read-only
  STATUS  current
  DESCRIPTION "Gencomm Page 168 Register 236 to 237"
  ::= { gencommP168Entry 120 }

gencommP168Reg-238-239 OBJECT-TYPE
  SYNTAX  Unsigned32
  MAX-ACCESS  read-only
  STATUS  current
  DESCRIPTION "Gencomm Page 168 Register 238 to 239"
  ::= { gencommP168Entry 121 }

gencommP168Reg-240-241 OBJECT-TYPE
  SYNTAX  Unsigned32
  MAX-ACCESS  read-only
  STATUS  current
  DESCRIPTION "Gencomm Page 168 Register 240 to 241"
  ::= { gencommP168Entry 122 }

gencommP168Reg-242-243 OBJECT-TYPE
  SYNTAX  Unsigned32
  MAX-ACCESS  read-only
  STATUS  current
  DESCRIPTION "Gencomm Page 168 Register 242 to 243"
  ::= { gencommP168Entry 123 }

gencommP168Reg-244-245 OBJECT-TYPE
  SYNTAX  Unsigned32
  MAX-ACCESS  read-only
  STATUS  current
  DESCRIPTION "Gencomm Page 168 Register 244 to 245"
  ::= { gencommP168Entry 124 }

gencommP168Reg-246-247 OBJECT-TYPE
  SYNTAX  Unsigned32
  MAX-ACCESS  read-only
  STATUS  current
  DESCRIPTION "Gencomm Page 168 Register 246 to 247"
  ::= { gencommP168Entry 125 }

gencommP168Reg-248-249 OBJECT-TYPE
  SYNTAX  Unsigned32
  MAX-ACCESS  read-only
  STATUS  current
  DESCRIPTION "Gencomm Page 168 Register 248 to 249"
  ::= { gencommP168Entry 126 }

gencommP168Reg-250-251 OBJECT-TYPE
  SYNTAX  Unsigned32
  MAX-ACCESS  read-only
  STATUS  current
  DESCRIPTION "Gencomm Page 168 Register 250 to 251"
  ::= { gencommP168Entry 127 }

gencommP168Reg-252-253 OBJECT-TYPE
  SYNTAX  Unsigned32
  MAX-ACCESS  read-only
  STATUS  current
  DESCRIPTION "Gencomm Page 168 Register 252 to 253"
  ::= { gencommP168Entry 128 }

gencommP168Reg-254-255 OBJECT-TYPE
  SYNTAX  Unsigned32
  MAX-ACCESS  read-only
  STATUS  current
  DESCRIPTION "Gencomm Page 168 Register 254 to 255"
  ::= { gencommP168Entry 129 }

gencommP169Reg-0-1 OBJECT-TYPE
  SYNTAX  Unsigned32
  MAX-ACCESS  read-only
  STATUS  current
  DESCRIPTION "Gencomm Page 169 Register 0 to 1"
  ::= { gencommP169Entry 2 }

gencommP169Reg-2-3 OBJECT-TYPE
  SYNTAX  Unsigned32
  MAX-ACCESS  read-only
  STATUS  current
  DESCRIPTION "Gencomm Page 169  Register 2 to 3"
  ::= { gencommP169Entry 3 }

gencommP169Reg-4-5 OBJECT-TYPE
  SYNTAX  Unsigned32
  MAX-ACCESS  read-only
  STATUS  current
  DESCRIPTION "Gencomm Page 169  Register 4 to 5"
  ::= { gencommP169Entry 4 }

gencommP169Reg-6-7 OBJECT-TYPE
  SYNTAX  Unsigned32
  MAX-ACCESS  read-only
  STATUS  current
  DESCRIPTION "Gencomm Page 169  Register 6 to 7"
  ::= { gencommP169Entry 5 }

gencommP169Reg-8-9 OBJECT-TYPE
  SYNTAX  Unsigned32
  MAX-ACCESS  read-only
  STATUS  current
  DESCRIPTION "Gencomm Page 169  Register 8 to 9"
  ::= { gencommP169Entry 6 }

gencommP169Reg-10-11 OBJECT-TYPE
  SYNTAX  Unsigned32
  MAX-ACCESS  read-only
  STATUS  current
  DESCRIPTION "Gencomm Page 169  Register 10 to 11"
  ::= { gencommP169Entry 7 }

gencommP169Reg-12-13 OBJECT-TYPE
  SYNTAX  Unsigned32
  MAX-ACCESS  read-only
  STATUS  current
  DESCRIPTION "Gencomm Page 169  Register 12 to 13"
  ::= { gencommP169Entry 8 }

gencommP169Reg-14-15 OBJECT-TYPE
  SYNTAX  Unsigned32
  MAX-ACCESS  read-only
  STATUS  current
  DESCRIPTION "Gencomm Page 169  Register 14 to 15"
  ::= { gencommP169Entry 9 }

gencommP169Reg-16-17 OBJECT-TYPE
  SYNTAX  Unsigned32
  MAX-ACCESS  read-only
  STATUS  current
  DESCRIPTION "Gencomm Page 169  Register 16 to 17"
  ::= { gencommP169Entry 10 }

gencommP169Reg-18-19 OBJECT-TYPE
  SYNTAX  Unsigned32
  MAX-ACCESS  read-only
  STATUS  current
  DESCRIPTION "Gencomm Page 169  Register 18 to 19"
  ::= { gencommP169Entry 11 }

gencommP169Reg-20-21 OBJECT-TYPE
  SYNTAX  Unsigned32
  MAX-ACCESS  read-only
  STATUS  current
  DESCRIPTION "Gencomm Page 169  Register 20 to 21"
  ::= { gencommP169Entry 12 }

gencommP169Reg-22-23 OBJECT-TYPE
  SYNTAX  Unsigned32
  MAX-ACCESS  read-only
  STATUS  current
  DESCRIPTION "Gencomm Page 169  Register 22 to 23"
  ::= { gencommP169Entry 13 }

gencommP169Reg-24-25 OBJECT-TYPE
  SYNTAX  Unsigned32
  MAX-ACCESS  read-only
  STATUS  current
  DESCRIPTION "Gencomm Page 169  Register 24 to 25"
  ::= { gencommP169Entry 14 }

gencommP169Reg-26-27 OBJECT-TYPE
  SYNTAX  Unsigned32
  MAX-ACCESS  read-only
  STATUS  current
  DESCRIPTION "Gencomm Page 169  Register 26 to 27"
  ::= { gencommP169Entry 15 }

gencommP169Reg-28-29 OBJECT-TYPE
  SYNTAX  Unsigned32
  MAX-ACCESS  read-only
  STATUS  current
  DESCRIPTION "Gencomm Page 169  Register 28 to 29"
  ::= { gencommP169Entry 16 }

gencommP169Reg-30-31 OBJECT-TYPE
  SYNTAX  Unsigned32
  MAX-ACCESS  read-only
  STATUS  current
  DESCRIPTION "Gencomm Page 169  Register 30 to 31"
  ::= { gencommP169Entry 17 }

gencommP169Reg-32-33 OBJECT-TYPE
  SYNTAX  Unsigned32
  MAX-ACCESS  read-only
  STATUS  current
  DESCRIPTION "Gencomm Page 169  Register 32 to 33"
  ::= { gencommP169Entry 18 }

gencommP169Reg-34-35 OBJECT-TYPE
  SYNTAX  Unsigned32
  MAX-ACCESS  read-only
  STATUS  current
  DESCRIPTION "Gencomm Page 169  Register 34 to 35"
  ::= { gencommP169Entry 19 }

gencommP169Reg-36-37 OBJECT-TYPE
  SYNTAX  Unsigned32
  MAX-ACCESS  read-only
  STATUS  current
  DESCRIPTION "Gencomm Page 169  Register 36 to 37"
  ::= { gencommP169Entry 20 }

gencommP169Reg-38-39 OBJECT-TYPE
  SYNTAX  Unsigned32
  MAX-ACCESS  read-only
  STATUS  current
  DESCRIPTION "Gencomm Page 169  Register 38 to 39"
  ::= { gencommP169Entry 21 }

gencommP169Reg-40-41 OBJECT-TYPE
  SYNTAX  Unsigned32
  MAX-ACCESS  read-only
  STATUS  current
  DESCRIPTION "Gencomm Page 169  Register 40 to 41"
  ::= { gencommP169Entry 22 }

gencommP169Reg-42-43 OBJECT-TYPE
  SYNTAX  Unsigned32
  MAX-ACCESS  read-only
  STATUS  current
  DESCRIPTION "Gencomm Page 169  Register 42 to 43"
  ::= { gencommP169Entry 23 }

gencommP169Reg-44-45 OBJECT-TYPE
  SYNTAX  Unsigned32
  MAX-ACCESS  read-only
  STATUS  current
  DESCRIPTION "Gencomm Page 169  Register 44 to 45"
  ::= { gencommP169Entry 24 }

gencommP169Reg-46-47 OBJECT-TYPE
  SYNTAX  Unsigned32
  MAX-ACCESS  read-only
  STATUS  current
  DESCRIPTION "Gencomm Page 169  Register 46 to 47"
  ::= { gencommP169Entry 25 }

gencommP169Reg-48-49 OBJECT-TYPE
  SYNTAX  Unsigned32
  MAX-ACCESS  read-only
  STATUS  current
  DESCRIPTION "Gencomm Page 169  Register 48 to 49"
  ::= { gencommP169Entry 26 }

gencommP169Reg-50-51 OBJECT-TYPE
  SYNTAX  Unsigned32
  MAX-ACCESS  read-only
  STATUS  current
  DESCRIPTION "Gencomm Page 169  Register 50 to 51"
  ::= { gencommP169Entry 27 }

gencommP169Reg-52-53 OBJECT-TYPE
  SYNTAX  Unsigned32
  MAX-ACCESS  read-only
  STATUS  current
  DESCRIPTION "Gencomm Page 169  Register 52 to 53"
  ::= { gencommP169Entry 28 }

gencommP169Reg-54-55 OBJECT-TYPE
  SYNTAX  Unsigned32
  MAX-ACCESS  read-only
  STATUS  current
  DESCRIPTION "Gencomm Page 169  Register 54 to 55"
  ::= { gencommP169Entry 29 }

gencommP169Reg-56-57 OBJECT-TYPE
  SYNTAX  Unsigned32
  MAX-ACCESS  read-only
  STATUS  current
  DESCRIPTION "Gencomm Page 169  Register 56 to 57"
  ::= { gencommP169Entry 30 }

gencommP169Reg-58-59 OBJECT-TYPE
  SYNTAX  Unsigned32
  MAX-ACCESS  read-only
  STATUS  current
  DESCRIPTION "Gencomm Page 169  Register 58 to 59"
  ::= { gencommP169Entry 31 }

gencommP169Reg-60-61 OBJECT-TYPE
  SYNTAX  Unsigned32
  MAX-ACCESS  read-only
  STATUS  current
  DESCRIPTION "Gencomm Page 169  Register 60 to 61"
  ::= { gencommP169Entry 32 }

gencommP169Reg-62-63 OBJECT-TYPE
  SYNTAX  Unsigned32
  MAX-ACCESS  read-only
  STATUS  current
  DESCRIPTION "Gencomm Page 169  Register 62 to 63"
  ::= { gencommP169Entry 33 }

gencommP169Reg-64-65 OBJECT-TYPE
  SYNTAX  Unsigned32
  MAX-ACCESS  read-only
  STATUS  current
  DESCRIPTION "Gencomm Page 169  Register 64 to 65"
  ::= { gencommP169Entry 34 }

gencommP169Reg-66-67 OBJECT-TYPE
  SYNTAX  Unsigned32
  MAX-ACCESS  read-only
  STATUS  current
  DESCRIPTION "Gencomm Page 169  Register 66 to 67"
  ::= { gencommP169Entry 35 }

gencommP169Reg-68-69 OBJECT-TYPE
  SYNTAX  Unsigned32
  MAX-ACCESS  read-only
  STATUS  current
  DESCRIPTION "Gencomm Page 169  Register 68 to 69"
  ::= { gencommP169Entry 36 }

gencommP169Reg-70-71 OBJECT-TYPE
  SYNTAX  Unsigned32
  MAX-ACCESS  read-only
  STATUS  current
  DESCRIPTION "Gencomm Page 169  Register 70 to 71"
  ::= { gencommP169Entry 37 }

gencommP169Reg-72-73 OBJECT-TYPE
  SYNTAX  Unsigned32
  MAX-ACCESS  read-only
  STATUS  current
  DESCRIPTION "Gencomm Page 169  Register 72 to 73"
  ::= { gencommP169Entry 38 }

gencommP169Reg-74-75 OBJECT-TYPE
  SYNTAX  Unsigned32
  MAX-ACCESS  read-only
  STATUS  current
  DESCRIPTION "Gencomm Page 169  Register 74 to 75"
  ::= { gencommP169Entry 39 }

gencommP169Reg-76-77 OBJECT-TYPE
  SYNTAX  Unsigned32
  MAX-ACCESS  read-only
  STATUS  current
  DESCRIPTION "Gencomm Page 169  Register 76 to 77"
  ::= { gencommP169Entry 40 }

gencommP169Reg-78-79 OBJECT-TYPE
  SYNTAX  Unsigned32
  MAX-ACCESS  read-only
  STATUS  current
  DESCRIPTION "Gencomm Page 169  Register 78 to 79"
  ::= { gencommP169Entry 41 }

gencommP169Reg-80-81 OBJECT-TYPE
  SYNTAX  Unsigned32
  MAX-ACCESS  read-only
  STATUS  current
  DESCRIPTION "Gencomm Page 169  Register 80 to 81"
  ::= { gencommP169Entry 42 }

gencommP169Reg-82-83 OBJECT-TYPE
  SYNTAX  Unsigned32
  MAX-ACCESS  read-only
  STATUS  current
  DESCRIPTION "Gencomm Page 169  Register 82 to 83"
  ::= { gencommP169Entry 43 }

gencommP169Reg-84-85 OBJECT-TYPE
  SYNTAX  Unsigned32
  MAX-ACCESS  read-only
  STATUS  current
  DESCRIPTION "Gencomm Page 169  Register 84 to 85"
  ::= { gencommP169Entry 44 }

gencommP169Reg-86-87 OBJECT-TYPE
  SYNTAX  Unsigned32
  MAX-ACCESS  read-only
  STATUS  current
  DESCRIPTION "Gencomm Page 169  Register 86 to 87"
  ::= { gencommP169Entry 45 }

gencommP169Reg-88-89 OBJECT-TYPE
  SYNTAX  Unsigned32
  MAX-ACCESS  read-only
  STATUS  current
  DESCRIPTION "Gencomm Page 169  Register 88 to 89"
  ::= { gencommP169Entry 46 }

gencommP169Reg-90-91 OBJECT-TYPE
  SYNTAX  Unsigned32
  MAX-ACCESS  read-only
  STATUS  current
  DESCRIPTION "Gencomm Page 169  Register 90 to 91"
  ::= { gencommP169Entry 47 }

gencommP169Reg-92-93 OBJECT-TYPE
  SYNTAX  Unsigned32
  MAX-ACCESS  read-only
  STATUS  current
  DESCRIPTION "Gencomm Page 169  Register 92 to 93"
  ::= { gencommP169Entry 48 }

gencommP169Reg-94-95 OBJECT-TYPE
  SYNTAX  Unsigned32
  MAX-ACCESS  read-only
  STATUS  current
  DESCRIPTION "Gencomm Page 169  Register 94 to 95"
  ::= { gencommP169Entry 49 }

gencommP169Reg-96-97 OBJECT-TYPE
  SYNTAX  Unsigned32
  MAX-ACCESS  read-only
  STATUS  current
  DESCRIPTION "Gencomm Page 169  Register 96 to 97"
  ::= { gencommP169Entry 50 }

gencommP169Reg-98-99 OBJECT-TYPE
  SYNTAX  Unsigned32
  MAX-ACCESS  read-only
  STATUS  current
  DESCRIPTION "Gencomm Page 169  Register 98 to 99"
  ::= { gencommP169Entry 51 }

gencommP169Reg-100-101 OBJECT-TYPE
  SYNTAX  Unsigned32
  MAX-ACCESS  read-only
  STATUS  current
  DESCRIPTION "Gencomm Page 169  Register 100 to 101"
  ::= { gencommP169Entry 52 }

gencommP169Reg-102-103 OBJECT-TYPE
  SYNTAX  Unsigned32
  MAX-ACCESS  read-only
  STATUS  current
  DESCRIPTION "Gencomm Page 169  Register 102 to 103"
  ::= { gencommP169Entry 53 }

gencommP169Reg-104-105 OBJECT-TYPE
  SYNTAX  Unsigned32
  MAX-ACCESS  read-only
  STATUS  current
  DESCRIPTION "Gencomm Page 169  Register 104 to 105"
  ::= { gencommP169Entry 54 }

gencommP169Reg-106-107 OBJECT-TYPE
  SYNTAX  Unsigned32
  MAX-ACCESS  read-only
  STATUS  current
  DESCRIPTION "Gencomm Page 169  Register 106 to 107"
  ::= { gencommP169Entry 55 }

gencommP169Reg-108-109 OBJECT-TYPE
  SYNTAX  Unsigned32
  MAX-ACCESS  read-only
  STATUS  current
  DESCRIPTION "Gencomm Page 169  Register 108 to 109"
  ::= { gencommP169Entry 56 }

gencommP169Reg-110-111 OBJECT-TYPE
  SYNTAX  Unsigned32
  MAX-ACCESS  read-only
  STATUS  current
  DESCRIPTION "Gencomm Page 169  Register 110 to 111"
  ::= { gencommP169Entry 57 }

gencommP169Reg-112-113 OBJECT-TYPE
  SYNTAX  Unsigned32
  MAX-ACCESS  read-only
  STATUS  current
  DESCRIPTION "Gencomm Page 169  Register 112 to 113"
  ::= { gencommP169Entry 58 }

gencommP169Reg-114-115 OBJECT-TYPE
  SYNTAX  Unsigned32
  MAX-ACCESS  read-only
  STATUS  current
  DESCRIPTION "Gencomm Page 169  Register 114 to 115"
  ::= { gencommP169Entry 59 }

gencommP169Reg-116-117 OBJECT-TYPE
  SYNTAX  Unsigned32
  MAX-ACCESS  read-only
  STATUS  current
  DESCRIPTION "Gencomm Page 169  Register 116 to 117"
  ::= { gencommP169Entry 60 }

gencommP169Reg-118-119 OBJECT-TYPE
  SYNTAX  Unsigned32
  MAX-ACCESS  read-only
  STATUS  current
  DESCRIPTION "Gencomm Page 169  Register 118 to 119"
  ::= { gencommP169Entry 61 }

gencommP169Reg-120-121 OBJECT-TYPE
  SYNTAX  Unsigned32
  MAX-ACCESS  read-only
  STATUS  current
  DESCRIPTION "Gencomm Page 169  Register 120 to 121"
  ::= { gencommP169Entry 62 }

gencommP169Reg-122-123 OBJECT-TYPE
  SYNTAX  Unsigned32
  MAX-ACCESS  read-only
  STATUS  current
  DESCRIPTION "Gencomm Page 169  Register 122 to 123"
  ::= { gencommP169Entry 63 }

gencommP169Reg-124-125 OBJECT-TYPE
  SYNTAX  Unsigned32
  MAX-ACCESS  read-only
  STATUS  current
  DESCRIPTION "Gencomm Page 169  Register 124 to 125"
  ::= { gencommP169Entry 64 }

gencommP169Reg-126-127 OBJECT-TYPE
  SYNTAX  Unsigned32
  MAX-ACCESS  read-only
  STATUS  current
  DESCRIPTION "Gencomm Page 169  Register 126 to 127"
  ::= { gencommP169Entry 65 }

gencommP169Reg-128-129 OBJECT-TYPE
  SYNTAX  Unsigned32
  MAX-ACCESS  read-only
  STATUS  current
  DESCRIPTION "Gencomm Page 169  Register 128 to 129"
  ::= { gencommP169Entry 66 }

gencommP169Reg-130-131 OBJECT-TYPE
  SYNTAX  Unsigned32
  MAX-ACCESS  read-only
  STATUS  current
  DESCRIPTION "Gencomm Page 169  Register 130 to 131"
  ::= { gencommP169Entry 67 }

gencommP169Reg-132-133 OBJECT-TYPE
  SYNTAX  Unsigned32
  MAX-ACCESS  read-only
  STATUS  current
  DESCRIPTION "Gencomm Page 169  Register 132 to 133"
  ::= { gencommP169Entry 68 }

gencommP169Reg-134-135 OBJECT-TYPE
  SYNTAX  Unsigned32
  MAX-ACCESS  read-only
  STATUS  current
  DESCRIPTION "Gencomm Page 169  Register 134 to 135"
  ::= { gencommP169Entry 69 }

gencommP169Reg-136-137 OBJECT-TYPE
  SYNTAX  Unsigned32
  MAX-ACCESS  read-only
  STATUS  current
  DESCRIPTION "Gencomm Page 169  Register 136 to 137"
  ::= { gencommP169Entry 70 }

gencommP169Reg-138-139 OBJECT-TYPE
  SYNTAX  Unsigned32
  MAX-ACCESS  read-only
  STATUS  current
  DESCRIPTION "Gencomm Page 169  Register 138 to 139"
  ::= { gencommP169Entry 71 }

gencommP169Reg-140-141 OBJECT-TYPE
  SYNTAX  Unsigned32
  MAX-ACCESS  read-only
  STATUS  current
  DESCRIPTION "Gencomm Page 169  Register 140 to 141"
  ::= { gencommP169Entry 72 }

gencommP169Reg-142-143 OBJECT-TYPE
  SYNTAX  Unsigned32
  MAX-ACCESS  read-only
  STATUS  current
  DESCRIPTION "Gencomm Page 169  Register 142 to 143"
  ::= { gencommP169Entry 73 }

gencommP169Reg-144-145 OBJECT-TYPE
  SYNTAX  Unsigned32
  MAX-ACCESS  read-only
  STATUS  current
  DESCRIPTION "Gencomm Page 169  Register 144 to 145"
  ::= { gencommP169Entry 74 }

gencommP169Reg-146-147 OBJECT-TYPE
  SYNTAX  Unsigned32
  MAX-ACCESS  read-only
  STATUS  current
  DESCRIPTION "Gencomm Page 169  Register 146 to 147"
  ::= { gencommP169Entry 75 }

gencommP169Reg-148-149 OBJECT-TYPE
  SYNTAX  Unsigned32
  MAX-ACCESS  read-only
  STATUS  current
  DESCRIPTION "Gencomm Page 169  Register 148 to 149"
  ::= { gencommP169Entry 76 }

gencommP169Reg-150-151 OBJECT-TYPE
  SYNTAX  Unsigned32
  MAX-ACCESS  read-only
  STATUS  current
  DESCRIPTION "Gencomm Page 169  Register 150 to 154"
  ::= { gencommP169Entry 77 }

gencommP169Reg-152-153 OBJECT-TYPE
  SYNTAX  Unsigned32
  MAX-ACCESS  read-only
  STATUS  current
  DESCRIPTION "Gencomm Page 169  Register 152 to 153"
  ::= { gencommP169Entry 78 }

gencommP169Reg-154-155 OBJECT-TYPE
  SYNTAX  Unsigned32
  MAX-ACCESS  read-only
  STATUS  current
  DESCRIPTION "Gencomm Page 169  Register 154 to 155"
  ::= { gencommP169Entry 79 }

gencommP169Reg-156-157 OBJECT-TYPE
  SYNTAX  Unsigned32
  MAX-ACCESS  read-only
  STATUS  current
  DESCRIPTION "Gencomm Page 169  Register 156 to 157"
  ::= { gencommP169Entry 80 }

gencommP169Reg-158-159 OBJECT-TYPE
  SYNTAX  Unsigned32
  MAX-ACCESS  read-only
  STATUS  current
  DESCRIPTION "Gencomm Page 169  Register 158 to 159"
  ::= { gencommP169Entry 81 }

gencommP169Reg-160-161 OBJECT-TYPE
  SYNTAX  Unsigned32
  MAX-ACCESS  read-only
  STATUS  current
  DESCRIPTION "Gencomm Page 169  Register 160 to 161"
  ::= { gencommP169Entry 82 }

gencommP169Reg-162-163 OBJECT-TYPE
  SYNTAX  Unsigned32
  MAX-ACCESS  read-only
  STATUS  current
  DESCRIPTION "Gencomm Page 169  Register 162 to 163"
  ::= { gencommP169Entry 83 }

gencommP169Reg-164-165 OBJECT-TYPE
  SYNTAX  Unsigned32
  MAX-ACCESS  read-only
  STATUS  current
  DESCRIPTION "Gencomm Page 169  Register 164 to 165"
  ::= { gencommP169Entry 84 }

gencommP169Reg-166-167 OBJECT-TYPE
  SYNTAX  Unsigned32
  MAX-ACCESS  read-only
  STATUS  current
  DESCRIPTION "Gencomm Page 169  Register 166 to 167"
  ::= { gencommP169Entry 85 }

gencommP169Reg-168-169 OBJECT-TYPE
  SYNTAX  Unsigned32
  MAX-ACCESS  read-only
  STATUS  current
  DESCRIPTION "Gencomm Page 169  Register 168 to 169"
  ::= { gencommP169Entry 86 }

gencommP169Reg-170-171 OBJECT-TYPE
  SYNTAX  Unsigned32
  MAX-ACCESS  read-only
  STATUS  current
  DESCRIPTION "Gencomm Page 169  Register 170 to 171"
  ::= { gencommP169Entry 87 }

gencommP169Reg-172-173 OBJECT-TYPE
  SYNTAX  Unsigned32
  MAX-ACCESS  read-only
  STATUS  current
  DESCRIPTION "Gencomm Page 169  Register 172 to 173"
  ::= { gencommP169Entry 88 }

gencommP169Reg-174-175 OBJECT-TYPE
  SYNTAX  Unsigned32
  MAX-ACCESS  read-only
  STATUS  current
  DESCRIPTION "Gencomm Page 169  Register 174 to 175"
  ::= { gencommP169Entry 89 }

gencommP169Reg-176-177 OBJECT-TYPE
  SYNTAX  Unsigned32
  MAX-ACCESS  read-only
  STATUS  current
  DESCRIPTION "Gencomm Page 169  Register 176 to 177"
  ::= { gencommP169Entry 90 }

gencommP169Reg-178-179 OBJECT-TYPE
  SYNTAX  Unsigned32
  MAX-ACCESS  read-only
  STATUS  current
  DESCRIPTION "Gencomm Page 169  Register 178 to 179"
  ::= { gencommP169Entry 91 }

gencommP169Reg-180-181 OBJECT-TYPE
  SYNTAX  Unsigned32
  MAX-ACCESS  read-only
  STATUS  current
  DESCRIPTION "Gencomm Page 169  Register 180 to 181"
  ::= { gencommP169Entry 92 }

gencommP169Reg-182-183 OBJECT-TYPE
  SYNTAX  Unsigned32
  MAX-ACCESS  read-only
  STATUS  current
  DESCRIPTION "Gencomm Page 169  Register 182 to 183"
  ::= { gencommP169Entry 93 }

gencommP169Reg-184-185 OBJECT-TYPE
  SYNTAX  Unsigned32
  MAX-ACCESS  read-only
  STATUS  current
  DESCRIPTION "Gencomm Page 169  Register 184 to 185"
  ::= { gencommP169Entry 94 }

gencommP169Reg-186-187 OBJECT-TYPE
  SYNTAX  Unsigned32
  MAX-ACCESS  read-only
  STATUS  current
  DESCRIPTION "Gencomm Page 169  Register 186 to 187"
  ::= { gencommP169Entry 95 }

gencommP169Reg-188-189 OBJECT-TYPE
  SYNTAX  Unsigned32
  MAX-ACCESS  read-only
  STATUS  current
  DESCRIPTION "Gencomm Page 169  Register 188 to 189"
  ::= { gencommP169Entry 96 }

gencommP169Reg-190-191 OBJECT-TYPE
  SYNTAX  Unsigned32
  MAX-ACCESS  read-only
  STATUS  current
  DESCRIPTION "Gencomm Page 169  Register 190 to 194"
  ::= { gencommP169Entry 97 }

gencommP169Reg-192-193 OBJECT-TYPE
  SYNTAX  Unsigned32
  MAX-ACCESS  read-only
  STATUS  current
  DESCRIPTION "Gencomm Page 169  Register 192 to 193"
  ::= { gencommP169Entry 98 }

gencommP169Reg-194-195 OBJECT-TYPE
  SYNTAX  Unsigned32
  MAX-ACCESS  read-only
  STATUS  current
  DESCRIPTION "Gencomm Page 169  Register 194 to 195"
  ::= { gencommP169Entry 99 }

gencommP169Reg-196-197 OBJECT-TYPE
  SYNTAX  Unsigned32
  MAX-ACCESS  read-only
  STATUS  current
  DESCRIPTION "Gencomm Page 169  Register 196 to 197"
  ::= { gencommP169Entry 100 }

gencommP169Reg-198-199 OBJECT-TYPE
  SYNTAX  Unsigned32
  MAX-ACCESS  read-only
  STATUS  current
  DESCRIPTION "Gencomm Page 169  Register 198 to 199"
  ::= { gencommP169Entry 101 }

gencommP169Reg-200-201 OBJECT-TYPE
  SYNTAX  Unsigned32
  MAX-ACCESS  read-only
  STATUS  current
  DESCRIPTION "Gencomm Page 169  Register 200 to 201"
  ::= { gencommP169Entry 102 }

gencommP169Reg-202-203 OBJECT-TYPE
  SYNTAX  Unsigned32
  MAX-ACCESS  read-only
  STATUS  current
  DESCRIPTION "Gencomm Page 169  Register 202 to 203"
  ::= { gencommP169Entry 103 }

gencommP169Reg-204-205 OBJECT-TYPE
  SYNTAX  Unsigned32
  MAX-ACCESS  read-only
  STATUS  current
  DESCRIPTION "Gencomm Page 169  Register 204 to 205"
  ::= { gencommP169Entry 104 }

gencommP169Reg-206-207 OBJECT-TYPE
  SYNTAX  Unsigned32
  MAX-ACCESS  read-only
  STATUS  current
  DESCRIPTION "Gencomm Page 169  Register 206 to 207"
  ::= { gencommP169Entry 105 }

gencommP169Reg-208-209 OBJECT-TYPE
  SYNTAX  Unsigned32
  MAX-ACCESS  read-only
  STATUS  current
  DESCRIPTION "Gencomm Page 169  Register 208 to 209"
  ::= { gencommP169Entry 106 }

gencommP169Reg-210-211 OBJECT-TYPE
  SYNTAX  Unsigned32
  MAX-ACCESS  read-only
  STATUS  current
  DESCRIPTION "Gencomm Page 169  Register 210 to 211"
  ::= { gencommP169Entry 107 }

gencommP169Reg-212-213 OBJECT-TYPE
  SYNTAX  Unsigned32
  MAX-ACCESS  read-only
  STATUS  current
  DESCRIPTION "Gencomm Page 169  Register 212 to 213"
  ::= { gencommP169Entry 108 }

gencommP169Reg-214-215 OBJECT-TYPE
  SYNTAX  Unsigned32
  MAX-ACCESS  read-only
  STATUS  current
  DESCRIPTION "Gencomm Page 169  Register 214 to 215"
  ::= { gencommP169Entry 109 }

gencommP169Reg-216-217 OBJECT-TYPE
  SYNTAX  Unsigned32
  MAX-ACCESS  read-only
  STATUS  current
  DESCRIPTION "Gencomm Page 169  Register 216 to 217"
  ::= { gencommP169Entry 110 }

gencommP169Reg-218-219 OBJECT-TYPE
  SYNTAX  Unsigned32
  MAX-ACCESS  read-only
  STATUS  current
  DESCRIPTION "Gencomm Page 169  Register 218 to 219"
  ::= { gencommP169Entry 111 }

gencommP169Reg-220-221 OBJECT-TYPE
  SYNTAX  Unsigned32
  MAX-ACCESS  read-only
  STATUS  current
  DESCRIPTION "Gencomm Page 169  Register 220 to 221"
  ::= { gencommP169Entry 112 }

gencommP169Reg-222-223 OBJECT-TYPE
  SYNTAX  Unsigned32
  MAX-ACCESS  read-only
  STATUS  current
  DESCRIPTION "Gencomm Page 169  Register 222 to 223"
  ::= { gencommP169Entry 113 }

gencommP169Reg-224-225 OBJECT-TYPE
  SYNTAX  Unsigned32
  MAX-ACCESS  read-only
  STATUS  current
  DESCRIPTION "Gencomm Page 169  Register 224 to 225"
  ::= { gencommP169Entry 114 }

gencommP169Reg-226-227 OBJECT-TYPE
  SYNTAX  Unsigned32
  MAX-ACCESS  read-only
  STATUS  current
  DESCRIPTION "Gencomm Page 169  Register 226 to 227"
  ::= { gencommP169Entry 115 }

gencommP169Reg-228-229 OBJECT-TYPE
  SYNTAX  Unsigned32
  MAX-ACCESS  read-only
  STATUS  current
  DESCRIPTION "Gencomm Page 169  Register 228 to 229"
  ::= { gencommP169Entry 116 }

gencommP169Reg-230-231 OBJECT-TYPE
  SYNTAX  Unsigned32
  MAX-ACCESS  read-only
  STATUS  current
  DESCRIPTION "Gencomm Page 169  Register 230 to 231"
  ::= { gencommP169Entry 117 }

gencommP169Reg-232-233 OBJECT-TYPE
  SYNTAX  Unsigned32
  MAX-ACCESS  read-only
  STATUS  current
  DESCRIPTION "Gencomm Page 169  Register 232 to 233"
  ::= { gencommP169Entry 118 }

gencommP169Reg-234-235 OBJECT-TYPE
  SYNTAX  Unsigned32
  MAX-ACCESS  read-only
  STATUS  current
  DESCRIPTION "Gencomm Page 169  Register 234 to 235"
  ::= { gencommP169Entry 119 }

gencommP169Reg-236-237 OBJECT-TYPE
  SYNTAX  Unsigned32
  MAX-ACCESS  read-only
  STATUS  current
  DESCRIPTION "Gencomm Page 169  Register 236 to 237"
  ::= { gencommP169Entry 120 }

gencommP169Reg-238-239 OBJECT-TYPE
  SYNTAX  Unsigned32
  MAX-ACCESS  read-only
  STATUS  current
  DESCRIPTION "Gencomm Page 169  Register 238 to 239"
  ::= { gencommP169Entry 121 }

gencommP169Reg-240-241 OBJECT-TYPE
  SYNTAX  Unsigned32
  MAX-ACCESS  read-only
  STATUS  current
  DESCRIPTION "Gencomm Page 169  Register 240 to 241"
  ::= { gencommP169Entry 122 }

gencommP169Reg-242-243 OBJECT-TYPE
  SYNTAX  Unsigned32
  MAX-ACCESS  read-only
  STATUS  current
  DESCRIPTION "Gencomm Page 169  Register 242 to 243"
  ::= { gencommP169Entry 123 }

gencommP169Reg-244-245 OBJECT-TYPE
  SYNTAX  Unsigned32
  MAX-ACCESS  read-only
  STATUS  current
  DESCRIPTION "Gencomm Page 169  Register 244 to 245"
  ::= { gencommP169Entry 124 }

gencommP169Reg-246-247 OBJECT-TYPE
  SYNTAX  Unsigned32
  MAX-ACCESS  read-only
  STATUS  current
  DESCRIPTION "Gencomm Page 169  Register 246 to 247"
  ::= { gencommP169Entry 125 }

gencommP169Reg-248-249 OBJECT-TYPE
  SYNTAX  Unsigned32
  MAX-ACCESS  read-only
  STATUS  current
  DESCRIPTION "Gencomm Page 169  Register 248 to 249"
  ::= { gencommP169Entry 126 }

gencommP169Reg-250-251 OBJECT-TYPE
  SYNTAX  Unsigned32
  MAX-ACCESS  read-only
  STATUS  current
  DESCRIPTION "Gencomm Page 169  Register 250 to 251"
  ::= { gencommP169Entry 127 }

gencommP169Reg-252-253 OBJECT-TYPE
  SYNTAX  Unsigned32
  MAX-ACCESS  read-only
  STATUS  current
  DESCRIPTION "Gencomm Page 169  Register 252 to 253"
  ::= { gencommP169Entry 128 }

gencommP169Reg-254-255 OBJECT-TYPE
  SYNTAX  Unsigned32
  MAX-ACCESS  read-only
  STATUS  current
  DESCRIPTION "Gencomm Page 169  Register 254 to 255"
  ::= { gencommP169Entry 129 }

-- *****************************************************  INIT OF TRAP DEFINITION  *****************************************************

ucdTraps OBJECT IDENTIFIER ::= { dseProduct 0 }

unnamedAlarmDigitalInputA                     NOTIFICATION-TYPE
                OBJECTS { dse8610SeqNr, dse8610TrapID, dse8610TrapState, dse8610TrapTimeStamp }
                STATUS current
                DESCRIPTION
                                "Digital Input A"
                ::= { ucdTraps 8192 }

unnamedAlarmDigitalInputB                     NOTIFICATION-TYPE
                OBJECTS { dse8610SeqNr, dse8610TrapID, dse8610TrapState, dse8610TrapTimeStamp }
                STATUS current
                DESCRIPTION
                                "Digital Input B"
                ::= { ucdTraps 8193 }

unnamedAlarmDigitalInputC                     NOTIFICATION-TYPE
                OBJECTS { dse8610SeqNr, dse8610TrapID, dse8610TrapState, dse8610TrapTimeStamp }
                STATUS current
                DESCRIPTION
                                "Digital Input C"
                ::= { ucdTraps 8194 }

unnamedAlarmDigitalInputD                     NOTIFICATION-TYPE
                OBJECTS { dse8610SeqNr, dse8610TrapID, dse8610TrapState, dse8610TrapTimeStamp }
                STATUS current
                DESCRIPTION
                                "Digital Input D"
                ::= { ucdTraps 8195 }

unnamedAlarmDigitalInputE                     NOTIFICATION-TYPE
                OBJECTS { dse8610SeqNr, dse8610TrapID, dse8610TrapState, dse8610TrapTimeStamp }
                STATUS current
                DESCRIPTION
                                "Digital Input E"
                ::= { ucdTraps 8196 }

unnamedAlarmDigitalInputF                     NOTIFICATION-TYPE
                OBJECTS { dse8610SeqNr, dse8610TrapID, dse8610TrapState, dse8610TrapTimeStamp }
                STATUS current
                DESCRIPTION
                                "Digital Input F"
                ::= { ucdTraps 8197 }

unnamedAlarmDigitalInputG                     NOTIFICATION-TYPE
                OBJECTS { dse8610SeqNr, dse8610TrapID, dse8610TrapState, dse8610TrapTimeStamp }
                STATUS current
                DESCRIPTION
                                "Digital Input G"
                ::= { ucdTraps 8198 }

unnamedAlarmDigitalInputH                     NOTIFICATION-TYPE
                OBJECTS { dse8610SeqNr, dse8610TrapID, dse8610TrapState, dse8610TrapTimeStamp }
                STATUS current
                DESCRIPTION
                                "Digital Input H"
                ::= { ucdTraps 8199 }

unnamedAlarmDigitalInputI                     NOTIFICATION-TYPE
                OBJECTS { dse8610SeqNr, dse8610TrapID, dse8610TrapState, dse8610TrapTimeStamp }
                STATUS current
                DESCRIPTION
                                "Digital Input I"
                ::= { ucdTraps 8200 }

unnamedAlarmDigitalInputJ                     NOTIFICATION-TYPE
                OBJECTS { dse8610SeqNr, dse8610TrapID, dse8610TrapState, dse8610TrapTimeStamp }
                STATUS current
                DESCRIPTION
                                "Digital Input J"
                ::= { ucdTraps 8201 }

unnamedAlarmDigitalInputK                     NOTIFICATION-TYPE
                OBJECTS { dse8610SeqNr, dse8610TrapID, dse8610TrapState, dse8610TrapTimeStamp }
                STATUS current
                DESCRIPTION
                                "Digital Input K"
                ::= { ucdTraps 8202 }

unnamedAlarmDigitalInputL                     NOTIFICATION-TYPE
                OBJECTS { dse8610SeqNr, dse8610TrapID, dse8610TrapState, dse8610TrapTimeStamp }
                STATUS current
                DESCRIPTION
                                "Digital Input L"
                ::= { ucdTraps 8203 }

unnamedAlarmAnalogueInputBDigital                     NOTIFICATION-TYPE
                OBJECTS { dse8610SeqNr, dse8610TrapID, dse8610TrapState, dse8610TrapTimeStamp }
                STATUS current
                DESCRIPTION
                                "Analogue Input B Digital"
                ::= { ucdTraps 8208 }

unnamedAlarmAnalogueInputCDigital                     NOTIFICATION-TYPE
                OBJECTS { dse8610SeqNr, dse8610TrapID, dse8610TrapState, dse8610TrapTimeStamp }
                STATUS current
                DESCRIPTION
                                "Analogue Input C Digital"
                ::= { ucdTraps 8209 }

unnamedAlarmAnalogueInputDDigital                     NOTIFICATION-TYPE
                OBJECTS { dse8610SeqNr, dse8610TrapID, dse8610TrapState, dse8610TrapTimeStamp }
                STATUS current
                DESCRIPTION
                                "Analogue Input D Digital"
                ::= { ucdTraps 8210 }

unnamedAlarm2130ExpansionModuleID0DigitalInputA                     NOTIFICATION-TYPE
                OBJECTS { dse8610SeqNr, dse8610TrapID, dse8610TrapState, dse8610TrapTimeStamp }
                STATUS current
                DESCRIPTION
                                "2130 Expansion Module ID0 Digital Input A"
                ::= { ucdTraps 8224 }

unnamedAlarm2130ExpansionModuleID0DigitalInputB                     NOTIFICATION-TYPE
                OBJECTS { dse8610SeqNr, dse8610TrapID, dse8610TrapState, dse8610TrapTimeStamp }
                STATUS current
                DESCRIPTION
                                "2130 Expansion Module ID0 Digital Input B"
                ::= { ucdTraps 8225 }

unnamedAlarm2130ExpansionModuleID0DigitalInputC                     NOTIFICATION-TYPE
                OBJECTS { dse8610SeqNr, dse8610TrapID, dse8610TrapState, dse8610TrapTimeStamp }
                STATUS current
                DESCRIPTION
                                "2130 Expansion Module ID0 Digital Input C"
                ::= { ucdTraps 8226 }

unnamedAlarm2130ExpansionModuleID0DigitalInputD                     NOTIFICATION-TYPE
                OBJECTS { dse8610SeqNr, dse8610TrapID, dse8610TrapState, dse8610TrapTimeStamp }
                STATUS current
                DESCRIPTION
                                "2130 Expansion Module ID0 Digital Input D"
                ::= { ucdTraps 8227 }

unnamedAlarm2130ExpansionModuleID0DigitalInputE                     NOTIFICATION-TYPE
                OBJECTS { dse8610SeqNr, dse8610TrapID, dse8610TrapState, dse8610TrapTimeStamp }
                STATUS current
                DESCRIPTION
                                "2130 Expansion Module ID0 Digital Input E"
                ::= { ucdTraps 8228 }

unnamedAlarm2130ExpansionModuleID0DigitalInputF                     NOTIFICATION-TYPE
                OBJECTS { dse8610SeqNr, dse8610TrapID, dse8610TrapState, dse8610TrapTimeStamp }
                STATUS current
                DESCRIPTION
                                "2130 Expansion Module ID0 Digital Input F"
                ::= { ucdTraps 8229 }

unnamedAlarm2130ExpansionModuleID0DigitalInputG                     NOTIFICATION-TYPE
                OBJECTS { dse8610SeqNr, dse8610TrapID, dse8610TrapState, dse8610TrapTimeStamp }
                STATUS current
                DESCRIPTION
                                "2130 Expansion Module ID0 Digital Input G"
                ::= { ucdTraps 8230 }

unnamedAlarm2130ExpansionModuleID0DigitalInputH                     NOTIFICATION-TYPE
                OBJECTS { dse8610SeqNr, dse8610TrapID, dse8610TrapState, dse8610TrapTimeStamp }
                STATUS current
                DESCRIPTION
                                "2130 Expansion Module ID0 Digital Input H"
                ::= { ucdTraps 8231 }

unnamedAlarm2130ExpansionModuleID1DigitalInputA                     NOTIFICATION-TYPE
                OBJECTS { dse8610SeqNr, dse8610TrapID, dse8610TrapState, dse8610TrapTimeStamp }
                STATUS current
                DESCRIPTION
                                "2130 Expansion Module ID1 Digital Input A"
                ::= { ucdTraps 8232 }

unnamedAlarm2130ExpansionModuleID1DigitalInputB                     NOTIFICATION-TYPE
                OBJECTS { dse8610SeqNr, dse8610TrapID, dse8610TrapState, dse8610TrapTimeStamp }
                STATUS current
                DESCRIPTION
                                "2130 Expansion Module ID1 Digital Input B"
                ::= { ucdTraps 8233 }

unnamedAlarm2130ExpansionModuleID1DigitalInputC                     NOTIFICATION-TYPE
                OBJECTS { dse8610SeqNr, dse8610TrapID, dse8610TrapState, dse8610TrapTimeStamp }
                STATUS current
                DESCRIPTION
                                "2130 Expansion Module ID1 Digital Input C"
                ::= { ucdTraps 8234 }

unnamedAlarm2130ExpansionModuleID1DigitalInputD                     NOTIFICATION-TYPE
                OBJECTS { dse8610SeqNr, dse8610TrapID, dse8610TrapState, dse8610TrapTimeStamp }
                STATUS current
                DESCRIPTION
                                "2130 Expansion Module ID1 Digital Input D"
                ::= { ucdTraps 8235 }

unnamedAlarm2130ExpansionModuleID1DigitalInputE                     NOTIFICATION-TYPE
                OBJECTS { dse8610SeqNr, dse8610TrapID, dse8610TrapState, dse8610TrapTimeStamp }
                STATUS current
                DESCRIPTION
                                "2130 Expansion Module ID1 Digital Input E"
                ::= { ucdTraps 8236 }

unnamedAlarm2130ExpansionModuleID1DigitalInputF                     NOTIFICATION-TYPE
                OBJECTS { dse8610SeqNr, dse8610TrapID, dse8610TrapState, dse8610TrapTimeStamp }
                STATUS current
                DESCRIPTION
                                "2130 Expansion Module ID1 Digital Input F"
                ::= { ucdTraps 8237 }

unnamedAlarm2130ExpansionModuleID1DigitalInputG                     NOTIFICATION-TYPE
                OBJECTS { dse8610SeqNr, dse8610TrapID, dse8610TrapState, dse8610TrapTimeStamp }
                STATUS current
                DESCRIPTION
                                "2130 Expansion Module ID1 Digital Input G"
                ::= { ucdTraps 8238 }

unnamedAlarm2130ExpansionModuleID1DigitalInputH                     NOTIFICATION-TYPE
                OBJECTS { dse8610SeqNr, dse8610TrapID, dse8610TrapState, dse8610TrapTimeStamp }
                STATUS current
                DESCRIPTION
                                "2130 Expansion Module ID1 Digital Input H"
                ::= { ucdTraps 8239 }

unnamedAlarm2130ExpansionModuleID2DigitalInputA                     NOTIFICATION-TYPE
                OBJECTS { dse8610SeqNr, dse8610TrapID, dse8610TrapState, dse8610TrapTimeStamp }
                STATUS current
                DESCRIPTION
                                "2130 Expansion Module ID2 Digital Input A"
                ::= { ucdTraps 8240 }

unnamedAlarm2130ExpansionModuleID2DigitalInputB                     NOTIFICATION-TYPE
                OBJECTS { dse8610SeqNr, dse8610TrapID, dse8610TrapState, dse8610TrapTimeStamp }
                STATUS current
                DESCRIPTION
                                "2130 Expansion Module ID2 Digital Input B"
                ::= { ucdTraps 8241 }

unnamedAlarm2130ExpansionModuleID2DigitalInputC                     NOTIFICATION-TYPE
                OBJECTS { dse8610SeqNr, dse8610TrapID, dse8610TrapState, dse8610TrapTimeStamp }
                STATUS current
                DESCRIPTION
                                "2130 Expansion Module ID2 Digital Input C"
                ::= { ucdTraps 8242 }

unnamedAlarm2130ExpansionModuleID2DigitalInputD                     NOTIFICATION-TYPE
                OBJECTS { dse8610SeqNr, dse8610TrapID, dse8610TrapState, dse8610TrapTimeStamp }
                STATUS current
                DESCRIPTION
                                "2130 Expansion Module ID2 Digital Input D"
                ::= { ucdTraps 8243 }

unnamedAlarm2130ExpansionModuleID2DigitalInputE                     NOTIFICATION-TYPE
                OBJECTS { dse8610SeqNr, dse8610TrapID, dse8610TrapState, dse8610TrapTimeStamp }
                STATUS current
                DESCRIPTION
                                "2130 Expansion Module ID2 Digital Input E"
                ::= { ucdTraps 8244 }

unnamedAlarm2130ExpansionModuleID2DigitalInputF                     NOTIFICATION-TYPE
                OBJECTS { dse8610SeqNr, dse8610TrapID, dse8610TrapState, dse8610TrapTimeStamp }
                STATUS current
                DESCRIPTION
                                "2130 Expansion Module ID2 Digital Input F"
                ::= { ucdTraps 8245 }

unnamedAlarm2130ExpansionModuleID2DigitalInputG                     NOTIFICATION-TYPE
                OBJECTS { dse8610SeqNr, dse8610TrapID, dse8610TrapState, dse8610TrapTimeStamp }
                STATUS current
                DESCRIPTION
                                "2130 Expansion Module ID2 Digital Input G"
                ::= { ucdTraps 8246 }

unnamedAlarm2130ExpansionModuleID2DigitalInputH                     NOTIFICATION-TYPE
                OBJECTS { dse8610SeqNr, dse8610TrapID, dse8610TrapState, dse8610TrapTimeStamp }
                STATUS current
                DESCRIPTION
                                "2130 Expansion Module ID2 Digital Input H"
                ::= { ucdTraps 8247 }

unnamedAlarm2130ExpansionModuleID3DigitalInputA                     NOTIFICATION-TYPE
                OBJECTS { dse8610SeqNr, dse8610TrapID, dse8610TrapState, dse8610TrapTimeStamp }
                STATUS current
                DESCRIPTION
                                "2130 Expansion Module ID3 Digital Input A"
                ::= { ucdTraps 8248 }

unnamedAlarm2130ExpansionModuleID3DigitalInputB                     NOTIFICATION-TYPE
                OBJECTS { dse8610SeqNr, dse8610TrapID, dse8610TrapState, dse8610TrapTimeStamp }
                STATUS current
                DESCRIPTION
                                "2130 Expansion Module ID3 Digital Input B"
                ::= { ucdTraps 8249 }

unnamedAlarm2130ExpansionModuleID3DigitalInputC                     NOTIFICATION-TYPE
                OBJECTS { dse8610SeqNr, dse8610TrapID, dse8610TrapState, dse8610TrapTimeStamp }
                STATUS current
                DESCRIPTION
                                "2130 Expansion Module ID3 Digital Input C"
                ::= { ucdTraps 8250 }

unnamedAlarm2130ExpansionModuleID3DigitalInputD                     NOTIFICATION-TYPE
                OBJECTS { dse8610SeqNr, dse8610TrapID, dse8610TrapState, dse8610TrapTimeStamp }
                STATUS current
                DESCRIPTION
                                "2130 Expansion Module ID3 Digital Input D"
                ::= { ucdTraps 8251 }

unnamedAlarm2130ExpansionModuleID3DigitalInputE                     NOTIFICATION-TYPE
                OBJECTS { dse8610SeqNr, dse8610TrapID, dse8610TrapState, dse8610TrapTimeStamp }
                STATUS current
                DESCRIPTION
                                "2130 Expansion Module ID3 Digital Input E"
                ::= { ucdTraps 8252 }

unnamedAlarm2130ExpansionModuleID3DigitalInputF                     NOTIFICATION-TYPE
                OBJECTS { dse8610SeqNr, dse8610TrapID, dse8610TrapState, dse8610TrapTimeStamp }
                STATUS current
                DESCRIPTION
                                "2130 Expansion Module ID3 Digital Input F"
                ::= { ucdTraps 8253 }

unnamedAlarm2130ExpansionModuleID3DigitalInputG                     NOTIFICATION-TYPE
                OBJECTS { dse8610SeqNr, dse8610TrapID, dse8610TrapState, dse8610TrapTimeStamp }
                STATUS current
                DESCRIPTION
                                "2130 Expansion Module ID3 Digital Input G"
                ::= { ucdTraps 8254 }

unnamedAlarm2130ExpansionModuleID3DigitalInputH                     NOTIFICATION-TYPE
                OBJECTS { dse8610SeqNr, dse8610TrapID, dse8610TrapState, dse8610TrapTimeStamp }
                STATUS current
                DESCRIPTION
                                "2130 Expansion Module ID3 Digital Input H"
                ::= { ucdTraps 8255 }

unnamedAlarm2131ExpansionModuleID0DigitalInputA                     NOTIFICATION-TYPE
                OBJECTS { dse8610SeqNr, dse8610TrapID, dse8610TrapState, dse8610TrapTimeStamp }
                STATUS current
                DESCRIPTION
                                "2131 Expansion Module ID0 Digital Input A"
                ::= { ucdTraps 8256 }

unnamedAlarm2131ExpansionModuleID0DigitalInputB                     NOTIFICATION-TYPE
                OBJECTS { dse8610SeqNr, dse8610TrapID, dse8610TrapState, dse8610TrapTimeStamp }
                STATUS current
                DESCRIPTION
                                "2131 Expansion Module ID0 Digital Input B"
                ::= { ucdTraps 8257 }

unnamedAlarm2131ExpansionModuleID0DigitalInputC                     NOTIFICATION-TYPE
                OBJECTS { dse8610SeqNr, dse8610TrapID, dse8610TrapState, dse8610TrapTimeStamp }
                STATUS current
                DESCRIPTION
                                "2131 Expansion Module ID0 Digital Input C"
                ::= { ucdTraps 8258 }

unnamedAlarm2131ExpansionModuleID0DigitalInputD                     NOTIFICATION-TYPE
                OBJECTS { dse8610SeqNr, dse8610TrapID, dse8610TrapState, dse8610TrapTimeStamp }
                STATUS current
                DESCRIPTION
                                "2131 Expansion Module ID0 Digital Input D"
                ::= { ucdTraps 8259 }

unnamedAlarm2131ExpansionModuleID0DigitalInputE                     NOTIFICATION-TYPE
                OBJECTS { dse8610SeqNr, dse8610TrapID, dse8610TrapState, dse8610TrapTimeStamp }
                STATUS current
                DESCRIPTION
                                "2131 Expansion Module ID0 Digital Input E"
                ::= { ucdTraps 8260 }

unnamedAlarm2131ExpansionModuleID0DigitalInputF                     NOTIFICATION-TYPE
                OBJECTS { dse8610SeqNr, dse8610TrapID, dse8610TrapState, dse8610TrapTimeStamp }
                STATUS current
                DESCRIPTION
                                "2131 Expansion Module ID0 Digital Input F"
                ::= { ucdTraps 8261 }

unnamedAlarm2131ExpansionModuleID0DigitalInputG                     NOTIFICATION-TYPE
                OBJECTS { dse8610SeqNr, dse8610TrapID, dse8610TrapState, dse8610TrapTimeStamp }
                STATUS current
                DESCRIPTION
                                "2131 Expansion Module ID0 Digital Input G"
                ::= { ucdTraps 8262 }

unnamedAlarm2131ExpansionModuleID0DigitalInputH                     NOTIFICATION-TYPE
                OBJECTS { dse8610SeqNr, dse8610TrapID, dse8610TrapState, dse8610TrapTimeStamp }
                STATUS current
                DESCRIPTION
                                "2131 Expansion Module ID0 Digital Input H"
                ::= { ucdTraps 8263 }

unnamedAlarm2131ExpansionModuleID0DigitalInputI                     NOTIFICATION-TYPE
                OBJECTS { dse8610SeqNr, dse8610TrapID, dse8610TrapState, dse8610TrapTimeStamp }
                STATUS current
                DESCRIPTION
                                "2131 Expansion Module ID0 Digital Input I"
                ::= { ucdTraps 8264 }

unnamedAlarm2131ExpansionModuleID0DigitalInputJ                     NOTIFICATION-TYPE
                OBJECTS { dse8610SeqNr, dse8610TrapID, dse8610TrapState, dse8610TrapTimeStamp }
                STATUS current
                DESCRIPTION
                                "2131 Expansion Module ID0 Digital Input J"
                ::= { ucdTraps 8265 }

unnamedAlarm2131ExpansionModuleID1DigitalInputA                     NOTIFICATION-TYPE
                OBJECTS { dse8610SeqNr, dse8610TrapID, dse8610TrapState, dse8610TrapTimeStamp }
                STATUS current
                DESCRIPTION
                                "2131 Expansion Module ID1 Digital Input A"
                ::= { ucdTraps 8266 }

unnamedAlarm2131ExpansionModuleID1DigitalInputB                     NOTIFICATION-TYPE
                OBJECTS { dse8610SeqNr, dse8610TrapID, dse8610TrapState, dse8610TrapTimeStamp }
                STATUS current
                DESCRIPTION
                                "2131 Expansion Module ID1 Digital Input B"
                ::= { ucdTraps 8267 }

unnamedAlarm2131ExpansionModuleID1DigitalInputC                     NOTIFICATION-TYPE
                OBJECTS { dse8610SeqNr, dse8610TrapID, dse8610TrapState, dse8610TrapTimeStamp }
                STATUS current
                DESCRIPTION
                                "2131 Expansion Module ID1 Digital Input C"
                ::= { ucdTraps 8268 }

unnamedAlarm2131ExpansionModuleID1DigitalInputD                     NOTIFICATION-TYPE
                OBJECTS { dse8610SeqNr, dse8610TrapID, dse8610TrapState, dse8610TrapTimeStamp }
                STATUS current
                DESCRIPTION
                                "2131 Expansion Module ID1 Digital Input D"
                ::= { ucdTraps 8269 }

unnamedAlarm2131ExpansionModuleID1DigitalInputE                     NOTIFICATION-TYPE
                OBJECTS { dse8610SeqNr, dse8610TrapID, dse8610TrapState, dse8610TrapTimeStamp }
                STATUS current
                DESCRIPTION
                                "2131 Expansion Module ID1 Digital Input E"
                ::= { ucdTraps 8270 }

unnamedAlarm2131ExpansionModuleID1DigitalInputF                     NOTIFICATION-TYPE
                OBJECTS { dse8610SeqNr, dse8610TrapID, dse8610TrapState, dse8610TrapTimeStamp }
                STATUS current
                DESCRIPTION
                                "2131 Expansion Module ID1 Digital Input F"
                ::= { ucdTraps 8271 }

unnamedAlarm2131ExpansionModuleID1DigitalInputG                     NOTIFICATION-TYPE
                OBJECTS { dse8610SeqNr, dse8610TrapID, dse8610TrapState, dse8610TrapTimeStamp }
                STATUS current
                DESCRIPTION
                                "2131 Expansion Module ID1 Digital Input G"
                ::= { ucdTraps 8272 }

unnamedAlarm2131ExpansionModuleID1DigitalInputH                     NOTIFICATION-TYPE
                OBJECTS { dse8610SeqNr, dse8610TrapID, dse8610TrapState, dse8610TrapTimeStamp }
                STATUS current
                DESCRIPTION
                                "2131 Expansion Module ID1 Digital Input H"
                ::= { ucdTraps 8273 }

unnamedAlarm2131ExpansionModuleID1DigitalInputI                     NOTIFICATION-TYPE
                OBJECTS { dse8610SeqNr, dse8610TrapID, dse8610TrapState, dse8610TrapTimeStamp }
                STATUS current
                DESCRIPTION
                                "2131 Expansion Module ID1 Digital Input I"
                ::= { ucdTraps 8274 }

unnamedAlarm2131ExpansionModuleID1DigitalInputJ                     NOTIFICATION-TYPE
                OBJECTS { dse8610SeqNr, dse8610TrapID, dse8610TrapState, dse8610TrapTimeStamp }
                STATUS current
                DESCRIPTION
                                "2131 Expansion Module ID1 Digital Input J"
                ::= { ucdTraps 8275 }

unnamedAlarm2131ExpansionModuleID2DigitalInputA                     NOTIFICATION-TYPE
                OBJECTS { dse8610SeqNr, dse8610TrapID, dse8610TrapState, dse8610TrapTimeStamp }
                STATUS current
                DESCRIPTION
                                "2131 Expansion Module ID2 Digital Input A"
                ::= { ucdTraps 8276 }

unnamedAlarm2131ExpansionModuleID2DigitalInputB                     NOTIFICATION-TYPE
                OBJECTS { dse8610SeqNr, dse8610TrapID, dse8610TrapState, dse8610TrapTimeStamp }
                STATUS current
                DESCRIPTION
                                "2131 Expansion Module ID2 Digital Input B"
                ::= { ucdTraps 8277 }

unnamedAlarm2131ExpansionModuleID2DigitalInputC                     NOTIFICATION-TYPE
                OBJECTS { dse8610SeqNr, dse8610TrapID, dse8610TrapState, dse8610TrapTimeStamp }
                STATUS current
                DESCRIPTION
                                "2131 Expansion Module ID2 Digital Input C"
                ::= { ucdTraps 8278 }

unnamedAlarm2131ExpansionModuleID2DigitalInputD                     NOTIFICATION-TYPE
                OBJECTS { dse8610SeqNr, dse8610TrapID, dse8610TrapState, dse8610TrapTimeStamp }
                STATUS current
                DESCRIPTION
                                "2131 Expansion Module ID2 Digital Input D"
                ::= { ucdTraps 8279 }

unnamedAlarm2131ExpansionModuleID2DigitalInputE                     NOTIFICATION-TYPE
                OBJECTS { dse8610SeqNr, dse8610TrapID, dse8610TrapState, dse8610TrapTimeStamp }
                STATUS current
                DESCRIPTION
                                "2131 Expansion Module ID2 Digital Input E"
                ::= { ucdTraps 8280 }

unnamedAlarm2131ExpansionModuleID2DigitalInputF                     NOTIFICATION-TYPE
                OBJECTS { dse8610SeqNr, dse8610TrapID, dse8610TrapState, dse8610TrapTimeStamp }
                STATUS current
                DESCRIPTION
                                "2131 Expansion Module ID2 Digital Input F"
                ::= { ucdTraps 8281 }

unnamedAlarm2131ExpansionModuleID2DigitalInputG                     NOTIFICATION-TYPE
                OBJECTS { dse8610SeqNr, dse8610TrapID, dse8610TrapState, dse8610TrapTimeStamp }
                STATUS current
                DESCRIPTION
                                "2131 Expansion Module ID2 Digital Input G"
                ::= { ucdTraps 8282 }

unnamedAlarm2131ExpansionModuleID2DigitalInputH                     NOTIFICATION-TYPE
                OBJECTS { dse8610SeqNr, dse8610TrapID, dse8610TrapState, dse8610TrapTimeStamp }
                STATUS current
                DESCRIPTION
                                "2131 Expansion Module ID2 Digital Input H"
                ::= { ucdTraps 8283 }

unnamedAlarm2131ExpansionModuleID2DigitalInputI                     NOTIFICATION-TYPE
                OBJECTS { dse8610SeqNr, dse8610TrapID, dse8610TrapState, dse8610TrapTimeStamp }
                STATUS current
                DESCRIPTION
                                "2131 Expansion Module ID2 Digital Input I"
                ::= { ucdTraps 8284 }

unnamedAlarm2131ExpansionModuleID2DigitalInputJ                     NOTIFICATION-TYPE
                OBJECTS { dse8610SeqNr, dse8610TrapID, dse8610TrapState, dse8610TrapTimeStamp }
                STATUS current
                DESCRIPTION
                                "2131 Expansion Module ID2 Digital Input J"
                ::= { ucdTraps 8285 }

unnamedAlarm2131ExpansionModuleID3DigitalInputA                     NOTIFICATION-TYPE
                OBJECTS { dse8610SeqNr, dse8610TrapID, dse8610TrapState, dse8610TrapTimeStamp }
                STATUS current
                DESCRIPTION
                                "2131 Expansion Module ID3 Digital Input A"
                ::= { ucdTraps 8286 }

unnamedAlarm2131ExpansionModuleID3DigitalInputB                     NOTIFICATION-TYPE
                OBJECTS { dse8610SeqNr, dse8610TrapID, dse8610TrapState, dse8610TrapTimeStamp }
                STATUS current
                DESCRIPTION
                                "2131 Expansion Module ID3 Digital Input B"
                ::= { ucdTraps 8287 }

unnamedAlarm2131ExpansionModuleID3DigitalInputC                     NOTIFICATION-TYPE
                OBJECTS { dse8610SeqNr, dse8610TrapID, dse8610TrapState, dse8610TrapTimeStamp }
                STATUS current
                DESCRIPTION
                                "2131 Expansion Module ID3 Digital Input C"
                ::= { ucdTraps 8288 }

unnamedAlarm2131ExpansionModuleID3DigitalInputD                     NOTIFICATION-TYPE
                OBJECTS { dse8610SeqNr, dse8610TrapID, dse8610TrapState, dse8610TrapTimeStamp }
                STATUS current
                DESCRIPTION
                                "2131 Expansion Module ID3 Digital Input D"
                ::= { ucdTraps 8289 }

unnamedAlarm2131ExpansionModuleID3DigitalInputE                     NOTIFICATION-TYPE
                OBJECTS { dse8610SeqNr, dse8610TrapID, dse8610TrapState, dse8610TrapTimeStamp }
                STATUS current
                DESCRIPTION
                                "2131 Expansion Module ID3 Digital Input E"
                ::= { ucdTraps 8290 }

unnamedAlarm2131ExpansionModuleID3DigitalInputF                     NOTIFICATION-TYPE
                OBJECTS { dse8610SeqNr, dse8610TrapID, dse8610TrapState, dse8610TrapTimeStamp }
                STATUS current
                DESCRIPTION
                                "2131 Expansion Module ID3 Digital Input F"
                ::= { ucdTraps 8291 }

unnamedAlarm2131ExpansionModuleID3DigitalInputG                     NOTIFICATION-TYPE
                OBJECTS { dse8610SeqNr, dse8610TrapID, dse8610TrapState, dse8610TrapTimeStamp }
                STATUS current
                DESCRIPTION
                                "2131 Expansion Module ID3 Digital Input G"
                ::= { ucdTraps 8292 }

unnamedAlarm2131ExpansionModuleID3DigitalInputH                     NOTIFICATION-TYPE
                OBJECTS { dse8610SeqNr, dse8610TrapID, dse8610TrapState, dse8610TrapTimeStamp }
                STATUS current
                DESCRIPTION
                                "2131 Expansion Module ID3 Digital Input H"
                ::= { ucdTraps 8293 }

unnamedAlarm2131ExpansionModuleID3DigitalInputI                     NOTIFICATION-TYPE
                OBJECTS { dse8610SeqNr, dse8610TrapID, dse8610TrapState, dse8610TrapTimeStamp }
                STATUS current
                DESCRIPTION
                                "2131 Expansion Module ID3 Digital Input I"
                ::= { ucdTraps 8294 }

unnamedAlarm2131ExpansionModuleID3DigitalInputJ                     NOTIFICATION-TYPE
                OBJECTS { dse8610SeqNr, dse8610TrapID, dse8610TrapState, dse8610TrapTimeStamp }
                STATUS current
                DESCRIPTION
                                "2131 Expansion Module ID3 Digital Input J"
                ::= { ucdTraps 8295 }

unnamedAlarm2130ExpansionModuleID0AnalogueInputELow                     NOTIFICATION-TYPE
                OBJECTS { dse8610SeqNr, dse8610TrapID, dse8610TrapState, dse8610TrapTimeStamp }
                STATUS current
                DESCRIPTION
                                "2130 Expansion Module ID0 Analogue Input E Low"
                ::= { ucdTraps 8304 }

unnamedAlarm2130ExpansionModuleID0AnalogueInputEHi                     NOTIFICATION-TYPE
                OBJECTS { dse8610SeqNr, dse8610TrapID, dse8610TrapState, dse8610TrapTimeStamp }
                STATUS current
                DESCRIPTION
                                "2130 Expansion Module ID0 Analogue Input E Hi"
                ::= { ucdTraps 8305 }

unnamedAlarm2130ExpansionModuleID0AnalogueInputFLow                     NOTIFICATION-TYPE
                OBJECTS { dse8610SeqNr, dse8610TrapID, dse8610TrapState, dse8610TrapTimeStamp }
                STATUS current
                DESCRIPTION
                                "2130 Expansion Module ID0 Analogue Input F Low"
                ::= { ucdTraps 8306 }

unnamedAlarm2130ExpansionModuleID0AnalogueInputFHi                     NOTIFICATION-TYPE
                OBJECTS { dse8610SeqNr, dse8610TrapID, dse8610TrapState, dse8610TrapTimeStamp }
                STATUS current
                DESCRIPTION
                                "2130 Expansion Module ID0 Analogue Input F Hi"
                ::= { ucdTraps 8307 }

unnamedAlarm2130ExpansionModuleID0AnalogueInputGLow                     NOTIFICATION-TYPE
                OBJECTS { dse8610SeqNr, dse8610TrapID, dse8610TrapState, dse8610TrapTimeStamp }
                STATUS current
                DESCRIPTION
                                "2130 Expansion Module ID0 Analogue Input G Low"
                ::= { ucdTraps 8308 }

unnamedAlarm2130ExpansionModuleID0AnalogueInputGHi                     NOTIFICATION-TYPE
                OBJECTS { dse8610SeqNr, dse8610TrapID, dse8610TrapState, dse8610TrapTimeStamp }
                STATUS current
                DESCRIPTION
                                "2130 Expansion Module ID0 Analogue Input G Hi"
                ::= { ucdTraps 8309 }

unnamedAlarm2130ExpansionModuleID0AnalogueInputHLow                     NOTIFICATION-TYPE
                OBJECTS { dse8610SeqNr, dse8610TrapID, dse8610TrapState, dse8610TrapTimeStamp }
                STATUS current
                DESCRIPTION
                                "2130 Expansion Module ID0 Analogue Input H Low"
                ::= { ucdTraps 8310 }

unnamedAlarm2130ExpansionModuleID0AnalogueInputHHi                     NOTIFICATION-TYPE
                OBJECTS { dse8610SeqNr, dse8610TrapID, dse8610TrapState, dse8610TrapTimeStamp }
                STATUS current
                DESCRIPTION
                                "2130 Expansion Module ID0 Analogue Input H Hi"
                ::= { ucdTraps 8311 }

unnamedAlarm2130ExpansionModuleID1AnalogueInputELow                     NOTIFICATION-TYPE
                OBJECTS { dse8610SeqNr, dse8610TrapID, dse8610TrapState, dse8610TrapTimeStamp }
                STATUS current
                DESCRIPTION
                                "2130 Expansion Module ID1 Analogue Input E Low"
                ::= { ucdTraps 8312 }

unnamedAlarm2130ExpansionModuleID1AnalogueInputEHi                     NOTIFICATION-TYPE
                OBJECTS { dse8610SeqNr, dse8610TrapID, dse8610TrapState, dse8610TrapTimeStamp }
                STATUS current
                DESCRIPTION
                                "2130 Expansion Module ID1 Analogue Input E Hi"
                ::= { ucdTraps 8313 }

unnamedAlarm2130ExpansionModuleID1AnalogueInputFLow                     NOTIFICATION-TYPE
                OBJECTS { dse8610SeqNr, dse8610TrapID, dse8610TrapState, dse8610TrapTimeStamp }
                STATUS current
                DESCRIPTION
                                "2130 Expansion Module ID1 Analogue Input F Low"
                ::= { ucdTraps 8314 }

unnamedAlarm2130ExpansionModuleID1AnalogueInputFHi                     NOTIFICATION-TYPE
                OBJECTS { dse8610SeqNr, dse8610TrapID, dse8610TrapState, dse8610TrapTimeStamp }
                STATUS current
                DESCRIPTION
                                "2130 Expansion Module ID1 Analogue Input F Hi"
                ::= { ucdTraps 8315 }

unnamedAlarm2130ExpansionModuleID1AnalogueInputGLow                     NOTIFICATION-TYPE
                OBJECTS { dse8610SeqNr, dse8610TrapID, dse8610TrapState, dse8610TrapTimeStamp }
                STATUS current
                DESCRIPTION
                                "2130 Expansion Module ID1 Analogue Input G Low"
                ::= { ucdTraps 8316 }

unnamedAlarm2130ExpansionModuleID1AnalogueInputGHi                     NOTIFICATION-TYPE
                OBJECTS { dse8610SeqNr, dse8610TrapID, dse8610TrapState, dse8610TrapTimeStamp }
                STATUS current
                DESCRIPTION
                                "2130 Expansion Module ID1 Analogue Input G Hi"
                ::= { ucdTraps 8317 }

unnamedAlarm2130ExpansionModuleID1AnalogueInputHLow                     NOTIFICATION-TYPE
                OBJECTS { dse8610SeqNr, dse8610TrapID, dse8610TrapState, dse8610TrapTimeStamp }
                STATUS current
                DESCRIPTION
                                "2130 Expansion Module ID1 Analogue Input H Low"
                ::= { ucdTraps 8318 }

unnamedAlarm2130ExpansionModuleID1AnalogueInputHHi                     NOTIFICATION-TYPE
                OBJECTS { dse8610SeqNr, dse8610TrapID, dse8610TrapState, dse8610TrapTimeStamp }
                STATUS current
                DESCRIPTION
                                "2130 Expansion Module ID1 Analogue Input H Hi"
                ::= { ucdTraps 8319 }

unnamedAlarm2130ExpansionModuleID2AnalogueInputELow                     NOTIFICATION-TYPE
                OBJECTS { dse8610SeqNr, dse8610TrapID, dse8610TrapState, dse8610TrapTimeStamp }
                STATUS current
                DESCRIPTION
                                "2130 Expansion Module ID2 Analogue Input E Low"
                ::= { ucdTraps 8320 }

unnamedAlarm2130ExpansionModuleID2AnalogueInputEHi                     NOTIFICATION-TYPE
                OBJECTS { dse8610SeqNr, dse8610TrapID, dse8610TrapState, dse8610TrapTimeStamp }
                STATUS current
                DESCRIPTION
                                "2130 Expansion Module ID2 Analogue Input E Hi"
                ::= { ucdTraps 8321 }

unnamedAlarm2130ExpansionModuleID2AnalogueInputFLow                     NOTIFICATION-TYPE
                OBJECTS { dse8610SeqNr, dse8610TrapID, dse8610TrapState, dse8610TrapTimeStamp }
                STATUS current
                DESCRIPTION
                                "2130 Expansion Module ID2 Analogue Input F Low"
                ::= { ucdTraps 8322 }

unnamedAlarm2130ExpansionModuleID2AnalogueInputFHi                     NOTIFICATION-TYPE
                OBJECTS { dse8610SeqNr, dse8610TrapID, dse8610TrapState, dse8610TrapTimeStamp }
                STATUS current
                DESCRIPTION
                                "2130 Expansion Module ID2 Analogue Input F Hi"
                ::= { ucdTraps 8323 }

unnamedAlarm2130ExpansionModuleID2AnalogueInputGLow                     NOTIFICATION-TYPE
                OBJECTS { dse8610SeqNr, dse8610TrapID, dse8610TrapState, dse8610TrapTimeStamp }
                STATUS current
                DESCRIPTION
                                "2130 Expansion Module ID2 Analogue Input G Low"
                ::= { ucdTraps 8324 }

unnamedAlarm2130ExpansionModuleID2AnalogueInputGHi                     NOTIFICATION-TYPE
                OBJECTS { dse8610SeqNr, dse8610TrapID, dse8610TrapState, dse8610TrapTimeStamp }
                STATUS current
                DESCRIPTION
                                "2130 Expansion Module ID2 Analogue Input G Hi"
                ::= { ucdTraps 8325 }

unnamedAlarm2130ExpansionModuleID2AnalogueInputHLow                     NOTIFICATION-TYPE
                OBJECTS { dse8610SeqNr, dse8610TrapID, dse8610TrapState, dse8610TrapTimeStamp }
                STATUS current
                DESCRIPTION
                                "2130 Expansion Module ID2 Analogue Input H Low"
                ::= { ucdTraps 8326 }

unnamedAlarm2130ExpansionModuleID2AnalogueInputHHi                     NOTIFICATION-TYPE
                OBJECTS { dse8610SeqNr, dse8610TrapID, dse8610TrapState, dse8610TrapTimeStamp }
                STATUS current
                DESCRIPTION
                                "2130 Expansion Module ID2 Analogue Input H Hi"
                ::= { ucdTraps 8327 }

unnamedAlarm2130ExpansionModuleID3AnalogueInputGLow                     NOTIFICATION-TYPE
                OBJECTS { dse8610SeqNr, dse8610TrapID, dse8610TrapState, dse8610TrapTimeStamp }
                STATUS current
                DESCRIPTION
                                "2130 Expansion Module ID3 Analogue Input G Low"
                ::= { ucdTraps 8332 }

unnamedAlarm2130ExpansionModuleID3AnalogueInputGHi                     NOTIFICATION-TYPE
                OBJECTS { dse8610SeqNr, dse8610TrapID, dse8610TrapState, dse8610TrapTimeStamp }
                STATUS current
                DESCRIPTION
                                "2130 Expansion Module ID3 Analogue Input G Hi"
                ::= { ucdTraps 8333 }

unnamedAlarm2130ExpansionModuleID3AnalogueInputHLow                     NOTIFICATION-TYPE
                OBJECTS { dse8610SeqNr, dse8610TrapID, dse8610TrapState, dse8610TrapTimeStamp }
                STATUS current
                DESCRIPTION
                                "2130 Expansion Module ID3 Analogue Input H Low"
                ::= { ucdTraps 8334 }

unnamedAlarm2130ExpansionModuleID3AnalogueInputHHi                     NOTIFICATION-TYPE
                OBJECTS { dse8610SeqNr, dse8610TrapID, dse8610TrapState, dse8610TrapTimeStamp }
                STATUS current
                DESCRIPTION
                                "2130 Expansion Module ID3 Analogue Input H Hi"
                ::= { ucdTraps 8335 }

unnamedAlarmFlexibleSensorBLow                     NOTIFICATION-TYPE
                OBJECTS { dse8610SeqNr, dse8610TrapID, dse8610TrapState, dse8610TrapTimeStamp }
                STATUS current
                DESCRIPTION
                                "Flexible Sensor B Low"
                ::= { ucdTraps 8386 }

unnamedAlarmFlexibleSensorBHigh                     NOTIFICATION-TYPE
                OBJECTS { dse8610SeqNr, dse8610TrapID, dse8610TrapState, dse8610TrapTimeStamp }
                STATUS current
                DESCRIPTION
                                "Flexible Sensor B High"
                ::= { ucdTraps 8387 }

unnamedAlarmFlexibleSensorCLow                     NOTIFICATION-TYPE
                OBJECTS { dse8610SeqNr, dse8610TrapID, dse8610TrapState, dse8610TrapTimeStamp }
                STATUS current
                DESCRIPTION
                                "Flexible Sensor C Low"
                ::= { ucdTraps 8388 }

unnamedAlarmFlexibleSensorCHigh                     NOTIFICATION-TYPE
                OBJECTS { dse8610SeqNr, dse8610TrapID, dse8610TrapState, dse8610TrapTimeStamp }
                STATUS current
                DESCRIPTION
                                "Flexible Sensor C High"
                ::= { ucdTraps 8389 }

unnamedAlarmFlexibleSensorDLow                     NOTIFICATION-TYPE
                OBJECTS { dse8610SeqNr, dse8610TrapID, dse8610TrapState, dse8610TrapTimeStamp }
                STATUS current
                DESCRIPTION
                                "Flexible Sensor D Low"
                ::= { ucdTraps 8390 }

unnamedAlarmFlexibleSensorDHigh                     NOTIFICATION-TYPE
                OBJECTS { dse8610SeqNr, dse8610TrapID, dse8610TrapState, dse8610TrapTimeStamp }
                STATUS current
                DESCRIPTION
                                "Flexible Sensor D High"
                ::= { ucdTraps 8391 }

unnamedAlarmMaintenanceAlarm1                     NOTIFICATION-TYPE
                OBJECTS { dse8610SeqNr, dse8610TrapID, dse8610TrapState, dse8610TrapTimeStamp }
                STATUS current
                DESCRIPTION
                                "Maintenance Alarm 1"
                ::= { ucdTraps 8394 }

unnamedAlarmMaintenanceAlarm2                     NOTIFICATION-TYPE
                OBJECTS { dse8610SeqNr, dse8610TrapID, dse8610TrapState, dse8610TrapTimeStamp }
                STATUS current
                DESCRIPTION
                                "Maintenance Alarm 2"
                ::= { ucdTraps 8395 }

unnamedAlarmMaintenanceAlarm3                     NOTIFICATION-TYPE
                OBJECTS { dse8610SeqNr, dse8610TrapID, dse8610TrapState, dse8610TrapTimeStamp }
                STATUS current
                DESCRIPTION
                                "Maintenance Alarm 3"
                ::= { ucdTraps 8396 }

unnamedAlarmPLCAlarm1                     NOTIFICATION-TYPE
                OBJECTS { dse8610SeqNr, dse8610TrapID, dse8610TrapState, dse8610TrapTimeStamp }
                STATUS current
                DESCRIPTION
                                "PLC Alarm 1"
                ::= { ucdTraps 8397 }

unnamedAlarmPLCAlarm2                     NOTIFICATION-TYPE
                OBJECTS { dse8610SeqNr, dse8610TrapID, dse8610TrapState, dse8610TrapTimeStamp }
                STATUS current
                DESCRIPTION
                                "PLC Alarm 2"
                ::= { ucdTraps 8398 }

unnamedAlarmPLCAlarm3                     NOTIFICATION-TYPE
                OBJECTS { dse8610SeqNr, dse8610TrapID, dse8610TrapState, dse8610TrapTimeStamp }
                STATUS current
                DESCRIPTION
                                "PLC Alarm 3"
                ::= { ucdTraps 8399 }

unnamedAlarmPLCAlarm4                     NOTIFICATION-TYPE
                OBJECTS { dse8610SeqNr, dse8610TrapID, dse8610TrapState, dse8610TrapTimeStamp }
                STATUS current
                DESCRIPTION
                                "PLC Alarm 4"
                ::= { ucdTraps 8400 }

unnamedAlarmPLCAlarm5                     NOTIFICATION-TYPE
                OBJECTS { dse8610SeqNr, dse8610TrapID, dse8610TrapState, dse8610TrapTimeStamp }
                STATUS current
                DESCRIPTION
                                "PLC Alarm 5"
                ::= { ucdTraps 8401 }

unnamedAlarmPLCAlarm6                     NOTIFICATION-TYPE
                OBJECTS { dse8610SeqNr, dse8610TrapID, dse8610TrapState, dse8610TrapTimeStamp }
                STATUS current
                DESCRIPTION
                                "PLC Alarm 6"
                ::= { ucdTraps 8402 }

unnamedAlarmPLCAlarm7                     NOTIFICATION-TYPE
                OBJECTS { dse8610SeqNr, dse8610TrapID, dse8610TrapState, dse8610TrapTimeStamp }
                STATUS current
                DESCRIPTION
                                "PLC Alarm 7"
                ::= { ucdTraps 8403 }

unnamedAlarmPLCAlarm8                     NOTIFICATION-TYPE
                OBJECTS { dse8610SeqNr, dse8610TrapID, dse8610TrapState, dse8610TrapTimeStamp }
                STATUS current
                DESCRIPTION
                                "PLC Alarm 8"
                ::= { ucdTraps 8404 }

unnamedAlarmPLCAlarm9                     NOTIFICATION-TYPE
                OBJECTS { dse8610SeqNr, dse8610TrapID, dse8610TrapState, dse8610TrapTimeStamp }
                STATUS current
                DESCRIPTION
                                "PLC Alarm 9"
                ::= { ucdTraps 8405 }

unnamedAlarmPLCAlarm10                     NOTIFICATION-TYPE
                OBJECTS { dse8610SeqNr, dse8610TrapID, dse8610TrapState, dse8610TrapTimeStamp }
                STATUS current
                DESCRIPTION
                                "PLC Alarm 10"
                ::= { ucdTraps 8406 }

unnamedAlarmPLCAlarm11                     NOTIFICATION-TYPE
                OBJECTS { dse8610SeqNr, dse8610TrapID, dse8610TrapState, dse8610TrapTimeStamp }
                STATUS current
                DESCRIPTION
                                "PLC Alarm 11"
                ::= { ucdTraps 8407 }

unnamedAlarmPLCAlarm12                     NOTIFICATION-TYPE
                OBJECTS { dse8610SeqNr, dse8610TrapID, dse8610TrapState, dse8610TrapTimeStamp }
                STATUS current
                DESCRIPTION
                                "PLC Alarm 12"
                ::= { ucdTraps 8408 }

unnamedAlarmPLCAlarm13                     NOTIFICATION-TYPE
                OBJECTS { dse8610SeqNr, dse8610TrapID, dse8610TrapState, dse8610TrapTimeStamp }
                STATUS current
                DESCRIPTION
                                "PLC Alarm 13"
                ::= { ucdTraps 8409 }

unnamedAlarmPLCAlarm14                     NOTIFICATION-TYPE
                OBJECTS { dse8610SeqNr, dse8610TrapID, dse8610TrapState, dse8610TrapTimeStamp }
                STATUS current
                DESCRIPTION
                                "PLC Alarm 14"
                ::= { ucdTraps 8410 }

unnamedAlarmPLCAlarm15                     NOTIFICATION-TYPE
                OBJECTS { dse8610SeqNr, dse8610TrapID, dse8610TrapState, dse8610TrapTimeStamp }
                STATUS current
                DESCRIPTION
                                "PLC Alarm 15"
                ::= { ucdTraps 8411 }

unnamedAlarmPLCAlarm16                     NOTIFICATION-TYPE
                OBJECTS { dse8610SeqNr, dse8610TrapID, dse8610TrapState, dse8610TrapTimeStamp }
                STATUS current
                DESCRIPTION
                                "PLC Alarm 16"
                ::= { ucdTraps 8412 }

unnamedAlarmPLCAlarm17                     NOTIFICATION-TYPE
                OBJECTS { dse8610SeqNr, dse8610TrapID, dse8610TrapState, dse8610TrapTimeStamp }
                STATUS current
                DESCRIPTION
                                "PLC Alarm 17"
                ::= { ucdTraps 8413 }

unnamedAlarmPLCAlarm18                     NOTIFICATION-TYPE
                OBJECTS { dse8610SeqNr, dse8610TrapID, dse8610TrapState, dse8610TrapTimeStamp }
                STATUS current
                DESCRIPTION
                                "PLC Alarm 18"
                ::= { ucdTraps 8414 }

unnamedAlarmPLCAlarm19                     NOTIFICATION-TYPE
                OBJECTS { dse8610SeqNr, dse8610TrapID, dse8610TrapState, dse8610TrapTimeStamp }
                STATUS current
                DESCRIPTION
                                "PLC Alarm 19"
                ::= { ucdTraps 8415 }

unnamedAlarmPLCAlarm20                     NOTIFICATION-TYPE
                OBJECTS { dse8610SeqNr, dse8610TrapID, dse8610TrapState, dse8610TrapTimeStamp }
                STATUS current
                DESCRIPTION
                                "PLC Alarm 20"
                ::= { ucdTraps 8416 }

unnamedAlarmLowLoad                     NOTIFICATION-TYPE
                OBJECTS { dse8610SeqNr, dse8610TrapID, dse8610TrapState, dse8610TrapTimeStamp }
                STATUS current
                DESCRIPTION
                                "Low Load"
                ::= { ucdTraps 8437 }

unnamedAlarm2131ExpansionModuleID0AnalogueInputALow                     NOTIFICATION-TYPE
                OBJECTS { dse8610SeqNr, dse8610TrapID, dse8610TrapState, dse8610TrapTimeStamp }
                STATUS current
                DESCRIPTION
                                "2131 Expansion Module ID0 Analogue Input A Low"
                ::= { ucdTraps 8444 }

unnamedAlarm2131ExpansionModuleID0AnalogueInputAHi                     NOTIFICATION-TYPE
                OBJECTS { dse8610SeqNr, dse8610TrapID, dse8610TrapState, dse8610TrapTimeStamp }
                STATUS current
                DESCRIPTION
                                "2131 Expansion Module ID0 Analogue Input A Hi"
                ::= { ucdTraps 8445 }

unnamedAlarm2131ExpansionModuleID0AnalogueInputBLow                     NOTIFICATION-TYPE
                OBJECTS { dse8610SeqNr, dse8610TrapID, dse8610TrapState, dse8610TrapTimeStamp }
                STATUS current
                DESCRIPTION
                                "2131 Expansion Module ID0 Analogue Input B Low"
                ::= { ucdTraps 8446 }

unnamedAlarm2131ExpansionModuleID0AnalogueInputBHi                     NOTIFICATION-TYPE
                OBJECTS { dse8610SeqNr, dse8610TrapID, dse8610TrapState, dse8610TrapTimeStamp }
                STATUS current
                DESCRIPTION
                                "2131 Expansion Module ID0 Analogue Input B Hi"
                ::= { ucdTraps 8447 }

unnamedAlarm2131ExpansionModuleID0AnalogueInputCLow                     NOTIFICATION-TYPE
                OBJECTS { dse8610SeqNr, dse8610TrapID, dse8610TrapState, dse8610TrapTimeStamp }
                STATUS current
                DESCRIPTION
                                "2131 Expansion Module ID0 Analogue Input C Low"
                ::= { ucdTraps 8448 }

unnamedAlarm2131ExpansionModuleID0AnalogueInputCHi                     NOTIFICATION-TYPE
                OBJECTS { dse8610SeqNr, dse8610TrapID, dse8610TrapState, dse8610TrapTimeStamp }
                STATUS current
                DESCRIPTION
                                "2131 Expansion Module ID0 Analogue Input C Hi"
                ::= { ucdTraps 8449 }

unnamedAlarm2131ExpansionModuleID0AnalogueInputDLow                     NOTIFICATION-TYPE
                OBJECTS { dse8610SeqNr, dse8610TrapID, dse8610TrapState, dse8610TrapTimeStamp }
                STATUS current
                DESCRIPTION
                                "2131 Expansion Module ID0 Analogue Input D Low"
                ::= { ucdTraps 8450 }

unnamedAlarm2131ExpansionModuleID0AnalogueInputDHi                     NOTIFICATION-TYPE
                OBJECTS { dse8610SeqNr, dse8610TrapID, dse8610TrapState, dse8610TrapTimeStamp }
                STATUS current
                DESCRIPTION
                                "2131 Expansion Module ID0 Analogue Input D Hi"
                ::= { ucdTraps 8451 }

unnamedAlarm2131ExpansionModuleID0AnalogueInputELow                     NOTIFICATION-TYPE
                OBJECTS { dse8610SeqNr, dse8610TrapID, dse8610TrapState, dse8610TrapTimeStamp }
                STATUS current
                DESCRIPTION
                                "2131 Expansion Module ID0 Analogue Input E Low"
                ::= { ucdTraps 8452 }

unnamedAlarm2131ExpansionModuleID0AnalogueInputEHi                     NOTIFICATION-TYPE
                OBJECTS { dse8610SeqNr, dse8610TrapID, dse8610TrapState, dse8610TrapTimeStamp }
                STATUS current
                DESCRIPTION
                                "2131 Expansion Module ID0 Analogue Input E Hi"
                ::= { ucdTraps 8453 }

unnamedAlarm2131ExpansionModuleID0AnalogueInputFLow                     NOTIFICATION-TYPE
                OBJECTS { dse8610SeqNr, dse8610TrapID, dse8610TrapState, dse8610TrapTimeStamp }
                STATUS current
                DESCRIPTION
                                "2131 Expansion Module ID0 Analogue Input F Low"
                ::= { ucdTraps 8454 }

unnamedAlarm2131ExpansionModuleID0AnalogueInputFHi                     NOTIFICATION-TYPE
                OBJECTS { dse8610SeqNr, dse8610TrapID, dse8610TrapState, dse8610TrapTimeStamp }
                STATUS current
                DESCRIPTION
                                "2131 Expansion Module ID0 Analogue Input F Hi"
                ::= { ucdTraps 8455 }

unnamedAlarm2131ExpansionModuleID0AnalogueInputGLow                     NOTIFICATION-TYPE
                OBJECTS { dse8610SeqNr, dse8610TrapID, dse8610TrapState, dse8610TrapTimeStamp }
                STATUS current
                DESCRIPTION
                                "2131 Expansion Module ID0 Analogue Input G Low"
                ::= { ucdTraps 8456 }

unnamedAlarm2131ExpansionModuleID0AnalogueInputGHi                     NOTIFICATION-TYPE
                OBJECTS { dse8610SeqNr, dse8610TrapID, dse8610TrapState, dse8610TrapTimeStamp }
                STATUS current
                DESCRIPTION
                                "2131 Expansion Module ID0 Analogue Input G Hi"
                ::= { ucdTraps 8457 }

unnamedAlarm2131ExpansionModuleID0AnalogueInputHLow                     NOTIFICATION-TYPE
                OBJECTS { dse8610SeqNr, dse8610TrapID, dse8610TrapState, dse8610TrapTimeStamp }
                STATUS current
                DESCRIPTION
                                "2131 Expansion Module ID0 Analogue Input H Low"
                ::= { ucdTraps 8458 }

unnamedAlarm2131ExpansionModuleID0AnalogueInputHHi                     NOTIFICATION-TYPE
                OBJECTS { dse8610SeqNr, dse8610TrapID, dse8610TrapState, dse8610TrapTimeStamp }
                STATUS current
                DESCRIPTION
                                "2131 Expansion Module ID0 Analogue Input H Hi"
                ::= { ucdTraps 8459 }

unnamedAlarm2131ExpansionModuleID0AnalogueInputILow                     NOTIFICATION-TYPE
                OBJECTS { dse8610SeqNr, dse8610TrapID, dse8610TrapState, dse8610TrapTimeStamp }
                STATUS current
                DESCRIPTION
                                "2131 Expansion Module ID0 Analogue Input I Low"
                ::= { ucdTraps 8460 }

unnamedAlarm2131ExpansionModuleID0AnalogueInputIHi                     NOTIFICATION-TYPE
                OBJECTS { dse8610SeqNr, dse8610TrapID, dse8610TrapState, dse8610TrapTimeStamp }
                STATUS current
                DESCRIPTION
                                "2131 Expansion Module ID0 Analogue Input I Hi"
                ::= { ucdTraps 8461 }

unnamedAlarm2131ExpansionModuleID0AnalogueInputJLow                     NOTIFICATION-TYPE
                OBJECTS { dse8610SeqNr, dse8610TrapID, dse8610TrapState, dse8610TrapTimeStamp }
                STATUS current
                DESCRIPTION
                                "2131 Expansion Module ID0 Analogue Input J Low"
                ::= { ucdTraps 8462 }

unnamedAlarm2131ExpansionModuleID0AnalogueInputJHi                     NOTIFICATION-TYPE
                OBJECTS { dse8610SeqNr, dse8610TrapID, dse8610TrapState, dse8610TrapTimeStamp }
                STATUS current
                DESCRIPTION
                                "2131 Expansion Module ID0 Analogue Input J Hi"
                ::= { ucdTraps 8463 }

unnamedAlarm2131ExpansionModuleID1AnalogueInputALow                     NOTIFICATION-TYPE
                OBJECTS { dse8610SeqNr, dse8610TrapID, dse8610TrapState, dse8610TrapTimeStamp }
                STATUS current
                DESCRIPTION
                                "2131 Expansion Module ID1 Analogue Input A Low"
                ::= { ucdTraps 8464 }

unnamedAlarm2131ExpansionModuleID1AnalogueInputAHi                     NOTIFICATION-TYPE
                OBJECTS { dse8610SeqNr, dse8610TrapID, dse8610TrapState, dse8610TrapTimeStamp }
                STATUS current
                DESCRIPTION
                                "2131 Expansion Module ID1 Analogue Input A Hi"
                ::= { ucdTraps 8465 }

unnamedAlarm2131ExpansionModuleID1AnalogueInputBLow                     NOTIFICATION-TYPE
                OBJECTS { dse8610SeqNr, dse8610TrapID, dse8610TrapState, dse8610TrapTimeStamp }
                STATUS current
                DESCRIPTION
                                "2131 Expansion Module ID1 Analogue Input B Low"
                ::= { ucdTraps 8466 }

unnamedAlarm2131ExpansionModuleID1AnalogueInputBHi                     NOTIFICATION-TYPE
                OBJECTS { dse8610SeqNr, dse8610TrapID, dse8610TrapState, dse8610TrapTimeStamp }
                STATUS current
                DESCRIPTION
                                "2131 Expansion Module ID1 Analogue Input B Hi"
                ::= { ucdTraps 8467 }

unnamedAlarm2131ExpansionModuleID1AnalogueInputCLow                     NOTIFICATION-TYPE
                OBJECTS { dse8610SeqNr, dse8610TrapID, dse8610TrapState, dse8610TrapTimeStamp }
                STATUS current
                DESCRIPTION
                                "2131 Expansion Module ID1 Analogue Input C Low"
                ::= { ucdTraps 8468 }

unnamedAlarm2131ExpansionModuleID1AnalogueInputCHi                     NOTIFICATION-TYPE
                OBJECTS { dse8610SeqNr, dse8610TrapID, dse8610TrapState, dse8610TrapTimeStamp }
                STATUS current
                DESCRIPTION
                                "2131 Expansion Module ID1 Analogue Input C Hi"
                ::= { ucdTraps 8469 }

unnamedAlarm2131ExpansionModuleID1AnalogueInputDLow                     NOTIFICATION-TYPE
                OBJECTS { dse8610SeqNr, dse8610TrapID, dse8610TrapState, dse8610TrapTimeStamp }
                STATUS current
                DESCRIPTION
                                "2131 Expansion Module ID1 Analogue Input D Low"
                ::= { ucdTraps 8470 }

unnamedAlarm2131ExpansionModuleID1AnalogueInputDHi                     NOTIFICATION-TYPE
                OBJECTS { dse8610SeqNr, dse8610TrapID, dse8610TrapState, dse8610TrapTimeStamp }
                STATUS current
                DESCRIPTION
                                "2131 Expansion Module ID1 Analogue Input D Hi"
                ::= { ucdTraps 8471 }

unnamedAlarm2131ExpansionModuleID1AnalogueInputELow                     NOTIFICATION-TYPE
                OBJECTS { dse8610SeqNr, dse8610TrapID, dse8610TrapState, dse8610TrapTimeStamp }
                STATUS current
                DESCRIPTION
                                "2131 Expansion Module ID1 Analogue Input E Low"
                ::= { ucdTraps 8472 }

unnamedAlarm2131ExpansionModuleID1AnalogueInputEHi                     NOTIFICATION-TYPE
                OBJECTS { dse8610SeqNr, dse8610TrapID, dse8610TrapState, dse8610TrapTimeStamp }
                STATUS current
                DESCRIPTION
                                "2131 Expansion Module ID1 Analogue Input E Hi"
                ::= { ucdTraps 8473 }

unnamedAlarm2131ExpansionModuleID1AnalogueInputFLow                     NOTIFICATION-TYPE
                OBJECTS { dse8610SeqNr, dse8610TrapID, dse8610TrapState, dse8610TrapTimeStamp }
                STATUS current
                DESCRIPTION
                                "2131 Expansion Module ID1 Analogue Input F Low"
                ::= { ucdTraps 8474 }

unnamedAlarm2131ExpansionModuleID1AnalogueInputFHi                     NOTIFICATION-TYPE
                OBJECTS { dse8610SeqNr, dse8610TrapID, dse8610TrapState, dse8610TrapTimeStamp }
                STATUS current
                DESCRIPTION
                                "2131 Expansion Module ID1 Analogue Input F Hi"
                ::= { ucdTraps 8475 }

unnamedAlarm2131ExpansionModuleID1AnalogueInputGLow                     NOTIFICATION-TYPE
                OBJECTS { dse8610SeqNr, dse8610TrapID, dse8610TrapState, dse8610TrapTimeStamp }
                STATUS current
                DESCRIPTION
                                "2131 Expansion Module ID1 Analogue Input G Low"
                ::= { ucdTraps 8476 }

unnamedAlarm2131ExpansionModuleID1AnalogueInputGHi                     NOTIFICATION-TYPE
                OBJECTS { dse8610SeqNr, dse8610TrapID, dse8610TrapState, dse8610TrapTimeStamp }
                STATUS current
                DESCRIPTION
                                "2131 Expansion Module ID1 Analogue Input G Hi"
                ::= { ucdTraps 8477 }

unnamedAlarm2131ExpansionModuleID1AnalogueInputHLow                     NOTIFICATION-TYPE
                OBJECTS { dse8610SeqNr, dse8610TrapID, dse8610TrapState, dse8610TrapTimeStamp }
                STATUS current
                DESCRIPTION
                                "2131 Expansion Module ID1 Analogue Input H Low"
                ::= { ucdTraps 8478 }

unnamedAlarm2131ExpansionModuleID1AnalogueInputHHi                     NOTIFICATION-TYPE
                OBJECTS { dse8610SeqNr, dse8610TrapID, dse8610TrapState, dse8610TrapTimeStamp }
                STATUS current
                DESCRIPTION
                                "2131 Expansion Module ID1 Analogue Input H Hi"
                ::= { ucdTraps 8479 }

unnamedAlarm2131ExpansionModuleID1AnalogueInputILow                     NOTIFICATION-TYPE
                OBJECTS { dse8610SeqNr, dse8610TrapID, dse8610TrapState, dse8610TrapTimeStamp }
                STATUS current
                DESCRIPTION
                                "2131 Expansion Module ID1 Analogue Input I Low"
                ::= { ucdTraps 8480 }

unnamedAlarm2131ExpansionModuleID1AnalogueInputIHi                     NOTIFICATION-TYPE
                OBJECTS { dse8610SeqNr, dse8610TrapID, dse8610TrapState, dse8610TrapTimeStamp }
                STATUS current
                DESCRIPTION
                                "2131 Expansion Module ID1 Analogue Input I Hi"
                ::= { ucdTraps 8481 }

unnamedAlarm2131ExpansionModuleID1AnalogueInputJLow                     NOTIFICATION-TYPE
                OBJECTS { dse8610SeqNr, dse8610TrapID, dse8610TrapState, dse8610TrapTimeStamp }
                STATUS current
                DESCRIPTION
                                "2131 Expansion Module ID1 Analogue Input J Low"
                ::= { ucdTraps 8482 }

unnamedAlarm2131ExpansionModuleID1AnalogueInputJHi                     NOTIFICATION-TYPE
                OBJECTS { dse8610SeqNr, dse8610TrapID, dse8610TrapState, dse8610TrapTimeStamp }
                STATUS current
                DESCRIPTION
                                "2131 Expansion Module ID1 Analogue Input J Hi"
                ::= { ucdTraps 8483 }

unnamedAlarm2131ExpansionModuleID2AnalogueInputALow                     NOTIFICATION-TYPE
                OBJECTS { dse8610SeqNr, dse8610TrapID, dse8610TrapState, dse8610TrapTimeStamp }
                STATUS current
                DESCRIPTION
                                "2131 Expansion Module ID2 Analogue Input A Low"
                ::= { ucdTraps 8484 }

unnamedAlarm2131ExpansionModuleID2AnalogueInputAHi                     NOTIFICATION-TYPE
                OBJECTS { dse8610SeqNr, dse8610TrapID, dse8610TrapState, dse8610TrapTimeStamp }
                STATUS current
                DESCRIPTION
                                "2131 Expansion Module ID2 Analogue Input A Hi"
                ::= { ucdTraps 8485 }

unnamedAlarm2131ExpansionModuleID2AnalogueInputBLow                     NOTIFICATION-TYPE
                OBJECTS { dse8610SeqNr, dse8610TrapID, dse8610TrapState, dse8610TrapTimeStamp }
                STATUS current
                DESCRIPTION
                                "2131 Expansion Module ID2 Analogue Input B Low"
                ::= { ucdTraps 8486 }

unnamedAlarm2131ExpansionModuleID2AnalogueInputBHi                     NOTIFICATION-TYPE
                OBJECTS { dse8610SeqNr, dse8610TrapID, dse8610TrapState, dse8610TrapTimeStamp }
                STATUS current
                DESCRIPTION
                                "2131 Expansion Module ID2 Analogue Input B Hi"
                ::= { ucdTraps 8487 }

unnamedAlarm2131ExpansionModuleID2AnalogueInputCLow                     NOTIFICATION-TYPE
                OBJECTS { dse8610SeqNr, dse8610TrapID, dse8610TrapState, dse8610TrapTimeStamp }
                STATUS current
                DESCRIPTION
                                "2131 Expansion Module ID2 Analogue Input C Low"
                ::= { ucdTraps 8488 }

unnamedAlarm2131ExpansionModuleID2AnalogueInputCHi                     NOTIFICATION-TYPE
                OBJECTS { dse8610SeqNr, dse8610TrapID, dse8610TrapState, dse8610TrapTimeStamp }
                STATUS current
                DESCRIPTION
                                "2131 Expansion Module ID2 Analogue Input C Hi"
                ::= { ucdTraps 8489 }

unnamedAlarm2131ExpansionModuleID2AnalogueInputDLow                     NOTIFICATION-TYPE
                OBJECTS { dse8610SeqNr, dse8610TrapID, dse8610TrapState, dse8610TrapTimeStamp }
                STATUS current
                DESCRIPTION
                                "2131 Expansion Module ID2 Analogue Input D Low"
                ::= { ucdTraps 8490 }

unnamedAlarm2131ExpansionModuleID2AnalogueInputDHi                     NOTIFICATION-TYPE
                OBJECTS { dse8610SeqNr, dse8610TrapID, dse8610TrapState, dse8610TrapTimeStamp }
                STATUS current
                DESCRIPTION
                                "2131 Expansion Module ID2 Analogue Input D Hi"
                ::= { ucdTraps 8491 }

unnamedAlarm2131ExpansionModuleID2AnalogueInputELow                     NOTIFICATION-TYPE
                OBJECTS { dse8610SeqNr, dse8610TrapID, dse8610TrapState, dse8610TrapTimeStamp }
                STATUS current
                DESCRIPTION
                                "2131 Expansion Module ID2 Analogue Input E Low"
                ::= { ucdTraps 8492 }

unnamedAlarm2131ExpansionModuleID2AnalogueInputEHi                     NOTIFICATION-TYPE
                OBJECTS { dse8610SeqNr, dse8610TrapID, dse8610TrapState, dse8610TrapTimeStamp }
                STATUS current
                DESCRIPTION
                                "2131 Expansion Module ID2 Analogue Input E Hi"
                ::= { ucdTraps 8493 }

unnamedAlarm2131ExpansionModuleID2AnalogueInputFLow                     NOTIFICATION-TYPE
                OBJECTS { dse8610SeqNr, dse8610TrapID, dse8610TrapState, dse8610TrapTimeStamp }
                STATUS current
                DESCRIPTION
                                "2131 Expansion Module ID2 Analogue Input F Low"
                ::= { ucdTraps 8494 }

unnamedAlarm2131ExpansionModuleID2AnalogueInputFHi                     NOTIFICATION-TYPE
                OBJECTS { dse8610SeqNr, dse8610TrapID, dse8610TrapState, dse8610TrapTimeStamp }
                STATUS current
                DESCRIPTION
                                "2131 Expansion Module ID2 Analogue Input F Hi"
                ::= { ucdTraps 8495 }

unnamedAlarm2131ExpansionModuleID2AnalogueInputGLow                     NOTIFICATION-TYPE
                OBJECTS { dse8610SeqNr, dse8610TrapID, dse8610TrapState, dse8610TrapTimeStamp }
                STATUS current
                DESCRIPTION
                                "2131 Expansion Module ID2 Analogue Input G Low"
                ::= { ucdTraps 8496 }

unnamedAlarm2131ExpansionModuleID2AnalogueInputGHi                     NOTIFICATION-TYPE
                OBJECTS { dse8610SeqNr, dse8610TrapID, dse8610TrapState, dse8610TrapTimeStamp }
                STATUS current
                DESCRIPTION
                                "2131 Expansion Module ID2 Analogue Input G Hi"
                ::= { ucdTraps 8497 }

unnamedAlarm2131ExpansionModuleID2AnalogueInputHLow                     NOTIFICATION-TYPE
                OBJECTS { dse8610SeqNr, dse8610TrapID, dse8610TrapState, dse8610TrapTimeStamp }
                STATUS current
                DESCRIPTION
                                "2131 Expansion Module ID2 Analogue Input H Low"
                ::= { ucdTraps 8498 }

unnamedAlarm2131ExpansionModuleID2AnalogueInputHHi                     NOTIFICATION-TYPE
                OBJECTS { dse8610SeqNr, dse8610TrapID, dse8610TrapState, dse8610TrapTimeStamp }
                STATUS current
                DESCRIPTION
                                "2131 Expansion Module ID2 Analogue Input H Hi"
                ::= { ucdTraps 8499 }

unnamedAlarm2131ExpansionModuleID2AnalogueInputILow                     NOTIFICATION-TYPE
                OBJECTS { dse8610SeqNr, dse8610TrapID, dse8610TrapState, dse8610TrapTimeStamp }
                STATUS current
                DESCRIPTION
                                "2131 Expansion Module ID2 Analogue Input I Low"
                ::= { ucdTraps 8500 }

unnamedAlarm2131ExpansionModuleID2AnalogueInputIHi                     NOTIFICATION-TYPE
                OBJECTS { dse8610SeqNr, dse8610TrapID, dse8610TrapState, dse8610TrapTimeStamp }
                STATUS current
                DESCRIPTION
                                "2131 Expansion Module ID2 Analogue Input I Hi"
                ::= { ucdTraps 8501 }

unnamedAlarm2131ExpansionModuleID2AnalogueInputJLow                     NOTIFICATION-TYPE
                OBJECTS { dse8610SeqNr, dse8610TrapID, dse8610TrapState, dse8610TrapTimeStamp }
                STATUS current
                DESCRIPTION
                                "2131 Expansion Module ID2 Analogue Input J Low"
                ::= { ucdTraps 8502 }

unnamedAlarm2131ExpansionModuleID2AnalogueInputJHi                     NOTIFICATION-TYPE
                OBJECTS { dse8610SeqNr, dse8610TrapID, dse8610TrapState, dse8610TrapTimeStamp }
                STATUS current
                DESCRIPTION
                                "2131 Expansion Module ID2 Analogue Input J Hi"
                ::= { ucdTraps 8503 }

unnamedAlarm2131ExpansionModuleID3AnalogueInputALow                     NOTIFICATION-TYPE
                OBJECTS { dse8610SeqNr, dse8610TrapID, dse8610TrapState, dse8610TrapTimeStamp }
                STATUS current
                DESCRIPTION
                                "2131 Expansion Module ID3 Analogue Input A Low"
                ::= { ucdTraps 8504 }

unnamedAlarm2131ExpansionModuleID3AnalogueInputAHi                     NOTIFICATION-TYPE
                OBJECTS { dse8610SeqNr, dse8610TrapID, dse8610TrapState, dse8610TrapTimeStamp }
                STATUS current
                DESCRIPTION
                                "2131 Expansion Module ID3 Analogue Input A Hi"
                ::= { ucdTraps 8505 }

unnamedAlarm2131ExpansionModuleID3AnalogueInputBLow                     NOTIFICATION-TYPE
                OBJECTS { dse8610SeqNr, dse8610TrapID, dse8610TrapState, dse8610TrapTimeStamp }
                STATUS current
                DESCRIPTION
                                "2131 Expansion Module ID3 Analogue Input B Low"
                ::= { ucdTraps 8506 }

unnamedAlarm2131ExpansionModuleID3AnalogueInputBHi                     NOTIFICATION-TYPE
                OBJECTS { dse8610SeqNr, dse8610TrapID, dse8610TrapState, dse8610TrapTimeStamp }
                STATUS current
                DESCRIPTION
                                "2131 Expansion Module ID3 Analogue Input B Hi"
                ::= { ucdTraps 8507 }

unnamedAlarm2131ExpansionModuleID3AnalogueInputCLow                     NOTIFICATION-TYPE
                OBJECTS { dse8610SeqNr, dse8610TrapID, dse8610TrapState, dse8610TrapTimeStamp }
                STATUS current
                DESCRIPTION
                                "2131 Expansion Module ID3 Analogue Input C Low"
                ::= { ucdTraps 8508 }

unnamedAlarm2131ExpansionModuleID3AnalogueInputCHi                     NOTIFICATION-TYPE
                OBJECTS { dse8610SeqNr, dse8610TrapID, dse8610TrapState, dse8610TrapTimeStamp }
                STATUS current
                DESCRIPTION
                                "2131 Expansion Module ID3 Analogue Input C Hi"
                ::= { ucdTraps 8509 }

unnamedAlarm2131ExpansionModuleID3AnalogueInputDLow                     NOTIFICATION-TYPE
                OBJECTS { dse8610SeqNr, dse8610TrapID, dse8610TrapState, dse8610TrapTimeStamp }
                STATUS current
                DESCRIPTION
                                "2131 Expansion Module ID3 Analogue Input D Low"
                ::= { ucdTraps 8510 }

unnamedAlarm2131ExpansionModuleID3AnalogueInputDHi                     NOTIFICATION-TYPE
                OBJECTS { dse8610SeqNr, dse8610TrapID, dse8610TrapState, dse8610TrapTimeStamp }
                STATUS current
                DESCRIPTION
                                "2131 Expansion Module ID3 Analogue Input D Hi"
                ::= { ucdTraps 8511 }

unnamedAlarm2131ExpansionModuleID3AnalogueInputELow                     NOTIFICATION-TYPE
                OBJECTS { dse8610SeqNr, dse8610TrapID, dse8610TrapState, dse8610TrapTimeStamp }
                STATUS current
                DESCRIPTION
                                "2131 Expansion Module ID3 Analogue Input E Low"
                ::= { ucdTraps 8512 }

unnamedAlarm2131ExpansionModuleID3AnalogueInputEHi                     NOTIFICATION-TYPE
                OBJECTS { dse8610SeqNr, dse8610TrapID, dse8610TrapState, dse8610TrapTimeStamp }
                STATUS current
                DESCRIPTION
                                "2131 Expansion Module ID3 Analogue Input E Hi"
                ::= { ucdTraps 8513 }

unnamedAlarm2131ExpansionModuleID3AnalogueInputFLow                     NOTIFICATION-TYPE
                OBJECTS { dse8610SeqNr, dse8610TrapID, dse8610TrapState, dse8610TrapTimeStamp }
                STATUS current
                DESCRIPTION
                                "2131 Expansion Module ID3 Analogue Input F Low"
                ::= { ucdTraps 8514 }

unnamedAlarm2131ExpansionModuleID3AnalogueInputFHi                     NOTIFICATION-TYPE
                OBJECTS { dse8610SeqNr, dse8610TrapID, dse8610TrapState, dse8610TrapTimeStamp }
                STATUS current
                DESCRIPTION
                                "2131 Expansion Module ID3 Analogue Input F Hi"
                ::= { ucdTraps 8515 }

unnamedAlarm2131ExpansionModuleID3AnalogueInputGLow                     NOTIFICATION-TYPE
                OBJECTS { dse8610SeqNr, dse8610TrapID, dse8610TrapState, dse8610TrapTimeStamp }
                STATUS current
                DESCRIPTION
                                "2131 Expansion Module ID3 Analogue Input G Low"
                ::= { ucdTraps 8516 }

unnamedAlarm2131ExpansionModuleID3AnalogueInputGHi                     NOTIFICATION-TYPE
                OBJECTS { dse8610SeqNr, dse8610TrapID, dse8610TrapState, dse8610TrapTimeStamp }
                STATUS current
                DESCRIPTION
                                "2131 Expansion Module ID3 Analogue Input G Hi"
                ::= { ucdTraps 8517 }

unnamedAlarm2131ExpansionModuleID3AnalogueInputHLow                     NOTIFICATION-TYPE
                OBJECTS { dse8610SeqNr, dse8610TrapID, dse8610TrapState, dse8610TrapTimeStamp }
                STATUS current
                DESCRIPTION
                                "2131 Expansion Module ID3 Analogue Input H Low"
                ::= { ucdTraps 8518 }

unnamedAlarm2131ExpansionModuleID3AnalogueInputHHi                     NOTIFICATION-TYPE
                OBJECTS { dse8610SeqNr, dse8610TrapID, dse8610TrapState, dse8610TrapTimeStamp }
                STATUS current
                DESCRIPTION
                                "2131 Expansion Module ID3 Analogue Input H Hi"
                ::= { ucdTraps 8519 }

unnamedAlarm2131ExpansionModuleID3AnalogueInputILow                     NOTIFICATION-TYPE
                OBJECTS { dse8610SeqNr, dse8610TrapID, dse8610TrapState, dse8610TrapTimeStamp }
                STATUS current
                DESCRIPTION
                                "2131 Expansion Module ID3 Analogue Input I Low"
                ::= { ucdTraps 8520 }

unnamedAlarm2131ExpansionModuleID3AnalogueInputIHi                     NOTIFICATION-TYPE
                OBJECTS { dse8610SeqNr, dse8610TrapID, dse8610TrapState, dse8610TrapTimeStamp }
                STATUS current
                DESCRIPTION
                                "2131 Expansion Module ID3 Analogue Input I Hi"
                ::= { ucdTraps 8521 }

unnamedAlarm2131ExpansionModuleID3AnalogueInputJLow                     NOTIFICATION-TYPE
                OBJECTS { dse8610SeqNr, dse8610TrapID, dse8610TrapState, dse8610TrapTimeStamp }
                STATUS current
                DESCRIPTION
                                "2131 Expansion Module ID3 Analogue Input J Low"
                ::= { ucdTraps 8522 }

unnamedAlarm2131ExpansionModuleID3AnalogueInputJHi                     NOTIFICATION-TYPE
                OBJECTS { dse8610SeqNr, dse8610TrapID, dse8610TrapState, dse8610TrapTimeStamp }
                STATUS current
                DESCRIPTION
                                "2131 Expansion Module ID3 Analogue Input J Hi"
                ::= { ucdTraps 8523 }

unnamedAlarm2133ExpansionModuleID0AnalogueInputALow                     NOTIFICATION-TYPE
                OBJECTS { dse8610SeqNr, dse8610TrapID, dse8610TrapState, dse8610TrapTimeStamp }
                STATUS current
                DESCRIPTION
                                "2133 Expansion Module ID0 Analogue Input A Low"
                ::= { ucdTraps 8524 }

unnamedAlarm2133ExpansionModuleID0AnalogueInputAHi                     NOTIFICATION-TYPE
                OBJECTS { dse8610SeqNr, dse8610TrapID, dse8610TrapState, dse8610TrapTimeStamp }
                STATUS current
                DESCRIPTION
                                "2133 Expansion Module ID0 Analogue Input A Hi"
                ::= { ucdTraps 8525 }

unnamedAlarm2133ExpansionModuleID0AnalogueInputBLow                     NOTIFICATION-TYPE
                OBJECTS { dse8610SeqNr, dse8610TrapID, dse8610TrapState, dse8610TrapTimeStamp }
                STATUS current
                DESCRIPTION
                                "2133 Expansion Module ID0 Analogue Input B Low"
                ::= { ucdTraps 8526 }

unnamedAlarm2133ExpansionModuleID0AnalogueInputBHi                     NOTIFICATION-TYPE
                OBJECTS { dse8610SeqNr, dse8610TrapID, dse8610TrapState, dse8610TrapTimeStamp }
                STATUS current
                DESCRIPTION
                                "2133 Expansion Module ID0 Analogue Input B Hi"
                ::= { ucdTraps 8527 }

unnamedAlarm2133ExpansionModuleID0AnalogueInputCLow                     NOTIFICATION-TYPE
                OBJECTS { dse8610SeqNr, dse8610TrapID, dse8610TrapState, dse8610TrapTimeStamp }
                STATUS current
                DESCRIPTION
                                "2133 Expansion Module ID0 Analogue Input C Low"
                ::= { ucdTraps 8528 }

unnamedAlarm2133ExpansionModuleID0AnalogueInputCHi                     NOTIFICATION-TYPE
                OBJECTS { dse8610SeqNr, dse8610TrapID, dse8610TrapState, dse8610TrapTimeStamp }
                STATUS current
                DESCRIPTION
                                "2133 Expansion Module ID0 Analogue Input C Hi"
                ::= { ucdTraps 8529 }

unnamedAlarm2133ExpansionModuleID0AnalogueInputDLow                     NOTIFICATION-TYPE
                OBJECTS { dse8610SeqNr, dse8610TrapID, dse8610TrapState, dse8610TrapTimeStamp }
                STATUS current
                DESCRIPTION
                                "2133 Expansion Module ID0 Analogue Input D Low"
                ::= { ucdTraps 8530 }

unnamedAlarm2133ExpansionModuleID0AnalogueInputDHi                     NOTIFICATION-TYPE
                OBJECTS { dse8610SeqNr, dse8610TrapID, dse8610TrapState, dse8610TrapTimeStamp }
                STATUS current
                DESCRIPTION
                                "2133 Expansion Module ID0 Analogue Input D Hi"
                ::= { ucdTraps 8531 }

unnamedAlarm2133ExpansionModuleID0AnalogueInputELow                     NOTIFICATION-TYPE
                OBJECTS { dse8610SeqNr, dse8610TrapID, dse8610TrapState, dse8610TrapTimeStamp }
                STATUS current
                DESCRIPTION
                                "2133 Expansion Module ID0 Analogue Input E Low"
                ::= { ucdTraps 8532 }

unnamedAlarm2133ExpansionModuleID0AnalogueInputEHi                     NOTIFICATION-TYPE
                OBJECTS { dse8610SeqNr, dse8610TrapID, dse8610TrapState, dse8610TrapTimeStamp }
                STATUS current
                DESCRIPTION
                                "2133 Expansion Module ID0 Analogue Input E Hi"
                ::= { ucdTraps 8533 }

unnamedAlarm2133ExpansionModuleID0AnalogueInputFLow                     NOTIFICATION-TYPE
                OBJECTS { dse8610SeqNr, dse8610TrapID, dse8610TrapState, dse8610TrapTimeStamp }
                STATUS current
                DESCRIPTION
                                "2133 Expansion Module ID0 Analogue Input F Low"
                ::= { ucdTraps 8534 }

unnamedAlarm2133ExpansionModuleID0AnalogueInputFHi                     NOTIFICATION-TYPE
                OBJECTS { dse8610SeqNr, dse8610TrapID, dse8610TrapState, dse8610TrapTimeStamp }
                STATUS current
                DESCRIPTION
                                "2133 Expansion Module ID0 Analogue Input F Hi"
                ::= { ucdTraps 8535 }

unnamedAlarm2133ExpansionModuleID0AnalogueInputGLow                     NOTIFICATION-TYPE
                OBJECTS { dse8610SeqNr, dse8610TrapID, dse8610TrapState, dse8610TrapTimeStamp }
                STATUS current
                DESCRIPTION
                                "2133 Expansion Module ID0 Analogue Input G Low"
                ::= { ucdTraps 8536 }

unnamedAlarm2133ExpansionModuleID0AnalogueInputGHi                     NOTIFICATION-TYPE
                OBJECTS { dse8610SeqNr, dse8610TrapID, dse8610TrapState, dse8610TrapTimeStamp }
                STATUS current
                DESCRIPTION
                                "2133 Expansion Module ID0 Analogue Input G Hi"
                ::= { ucdTraps 8537 }

unnamedAlarm2133ExpansionModuleID0AnalogueInputHLow                     NOTIFICATION-TYPE
                OBJECTS { dse8610SeqNr, dse8610TrapID, dse8610TrapState, dse8610TrapTimeStamp }
                STATUS current
                DESCRIPTION
                                "2133 Expansion Module ID0 Analogue Input H Low"
                ::= { ucdTraps 8538 }

unnamedAlarm2133ExpansionModuleID0AnalogueInputHHi                     NOTIFICATION-TYPE
                OBJECTS { dse8610SeqNr, dse8610TrapID, dse8610TrapState, dse8610TrapTimeStamp }
                STATUS current
                DESCRIPTION
                                "2133 Expansion Module ID0 Analogue Input H Hi"
                ::= { ucdTraps 8539 }

unnamedAlarm2133ExpansionModuleID1AnalogueInputALow                     NOTIFICATION-TYPE
                OBJECTS { dse8610SeqNr, dse8610TrapID, dse8610TrapState, dse8610TrapTimeStamp }
                STATUS current
                DESCRIPTION
                                "2133 Expansion Module ID1 Analogue Input A Low"
                ::= { ucdTraps 8540 }

unnamedAlarm2133ExpansionModuleID1AnalogueInputAHi                     NOTIFICATION-TYPE
                OBJECTS { dse8610SeqNr, dse8610TrapID, dse8610TrapState, dse8610TrapTimeStamp }
                STATUS current
                DESCRIPTION
                                "2133 Expansion Module ID1 Analogue Input A Hi"
                ::= { ucdTraps 8541 }

unnamedAlarm2133ExpansionModuleID1AnalogueInputBLow                     NOTIFICATION-TYPE
                OBJECTS { dse8610SeqNr, dse8610TrapID, dse8610TrapState, dse8610TrapTimeStamp }
                STATUS current
                DESCRIPTION
                                "2133 Expansion Module ID1 Analogue Input B Low"
                ::= { ucdTraps 8542 }

unnamedAlarm2133ExpansionModuleID1AnalogueInputBHi                     NOTIFICATION-TYPE
                OBJECTS { dse8610SeqNr, dse8610TrapID, dse8610TrapState, dse8610TrapTimeStamp }
                STATUS current
                DESCRIPTION
                                "2133 Expansion Module ID1 Analogue Input B Hi"
                ::= { ucdTraps 8543 }

unnamedAlarm2133ExpansionModuleID1AnalogueInputCLow                     NOTIFICATION-TYPE
                OBJECTS { dse8610SeqNr, dse8610TrapID, dse8610TrapState, dse8610TrapTimeStamp }
                STATUS current
                DESCRIPTION
                                "2133 Expansion Module ID1 Analogue Input C Low"
                ::= { ucdTraps 8544 }

unnamedAlarm2133ExpansionModuleID1AnalogueInputCHi                     NOTIFICATION-TYPE
                OBJECTS { dse8610SeqNr, dse8610TrapID, dse8610TrapState, dse8610TrapTimeStamp }
                STATUS current
                DESCRIPTION
                                "2133 Expansion Module ID1 Analogue Input C Hi"
                ::= { ucdTraps 8545 }

unnamedAlarm2133ExpansionModuleID1AnalogueInputDLow                     NOTIFICATION-TYPE
                OBJECTS { dse8610SeqNr, dse8610TrapID, dse8610TrapState, dse8610TrapTimeStamp }
                STATUS current
                DESCRIPTION
                                "2133 Expansion Module ID1 Analogue Input D Low"
                ::= { ucdTraps 8546 }

unnamedAlarm2133ExpansionModuleID1AnalogueInputDHi                     NOTIFICATION-TYPE
                OBJECTS { dse8610SeqNr, dse8610TrapID, dse8610TrapState, dse8610TrapTimeStamp }
                STATUS current
                DESCRIPTION
                                "2133 Expansion Module ID1 Analogue Input D Hi"
                ::= { ucdTraps 8547 }

unnamedAlarm2133ExpansionModuleID1AnalogueInputELow                     NOTIFICATION-TYPE
                OBJECTS { dse8610SeqNr, dse8610TrapID, dse8610TrapState, dse8610TrapTimeStamp }
                STATUS current
                DESCRIPTION
                                "2133 Expansion Module ID1 Analogue Input E Low"
                ::= { ucdTraps 8548 }

unnamedAlarm2133ExpansionModuleID1AnalogueInputEHi                     NOTIFICATION-TYPE
                OBJECTS { dse8610SeqNr, dse8610TrapID, dse8610TrapState, dse8610TrapTimeStamp }
                STATUS current
                DESCRIPTION
                                "2133 Expansion Module ID1 Analogue Input E Hi"
                ::= { ucdTraps 8549 }

unnamedAlarm2133ExpansionModuleID1AnalogueInputFLow                     NOTIFICATION-TYPE
                OBJECTS { dse8610SeqNr, dse8610TrapID, dse8610TrapState, dse8610TrapTimeStamp }
                STATUS current
                DESCRIPTION
                                "2133 Expansion Module ID1 Analogue Input F Low"
                ::= { ucdTraps 8550 }

unnamedAlarm2133ExpansionModuleID1AnalogueInputFHi                     NOTIFICATION-TYPE
                OBJECTS { dse8610SeqNr, dse8610TrapID, dse8610TrapState, dse8610TrapTimeStamp }
                STATUS current
                DESCRIPTION
                                "2133 Expansion Module ID1 Analogue Input F Hi"
                ::= { ucdTraps 8551 }

unnamedAlarm2133ExpansionModuleID1AnalogueInputGLow                     NOTIFICATION-TYPE
                OBJECTS { dse8610SeqNr, dse8610TrapID, dse8610TrapState, dse8610TrapTimeStamp }
                STATUS current
                DESCRIPTION
                                "2133 Expansion Module ID1 Analogue Input G Low"
                ::= { ucdTraps 8552 }

unnamedAlarm2133ExpansionModuleID1AnalogueInputGHi                     NOTIFICATION-TYPE
                OBJECTS { dse8610SeqNr, dse8610TrapID, dse8610TrapState, dse8610TrapTimeStamp }
                STATUS current
                DESCRIPTION
                                "2133 Expansion Module ID1 Analogue Input G Hi"
                ::= { ucdTraps 8553 }

unnamedAlarm2133ExpansionModuleID1AnalogueInputHLow                     NOTIFICATION-TYPE
                OBJECTS { dse8610SeqNr, dse8610TrapID, dse8610TrapState, dse8610TrapTimeStamp }
                STATUS current
                DESCRIPTION
                                "2133 Expansion Module ID1 Analogue Input H Low"
                ::= { ucdTraps 8554 }

unnamedAlarm2133ExpansionModuleID1AnalogueInputHHi                     NOTIFICATION-TYPE
                OBJECTS { dse8610SeqNr, dse8610TrapID, dse8610TrapState, dse8610TrapTimeStamp }
                STATUS current
                DESCRIPTION
                                "2133 Expansion Module ID1 Analogue Input H Hi"
                ::= { ucdTraps 8555 }

unnamedAlarm2133ExpansionModuleID2AnalogueInputALow                     NOTIFICATION-TYPE
                OBJECTS { dse8610SeqNr, dse8610TrapID, dse8610TrapState, dse8610TrapTimeStamp }
                STATUS current
                DESCRIPTION
                                "2133 Expansion Module ID2 Analogue Input A Low"
                ::= { ucdTraps 8556 }

unnamedAlarm2133ExpansionModuleID2AnalogueInputAHi                     NOTIFICATION-TYPE
                OBJECTS { dse8610SeqNr, dse8610TrapID, dse8610TrapState, dse8610TrapTimeStamp }
                STATUS current
                DESCRIPTION
                                "2133 Expansion Module ID2 Analogue Input A Hi"
                ::= { ucdTraps 8557 }

unnamedAlarm2133ExpansionModuleID2AnalogueInputBLow                     NOTIFICATION-TYPE
                OBJECTS { dse8610SeqNr, dse8610TrapID, dse8610TrapState, dse8610TrapTimeStamp }
                STATUS current
                DESCRIPTION
                                "2133 Expansion Module ID2 Analogue Input B Low"
                ::= { ucdTraps 8558 }

unnamedAlarm2133ExpansionModuleID2AnalogueInputBHi                     NOTIFICATION-TYPE
                OBJECTS { dse8610SeqNr, dse8610TrapID, dse8610TrapState, dse8610TrapTimeStamp }
                STATUS current
                DESCRIPTION
                                "2133 Expansion Module ID2 Analogue Input B Hi"
                ::= { ucdTraps 8559 }

unnamedAlarm2133ExpansionModuleID2AnalogueInputCLow                     NOTIFICATION-TYPE
                OBJECTS { dse8610SeqNr, dse8610TrapID, dse8610TrapState, dse8610TrapTimeStamp }
                STATUS current
                DESCRIPTION
                                "2133 Expansion Module ID2 Analogue Input C Low"
                ::= { ucdTraps 8560 }

unnamedAlarm2133ExpansionModuleID2AnalogueInputCHi                     NOTIFICATION-TYPE
                OBJECTS { dse8610SeqNr, dse8610TrapID, dse8610TrapState, dse8610TrapTimeStamp }
                STATUS current
                DESCRIPTION
                                "2133 Expansion Module ID2 Analogue Input C Hi"
                ::= { ucdTraps 8561 }

unnamedAlarm2133ExpansionModuleID2AnalogueInputDLow                     NOTIFICATION-TYPE
                OBJECTS { dse8610SeqNr, dse8610TrapID, dse8610TrapState, dse8610TrapTimeStamp }
                STATUS current
                DESCRIPTION
                                "2133 Expansion Module ID2 Analogue Input D Low"
                ::= { ucdTraps 8562 }

unnamedAlarm2133ExpansionModuleID2AnalogueInputDHi                     NOTIFICATION-TYPE
                OBJECTS { dse8610SeqNr, dse8610TrapID, dse8610TrapState, dse8610TrapTimeStamp }
                STATUS current
                DESCRIPTION
                                "2133 Expansion Module ID2 Analogue Input D Hi"
                ::= { ucdTraps 8563 }

unnamedAlarm2133ExpansionModuleID2AnalogueInputELow                     NOTIFICATION-TYPE
                OBJECTS { dse8610SeqNr, dse8610TrapID, dse8610TrapState, dse8610TrapTimeStamp }
                STATUS current
                DESCRIPTION
                                "2133 Expansion Module ID2 Analogue Input E Low"
                ::= { ucdTraps 8564 }

unnamedAlarm2133ExpansionModuleID2AnalogueInputEHi                     NOTIFICATION-TYPE
                OBJECTS { dse8610SeqNr, dse8610TrapID, dse8610TrapState, dse8610TrapTimeStamp }
                STATUS current
                DESCRIPTION
                                "2133 Expansion Module ID2 Analogue Input E Hi"
                ::= { ucdTraps 8565 }

unnamedAlarm2133ExpansionModuleID2AnalogueInputFLow                     NOTIFICATION-TYPE
                OBJECTS { dse8610SeqNr, dse8610TrapID, dse8610TrapState, dse8610TrapTimeStamp }
                STATUS current
                DESCRIPTION
                                "2133 Expansion Module ID2 Analogue Input F Low"
                ::= { ucdTraps 8566 }

unnamedAlarm2133ExpansionModuleID2AnalogueInputFHi                     NOTIFICATION-TYPE
                OBJECTS { dse8610SeqNr, dse8610TrapID, dse8610TrapState, dse8610TrapTimeStamp }
                STATUS current
                DESCRIPTION
                                "2133 Expansion Module ID2 Analogue Input F Hi"
                ::= { ucdTraps 8567 }

unnamedAlarm2133ExpansionModuleID2AnalogueInputGLow                     NOTIFICATION-TYPE
                OBJECTS { dse8610SeqNr, dse8610TrapID, dse8610TrapState, dse8610TrapTimeStamp }
                STATUS current
                DESCRIPTION
                                "2133 Expansion Module ID2 Analogue Input G Low"
                ::= { ucdTraps 8568 }

unnamedAlarm2133ExpansionModuleID2AnalogueInputGHi                     NOTIFICATION-TYPE
                OBJECTS { dse8610SeqNr, dse8610TrapID, dse8610TrapState, dse8610TrapTimeStamp }
                STATUS current
                DESCRIPTION
                                "2133 Expansion Module ID2 Analogue Input G Hi"
                ::= { ucdTraps 8569 }

unnamedAlarm2133ExpansionModuleID2AnalogueInputHLow                     NOTIFICATION-TYPE
                OBJECTS { dse8610SeqNr, dse8610TrapID, dse8610TrapState, dse8610TrapTimeStamp }
                STATUS current
                DESCRIPTION
                                "2133 Expansion Module ID2 Analogue Input H Low"
                ::= { ucdTraps 8570 }

unnamedAlarm2133ExpansionModuleID2AnalogueInputHHi                     NOTIFICATION-TYPE
                OBJECTS { dse8610SeqNr, dse8610TrapID, dse8610TrapState, dse8610TrapTimeStamp }
                STATUS current
                DESCRIPTION
                                "2133 Expansion Module ID2 Analogue Input H Hi"
                ::= { ucdTraps 8571 }

unnamedAlarm2133ExpansionModuleID3AnalogueInputALow                     NOTIFICATION-TYPE
                OBJECTS { dse8610SeqNr, dse8610TrapID, dse8610TrapState, dse8610TrapTimeStamp }
                STATUS current
                DESCRIPTION
                                "2133 Expansion Module ID3 Analogue Input A Low"
                ::= { ucdTraps 8572 }

unnamedAlarm2133ExpansionModuleID3AnalogueInputAHi                     NOTIFICATION-TYPE
                OBJECTS { dse8610SeqNr, dse8610TrapID, dse8610TrapState, dse8610TrapTimeStamp }
                STATUS current
                DESCRIPTION
                                "2133 Expansion Module ID3 Analogue Input A Hi"
                ::= { ucdTraps 8573 }

unnamedAlarm2133ExpansionModuleID3AnalogueInputBLow                     NOTIFICATION-TYPE
                OBJECTS { dse8610SeqNr, dse8610TrapID, dse8610TrapState, dse8610TrapTimeStamp }
                STATUS current
                DESCRIPTION
                                "2133 Expansion Module ID3 Analogue Input B Low"
                ::= { ucdTraps 8574 }

unnamedAlarm2133ExpansionModuleID3AnalogueInputBHi                     NOTIFICATION-TYPE
                OBJECTS { dse8610SeqNr, dse8610TrapID, dse8610TrapState, dse8610TrapTimeStamp }
                STATUS current
                DESCRIPTION
                                "2133 Expansion Module ID3 Analogue Input B Hi"
                ::= { ucdTraps 8575 }

unnamedAlarm2133ExpansionModuleID3AnalogueInputCLow                     NOTIFICATION-TYPE
                OBJECTS { dse8610SeqNr, dse8610TrapID, dse8610TrapState, dse8610TrapTimeStamp }
                STATUS current
                DESCRIPTION
                                "2133 Expansion Module ID3 Analogue Input C Low"
                ::= { ucdTraps 8576 }

unnamedAlarm2133ExpansionModuleID3AnalogueInputCHi                     NOTIFICATION-TYPE
                OBJECTS { dse8610SeqNr, dse8610TrapID, dse8610TrapState, dse8610TrapTimeStamp }
                STATUS current
                DESCRIPTION
                                "2133 Expansion Module ID3 Analogue Input C Hi"
                ::= { ucdTraps 8577 }

unnamedAlarm2133ExpansionModuleID3AnalogueInputDLow                     NOTIFICATION-TYPE
                OBJECTS { dse8610SeqNr, dse8610TrapID, dse8610TrapState, dse8610TrapTimeStamp }
                STATUS current
                DESCRIPTION
                                "2133 Expansion Module ID3 Analogue Input D Low"
                ::= { ucdTraps 8578 }

unnamedAlarm2133ExpansionModuleID3AnalogueInputDHi                     NOTIFICATION-TYPE
                OBJECTS { dse8610SeqNr, dse8610TrapID, dse8610TrapState, dse8610TrapTimeStamp }
                STATUS current
                DESCRIPTION
                                "2133 Expansion Module ID3 Analogue Input D Hi"
                ::= { ucdTraps 8579 }

unnamedAlarm2133ExpansionModuleID3AnalogueInputELow                     NOTIFICATION-TYPE
                OBJECTS { dse8610SeqNr, dse8610TrapID, dse8610TrapState, dse8610TrapTimeStamp }
                STATUS current
                DESCRIPTION
                                "2133 Expansion Module ID3 Analogue Input E Low"
                ::= { ucdTraps 8580 }

unnamedAlarm2133ExpansionModuleID3AnalogueInputEHi                     NOTIFICATION-TYPE
                OBJECTS { dse8610SeqNr, dse8610TrapID, dse8610TrapState, dse8610TrapTimeStamp }
                STATUS current
                DESCRIPTION
                                "2133 Expansion Module ID3 Analogue Input E Hi"
                ::= { ucdTraps 8581 }

unnamedAlarm2133ExpansionModuleID3AnalogueInputFLow                     NOTIFICATION-TYPE
                OBJECTS { dse8610SeqNr, dse8610TrapID, dse8610TrapState, dse8610TrapTimeStamp }
                STATUS current
                DESCRIPTION
                                "2133 Expansion Module ID3 Analogue Input F Low"
                ::= { ucdTraps 8582 }

unnamedAlarm2133ExpansionModuleID3AnalogueInputFHi                     NOTIFICATION-TYPE
                OBJECTS { dse8610SeqNr, dse8610TrapID, dse8610TrapState, dse8610TrapTimeStamp }
                STATUS current
                DESCRIPTION
                                "2133 Expansion Module ID3 Analogue Input F Hi"
                ::= { ucdTraps 8583 }

unnamedAlarm2133ExpansionModuleID3AnalogueInputGLow                     NOTIFICATION-TYPE
                OBJECTS { dse8610SeqNr, dse8610TrapID, dse8610TrapState, dse8610TrapTimeStamp }
                STATUS current
                DESCRIPTION
                                "2133 Expansion Module ID3 Analogue Input G Low"
                ::= { ucdTraps 8584 }

unnamedAlarm2133ExpansionModuleID3AnalogueInputGHi                     NOTIFICATION-TYPE
                OBJECTS { dse8610SeqNr, dse8610TrapID, dse8610TrapState, dse8610TrapTimeStamp }
                STATUS current
                DESCRIPTION
                                "2133 Expansion Module ID3 Analogue Input G Hi"
                ::= { ucdTraps 8585 }

unnamedAlarm2133ExpansionModuleID3AnalogueInputHLow                     NOTIFICATION-TYPE
                OBJECTS { dse8610SeqNr, dse8610TrapID, dse8610TrapState, dse8610TrapTimeStamp }
                STATUS current
                DESCRIPTION
                                "2133 Expansion Module ID3 Analogue Input H Low"
                ::= { ucdTraps 8586 }

unnamedAlarm2133ExpansionModuleID3AnalogueInputHHi                     NOTIFICATION-TYPE
                OBJECTS { dse8610SeqNr, dse8610TrapID, dse8610TrapState, dse8610TrapTimeStamp }
                STATUS current
                DESCRIPTION
                                "2133 Expansion Module ID3 Analogue Input H Hi"
                ::= { ucdTraps 8587 }

unnamedAlarm2130ExpansionModuleID3AnalogueInputELow                     NOTIFICATION-TYPE
                OBJECTS { dse8610SeqNr, dse8610TrapID, dse8610TrapState, dse8610TrapTimeStamp }
                STATUS current
                DESCRIPTION
                                "2130 Expansion Module ID3 Analogue Input E Low"
                ::= { ucdTraps 8616 }

unnamedAlarm2130ExpansionModuleID3AnalogueInputEHi                     NOTIFICATION-TYPE
                OBJECTS { dse8610SeqNr, dse8610TrapID, dse8610TrapState, dse8610TrapTimeStamp }
                STATUS current
                DESCRIPTION
                                "2130 Expansion Module ID3 Analogue Input E Hi"
                ::= { ucdTraps 8617 }

unnamedAlarm2130ExpansionModuleID3AnalogueInputFLow                     NOTIFICATION-TYPE
                OBJECTS { dse8610SeqNr, dse8610TrapID, dse8610TrapState, dse8610TrapTimeStamp }
                STATUS current
                DESCRIPTION
                                "2130 Expansion Module ID3 Analogue Input F Low"
                ::= { ucdTraps 8618 }

unnamedAlarm2130ExpansionModuleID3AnalogueInputFHi                     NOTIFICATION-TYPE
                OBJECTS { dse8610SeqNr, dse8610TrapID, dse8610TrapState, dse8610TrapTimeStamp }
                STATUS current
                DESCRIPTION
                                "2130 Expansion Module ID3 Analogue Input F Hi"
                ::= { ucdTraps 8619 }

unnamedAlarmAnalogueInputADigital                     NOTIFICATION-TYPE
                OBJECTS { dse8610SeqNr, dse8610TrapID, dse8610TrapState, dse8610TrapTimeStamp }
                STATUS current
                DESCRIPTION
                                "Analogue Input A Digital"
                ::= { ucdTraps 8737 }

unnamedAlarmFlexibleSensorALow                     NOTIFICATION-TYPE
                OBJECTS { dse8610SeqNr, dse8610TrapID, dse8610TrapState, dse8610TrapTimeStamp }
                STATUS current
                DESCRIPTION
                                "Flexible Sensor A Low"
                ::= { ucdTraps 8738 }

unnamedAlarmFlexibleSensorAHigh                     NOTIFICATION-TYPE
                OBJECTS { dse8610SeqNr, dse8610TrapID, dse8610TrapState, dse8610TrapTimeStamp }
                STATUS current
                DESCRIPTION
                                "Flexible Sensor A High"
                ::= { ucdTraps 8739 }

unnamedAlarmChargerID0CommonShutdown                     NOTIFICATION-TYPE
                OBJECTS { dse8610SeqNr, dse8610TrapID, dse8610TrapState, dse8610TrapTimeStamp }
                STATUS current
                DESCRIPTION
                                "Charger ID0 Common Shutdown"
                ::= { ucdTraps 8754 }

unnamedAlarmChargerID0CommonWarning                     NOTIFICATION-TYPE
                OBJECTS { dse8610SeqNr, dse8610TrapID, dse8610TrapState, dse8610TrapTimeStamp }
                STATUS current
                DESCRIPTION
                                "Charger ID0 Common Warning"
                ::= { ucdTraps 8755 }

unnamedAlarmChargerID1CommonShutdown                     NOTIFICATION-TYPE
                OBJECTS { dse8610SeqNr, dse8610TrapID, dse8610TrapState, dse8610TrapTimeStamp }
                STATUS current
                DESCRIPTION
                                "Charger ID1 Common Shutdown"
                ::= { ucdTraps 8756 }

unnamedAlarmChargerID1CommonWarning                     NOTIFICATION-TYPE
                OBJECTS { dse8610SeqNr, dse8610TrapID, dse8610TrapState, dse8610TrapTimeStamp }
                STATUS current
                DESCRIPTION
                                "Charger ID1 Common Warning"
                ::= { ucdTraps 8757 }

unnamedAlarmChargerID2CommonShutdown                     NOTIFICATION-TYPE
                OBJECTS { dse8610SeqNr, dse8610TrapID, dse8610TrapState, dse8610TrapTimeStamp }
                STATUS current
                DESCRIPTION
                                "Charger ID2 Common Shutdown"
                ::= { ucdTraps 8758 }

unnamedAlarmChargerID2CommonWarning                     NOTIFICATION-TYPE
                OBJECTS { dse8610SeqNr, dse8610TrapID, dse8610TrapState, dse8610TrapTimeStamp }
                STATUS current
                DESCRIPTION
                                "Charger ID2 Common Warning"
                ::= { ucdTraps 8759 }

unnamedAlarmChargerID3CommonShutdown                     NOTIFICATION-TYPE
                OBJECTS { dse8610SeqNr, dse8610TrapID, dse8610TrapState, dse8610TrapTimeStamp }
                STATUS current
                DESCRIPTION
                                "Charger ID3 Common Shutdown"
                ::= { ucdTraps 8760 }

unnamedAlarmChargerID3CommonWarning                     NOTIFICATION-TYPE
                OBJECTS { dse8610SeqNr, dse8610TrapID, dse8610TrapState, dse8610TrapTimeStamp }
                STATUS current
                DESCRIPTION
                                "Charger ID3 Common Warning"
                ::= { ucdTraps 8761 }

namedAlarmEmergencyStop                     NOTIFICATION-TYPE
                OBJECTS { dse8610SeqNr, dse8610TrapID, dse8610TrapState, dse8610TrapTimeStamp }
                STATUS current
                DESCRIPTION
                                "Emergency Stop"
                ::= { ucdTraps 4096 }

namedAlarmLowOilPressure                     NOTIFICATION-TYPE
                OBJECTS { dse8610SeqNr, dse8610TrapID, dse8610TrapState, dse8610TrapTimeStamp }
                STATUS current
                DESCRIPTION
                                "Low Oil Pressure"
                ::= { ucdTraps 4097 }

namedAlarmHighCoolantTemp                     NOTIFICATION-TYPE
                OBJECTS { dse8610SeqNr, dse8610TrapID, dse8610TrapState, dse8610TrapTimeStamp }
                STATUS current
                DESCRIPTION
                                "High Coolant Temp"
                ::= { ucdTraps 4098 }

namedAlarmLowCoolantTemp                     NOTIFICATION-TYPE
                OBJECTS { dse8610SeqNr, dse8610TrapID, dse8610TrapState, dse8610TrapTimeStamp }
                STATUS current
                DESCRIPTION
                                "Low Coolant Temp"
                ::= { ucdTraps 4099 }

namedAlarmUnderSpeed                     NOTIFICATION-TYPE
                OBJECTS { dse8610SeqNr, dse8610TrapID, dse8610TrapState, dse8610TrapTimeStamp }
                STATUS current
                DESCRIPTION
                                "Under Speed"
                ::= { ucdTraps 4100 }

namedAlarmOverSpeed                     NOTIFICATION-TYPE
                OBJECTS { dse8610SeqNr, dse8610TrapID, dse8610TrapState, dse8610TrapTimeStamp }
                STATUS current
                DESCRIPTION
                                "Over Speed"
                ::= { ucdTraps 4101 }

namedAlarmGeneratorUnderFrequency                     NOTIFICATION-TYPE
                OBJECTS { dse8610SeqNr, dse8610TrapID, dse8610TrapState, dse8610TrapTimeStamp }
                STATUS current
                DESCRIPTION
                                "Generator Under Frequency"
                ::= { ucdTraps 4102 }

namedAlarmGeneratorOverFrequency                     NOTIFICATION-TYPE
                OBJECTS { dse8610SeqNr, dse8610TrapID, dse8610TrapState, dse8610TrapTimeStamp }
                STATUS current
                DESCRIPTION
                                "Generator Over Frequency"
                ::= { ucdTraps 4103 }

namedAlarmGeneratorUnderVolts                     NOTIFICATION-TYPE
                OBJECTS { dse8610SeqNr, dse8610TrapID, dse8610TrapState, dse8610TrapTimeStamp }
                STATUS current
                DESCRIPTION
                                "Generator Under Volts"
                ::= { ucdTraps 4104 }

namedAlarmGeneratorOverVolts                     NOTIFICATION-TYPE
                OBJECTS { dse8610SeqNr, dse8610TrapID, dse8610TrapState, dse8610TrapTimeStamp }
                STATUS current
                DESCRIPTION
                                "Generator Over Volts"
                ::= { ucdTraps 4105 }

namedAlarmBatteryUnderVolts                     NOTIFICATION-TYPE
                OBJECTS { dse8610SeqNr, dse8610TrapID, dse8610TrapState, dse8610TrapTimeStamp }
                STATUS current
                DESCRIPTION
                                "Battery Under Volts"
                ::= { ucdTraps 4106 }

namedAlarmBatteryOverVolts                     NOTIFICATION-TYPE
                OBJECTS { dse8610SeqNr, dse8610TrapID, dse8610TrapState, dse8610TrapTimeStamp }
                STATUS current
                DESCRIPTION
                                "Battery Over Volts"
                ::= { ucdTraps 4107 }

namedAlarmChargeAlternatorFailure                     NOTIFICATION-TYPE
                OBJECTS { dse8610SeqNr, dse8610TrapID, dse8610TrapState, dse8610TrapTimeStamp }
                STATUS current
                DESCRIPTION
                                "Charge Alternator Failure"
                ::= { ucdTraps 4108 }

namedAlarmFailToStart                     NOTIFICATION-TYPE
                OBJECTS { dse8610SeqNr, dse8610TrapID, dse8610TrapState, dse8610TrapTimeStamp }
                STATUS current
                DESCRIPTION
                                "Fail To Start"
                ::= { ucdTraps 4109 }

namedAlarmFailToStop                     NOTIFICATION-TYPE
                OBJECTS { dse8610SeqNr, dse8610TrapID, dse8610TrapState, dse8610TrapTimeStamp }
                STATUS current
                DESCRIPTION
                                "Fail To Stop"
                ::= { ucdTraps 4110 }

namedAlarmGeneratorFailedToClose                     NOTIFICATION-TYPE
                OBJECTS { dse8610SeqNr, dse8610TrapID, dse8610TrapState, dse8610TrapTimeStamp }
                STATUS current
                DESCRIPTION
                                "Generator Failed To Close"
                ::= { ucdTraps 4111 }

namedAlarmMainsFailedToClose                     NOTIFICATION-TYPE
                OBJECTS { dse8610SeqNr, dse8610TrapID, dse8610TrapState, dse8610TrapTimeStamp }
                STATUS current
                DESCRIPTION
                                "Mains Failed To Close"
                ::= { ucdTraps 4112 }

namedAlarmOilPressureSensorOpenCircuit                     NOTIFICATION-TYPE
                OBJECTS { dse8610SeqNr, dse8610TrapID, dse8610TrapState, dse8610TrapTimeStamp }
                STATUS current
                DESCRIPTION
                                "Oil Pressure Sensor Open Circuit"
                ::= { ucdTraps 4113 }

namedAlarmLossOfMagPickupSignal                     NOTIFICATION-TYPE
                OBJECTS { dse8610SeqNr, dse8610TrapID, dse8610TrapState, dse8610TrapTimeStamp }
                STATUS current
                DESCRIPTION
                                "Loss Of Mag Pickup Signal"
                ::= { ucdTraps 4114 }

namedAlarmMagPickupOpenCircuit                     NOTIFICATION-TYPE
                OBJECTS { dse8610SeqNr, dse8610TrapID, dse8610TrapState, dse8610TrapTimeStamp }
                STATUS current
                DESCRIPTION
                                "Mag Pickup Open Circuit"
                ::= { ucdTraps 4115 }

namedAlarmGeneratorOverCurrent                     NOTIFICATION-TYPE
                OBJECTS { dse8610SeqNr, dse8610TrapID, dse8610TrapState, dse8610TrapTimeStamp }
                STATUS current
                DESCRIPTION
                                "Generator Over Current"
                ::= { ucdTraps 4116 }

namedAlarmCalibrationLost                     NOTIFICATION-TYPE
                OBJECTS { dse8610SeqNr, dse8610TrapID, dse8610TrapState, dse8610TrapTimeStamp }
                STATUS current
                DESCRIPTION
                                "Calibration Lost"
                ::= { ucdTraps 4117 }

namedAlarmLowFuelLevel                     NOTIFICATION-TYPE
                OBJECTS { dse8610SeqNr, dse8610TrapID, dse8610TrapState, dse8610TrapTimeStamp }
                STATUS current
                DESCRIPTION
                                "Low Fuel Level"
                ::= { ucdTraps 4118 }

namedAlarmECUAmber                     NOTIFICATION-TYPE
                OBJECTS { dse8610SeqNr, dse8610TrapID, dse8610TrapState, dse8610TrapTimeStamp }
                STATUS current
                DESCRIPTION
                                "ECU Amber"
                ::= { ucdTraps 4119 }

namedAlarmECURed                     NOTIFICATION-TYPE
                OBJECTS { dse8610SeqNr, dse8610TrapID, dse8610TrapState, dse8610TrapTimeStamp }
                STATUS current
                DESCRIPTION
                                "ECU Red"
                ::= { ucdTraps 4120 }

namedAlarmECUDataFail                     NOTIFICATION-TYPE
                OBJECTS { dse8610SeqNr, dse8610TrapID, dse8610TrapState, dse8610TrapTimeStamp }
                STATUS current
                DESCRIPTION
                                "ECU Data Fail"
                ::= { ucdTraps 4121 }

namedAlarmLowOilPressureSwitchAlarm                     NOTIFICATION-TYPE
                OBJECTS { dse8610SeqNr, dse8610TrapID, dse8610TrapState, dse8610TrapTimeStamp }
                STATUS current
                DESCRIPTION
                                "Low Oil Pressure Switch Alarm"
                ::= { ucdTraps 4122 }

namedAlarmHighTemperatureSwitchAlarm                     NOTIFICATION-TYPE
                OBJECTS { dse8610SeqNr, dse8610TrapID, dse8610TrapState, dse8610TrapTimeStamp }
                STATUS current
                DESCRIPTION
                                "High Temperature Switch Alarm"
                ::= { ucdTraps 4123 }

namedAlarmLowFuelSwitchAlarm                     NOTIFICATION-TYPE
                OBJECTS { dse8610SeqNr, dse8610TrapID, dse8610TrapState, dse8610TrapTimeStamp }
                STATUS current
                DESCRIPTION
                                "Low Fuel Switch Alarm"
                ::= { ucdTraps 4124 }

namedAlarmExpansionUnitWatchdogAlarm                     NOTIFICATION-TYPE
                OBJECTS { dse8610SeqNr, dse8610TrapID, dse8610TrapState, dse8610TrapTimeStamp }
                STATUS current
                DESCRIPTION
                                "Expansion Unit Watchdog Alarm"
                ::= { ucdTraps 4125 }

namedAlarmkWOverloadAlarm                     NOTIFICATION-TYPE
                OBJECTS { dse8610SeqNr, dse8610TrapID, dse8610TrapState, dse8610TrapTimeStamp }
                STATUS current
                DESCRIPTION
                                "kW Overload Alarm"
                ::= { ucdTraps 4126 }

namedAlarmNegativePhaseSequenceAlarm                     NOTIFICATION-TYPE
                OBJECTS { dse8610SeqNr, dse8610TrapID, dse8610TrapState, dse8610TrapTimeStamp }
                STATUS current
                DESCRIPTION
                                "Negative Phase Sequence Alarm"
                ::= { ucdTraps 4127 }

namedAlarmEarthFaultTrip                     NOTIFICATION-TYPE
                OBJECTS { dse8610SeqNr, dse8610TrapID, dse8610TrapState, dse8610TrapTimeStamp }
                STATUS current
                DESCRIPTION
                                "Earth Fault Trip"
                ::= { ucdTraps 4128 }

namedAlarmGeneratorPhaseRotationAlarm                     NOTIFICATION-TYPE
                OBJECTS { dse8610SeqNr, dse8610TrapID, dse8610TrapState, dse8610TrapTimeStamp }
                STATUS current
                DESCRIPTION
                                "Generator Phase Rotation Alarm"
                ::= { ucdTraps 4129 }

namedAlarmAutoVoltageSenseFail                     NOTIFICATION-TYPE
                OBJECTS { dse8610SeqNr, dse8610TrapID, dse8610TrapState, dse8610TrapTimeStamp }
                STATUS current
                DESCRIPTION
                                "Auto Voltage Sense Fail"
                ::= { ucdTraps 4130 }

namedAlarmMaintenanceAlarm                     NOTIFICATION-TYPE
                OBJECTS { dse8610SeqNr, dse8610TrapID, dse8610TrapState, dse8610TrapTimeStamp }
                STATUS current
                DESCRIPTION
                                "Maintenance Alarm"
                ::= { ucdTraps 4131 }

namedAlarmFailtoReachLoadingVoltage                     NOTIFICATION-TYPE
                OBJECTS { dse8610SeqNr, dse8610TrapID, dse8610TrapState, dse8610TrapTimeStamp }
                STATUS current
                DESCRIPTION
                                "Fail to Reach Loading Voltage"
                ::= { ucdTraps 4133 }

namedAlarmFuelUsageRunning                     NOTIFICATION-TYPE
                OBJECTS { dse8610SeqNr, dse8610TrapID, dse8610TrapState, dse8610TrapTimeStamp }
                STATUS current
                DESCRIPTION
                                "Fuel Usage Running"
                ::= { ucdTraps 4134 }

namedAlarmFuelUsageStopped                     NOTIFICATION-TYPE
                OBJECTS { dse8610SeqNr, dse8610TrapID, dse8610TrapState, dse8610TrapTimeStamp }
                STATUS current
                DESCRIPTION
                                "Fuel Usage Stopped"
                ::= { ucdTraps 4135 }

namedAlarmProtectionsDisabled                     NOTIFICATION-TYPE
                OBJECTS { dse8610SeqNr, dse8610TrapID, dse8610TrapState, dse8610TrapTimeStamp }
                STATUS current
                DESCRIPTION
                                "Protections Disabled"
                ::= { ucdTraps 4136 }

namedAlarmGeneratorBreakerFailedToOpen                     NOTIFICATION-TYPE
                OBJECTS { dse8610SeqNr, dse8610TrapID, dse8610TrapState, dse8610TrapTimeStamp }
                STATUS current
                DESCRIPTION
                                "Generator Breaker Failed To Open"
                ::= { ucdTraps 4138 }

namedAlarmMainsBreakerFailedToOpen                     NOTIFICATION-TYPE
                OBJECTS { dse8610SeqNr, dse8610TrapID, dse8610TrapState, dse8610TrapTimeStamp }
                STATUS current
                DESCRIPTION
                                "Mains Breaker Failed To Open"
                ::= { ucdTraps 4139 }

namedAlarmBusBreakerFailedToClose                     NOTIFICATION-TYPE
                OBJECTS { dse8610SeqNr, dse8610TrapID, dse8610TrapState, dse8610TrapTimeStamp }
                STATUS current
                DESCRIPTION
                                "Bus Breaker Failed To Close"
                ::= { ucdTraps 4140 }

namedAlarmBusBreakerFailedToOpen                     NOTIFICATION-TYPE
                OBJECTS { dse8610SeqNr, dse8610TrapID, dse8610TrapState, dse8610TrapTimeStamp }
                STATUS current
                DESCRIPTION
                                "Bus Breaker Failed To Open"
                ::= { ucdTraps 4141 }

namedAlarmGeneratorReversePowerAlarm                     NOTIFICATION-TYPE
                OBJECTS { dse8610SeqNr, dse8610TrapID, dse8610TrapState, dse8610TrapTimeStamp }
                STATUS current
                DESCRIPTION
                                "Generator Reverse Power Alarm"
                ::= { ucdTraps 4142 }

namedAlarmShortCircuitAlarm                     NOTIFICATION-TYPE
                OBJECTS { dse8610SeqNr, dse8610TrapID, dse8610TrapState, dse8610TrapTimeStamp }
                STATUS current
                DESCRIPTION
                                "Short Circuit Alarm"
                ::= { ucdTraps 4143 }

namedAlarmAirFlapClosedAlarm                     NOTIFICATION-TYPE
                OBJECTS { dse8610SeqNr, dse8610TrapID, dse8610TrapState, dse8610TrapTimeStamp }
                STATUS current
                DESCRIPTION
                                "Air Flap Closed Alarm"
                ::= { ucdTraps 4144 }

namedAlarmFailToSync                     NOTIFICATION-TYPE
                OBJECTS { dse8610SeqNr, dse8610TrapID, dse8610TrapState, dse8610TrapTimeStamp }
                STATUS current
                DESCRIPTION
                                "Fail To Sync"
                ::= { ucdTraps 4145 }

namedAlarmBusLive                     NOTIFICATION-TYPE
                OBJECTS { dse8610SeqNr, dse8610TrapID, dse8610TrapState, dse8610TrapTimeStamp }
                STATUS current
                DESCRIPTION
                                "Bus Live"
                ::= { ucdTraps 4146 }

namedAlarmBusNotLive                     NOTIFICATION-TYPE
                OBJECTS { dse8610SeqNr, dse8610TrapID, dse8610TrapState, dse8610TrapTimeStamp }
                STATUS current
                DESCRIPTION
                                "Bus Not Live"
                ::= { ucdTraps 4147 }

namedAlarmBusPhaseRotation                     NOTIFICATION-TYPE
                OBJECTS { dse8610SeqNr, dse8610TrapID, dse8610TrapState, dse8610TrapTimeStamp }
                STATUS current
                DESCRIPTION
                                "Bus Phase Rotation"
                ::= { ucdTraps 4148 }

namedAlarmPrioritySelectionError                     NOTIFICATION-TYPE
                OBJECTS { dse8610SeqNr, dse8610TrapID, dse8610TrapState, dse8610TrapTimeStamp }
                STATUS current
                DESCRIPTION
                                "Priority Selection Error"
                ::= { ucdTraps 4149 }

namedAlarmMSCDataError                     NOTIFICATION-TYPE
                OBJECTS { dse8610SeqNr, dse8610TrapID, dse8610TrapState, dse8610TrapTimeStamp }
                STATUS current
                DESCRIPTION
                                "MSC Data Error"
                ::= { ucdTraps 4150 }

namedAlarmMSCIDError                     NOTIFICATION-TYPE
                OBJECTS { dse8610SeqNr, dse8610TrapID, dse8610TrapState, dse8610TrapTimeStamp }
                STATUS current
                DESCRIPTION
                                "MSC ID Error"
                ::= { ucdTraps 4151 }

namedAlarmBusLowVoltage                     NOTIFICATION-TYPE
                OBJECTS { dse8610SeqNr, dse8610TrapID, dse8610TrapState, dse8610TrapTimeStamp }
                STATUS current
                DESCRIPTION
                                "Bus Low Voltage"
                ::= { ucdTraps 4152 }

namedAlarmBusHighVoltage                     NOTIFICATION-TYPE
                OBJECTS { dse8610SeqNr, dse8610TrapID, dse8610TrapState, dse8610TrapTimeStamp }
                STATUS current
                DESCRIPTION
                                "Bus High Voltage"
                ::= { ucdTraps 4153 }

namedAlarmBusLowFrequency                     NOTIFICATION-TYPE
                OBJECTS { dse8610SeqNr, dse8610TrapID, dse8610TrapState, dse8610TrapTimeStamp }
                STATUS current
                DESCRIPTION
                                "Bus Low Frequency"
                ::= { ucdTraps 4154 }

namedAlarmBusHighFrequency                     NOTIFICATION-TYPE
                OBJECTS { dse8610SeqNr, dse8610TrapID, dse8610TrapState, dse8610TrapTimeStamp }
                STATUS current
                DESCRIPTION
                                "Bus High Frequency"
                ::= { ucdTraps 4155 }

namedAlarmMSCFailure                     NOTIFICATION-TYPE
                OBJECTS { dse8610SeqNr, dse8610TrapID, dse8610TrapState, dse8610TrapTimeStamp }
                STATUS current
                DESCRIPTION
                                "MSC Failure"
                ::= { ucdTraps 4156 }

namedAlarmMSCTooFewSets                     NOTIFICATION-TYPE
                OBJECTS { dse8610SeqNr, dse8610TrapID, dse8610TrapState, dse8610TrapTimeStamp }
                STATUS current
                DESCRIPTION
                                "MSC Too Few Sets"
                ::= { ucdTraps 4157 }

namedAlarmMSCAlarmsInhibited                     NOTIFICATION-TYPE
                OBJECTS { dse8610SeqNr, dse8610TrapID, dse8610TrapState, dse8610TrapTimeStamp }
                STATUS current
                DESCRIPTION
                                "MSC Alarms Inhibited"
                ::= { ucdTraps 4158 }

namedAlarmMSCOldVersionUnitsOnTheBus                     NOTIFICATION-TYPE
                OBJECTS { dse8610SeqNr, dse8610TrapID, dse8610TrapState, dse8610TrapTimeStamp }
                STATUS current
                DESCRIPTION
                                "MSC Old Version Units On The Bus"
                ::= { ucdTraps 4159 }

namedAlarmMainsReversePowerAlarm                     NOTIFICATION-TYPE
                OBJECTS { dse8610SeqNr, dse8610TrapID, dse8610TrapState, dse8610TrapTimeStamp }
                STATUS current
                DESCRIPTION
                                "Mains Reverse Power Alarm"
                ::= { ucdTraps 4160 }

namedAlarmMinimumSetsNotReached                     NOTIFICATION-TYPE
                OBJECTS { dse8610SeqNr, dse8610TrapID, dse8610TrapState, dse8610TrapTimeStamp }
                STATUS current
                DESCRIPTION
                                "Minimum Sets Not Reached"
                ::= { ucdTraps 4161 }

namedAlarmInsufficientCapacity                     NOTIFICATION-TYPE
                OBJECTS { dse8610SeqNr, dse8610TrapID, dse8610TrapState, dse8610TrapTimeStamp }
                STATUS current
                DESCRIPTION
                                "Insufficient Capacity"
                ::= { ucdTraps 4162 }

namedAlarmOutOfSync                     NOTIFICATION-TYPE
                OBJECTS { dse8610SeqNr, dse8610TrapID, dse8610TrapState, dse8610TrapTimeStamp }
                STATUS current
                DESCRIPTION
                                "Out Of Sync"
                ::= { ucdTraps 4163 }

namedAlarmAlternativeAuxMainsFail                     NOTIFICATION-TYPE
                OBJECTS { dse8610SeqNr, dse8610TrapID, dse8610TrapState, dse8610TrapTimeStamp }
                STATUS current
                DESCRIPTION
                                "Alternative Aux Mains Fail"
                ::= { ucdTraps 4164 }

namedAlarmLossOfExcitation                     NOTIFICATION-TYPE
                OBJECTS { dse8610SeqNr, dse8610TrapID, dse8610TrapState, dse8610TrapTimeStamp }
                STATUS current
                DESCRIPTION
                                "Loss Of Excitation"
                ::= { ucdTraps 4165 }

namedAlarmMainsROCOF                     NOTIFICATION-TYPE
                OBJECTS { dse8610SeqNr, dse8610TrapID, dse8610TrapState, dse8610TrapTimeStamp }
                STATUS current
                DESCRIPTION
                                "Mains ROCOF"
                ::= { ucdTraps 4166 }

namedAlarmMainsVectorShift                     NOTIFICATION-TYPE
                OBJECTS { dse8610SeqNr, dse8610TrapID, dse8610TrapState, dse8610TrapTimeStamp }
                STATUS current
                DESCRIPTION
                                "Mains Vector Shift"
                ::= { ucdTraps 4167 }

namedAlarmMainsDecouplingLowFrequency                     NOTIFICATION-TYPE
                OBJECTS { dse8610SeqNr, dse8610TrapID, dse8610TrapState, dse8610TrapTimeStamp }
                STATUS current
                DESCRIPTION
                                "Mains Decoupling Low Frequency"
                ::= { ucdTraps 4168 }

namedAlarmMainsDecouplingHighFrequency                     NOTIFICATION-TYPE
                OBJECTS { dse8610SeqNr, dse8610TrapID, dse8610TrapState, dse8610TrapTimeStamp }
                STATUS current
                DESCRIPTION
                                "Mains Decoupling High Frequency"
                ::= { ucdTraps 4169 }

namedAlarmMainsDecouplingLowVoltage                     NOTIFICATION-TYPE
                OBJECTS { dse8610SeqNr, dse8610TrapID, dse8610TrapState, dse8610TrapTimeStamp }
                STATUS current
                DESCRIPTION
                                "Mains Decoupling Low Voltage"
                ::= { ucdTraps 4170 }

namedAlarmMainsDecouplingHighVoltage                     NOTIFICATION-TYPE
                OBJECTS { dse8610SeqNr, dse8610TrapID, dse8610TrapState, dse8610TrapTimeStamp }
                STATUS current
                DESCRIPTION
                                "Mains Decoupling High Voltage"
                ::= { ucdTraps 4171 }

namedAlarmMainsDecouplingCombinedAlarm                     NOTIFICATION-TYPE
                OBJECTS { dse8610SeqNr, dse8610TrapID, dse8610TrapState, dse8610TrapTimeStamp }
                STATUS current
                DESCRIPTION
                                "Mains Decoupling Combined Alarm"
                ::= { ucdTraps 4172 }

namedAlarmMainsPhaseRotationAlarm                     NOTIFICATION-TYPE
                OBJECTS { dse8610SeqNr, dse8610TrapID, dse8610TrapState, dse8610TrapTimeStamp }
                STATUS current
                DESCRIPTION
                                "Mains Phase Rotation Alarm"
                ::= { ucdTraps 4174 }

namedAlarmAVRMaxTrimLimitAlarm                     NOTIFICATION-TYPE
                OBJECTS { dse8610SeqNr, dse8610TrapID, dse8610TrapState, dse8610TrapTimeStamp }
                STATUS current
                DESCRIPTION
                                "AVR Max Trim Limit Alarm"
                ::= { ucdTraps 4175 }

namedAlarmHighCoolantTempElecTripAlarm                     NOTIFICATION-TYPE
                OBJECTS { dse8610SeqNr, dse8610TrapID, dse8610TrapState, dse8610TrapTimeStamp }
                STATUS current
                DESCRIPTION
                                "High Coolant Temp Elec Trip Alarm"
                ::= { ucdTraps 4176 }

namedAlarmTempSenderOpenCircuitAlarm                     NOTIFICATION-TYPE
                OBJECTS { dse8610SeqNr, dse8610TrapID, dse8610TrapState, dse8610TrapTimeStamp }
                STATUS current
                DESCRIPTION
                                "Temp Sender Open Circuit Alarm"
                ::= { ucdTraps 4177 }

namedAlarmFailtoReachLoadingFrequency                     NOTIFICATION-TYPE
                OBJECTS { dse8610SeqNr, dse8610TrapID, dse8610TrapState, dse8610TrapTimeStamp }
                STATUS current
                DESCRIPTION
                                "Fail to Reach Loading Frequency"
                ::= { ucdTraps 4178 }

namedAlarmProtectionsBlocked                     NOTIFICATION-TYPE
                OBJECTS { dse8610SeqNr, dse8610TrapID, dse8610TrapState, dse8610TrapTimeStamp }
                STATUS current
                DESCRIPTION
                                "Protections Blocked"
                ::= { ucdTraps 4187 }

namedAlarmOutOfSyncBus                     NOTIFICATION-TYPE
                OBJECTS { dse8610SeqNr, dse8610TrapID, dse8610TrapState, dse8610TrapTimeStamp }
                STATUS current
                DESCRIPTION
                                "Out Of Sync Bus"
                ::= { ucdTraps 4188 }

namedAlarmOutOfSyncMains                     NOTIFICATION-TYPE
                OBJECTS { dse8610SeqNr, dse8610TrapID, dse8610TrapState, dse8610TrapTimeStamp }
                STATUS current
                DESCRIPTION
                                "Out Of Sync Mains"
                ::= { ucdTraps 4189 }

namedAlarmECUControlledHeaters                     NOTIFICATION-TYPE
                OBJECTS { dse8610SeqNr, dse8610TrapID, dse8610TrapState, dse8610TrapTimeStamp }
                STATUS current
                DESCRIPTION
                                "ECU Controlled Heaters"
                ::= { ucdTraps 4197 }

namedAlarmECUControlledCoolers                     NOTIFICATION-TYPE
                OBJECTS { dse8610SeqNr, dse8610TrapID, dse8610TrapState, dse8610TrapTimeStamp }
                STATUS current
                DESCRIPTION
                                "ECU Controlled Coolers"
                ::= { ucdTraps 4198 }

namedAlarmECUProtect                     NOTIFICATION-TYPE
                OBJECTS { dse8610SeqNr, dse8610TrapID, dse8610TrapState, dse8610TrapTimeStamp }
                STATUS current
                DESCRIPTION
                                "ECU Protect"
                ::= { ucdTraps 4199 }

namedAlarmECUMalfunction                     NOTIFICATION-TYPE
                OBJECTS { dse8610SeqNr, dse8610TrapID, dse8610TrapState, dse8610TrapTimeStamp }
                STATUS current
                DESCRIPTION
                                "ECU Malfunction"
                ::= { ucdTraps 4200 }

namedAlarmIndication                     NOTIFICATION-TYPE
                OBJECTS { dse8610SeqNr, dse8610TrapID, dse8610TrapState, dse8610TrapTimeStamp }
                STATUS current
                DESCRIPTION
                                "Indication"
                ::= { ucdTraps 4201 }

namedAlarmWaterinFuel                     NOTIFICATION-TYPE
                OBJECTS { dse8610SeqNr, dse8610TrapID, dse8610TrapState, dse8610TrapTimeStamp }
                STATUS current
                DESCRIPTION
                                "Water in Fuel"
                ::= { ucdTraps 4206 }

namedAlarmHESTActive                     NOTIFICATION-TYPE
                OBJECTS { dse8610SeqNr, dse8610TrapID, dse8610TrapState, dse8610TrapTimeStamp }
                STATUS current
                DESCRIPTION
                                "HEST Active"
                ::= { ucdTraps 4225 }

namedAlarmDPTCFilter                     NOTIFICATION-TYPE
                OBJECTS { dse8610SeqNr, dse8610TrapID, dse8610TrapState, dse8610TrapTimeStamp }
                STATUS current
                DESCRIPTION
                                "DPTC Filter"
                ::= { ucdTraps 4226 }

namedAlarmHighFuelLevel                     NOTIFICATION-TYPE
                OBJECTS { dse8610SeqNr, dse8610TrapID, dse8610TrapState, dse8610TrapTimeStamp }
                STATUS current
                DESCRIPTION
                                "High Fuel Level"
                ::= { ucdTraps 4227 }

namedAlarmHeaterSensorFailureAlarm                     NOTIFICATION-TYPE
                OBJECTS { dse8610SeqNr, dse8610TrapID, dse8610TrapState, dse8610TrapTimeStamp }
                STATUS current
                DESCRIPTION
                                "Heater Sensor Failure Alarm"
                ::= { ucdTraps 4233 }

namedAlarmDEFLevelLow                     NOTIFICATION-TYPE
                OBJECTS { dse8610SeqNr, dse8610TrapID, dse8610TrapState, dse8610TrapTimeStamp }
                STATUS current
                DESCRIPTION
                                "DEF Level Low"
                ::= { ucdTraps 4313 }

namedAlarmSCRInducement                     NOTIFICATION-TYPE
                OBJECTS { dse8610SeqNr, dse8610TrapID, dse8610TrapState, dse8610TrapTimeStamp }
                STATUS current
                DESCRIPTION
                                "SCR Inducement"
                ::= { ucdTraps 4314 }

namedAlarmInletTemperature                     NOTIFICATION-TYPE
                OBJECTS { dse8610SeqNr, dse8610TrapID, dse8610TrapState, dse8610TrapTimeStamp }
                STATUS current
                DESCRIPTION
                                "Inlet Temperature"
                ::= { ucdTraps 4364 }

namedAlarmElectricalTripStopInhibited                     NOTIFICATION-TYPE
                OBJECTS { dse8610SeqNr, dse8610TrapID, dse8610TrapState, dse8610TrapTimeStamp }
                STATUS current
                DESCRIPTION
                                "Electrical Trip Stop Inhibited"
                ::= { ucdTraps 4367 }

namedAlarmFuelTankBundLevelHigh                     NOTIFICATION-TYPE
                OBJECTS { dse8610SeqNr, dse8610TrapID, dse8610TrapState, dse8610TrapTimeStamp }
                STATUS current
                DESCRIPTION
                                "Fuel Tank Bund Level High"
                ::= { ucdTraps 4372 }

namedAlarmMSCLink1DataError                     NOTIFICATION-TYPE
                OBJECTS { dse8610SeqNr, dse8610TrapID, dse8610TrapState, dse8610TrapTimeStamp }
                STATUS current
                DESCRIPTION
                                "MSC Link 1 Data Error"
                ::= { ucdTraps 4379 }

namedAlarmMSCLink2DataError                     NOTIFICATION-TYPE
                OBJECTS { dse8610SeqNr, dse8610TrapID, dse8610TrapState, dse8610TrapTimeStamp }
                STATUS current
                DESCRIPTION
                                "MSC Link 2 Data Error"
                ::= { ucdTraps 4380 }

namedAlarmMSCLink1Failure                     NOTIFICATION-TYPE
                OBJECTS { dse8610SeqNr, dse8610TrapID, dse8610TrapState, dse8610TrapTimeStamp }
                STATUS current
                DESCRIPTION
                                "MSC Link 1 Failure"
                ::= { ucdTraps 4381 }

namedAlarmMSCLink2Failure                     NOTIFICATION-TYPE
                OBJECTS { dse8610SeqNr, dse8610TrapID, dse8610TrapState, dse8610TrapTimeStamp }
                STATUS current
                DESCRIPTION
                                "MSC Link 2 Failure"
                ::= { ucdTraps 4382 }

namedAlarmMSCLink1TooFewSets                     NOTIFICATION-TYPE
                OBJECTS { dse8610SeqNr, dse8610TrapID, dse8610TrapState, dse8610TrapTimeStamp }
                STATUS current
                DESCRIPTION
                                "MSC Link 1 Too Few Sets"
                ::= { ucdTraps 4383 }

namedAlarmMSCLink2TooFewSets                     NOTIFICATION-TYPE
                OBJECTS { dse8610SeqNr, dse8610TrapID, dse8610TrapState, dse8610TrapTimeStamp }
                STATUS current
                DESCRIPTION
                                "MSC Link 2 Too Few Sets"
                ::= { ucdTraps 4384 }

namedAlarmMSCLink1and2Failure                     NOTIFICATION-TYPE
                OBJECTS { dse8610SeqNr, dse8610TrapID, dse8610TrapState, dse8610TrapTimeStamp }
                STATUS current
                DESCRIPTION
                                "MSC Link 1 and 2 Failure"
                ::= { ucdTraps 4385 }

namedAlarmElectricalTripfrom8660                     NOTIFICATION-TYPE
                OBJECTS { dse8610SeqNr, dse8610TrapID, dse8610TrapState, dse8610TrapTimeStamp }
                STATUS current
                DESCRIPTION
                                "Electrical Trip from 8660"
                ::= { ucdTraps 4387 }

notifModeChange                     NOTIFICATION-TYPE
                OBJECTS { dse8610SeqNr, dse8610TrapID, dse8610TrapState, dse8610TrapTimeStamp }
                STATUS current
                DESCRIPTION
                                "Mode Changed Notification"
                ::= { ucdTraps 16384 }

notifModuleRestart                     NOTIFICATION-TYPE
                OBJECTS { dse8610SeqNr, dse8610TrapID, dse8610TrapState, dse8610TrapTimeStamp }
                STATUS current
                DESCRIPTION
                                "Module Restart Notification"
                ::= { ucdTraps 12297 }

notifEngineStarts                     NOTIFICATION-TYPE
                OBJECTS { dse8610SeqNr, dse8610TrapID, dse8610TrapState, dse8610TrapTimeStamp }
                STATUS current
                DESCRIPTION
                                "Engine Starts Notification"
                ::= { ucdTraps 12591 }

notifEngineStops                     NOTIFICATION-TYPE
                OBJECTS { dse8610SeqNr, dse8610TrapID, dse8610TrapState, dse8610TrapTimeStamp }
                STATUS current
                DESCRIPTION
                                "Engine Stops Notification"
                ::= { ucdTraps 12299 }

notifMainsFail                     NOTIFICATION-TYPE
                OBJECTS { dse8610SeqNr, dse8610TrapID, dse8610TrapState, dse8610TrapTimeStamp }
                STATUS current
                DESCRIPTION
                                "Mains Fail Notification"
                ::= { ucdTraps 12391 }

notifMainsReturn                     NOTIFICATION-TYPE
                OBJECTS { dse8610SeqNr, dse8610TrapID, dse8610TrapState, dse8610TrapTimeStamp }
                STATUS current
                DESCRIPTION
                                "Mains Return Notification"
                ::= { ucdTraps 12392 }

notifECUlampProtect                     NOTIFICATION-TYPE
                OBJECTS { dse8610SeqNr, dse8610TrapID, dse8610TrapState, dse8610TrapTimeStamp }
                STATUS current
                DESCRIPTION
                                "ECU Lamp Protect Notification"
                ::= { ucdTraps 20480 }

notifECUlampMalfunction                     NOTIFICATION-TYPE
                OBJECTS { dse8610SeqNr, dse8610TrapID, dse8610TrapState, dse8610TrapTimeStamp }
                STATUS current
                DESCRIPTION
                                "ECU Lamp Malfunction Notification"
                ::= { ucdTraps 20481 }

notifECUlampShutdown                     NOTIFICATION-TYPE
                OBJECTS { dse8610SeqNr, dse8610TrapID, dse8610TrapState, dse8610TrapTimeStamp }
                STATUS current
                DESCRIPTION
                                "ECU Lamp Shutdown Notification"
                ::= { ucdTraps 20482 }

notifECUlampWarning                     NOTIFICATION-TYPE
                OBJECTS { dse8610SeqNr, dse8610TrapID, dse8610TrapState, dse8610TrapTimeStamp }
                STATUS current
                DESCRIPTION
                                "ECU Lamp Warning"
                ::= { ucdTraps 20483 }

notifLevelStatusMonitoring                     NOTIFICATION-TYPE
                OBJECTS { dse8610SeqNr, dse8610TrapID, dse8610TrapState, dse8610TrapTimeStamp }
                STATUS current
                DESCRIPTION
                                "Level Status Monitoring Notification"
                ::= { ucdTraps 24576 }

-- *****************************************************  END OF TRAP DEFINITION  *****************************************************

snmpMIBConformance
               OBJECT IDENTIFIER ::= { dse8610 100 }

snmpMIBCompliances
               OBJECT IDENTIFIER ::= { snmpMIBConformance 1 }
snmpMIBGroups  OBJECT IDENTIFIER ::= { snmpMIBConformance 2 }

-- compliance statements

snmpBasicCompliance MODULE-COMPLIANCE
    STATUS  deprecated
    DESCRIPTION
            "The compliance statement for SNMPv2 entities which
            implement the SNMPv2 MIB.

            This compliance statement is replaced by
            snmpBasicComplianceRev2."
    MODULE  -- this module
        MANDATORY-GROUPS { generatorGroup, engineGroup, busGroup, gencommP166Group, gencommP167Group, gencommP168Group, gencommP169Group, keypressGroup, trapVarsGroup, snmpBasicNotificationsGroup }
        GROUP   trapVarsGroup
        DESCRIPTION
            "This group is mandatory for SNMPv2 entities which
            support community-based authentication."
    ::= { snmpMIBCompliances 1 }

-- ************************************* units of conformance *************************************

generatorGroup OBJECT-GROUP
    OBJECTS {
		genFreq,
		genL1Volts,
		genL2Volts,
		genL3Volts,
		genL1L2Volts,
		genL2L3Volts,
		genL3L1Volts,
		genL1Current,
		genL2Current,
		genL3Current,
		genECurrent,
		genL1Watts,
		genL2Watts,
		genL3Watts,
		genRotation,
		genWattsTotal,
		genL1VA,
		genL2VA,
		genL3VA,
		genTotalVA,
		genL1VAr,
		genL2VAr,
		genL3VAr,
		genTotalVAr,
		genPowerFactorL1,
		genPowerFactorL2,
		genPowerFactorL3,
		genAvgPowerFactor,
		genPowerTotalPC,
		genVARTotalPC,
		genPhase1,
		genPhase2,
		genPhase3,
		genPhaseTotal,
		genPowerL1PC,
		genPowerL2PC,
		genPowerL3PC,
		genVoltageLNAvg,
		genVoltageLNDiff,
		genVoltageLNMin,
		genVoltageLNMax,
		genVoltageLLAvg,
		genVoltageLLDiff,
		genVoltageLLMin,
		genVoltageLLMax,
		genCurrentAve,
		genCurrentDif,
		genCurrentMin,
		genCurrentMax,
		genPowerTotalAvgPC,
		genPowerTotalDiffPC,
		genPowerTotalMinPC,
		genPowerTotalMaxPC,
		genVATotalAvgPC,
		genVADiffPC,
		genVAMinPC,
		genVAMaxPC,
		genVARTotalAvgPC,
		genVARDiffPC,
		genVARMinPC,
		genVARMaxPC,
		genPFTotalAvgPC,
		genPFDiffPC,
		genPFMinPC,
		genPFMaxPC
		}
    STATUS  current
    DESCRIPTION
            "A collection of objects providing basic instrumentation
            and control of an SNMP entity."
    ::= { snmpMIBGroups 2 }

engineGroup OBJECT-GROUP
    OBJECTS {
		engOilPress,
		engTemp,
		engOilTemp,
		engFuelLevel,
		engChargeAltVolts,
		engBatteryVolts,
		engSpeedDisplay,
		engCoolantP1,
		engCoolantP2,
		engFuelP1,
		engFuelP2,
		engTurboP1,
		engTurboP2,
		engInMainfoldT1,
		engInMainfoldT2,
		engExhaustT1,
		engExhaustT2,
		engFuelConsumption,
		engWaterInFuel,
		engCANBitData,
		engAtmosphericP,
		engFuelT,
		engFuelLevelUnits,
		engTankFuelUnits,
		engAfttrt1FuelUSed,
		engAfttrt1ExGasT1,
		engAfttrt1ExGasT3,
		engRefTorque,
		engPerTorque,
		engDemandPerTorque,
		engPCLoadAtSpeed,
		engAccelPedalPos,
		engNomFricPerTorque,
		engOilLevel,
		engCrankCasePress,
		engCoolantLevel,
		engInjectorRail1,
		engInjectorRail2,
		engEgrFlowRate,
		engPreFilOilPress,
		engInstBreakPower,
		engExhGasPort1Temp,
		engExhGasPort2Temp,
		engExhGasPort3Temp,
		engExhGasPort4Temp,
		engExhGasPort5Temp,
		engExhGasPort6Temp,
		engExhGasPort7Temp,
		engExhGasPort8Temp,
		engExhGasPort9Temp,
		engExhGasPort10Temp,
		engExhGasPort11Temp,
		engExhGasPort12Temp,
		engExhGasPort13Temp,
		engExhGasPort14Temp,
		engExhGasPort15Temp,
		engExhGasPort16Temp,
		engIntercoolerTemp,
		engTurboOilTemp,
		engECUTemp,
		engFanSpeed,
		engTotalRev,
		engAirInPress,
		engAirFilDiffPres,
		engTrapInPress,
		engTurboP3,
		engTurboP4,
		engInMainfoldT3,
		engInMainfoldT4,
		engInMainfoldT5,
		engInMainfoldT6,
		engTripFuel,
		engElectPotential,
		engPGIEngType,
		engPGIVerNum,
		engDPTCFilLampCmd,
		engExhSysHighTemp,
		engDPTCActRegFor,
		engSDWNWaitStart,
		engSDWNProtection,
		engSDWNApproaching,
		engOperatingState,
		engSDWNClOverride,
		engBattleshortOvr,
		engModHours,
		engModOilPress,
		engModCoolTemp,
		engModRPM,
		engModChargeAlt,
		engModSpeedFeed,
		engModFreqAdj,
		engAlarmWarn,
		engAlarmShdwn,
		engAlarmElectr,
		engAmberStopLamp,
		engAmberLampFlash,
		engRedStopLamp,
		engRedLampFlash,
		engProtLamp,
		engProtLampFlash,
		engMalfLamp,
		engMalfLampFlash,
		engBattSwitched,
		engChargPotential,
		engCharAltCurr,
		engBattCurr,
		engTorqueMode,
		engStarterMode,
		engCIStatus,
		engDemandedSpeed,
		engSpeedFBUp,
		engSpeedFBDown,
		engSpeedFailMode,
		engCurrSDSrc,
		engFbackSDCAN,
		engFbackSDAnalog,
		engFailureCodes,
		engActDrop,
		engStartStatus,
		engProtOrStatus,
		engMTURuniingState,
		engCylCutOff,
		engLoadGenStatus,
		engEtxStopState,
		engCurrOPMode,
		engMTUReqTorque,
		engTripAvgFuel,
		engECURatedPower,
		engECURatedSpeed,
		engECUIdleSpeed,
		engECUDesirSpeed,
		engECUPreheatStat,
		engManiFoldPres,
		engIntercoolerLevel,
		engCANLinkState,
		engAutoDFPRegInh,
		engDPTCActRegInhSwitch,
		engSootLoadPC,
		engAshLoadPC,
		engDefTankLevel,
		engDefTankTemp,
		engDefLevelWarn,
		engDefReagentCons,
		engDefInducReason,
		engDefInducSever,
		engDefCounterMin,
		engTLTTorqueReduc,
		engTLTVehspdReduc,
		engEGRPress,
		engEGRTemp,
		engAmbAirTemp,
		engAirIntakeTemp,
		engSRCOperatInduc,
		engTankLevLowLost,
		engMiscAltSpeedSel,
		engExhGasP17Temp,
		engExhGasP18Temp,
		engExhGasP19Temp,
		engExhGasP20Temp,
		engInstFuelRate,
		engDPTCFiltStat,
		engDPTCActRegInh,
		engDPTCActRegInhEt,
		engDefTankStat,
		engFuelGasPress,
		engThrotPos1,
		engThrotPos2
		}
    STATUS  current
    DESCRIPTION
            "A collection of objects providing basic instrumentation
            and control of an SNMP entity."
    ::= { snmpMIBGroups 3 }

busGroup OBJECT-GROUP
    OBJECTS {
		busFreq,
		busL1Volts,
		busL2Volts,
		busL3Volts,
		busL1L2Volts,
		busL2L3Volts,
		busL3L1Volts,
		busL1Current,
		busL2Current,
		busL3Current,
		busECurrent,
		busL1Watts,
		busL2Watts,
		busL3Watts,
		busRotations,
		busWattsTotal,
		busL1VA,
		busL2VA,
		busL3VA,
		busTotalVA,
		busL1VAr,
		busL2VAr,
		busL3VAr,
		busTotalVAr,
		busPowerFactorL1,
		busPowerFactorL2,
		busPowerFactorL3,
		busAvgPowerFactor,
		busPowerTotalPC,
		busVARTotalPC,
		busVoltageLNAvg,
		busVoltageLNDiff,
		busVoltageLNMin,
		busVoltageLNMax,
		busVoltageLLAvg,
		busVoltageLLDiff,
		busVoltageLLMin,
		busVoltageLLMax
		}
    STATUS  current
    DESCRIPTION
            "A collection of objects providing basic instrumentation
            and control of an SNMP entity."
    ::= { snmpMIBGroups 4 }

gencommP166Group OBJECT-GROUP
    OBJECTS {
		gencommP166Reg-0-1,
		gencommP166Reg-2-3,
		gencommP166Reg-4-5,
		gencommP166Reg-6-7,
		gencommP166Reg-8-9,
		gencommP166Reg-10-11,
		gencommP166Reg-12-13,
		gencommP166Reg-14-15,
		gencommP166Reg-16-17,
		gencommP166Reg-18-19,
		gencommP166Reg-20-21,
		gencommP166Reg-22-23,
		gencommP166Reg-24-25,
		gencommP166Reg-26-27,
		gencommP166Reg-28-29,
		gencommP166Reg-30-31,
		gencommP166Reg-32-33,
		gencommP166Reg-34-35,
		gencommP166Reg-36-37,
		gencommP166Reg-38-39,
		gencommP166Reg-40-41,
		gencommP166Reg-42-43,
		gencommP166Reg-44-45,
		gencommP166Reg-46-47,
		gencommP166Reg-48-49,
		gencommP166Reg-50-51,
		gencommP166Reg-52-53,
		gencommP166Reg-54-55,
		gencommP166Reg-56-57,
		gencommP166Reg-58-59,
		gencommP166Reg-60-61,
		gencommP166Reg-62-63,
		gencommP166Reg-64-65,
		gencommP166Reg-66-67,
		gencommP166Reg-68-69,
		gencommP166Reg-70-71,
		gencommP166Reg-72-73,
		gencommP166Reg-74-75,
		gencommP166Reg-76-77,
		gencommP166Reg-78-79,
		gencommP166Reg-80-81,
		gencommP166Reg-82-83,
		gencommP166Reg-84-85,
		gencommP166Reg-86-87,
		gencommP166Reg-88-89,
		gencommP166Reg-90-91,
		gencommP166Reg-92-93,
		gencommP166Reg-94-95,
		gencommP166Reg-96-97,
		gencommP166Reg-98-99,
		gencommP166Reg-100-101,
		gencommP166Reg-102-103,
		gencommP166Reg-104-105,
		gencommP166Reg-106-107,
		gencommP166Reg-108-109,
		gencommP166Reg-110-111,
		gencommP166Reg-112-113,
		gencommP166Reg-114-115,
		gencommP166Reg-116-117,
		gencommP166Reg-118-119,
		gencommP166Reg-120-121,
		gencommP166Reg-122-123,
		gencommP166Reg-124-125,
		gencommP166Reg-126-127,
		gencommP166Reg-128-129,
		gencommP166Reg-130-131,
		gencommP166Reg-132-133,
		gencommP166Reg-134-135,
		gencommP166Reg-136-137,
		gencommP166Reg-138-139,
		gencommP166Reg-140-141,
		gencommP166Reg-142-143,
		gencommP166Reg-144-145,
		gencommP166Reg-146-147,
		gencommP166Reg-148-149,
		gencommP166Reg-150-151,
		gencommP166Reg-152-153,
		gencommP166Reg-154-155,
		gencommP166Reg-156-157,
		gencommP166Reg-158-159,
		gencommP166Reg-160-161,
		gencommP166Reg-162-163,
		gencommP166Reg-164-165,
		gencommP166Reg-166-167,
		gencommP166Reg-168-169,
		gencommP166Reg-170-171,
		gencommP166Reg-172-173,
		gencommP166Reg-174-175,
		gencommP166Reg-176-177,
		gencommP166Reg-178-179,
		gencommP166Reg-180-181,
		gencommP166Reg-182-183,
		gencommP166Reg-184-185,
		gencommP166Reg-186-187,
		gencommP166Reg-188-189,
		gencommP166Reg-190-191,
		gencommP166Reg-192-193,
		gencommP166Reg-194-195,
		gencommP166Reg-196-197,
		gencommP166Reg-198-199,
		gencommP166Reg-200-201,
		gencommP166Reg-202-203,
		gencommP166Reg-204-205,
		gencommP166Reg-206-207,
		gencommP166Reg-208-209,
		gencommP166Reg-210-211,
		gencommP166Reg-212-213,
		gencommP166Reg-214-215,
		gencommP166Reg-216-217,
		gencommP166Reg-218-219,
		gencommP166Reg-220-221,
		gencommP166Reg-222-223,
		gencommP166Reg-224-225,
		gencommP166Reg-226-227,
		gencommP166Reg-228-229,
		gencommP166Reg-230-231,
		gencommP166Reg-232-233,
		gencommP166Reg-234-235,
		gencommP166Reg-236-237,
		gencommP166Reg-238-239,
		gencommP166Reg-240-241,
		gencommP166Reg-242-243,
		gencommP166Reg-244-245,
		gencommP166Reg-246-247,
		gencommP166Reg-248-249,
		gencommP166Reg-250-251,
		gencommP166Reg-252-253,
		gencommP166Reg-254-255
		}
    STATUS  current
    DESCRIPTION
            "A collection of objects providing basic instrumentation
            and control of an SNMP entity."
    ::= { snmpMIBGroups 5 }

gencommP167Group OBJECT-GROUP
    OBJECTS {
		gencommP167Reg-0-1,
		gencommP167Reg-2-3,
		gencommP167Reg-4-5,
		gencommP167Reg-6-7,
		gencommP167Reg-8-9,
		gencommP167Reg-10-11,
		gencommP167Reg-12-13,
		gencommP167Reg-14-15,
		gencommP167Reg-16-17,
		gencommP167Reg-18-19,
		gencommP167Reg-20-21,
		gencommP167Reg-22-23,
		gencommP167Reg-24-25,
		gencommP167Reg-26-27,
		gencommP167Reg-28-29,
		gencommP167Reg-30-31,
		gencommP167Reg-32-33,
		gencommP167Reg-34-35,
		gencommP167Reg-36-37,
		gencommP167Reg-38-39,
		gencommP167Reg-40-41,
		gencommP167Reg-42-43,
		gencommP167Reg-44-45,
		gencommP167Reg-46-47,
		gencommP167Reg-48-49,
		gencommP167Reg-50-51,
		gencommP167Reg-52-53,
		gencommP167Reg-54-55,
		gencommP167Reg-56-57,
		gencommP167Reg-58-59,
		gencommP167Reg-60-61,
		gencommP167Reg-62-63,
		gencommP167Reg-64-65,
		gencommP167Reg-66-67,
		gencommP167Reg-68-69,
		gencommP167Reg-70-71,
		gencommP167Reg-72-73,
		gencommP167Reg-74-75,
		gencommP167Reg-76-77,
		gencommP167Reg-78-79,
		gencommP167Reg-80-81,
		gencommP167Reg-82-83,
		gencommP167Reg-84-85,
		gencommP167Reg-86-87,
		gencommP167Reg-88-89,
		gencommP167Reg-90-91,
		gencommP167Reg-92-93,
		gencommP167Reg-94-95,
		gencommP167Reg-96-97,
		gencommP167Reg-98-99,
		gencommP167Reg-100-101,
		gencommP167Reg-102-103,
		gencommP167Reg-104-105,
		gencommP167Reg-106-107,
		gencommP167Reg-108-109,
		gencommP167Reg-110-111,
		gencommP167Reg-112-113,
		gencommP167Reg-114-115,
		gencommP167Reg-116-117,
		gencommP167Reg-118-119,
		gencommP167Reg-120-121,
		gencommP167Reg-122-123,
		gencommP167Reg-124-125,
		gencommP167Reg-126-127,
		gencommP167Reg-128-129,
		gencommP167Reg-130-131,
		gencommP167Reg-132-133,
		gencommP167Reg-134-135,
		gencommP167Reg-136-137,
		gencommP167Reg-138-139,
		gencommP167Reg-140-141,
		gencommP167Reg-142-143,
		gencommP167Reg-144-145,
		gencommP167Reg-146-147,
		gencommP167Reg-148-149,
		gencommP167Reg-150-151,
		gencommP167Reg-152-153,
		gencommP167Reg-154-155,
		gencommP167Reg-156-157,
		gencommP167Reg-158-159,
		gencommP167Reg-160-161,
		gencommP167Reg-162-163,
		gencommP167Reg-164-165,
		gencommP167Reg-166-167,
		gencommP167Reg-168-169,
		gencommP167Reg-170-171,
		gencommP167Reg-172-173,
		gencommP167Reg-174-175,
		gencommP167Reg-176-177,
		gencommP167Reg-178-179,
		gencommP167Reg-180-181,
		gencommP167Reg-182-183,
		gencommP167Reg-184-185,
		gencommP167Reg-186-187,
		gencommP167Reg-188-189,
		gencommP167Reg-190-191,
		gencommP167Reg-192-193,
		gencommP167Reg-194-195,
		gencommP167Reg-196-197,
		gencommP167Reg-198-199,
		gencommP167Reg-200-201,
		gencommP167Reg-202-203,
		gencommP167Reg-204-205,
		gencommP167Reg-206-207,
		gencommP167Reg-208-209,
		gencommP167Reg-210-211,
		gencommP167Reg-212-213,
		gencommP167Reg-214-215,
		gencommP167Reg-216-217,
		gencommP167Reg-218-219,
		gencommP167Reg-220-221,
		gencommP167Reg-222-223,
		gencommP167Reg-224-225,
		gencommP167Reg-226-227,
		gencommP167Reg-228-229,
		gencommP167Reg-230-231,
		gencommP167Reg-232-233,
		gencommP167Reg-234-235,
		gencommP167Reg-236-237,
		gencommP167Reg-238-239,
		gencommP167Reg-240-241,
		gencommP167Reg-242-243,
		gencommP167Reg-244-245,
		gencommP167Reg-246-247,
		gencommP167Reg-248-249,
		gencommP167Reg-250-251,
		gencommP167Reg-252-253,
		gencommP167Reg-254-255
		}
    STATUS  current
    DESCRIPTION
            "A collection of objects providing basic instrumentation
            and control of an SNMP entity."
    ::= { snmpMIBGroups 6 }

gencommP168Group OBJECT-GROUP
    OBJECTS {
		gencommP168Reg-0-1,
		gencommP168Reg-2-3,
		gencommP168Reg-4-5,
		gencommP168Reg-6-7,
		gencommP168Reg-8-9,
		gencommP168Reg-10-11,
		gencommP168Reg-12-13,
		gencommP168Reg-14-15,
		gencommP168Reg-16-17,
		gencommP168Reg-18-19,
		gencommP168Reg-20-21,
		gencommP168Reg-22-23,
		gencommP168Reg-24-25,
		gencommP168Reg-26-27,
		gencommP168Reg-28-29,
		gencommP168Reg-30-31,
		gencommP168Reg-32-33,
		gencommP168Reg-34-35,
		gencommP168Reg-36-37,
		gencommP168Reg-38-39,
		gencommP168Reg-40-41,
		gencommP168Reg-42-43,
		gencommP168Reg-44-45,
		gencommP168Reg-46-47,
		gencommP168Reg-48-49,
		gencommP168Reg-50-51,
		gencommP168Reg-52-53,
		gencommP168Reg-54-55,
		gencommP168Reg-56-57,
		gencommP168Reg-58-59,
		gencommP168Reg-60-61,
		gencommP168Reg-62-63,
		gencommP168Reg-64-65,
		gencommP168Reg-66-67,
		gencommP168Reg-68-69,
		gencommP168Reg-70-71,
		gencommP168Reg-72-73,
		gencommP168Reg-74-75,
		gencommP168Reg-76-77,
		gencommP168Reg-78-79,
		gencommP168Reg-80-81,
		gencommP168Reg-82-83,
		gencommP168Reg-84-85,
		gencommP168Reg-86-87,
		gencommP168Reg-88-89,
		gencommP168Reg-90-91,
		gencommP168Reg-92-93,
		gencommP168Reg-94-95,
		gencommP168Reg-96-97,
		gencommP168Reg-98-99,
		gencommP168Reg-100-101,
		gencommP168Reg-102-103,
		gencommP168Reg-104-105,
		gencommP168Reg-106-107,
		gencommP168Reg-108-109,
		gencommP168Reg-110-111,
		gencommP168Reg-112-113,
		gencommP168Reg-114-115,
		gencommP168Reg-116-117,
		gencommP168Reg-118-119,
		gencommP168Reg-120-121,
		gencommP168Reg-122-123,
		gencommP168Reg-124-125,
		gencommP168Reg-126-127,
		gencommP168Reg-128-129,
		gencommP168Reg-130-131,
		gencommP168Reg-132-133,
		gencommP168Reg-134-135,
		gencommP168Reg-136-137,
		gencommP168Reg-138-139,
		gencommP168Reg-140-141,
		gencommP168Reg-142-143,
		gencommP168Reg-144-145,
		gencommP168Reg-146-147,
		gencommP168Reg-148-149,
		gencommP168Reg-150-151,
		gencommP168Reg-152-153,
		gencommP168Reg-154-155,
		gencommP168Reg-156-157,
		gencommP168Reg-158-159,
		gencommP168Reg-160-161,
		gencommP168Reg-162-163,
		gencommP168Reg-164-165,
		gencommP168Reg-166-167,
		gencommP168Reg-168-169,
		gencommP168Reg-170-171,
		gencommP168Reg-172-173,
		gencommP168Reg-174-175,
		gencommP168Reg-176-177,
		gencommP168Reg-178-179,
		gencommP168Reg-180-181,
		gencommP168Reg-182-183,
		gencommP168Reg-184-185,
		gencommP168Reg-186-187,
		gencommP168Reg-188-189,
		gencommP168Reg-190-191,
		gencommP168Reg-192-193,
		gencommP168Reg-194-195,
		gencommP168Reg-196-197,
		gencommP168Reg-198-199,
		gencommP168Reg-200-201,
		gencommP168Reg-202-203,
		gencommP168Reg-204-205,
		gencommP168Reg-206-207,
		gencommP168Reg-208-209,
		gencommP168Reg-210-211,
		gencommP168Reg-212-213,
		gencommP168Reg-214-215,
		gencommP168Reg-216-217,
		gencommP168Reg-218-219,
		gencommP168Reg-220-221,
		gencommP168Reg-222-223,
		gencommP168Reg-224-225,
		gencommP168Reg-226-227,
		gencommP168Reg-228-229,
		gencommP168Reg-230-231,
		gencommP168Reg-232-233,
		gencommP168Reg-234-235,
		gencommP168Reg-236-237,
		gencommP168Reg-238-239,
		gencommP168Reg-240-241,
		gencommP168Reg-242-243,
		gencommP168Reg-244-245,
		gencommP168Reg-246-247,
		gencommP168Reg-248-249,
		gencommP168Reg-250-251,
		gencommP168Reg-252-253,
		gencommP168Reg-254-255
		}
    STATUS  current
    DESCRIPTION
            "A collection of objects providing basic instrumentation
            and control of an SNMP entity."
    ::= { snmpMIBGroups 7 }

gencommP169Group OBJECT-GROUP
    OBJECTS {
		gencommP169Reg-0-1,
		gencommP169Reg-2-3,
		gencommP169Reg-4-5,
		gencommP169Reg-6-7,
		gencommP169Reg-8-9,
		gencommP169Reg-10-11,
		gencommP169Reg-12-13,
		gencommP169Reg-14-15,
		gencommP169Reg-16-17,
		gencommP169Reg-18-19,
		gencommP169Reg-20-21,
		gencommP169Reg-22-23,
		gencommP169Reg-24-25,
		gencommP169Reg-26-27,
		gencommP169Reg-28-29,
		gencommP169Reg-30-31,
		gencommP169Reg-32-33,
		gencommP169Reg-34-35,
		gencommP169Reg-36-37,
		gencommP169Reg-38-39,
		gencommP169Reg-40-41,
		gencommP169Reg-42-43,
		gencommP169Reg-44-45,
		gencommP169Reg-46-47,
		gencommP169Reg-48-49,
		gencommP169Reg-50-51,
		gencommP169Reg-52-53,
		gencommP169Reg-54-55,
		gencommP169Reg-56-57,
		gencommP169Reg-58-59,
		gencommP169Reg-60-61,
		gencommP169Reg-62-63,
		gencommP169Reg-64-65,
		gencommP169Reg-66-67,
		gencommP169Reg-68-69,
		gencommP169Reg-70-71,
		gencommP169Reg-72-73,
		gencommP169Reg-74-75,
		gencommP169Reg-76-77,
		gencommP169Reg-78-79,
		gencommP169Reg-80-81,
		gencommP169Reg-82-83,
		gencommP169Reg-84-85,
		gencommP169Reg-86-87,
		gencommP169Reg-88-89,
		gencommP169Reg-90-91,
		gencommP169Reg-92-93,
		gencommP169Reg-94-95,
		gencommP169Reg-96-97,
		gencommP169Reg-98-99,
		gencommP169Reg-100-101,
		gencommP169Reg-102-103,
		gencommP169Reg-104-105,
		gencommP169Reg-106-107,
		gencommP169Reg-108-109,
		gencommP169Reg-110-111,
		gencommP169Reg-112-113,
		gencommP169Reg-114-115,
		gencommP169Reg-116-117,
		gencommP169Reg-118-119,
		gencommP169Reg-120-121,
		gencommP169Reg-122-123,
		gencommP169Reg-124-125,
		gencommP169Reg-126-127,
		gencommP169Reg-128-129,
		gencommP169Reg-130-131,
		gencommP169Reg-132-133,
		gencommP169Reg-134-135,
		gencommP169Reg-136-137,
		gencommP169Reg-138-139,
		gencommP169Reg-140-141,
		gencommP169Reg-142-143,
		gencommP169Reg-144-145,
		gencommP169Reg-146-147,
		gencommP169Reg-148-149,
		gencommP169Reg-150-151,
		gencommP169Reg-152-153,
		gencommP169Reg-154-155,
		gencommP169Reg-156-157,
		gencommP169Reg-158-159,
		gencommP169Reg-160-161,
		gencommP169Reg-162-163,
		gencommP169Reg-164-165,
		gencommP169Reg-166-167,
		gencommP169Reg-168-169,
		gencommP169Reg-170-171,
		gencommP169Reg-172-173,
		gencommP169Reg-174-175,
		gencommP169Reg-176-177,
		gencommP169Reg-178-179,
		gencommP169Reg-180-181,
		gencommP169Reg-182-183,
		gencommP169Reg-184-185,
		gencommP169Reg-186-187,
		gencommP169Reg-188-189,
		gencommP169Reg-190-191,
		gencommP169Reg-192-193,
		gencommP169Reg-194-195,
		gencommP169Reg-196-197,
		gencommP169Reg-198-199,
		gencommP169Reg-200-201,
		gencommP169Reg-202-203,
		gencommP169Reg-204-205,
		gencommP169Reg-206-207,
		gencommP169Reg-208-209,
		gencommP169Reg-210-211,
		gencommP169Reg-212-213,
		gencommP169Reg-214-215,
		gencommP169Reg-216-217,
		gencommP169Reg-218-219,
		gencommP169Reg-220-221,
		gencommP169Reg-222-223,
		gencommP169Reg-224-225,
		gencommP169Reg-226-227,
		gencommP169Reg-228-229,
		gencommP169Reg-230-231,
		gencommP169Reg-232-233,
		gencommP169Reg-234-235,
		gencommP169Reg-236-237,
		gencommP169Reg-238-239,
		gencommP169Reg-240-241,
		gencommP169Reg-242-243,
		gencommP169Reg-244-245,
		gencommP169Reg-246-247,
		gencommP169Reg-248-249,
		gencommP169Reg-250-251,
		gencommP169Reg-252-253,
		gencommP169Reg-254-255
		}
    STATUS  current
    DESCRIPTION
            "A collection of objects providing basic instrumentation
            and control of an SNMP entity."
    ::= { snmpMIBGroups 8 }

keypressGroup OBJECT-GROUP
    OBJECTS {
		keypress
		}
    STATUS  current
    DESCRIPTION
            "A collection of objects providing basic instrumentation
            and control of an SNMP entity."
    ::= { snmpMIBGroups 9 }

trapVarsGroup OBJECT-GROUP
    OBJECTS {
		dse8610SeqNr,
		dse8610TrapID,
		dse8610TrapState,
		dse8610TrapTimeStamp
		}
    STATUS  current
    DESCRIPTION
            "A collection of objects providing basic instrumentation
            and control of an SNMP entity."
    ::= { snmpMIBGroups 10 }

snmpBasicNotificationsGroup NOTIFICATION-GROUP
    NOTIFICATIONS {
		namedAlarmEmergencyStop,
		namedAlarmLowOilPressure,
		namedAlarmHighCoolantTemp,
		namedAlarmLowCoolantTemp,
		namedAlarmUnderSpeed,
		namedAlarmOverSpeed,
		namedAlarmGeneratorUnderFrequency,
		namedAlarmGeneratorOverFrequency,
		namedAlarmGeneratorUnderVolts,
		namedAlarmGeneratorOverVolts,
		namedAlarmBatteryUnderVolts,
		namedAlarmBatteryOverVolts,
		namedAlarmChargeAlternatorFailure,
		namedAlarmFailToStart,
		namedAlarmFailToStop,
		namedAlarmGeneratorFailedToClose,
		namedAlarmMainsFailedToClose,
		namedAlarmOilPressureSensorOpenCircuit,
		namedAlarmLossOfMagPickupSignal,
		namedAlarmMagPickupOpenCircuit,
		namedAlarmGeneratorOverCurrent,
		namedAlarmCalibrationLost,
		namedAlarmLowFuelLevel,
		namedAlarmECUAmber,
		namedAlarmECURed,
		namedAlarmECUDataFail,
		namedAlarmLowOilPressureSwitchAlarm,
		namedAlarmHighTemperatureSwitchAlarm,
		namedAlarmLowFuelSwitchAlarm,
		namedAlarmExpansionUnitWatchdogAlarm,
		namedAlarmkWOverloadAlarm,
		namedAlarmNegativePhaseSequenceAlarm,
		namedAlarmEarthFaultTrip,
		namedAlarmGeneratorPhaseRotationAlarm,
		namedAlarmAutoVoltageSenseFail,
		namedAlarmMaintenanceAlarm,
		namedAlarmFailtoReachLoadingVoltage,
		namedAlarmFuelUsageRunning,
		namedAlarmFuelUsageStopped,
		namedAlarmProtectionsDisabled,
		namedAlarmGeneratorBreakerFailedToOpen,
		namedAlarmMainsBreakerFailedToOpen,
		namedAlarmBusBreakerFailedToClose,
		namedAlarmBusBreakerFailedToOpen,
		namedAlarmGeneratorReversePowerAlarm,
		namedAlarmShortCircuitAlarm,
		namedAlarmAirFlapClosedAlarm,
		namedAlarmFailToSync,
		namedAlarmBusLive,
		namedAlarmBusNotLive,
		namedAlarmBusPhaseRotation,
		namedAlarmPrioritySelectionError,
		namedAlarmMSCDataError,
		namedAlarmMSCIDError,
		namedAlarmBusLowVoltage,
		namedAlarmBusHighVoltage,
		namedAlarmBusLowFrequency,
		namedAlarmBusHighFrequency,
		namedAlarmMSCFailure,
		namedAlarmMSCTooFewSets,
		namedAlarmMSCAlarmsInhibited,
		namedAlarmMSCOldVersionUnitsOnTheBus,
		namedAlarmMainsReversePowerAlarm,
		namedAlarmMinimumSetsNotReached,
		namedAlarmInsufficientCapacity,
		namedAlarmOutOfSync,
		namedAlarmAlternativeAuxMainsFail,
		namedAlarmLossOfExcitation,
		namedAlarmMainsROCOF,
		namedAlarmMainsVectorShift,
		namedAlarmMainsDecouplingLowFrequency,
		namedAlarmMainsDecouplingHighFrequency,
		namedAlarmMainsDecouplingLowVoltage,
		namedAlarmMainsDecouplingHighVoltage,
		namedAlarmMainsDecouplingCombinedAlarm,
		namedAlarmMainsPhaseRotationAlarm,
		namedAlarmAVRMaxTrimLimitAlarm,
		namedAlarmHighCoolantTempElecTripAlarm,
		namedAlarmTempSenderOpenCircuitAlarm,
		namedAlarmFailtoReachLoadingFrequency,
		namedAlarmProtectionsBlocked,
		namedAlarmOutOfSyncBus,
		namedAlarmOutOfSyncMains,
		namedAlarmECUControlledHeaters,
		namedAlarmECUControlledCoolers,
		namedAlarmECUProtect,
		namedAlarmECUMalfunction,
		namedAlarmIndication,
		namedAlarmWaterinFuel,
		namedAlarmHESTActive,
		namedAlarmDPTCFilter,
		namedAlarmHighFuelLevel,
		namedAlarmHeaterSensorFailureAlarm,
		namedAlarmDEFLevelLow,
		namedAlarmSCRInducement,
		namedAlarmInletTemperature,
		namedAlarmElectricalTripStopInhibited,
		namedAlarmFuelTankBundLevelHigh,
		namedAlarmMSCLink1DataError,
		namedAlarmMSCLink2DataError,
		namedAlarmMSCLink1Failure,
		namedAlarmMSCLink2Failure,
		namedAlarmMSCLink1TooFewSets,
		namedAlarmMSCLink2TooFewSets,
		namedAlarmMSCLink1and2Failure,
		namedAlarmElectricalTripfrom8660,
		unnamedAlarmDigitalInputA,
		unnamedAlarmDigitalInputB,
		unnamedAlarmDigitalInputC,
		unnamedAlarmDigitalInputD,
		unnamedAlarmDigitalInputE,
		unnamedAlarmDigitalInputF,
		unnamedAlarmDigitalInputG,
		unnamedAlarmDigitalInputH,
		unnamedAlarmDigitalInputI,
		unnamedAlarmDigitalInputJ,
		unnamedAlarmDigitalInputK,
		unnamedAlarmDigitalInputL,
		unnamedAlarmAnalogueInputBDigital,
		unnamedAlarmAnalogueInputCDigital,
		unnamedAlarmAnalogueInputDDigital,
		unnamedAlarm2130ExpansionModuleID0DigitalInputA,
		unnamedAlarm2130ExpansionModuleID0DigitalInputB,
		unnamedAlarm2130ExpansionModuleID0DigitalInputC,
		unnamedAlarm2130ExpansionModuleID0DigitalInputD,
		unnamedAlarm2130ExpansionModuleID0DigitalInputE,
		unnamedAlarm2130ExpansionModuleID0DigitalInputF,
		unnamedAlarm2130ExpansionModuleID0DigitalInputG,
		unnamedAlarm2130ExpansionModuleID0DigitalInputH,
		unnamedAlarm2130ExpansionModuleID1DigitalInputA,
		unnamedAlarm2130ExpansionModuleID1DigitalInputB,
		unnamedAlarm2130ExpansionModuleID1DigitalInputC,
		unnamedAlarm2130ExpansionModuleID1DigitalInputD,
		unnamedAlarm2130ExpansionModuleID1DigitalInputE,
		unnamedAlarm2130ExpansionModuleID1DigitalInputF,
		unnamedAlarm2130ExpansionModuleID1DigitalInputG,
		unnamedAlarm2130ExpansionModuleID1DigitalInputH,
		unnamedAlarm2130ExpansionModuleID2DigitalInputA,
		unnamedAlarm2130ExpansionModuleID2DigitalInputB,
		unnamedAlarm2130ExpansionModuleID2DigitalInputC,
		unnamedAlarm2130ExpansionModuleID2DigitalInputD,
		unnamedAlarm2130ExpansionModuleID2DigitalInputE,
		unnamedAlarm2130ExpansionModuleID2DigitalInputF,
		unnamedAlarm2130ExpansionModuleID2DigitalInputG,
		unnamedAlarm2130ExpansionModuleID2DigitalInputH,
		unnamedAlarm2130ExpansionModuleID3DigitalInputA,
		unnamedAlarm2130ExpansionModuleID3DigitalInputB,
		unnamedAlarm2130ExpansionModuleID3DigitalInputC,
		unnamedAlarm2130ExpansionModuleID3DigitalInputD,
		unnamedAlarm2130ExpansionModuleID3DigitalInputE,
		unnamedAlarm2130ExpansionModuleID3DigitalInputF,
		unnamedAlarm2130ExpansionModuleID3DigitalInputG,
		unnamedAlarm2130ExpansionModuleID3DigitalInputH,
		unnamedAlarm2131ExpansionModuleID0DigitalInputA,
		unnamedAlarm2131ExpansionModuleID0DigitalInputB,
		unnamedAlarm2131ExpansionModuleID0DigitalInputC,
		unnamedAlarm2131ExpansionModuleID0DigitalInputD,
		unnamedAlarm2131ExpansionModuleID0DigitalInputE,
		unnamedAlarm2131ExpansionModuleID0DigitalInputF,
		unnamedAlarm2131ExpansionModuleID0DigitalInputG,
		unnamedAlarm2131ExpansionModuleID0DigitalInputH,
		unnamedAlarm2131ExpansionModuleID0DigitalInputI,
		unnamedAlarm2131ExpansionModuleID0DigitalInputJ,
		unnamedAlarm2131ExpansionModuleID1DigitalInputA,
		unnamedAlarm2131ExpansionModuleID1DigitalInputB,
		unnamedAlarm2131ExpansionModuleID1DigitalInputC,
		unnamedAlarm2131ExpansionModuleID1DigitalInputD,
		unnamedAlarm2131ExpansionModuleID1DigitalInputE,
		unnamedAlarm2131ExpansionModuleID1DigitalInputF,
		unnamedAlarm2131ExpansionModuleID1DigitalInputG,
		unnamedAlarm2131ExpansionModuleID1DigitalInputH,
		unnamedAlarm2131ExpansionModuleID1DigitalInputI,
		unnamedAlarm2131ExpansionModuleID1DigitalInputJ,
		unnamedAlarm2131ExpansionModuleID2DigitalInputA,
		unnamedAlarm2131ExpansionModuleID2DigitalInputB,
		unnamedAlarm2131ExpansionModuleID2DigitalInputC,
		unnamedAlarm2131ExpansionModuleID2DigitalInputD,
		unnamedAlarm2131ExpansionModuleID2DigitalInputE,
		unnamedAlarm2131ExpansionModuleID2DigitalInputF,
		unnamedAlarm2131ExpansionModuleID2DigitalInputG,
		unnamedAlarm2131ExpansionModuleID2DigitalInputH,
		unnamedAlarm2131ExpansionModuleID2DigitalInputI,
		unnamedAlarm2131ExpansionModuleID2DigitalInputJ,
		unnamedAlarm2131ExpansionModuleID3DigitalInputA,
		unnamedAlarm2131ExpansionModuleID3DigitalInputB,
		unnamedAlarm2131ExpansionModuleID3DigitalInputC,
		unnamedAlarm2131ExpansionModuleID3DigitalInputD,
		unnamedAlarm2131ExpansionModuleID3DigitalInputE,
		unnamedAlarm2131ExpansionModuleID3DigitalInputF,
		unnamedAlarm2131ExpansionModuleID3DigitalInputG,
		unnamedAlarm2131ExpansionModuleID3DigitalInputH,
		unnamedAlarm2131ExpansionModuleID3DigitalInputI,
		unnamedAlarm2131ExpansionModuleID3DigitalInputJ,
		unnamedAlarm2130ExpansionModuleID0AnalogueInputELow,
		unnamedAlarm2130ExpansionModuleID0AnalogueInputEHi,
		unnamedAlarm2130ExpansionModuleID0AnalogueInputFLow,
		unnamedAlarm2130ExpansionModuleID0AnalogueInputFHi,
		unnamedAlarm2130ExpansionModuleID0AnalogueInputGLow,
		unnamedAlarm2130ExpansionModuleID0AnalogueInputGHi,
		unnamedAlarm2130ExpansionModuleID0AnalogueInputHLow,
		unnamedAlarm2130ExpansionModuleID0AnalogueInputHHi,
		unnamedAlarm2130ExpansionModuleID1AnalogueInputELow,
		unnamedAlarm2130ExpansionModuleID1AnalogueInputEHi,
		unnamedAlarm2130ExpansionModuleID1AnalogueInputFLow,
		unnamedAlarm2130ExpansionModuleID1AnalogueInputFHi,
		unnamedAlarm2130ExpansionModuleID1AnalogueInputGLow,
		unnamedAlarm2130ExpansionModuleID1AnalogueInputGHi,
		unnamedAlarm2130ExpansionModuleID1AnalogueInputHLow,
		unnamedAlarm2130ExpansionModuleID1AnalogueInputHHi,
		unnamedAlarm2130ExpansionModuleID2AnalogueInputELow,
		unnamedAlarm2130ExpansionModuleID2AnalogueInputEHi,
		unnamedAlarm2130ExpansionModuleID2AnalogueInputFLow,
		unnamedAlarm2130ExpansionModuleID2AnalogueInputFHi,
		unnamedAlarm2130ExpansionModuleID2AnalogueInputGLow,
		unnamedAlarm2130ExpansionModuleID2AnalogueInputGHi,
		unnamedAlarm2130ExpansionModuleID2AnalogueInputHLow,
		unnamedAlarm2130ExpansionModuleID2AnalogueInputHHi,
		unnamedAlarm2130ExpansionModuleID3AnalogueInputGLow,
		unnamedAlarm2130ExpansionModuleID3AnalogueInputGHi,
		unnamedAlarm2130ExpansionModuleID3AnalogueInputHLow,
		unnamedAlarm2130ExpansionModuleID3AnalogueInputHHi,
		unnamedAlarmFlexibleSensorBLow,
		unnamedAlarmFlexibleSensorBHigh,
		unnamedAlarmFlexibleSensorCLow,
		unnamedAlarmFlexibleSensorCHigh,
		unnamedAlarmFlexibleSensorDLow,
		unnamedAlarmFlexibleSensorDHigh,
		unnamedAlarmMaintenanceAlarm1,
		unnamedAlarmMaintenanceAlarm2,
		unnamedAlarmMaintenanceAlarm3,
		unnamedAlarmPLCAlarm1,
		unnamedAlarmPLCAlarm2,
		unnamedAlarmPLCAlarm3,
		unnamedAlarmPLCAlarm4,
		unnamedAlarmPLCAlarm5,
		unnamedAlarmPLCAlarm6,
		unnamedAlarmPLCAlarm7,
		unnamedAlarmPLCAlarm8,
		unnamedAlarmPLCAlarm9,
		unnamedAlarmPLCAlarm10,
		unnamedAlarmPLCAlarm11,
		unnamedAlarmPLCAlarm12,
		unnamedAlarmPLCAlarm13,
		unnamedAlarmPLCAlarm14,
		unnamedAlarmPLCAlarm15,
		unnamedAlarmPLCAlarm16,
		unnamedAlarmPLCAlarm17,
		unnamedAlarmPLCAlarm18,
		unnamedAlarmPLCAlarm19,
		unnamedAlarmPLCAlarm20,
		unnamedAlarmLowLoad,
		unnamedAlarm2131ExpansionModuleID0AnalogueInputALow,
		unnamedAlarm2131ExpansionModuleID0AnalogueInputAHi,
		unnamedAlarm2131ExpansionModuleID0AnalogueInputBLow,
		unnamedAlarm2131ExpansionModuleID0AnalogueInputBHi,
		unnamedAlarm2131ExpansionModuleID0AnalogueInputCLow,
		unnamedAlarm2131ExpansionModuleID0AnalogueInputCHi,
		unnamedAlarm2131ExpansionModuleID0AnalogueInputDLow,
		unnamedAlarm2131ExpansionModuleID0AnalogueInputDHi,
		unnamedAlarm2131ExpansionModuleID0AnalogueInputELow,
		unnamedAlarm2131ExpansionModuleID0AnalogueInputEHi,
		unnamedAlarm2131ExpansionModuleID0AnalogueInputFLow,
		unnamedAlarm2131ExpansionModuleID0AnalogueInputFHi,
		unnamedAlarm2131ExpansionModuleID0AnalogueInputGLow,
		unnamedAlarm2131ExpansionModuleID0AnalogueInputGHi,
		unnamedAlarm2131ExpansionModuleID0AnalogueInputHLow,
		unnamedAlarm2131ExpansionModuleID0AnalogueInputHHi,
		unnamedAlarm2131ExpansionModuleID0AnalogueInputILow,
		unnamedAlarm2131ExpansionModuleID0AnalogueInputIHi,
		unnamedAlarm2131ExpansionModuleID0AnalogueInputJLow,
		unnamedAlarm2131ExpansionModuleID0AnalogueInputJHi,
		unnamedAlarm2131ExpansionModuleID1AnalogueInputALow,
		unnamedAlarm2131ExpansionModuleID1AnalogueInputAHi,
		unnamedAlarm2131ExpansionModuleID1AnalogueInputBLow,
		unnamedAlarm2131ExpansionModuleID1AnalogueInputBHi,
		unnamedAlarm2131ExpansionModuleID1AnalogueInputCLow,
		unnamedAlarm2131ExpansionModuleID1AnalogueInputCHi,
		unnamedAlarm2131ExpansionModuleID1AnalogueInputDLow,
		unnamedAlarm2131ExpansionModuleID1AnalogueInputDHi,
		unnamedAlarm2131ExpansionModuleID1AnalogueInputELow,
		unnamedAlarm2131ExpansionModuleID1AnalogueInputEHi,
		unnamedAlarm2131ExpansionModuleID1AnalogueInputFLow,
		unnamedAlarm2131ExpansionModuleID1AnalogueInputFHi,
		unnamedAlarm2131ExpansionModuleID1AnalogueInputGLow,
		unnamedAlarm2131ExpansionModuleID1AnalogueInputGHi,
		unnamedAlarm2131ExpansionModuleID1AnalogueInputHLow,
		unnamedAlarm2131ExpansionModuleID1AnalogueInputHHi,
		unnamedAlarm2131ExpansionModuleID1AnalogueInputILow,
		unnamedAlarm2131ExpansionModuleID1AnalogueInputIHi,
		unnamedAlarm2131ExpansionModuleID1AnalogueInputJLow,
		unnamedAlarm2131ExpansionModuleID1AnalogueInputJHi,
		unnamedAlarm2131ExpansionModuleID2AnalogueInputALow,
		unnamedAlarm2131ExpansionModuleID2AnalogueInputAHi,
		unnamedAlarm2131ExpansionModuleID2AnalogueInputBLow,
		unnamedAlarm2131ExpansionModuleID2AnalogueInputBHi,
		unnamedAlarm2131ExpansionModuleID2AnalogueInputCLow,
		unnamedAlarm2131ExpansionModuleID2AnalogueInputCHi,
		unnamedAlarm2131ExpansionModuleID2AnalogueInputDLow,
		unnamedAlarm2131ExpansionModuleID2AnalogueInputDHi,
		unnamedAlarm2131ExpansionModuleID2AnalogueInputELow,
		unnamedAlarm2131ExpansionModuleID2AnalogueInputEHi,
		unnamedAlarm2131ExpansionModuleID2AnalogueInputFLow,
		unnamedAlarm2131ExpansionModuleID2AnalogueInputFHi,
		unnamedAlarm2131ExpansionModuleID2AnalogueInputGLow,
		unnamedAlarm2131ExpansionModuleID2AnalogueInputGHi,
		unnamedAlarm2131ExpansionModuleID2AnalogueInputHLow,
		unnamedAlarm2131ExpansionModuleID2AnalogueInputHHi,
		unnamedAlarm2131ExpansionModuleID2AnalogueInputILow,
		unnamedAlarm2131ExpansionModuleID2AnalogueInputIHi,
		unnamedAlarm2131ExpansionModuleID2AnalogueInputJLow,
		unnamedAlarm2131ExpansionModuleID2AnalogueInputJHi,
		unnamedAlarm2131ExpansionModuleID3AnalogueInputALow,
		unnamedAlarm2131ExpansionModuleID3AnalogueInputAHi,
		unnamedAlarm2131ExpansionModuleID3AnalogueInputBLow,
		unnamedAlarm2131ExpansionModuleID3AnalogueInputBHi,
		unnamedAlarm2131ExpansionModuleID3AnalogueInputCLow,
		unnamedAlarm2131ExpansionModuleID3AnalogueInputCHi,
		unnamedAlarm2131ExpansionModuleID3AnalogueInputDLow,
		unnamedAlarm2131ExpansionModuleID3AnalogueInputDHi,
		unnamedAlarm2131ExpansionModuleID3AnalogueInputELow,
		unnamedAlarm2131ExpansionModuleID3AnalogueInputEHi,
		unnamedAlarm2131ExpansionModuleID3AnalogueInputFLow,
		unnamedAlarm2131ExpansionModuleID3AnalogueInputFHi,
		unnamedAlarm2131ExpansionModuleID3AnalogueInputGLow,
		unnamedAlarm2131ExpansionModuleID3AnalogueInputGHi,
		unnamedAlarm2131ExpansionModuleID3AnalogueInputHLow,
		unnamedAlarm2131ExpansionModuleID3AnalogueInputHHi,
		unnamedAlarm2131ExpansionModuleID3AnalogueInputILow,
		unnamedAlarm2131ExpansionModuleID3AnalogueInputIHi,
		unnamedAlarm2131ExpansionModuleID3AnalogueInputJLow,
		unnamedAlarm2131ExpansionModuleID3AnalogueInputJHi,
		unnamedAlarm2133ExpansionModuleID0AnalogueInputALow,
		unnamedAlarm2133ExpansionModuleID0AnalogueInputAHi,
		unnamedAlarm2133ExpansionModuleID0AnalogueInputBLow,
		unnamedAlarm2133ExpansionModuleID0AnalogueInputBHi,
		unnamedAlarm2133ExpansionModuleID0AnalogueInputCLow,
		unnamedAlarm2133ExpansionModuleID0AnalogueInputCHi,
		unnamedAlarm2133ExpansionModuleID0AnalogueInputDLow,
		unnamedAlarm2133ExpansionModuleID0AnalogueInputDHi,
		unnamedAlarm2133ExpansionModuleID0AnalogueInputELow,
		unnamedAlarm2133ExpansionModuleID0AnalogueInputEHi,
		unnamedAlarm2133ExpansionModuleID0AnalogueInputFLow,
		unnamedAlarm2133ExpansionModuleID0AnalogueInputFHi,
		unnamedAlarm2133ExpansionModuleID0AnalogueInputGLow,
		unnamedAlarm2133ExpansionModuleID0AnalogueInputGHi,
		unnamedAlarm2133ExpansionModuleID0AnalogueInputHLow,
		unnamedAlarm2133ExpansionModuleID0AnalogueInputHHi,
		unnamedAlarm2133ExpansionModuleID1AnalogueInputALow,
		unnamedAlarm2133ExpansionModuleID1AnalogueInputAHi,
		unnamedAlarm2133ExpansionModuleID1AnalogueInputBLow,
		unnamedAlarm2133ExpansionModuleID1AnalogueInputBHi,
		unnamedAlarm2133ExpansionModuleID1AnalogueInputCLow,
		unnamedAlarm2133ExpansionModuleID1AnalogueInputCHi,
		unnamedAlarm2133ExpansionModuleID1AnalogueInputDLow,
		unnamedAlarm2133ExpansionModuleID1AnalogueInputDHi,
		unnamedAlarm2133ExpansionModuleID1AnalogueInputELow,
		unnamedAlarm2133ExpansionModuleID1AnalogueInputEHi,
		unnamedAlarm2133ExpansionModuleID1AnalogueInputFLow,
		unnamedAlarm2133ExpansionModuleID1AnalogueInputFHi,
		unnamedAlarm2133ExpansionModuleID1AnalogueInputGLow,
		unnamedAlarm2133ExpansionModuleID1AnalogueInputGHi,
		unnamedAlarm2133ExpansionModuleID1AnalogueInputHLow,
		unnamedAlarm2133ExpansionModuleID1AnalogueInputHHi,
		unnamedAlarm2133ExpansionModuleID2AnalogueInputALow,
		unnamedAlarm2133ExpansionModuleID2AnalogueInputAHi,
		unnamedAlarm2133ExpansionModuleID2AnalogueInputBLow,
		unnamedAlarm2133ExpansionModuleID2AnalogueInputBHi,
		unnamedAlarm2133ExpansionModuleID2AnalogueInputCLow,
		unnamedAlarm2133ExpansionModuleID2AnalogueInputCHi,
		unnamedAlarm2133ExpansionModuleID2AnalogueInputDLow,
		unnamedAlarm2133ExpansionModuleID2AnalogueInputDHi,
		unnamedAlarm2133ExpansionModuleID2AnalogueInputELow,
		unnamedAlarm2133ExpansionModuleID2AnalogueInputEHi,
		unnamedAlarm2133ExpansionModuleID2AnalogueInputFLow,
		unnamedAlarm2133ExpansionModuleID2AnalogueInputFHi,
		unnamedAlarm2133ExpansionModuleID2AnalogueInputGLow,
		unnamedAlarm2133ExpansionModuleID2AnalogueInputGHi,
		unnamedAlarm2133ExpansionModuleID2AnalogueInputHLow,
		unnamedAlarm2133ExpansionModuleID2AnalogueInputHHi,
		unnamedAlarm2133ExpansionModuleID3AnalogueInputALow,
		unnamedAlarm2133ExpansionModuleID3AnalogueInputAHi,
		unnamedAlarm2133ExpansionModuleID3AnalogueInputBLow,
		unnamedAlarm2133ExpansionModuleID3AnalogueInputBHi,
		unnamedAlarm2133ExpansionModuleID3AnalogueInputCLow,
		unnamedAlarm2133ExpansionModuleID3AnalogueInputCHi,
		unnamedAlarm2133ExpansionModuleID3AnalogueInputDLow,
		unnamedAlarm2133ExpansionModuleID3AnalogueInputDHi,
		unnamedAlarm2133ExpansionModuleID3AnalogueInputELow,
		unnamedAlarm2133ExpansionModuleID3AnalogueInputEHi,
		unnamedAlarm2133ExpansionModuleID3AnalogueInputFLow,
		unnamedAlarm2133ExpansionModuleID3AnalogueInputFHi,
		unnamedAlarm2133ExpansionModuleID3AnalogueInputGLow,
		unnamedAlarm2133ExpansionModuleID3AnalogueInputGHi,
		unnamedAlarm2133ExpansionModuleID3AnalogueInputHLow,
		unnamedAlarm2133ExpansionModuleID3AnalogueInputHHi,
		unnamedAlarm2130ExpansionModuleID3AnalogueInputELow,
		unnamedAlarm2130ExpansionModuleID3AnalogueInputEHi,
		unnamedAlarm2130ExpansionModuleID3AnalogueInputFLow,
		unnamedAlarm2130ExpansionModuleID3AnalogueInputFHi,
		unnamedAlarmAnalogueInputADigital,
		unnamedAlarmFlexibleSensorALow,
		unnamedAlarmFlexibleSensorAHigh,
		unnamedAlarmChargerID0CommonShutdown,
		unnamedAlarmChargerID0CommonWarning,
		unnamedAlarmChargerID1CommonShutdown,
		unnamedAlarmChargerID1CommonWarning,
		unnamedAlarmChargerID2CommonShutdown,
		unnamedAlarmChargerID2CommonWarning,
		unnamedAlarmChargerID3CommonShutdown,
		unnamedAlarmChargerID3CommonWarning,
		notifModeChange,
		notifModuleRestart,
		notifEngineStarts,
		notifEngineStops,
		notifMainsFail,
		notifMainsReturn,
		notifECUlampProtect,
		notifECUlampMalfunction,
		notifECUlampShutdown,
		notifECUlampWarning,
		notifLevelStatusMonitoring
		}
    STATUS  current
    DESCRIPTION
            "A collection of objects providing basic instrumentation
            and control of an SNMP entity."
    ::= { snmpMIBGroups 11 }

END
