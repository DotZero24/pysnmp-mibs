RAD-Sonet-MIB DEFINITIONS ::= BEGIN


-- It is RAD's intent to encourage the widespread use of
-- this Specification in connection with the management of
-- RAD products. RAD grants vendors, end-users,
-- and other interested parties a non-exclusive license to
-- use this Specification in connection with the management
-- of RAD products.

-- This Specification is supplied "as is," and RAD makes
-- no warranty, either express or implied, as to the use,
-- operation, condition, or performance of the Specification.


IMPORTS

       InterfaceIndex, ifAlias, ifIndex     FROM  IF-MIB
       PerfCurrentCount, PerfIntervalCount     FROM  PerfHist-TC-MIB
       SnmpAdminString     FROM  SNMP-FRAMEWORK-MIB
       Integer32, Counter32, IpAddress,
       Gauge32, Unsigned32, OBJECT-TYPE,
       MODULE-IDENTITY, NOTIFICATION-TYPE     FROM  SNMPv2-SMI
       RowStatus, DateAndTime, TruthValue     FROM  SNMPv2-TC
       sonetSectionCurrentESs, sonetSectionCurrentSESs, sonetSectionCurrentSEFSs,
       sonetSectionCurrentCVs, sonetLineCurrentESs, sonetLineCurrentSESs,
       sonetLineCurrentCVs, sonetLineCurrentUASs, sonetMediumLoopbackConfig     FROM  SONET-MIB
       diverseIfWanGen     FROM  RAD-SMI-MIB
       DayType, ProtectLastSwitchReasonType     FROM  RAD-TC
       alarmEventLogSourceName, alarmEventLogAlarmOrEventId, alarmEventLogDescription,
       alarmEventLogSeverity, alarmEventLogDateAndTime, alarmEventReason     FROM  RAD-GEN-MIB
       protectGroupLastSwitchReason, protectGroupLastCmd     FROM  RAD-Protection-MIB;


    sonetInterface MODULE-IDENTITY
        LAST-UPDATED "201605151808Z"  -- May 15, 2016
        ORGANIZATION "RAD Data Communications Ltd."
        CONTACT-INFO
        "System Department

         Email:  mibs@rad.com
         Postal: RAD Data Communications Ltd.
                 24 Raoul Wallenberg St.
                 Tel-Aviv 6971920
                 Israel

         Phone:  +972-3-645-5421
         Fax:    +972-3-760-7844"
         DESCRIPTION
            "SONET MIB."
    ::= { diverseIfWanGen 2 }


-- sonetInterface  OBJECT IDENTIFIER  ::=  {diverseIfWanGen 2}

prtSonetEvents       OBJECT IDENTIFIER  ::=  {sonetInterface 0}
prtSonetPerfHistory  OBJECT IDENTIFIER  ::=  {sonetInterface 1}


-- The SONET Medium Table

prtSonetMediumTable OBJECT-TYPE
    SYNTAX  SEQUENCE OF PrtSonetMediumEntry
    MAX-ACCESS  not-accessible
    STATUS  current
    DESCRIPTION
            "The SONET Medium table."
    ::= { prtSonetPerfHistory 1 }

prtSonetMediumEntry OBJECT-TYPE
    SYNTAX  PrtSonetMediumEntry
    MAX-ACCESS  not-accessible
    STATUS  current
    DESCRIPTION
            "An entry in the SONET Medium table. ifIndex of the
             lowest SONET layer of type sonet(39)."
    INDEX   { ifIndex }
    ::= { prtSonetMediumTable 1 }

PrtSonetMediumEntry ::=
    SEQUENCE {
        prtSonetMediumTimeElapsed
            Integer32,
        prtSonetMediumValidIntervals
            Integer32,
		prtSonetMediumSsmRX
		    OCTET STRING,
		prtSonetMediumSsmTX
		    OCTET STRING
           }

prtSonetMediumTimeElapsed OBJECT-TYPE
     SYNTAX  Integer32 (0..899)
     MAX-ACCESS  read-only
     STATUS  current
     DESCRIPTION
     "The number of seconds that have elapsed since
     the beginning of the near end current error-
     measurement period."
    ::= { prtSonetMediumEntry 1 }

prtSonetMediumValidIntervals OBJECT-TYPE
     SYNTAX  Integer32 (0..96)
     MAX-ACCESS  read-only
     STATUS  current
     DESCRIPTION
     "The number of previous near end intervals for
     which valid data was collected.  The value will be
     96 unless the interface was brought online within
     the last 24 hours, in which case the value will be
     the number of complete 15 minute near end
     intervals since the interface has been online."
    ::= { prtSonetMediumEntry 2 }

prtSonetMediumSsmRX OBJECT-TYPE
     SYNTAX  OCTET STRING	(SIZE (1))
     MAX-ACCESS  read-only
     STATUS  current
     DESCRIPTION
     "This parameter indicates SSM RX value (quality level of clock signal).
      SSM (Synchronization Status Messages) octet is encoded as follows:
	  Bit1 = '1' - indicates all octet is Not Applicable
	  Bits 8-5 (when bit1=0):
	  Left is MSB, where - MSB(8) ---> LSB(5)
	  8765
	  0000	Quality Unknown
	  0001  PRS (Stratum 1 Traceable)
      0010	PRC (Primary Reference Clock)    - Rec. G.811
      0100	SSU-T (Sync. Source Unit-Transit)- Rec. G.812 Transit for SDH
	        TNC (Transit Node Clock Traceable) - for SONET
	  0111  ST2 (Stratum 2 Traceable)
      1000	SSU-L (Sync. Source Unit Local)	 - Rec. G.812 Local
	  1010  ST3 (Stratum 3 Traceable)
      1011	SEC (SDH Equipment Clock)
	  1100  SMC (SONET Minimum Clock Traceable)
	  1101  STS3E (Stratum 3E Traceable)
      1111	DNU (do not use for synchronization) "
    ::= {prtSonetMediumEntry 3}

prtSonetMediumSsmTX OBJECT-TYPE
     SYNTAX  OCTET STRING	(SIZE (1))
     MAX-ACCESS  read-only
     STATUS  current
     DESCRIPTION
     "This parameter indicates SSM TX value (quality level of clock signal).
      SSM (Synchronization Status Messages) octet is encoded the same as
      prtSonetMediumSsmRX."
    ::= {prtSonetMediumEntry 4}


-- The SONET Section/Line Current   Table

-- The SONET Section/Line Current table contains various statistics being
-- collected for the current 15 minute interval.

prtSonetSectionLineCurrentTable OBJECT-TYPE
    SYNTAX  SEQUENCE OF PrtSectionLineCurrentEntry
    MAX-ACCESS  not-accessible
    STATUS  current
    DESCRIPTION
            "The SONET Section/Line Current table."
    ::= { prtSonetPerfHistory 2 }

prtSectionLineCurrentEntry OBJECT-TYPE
    SYNTAX  PrtSectionLineCurrentEntry
    MAX-ACCESS  not-accessible
    STATUS  current
    DESCRIPTION
            "An entry in the SONET Section/Line Current table.
             ifIndex of the section/line SONET layer of IANAifType
             sonet(39)."
    INDEX   { ifIndex }
    ::= { prtSonetSectionLineCurrentTable 1 }

PrtSectionLineCurrentEntry ::= SEQUENCE {
    prtSonetCurrentLOS                  Gauge32,
    prtSonetCurrentLOF                  Gauge32,
    prtSonetCurrentLineAIS              Gauge32,
    prtSonetCurrentLineFERF             Gauge32,
    prtSonetCurrentSectionBIP           Gauge32,
    prtSonetCurrentLineBIP              Gauge32,
    prtSonetCurrentLineFEBE             Gauge32,
    prtSonetCurrentUAS                  Gauge32,
    prtSonetCurrentSES                  Gauge32,
    prtSonetCurrentES                   Gauge32,
    prtSonetCurrentStatus               OCTET STRING,
    prtSonetCurrentLSV                  Gauge32,
    prtSonetCurrentXStatus              Integer32,
    prtSonetCurrentLineRDI              Gauge32
 }

prtSonetCurrentLOS OBJECT-TYPE
    SYNTAX  Gauge32
    MAX-ACCESS  read-only
    STATUS  current
    DESCRIPTION
            "The counter associated with the number of LOS
             seconds, encountered by a SONET interface in
            the current 15 minute interval."
    ::= { prtSectionLineCurrentEntry 1 }

prtSonetCurrentLOF OBJECT-TYPE
    SYNTAX  Gauge32
    MAX-ACCESS  read-only
    STATUS  current
    DESCRIPTION
            "The counter associated with the number of LOF
             seconds, encountered by a SONET
             interface in the current 15 minute interval."
    ::= { prtSectionLineCurrentEntry 2 }

prtSonetCurrentLineAIS OBJECT-TYPE
    SYNTAX  Gauge32
    MAX-ACCESS  read-only
    STATUS  current
    DESCRIPTION
            "The counter associated with the number of Line AIS
            seconds, encountered by a SONET
            interface in the current 15 minute interval."
    ::= { prtSectionLineCurrentEntry 3 }

prtSonetCurrentLineFERF OBJECT-TYPE
    SYNTAX  Gauge32
    MAX-ACCESS  read-only
    STATUS  current
    DESCRIPTION
            "The counter associated with the number of Line
            FERF seconds, encountered by a SONET
            interface in the current 15 minute interval."
    ::= { prtSectionLineCurrentEntry 4 }

prtSonetCurrentSectionBIP OBJECT-TYPE
    SYNTAX  Gauge32
    MAX-ACCESS  read-only
    STATUS  current
    DESCRIPTION
            "The counter associated with the number of Section
            BIP errors, encountered by a SONET
            interface in the current 15 minute interval."
    ::= { prtSectionLineCurrentEntry 5 }

prtSonetCurrentLineBIP OBJECT-TYPE
    SYNTAX  Gauge32
    MAX-ACCESS  read-only
    STATUS  current
    DESCRIPTION
            "The counter associated with the number of Line
            BIP errors, encountered by a SONET
            interface in the current 15 minute interval."
    ::= { prtSectionLineCurrentEntry 6 }

prtSonetCurrentLineFEBE OBJECT-TYPE
    SYNTAX  Gauge32
    MAX-ACCESS  read-only
    STATUS  current
    DESCRIPTION
            "The counter associated with the number of Line
            FEBE errors, encountered by a SONET
            interface in the current 15 minute interval."
    ::= { prtSectionLineCurrentEntry 7 }

prtSonetCurrentUAS OBJECT-TYPE
    SYNTAX  Gauge32
    MAX-ACCESS  read-only
    STATUS  current
    DESCRIPTION
            "The counter associated with the number of UAS
             encountered by a SONET
             interface in the current 15 minute interval."
    ::= { prtSectionLineCurrentEntry 8 }

prtSonetCurrentSES OBJECT-TYPE
    SYNTAX  Gauge32
    MAX-ACCESS  read-only
    STATUS  current
    DESCRIPTION
            "The counter associated with the number of SES
             encountered by a SONET
             interface in the current 15 minute interval."
    ::= { prtSectionLineCurrentEntry 9 }

prtSonetCurrentES OBJECT-TYPE
    SYNTAX Gauge32
    MAX-ACCESS  read-only
    STATUS  current
    DESCRIPTION
            "The number of Errored Seconds, encountered  by a
              SONET interface in the current 15 minute interval."
    ::= { prtSectionLineCurrentEntry 10 }

prtSonetCurrentStatus OBJECT-TYPE
    SYNTAX OCTET STRING  (SIZE (4))
    MAX-ACCESS  read-only
    STATUS  current
    DESCRIPTION
            "The statuses of the current interval:
              0 - O.K.
              1 - The link has been switched by a redundancy mechanism.
              2 - Module is in/out.
              4 - Empty - card is out."
    ::= { prtSectionLineCurrentEntry 11 }

prtSonetCurrentLSV OBJECT-TYPE
    SYNTAX  Gauge32
    MAX-ACCESS  read-only
    STATUS  current
    DESCRIPTION
             "The counter associated with the number of LSV
              seconds (Line Symbol Violation), encountered by a
              SONET interface in the current 15 minute interval."
    ::= { prtSectionLineCurrentEntry 12 }

prtSonetCurrentXStatus OBJECT-TYPE
    SYNTAX      Integer32
    MAX-ACCESS  read-only
    STATUS      current
    DESCRIPTION
            "This variable indicates the Status of the interface.
            It contains failure state information.
            The variable is a bit map represented as a sum, therefore,
            it can represent multiple failures simultaneously.
            The sonetSectionLineNoDefect must be set if and only if no
            other flag is set.
            The various bit positions are:
                1    sonetSectionLineNoDefect
                2    sonetSectionLOS  Loss Of Signal
                4    sonetSectionLOF  Loss Of Frame
                8    sonetSectionLOC  Loss Of Clock
                16   sonetLineAIS     Alarm Indication Signal
                32   sonetLineRDI     Remote Defect Indication
                64   sonetLineRFI     Remote Failure Indication
                     (RDI lasts for 2.5 (+-0.5) seconds)
                128  sonetLineEBER    Excessive Bit Error Rate (i.e.EED)
                256  sonetLineSD      Signal Degradation
                512  sonetOOF         Out Of Frame
                1024 sonetSectionTIM  Trace Identifier Mismatch"
    ::= { prtSectionLineCurrentEntry 13 }

prtSonetCurrentLineRDI  OBJECT-TYPE
    SYNTAX  Gauge32
    MAX-ACCESS  read-only
    STATUS  current
    DESCRIPTION
            "The counter associated with the number of Line RDI
            seconds, encountered by a SONET
            interface in the current 15 minute interval."
    ::= { prtSectionLineCurrentEntry 14 }


 -- The SONET Section/Line interface Interval

 -- The SONET Section/Line Interval Table contains various statistics
 -- collected by the Interface over the previous 24
 -- hours of operation.  The past 24 hours are broken into 96
 -- completed 15 minute intervals.

prtSonetSectionLineIntervalTable OBJECT-TYPE
    SYNTAX  SEQUENCE OF PrtSectionLineIntervalEntry
    MAX-ACCESS  not-accessible
    STATUS  current
    DESCRIPTION
             "The Section/Line Interval table."
    ::= { prtSonetPerfHistory 3 }

prtSectionLineIntervalEntry OBJECT-TYPE
    SYNTAX      PrtSectionLineIntervalEntry
    MAX-ACCESS  not-accessible
    STATUS      current
    DESCRIPTION
            "An entry in the SONET Section/Line Interval table.
            ifIndex of the section/line SONET layer of IANAifType
            sonet(39)."
    INDEX   { ifIndex, prtSonetLineIntervalNumber }
    ::= { prtSonetSectionLineIntervalTable 1 }

PrtSectionLineIntervalEntry ::= SEQUENCE {
    prtSonetLineIntervalNumber          Integer32,
    prtSonetIntervalLOS                 Gauge32,
    prtSonetIntervalLOF                 Gauge32,
    prtSonetIntervalLineAIS             Gauge32,
    prtSonetIntervalLineFERF            Gauge32,
    prtSonetIntervalSectionBIP          Gauge32,
    prtSonetIntervalLineBIP             Gauge32,
    prtSonetIntervalLineFEBE            Gauge32,
    prtSonetIntervalUAS                 Gauge32,
    prtSonetIntervalSES                 Gauge32,
    prtSonetIntervalES                  Gauge32,
    prtSonetIntervalStatus              OCTET STRING,
    prtSonetIntervalLSV                 Gauge32,
    prtSonetIntervalLineRDI             Gauge32,
    prtSonetIntervalSectionTimeElapsed  Integer32,
    prtSonetIntervalFC                  PerfIntervalCount,
    prtSonetIntervalFarEndFC            PerfIntervalCount
 }

prtSonetLineIntervalNumber OBJECT-TYPE
    SYNTAX  Integer32 (1..96)
    MAX-ACCESS  read-only
    STATUS  current
    DESCRIPTION
            "A number between 1 and 96, where 1 is the most
            recently completed 15 minute interval and 96 is
            the least recently completed 15 minutes interval
            (assuming that all 96 intervals are valid)."
    ::= { prtSectionLineIntervalEntry 1 }

prtSonetIntervalLOS OBJECT-TYPE
    SYNTAX  Gauge32
    MAX-ACCESS  read-only
    STATUS  current
    DESCRIPTION
            "The counter associated with the number of LOS
            seconds , encountered by a SONET interface in
            one of the previous 15 minute
            intervals."
    ::= { prtSectionLineIntervalEntry 2 }

prtSonetIntervalLOF OBJECT-TYPE
    SYNTAX  Gauge32
    MAX-ACCESS  read-only
    STATUS  current
    DESCRIPTION
            "The counter associated with the number of LOF
            seconds, encountered by a SONET
            interface in one of the previous 15
            minute, intervals."
    ::= { prtSectionLineIntervalEntry 3 }

prtSonetIntervalLineAIS OBJECT-TYPE
    SYNTAX  Gauge32
    MAX-ACCESS  read-only
    STATUS  current
    DESCRIPTION
           "The counter associated with the number of Line
           AIS seconds, encountered by a SONET/SDH
           interface in one of
           individual 15 minute, intervals."
   ::= { prtSectionLineIntervalEntry 4 }

prtSonetIntervalLineFERF OBJECT-TYPE
    SYNTAX  Gauge32
    MAX-ACCESS  read-only
    STATUS  current
    DESCRIPTION
            "The counter associated with the number of Line
            FERF seconds, encountered by a SONET/SDH
            interface in one of the previous 15 minute intervals."
    ::= { prtSectionLineIntervalEntry 5 }

prtSonetIntervalSectionBIP OBJECT-TYPE
    SYNTAX  Gauge32
    MAX-ACCESS  read-only
    STATUS  current
    DESCRIPTION
            "The counter associated with the number of Section
            BIP errors, encountered by a SONET/SDH
            interface in one of the previous 15 minute intervals."
    ::= { prtSectionLineIntervalEntry 6 }

prtSonetIntervalLineBIP OBJECT-TYPE
    SYNTAX  Gauge32
    MAX-ACCESS  read-only
    STATUS  current
    DESCRIPTION
            "The counter associated with the number of Line
            BIP errors, encountered by a SONET/SDH
            interface in one of the previous 15 minute intervals."
    ::= { prtSectionLineIntervalEntry 7 }

prtSonetIntervalLineFEBE OBJECT-TYPE
    SYNTAX  Gauge32
    MAX-ACCESS  read-only
    STATUS  current
    DESCRIPTION
            "The counter associated with the number of Line
            FEBE errors, encountered by a SONET/SDH
            interface in one of the previous 15 minute intervals."
    ::= { prtSectionLineIntervalEntry 8 }

prtSonetIntervalUAS OBJECT-TYPE
    SYNTAX  Gauge32
    MAX-ACCESS  read-only
    STATUS  current
    DESCRIPTION
            "The counter associated with the number of UnAvailable
            Seconds encountered by a SONET/SDH interface in one of the
            previous 15 minute intervals."
    ::= { prtSectionLineIntervalEntry 9 }

prtSonetIntervalSES OBJECT-TYPE
    SYNTAX  Gauge32
    MAX-ACCESS  read-only
    STATUS  current
    DESCRIPTION
            "The counter associated with the number of Severely Errored
            Seconds encountered by a SONET/SDH interface in one of the
            previous 15 minute intervals."
    ::= { prtSectionLineIntervalEntry 10 }

prtSonetIntervalES OBJECT-TYPE
    SYNTAX Gauge32
    MAX-ACCESS  read-only
    STATUS current
    DESCRIPTION
            "The number of Errored Seconds encountered  by a
            SONET/SDH interface in one of the previous 15
            minute intervals."
    ::= { prtSectionLineIntervalEntry 11 }

prtSonetIntervalStatus OBJECT-TYPE
    SYNTAX OCTET STRING  (SIZE (4))
    MAX-ACCESS  read-only
    STATUS  current
    DESCRIPTION
             " The statuses of the current interval:
               0 - O.K.
               1 - The link has been switched by a redundancy mechanism.
               2 - Module is in/out.
               4 - Empty - card is out."
    ::= { prtSectionLineIntervalEntry 12 }

prtSonetIntervalLSV OBJECT-TYPE
    SYNTAX  Gauge32
    MAX-ACCESS  read-only
    STATUS  current
    DESCRIPTION
             "The counter associated with the number of LSV seconds
             (Line Symbol Violation), encountered by a SONET/SDH
             interface in one of the previous 15 minute intervals."
    ::= { prtSectionLineIntervalEntry 13 }

prtSonetIntervalLineRDI OBJECT-TYPE
    SYNTAX  Gauge32
    MAX-ACCESS  read-only
    STATUS  current
    DESCRIPTION
           "The counter associated with the number of Line RDI seconds
           encountered by a SONET/SDH interface in one of the previous
           15 minute intervals."
   ::= { prtSectionLineIntervalEntry 14 }

prtSonetIntervalSectionTimeElapsed OBJECT-TYPE
    SYNTAX      Integer32 (1..900)
    MAX-ACCESS  read-only
    STATUS      current
    DESCRIPTION
            "The object contains duration in seconds of the interval
            measurement period. The partial second is counted."
    ::= { prtSectionLineIntervalEntry 15 }

prtSonetIntervalFC OBJECT-TYPE
    SYNTAX      PerfIntervalCount
    MAX-ACCESS  read-only
    STATUS      current
    DESCRIPTION
            "The counter associated with the number of Failure Counts
            encountered by a SONET interface in one of the previous
            15 minute intervals. It is not defined at the Section level."
    ::= { prtSectionLineIntervalEntry 16 }

prtSonetIntervalFarEndFC OBJECT-TYPE
    SYNTAX      PerfIntervalCount
    MAX-ACCESS  read-only
    STATUS      current
    DESCRIPTION
            "The counter associated with the number of Failure Counts
            encountered by a Far End SONET interface in one of the
            previous 15 minute intervals. It is not defined at the
            Section level."
    ::= { prtSectionLineIntervalEntry 17 }


-- The SONET Path Current Table

-- The SONET Path Current table contains various statistics being
-- collected for the current 15 minute interval.

prtSonetPathCurrentTable OBJECT-TYPE
    SYNTAX      SEQUENCE OF PrtPathCurrentEntry
    MAX-ACCESS  not-accessible
    STATUS      current
    DESCRIPTION
            "The SONET Path Current table."
    ::= { prtSonetPerfHistory 4 }

prtPathCurrentEntry OBJECT-TYPE
    SYNTAX  PrtPathCurrentEntry
    MAX-ACCESS  not-accessible
    STATUS  current
    DESCRIPTION
            "An entry in the SONET Path Current table.
            ifIndex of the Path SONET layer of IANAifType
            sonetPath(50)."
    INDEX   { ifIndex }
    ::= { prtSonetPathCurrentTable 1 }

PrtPathCurrentEntry ::= SEQUENCE {
    prtSonetCurrentPathAIS      Gauge32,
    prtSonetCurrentPathFERF     Gauge32,
    prtSonetCurrentLOP          Gauge32,
    prtSonetCurrentSLM          Gauge32,
    prtSonetCurrentLOC          Gauge32,
    prtSonetCurrentPathBIP      Gauge32,
    prtSonetCurrentPathFEBE     Gauge32,
    prtSonetPathCurrentStatus   Integer32,
    prtSonetCurrentPathRDI      Gauge32
 }

prtSonetCurrentPathAIS OBJECT-TYPE
    SYNTAX      Gauge32
    MAX-ACCESS  read-only
    STATUS      current
    DESCRIPTION
            "The counter associated with the number of Path AIS
             seconds, encountered by a SONET interface in
            the current 15 minute interval."
    ::= { prtPathCurrentEntry 1 }

prtSonetCurrentPathFERF OBJECT-TYPE
    SYNTAX  Gauge32
    MAX-ACCESS  read-only
    STATUS  current
    DESCRIPTION
            "The counter associated with the number of Path FERF
             seconds, encountered by a SONET
             interface in the current 15 minute interval."
    ::= { prtPathCurrentEntry 2 }

prtSonetCurrentLOP OBJECT-TYPE
    SYNTAX  Gauge32
    MAX-ACCESS  read-only
    STATUS  current
    DESCRIPTION
            "The counter associated with the number LOP
            seconds, encountered by a SONET
            interface in the current 15 minute interval."
    ::= { prtPathCurrentEntry 3 }

prtSonetCurrentSLM OBJECT-TYPE
    SYNTAX  Gauge32
    MAX-ACCESS  read-only
    STATUS  current
    DESCRIPTION
            "The counter associated with the number of SLM
             seconds, encountered by a SONET
             interface in the current 15 minute interval."
    ::= { prtPathCurrentEntry 4 }

prtSonetCurrentLOC OBJECT-TYPE
    SYNTAX  Gauge32
    MAX-ACCESS  read-only
    STATUS  current
    DESCRIPTION
            "The counter associated with the number of LOC
            seconds, encountered by a SONET
            interface in the current 15 minute interval."
    ::= { prtPathCurrentEntry 5 }

prtSonetCurrentPathBIP OBJECT-TYPE
    SYNTAX  Gauge32
    MAX-ACCESS  read-only
    STATUS  current
    DESCRIPTION
            "The counter associated with the number of Path
            BIP errors, encountered by a SONET
            interface in the current 15 minute interval."
    ::= { prtPathCurrentEntry 6 }

prtSonetCurrentPathFEBE OBJECT-TYPE
    SYNTAX  Gauge32
    MAX-ACCESS  read-only
    STATUS  current
    DESCRIPTION
            "The counter associated with the number of Path
            FEBE errors, encountered by a SONET
            interface in the current 15 minute interval."
    ::= { prtPathCurrentEntry 7 }

prtSonetPathCurrentStatus OBJECT-TYPE
    SYNTAX      Integer32
    MAX-ACCESS  read-only
    STATUS      current
    DESCRIPTION
            "This variable indicates the Status of the interface.
            It contains failure state information.
            The variable is a bit map represented as a sum, therefore,
            it can represent multiple failures simultaneously.
            The sonetPathNoDefect must be set if and only if no other
            flag is set.

            The various bit positions are:
            1   sonetPathNoDefect
            2   sonetPathSTSLOP              Loss Of Pointer
            4   sonetPathSTSAIS              Alarm Indication Signal
            8   sonetPathSTSRDI              Remote Defect Indication
           16   sonetPathUnequipped          Signal Label Unequipped
           32   sonetPathSignalLabelMismatch Signal Label Mismatch
           64   sonetPathRFI                 Remote Failure Indication
                                    (RDI lasts for 2.5 (+-0.5) seconds)
          128   sonetPathEBER                Excessive Bit Error Rate
          256   sonetPathSD                  Signal Degradation
          512   sonetPathLOM                 Loss Of Multiframe
         1024   sonetSectionTIM              Trace Identifier Mismatch"
    ::= { prtPathCurrentEntry 8 }

prtSonetCurrentPathRDI OBJECT-TYPE
    SYNTAX      Gauge32
    MAX-ACCESS  read-only
    STATUS      current
    DESCRIPTION
            "The counter associated with the number of Path RDI
             seconds, encountered by a SONET interface in
             the current 15 minute interval."
    ::= { prtPathCurrentEntry 9 }


-- The SONET Path interface Interval

-- The SONET Path Interval Table contains various statistics
-- collected by the Interface over the previous 24
-- hours of operation.  The past 24 hours are broken into 96
-- completed 15 minute intervals.

prtSonetPathIntervalTable OBJECT-TYPE
    SYNTAX SEQUENCE OF PrtPathIntervalEntry
    MAX-ACCESS  not-accessible
    STATUS      current
    DESCRIPTION
            "The Path Interval table."
    ::= { prtSonetPerfHistory 5 }

prtPathIntervalEntry OBJECT-TYPE
    SYNTAX      PrtPathIntervalEntry
    MAX-ACCESS  not-accessible
    STATUS      current
    DESCRIPTION
            "An entry in the SONET Path Interval table."
    INDEX   { ifIndex, prtSonetPathIntervalNumber }
    ::= { prtSonetPathIntervalTable 1 }

PrtPathIntervalEntry ::= SEQUENCE {
    prtSonetPathIntervalNumber   Integer32,
    prtSonetIntervalPathAIS      Gauge32,
    prtSonetIntervalPathFERF     Gauge32,
    prtSonetIntervalLOP          Gauge32,
    prtSonetIntervalSLM          Gauge32,
    prtSonetIntervalLOC          Gauge32,
    prtSonetIntervalPathBIP      Gauge32,
    prtSonetIntervalPathFEBE     Gauge32,
    prtSonetIntervalPathRDI      Gauge32
 }

prtSonetPathIntervalNumber OBJECT-TYPE
    SYNTAX      Integer32 (1..96)
    MAX-ACCESS  read-only
    STATUS      current
    DESCRIPTION
            "A number between 1 and 96, where 1 is the most
            recently completed 15 minute interval and 96 is
            the least recently completed 15 minutes interval
            (assuming that all 96 intervals are valid)."
    ::= { prtPathIntervalEntry 1 }

prtSonetIntervalPathAIS OBJECT-TYPE
    SYNTAX  Gauge32
    MAX-ACCESS  read-only
    STATUS  current
    DESCRIPTION
            "The counter associated with the number of Path
            AIS seconds, encountered by a SONET Path interface in
            one of the previous 96, individual 15 minute
            intervals."
    ::= { prtPathIntervalEntry 2 }

prtSonetIntervalPathFERF OBJECT-TYPE
    SYNTAX  Gauge32
    MAX-ACCESS  read-only
    STATUS  current
    DESCRIPTION
            "The counter associated with the number of Path FERF seconds
            encountered by a SONET Path interface in one of the previous
            96, individual 15 minute intervals."
    ::= { prtPathIntervalEntry 3 }

prtSonetIntervalLOP OBJECT-TYPE
    SYNTAX  Gauge32
    MAX-ACCESS  read-only
    STATUS  current
    DESCRIPTION
            "The counter associated with the number of LOP seconds
            encountered by a SONET Path interface in one of the previous
            96, individual 15 minute intervals."
    ::= { prtPathIntervalEntry 4 }

prtSonetIntervalSLM OBJECT-TYPE
    SYNTAX  Gauge32
    MAX-ACCESS  read-only
    STATUS  current
    DESCRIPTION
            "The counter associated with the number of SLM seconds,
            encountered by a SONET Path interface in one of the previous
            96, individual 15 minute intervals."
    ::= { prtPathIntervalEntry 5 }

prtSonetIntervalLOC OBJECT-TYPE
    SYNTAX  Gauge32
    MAX-ACCESS  read-only
    STATUS  current
    DESCRIPTION
            "The counter associated with the number of LOC seconds,
            encountered by a SONET Path interface in one of the previous
            96, individual 15 minute intervals."
    ::= { prtPathIntervalEntry 6 }

prtSonetIntervalPathBIP OBJECT-TYPE
    SYNTAX  Gauge32
    MAX-ACCESS  read-only
    STATUS  current
    DESCRIPTION
            "The counter associated with the number of Path BIP errors,
            encountered by a SONET Path interface in one of the previous
            96, individual 15 minute intervals."
    ::= { prtPathIntervalEntry 7 }

prtSonetIntervalPathFEBE OBJECT-TYPE
    SYNTAX  Gauge32
    MAX-ACCESS  read-only
    STATUS  current
    DESCRIPTION
            "The counter associated with the number of Path FEBE errors,
            encountered by a SONET Path interface in one of the previous
            96, individual 15 minute intervals."
    ::= { prtPathIntervalEntry 8 }

prtSonetIntervalPathRDI OBJECT-TYPE
    SYNTAX  Gauge32
    MAX-ACCESS  read-only
    STATUS  current
    DESCRIPTION
            "The counter associated with the number of Path RDI seconds,
            encountered by a SONET Path interface in one of the previous
            96, individual 15 minute intervals."
    ::= { prtPathIntervalEntry 9 }


virtualIfStatistics  OBJECT IDENTIFIER  ::=  { prtSonetPerfHistory 6}

-- the Virtual Interface Current Table

virtualIfCurrentTable OBJECT-TYPE
    SYNTAX  SEQUENCE OF VirtualIfCurrentEntry
    MAX-ACCESS  not-accessible
    STATUS  current
    DESCRIPTION
       "The Virtual Interface Current table."
    ::= { virtualIfStatistics 1 }

virtualIfCurrentEntry OBJECT-TYPE
    SYNTAX  VirtualIfCurrentEntry
    MAX-ACCESS  not-accessible
    STATUS  current
    DESCRIPTION
       "An entry in the Virtual Interface Current table."
    INDEX   { ifIndex  }
    ::= { virtualIfCurrentTable 1 }

VirtualIfCurrentEntry ::= SEQUENCE {
    virtualIfCurrentMinActiveVC               Integer32,
    virtualIfCurrentMaxActiveVC               Integer32,
    virtualIfCurrentRxFrames                  Counter32,
    virtualIfCurrentTxFrames                  Counter32,
    virtualIfCurrentRxAbortFrames             PerfCurrentCount,
    virtualIfCurrentTxAbortFrames             PerfCurrentCount,
    virtualIfCurrentMinLengthViolation        PerfCurrentCount,
    virtualIfCurrentMaxLengthViolation        PerfCurrentCount,
    virtualIfCurrentFcsError                  PerfCurrentCount,
    virtualIfCurrentByteDestuffingViolation   PerfCurrentCount,
    virtualIfCurrentAdressMismatch            PerfCurrentCount,
    virtualIfCurrentControlMismatch           PerfCurrentCount,
    virtualIfCurrentActiveVC                  Integer32
 }

virtualIfCurrentMinActiveVC OBJECT-TYPE
    SYNTAX  Integer32 (1..63)
    MAX-ACCESS  read-only
    STATUS  current
    DESCRIPTION
       "This object holds the minimum number of active virtual containers (VCs)
        of the Virtual Concatenation Group in the current 15-minute interval."
     ::= { virtualIfCurrentEntry 1 }

 virtualIfCurrentMaxActiveVC OBJECT-TYPE
    SYNTAX  Integer32 (1..63)
    MAX-ACCESS  read-only
    STATUS  current
    DESCRIPTION
       "This object holds the maximum number of active virtual containers (VCs)
        of the Virtual Concatenation Group in the current 15-minute interval."
     ::= {virtualIfCurrentEntry 2 }

virtualIfCurrentRxFrames OBJECT-TYPE
    SYNTAX  Counter32
    MAX-ACCESS  read-only
    STATUS  current
    DESCRIPTION
       "This counter is associated with the number of frames received from STS-3/STM-1
        by a Virtual Interface in the current 15-minute interval."
    ::= { virtualIfCurrentEntry 3}

virtualIfCurrentTxFrames OBJECT-TYPE
    SYNTAX  Counter32
    MAX-ACCESS  read-only
    STATUS  current
    DESCRIPTION
       "This counter is associated with the number of frames transmitted to STS-3/STM-1
        by a Virtual Interface in the current 15-minute interval."
    ::= { virtualIfCurrentEntry 4 }

 virtualIfCurrentRxAbortFrames OBJECT-TYPE
    SYNTAX  PerfCurrentCount
    MAX-ACCESS  read-only
    STATUS  current
    DESCRIPTION
       "The counter associated with the number of Received Aborted frames
        encountered by a Virtual Interface in the current 15-minute interval."
     ::= { virtualIfCurrentEntry 5 }

virtualIfCurrentTxAbortFrames OBJECT-TYPE
    SYNTAX  PerfCurrentCount
    MAX-ACCESS  read-only
    STATUS  current
    DESCRIPTION
       "The counter associated with the number of Transmitted Aborted frames
        encountered by a Virtual Interface in the current 15-minute interval."
     ::= { virtualIfCurrentEntry 6 }

virtualIfCurrentMinLengthViolation OBJECT-TYPE
    SYNTAX  PerfCurrentCount
    MAX-ACCESS  read-only
    STATUS  current
    DESCRIPTION
       "This counter is associated with the number of
        Rx payload Min Length Violation frames encountered by a Virtual Interface
        in the current 15-minute interval."
    ::= { virtualIfCurrentEntry 7 }

virtualIfCurrentMaxLengthViolation OBJECT-TYPE
    SYNTAX  PerfCurrentCount
    MAX-ACCESS  read-only
    STATUS  current
    DESCRIPTION
       "This counter is associated with the number of
        Rx payload Max Length Violation frames
        encountered by a Virtual Interface in the current 15-minute interval."
    ::= { virtualIfCurrentEntry 8 }

virtualIfCurrentFcsError OBJECT-TYPE
    SYNTAX  PerfCurrentCount
    MAX-ACCESS  read-only
    STATUS  current
    DESCRIPTION
       "The counter is associated with the number of
        Frame Check Sequence errors encountered by a Virtual Interface
        in the current 15-minute interval."
    ::= { virtualIfCurrentEntry 9 }

virtualIfCurrentByteDestuffingViolation OBJECT-TYPE
    SYNTAX  PerfCurrentCount
    MAX-ACCESS  read-only
    STATUS  current
    DESCRIPTION
       "The counter associated with the number of
        Byte De-stuffing Violations encountered by a Virtual Interface
        in the current 15-minute interval."
    ::= {virtualIfCurrentEntry 10 }


virtualIfCurrentAdressMismatch   OBJECT-TYPE
    SYNTAX  PerfCurrentCount
    MAX-ACCESS  read-only
    STATUS  current
    DESCRIPTION
       "The counter associated with the number of
        Adress Mismatch encountered by a Virtual Interface
        in the current 15-minute interval."
    ::= {virtualIfCurrentEntry 11 }

virtualIfCurrentControlMismatch OBJECT-TYPE
    SYNTAX  PerfCurrentCount
    MAX-ACCESS  read-only
    STATUS  current
    DESCRIPTION
       "The counter associated with the number of
        Control Mismatch encountered by a Virtual Interface
        in the current 15-minute interval."
    ::= {virtualIfCurrentEntry 12 }

virtualIfCurrentActiveVC OBJECT-TYPE
    SYNTAX  Integer32 (1..64)
    MAX-ACCESS  read-only
    STATUS  current
    DESCRIPTION
       "This object holds the number of active virtual containers (VCs)
        of the Virtual Concatenation Group in the current 15-minute interval."
     ::= {virtualIfCurrentEntry 13 }



-- the Virtual Interface Interval Table

-- The Virtual Interface Interval Table
-- contains various statistics collected  over a maximum
-- of the previous 24 hours of operation.
-- The past 24 hours may be broken into 96
-- completed 15 minute intervals.

virtualIfIntervalTable OBJECT-TYPE
    SYNTAX  SEQUENCE OF VirtualIfIntervalEntry
    MAX-ACCESS  not-accessible
    STATUS  current
    DESCRIPTION
       "The Virtual Interface Interval table."
    ::= { virtualIfStatistics 2 }

virtualIfIntervalEntry OBJECT-TYPE
    SYNTAX  VirtualIfIntervalEntry
    MAX-ACCESS  not-accessible
    STATUS  current
    DESCRIPTION
       "An entry in the Virtual Interface Interval table."
    INDEX   { ifIndex, virtualIfIntervalNumber }
    ::= { virtualIfIntervalTable 1 }

VirtualIfIntervalEntry ::= SEQUENCE {
    virtualIfIntervalNumber                   Integer32,
    virtualIfIntervalMinActiveVC              Integer32,
    virtualIfIntervalMaxActiveVC              Integer32,
    virtualIfIntervalRxFrames                 Counter32,
    virtualIfIntervalTxFrames                 Counter32,
    virtualIfIntervalRxAbortFrames            PerfIntervalCount,
    virtualIfIntervalTxAbortFrames            PerfIntervalCount,
    virtualIfIntervalMinLengthViolation       PerfIntervalCount,
    virtualIfIntervalMaxLengthViolation       PerfIntervalCount,
    virtualIfIntervalFcsError                 PerfIntervalCount,
    virtualIfIntervalByteDestuffingViolation  PerfIntervalCount,
    virtualIfIntervalAdressMismatch           PerfIntervalCount,
    virtualIfIntervalControlMismatch          PerfIntervalCount,
    virtualIfIntervalBelowMinThreshold        PerfIntervalCount
 }

virtualIfIntervalNumber OBJECT-TYPE
    SYNTAX  Integer32 (1..96)
    MAX-ACCESS  not-accessible
    STATUS  current
    DESCRIPTION
      "A number between 1 and 96, which identifies the
       interval for which the set of statistics is available.
       The interval identified by 1 is the most recently
       completed 15 minute interval,
       and the interval identified
       by N is the interval immediately preceding the
       one identified  by N-1."
    ::= { virtualIfIntervalEntry 1 }

virtualIfIntervalMinActiveVC OBJECT-TYPE
    SYNTAX  Integer32 (1..64)
    MAX-ACCESS  read-only
    STATUS  current
    DESCRIPTION
      "This object holds the minimum number of
       active virtual containers (VCs) of the Virtual Concatenation Group, in a
       particular 15-minute interval in the past 24 hours."
    ::= { virtualIfIntervalEntry 2 }

virtualIfIntervalMaxActiveVC OBJECT-TYPE
    SYNTAX  Integer32 (1..64)
    MAX-ACCESS  read-only
    STATUS  current
    DESCRIPTION
      "This object holds the maximum number of
       active virtual containers (VCs) of the Virtual Concatenation Group, in a
       particular 15-minute interval in the past 24 hours."
    ::= { virtualIfIntervalEntry 3 }

virtualIfIntervalRxFrames OBJECT-TYPE
    SYNTAX  Counter32
    MAX-ACCESS  read-only
    STATUS  current
    DESCRIPTION
       "This counter is associated with the number of
        frames received from STS-3/STM-1 by a Virtual Interface in a
        particular 15-minute interval in the past 24 hours."
    ::= { virtualIfIntervalEntry 4 }

virtualIfIntervalTxFrames OBJECT-TYPE
    SYNTAX  Counter32
    MAX-ACCESS  read-only
    STATUS  current
    DESCRIPTION
       "This counter is associated with the number of
        frames transmitted to STS-3/STM-1 by a Virtual Interface in a
        particular 15-minute interval in the past 24 hours."
    ::= { virtualIfIntervalEntry 5 }

  virtualIfIntervalRxAbortFrames OBJECT-TYPE
    SYNTAX  PerfIntervalCount
    MAX-ACCESS  read-only
    STATUS  current
    DESCRIPTION
       "This counter is associated with the number of
        Received Abort frames encountered by a Virtual Interface in a
        particular 15-minute interval in the past 24 hours."
    ::= {virtualIfIntervalEntry 6 }

virtualIfIntervalTxAbortFrames OBJECT-TYPE
    SYNTAX  PerfIntervalCount
    MAX-ACCESS  read-only
    STATUS  current
    DESCRIPTION
       "This counter is associated with the number of
        Transmitted Abort frames encountered by a Virtual Interface in a
        particular 15-minute interval in the past 24 hours."
    ::= { virtualIfIntervalEntry 7 }

virtualIfIntervalMinLengthViolation OBJECT-TYPE
    SYNTAX  PerfIntervalCount
    MAX-ACCESS  read-only
    STATUS  current
    DESCRIPTION
       "This counter is associated with the number of
        Rx payload Min Length Violation frames
        encountered by a Virtual Interface in a
        particular 15-minute interval in the past 24 hours."
    ::= { virtualIfIntervalEntry 8 }

virtualIfIntervalMaxLengthViolation OBJECT-TYPE
    SYNTAX  PerfIntervalCount
    MAX-ACCESS  read-only
    STATUS  current
    DESCRIPTION
       "This counter is associated with the number of
        Rx payload Max Length Violation frames
        encountered by a Virtual Interface in a
        particular 15-minute interval in the past 24 hours."
    ::= { virtualIfIntervalEntry 9 }

virtualIfIntervalFcsError OBJECT-TYPE
    SYNTAX  PerfIntervalCount
    MAX-ACCESS  read-only
    STATUS  current
    DESCRIPTION
       "This counter is associated with the number of
        Frame Check Sequence errors encountered by a Virtual Interface in a
        particular 15-minute interval in the past 24 hours."
    ::= { virtualIfIntervalEntry 10 }

virtualIfIntervalByteDestuffingViolation OBJECT-TYPE
    SYNTAX  PerfIntervalCount
    MAX-ACCESS  read-only
    STATUS  current
    DESCRIPTION
       "This counter is associated with the number of
        Byte De-stuffing Violations
        encountered by a Virtual Interface in a
        particular 15-minute interval in the past 24 hours."
    ::= { virtualIfIntervalEntry 11 }


virtualIfIntervalAdressMismatch    OBJECT-TYPE
    SYNTAX  PerfIntervalCount
    MAX-ACCESS  read-only
    STATUS  current
    DESCRIPTION
       "This counter is associated with the number of
        Address Mismatch encountered by a Virtual Interface in a
        particular 15-minute interval in the past 24 hours."
    ::= { virtualIfIntervalEntry 12 }

virtualIfIntervalControlMismatch  OBJECT-TYPE
    SYNTAX  PerfIntervalCount
    MAX-ACCESS  read-only
    STATUS  current
    DESCRIPTION
       "This counter is associated with the number of
        Control mismatch encountered by a Virtual Interface in a
        particular 15-minute interval in the past 24 hours."
    ::= { virtualIfIntervalEntry 13 }

virtualIfIntervalBelowMinThreshold   OBJECT-TYPE
    SYNTAX  PerfIntervalCount
    MAX-ACCESS  read-only
    STATUS  current
    DESCRIPTION
       "This counter is associated with the number of
        seconds that number of active VCs was below minimum threshold
        defined by vcGroupCnfgNoOfVCs,
        encountered by Virtual Interface in a
        particular 15-minute interval in the past 24 hours."
    ::= { virtualIfIntervalEntry 14 }



-- the  Virtual Interface LAPS Current Table

virtualIfLAPSCurrentTable OBJECT-TYPE
    SYNTAX  SEQUENCE OF VcGroupLAPSCurrentEntry
    MAX-ACCESS  not-accessible
    STATUS  current
    DESCRIPTION
       "The Virtual Interface LAPS Current table."
     ::= { virtualIfStatistics 3 }

virtualIfLAPSCurrentEntry OBJECT-TYPE
    SYNTAX  VcGroupLAPSCurrentEntry
    MAX-ACCESS  not-accessible
    STATUS  current
    DESCRIPTION
       "An entry in the Virtual Interface
        LAPS Current table."
    INDEX   { ifIndex  }
     ::= { virtualIfLAPSCurrentTable 1 }

VcGroupLAPSCurrentEntry ::=
    SEQUENCE {
           virtualIfLAPSCurrentSapiMismatch            PerfCurrentCount
             }


virtualIfLAPSCurrentSapiMismatch OBJECT-TYPE
    SYNTAX  PerfCurrentCount
    MAX-ACCESS  read-only
    STATUS  current
    DESCRIPTION
       "This counter is associated with the number of
        received SAPI field mismatch
        encountered by a Virtual Interface
        in the current 15-minute interval."
    ::= { virtualIfLAPSCurrentEntry 1 }



-- the Virtual Interface LAPS Interval Table

-- The Virtual Interface LAPS Interval Table
-- contains various statistics collected  over a maximum
-- of the previous 24 hours of operation.
-- The past 24 hours may be broken into 96
-- completed 15 minute intervals.

virtualIfLAPSIntervalTable OBJECT-TYPE
    SYNTAX  SEQUENCE OF VirtualIfLAPSIntervalEntry
    MAX-ACCESS  not-accessible
    STATUS  current
    DESCRIPTION
       "The Virtual Interface LAPS table."
     ::= { virtualIfStatistics 4 }

virtualIfLAPSIntervalEntry OBJECT-TYPE
    SYNTAX  VirtualIfLAPSIntervalEntry
    MAX-ACCESS  not-accessible
    STATUS  current
    DESCRIPTION
       "An entry in the Virtual Interface
       LAPS Interval table."
    INDEX   { ifIndex, virtualIfIntervalNumber }
     ::= { virtualIfLAPSIntervalTable 1 }

VirtualIfLAPSIntervalEntry ::=
    SEQUENCE {
         virtualIfLAPSIntervalSapiMismatch     PerfIntervalCount
              }

virtualIfLAPSIntervalSapiMismatch OBJECT-TYPE
    SYNTAX  PerfIntervalCount
    MAX-ACCESS  read-only
    STATUS  current
    DESCRIPTION
       "This counter is associated with the number of
        received SAPI field mismatch
        encountered by a Virtual Interface in a
        particular 15-minute interval in the past 24 hours."
    ::= { virtualIfLAPSIntervalEntry 1 }


-- the Virtual Interface LAPF Current Table

virtualIfLAPFCurrentTable OBJECT-TYPE
    SYNTAX  SEQUENCE OF VirtualIfLAPFCurrentEntry
    MAX-ACCESS  not-accessible
    STATUS  current
    DESCRIPTION
       "The Virtual Interface LAPF Current table."
     ::= { virtualIfStatistics 5 }

virtualIfLAPFCurrentEntry OBJECT-TYPE
    SYNTAX  VirtualIfLAPFCurrentEntry
    MAX-ACCESS  not-accessible
    STATUS  current
    DESCRIPTION
       "An entry in the Virtual Interface
        LAPF Current table."
    INDEX   { ifIndex  }
     ::= { virtualIfLAPFCurrentTable 1 }

VirtualIfLAPFCurrentEntry ::=
    SEQUENCE {
		 virtualIfLAPFCurrentNlpidMismatch  PerfCurrentCount,
         virtualIfLAPFCurrentOuiMismatch    PerfCurrentCount,
		 virtualIfLAPFCurrentPidMismatch	  PerfCurrentCount,
		 virtualIfLAPFCurrentDlciMismatch	  PerfCurrentCount,
		 virtualIfLAPFCurrentMacRxFrames    PerfCurrentCount,
		 virtualIfLAPFCurrentMacTxFrames    PerfCurrentCount
    }


virtualIfLAPFCurrentNlpidMismatch OBJECT-TYPE
    SYNTAX  PerfCurrentCount
    MAX-ACCESS  read-only
    STATUS  current
    DESCRIPTION
       "This counter is associated with the number of
        received NLPID field mismatch
        encountered by a Virtual Interface
        in the current 15-minute interval."
    ::= { virtualIfLAPFCurrentEntry 1 }

virtualIfLAPFCurrentOuiMismatch OBJECT-TYPE
    SYNTAX  PerfCurrentCount
    MAX-ACCESS  read-only
    STATUS  current
    DESCRIPTION
       "This counter is associated with the number of
        received OUI field mismatch
        encountered by a Virtual Interface
        in the current 15-minute interval."
    ::= { virtualIfLAPFCurrentEntry 2 }


virtualIfLAPFCurrentPidMismatch OBJECT-TYPE
    SYNTAX  PerfCurrentCount
    MAX-ACCESS  read-only
    STATUS  current
    DESCRIPTION
       "This counter is associated with the number of
        received PID field mismatch
        encountered by a Virtual Interface
        in the current 15-minute interval."
    ::= { virtualIfLAPFCurrentEntry 3 }


virtualIfLAPFCurrentDlciMismatch OBJECT-TYPE
    SYNTAX  PerfCurrentCount
    MAX-ACCESS  read-only
    STATUS  current
    DESCRIPTION
       "This counter is associated with the number of
        received DLCI field mismatch
        encountered by a Virtual Interface
        in the current 15-minute interval."
    ::= { virtualIfLAPFCurrentEntry 4 }


virtualIfLAPFCurrentMacRxFrames OBJECT-TYPE
    SYNTAX  PerfCurrentCount
    MAX-ACCESS  read-only
    STATUS  current
    DESCRIPTION
       "This counter is associated with the number of
        frames received from LAN
        by a Virtual Interface
        in the current 15-minute interval."
    ::= { virtualIfLAPFCurrentEntry 5 }


virtualIfLAPFCurrentMacTxFrames OBJECT-TYPE
    SYNTAX  PerfCurrentCount
    MAX-ACCESS  read-only
    STATUS  current
    DESCRIPTION
       "This counter is associated with the number of
        frames transmitted to LAN
        by a Virtual Interface
        in the current 15-minute interval."
    ::= { virtualIfLAPFCurrentEntry 6 }


-- the Virtual Interface LAPF Interval Table

-- The Virtual Interface LAPF Interval Table
-- contains various statistics collected  over a maximum
-- of the previous 24 hours of operation.
-- The past 24 hours may be broken into 96
-- completed 15 minute intervals.

virtualIfLAPFIntervalTable OBJECT-TYPE
    SYNTAX  SEQUENCE OF VirtualIfLAPFIntervalEntry
    MAX-ACCESS  not-accessible
    STATUS  current
    DESCRIPTION
       "The Virtual Interface LAPF Interval table."
     ::= { virtualIfStatistics 6 }

virtualIfLAPFIntervalEntry OBJECT-TYPE
    SYNTAX  VirtualIfLAPFIntervalEntry
    MAX-ACCESS  not-accessible
    STATUS  current
    DESCRIPTION
       "An entry in the Virtual Interface Interval table."
    INDEX   { ifIndex, virtualIfIntervalNumber }
     ::= { virtualIfLAPFIntervalTable 1 }

VirtualIfLAPFIntervalEntry ::=
    SEQUENCE {
         virtualIfLAPFIntervalNlpidMismatch   PerfIntervalCount,
         virtualIfLAPFIntervalOuiMismatch     PerfIntervalCount,
		 virtualIfLAPFIntervalPidMismatch	  PerfIntervalCount,
		 virtualIfLAPFIntervalDlciMismatch    PerfIntervalCount,
		 virtualIfLAPFIntervalMacRxFrames     PerfIntervalCount,
		 virtualIfLAPFIntervalMacTxFrames     PerfIntervalCount
     }


virtualIfLAPFIntervalNlpidMismatch OBJECT-TYPE
    SYNTAX  PerfIntervalCount
    MAX-ACCESS  read-only
    STATUS  current
    DESCRIPTION
       "This counter is associated with the number of
        received NLPID field mismatch
        encountered by a Virtual Interface in a
        particular 15-minute interval in the past 24 hours."
    ::= { virtualIfLAPFIntervalEntry 1 }


virtualIfLAPFIntervalOuiMismatch OBJECT-TYPE
    SYNTAX  PerfIntervalCount
    MAX-ACCESS  read-only
    STATUS  current
    DESCRIPTION
       "This counter is associated with the number of
        received OUI field mismatch
        encountered by a Virtual Interface in a
        particular 15-minute interval in the past 24 hours."
    ::= { virtualIfLAPFIntervalEntry 2 }



virtualIfLAPFIntervalPidMismatch OBJECT-TYPE
    SYNTAX  PerfIntervalCount
    MAX-ACCESS  read-only
    STATUS  current
    DESCRIPTION
       "This counter is associated with the number of
        received PID field mismatch
        encountered by a Virtual Interface in a
        particular 15-minute interval in the past 24 hours."
    ::= { virtualIfLAPFIntervalEntry 3 }


virtualIfLAPFIntervalDlciMismatch OBJECT-TYPE
    SYNTAX  PerfIntervalCount
    MAX-ACCESS  read-only
    STATUS  current
    DESCRIPTION
       "This counter is associated with the number of
        received DLCI field mismatch
        by a Virtual Interface in a
        particular 15-minute interval in the past 24 hours."
    ::= { virtualIfLAPFIntervalEntry 4 }

virtualIfLAPFIntervalMacRxFrames OBJECT-TYPE
    SYNTAX  PerfIntervalCount
    MAX-ACCESS  read-only
    STATUS  current
    DESCRIPTION
       "This counter is associated with the number of
        frames received from LAN
        by a Virtual Interface in a
        particular 15-minute interval in the past 24 hours."
    ::= { virtualIfLAPFIntervalEntry 5 }

virtualIfLAPFIntervalMacTxFrames OBJECT-TYPE
    SYNTAX  PerfIntervalCount
    MAX-ACCESS  read-only
    STATUS  current
    DESCRIPTION
       "This counter is associated with the number of
        frames transmitted to LAN
        encountered by a Virtual Interface in a
        particular 15-minute interval in the past 24 hours."
    ::= { virtualIfLAPFIntervalEntry 6 }


-- the Virtual Interface GFP Current Table

virtualIfGFPCurrentTable OBJECT-TYPE
    SYNTAX  SEQUENCE OF VirtualIfGFPCurrentEntry
    MAX-ACCESS  not-accessible
    STATUS  current
    DESCRIPTION
       "The Virtual Interface GFP Current table."
     ::= { virtualIfStatistics 7 }

virtualIfGFPCurrentEntry OBJECT-TYPE
    SYNTAX  VirtualIfGFPCurrentEntry
    MAX-ACCESS  not-accessible
    STATUS  current
    DESCRIPTION
       "An entry in the Virtual Interface
       GFP Current table."
    INDEX   { ifIndex  }
     ::= { virtualIfGFPCurrentTable 1 }

VirtualIfGFPCurrentEntry ::=
    SEQUENCE {
		 virtualIfGFPCurrentIdleFrameError  PerfCurrentCount,
		 virtualIfGFPCurrentCHecSbError     PerfCurrentCount,
         virtualIfGFPCurrentPtiMismatch     PerfCurrentCount,
		 virtualIfGFPCurrentExiMismatch     PerfCurrentCount,
		 virtualIfGFPCurrentUpiMismatch     PerfCurrentCount,
		 virtualIfGFPCurrentTHecSbError     PerfCurrentCount,
		 virtualIfGFPCurrentTHecMbError     PerfCurrentCount,
         virtualIfGFPCurrentCidMismatch     PerfCurrentCount,
         virtualIfGFPCurrentEHecSbError     PerfCurrentCount,
         virtualIfGFPCurrentEHecMbError     PerfCurrentCount
    }

virtualIfGFPCurrentIdleFrameError OBJECT-TYPE
    SYNTAX  PerfCurrentCount
    MAX-ACCESS  read-only
    STATUS  current
    DESCRIPTION
       "This counter is associated with the number of
        received  GFP IDLE frames that are
        detected to be in error,
        encountered by a Virtual Interface
        in the current 15-minute interval."
     ::= { virtualIfGFPCurrentEntry 1}

virtualIfGFPCurrentCHecSbError OBJECT-TYPE
    SYNTAX  PerfCurrentCount
    MAX-ACCESS  read-only
    STATUS  current
    DESCRIPTION
       "This counter is associated with the number of
        received GFP frames that are detected to have
        single-bit errors in the Core
        header (i.e. cHEC field) only,
        encountered by a Virtual Interface
        in the current 15-minute interval."
    ::= { virtualIfGFPCurrentEntry 2 }

virtualIfGFPCurrentPtiMismatch OBJECT-TYPE
    SYNTAX  PerfCurrentCount
    MAX-ACCESS  read-only
    STATUS  current
    DESCRIPTION
       "This counter is associated with the number of
        rreceived GFP frames that are detected with
        a mismatch on the PTI field
        (i.e. value of PTI is not equal to
        Client Data or Management frame),
        encountered by a Virtual Interface
        in the current 15-minute interval."
    ::= { virtualIfGFPCurrentEntry 3 }


virtualIfGFPCurrentExiMismatch OBJECT-TYPE
    SYNTAX  PerfCurrentCount
    MAX-ACCESS  read-only
    STATUS  current
    DESCRIPTION
       "This counter is associated with the number of
        received GFP frames that are detected with
        a mismatch on the EXI field
        (i.e. value of EXI is not equal
        to NULL or LINEAR modes),
        encountered by a Virtual Interface
        in the current 15-minute interval."
    ::= { virtualIfGFPCurrentEntry 4 }


virtualIfGFPCurrentUpiMismatch OBJECT-TYPE
    SYNTAX  PerfCurrentCount
    MAX-ACCESS  read-only
    STATUS  current
    DESCRIPTION
       "This counter is associated with the number of
        received GFP frames that are detected with a
        mismatch on the UPI field
        (i.e. value of EXI is not equal to 00000001),
        encountered by a Virtual Interface
        in the current 15-minute interval."
    ::= { virtualIfGFPCurrentEntry 5 }


virtualIfGFPCurrentTHecSbError OBJECT-TYPE
    SYNTAX  PerfCurrentCount
    MAX-ACCESS  read-only
    STATUS  current
    DESCRIPTION
       "This counter is associated with the number of
        received GFP frames that are detected
        to only have single-bit errors in the Type header
        (i.e. tHEC field),
        encountered by a Virtual Interface
        in the current 15-minute interval."
    ::= { virtualIfGFPCurrentEntry 6 }


virtualIfGFPCurrentTHecMbError OBJECT-TYPE
    SYNTAX  PerfCurrentCount
    MAX-ACCESS  read-only
    STATUS  current
    DESCRIPTION
       "This counter is associated with the number of
       received GFP frames that are detected to
       only have multi-bit errors in the
       Type header (i.e. tHEC field),
       encountered by a Virtual Interface
        in the current 15-minute interval."
    ::= { virtualIfGFPCurrentEntry 7 }

virtualIfGFPCurrentCidMismatch OBJECT-TYPE
    SYNTAX  PerfCurrentCount
    MAX-ACCESS  read-only
    STATUS  current
    DESCRIPTION
       "This counter is associated with the number of
       received GFP frames that are detected to have a
       mismatch/unsupported value in the CID field only,
       encountered by a Virtual Interface
       in the current 15-minute interval."
    ::= { virtualIfGFPCurrentEntry 8 }

virtualIfGFPCurrentEHecSbError OBJECT-TYPE
    SYNTAX  PerfCurrentCount
    MAX-ACCESS  read-only
    STATUS  current
    DESCRIPTION
       "This counter is associated with the number of
        received  GFP frames that are detected
        to only have single-bit errors
        in the Extension header (i.e. eHEC field),
        encountered by a Virtual Interface
        in the current 15-minute interval."
    ::= { virtualIfGFPCurrentEntry 9 }

virtualIfGFPCurrentEHecMbError OBJECT-TYPE
    SYNTAX  PerfCurrentCount
    MAX-ACCESS  read-only
    STATUS  current
    DESCRIPTION
       "This counter is associated with the number of
        received GFP frames that are detected to only
        have single-bit errors in the
        Extension header (i.e. eHEC field),
        encountered by a Virtual Interface
        in the current 15-minute interval."
    ::= { virtualIfGFPCurrentEntry 10 }


-- the Virtual Interface GFP Interval Table

-- The Virtual Interface GFP Interval Table
-- contains various statistics collected  over a maximum
-- of the previous 24 hours of operation.
-- The past 24 hours may be broken into 96
-- completed 15 minute intervals.

virtualIfGFPIntervalTable OBJECT-TYPE
    SYNTAX  SEQUENCE OF VirtualIfGFPIntervalEntry
    MAX-ACCESS  not-accessible
    STATUS  current
    DESCRIPTION
       "The Virtual Interface GFP Interval table."
     ::= { virtualIfStatistics 8 }

virtualIfGFPIntervalEntry OBJECT-TYPE
    SYNTAX  VirtualIfGFPIntervalEntry
    MAX-ACCESS  not-accessible
    STATUS  current
    DESCRIPTION
       "An entry in the Virtual Interface
       GFP Interval table."
    INDEX   { ifIndex, virtualIfIntervalNumber }
     ::= { virtualIfGFPIntervalTable 1 }

VirtualIfGFPIntervalEntry ::=
    SEQUENCE {
     	  virtualIfGFPIntervalIdleFrameError	  PerfIntervalCount,
     	  virtualIfGFPIntervalCHecSbError	      PerfIntervalCount,
     	  virtualIfGFPIntervalPtiMismatch	      PerfIntervalCount,
     	  virtualIfGFPIntervalExiMismatch	      PerfIntervalCount,
     	  virtualIfGFPIntervalUpiMismatch	      PerfIntervalCount,
     	  virtualIfGFPIntervalTHecSbError	      PerfIntervalCount,
     	  virtualIfGFPIntervalTHecMbError	      PerfIntervalCount,
     	  virtualIfGFPIntervalCidMismatch	      PerfIntervalCount,
     	  virtualIfGFPIntervalEHecSbError	      PerfIntervalCount,
     	  virtualIfGFPIntervalEHecMbError	      PerfIntervalCount
     	      }

virtualIfGFPIntervalIdleFrameError OBJECT-TYPE
    SYNTAX  PerfIntervalCount
    MAX-ACCESS  read-only
    STATUS  current
    DESCRIPTION
       "This counter is associated with the number of
        received  GFP IDLE frames that are detected to be in error,
        encountered by a Virtual Interface in a
        particular 15-minute interval in the past 24 hours."
    ::= { virtualIfGFPIntervalEntry 1 }

virtualIfGFPIntervalCHecSbError OBJECT-TYPE
    SYNTAX  PerfIntervalCount
    MAX-ACCESS  read-only
    STATUS  current
    DESCRIPTION
       "This counter is associated with the number of
        received GFP frames that are detected to have
        single-bit errors in the Core header (i.e. cHEC field) only,
        encountered by a Virtual Interface in a
        particular 15-minute interval in the past 24 hours."
    ::= { virtualIfGFPIntervalEntry 2 }

virtualIfGFPIntervalPtiMismatch OBJECT-TYPE
    SYNTAX  PerfIntervalCount
    MAX-ACCESS  read-only
    STATUS  current
    DESCRIPTION
       "This counter is associated with the number of
        rreceived GFP frames that are detected with
        a mismatch on the PTI field (i.e. value of PTI
        is not equal to Client Data or Management frame),
        encountered by a Virtual Interface in a
        particular 15-minute interval in the past 24 hours."
    ::= { virtualIfGFPIntervalEntry 3 }

virtualIfGFPIntervalExiMismatch OBJECT-TYPE
    SYNTAX  PerfIntervalCount
    MAX-ACCESS  read-only
    STATUS  current
    DESCRIPTION
       "This counter is associated with the number of
        received GFP frames that are detected with
        a mismatch on the EXI field (i.e. value of EXI is not
        equal  to NULL or LINEAR modes),
        encountered by a Virtual Interface in a
        particular 15-minute interval in the past 24 hours."
    ::= { virtualIfGFPIntervalEntry 4 }

virtualIfGFPIntervalUpiMismatch OBJECT-TYPE
    SYNTAX  PerfIntervalCount
    MAX-ACCESS  read-only
    STATUS  current
    DESCRIPTION
       "This counter is associated with the number of
        received GFP frames that are detected with a
        mismatch on the UPI field (i.e. value of EXI
        is not equal to 00000001),
         encountered by a Virtual Interface in a
        particular 15-minute interval in the past 24 hours."
    ::= { virtualIfGFPIntervalEntry 5 }

virtualIfGFPIntervalTHecSbError OBJECT-TYPE
    SYNTAX  PerfIntervalCount
    MAX-ACCESS  read-only
    STATUS  current
    DESCRIPTION
       "This counter is associated with the number of
        received GFP frames that are detected to only have
         single-bit errors in the Type header (i.e. tHEC field),
        encountered by a Virtual Interface in a
        particular 15-minute interval in the past 24 hours."
    ::= { virtualIfGFPIntervalEntry 6 }

virtualIfGFPIntervalTHecMbError OBJECT-TYPE
    SYNTAX  PerfIntervalCount
    MAX-ACCESS  read-only
    STATUS  current
    DESCRIPTION
       "This counter is associated withthe number of
       received GFP frames that are detected to only have
       multi-bit errors in the Type header (i.e. tHEC field),
       encountered by a Virtual Interface in a
       particular 15-minute interval in the past 24 hours."
    ::= { virtualIfGFPIntervalEntry 7 }

virtualIfGFPIntervalCidMismatch OBJECT-TYPE
    SYNTAX  PerfIntervalCount
    MAX-ACCESS  read-only
    STATUS  current
    DESCRIPTION
       "This counter is associated with  the number of
       received GFP frames that are detected to have a
       mismatch/unsupported value in the CID field only,
       encountered by a Virtual Interface in a
       particular 15-minute interval in the past 24 hours."
    ::= { virtualIfGFPIntervalEntry 8 }

virtualIfGFPIntervalEHecSbError OBJECT-TYPE
    SYNTAX  PerfIntervalCount
    MAX-ACCESS  read-only
    STATUS  current
    DESCRIPTION
       "This counter is associated with the number of
        received  GFP frames that are detected
        to only have single-bit errors
        in the Extension header (i.e. eHEC field),
        encountered by a Virtual Interface in a
        particular 15-minute interval in the past 24 hours."
    ::= { virtualIfGFPIntervalEntry 9 }

virtualIfGFPIntervalEHecMbError OBJECT-TYPE
    SYNTAX  PerfIntervalCount
    MAX-ACCESS  read-only
    STATUS  current
    DESCRIPTION
       "This counter is associated with the the number of
        received GFP frames that are detected to only  have
        multi-bit errors in the  Extension header (i.e. eHEC field),
        encountered by a Virtual Interface in a
        particular 15-minute interval in the past 24 hours."
    ::= { virtualIfGFPIntervalEntry 10 }

prtSonetConfig  OBJECT IDENTIFIER  ::=  { sonetInterface 2 }

prtSonetGen     OBJECT IDENTIFIER  ::=  { prtSonetConfig 1 }

prtSonetGenTable OBJECT-TYPE
    SYNTAX  SEQUENCE OF PrtSonetGenEntry
    MAX-ACCESS  not-accessible
    STATUS      current
    DESCRIPTION
            "Sonet/SDH general port configuration table."
    ::= { prtSonetGen 1 }

prtSonetGenEntry   OBJECT-TYPE
    SYNTAX      PrtSonetGenEntry
    MAX-ACCESS  not-accessible
    STATUS      current
    DESCRIPTION
            "An entry in the Sonet/SDH general port configuration table."
    INDEX { prtSonetGenCnfgIdx, prtSonetGenIdx }
    ::= { prtSonetGenTable 1 }

PrtSonetGenEntry ::= SEQUENCE {
    prtSonetGenCnfgIdx          Integer32,
    prtSonetGenIdx              Integer32,
    prtSonetGenSdThreshold      INTEGER,
    prtSonetGenEedThreshold     INTEGER,
    prtSonetGenBerEnable        INTEGER
 }

prtSonetGenCnfgIdx OBJECT-TYPE
    SYNTAX      Integer32 (1..255)
    MAX-ACCESS  read-only
    STATUS      current
    DESCRIPTION
            "This object indicates the Idx of the Config being accessed.
            Idx of 255 relates to the Temporary (Scratch) Config.
            For products that support several configurations, Set can be
            performed only to the Temporary Config (=255)."
    ::= { prtSonetGenEntry 1 }

prtSonetGenIdx OBJECT-TYPE
    SYNTAX      Integer32
    MAX-ACCESS  read-only
    STATUS      current
    DESCRIPTION
            "This object indicates a unique  port or interface number.
            For numbering, see product's spec.
            For some products, the numbering can equal ifIndex."
    ::= { prtSonetGenEntry 2 }

prtSonetGenSdThreshold OBJECT-TYPE
    SYNTAX  INTEGER {
     notApplicable(1),
     n3           (3),
     n4           (4),
     n5           (5),
     n6           (6),
     n7           (7),
     n8           (8),
     n9           (9)
     }
    MAX-ACCESS  read-write
    STATUS  current
    DESCRIPTION
     "SD=Signal Degraded Threshold. Units: [10E-].
      The threshold is 10E-x relative to the frequency of the data flow.
      x=3, 4, 5, 6, 7, 8, 9.
      n3= 10E-3
      n4= 10E-4
      n5= 10E-5
      n6= 10E-6
      n7= 10E-7
      n8= 10E-8
      n9= 10E-9  ."
    ::= { prtSonetGenEntry 3 }

prtSonetGenEedThreshold OBJECT-TYPE
    SYNTAX  INTEGER {
     notApplicable(1),
     n3           (3),
     n4           (4),
     n5           (5),
     n6           (6),
     n7           (7),
     n8           (8),
     n9           (9)
     }
    MAX-ACCESS  read-write
    STATUS  current
    DESCRIPTION
     "EED=Excessive Error Defect Threshold. Units: [10E-].
      The threshold is 10E-x relative to the frequency of the data flow.
      x=3, 4, 5, 6, 7, 8, 9.
      n3= 10E-3
      n4= 10E-4
      n5= 10E-5
      n6= 10E-6
      n7= 10E-7
      n8= 10E-8
      n9= 10E-9 ."
    ::= { prtSonetGenEntry 4 }

prtSonetGenBerEnable OBJECT-TYPE
    SYNTAX  INTEGER {
        notApplicable (1),
        disable       (2),
        enable        (3)
        }
    MAX-ACCESS  read-write
    STATUS      current
    DESCRIPTION
            "Controls the activation of the Line Ber (Bit Error Rate),
            means whether SD and EED threshold parameters will be
            enabled."
    ::= { prtSonetGenEntry 5 }


--STM-1 ports

prtSonetStm1    OBJECT IDENTIFIER  ::=  {prtSonetConfig 2}


prtSonetStm1Table OBJECT-TYPE
    SYNTAX  SEQUENCE OF PrtSonetStm1Entry
    MAX-ACCESS  not-accessible
    STATUS  current
    DESCRIPTION
     "Sonet/SDH STM-1 port configuration table."
    ::= { prtSonetStm1 1}

prtSonetStm1Entry   OBJECT-TYPE
    SYNTAX  PrtSonetStm1Entry
    MAX-ACCESS  not-accessible
    STATUS  current
    DESCRIPTION
     " An entry in the Sonet/SDH STM-1 port configuration table."
     INDEX { prtSonetStm1CnfgIdx, prtSonetStm1Idx }
    ::= { prtSonetStm1Table 1}

PrtSonetStm1Entry ::= SEQUENCE {
    prtSonetStm1CnfgIdx      Integer32,
    prtSonetStm1Idx      Integer32,
    prtSonetStm1ClockSrc      INTEGER,
     prtSonetStm1DccMode
     INTEGER,
	 prtSonetStm1RoutingProt
	 INTEGER,
	 prtSonetStm1MngProt
	 INTEGER,
	 prtSonetStm1OperationalMode
	 INTEGER,
     prtSonetStm1VoiceChannel
     INTEGER,
     prtSonetStm1OutputRate
     Integer32,
     prtSonetStm1S1ProtocolClock
     INTEGER,
     prtSonetStm1GatewayRingSubnetAddress
     IpAddress,
     prtSonetStm1GatewayRingSubnetMask
	 IpAddress,
	 prtSonetStm1MngProtDeviationType
	 INTEGER,
	 prtSonetStm1MngSameIpAsHost
	 INTEGER,
	 prtSonetStm1MngIpAddress
	 IpAddress,
	 prtSonetStm1MngIpSubnetMask
	 IpAddress,
	 prtSonetStm1MngDefaultGateway
	 IpAddress
 }

prtSonetStm1CnfgIdx OBJECT-TYPE
    SYNTAX  Integer32 (1..255)
    MAX-ACCESS  read-only
    STATUS  current
    DESCRIPTION
     "This object indicates the Idx of the Config being accessed.
      Idx of 255 relates to the Temporary (Scratch) Config.
      For products that support several configurations, Set can be performed
      only to the Temporary Config (=255). "
    ::= { prtSonetStm1Entry 1}

prtSonetStm1Idx OBJECT-TYPE
    SYNTAX  Integer32
    MAX-ACCESS  read-only
    STATUS  current
    DESCRIPTION
     "This object indicates a unique  port or interface number.
     For numbering, see product's spec.
     For some products, the numbering can equal ifIndex."
    ::= { prtSonetStm1Entry 2}

prtSonetStm1ClockSrc OBJECT-TYPE
    SYNTAX  INTEGER {
     notApplicable(1),
     internal     (2),
     lbt          (3),
     systemClk    (4)
     }
    MAX-ACCESS  read-write
    STATUS  current
    DESCRIPTION
     "Clock Source of the STM-1 port.
      lbt = Loop Back Timing."
    ::= { prtSonetStm1Entry 3 }

prtSonetStm1DccMode OBJECT-TYPE
     SYNTAX  INTEGER {
     notApplicable(1),
     none         (2),
     d1ToD3       (3),
     d4ToD12      (4),
     d1           (5),
     d2           (6),
     d3           (7),
     d4           (8),
     d5           (9),
     d6           (10),
     d7           (11),
     d8           (12),
     d9           (13),
     d10          (14),
     d11          (15),
     d12          (16)
     }
     MAX-ACCESS  read-write
     STATUS  current
     DESCRIPTION
     "DCC Mode. DCC=Data Communication Channel.
	  d1ToD3 = D1-D3  bytes are used (RS=Regeneration Section).
	  d4ToD12= D4-D12 bytes are used (MS=Multiplexing Section).
	  d1.... d12 enable user to select single DCC byte "
     ::= { prtSonetStm1Entry 4 }

prtSonetStm1RoutingProt OBJECT-TYPE
     SYNTAX  INTEGER {
      notApplicable (1),
      none          (2),
      proprietary   (3),
	  rip2          (4)
     }
     MAX-ACCESS  read-write
     STATUS  current
     DESCRIPTION
     "Routing Protocol."
     ::= { prtSonetStm1Entry 5 }

prtSonetStm1MngProt OBJECT-TYPE
     SYNTAX  INTEGER {
      notApplicable (1),
      -- none (2)
      proprietary   (3),
      -- rip2  (4)
      ppp           (5),
	  frameRelay    (6),
	  hdlc          (7),
	  lapdOverHdlc  (8)
     }
     MAX-ACCESS  read-write
     STATUS  current
     DESCRIPTION
     "Management Protocol over DCC:  Proprietary, PPP, Frame Relay,
     HDLC or LAPD over HDLC .
     ppp = according to STD-51 ( rfc1661/1662)"
     ::= { prtSonetStm1Entry 6 }

prtSonetStm1OperationalMode OBJECT-TYPE
     SYNTAX  INTEGER {
      notApplicable    (1),
      terminal         (2),
      linear           (3),
      linearProtection (4),
	  dualRing         (5)
     }
     MAX-ACCESS  read-write
     STATUS  current
     DESCRIPTION
     "Operational Mode.
      linear - cannot be selected when there is Redundancy between the
               STM-1 ports."
     ::= { prtSonetStm1Entry 7 }

prtSonetStm1VoiceChannel  OBJECT-TYPE
     SYNTAX  INTEGER {
      notApplicable (1),
      none   (2),
      e1Byte (3),
      e2Byte (4)
     }
     MAX-ACCESS  read-write
     STATUS  current
     DESCRIPTION
     "This parameter enable user to select whether
      voice channel will be transferred using E1 byte, E2 Byte, or not at all."
     ::= { prtSonetStm1Entry 8 }

prtSonetStm1OutputRate  OBJECT-TYPE
     SYNTAX  Integer32
     MAX-ACCESS  read-write
     STATUS  current
     DESCRIPTION
     "This parameter indicates the output rate in cells/sec, which is
      supported per port."
     ::= { prtSonetStm1Entry 9 }

prtSonetStm1S1ProtocolClock  OBJECT-TYPE
     SYNTAX  INTEGER {
      notApplicable (1),
      disable       (2),
	  enable        (3),
	  transparent   (4)
     }
     MAX-ACCESS  read-write
     STATUS  current
     DESCRIPTION
     "This parameter allows user to select whether to enable use of
      Remote Side Clock according to the Protocol passed on S1 Bit."
     ::= { prtSonetStm1Entry 10 }

prtSonetStm1GatewayRingSubnetAddress	 OBJECT-TYPE
     SYNTAX  IpAddress
     MAX-ACCESS  read-write
     STATUS  current
     DESCRIPTION
     "This parameter defines subnet for static routing,
      together with prtSonetStm1GatewayRingSubnetMask"
      ::= { prtSonetStm1Entry 11 }

prtSonetStm1GatewayRingSubnetMask	 OBJECT-TYPE
     SYNTAX  IpAddress
     MAX-ACCESS  read-write
     STATUS  current
     DESCRIPTION
     "This parameter defines subnet for static routing,
      together with prtSonetStm1GatewayRingSubnetAddress"
     ::= { prtSonetStm1Entry 12 }

prtSonetStm1MngProtDeviationType OBJECT-TYPE
     SYNTAX  INTEGER
     {
	 notApplicable (1),
	 standard      (2),
	 type1         (3)
     }
     MAX-ACCESS  read-write
     STATUS  current
     DESCRIPTION
     "This parameter is used in conjunction with prtSonetStm1MngProt
      to define management protocol used & type of deviation
      (if exist) from standard.
      Standard  = no deviation from standard protocol
      Type1     = PPP without sending Address and Control overhead
                  in Link Control Protocol (LCP) packets"
     ::= { prtSonetStm1Entry 13 }

prtSonetStm1MngSameIpAsHost  OBJECT-TYPE
     SYNTAX  INTEGER
     {
	 notApplicable (1),
	 no            (2),
	 yes           (3)
     }
     MAX-ACCESS  read-write
     STATUS  current
     DESCRIPTION
     "This parameter indicates whether IP address
      used for management is same as the device IP address"
     ::= { prtSonetStm1Entry 14 }

prtSonetStm1MngIpAddress  OBJECT-TYPE
     SYNTAX  IpAddress
     MAX-ACCESS  read-write
     STATUS  current
     DESCRIPTION
     "This parameter defines IP address for DCC management
      for this link, together with prtSonetStm1MngIpSubnetMask.
      This parameter is applicable only if prtSonetStm1MngSameIpAsHost=no."
      ::= { prtSonetStm1Entry 15 }

prtSonetStm1MngIpSubnetMask	 OBJECT-TYPE
     SYNTAX  IpAddress
     MAX-ACCESS  read-write
     STATUS  current
     DESCRIPTION
     "This parameter defines IP subnet mask for DCC management
      for this link, together with prtSonetStm1MngIpAddress
      This parameter is applicable only if prtSonetStm1MngSameIp=no"
      ::= { prtSonetStm1Entry 16 }

prtSonetStm1MngDefaultGateway	 OBJECT-TYPE
     SYNTAX  IpAddress
     MAX-ACCESS  read-write
     STATUS  current
     DESCRIPTION
     "This parameter defines default Gateway address for DCC management
      for this link.
      This parameter is applicable only if prtSonetStm1MngSameIp=no"
      ::= { prtSonetStm1Entry 17 }

--SONET/SDH VC-3, VC-4 and VC-12 ports parameters

prtSonetVc      OBJECT IDENTIFIER  ::=  { prtSonetConfig 3}


prtSonetVcTable OBJECT-TYPE
    SYNTAX  SEQUENCE OF PrtSonetVcEntry
    MAX-ACCESS  not-accessible
    STATUS  current
    DESCRIPTION
     "Sonet/SDH VC port configuration table."
    ::= { prtSonetVc 1}

prtSonetVcEntry   OBJECT-TYPE
    SYNTAX      PrtSonetVcEntry
    MAX-ACCESS  not-accessible
    STATUS      current
    DESCRIPTION
            "An entry in the Sonet/SDH VC port configuration table."
    INDEX { prtSonetVcCnfgIdx, prtSonetVcIdx }
    ::= { prtSonetVcTable 1}

PrtSonetVcEntry ::= SEQUENCE {
    prtSonetVcCnfgIdx                       Integer32,
    prtSonetVcIdx                           Integer32,
    prtSonetVcJTxPathTraceEnable            INTEGER,
    prtSonetVcJRxPathTraceEnable            INTEGER,
    prtSonetVcJPathTrace                    SnmpAdminString,
	 prtSonetVcConnect
	 INTEGER,
    prtSonetVcSignalLabel                   OCTET STRING,
    prtSonetVcPathTracePadding              INTEGER,
	 prtSonetVcPayloadBlockOnPathTrace
	 INTEGER,
	 prtSonetVcPayloadType
	 INTEGER,
	 prtSonetVcPathTraceSize
	 INTEGER
 }

prtSonetVcCnfgIdx OBJECT-TYPE
    SYNTAX  Integer32 (1..255)
    MAX-ACCESS  read-only
    STATUS  current
    DESCRIPTION
     "This object indicates the Idx of the Config being accessed.
      Idx of 255 relates to the Temporary (Scratch) Config.
      For products that support several configurations, Set can be performed
      only to the Temporary Config (=255). "
    ::= { prtSonetVcEntry 1}

prtSonetVcIdx OBJECT-TYPE
    SYNTAX  Integer32
    MAX-ACCESS  read-only
    STATUS  current
    DESCRIPTION
     "This object indicates a unique  port or interface number.
     For numbering, see product's spec.
     For some products, the numbering can equal ifIndex."
    ::= { prtSonetVcEntry 2}

prtSonetVcJTxPathTraceEnable OBJECT-TYPE
    SYNTAX      INTEGER {
        notApplicable(1),
        disable      (2),
        enable       (3)
        }
    MAX-ACCESS  read-write
    STATUS      current
    DESCRIPTION
            "Enable/Disable transmitting Jy Path Trace. y = 0, 1, 2:
            J0 - for SDH/SONET layer
            J1 - for VC-4  layer
            J2 - for VC-12 layer.
            The default value is 'enable' (3)."
    ::= { prtSonetVcEntry 3 }

prtSonetVcJRxPathTraceEnable OBJECT-TYPE
    SYNTAX  INTEGER {
     notApplicable(1),
     disable      (2),
     enable       (3)
     }
    MAX-ACCESS  read-write
    STATUS  current
    DESCRIPTION
            "Enable/Disable checking Jy Path Trace. y = 0, 1, 2:
            J0 - for SDH/SONET layer
            J1 - for VC-4  layer
            J2 - for VC-12 layer."
    ::= { prtSonetVcEntry 4 }

prtSonetVcJPathTrace OBJECT-TYPE
    SYNTAX SnmpAdminString (SIZE(0..62))
    MAX-ACCESS  read-write
    STATUS      current
    DESCRIPTION
            "Jy Path Trace. y = 0, 1, 2:
            J0 - for SDH/SONET layer
            J1 - for VC-4  layer
            J2 - for VC-12 layer.
            This object is applicable only if one of the previous 2
            objects is 'enable'.
            The J0 SDH default value is 0x00.
            The J0 SONET default value is 0x01.
            For J1 and J2 default value is 0x00.
            This object may be used to configure TX trace messages.
            The prtSonetVcStatTable.prtSonetVcRxJPathTrace OBJECT
            contains RX Trace message values."
    ::= { prtSonetVcEntry 5 }

prtSonetVcConnect  OBJECT-TYPE
      SYNTAX  INTEGER
      {
      notApplicable (1),
	  no (2),
	  yes (3)
      }
      MAX-ACCESS  read-write
      STATUS  current
      DESCRIPTION
      "Connect VCn (n - 11,12,2,3,4) port (yes/no)."
     ::= { prtSonetVcEntry 6 }


prtSonetVcSignalLabel  OBJECT-TYPE
     SYNTAX  OCTET STRING   (SIZE (1))
     MAX-ACCESS  read-write
     STATUS  current
     DESCRIPTION
      "Signal Label.
       For VC-3:
       The SONET standard defines the C2 byte as
       the path signal label. The purpose of this byte is to
       communicate the payload type being encapsulated by the
       SONET Framing OverHead. It allows a single interface to
       transport multiple payload types simultaneously.

       For VC-12, VT-1.5:
       VT path overhead V5 byte allocates bits 5-7  for
       VT Path Signal Label, to indicate the content of the VT SPE.
        000 Unequipped
        001 Equipped : non-specific payload
        010 Asynchronous mapping
        011 Bit synchronous mapping (no longer valid for DS1)
        100 Byte synchronous mapping
        101 Unassigned
        110 Unassigned
        111 Unassigned

       Agents that do not support this feature will send SIZE 0."
    ::= { prtSonetVcEntry 7 }

prtSonetVcPathTracePadding OBJECT-TYPE
    SYNTAX      INTEGER{
        notApplicable (1),
        nulls  (2),
        spaces (3)
        }
    MAX-ACCESS  read-write
    STATUS      current
    DESCRIPTION
            "Padding character will pad prtSonetVcJPathTrace string
            to fill required number of characters.
            The default value is nulls (2) '0x00'."
    ::= { prtSonetVcEntry 8 }

prtSonetVcPayloadBlockOnPathTrace  OBJECT-TYPE
      SYNTAX  INTEGER
      {
      notApplicable (1),
	  disable   (2),
	  enable (3)
      }
      MAX-ACCESS  read-write
      STATUS  current
      DESCRIPTION
      "Block payload on this VC upon PathTrace (TIM)."
     ::= { prtSonetVcEntry 9 }


prtSonetVcPayloadType  OBJECT-TYPE
      SYNTAX  INTEGER
      {
      notApplicable (1),
	  pos           (2),
	  clearchannel  (3),
	  channelized   (4),
	  vc1x     		(5)
       }
      MAX-ACCESS  read-write
      STATUS  current
      DESCRIPTION
      "Payload type, applicable for STS-1/TUG-3 layer.
      vc1x = vc12 or vc11 for SDH, VT1.5, VT2 for SONET.
	  clear channel	 - complete TUG-3 or STS-1
      For Egate-100:
      POS (Packets over Sonet) configuration is valid per STM1/OC3,
      change this mode to POS for one TUG3/STS1 change values
      to POS for all TUG3/STS1 under  this STM1/OC3.
      Clear Channel/channelize/ configuration is valid per TUG3/STS1."
     ::= { prtSonetVcEntry 10 }


prtSonetVcPathTraceSize  OBJECT-TYPE
      SYNTAX  INTEGER
      {
      notApplicable (1),
	  b16           (2),
	  b64           (3)
       }
      MAX-ACCESS  read-write
      STATUS  current
      DESCRIPTION
      "Path Trace Size in Bytes - 16 or 64."
     ::= { prtSonetVcEntry 11 }


--TU-12 (within VC-4) Connect Table

prtSonetTuTable  OBJECT-TYPE
     SYNTAX SEQUENCE OF PrtSonetTuEntry
     MAX-ACCESS not-accessible
     STATUS  current
     DESCRIPTION
      "The write operation into the Table's Objects is valid only
       for the TmpCnfg entry (Scratch)."
  ::= { prtSonetVc 2}

prtSonetTuEntry OBJECT-TYPE
      SYNTAX PrtSonetTuEntry
      MAX-ACCESS not-accessible
      STATUS current
	DESCRIPTION  "An entry in table."
	INDEX {prtSonetTuCnfgIdx, prtSonetTuPrtIdx, prtSonetTuIdx, prtSonetTuConPrtIdx }
      ::= { prtSonetTuTable 1}

PrtSonetTuEntry ::=
      SEQUENCE {
      prtSonetTuCnfgIdx        Integer32,
      prtSonetTuPrtIdx         Integer32,
      prtSonetTuIdx            Integer32,
      prtSonetTuConPrtIdx      Integer32,
      prtSonetTuType           INTEGER,
      prtSonetTuMode           INTEGER,
	  prtSonetTuRowStatus      RowStatus
      }

prtSonetTuCnfgIdx OBJECT-TYPE
      SYNTAX  Integer32  (1..255)
      MAX-ACCESS  read-only
      STATUS  current
      DESCRIPTION
      "This object indicates the Idx of the Config being accessed.
      Idx of 255 relates to the Temporary (Scratch) Config.
      For products that support several configurations, Set can be performed
      only to the Temporary Config (=255). "
      ::= { prtSonetTuEntry 1}

prtSonetTuPrtIdx OBJECT-TYPE
      SYNTAX  Integer32
      MAX-ACCESS  read-only
      STATUS  current
      DESCRIPTION
      "This object indicates a unique  port or interface number.
	  For port numbering, see product's spec.
      For some products, the numbering can equal ifIndex."
      ::= { prtSonetTuEntry 2}

prtSonetTuIdx OBJECT-TYPE
      SYNTAX  Integer32
      MAX-ACCESS  read-only
      STATUS  current
      DESCRIPTION
      "This object indicates a unique TU (Tributary Unit) within VC-4.
	   The valid TUs are 1..63."
      ::= { prtSonetTuEntry 3}

prtSonetTuConPrtIdx OBJECT-TYPE
      SYNTAX  Integer32
      MAX-ACCESS  read-only
      STATUS  current
      DESCRIPTION
      "This object indicates the connected port, when prtSonetTuType=connect.
	   For port numbering, see product's spec.
       For some products, the numbering can equal ifIndex.
       notApplicable - will be indicated as 100."
      ::= {prtSonetTuEntry 4}

prtSonetTuType  OBJECT-TYPE
      SYNTAX  INTEGER
      {
      connect (2),
	  bypass  (3)
      }
      MAX-ACCESS  read-create
      STATUS  current
      DESCRIPTION
      "The type of TU (Tributary Unit).
       connect - connected to one of the E1 ports.
	   bypass  - bypassed to the other VC4 port.
       TUs that are not connected or bypassed, will not exist in this table."
      ::= { prtSonetTuEntry 5}

prtSonetTuMode  OBJECT-TYPE
      SYNTAX  INTEGER
      {
      notApplicable(1),
      addAndDrop   (2),
      add          (3)
      }
      MAX-ACCESS  read-create
      STATUS  current
      DESCRIPTION
      "TU Mode of connection.
       addAndDrop    - Add & Drop
       add           - Add (TU receives from the E1 ports)."
      ::= { prtSonetTuEntry 6}

prtSonetTuRowStatus OBJECT-TYPE
      SYNTAX RowStatus
      MAX-ACCESS read-create
      STATUS current
      DESCRIPTION
      "Creation/Deletion of rows in the table."
      ::= { prtSonetTuEntry 7}


-- SDH Cross Connect Table
-- May be used also for SONET

prtSonetXConnect  OBJECT IDENTIFIER  ::= {sonetInterface 3}

prtSonetXConnectTable  OBJECT-TYPE
     SYNTAX SEQUENCE OF PrtSonetXConnectEntry
     MAX-ACCESS not-accessible
     STATUS  current
     DESCRIPTION
      "The write operation into the Table's Objects is valid only
       for the TmpCnfg entry (Scratch)."
     ::= { prtSonetXConnect 1}

prtSonetXConnectEntry OBJECT-TYPE
      SYNTAX PrtSonetXConnectEntry
      MAX-ACCESS not-accessible
      STATUS current
      DESCRIPTION  "An entry in table."
	  INDEX  {
	         prtSonetXConnectCnfgIdx,
	         prtSonetXConnectPrtIdx,
	         prtSonetXConnectConPrtIdx,
	         prtSonetXConnectAUGIdx,
	         prtSonetXConnectTUG3Idx,
	         prtSonetXConnectTUG2Idx,
	         prtSonetXConnectTUnIdx
	         }
	      ::= { prtSonetXConnectTable 1}

PrtSonetXConnectEntry ::=
      SEQUENCE {
      prtSonetXConnectCnfgIdx        Integer32,
      prtSonetXConnectPrtIdx         Integer32,
	  prtSonetXConnectConPrtIdx      Integer32,
      prtSonetXConnectAUGIdx         Integer32,
      prtSonetXConnectTUG3Idx        Integer32,
      prtSonetXConnectTUG2Idx        Integer32,
      prtSonetXConnectTUnIdx         Integer32,
	  prtSonetXConnectRowStatus      RowStatus,
	  prtSonetXConnectDirection      INTEGER,
      prtSonetXConnectTuNumber       INTEGER,
	  prtSonetXConnectMode			 INTEGER
      }

prtSonetXConnectCnfgIdx OBJECT-TYPE
      SYNTAX  Integer32  (1..255)
      MAX-ACCESS  read-only
      STATUS  current
      DESCRIPTION
      "This object indicates the Idx of the Config being accessed.
       Idx of 255 relates to the Temporary (Scratch) Config.
       For products that support several configurations, Set can be performed
       only to the Temporary Config (=255). "
      ::= { prtSonetXConnectEntry 1}

prtSonetXConnectPrtIdx OBJECT-TYPE
      SYNTAX  Integer32
      MAX-ACCESS  read-only
      STATUS  current
      DESCRIPTION
      "This object indicates a unique  port or interface number.
	   For port numbering, see product's spec.
       For some products, the numbering can equal ifIndex."
      ::= { prtSonetXConnectEntry 2}

prtSonetXConnectConPrtIdx OBJECT-TYPE
      SYNTAX  Integer32
      MAX-ACCESS  read-only
      STATUS  current
      DESCRIPTION
      "This object indicates the connected port.
	   For port numbering, see product's spec.
       For some products, the numbering can equal ifIndex.
       notApplicable - will be indicated as 255."
      ::= {prtSonetXConnectEntry 3}


prtSonetXConnectAUGIdx OBJECT-TYPE
      SYNTAX  Integer32
      MAX-ACCESS  read-only
      STATUS  current
      DESCRIPTION
      "This object indicates an  AUG (Administrative Unit Group) within STM-N.
	   The valid AUGs values are:
	   1 for STM-1
	   1...4 for STM-4,
	   1..16 for STM-16  and
	   1..64 for STM-64  (STM-64)
	   255 designates NA."
      ::= { prtSonetXConnectEntry 4}

prtSonetXConnectTUG3Idx OBJECT-TYPE
      SYNTAX  Integer32
      MAX-ACCESS  read-only
      STATUS  current
      DESCRIPTION
      "This object indicates a  TUG-3 (Tributary Unit Group 3) within VC-4.
	   The valid TUG3s are values are 1..3. and 255 which designates NA "
      ::= { prtSonetXConnectEntry 5}

prtSonetXConnectTUG2Idx OBJECT-TYPE
      SYNTAX  Integer32
      MAX-ACCESS  read-only
      STATUS  current
      DESCRIPTION
      "This object indicates a TUG2 (Tributary Unit Group 2 ) within VC-3.
	   The valid TUG2's values  are 1..7 and 255 which designates NA "
      ::= { prtSonetXConnectEntry 6}

prtSonetXConnectTUnIdx OBJECT-TYPE
      SYNTAX  Integer32
      MAX-ACCESS  read-only
      STATUS  current
      DESCRIPTION
      "This object indicates a TUn within TUG-2 or TUG-3
       (Tributary Unit n, where  n is 2, 12 or 11 within TUG-2,
       or 3 within TUG-3)
       valid values are
	   1 for TU-2
	   1 for TU-3
	   1..4  for TU-11
	   1..3  for TU-12
	   255 designates NA"
	   ::= { prtSonetXConnectEntry 7}


prtSonetXConnectRowStatus OBJECT-TYPE
      SYNTAX RowStatus
      MAX-ACCESS read-create
      STATUS current
      DESCRIPTION
      "Creation/Deletion of rows in the table."
      ::= { prtSonetXConnectEntry 8}


prtSonetXConnectDirection  OBJECT-TYPE
      SYNTAX  INTEGER
      {
      notApplicable(1),
      rx   (2),
      tx   (3),
	  both (4)
      }
      MAX-ACCESS  read-create
      STATUS  current
      DESCRIPTION
      "TU direction of connection.
      rx=Drop
      tx=Add
      both = Add & Drop"
      ::= { prtSonetXConnectEntry 9}

prtSonetXConnectTuNumber OBJECT-TYPE
      SYNTAX  INTEGER
      {
      notApplicable (1),
      tu2			(2),
      tu3           (3),
      tu11          (4),
	  tu12          (5),
	  tuFour4c      (6),
	  sts12c    	(7)
      }
      MAX-ACCESS  read-create
      STATUS  current
      DESCRIPTION
       "This object indicates which TU is used in prtSonetXConnectTUnIdx "
      ::= { prtSonetXConnectEntry 10}

prtSonetXConnectMode  OBJECT-TYPE
      SYNTAX  INTEGER
      {
      notApplicable(1),
      addAndDrop   (2),
      bypass  (3)
      }
      MAX-ACCESS  read-create
      STATUS  current
      DESCRIPTION
      "TU Mode of connection.
       addAndDrop    - Add & Drop
       bypass  - bypassed to the other VC4 port."
      ::= {prtSonetXConnectEntry 11}


prtSonetStatus  OBJECT IDENTIFIER  ::= {sonetInterface 4}

prtSonetVcStatTable  OBJECT-TYPE
    SYNTAX  SEQUENCE OF PrtSonetVcStatEntry
    MAX-ACCESS  not-accessible
    STATUS  current
    DESCRIPTION
       "VC Status Table "
     ::= { prtSonetStatus 1 }

prtSonetVcStatEntry OBJECT-TYPE
    SYNTAX      PrtSonetVcStatEntry
    MAX-ACCESS  not-accessible
    STATUS  current
    DESCRIPTION
       "An entry in the VC status Table."
    INDEX   {prtSonetVcIdx}
     ::= { prtSonetVcStatTable 1 }

PrtSonetVcStatEntry ::=
    SEQUENCE {
	 prtSonetVcRxJPathTrace	   SnmpAdminString,
	 prtSonetVcRxSignalLabel   OCTET STRING,
	 prtSonetVcLcasSourceState INTEGER,
	 prtSonetVcLcasSinkState   INTEGER,
	 prtSonetVcStatus	   	   Integer32,
	 prtSonetVcRxSeqNumber	   Unsigned32,
	 prtSonetVcTxSeqNumber	   Unsigned32,
	 prtSonetVcMfiDiffDelay	   Unsigned32,
	 prtSonetVcLoMF			   INTEGER,
	 prtSonetVcLoopStatus	   INTEGER,
	 prtSonetVcLcasTxStateMachineStatus	 INTEGER,
	 prtSonetVcLcasRxStateMachineStatus	 INTEGER,
	 prtSonetVcMFLengthErrorCounter		Counter32,
	 prtSonetVcCntrlPktCRCErrorCounter	Counter32
	  }

prtSonetVcRxJPathTrace OBJECT-TYPE
     SYNTAX  SnmpAdminString (SIZE(0..62))
     MAX-ACCESS  read-only
     STATUS  current
     DESCRIPTION
     "Jy Path Trace value received from network.
      y=1, 2:
      J1 - for VC-4  layer
      J2 - for VC-12 layer."
     ::= { prtSonetVcStatEntry 1 }

prtSonetVcRxSignalLabel  OBJECT-TYPE
      SYNTAX  OCTET STRING	(SIZE (1))
      MAX-ACCESS  read-only
      STATUS  current
      DESCRIPTION
      "Signal Label received from network.
       For VC-3:
       The SONET standard defines the C2 byte as
       the path signal label. The purpose of this byte is to
       communicate the payload type being encapsulated by the
       SONET Framing OverHead. It allows a single interface to
       transport multiple payload types simultaneously.

	   For VC-12, VT-1.5:
       VT path overhead V5 byte allocates bits 5-7  for
       VT Path Signal Label, to indicate the content of the VT SPE.
        000 - Unequipped
        001 - Equipped - non specific payload
        010 - Asynchronous Mapping
        011 - Bit Synchronous Mapping (no longer used)
        100 - Byte Synchronous Mapping (TU11 or TU12)
        101 - Extended Signal Label for Virtual
              Concatenation Applications (FCD-155 Default)
        110 - Test Signal (0.181) (ITU)
        111 - VC AIS (ITU)"
     ::= { prtSonetVcStatEntry 2 }

prtSonetVcLcasSourceState	OBJECT-TYPE
     SYNTAX INTEGER
     {
      notApplicable (1),
      fixed         (2),
      add           (3),
      norm          (4),
      eos           (5),
      idle          (6),
      dnu           (7)
      }
     MAX-ACCESS read-only
     STATUS current
     DESCRIPTION
     "Fixed - This is an indication that this end
              uses fixed bandwidth (non-LCAS mode)

      Add -   This member is about to be added to the group

	  Norm -  Normal transmission.

      EOS  -  End of Sequence indication
              and Normal transmission.

      Idle  - IDLE	This member is not part of
              the group or about to be removed.

      Dnu   - Do Not use - Do Not Use (the payload)
              the Sk side reported FAIL status."
     ::= { prtSonetVcStatEntry 3}

prtSonetVcLcasSinkState	OBJECT-TYPE
     SYNTAX INTEGER
     {
      notApplicable (1),
      fixed         (2),
      add           (3),
      norm          (4),
      eos           (5),
      idle          (6),
      dnu           (7)
      }
     MAX-ACCESS read-only
     STATUS current
     DESCRIPTION
     "Fixed - This is an indication that this end
              uses fixed bandwidth (non-LCAS mode)

      Add -   This member is about to be added to the group

	  Norm -  Normal transmission.

      EOS  -  End of Sequence indication
              and Normal transmission.

      Idle  - IDLE	This member is not part of
              the group or about to be removed.

      Dnu   - Do Not use - Do Not Use (the payload)
              the Sk side reported FAIL status."
     ::= { prtSonetVcStatEntry 4}

prtSonetVcStatus OBJECT-TYPE
     SYNTAX  Integer32
     MAX-ACCESS  read-only
     STATUS  current
     DESCRIPTION
     "This variable indicates the Status of the interface.
     It contains failure state information.
     The variable is a bit map represented as a sum, therefore, it
     can represent multiple failures simultaneously.
     The sonetVCNoDefect must be set if and only if no other flag is set.

     The various bit positions are:
            1   sonetVCNoDefect			   	No alarm present
            2   sonetVCLOP				   	Loss Of Pointer
            4   sonetVCPathAIS			   	Alarm Indication Signal
            8   sonetVCPathRDI			   	Remote Defect Indication
           16   sonetVCPathRFI			   	Remote Failure Indication
           									(RDI lasts for 2.5 (+-0.5) seconds)
           32   sonetVCUnequipped			Signal Label Unequipped
           64   sonetVCSignalLabelMismatch 	Signal Label Mismatch
     	  128   sonetVCEBER  	 			Excessive Bit Error Rate
      	  256   sonetVCSD    	 			Signal Degradation."
     ::= { prtSonetVcStatEntry 5 }


prtSonetVcRxSeqNumber OBJECT-TYPE
     SYNTAX  Unsigned32
     MAX-ACCESS  read-only
     STATUS  current
     DESCRIPTION
      "This variable indeticates the LCAS Rx
       sequence number of this VC."
     ::= { prtSonetVcStatEntry 6 }

prtSonetVcTxSeqNumber OBJECT-TYPE
     SYNTAX  Unsigned32
     MAX-ACCESS  read-only
     STATUS  current
     DESCRIPTION
     "This variable indicates the LCAS Tx sequence number of this VC."
     ::= { prtSonetVcStatEntry 7 }

prtSonetVcMfiDiffDelay OBJECT-TYPE
     SYNTAX  Unsigned32
     MAX-ACCESS  read-only
     STATUS  current
     DESCRIPTION
     "This variable indicates time difference (based on MFI field) from the
      fastest channel (on which it will be 0), in miliSeconds units"
     ::= { prtSonetVcStatEntry 8 }

prtSonetVcLoMF OBJECT-TYPE
     SYNTAX  INTEGER
	 {
	  notApplicable (1),
	  off (2),  -- OK
	  on  (3)  -- Loss of Multiframe defect
	 }
     MAX-ACCESS  read-only
     STATUS  current
     DESCRIPTION
     "This variable indicates loss of Multiframe defect."
     ::= { prtSonetVcStatEntry 9 }

prtSonetVcLoopStatus OBJECT-TYPE
     SYNTAX  INTEGER
	 {
	  notApplicable  (1),
	  off            (2),
	  on             (3)
	 }
     MAX-ACCESS  read-only
     STATUS  current
     DESCRIPTION
     "This variable indicates Loop Status."
     ::= { prtSonetVcStatEntry 10 }


prtSonetVcLcasTxStateMachineStatus	OBJECT-TYPE
     SYNTAX INTEGER
     {
      notApplicable (1),
      -- fixed      (2),
      add           (3),
      norm          (4),
      -- eos        (5),
      idle          (6),
      dnu           (7),
      remove        (8)
      }
     MAX-ACCESS read-only
     STATUS current
     DESCRIPTION
     "LCAS State machine status."
     ::= { prtSonetVcStatEntry 11}

prtSonetVcLcasRxStateMachineStatus	OBJECT-TYPE
     SYNTAX INTEGER
     {
      notApplicable (1),
      -- fixed      (2),
      -- add        (3),
      -- norm       (4),
      -- eos        (5),
      idle          (6),
      -- dnu        (7),
      ok            (9),
      fail          (10)
      }
     MAX-ACCESS read-only
     STATUS current
     DESCRIPTION
     "LCAS State machine status."
     ::= { prtSonetVcStatEntry 12}

prtSonetVcMFLengthErrorCounter OBJECT-TYPE
     SYNTAX  Counter32
     MAX-ACCESS  read-only
     STATUS  current
     DESCRIPTION
     "Counts the multi-frames that had wrong length (shorter or longer)"
     ::= { prtSonetVcStatEntry 13 }

prtSonetVcCntrlPktCRCErrorCounter OBJECT-TYPE
     SYNTAX  Counter32
     MAX-ACCESS  read-only
     STATUS  current
     DESCRIPTION
     "Counts Number of Control Packet CRC errors"
     ::= { prtSonetVcStatEntry 14 }


prtSonetPathProtTable  OBJECT-TYPE
    SYNTAX  SEQUENCE OF PrtSonetPathProtEntry
    MAX-ACCESS  not-accessible
    STATUS  current
    DESCRIPTION
       "Path Protection Monitoring Table "
     ::= { prtSonetStatus 2 }

prtSonetPathProtEntry OBJECT-TYPE
    SYNTAX      PrtSonetPathProtEntry
    MAX-ACCESS  not-accessible
    STATUS  current
    DESCRIPTION
       "An entry in the Path Protection monitoring Table.
        This table indicates for each protected interface
        which VCs are mapped as Working VC,
        which VCs are mapped as Protection VC,
        and which of them are currently active."
    INDEX   {prtSonetPathProtProtectedInterface,prtSonetPathProtIdx}
     ::= { prtSonetPathProtTable 1 }

PrtSonetPathProtEntry ::=
    SEQUENCE {
	 prtSonetPathProtProtectedInterface  InterfaceIndex,
	 prtSonetPathProtIdx	             Unsigned32,
	 prtSonetPathProtWorkingVc           Unsigned32,
	 prtSonetPathProtProtectionVc        Unsigned32,
	 prtSonetPathProtActiveVc            INTEGER
	  }

prtSonetPathProtProtectedInterface OBJECT-TYPE
     SYNTAX  InterfaceIndex
     MAX-ACCESS  not-accessible
     STATUS  current
     DESCRIPTION
     "Interface protected by path-protection,
      e.g. PDH (E1/T1/E3/T3) port, VCG (Virtual Concatenation Group)."
     ::= { prtSonetPathProtEntry 1 }

prtSonetPathProtIdx OBJECT-TYPE
     SYNTAX  Unsigned32
     MAX-ACCESS  not-accessible
     STATUS  current
     DESCRIPTION
     "Runing index of entries which are mapped
     to a specific interface, indicated by PrtSonetPathProtProtectedInterface.
     e.g - multiple working VCs and protection VCs are mapped to single
           Virtual Concatenation Group (VCG)."
     ::= { prtSonetPathProtEntry 2 }

prtSonetPathProtWorkingVc OBJECT-TYPE
     SYNTAX  Unsigned32
     MAX-ACCESS  read-only
     STATUS  current
     DESCRIPTION
     "A VC mapped to interface indicated by
     prtSonetPathProtProtectedInterface as
     working VC. The value of this object may be
     equal to  the value of ifIndex of working VC "
     ::= { prtSonetPathProtEntry 3 }

prtSonetPathProtProtectionVc OBJECT-TYPE
     SYNTAX  Unsigned32
     MAX-ACCESS  read-only
     STATUS  current
     DESCRIPTION
     "A VC mapped to interface indicated by
     prtSonetPathProtProtectedInterface
     as protection VC. The value of this object may be
     equal to  the value of ifIndex of protection VC "
     ::= { prtSonetPathProtEntry 4 }


prtSonetPathProtActiveVc OBJECT-TYPE
     SYNTAX  INTEGER
                {
	 			 working    (2),
				 protection (3)
	            }
     MAX-ACCESS read-only
     STATUS  current
     DESCRIPTION
     "This object indicates which of the path protection
      VCs is currently active."
     ::= { prtSonetPathProtEntry 5 }

vcGroupStat OBJECT IDENTIFIER  ::= {sonetInterface 6}

vcGroupStatTable OBJECT-TYPE
     SYNTAX  SEQUENCE OF VcGroupStatEntry
     MAX-ACCESS  not-accessible
     STATUS  current
     DESCRIPTION
     "Sonet/SDH VCG status table."
     ::= { vcGroupStat 1}

vcGroupStatEntry   OBJECT-TYPE
     SYNTAX  VcGroupStatEntry
     MAX-ACCESS  not-accessible
     STATUS  current
     DESCRIPTION
     " An entry in the Sonet/SDH VCG gen staus table."
     INDEX { ifIndex }
     ::= { vcGroupStatTable 1}

VcGroupStatEntry ::=
     SEQUENCE {
     vcGroupStatRemoteChannelStatus  OCTET STRING
     }

vcGroupStatRemoteChannelStatus OBJECT-TYPE
     SYNTAX  OCTET STRING
     MAX-ACCESS  read-only
     STATUS  current
     DESCRIPTION
     "Status of remote VCG channels as received in the local station,
      represented by 1 bit per channel. Refer to product spec for details."
     ::= { vcGroupStatEntry 1}


radAps  OBJECT IDENTIFIER  ::=  { sonetInterface 5 }


radApsEvents  OBJECT IDENTIFIER  ::=  { radAps 0 }

apsActiveChannelTrap  NOTIFICATION-TYPE
     OBJECTS       { radApsStatusCurrentWorkingChannel }
     STATUS	current
     DESCRIPTION
	 "The trap is sent upon change of Active Channel of APS Group."
     ::= { radApsEvents 1 }


radApsConfigTable OBJECT-TYPE
    SYNTAX  SEQUENCE OF RadApsConfigEntry
    MAX-ACCESS  not-accessible
    STATUS  current
    DESCRIPTION
       "An Augment to the APS Configuration Table
        (apsConfigTable in APS-MIB)."
     ::= { radAps 1 }

radApsConfigEntry OBJECT-TYPE
    SYNTAX  RadApsConfigEntry
    MAX-ACCESS  not-accessible
    STATUS  current
    DESCRIPTION
       "An entry in the table."
    AUGMENTS { apsConfigEntry }
     ::= { radApsConfigTable 1 }

RadApsConfigEntry ::=
    SEQUENCE {
		radApsConfigClearCounters		INTEGER,
		radApsConfigCommandAndStatus	INTEGER,
		radApsConfigFlipOnSD            INTEGER
		}

radApsConfigClearCounters OBJECT-TYPE
     SYNTAX  INTEGER {
     	off(2),
	 	on (3)
	 }
     MAX-ACCESS  read-create
     STATUS  current
     DESCRIPTION
     "Setting this object to on(3) will clear APS Counters.
      Upon performing this operation, the value will be
      automatically changed to off(2)."
     ::= { radApsConfigEntry 1}

radApsConfigCommandAndStatus OBJECT-TYPE
     SYNTAX  INTEGER {
     	noOp			(1),
		clear			(2),
     	forcedSwitch	(3),
		lockout			(4)
	 }
     MAX-ACCESS  read-create
     STATUS  current
     DESCRIPTION
     "noOp			- 	initial state only (cannot be Set by user).

	  clear			-	clearing the last performed command.
						Can be Set only if previous state was other than noOp or clear.

	  forcedSwitch	- 	transferring service from primary channel to the secondary channel.
						Can be Set only if previous state was noOp or clear.
						If the non-Active channel is failed, the command will be rejected.

	  lockout		-	freezing the current state.
						In 1+1 Bidirectional Optimized switching, Lockout is considered
						as a local request which is not signalled across the K-bytes.
						The effect of lockout is to freeze the selector position
						and transmitted	K-bytes until the lockout request is cleared.
						Can be Set only if previous state was noOp or Clear."
     ::= { radApsConfigEntry 2}


radApsConfigFlipOnSD OBJECT-TYPE
     SYNTAX  INTEGER {
     	no  (2),
	 	yes (3)
	 }
     MAX-ACCESS  read-create
     STATUS  current
     DESCRIPTION
     "Flip active channel according to SD (Signal Degradation)."
     ::= { radApsConfigEntry 3}



radApsStatusTable OBJECT-TYPE
    SYNTAX  SEQUENCE OF RadApsStatusEntry
    MAX-ACCESS  not-accessible
    STATUS  current
    DESCRIPTION
       "An Augment to the APS Status Table
        (apsStatusTable in APS-MIB)."
     ::= { radAps 2 }

radApsStatusEntry OBJECT-TYPE
    SYNTAX  RadApsStatusEntry
    MAX-ACCESS  not-accessible
    STATUS  current
    DESCRIPTION
       "An entry in the table."
    AUGMENTS { apsConfigEntry }
     ::= { radApsStatusTable 1 }

RadApsStatusEntry ::=
    SEQUENCE {
		radApsStatusCurrentWorkingChannel		Integer32
		}

radApsStatusCurrentWorkingChannel OBJECT-TYPE
     SYNTAX  Integer32
     MAX-ACCESS  read-only
     STATUS  current
     DESCRIPTION
     "This object indicates the port/interface index of
      the Current Working Channel."
     ::= { radApsStatusEntry 1}



prtVcGroupCnfg  OBJECT IDENTIFIER  ::=  {prtSonetConfig 4}

vcGroupCnfgTable OBJECT-TYPE
    SYNTAX  SEQUENCE OF VcGroupCnfgEntry
    MAX-ACCESS  not-accessible
    STATUS  current
    DESCRIPTION
       "The Virtual Concatenation Group configuration table."
    ::= { prtVcGroupCnfg 1 }

vcGroupCnfgEntry OBJECT-TYPE
    SYNTAX  VcGroupCnfgEntry
    MAX-ACCESS  not-accessible
    STATUS  current
    DESCRIPTION
       "An entry in the Virtual Concatenation Group
        configuration table."
    INDEX   { vcGroupCnfgIdx,vcGroupCnfgNumber}
    ::= { vcGroupCnfgTable 1 }

VcGroupCnfgEntry ::= SEQUENCE {
    vcGroupCnfgIdx               Integer32,
    vcGroupCnfgNumber            Integer32,
    vcGroupCnfgRowStatus         RowStatus,
    vcGroupCnfgVcType            INTEGER,
    vcGroupCnfgNoOfVCs           Integer32,
    vcGroupCnfgLCAS              INTEGER,
    vcGroupCnfgEncapsulation     INTEGER,
    vcGroupCnfgGroupIfIndex      InterfaceIndex,
    vcGroupCnfgRip2              INTEGER,
    vcGroupCnfgGfpChId           Integer32,
    vcGroupCnfgK4                INTEGER,
    vcGroupCnfgExSignalLabel     OCTET STRING,
    vcGroupCnfgLcasMinNoOfVCs    Integer32,
    vcGroupCnfgLcasStatus        INTEGER,
    vcGroupCnfgMappingMode       INTEGER,
    vcGroupCnfgTrafficType       INTEGER,
    vcGroupCnfgGroupName         SnmpAdminString,
    vcGroupCnfgLoopDetection     INTEGER,
    vcGroupCnfgLcasWaitToRestore Unsigned32,
    vcGroupCnfgLcasHoldOff       Unsigned32
 }

vcGroupCnfgIdx OBJECT-TYPE
    SYNTAX  Integer32 (1..255)
    MAX-ACCESS  not-accessible
    STATUS  current
    DESCRIPTION
     "This object indicates the Idx of the Config being accessed.
      Idx of 255 relates to the Temporary (Scratch) Config.
      For products that support several configurations, Set can be performed
      only to the Temporary Config (=255). "
    ::= { vcGroupCnfgEntry 1}

vcGroupCnfgNumber OBJECT-TYPE
    SYNTAX    Integer32
     MAX-ACCESS not-accessible
     STATUS current
     DESCRIPTION
      "Virtual Concatenation Group Number.
       For FCD-155 up to eight groups are defined
       valid values are 1..8.
       For MP-4100, group ifIndex is used."
     ::= { vcGroupCnfgEntry 2}

vcGroupCnfgRowStatus OBJECT-TYPE
     SYNTAX RowStatus
     MAX-ACCESS read-create
     STATUS current
     DESCRIPTION
      "Creation/Deletion of rows in the table."
     ::= { vcGroupCnfgEntry 3}

vcGroupCnfgVcType OBJECT-TYPE
     SYNTAX INTEGER
      {
       notApplicable  (1),
       vc12           (2), --SDH
       vc3            (3), --SDH
       vc4            (4), --SDH
       vt1dot5        (5), --SONET VT1.5
       sts1           (6), --SONET STS1 /SPE
       sts12c         (7),  --STS12c
       vcFour4c       (8)  --VC4-4c
       }
     MAX-ACCESS read-create
     STATUS current
     DESCRIPTION
      "User may select type of SDH Virtual Containers (VC)
       (SONET Virtual Tributaries VT ) to be concatenated
       in this Virtual Concatenation Group.
       For SDH,  values 2,3,4 and 8 are valid.
       For SONET, values 5, 6,7 are valid."
     ::= { vcGroupCnfgEntry 4}

vcGroupCnfgNoOfVCs  OBJECT-TYPE
    SYNTAX    Integer32 (0..84)
     MAX-ACCESS read-create
     STATUS current
     DESCRIPTION
      "User may select number of  Virtual Containers (VC)
       (SONET Virtual Tributaries VT ) to be concatenated
       in this Virtual Concatenation Group.
       Valid range for this number depends on
       type VC selected by vcGroupCnfgVCType
       For SDH,  up to 63 VC12, or
                 up to 3  VC3,  or
                       1  VC4  are valid
       For SONET, up to 84 VT1.5 without LCAS,
                  or 64 VT1.5 under  LCAS control.
                  or up tp 3 STS-1/SPE, or
                           1 STS-3"
     ::= { vcGroupCnfgEntry 5}

vcGroupCnfgLCAS OBJECT-TYPE
     SYNTAX INTEGER
      {
       notApplicable (1),
       lcasNotActive (2),
       lcasActive    (3)
       }
     MAX-ACCESS read-create
     STATUS current
     DESCRIPTION
      "This object controls Link Capacity Adjustment
      Scheme (LCAS)  activation."
     ::= { vcGroupCnfgEntry 6}

vcGroupCnfgEncapsulation OBJECT-TYPE
     SYNTAX INTEGER
      {
       notApplicable (1),
       laps          (2), -- Link access protocol S
       lapf          (3), -- Link access protocol F (Frame relay)
       gfp           (4)  -- Generic Framing Procedure
       }
     MAX-ACCESS read-create
     STATUS current
     DESCRIPTION
      "This object enables user to select encapsulation method."
     ::= { vcGroupCnfgEntry 7}


vcGroupCnfgGroupIfIndex  OBJECT-TYPE
     SYNTAX InterfaceIndex
     MAX-ACCESS read-only
     STATUS current
     DESCRIPTION
      "The ifIndex assigend to this group."
     ::= { vcGroupCnfgEntry 8}

vcGroupCnfgRip2 OBJECT-TYPE
     SYNTAX INTEGER
      {
       notApplicable (1),
       no            (2),
       yes           (3)
       }
     MAX-ACCESS read-create
     STATUS current
     DESCRIPTION
      "This object controls RIP 2.
      User may select to send RIP 2 message over
      selected group or not"
     ::= { vcGroupCnfgEntry 9}


vcGroupCnfgGfpChId  OBJECT-TYPE
     SYNTAX    Integer32 (0..255)
     MAX-ACCESS read-create
     STATUS current
     DESCRIPTION
      "Generic Framing Procedure (GFP) Channel ID,
      Valid only when vcGroupCnfgEncapsulation = gfp (4)
      Valid values are 0x00 - oxFF  (hex) "
     ::= { vcGroupCnfgEntry 10}


vcGroupCnfgK4  OBJECT-TYPE
     SYNTAX INTEGER
      {
       notApplicable (1),
       no            (2),
       yes           (3)
       }
     MAX-ACCESS read-create
     STATUS current
     DESCRIPTION
      "This object controls whether K4 byte
       (of Line Overhead) is used as an indication for
       virtual concatenation (VCAT).
       This object is applicable, when VCG
       includes only a single Virtual Container (VC)
       (or SONET VT)  "
     ::= { vcGroupCnfgEntry 11}

vcGroupCnfgExSignalLabel  OBJECT-TYPE
     SYNTAX  OCTET STRING   (SIZE (1))
     MAX-ACCESS  read-create
     STATUS  current
     DESCRIPTION
      "Extended Signal Label.
       Relevant only when vcGroupCnfgK4 = yes(3).
       Agents that do not support this feature will send SIZE 0."
    ::= { vcGroupCnfgEntry 12 }

vcGroupCnfgLcasMinNoOfVCs  OBJECT-TYPE
     SYNTAX    Integer32 (0..83)
     MAX-ACCESS read-create
     STATUS current
     DESCRIPTION
      "Minimum number of VC's to declare alarm, in LCAS mode.
       Applicable only when LCAS is active
       (vcGroupCnfgLCAS =lcasActive)
       1...63 for SDH, 1...84 for SONET
       0= not applicable. "
     ::= { vcGroupCnfgEntry 13}

vcGroupCnfgLcasStatus  OBJECT-TYPE
     SYNTAX INTEGER
      {
       notApplicable    (1),
       belowMinNoOfVCs  (2),
       withinRange      (3),
       allNorm          (4)
       }
     MAX-ACCESS read-only
     STATUS current
     DESCRIPTION
      "This object summarize LCAS states of all VCs in VCG:

       belowMinNoOfVCs -  Number of VCs in Norm state is less than
                          the minimum number of VCs
                          (indicated by vcGroupCnfgLcasMinNoOfVCs)

      withinRange - Number of VCs in Norm state is higher than
                    the minimum number of VCs
                    indicated by vcGroupCnfgLcasMinNoOfVCs)
                    but is lower than Number of VCs mapped

       allNorm - Number of VCs in Norm state equals
                 number of mapped VCs. "
     ::= { vcGroupCnfgEntry 14}

vcGroupCnfgMappingMode  OBJECT-TYPE
     SYNTAX INTEGER
      {
       notApplicable    (1),
       off              (2),
       auto             (3),
       manual           (4)
       }
     MAX-ACCESS read-create
     STATUS current
     DESCRIPTION
      "This object define Path Protection mode for VCG.
       Auto -  the entire mapping for Virtual Concatenation Group x
       is copied  automatically by agent for the protection group
       to same TUs on the other SONET/SDH link which reside on same slot..
       Manual - the user may configure mapping for the protection group
       on the same link as for other group, or on the other link(s).
       Same type of TUs  should be used for both groups.
       The TUs selected for each group don't have to be the same."
     ::= { vcGroupCnfgEntry 15}

vcGroupCnfgTrafficType  OBJECT-TYPE
     SYNTAX INTEGER
      {
       notApplicable  (1),
       managementOnly (2),
       dataOnly       (3),
       mixed          (4)
       }
     MAX-ACCESS read-create
     STATUS current
     DESCRIPTION
      "This object allows to select traffic type for
       specific VCG."
     ::= { vcGroupCnfgEntry 16}

vcGroupCnfgGroupName  OBJECT-TYPE
     SYNTAX     SnmpAdminString
     MAX-ACCESS read-create
     STATUS current
     DESCRIPTION
      "Virtual Concatenation Group (VCG) Name.
       String length is limited to 15 characters."
     ::= { vcGroupCnfgEntry 17}

vcGroupCnfgLoopDetection  OBJECT-TYPE
     SYNTAX     INTEGER
      {
      notApplicable (1),
      disabled      (2),
      enabeld       (3)
      }
     MAX-ACCESS read-create
     STATUS current
     DESCRIPTION
      "VCAT Loop detecetion enabled."
     ::= { vcGroupCnfgEntry 18}

vcGroupCnfgLcasWaitToRestore OBJECT-TYPE
     SYNTAX     Unsigned32
     MAX-ACCESS read-create
     STATUS current
     DESCRIPTION
      "Time duration (in milliseconds units) waited after
      errors on channel stopped, before channel is reused."
     ::= { vcGroupCnfgEntry 19}

vcGroupCnfgLcasHoldOff OBJECT-TYPE
     SYNTAX     Unsigned32
     MAX-ACCESS read-create
     STATUS current
     DESCRIPTION
      "Time duration (in milliseconds units) in which errors on channel
      are disregarded. (Threshold)"
     ::= { vcGroupCnfgEntry 20}


vcgGfpMuxCnfgTable	OBJECT-TYPE
      SYNTAX  SEQUENCE OF VcgGfpMuxCnfgEntry
      MAX-ACCESS  not-accessible
      STATUS  current
      DESCRIPTION
      "The Virtual Concatenation Group GFP Mux configuration table."
       ::= { prtVcGroupCnfg 2 }

-- This table defines multiplexing scheme for GFP mux of
-- Virtual Concatenation Groups:
-- Primary group, Secondary group/s and bandwidth allocation
-- to each group.

vcgGfpMuxCnfgEntry OBJECT-TYPE
      SYNTAX  VcgGfpMuxCnfgEntry
      MAX-ACCESS  not-accessible
      STATUS  current
      DESCRIPTION
      "An entry in the Virtual Concatenation Group GFP Mux
       configuration table."
      INDEX   { vcgGfpMuxCnfgIdx,vcgGfpMuxCnfgMuxNumber}
       ::= { vcgGfpMuxCnfgTable 1 }

VcgGfpMuxCnfgEntry ::=
    SEQUENCE {
 		      vcgGfpMuxCnfgIdx     Integer32,
			  vcgGfpMuxCnfgMuxNumber   Integer32,
 		      vcgGfpMuxCnfgRowStatus   RowStatus,
			  vcgGfpMuxCnfgMuxName     SnmpAdminString,
 		      vcgGfpMuxCnfgPrimeGroup  Integer32,
  		      vcgGfpMuxCnfgGrpBwAlloc  OCTET STRING
 		      }

vcgGfpMuxCnfgIdx OBJECT-TYPE
      SYNTAX  Integer32 (1..255)
      MAX-ACCESS  not-accessible
      STATUS  current
      DESCRIPTION
      "This object indicates the Index of the configuration being accessed.
       Index of 255 relates to the Temporary (Scratch) coninguration.
       For products that support several configurations, Set can be performed
       only to the Temporary Config (=255). "
      ::= { vcgGfpMuxCnfgEntry 1}

vcgGfpMuxCnfgMuxNumber OBJECT-TYPE
      SYNTAX    Integer32
      MAX-ACCESS not-accessible
      STATUS current
      DESCRIPTION
      "Virtual Concatenation Group GFP Mux Number.
       Refer to device specification for definition of
        - maximum number of GFP-mux.
        - concatenation of Slot and GFP mux number."
      ::= { vcgGfpMuxCnfgEntry 2}

vcgGfpMuxCnfgRowStatus OBJECT-TYPE
      SYNTAX RowStatus
      MAX-ACCESS read-create
      STATUS current
      DESCRIPTION
      "Creation/Deletion of rows in the table."
      ::= { vcgGfpMuxCnfgEntry 3}

vcgGfpMuxCnfgMuxName  OBJECT-TYPE
      SYNTAX    SnmpAdminString
      MAX-ACCESS read-create
      STATUS current
      DESCRIPTION
      "Virtual Concatenation Group, GFP Mux name."
      ::= { vcgGfpMuxCnfgEntry 4}

vcgGfpMuxCnfgPrimeGroup OBJECT-TYPE
     SYNTAX  Integer32
     MAX-ACCESS  read-create
     STATUS  current
     DESCRIPTION
     "Index of Virtual Concatenation Group used as
      Primary for the GFP mux created
      for FCD 155 up to 8 Virtual Concatenation Group are defined:
      1 -> Virtual Concatenation Group 1
	  2 -> Virtual Concatenation Group 2
      3 -> Virtual Concatenation Group 3
      4 -> Virtual Concatenation Group 4
      5 -> Virtual Concatenation Group 5
	  6 -> Virtual Concatenation Group 6
      7 -> Virtual Concatenation Group 7
      8 -> Virtual Concatenation Group 8
      "
     ::= { vcgGfpMuxCnfgEntry 5}

vcgGfpMuxCnfgGrpBwAlloc OBJECT-TYPE
     SYNTAX  OCTET STRING
     MAX-ACCESS  read-create
     STATUS  current
     DESCRIPTION
     "This object indicates the  allocated bandwidth (BW) to each
     Virtual Concatenation Group (VCG).
     Each nibble indicates BW percentage, in 12.5% steps,
     assigned to a group.

     For FCD-155, there may be 4 or 8 VCGs. When only 4 VCG exists,
	 only two octets are used.
     In current GFP Mux,one VCG is identified as primary group
     by vcGfpMuxConfPrimeGroup.
	 Other VCGs may be secondaries.
	 VCG with allocated BW value of zero does not belong to the GFPmux
	 defined by GFP Mux number.
	          ________________________________________
	         |     Octet 0       |     Octet 1       |
             |Nibble 4 | Nibble 3| Nibble 2| Nibble 1|
	   MSB   | 7 6 5 4 | 3 2 1 0 | 7 6 5 4 | 3 2 1 0 |
			 +___________________+___________________+
	           VCG1        VCG2     VCG 3    VCG4

	          ________________________________________
	         |     Octet 3       |     Octet 4       |
             |Nibble 4 | Nibble 3| Nibble 2| Nibble 1|
	         | 7 6 5 4 | 3 2 1 0 | 7 6 5 4 | 3 2 1 0 | LSB
			 +___________________+___________________+
	           VCG5        VCG6     VCG 7    VCG8


       Nibble value - BW Percentage
       (0...7)         (0 ...87.5%)
      1   0001            12.5 %
      2   0010 		      25%
	  3   0011            37.5
	  .....
	  7   0111            87.5%

	  at least one nibble must be greater that zero.
	  Sum of alloacted BW must be 100%.
	  Primary VCG BW must be greater than zero."
     ::= { vcgGfpMuxCnfgEntry 6}


virtualIfConfiguration  OBJECT IDENTIFIER  ::=  { prtSonetConfig 5}

virtualIfGenTable OBJECT-TYPE
     SYNTAX  SEQUENCE OF VirtualIfGenEntry
     MAX-ACCESS  not-accessible
     STATUS  current
     DESCRIPTION
     "Sonet/SDH general port configuration table."
     ::= { virtualIfConfiguration 1}

virtualIfGenEntry   OBJECT-TYPE
     SYNTAX  VirtualIfGenEntry
     MAX-ACCESS  not-accessible
     STATUS  current
     DESCRIPTION
     " An entry in the Sonet/SDH general port configuration table."
     INDEX { virtualIfGenCnfgIdx, virtualIfGenIdx }
     ::= { virtualIfGenTable 1}

VirtualIfGenEntry ::=
     SEQUENCE {
     virtualIfGenCnfgIdx
     Integer32,
     virtualIfGenIdx
     Integer32,
     virtualIfGenFrameFormat
     INTEGER
      }

virtualIfGenCnfgIdx OBJECT-TYPE
     SYNTAX  Integer32 (1..255)
     MAX-ACCESS  read-only
     STATUS  current
     DESCRIPTION
     "This object indicates the Idx of the Config being accessed.
      Idx of 255 relates to the Temporary (Scratch) Config.
      For products that support several configurations, Set can be performed
      only to the Temporary Config (=255). "
     ::= { virtualIfGenEntry 1}

virtualIfGenIdx OBJECT-TYPE
     SYNTAX  Integer32
     MAX-ACCESS  read-only
     STATUS  current
     DESCRIPTION
     "This object indicates a unique  port or interface number.
	 For numbering, see product's spec.
     For some products, the numbering can equal ifIndex."
     ::= { virtualIfGenEntry 2}

virtualIfGenFrameFormat OBJECT-TYPE
     SYNTAX  INTEGER {
     notApplicable(1),
     fcsEnable     (2),
     fcsDisable   (3)

     }
     MAX-ACCESS  read-write
     STATUS  current
     DESCRIPTION
     "The frame format.
      fcsEnabe = Frame will be sent with the FCS bits.
      fcsDisable = Frame will be sent without the FCS bits ."
     ::= { virtualIfGenEntry 3 }
-----------------------------------
-- System Common Trap Definitions
-----------------------------------

sonetAlarmLOS  NOTIFICATION-TYPE
	OBJECTS  {alarmSeverity, alarmState, ifAlias}
	STATUS  current
	DESCRIPTION
	"This trap indicates Loss Of Signal."
	::= { prtSonetEvents 1 }

sonetAlarmLOF  NOTIFICATION-TYPE
	OBJECTS  {alarmSeverity, alarmState, ifAlias}
	STATUS  current
	DESCRIPTION
	"This trap indicates Loss Of Frame."
	::= { prtSonetEvents 2 }

sonetAlarmOOF  NOTIFICATION-TYPE
	OBJECTS  {alarmSeverity, alarmState, ifAlias}
	STATUS  current
	DESCRIPTION
	"This trap indicates Out Of Frame."
	::= { prtSonetEvents 3 }

sonetAlarmLineAIS  NOTIFICATION-TYPE
	OBJECTS  {alarmSeverity, alarmState, ifAlias}
	STATUS  current
	DESCRIPTION
	"This trap indicates Line Alarm Indication Signal."
	::= { prtSonetEvents 4 }

sonetAlarmLineEED  NOTIFICATION-TYPE
	OBJECTS  {alarmSeverity, alarmState, ifAlias}
	STATUS  current
	DESCRIPTION
	"This trap indicates Line Excessive Error Detect."
	::= { prtSonetEvents 5 }

sonetAlarmLineRDI  NOTIFICATION-TYPE
	OBJECTS  {alarmSeverity, alarmState, ifAlias}
	STATUS  current
	DESCRIPTION
	"This trap indicates Line Remote Defect Indication."
	::= { prtSonetEvents 6 }

sonetAlarmLineSD  NOTIFICATION-TYPE
	OBJECTS  {alarmSeverity, alarmState, ifAlias}
	STATUS  current
	DESCRIPTION
	"This trap indicates Line Signal Degrade."
	::= { prtSonetEvents 7 }

sonetAlarmPathLOP  NOTIFICATION-TYPE
	OBJECTS  {alarmSeverity, alarmState, ifAlias}
	STATUS  current
	DESCRIPTION
	"This trap indicates Path Loss of Pointer."
	::= { prtSonetEvents 8 }

sonetAlarmPathAIS  NOTIFICATION-TYPE
	OBJECTS  {alarmSeverity, alarmState, ifAlias}
	STATUS  current
	DESCRIPTION
	"This trap indicates Path Alarm Indication Signal."
	::= { prtSonetEvents 9 }

sonetAlarmPathEED  NOTIFICATION-TYPE
	OBJECTS  {alarmSeverity, alarmState, ifAlias}
	STATUS  current
	DESCRIPTION
	"This trap indicates Path Excessive Error Detect."
	::= { prtSonetEvents 10 }

sonetAlarmPathSLM  NOTIFICATION-TYPE
	OBJECTS  {alarmSeverity, alarmState, ifAlias}
	STATUS  current
	DESCRIPTION
	"This trap indicates Path Signal Label Mismatch."
	::= { prtSonetEvents 11 }

sonetAlarmPathLOMF  NOTIFICATION-TYPE
	OBJECTS  {alarmSeverity, alarmState, ifAlias}
	STATUS  current
	DESCRIPTION
	"This trap indicates Path Loss of Multi-Frame."
	::= { prtSonetEvents 12 }

sonetAlarmPathRDI  NOTIFICATION-TYPE
	OBJECTS  {alarmSeverity, alarmState, ifAlias}
	STATUS  current
	DESCRIPTION
	"This trap indicates Path Remote Defect Indication."
	::= { prtSonetEvents 13 }

sonetAlarmPathSD  NOTIFICATION-TYPE
	OBJECTS  {alarmSeverity, alarmState, ifAlias}
	STATUS  current
	DESCRIPTION
	"This trap indicates Path Signal Degrade."
	::= { prtSonetEvents 14 }

sonetAlarmVtLOP  NOTIFICATION-TYPE
	OBJECTS  {alarmSeverity, alarmState, ifAlias}
	STATUS  current
	DESCRIPTION
	"This trap indicates VT Loss of Pointer."
	::= { prtSonetEvents 15 }

sonetAlarmVtAIS  NOTIFICATION-TYPE
	OBJECTS  {alarmSeverity, alarmState, ifAlias}
	STATUS  current
	DESCRIPTION
	"This trap indicates VT Alarm Indication Signal."
	::= { prtSonetEvents 16 }

sonetAlarmVtEED  NOTIFICATION-TYPE
	OBJECTS  {alarmSeverity, alarmState, ifAlias}
	STATUS  current
	DESCRIPTION
	"This trap indicates VT Excessive Error Detect."
	::= { prtSonetEvents 17 }

sonetAlarmVtSLM  NOTIFICATION-TYPE
	OBJECTS  {alarmSeverity, alarmState, ifAlias}
	STATUS  current
	DESCRIPTION
	"This trap indicates VT Signal Label Mismatch."
	::= { prtSonetEvents 18 }

sonetAlarmVtRDI  NOTIFICATION-TYPE
	OBJECTS  {alarmSeverity, alarmState, ifAlias}
	STATUS  current
	DESCRIPTION
	"This trap indicates VT Remote Defect Indication."
	::= { prtSonetEvents 19 }

sonetAlarmVtSD  NOTIFICATION-TYPE
	OBJECTS  {alarmSeverity, alarmState, ifAlias}
	STATUS  current
	DESCRIPTION
	"This trap indicates VT Signal Degrade."
	::= { prtSonetEvents 20 }

-- VCG MINIMUM MEMBERS TCA

vcgMinimumMembers    NOTIFICATION-TYPE
	OBJECTS { alarmEventLogSourceName, alarmEventLogAlarmOrEventId, alarmEventLogDescription,
     alarmEventLogSeverity, alarmEventLogDateAndTime, alarmEventReason,
     ifAlias, vcGroupCnfgLcasMinNoOfVCs }
     STATUS  current
     DESCRIPTION
      "This trap indicates that number of Members of VCG is less than
      the minimum defined by vcGroupCnfgLcasMinNoOfVCs
      (Thresdhold Crossing Alarm)."
     ::= { prtSonetEvents 21 }


--SDH/SONET LOF
sdhSonetLof NOTIFICATION-TYPE
	OBJECTS { alarmEventLogSourceName, alarmEventLogAlarmOrEventId, alarmEventLogDescription,
     alarmEventLogSeverity, alarmEventLogDateAndTime, alarmEventReason,
     ifAlias, prtSonetCurrentXStatus }
     STATUS  current
     DESCRIPTION
      "This trap indicates SDH/SONET Loss of frame (LOF).
      "
     ::= {prtSonetEvents  22}

--SDH/SONET LOS
sdhSonetLos     NOTIFICATION-TYPE
	OBJECTS { alarmEventLogSourceName, alarmEventLogAlarmOrEventId, alarmEventLogDescription,
     alarmEventLogSeverity, alarmEventLogDateAndTime, alarmEventReason,
     ifAlias, prtSonetCurrentXStatus }
     STATUS  current
     DESCRIPTION
      "This trap indicates SDH/SONET Loss of Signal.
      "
     ::= {prtSonetEvents  24}

--SDH/SONET AIS
sdhSonetAis     NOTIFICATION-TYPE
	OBJECTS { alarmEventLogSourceName, alarmEventLogAlarmOrEventId, alarmEventLogDescription,
     alarmEventLogSeverity, alarmEventLogDateAndTime, alarmEventReason,
     ifAlias, prtSonetCurrentXStatus }
     STATUS  current
     DESCRIPTION
      "This trap indicates SDH/SONET Alarm Indication Signal (AIS)
      "
     ::= {prtSonetEvents  25}

--SDH/SONET SD
sdhSonetSd      NOTIFICATION-TYPE
	OBJECTS { alarmEventLogSourceName, alarmEventLogAlarmOrEventId, alarmEventLogDescription,
     alarmEventLogSeverity, alarmEventLogDateAndTime, alarmEventReason,
     ifAlias, prtSonetCurrentXStatus }
     STATUS  current
     DESCRIPTION
      "This trap indicates SDH/SONET Signal Degradation (SD)
      "
     ::= {prtSonetEvents 27}

--SDH/SONET EED
sdhSonetEed     NOTIFICATION-TYPE
	OBJECTS { alarmEventLogSourceName, alarmEventLogAlarmOrEventId, alarmEventLogDescription,
     alarmEventLogSeverity, alarmEventLogDateAndTime, alarmEventReason,
     ifAlias, prtSonetCurrentXStatus }
     STATUS  current
     DESCRIPTION
      "This trap indicates SDH/SONET Excessive Error Defect (EED)
      "
     ::= {prtSonetEvents 28  }

vcgDifferentialDelayExceeded              NOTIFICATION-TYPE
	OBJECTS { alarmEventLogSourceName, alarmEventLogAlarmOrEventId, alarmEventLogDescription,
     alarmEventLogSeverity, alarmEventLogDateAndTime, alarmEventReason,
     ifAlias }
      STATUS  current
      DESCRIPTION
      "Differential delay between VCG links exceeded the maximum allowed."
      ::= { prtSonetEvents 92 }

vcgLoa                       NOTIFICATION-TYPE
	OBJECTS { alarmEventLogSourceName, alarmEventLogAlarmOrEventId, alarmEventLogDescription,
     alarmEventLogSeverity, alarmEventLogDateAndTime, alarmEventReason,
     ifAlias }
      STATUS  current
      DESCRIPTION
      "VCG loss of alignment (LOA) occurred"
      ::= { prtSonetEvents 93 }

 vcgLoopDetection NOTIFICATION-TYPE
	OBJECTS { alarmEventLogSourceName, alarmEventLogAlarmOrEventId, alarmEventLogDescription,
     alarmEventLogSeverity, alarmEventLogDateAndTime, alarmEventReason,
     ifAlias, ifAlias }
    STATUS  current
    DESCRIPTION
    "VCG Loop was detected.
     The first  ifAlias that is attached is the Group's  ifAlias (Example: GFP).
     The second ifAlias that is attached is the Member's ifAlias (Example: VCG)."
    ::= { prtSonetEvents 95 }

END
