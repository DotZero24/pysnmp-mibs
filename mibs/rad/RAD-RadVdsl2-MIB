RAD-RadVdsl2-MIB DEFINITIONS ::= BEGIN


-- It is RAD's intent to encourage the widespread use of
-- this Specification in connection with the management of
-- RAD products. RAD grants vendors, end-users,
-- and other interested parties a non-exclusive license to
-- use this Specification in connection with the management
-- of RAD products.

-- This Specification is supplied "as is," and RAD makes
-- no warranty, either express or implied, as to the use,
-- operation, condition, or performance of the Specification.


IMPORTS

       ifAlias, ifIndex     FROM  IF-MIB
       OBJECT-TYPE, MODULE-IDENTITY, NOTIFICATION-TYPE     FROM  SNMPv2-SMI
       diverseIfWanGen     FROM  RAD-SMI-MIB
       alarmEventLogSourceName, alarmEventLogAlarmOrEventId, alarmEventLogDescription,
       alarmEventLogSeverity, alarmEventLogDateAndTime, alarmEventReason     FROM  RAD-GEN-MIB;

    vdsl2If MODULE-IDENTITY
        LAST-UPDATED "201504021753Z"  -- April 02, 2015
        ORGANIZATION "RAD Data Communications Ltd."
        CONTACT-INFO
        "System Department

         Email:  mibs@rad.com
         Postal: RAD Data Communications Ltd.
                 24 Raoul Wallenberg St.
                 Tel-Aviv 6971920
                 Israel

         Phone:  +972-3-645-5421
         Fax:    +972-3-760-7844"
         DESCRIPTION
            "VDSL2 MIB."
    ::= { diverseIfWanGen 19 }


vdsl2Events   OBJECT IDENTIFIER ::= { vdsl2If 0 }
vdsl2Objects  OBJECT IDENTIFIER ::= { vdsl2If 1 }


-- --------------------------
-- VSDL2 Objects
-- --------------------------

--VDSL2 Notifications Varbinds

vdsl2IfNotifVarbindTable OBJECT-TYPE
    SYNTAX      SEQUENCE OF Vdsl2IfNotifVarbindEntry
    MAX-ACCESS  not-accessible
    STATUS      current
    DESCRIPTION
    "This table provides VDSL2 notifications varbind values per interface
     index."
    ::= { vdsl2Objects 2 }

vdsl2IfNotifVarbindEntry OBJECT-TYPE
    SYNTAX      Vdsl2IfNotifVarbindEntry
    MAX-ACCESS  not-accessible
    STATUS      current
    DESCRIPTION
    "An entry in the vdsl2IfNotifVarbindTable."
    INDEX { ifIndex, vdsl2SideIdx}
    ::= { vdsl2IfNotifVarbindTable 1 }

Vdsl2IfNotifVarbindEntry ::= SEQUENCE {
    vdsl2SideIdx                   INTEGER,
    vdsl2LinkDownReason            INTEGER
 }

vdsl2SideIdx OBJECT-TYPE
    SYNTAX  INTEGER
    {
    nearEnd (2),
    farEnd  (3)
    }
    MAX-ACCESS  not-accessible
    STATUS      current
    DESCRIPTION
    "This object indicates the side of the managed object: Near-End or
     Far-End."
    ::= {vdsl2IfNotifVarbindEntry 1}

vdsl2LinkDownReason          OBJECT-TYPE
      SYNTAX                 INTEGER
		{
		lossOfFraming   (1), -- Loss of frame synchronization
		lossOfSignal   	(2), -- Loss of signal
		lossOfPower   	(3), -- Loss of power. Usually this failure may be reported for CPE units only.
		initFailure     (4) -- Recent initialization process failed. Never active on xTU-R.
		}
    MAX-ACCESS  accessible-for-notify
      STATUS      current
      DESCRIPTION
       " This object provides the reason for the VDSL2 link down.
       "
   ::= { vdsl2IfNotifVarbindEntry 2 }


-- -----------------------------
    -- VSDL2 Notifications
-- -----------------------------

vdsl2LinkDown   NOTIFICATION-TYPE
	OBJECTS { alarmEventLogSourceName, alarmEventLogAlarmOrEventId, alarmEventLogDescription,
     alarmEventLogSeverity, alarmEventLogDateAndTime, alarmEventReason,
     ifAlias, vdsl2LinkDownReason }
    STATUS  current
    DESCRIPTION
    "This trap indicates that the VDSL2 link is down."
    ::= { vdsl2Events 1 }


END
