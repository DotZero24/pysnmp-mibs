RAD-TC DEFINITIONS ::= BEGIN


-- It is RAD's intent to encourage the widespread use of
-- this Specification in connection with the management of
-- RAD products. RAD grants vendors, end-users,
-- and other interested parties a non-exclusive license to
-- use this Specification in connection with the management
-- of RAD products.

-- This Specification is supplied "as is," and RAD makes
-- no warranty, either express or implied, as to the use,
-- operation, condition, or performance of the Specification.


IMPORTS

MODULE-IDENTITY                                      FROM SNMPv2-SMI
TEXTUAL-CONVENTION                                   FROM SNMPv2-TC
rad                                                  FROM RAD-SMI-MIB;


    radTextualConventions MODULE-IDENTITY
        LAST-UPDATED "201608041854Z"  -- August 04, 2016
        ORGANIZATION "RAD Data Communications Ltd."
        CONTACT-INFO
        "System Department

         Email:  mibs@rad.com
         Postal: RAD Data Communications Ltd.
                 24 Raoul Wallenberg St.
                 Tel-Aviv 6971920
                 Israel

         Phone:  +972-3-645-5421
         Fax:    +972-3-760-7844"
         DESCRIPTION
            "Textual Convention MIB."
    ::= { rad 100 }


DayType ::= TEXTUAL-CONVENTION
    STATUS      current
    DESCRIPTION
            "This index defines access to the statistics of either previous or
            current day."
    SYNTAX      INTEGER
        {
        current  (1),
        previous (2)
        }

ProtectClassType ::= TEXTUAL-CONVENTION
    STATUS  current
    DESCRIPTION
            "This type defines the different protection group types.
            eps (6),  - According to G.8031 Ethernet Protection Switching.
            tpCmdChannel (8)  - for Tele Protection Cmd-Channel
                "
    SYNTAX      INTEGER
        {
        mainCard     (1),
        ioCard       (2),
        ethernetPort (3),
        pathSdhSonet (4),
        tdmPw        (5),
        eps          (6),
        tdmPort      (7),
        tpCmdChannel (8),
        ds0Bundle    (9)
        }

ProtectGroupCmdType ::= TEXTUAL-CONVENTION
    STATUS  current
    DESCRIPTION
            "This type define list of commands that the protection group should
            perform.
            lockout  (4) is specified according to protection technology and
            specific device solution.
            exercise (6) is a command to test if the APS communication is operating
            correctly

            Four commands:
            forcedSwitchWorkToProtect, forcedSwitchProtectToWork
            manualSwitchWorkToProtect, manualSwitchProtectToWork
            are simmilar to ApsSwitchCommand but each of them can be specified to
            either protection or to working."

    SYNTAX      INTEGER
        {
        none         (1),
        manualSwitch (2),
        forcedSwitch (3),
        lockout      (4),
        clear        (5),
        exercise     (6),
        forcedSwitchWorkToProtect  (7),
        forcedSwitchProtectToWork  (8),
        manualSwitchWorkToProtect  (9),
        manualSwitchProtectToWork (10)
        }

ProtectLastSwitchReasonType ::= TEXTUAL-CONVENTION
    STATUS current
    DESCRIPTION
            "This type specifies the last protection switch reason. The object
            should be updated by agent on each protection switch."
    SYNTAX      INTEGER
       {
        none            (1),
        cardRemoved     (2),
        cardFailed      (3),
        signalFailed    (4),
        signalDegraded  (5),
        portRecovered   (6),
        userInitiated   (7),
        oamFailed       (8),
        pwRecovered     (9),
        other           (255)
        }

ProtectionStateType ::= TEXTUAL-CONVENTION
    STATUS current
    DESCRIPTION
            "This type defines list of the Protection Member states.
            notApplicableStandalone (1) - protection is not applicable  because the Member
            is standalone or due to other
            reason.
            standbySecondary (2) - this value defines Protecting (Standby or
                Secondary) Member state.
            activePrimary (3) - this value defines Protected (Active or
            Primary) Member state."
    SYNTAX      INTEGER
        {
        notApplicableStandalone (1),
        standbySecondary        (2),
        activePrimary           (3)
        }

FileType ::= TEXTUAL-CONVENTION
    STATUS  current
    DESCRIPTION
     "This object represents the File Object Type.
     Possible Types and their representation are specified below:

         Type value     Represents
         ----------     ----------
            x           Unclassified file
            2x          Software File
            3x          Configuration File
            4x          License File
            5x          Boot File
            6x          Log File
            7x          XML File
            8x          User File

      File operation should use proper type value, i.e. one of the
      defined by the FileType enumeration.
      Using of the otherType (2) is not allowed when the type can be
      specified by another value from the list."
    SYNTAX  INTEGER
    {
    otherType               (2),  -- Other type or MAC Table and STAT collection that the agent will generate
    mainSw                  (21),
    backupSw                (22),
    moduleTypeSw            (23),
    swPack                  (24),
    startupConfig           (31),
    rollbackConfig          (32),
    userDefaultConfig       (33),
    factoryDefaultConfig    (34),
    runningConfig           (35),
    candidateConfig         (36),
    restorePointConfig      (37),
    license                 (41),
    mainBoot                (51),
    backupBoot              (52),
    alarmEventLog           (61),
    monitoringLog           (62), --  Trace log files
    xmlZeroTouch            (71),
    userFile                (81) -- files that are created by the user
    }


SlotType  ::= TEXTUAL-CONVENTION
    STATUS  current
    DESCRIPTION
    "This object indicates a unique number of the slot position in which
    the module is inserted.
    The Kilomux should use enumerated values starting with kmx."
    SYNTAX  INTEGER
    {
      psA    (1),
      psB    (2),
      clA    (3),
      clB    (4),
      io1    (5),
      io2    (6),
      io3    (7),
      io4    (8),
      io5    (9),
      io6    (10),
      io7    (11),
      io8    (12),
      io9    (13),
      io10   (14),
      io11   (15),
      io12   (16),
      io13   (17),
      io14   (18),
      io15   (19),
      psC    (20),
      fan    (21),
      ve     (22),    -- Virtual Engine Module
      kmxPsA (101),
      kmxPsB (102),
      kmxMlA (103),
      kmxMlB (104),
      kmxCl  (105),
      kmxOpt (106),
      kmxIO1 (107),
      kmxIO2 (108),
      kmxIO3 (109),
      kmxIO4 (110),
      kmxIO5 (111),
      kmxIO6 (112),
      kmxIO7 (113),
      kmxIO8 (114),
      kmxIO9 (115),
      kmxIO10(116),
      kmxIO11(117),
      kmxIO12(118),
      io1Ve   (125),
      io2Ve   (126),
      io3Ve   (127),
      io4Ve   (128),
      io5Ve   (129),
      io6Ve   (130),
      io7Ve   (131),
      io8Ve   (132),
      io9Ve   (133),
      io10Ve  (134),
      io11Ve  (135),
      io12Ve  (136),
      io13Ve  (137),
      io14Ve  (138),
      io15Ve  (139),
      notApplicable(255)
    }




CardType    ::= TEXTUAL-CONVENTION
      STATUS  current
      DESCRIPTION
      "This object indicates the card type assigned to the specific slot in
      the common configuration."

      SYNTAX  INTEGER
       {
  --
  -- General types
  --
  unknown        (1),
  empty          (2),

  -- Power Supply Modules
  --
  psAC           (10),
  psDC           (11),

  --
  -- Cl Modules
  --
        gCl1           (18),  -- IPmux1000 CL1
        gCl2           (19),  -- IPmux1000 CL2
        dCl            (20),
        kCl            (21),
        dcl2           (22),
        dcl2Eth        (23),
        kClEth         (24),
        dcl3           (25),
        dcl3Eth        (26),
        dcl4           (27),

  --
  -- T1/E1 Modules
  --
        d4T1           (28),
        d8T1           (29),
        dT1DSU         (30),
        dT1CSU         (31),
        dE1DSU         (32),
        dE1LTU         (33),
        dE1aDSU        (34),
        dE1aLTU        (35),
        dT1F           (36),
        dE1F           (37),
        d4E1           (38),
        d8E1           (39),

  --
  -- xDSL Modules

        dE1Hdsl        (40),  --Double Slot
        dT1Hdsl        (41),  --Double Slot
        dE1HdslS       (42),  --Single Slot
        dT1HdslS       (43),  --Single Slot
        d16gsdsl       (44),  --Single Slot, for DXC3000 only
        d8sl           (45),  --Single Slot
        d4slStuC       (46),  --Single Slot
        d4slStuR       (47),  --Single Slot

        -- KMUX Main Links
  --
  kML1           (50),
  kML2           (51),
  kML3           (52),
  kML4           (53),
  kML5           (54),
  kML6           (55),
  kML7           (56),
  kML8           (57),
  kML10          (59),
  kMLF           (60),
  kML10New       (61),
  kML11RJ45      (62),
  kML11FO        (63),

        --LS  Modules
  --
  kLS1           (70),
  kLS1New        (71),
  kLS2           (72),

        --LAN  Modules
  --
  kTRE           (80),
  kMBE           (81),
  kMBENew        (82),
  fLAN           (83), -- FCD STM LAN moudle

        --Optional  Modules
  --
  kai           (90),
  kdi           (91),
  kdiCH         (92),

  -- HS Modules
  --
  dHS2           (100),
  d8U            (101),
  d16U           (102),
  d4HS           (103),
  d8HS           (104),

  kHS1           (110),
  kHS2           (111),
  kHSU1          (112),
  kHSU2          (113),
  kHS703         (114),

  -- Voice Modules
  --
  kVC1EM         (130),
  kVC1FXO        (131),
  kVC1FXS        (132),
  kVC1MEM        (133),
  kVC1MFXO       (134),
  kVC1MFXS       (135),
  kVC1MFXSW      (136),
  kVC2EM         (137),
  kVC2FXO        (138),
  kVC2FXS        (139),
  kVC2s1EM       (140), --KVC2/1/E&M
  kVC2s1FXO      (141), --KVC2/1/FXO
  kVC2s1FXS      (142), --KVC2/1/FXS
  kVC3EM         (143),
  kVC3FXO        (144),
  kVC3FXS        (145),
  kVC3S0         (146),

  -- Fax Modules
  --
  kVF1EM            (170),
  kVF1FXO           (171),
  kVF1FXS           (172),
  kVF3EM            (173),
  kVF3FXO           (174),
  kVF3FXS           (175),
  kVF4EM            (176),
  kVF4FXO           (177),
  kVF4FXS           (178),
  kVF4FXSW          (179),
  kVF4S0            (180),
  kVF5PbxE1         (181),
  kVF5E1PbxSlave    (182),
  kVF5PbxT1         (183),
  kVF5T1PbxSlave    (184),
  kVF5PbxE1New      (185),
  kVF5E1PbxSlaveNew (186),
  kVF5PbxT1New      (187),
  kVF5T1PbxSlaveNew (188),
  kVF4FXO3          (189),
  kVF4FXS3          (190),
  kVF4NS0           (191),
  kVF6E1s16         (192), --KVF.6/E1/16
  kVF6E1s31         (193), --KVF.6/E1/31
  kVF6T1s12         (194), --KVF.6/T1/12
  kVF6T1s24         (195), --KVF.6/T1/24
  kVF8EM            (196),
  kVF8FXO           (197),
  kVF8FXS           (198),

  -- DIM Modules
  --
  dimETUR        (200),
  dimV35         (201),
  dimRS422       (202),
  dimRS530       (203),
  dimHssi        (204),
  dimX21         (205),
  dim10BaseT     (206),
  dimE1          (207),
  dim100         (208),

  --DACS T3/E3 Modules
  --
  dt3G747        (209),
  dt3            (210),
  dt3f           (211),
  de3            (212),
  de3f           (213),

  -- STM-1 Modules
  --
  dstm1s1        (214),  --DSTM1/1 Fractional
  dstm1s2        (215),  --DSTM1/2 Fractional + Redundancy
  fstm1          (216),  --FCD STM STM1 card
  dstm1          (217),  --DSTM1 Full
  dstm1R         (218),   --DSTM1 Full + Redundancy
  f2stm1         (219),   -- FCD STM 2 STM1 ports card
  gstm1          (220),   -- IPmux1000 (GMUX) STM-1 card
  goc3           (221),   -- IPmux1000 (GMUX) OC-3 card
  gstm1D         (222),   -- IPmux1000 (GMUX) STM-1 card    with 2 ports
  goc3D          (223),   -- IPmux1000 (GMUX) OC-3 card with 2 ports
  gChanOc3       (224),   -- Gmux-2000 Channelized OC-3 card
  gChanStm1      (225),   -- Gmux-2000 Channelized STM-1 card


  -- The following numbers are used in mdlSCardType, for LA modules:
  --
  -- laSUB          (230)
  -- laVEM          (231)
  -- laVFXO         (232)
  -- laVFXS         (233)
  -- laV11          (234)
  -- laV24          (235)
  -- laV35          (236)
  -- laT1           (237),
  -- laT1Vxx        (238),
  -- laE1           (239),
  -- laE1Vxx        (240),
  -- laISDN         (241),
  -- laVxx          (242),
  -- laEth          (243),
  -- laISDNwBU      (244),
  -- laIsdnNT       (245), LA-140 ISDN NT
  -- laIsdnNTwBU    (246), LA-140 ISDN NT with backup (lifeline bottom connector)
  -- laIsdnTE       (247), LA-140 ISDN TE
  -- laFXSwBU       (248), LA-140 FXS with backup (lifeline bottom connector)
  -- laFXSs         (249), LA-140 bottom row FXS
  -- laFXSwBUs      (250), LA-140 bottom row FXS with backup (lifeline Top port)
  -- laIsdnNTs      (251), LA-140 bottom row ISDN NT
  -- laIsdnNTwBUs   (252), LA-140 bottom row ISDN NT with backup (lifeline Top port)
  -- laIsdnTEs      (253), LA-140 bottom row ISDN TE
  -- laDp           (254), LA-140 bottom single data port X21/V35/RS50
  -- laSdsl         (255), LA-140 top SDSL port
  -- laSdslDp       (256), LA-140 top SDSL port with bottom X21 or V35 Data Port
  -- laAdslA        (257), LA-140 bottom ADSLA port
  -- laAdslADp      (258), LA-140 bottom ADSLA port with top X21 or V35 Data Port
  -- laAdslB        (259), LA-140 bottom ADSLB port
  -- laAdslBDp      (260), LA-140 bottom ADSLB port with top X21 or V35 Data Port
  -- laShdsl        (261), LA-140 bottom SHDSL port
  -- laShdslDp      (262), LA-140 bottom SHDSL port with top X21 or V35 Data Port
  -- laT1b          (263), LA-140 bottom T1 port
  -- laT1bDp        (264), LA-140 bottom T1 port with top data port
  -- laIsdnTEwBU    (265), LA-140 ISDN TE with backup
  -- laIsdnTEwBUs   (266), LA-140 bottom row ISDN TE with backup
  -- laShdsl4w      (267), LA-140 bottom 4 wires SHDSL port
  -- laShdsl4wDp    (268), LA-140 bottom 4 wires SHDSL port with top Data Port
  -- laEthSwitch    (269)  FCD-IPM

  -- Server Modules
  --
  serverE1          (270),   -- IPmux1000 (GMUX) Server E1 Card
  serverT1          (271),   -- IPmux1000 (GMUX) Server T1 Card
  serverE1Pw        (272),   -- Gmux2000 Server E1 PW Card
  serverT1Pw        (273),   -- Gmux2000 Server T1 PW Card


 -- GiGabit ETH Modules
  --
  gigabitEth        (280),   -- Gmux2000 Gigabit ETH Card
  gigabitEth2       (281),   -- Gmux2000 new Gigabit ETH Card - 2 GbE ports with SFP connector
  eth2              (282),   -- Gmux2000 new ETH Card - 2 ETH ports with RJ45 connectors (10/100/1000)
  gigabitEth8       (283),    -- Gmux2000 new Gigabit ETH Card   - 8 GbE ports with SFP connector
  eth8              (284),    -- Gmux2000 new ETH Card - 8 ETH ports with RJ45 connectors (10/100/1000)

-- CT3 Modules
  --
  channelizedT3Pw1  (290),   -- Gmux2000 Channelized T3 PW Card

  -- T1/E1 Modules
  --
  cesT128          (300),    -- Gmux2000 CES T1 28 ports (external T1 ports) card.
  cesE128          (301),    -- Gmux2000 CES E1 28 ports (external E1 ports) card.
  cesT1Pw28        (302),    -- Gmux2000 CES T1 PW ports (external T1 ports) card.
  cesE1Pw28        (303),    -- Gmux2000 CES E1 PW ports (external E1 ports) card.


  -- Vmux Modules
  --
  vmxE1VeDe   (310),     -- Gmux-2000 Vmux E1 card with external voice + external Data ports.
  vmxE1VeDi   (311),     -- Gmux-2000 Vmux E1 card with external voice + internal Data ports.
  vmxE1ViDe   (312),     -- Gmux-2000 Vmux E1 card with internal voice + external Data ports.
  vmxE1ViDi   (313),     -- Gmux-2000 Vmux E1 card with internal voice + internal Data ports.
  vmxT1VeDe   (314),     -- Gmux-2000 Vmux T1 card with external voice + external Data ports.
  vmxT1VeDi   (315),     -- Gmux-2000 Vmux T1 card with external voice + internal Data ports.
  vmxT1ViDe   (316),     -- Gmux-2000 Vmux T1 card with internal voice + external Data ports.
  vmxT1ViDi   (317),     -- Gmux-2000 Vmux T1 card with internal voice + internal Data ports.
  vc12E1UeNe  (318),   -- Gmux-2000 Vmux E1 card with 12 external User (voice) + 2 external Network (Data) ports.
  vc12E1UeNi  (319),   -- Gmux-2000 Vmux E1 card with 12 external User (voice) + 2 internal Network (Data) ports.
  vc12E1UiNe  (320),   -- Gmux-2000 Vmux E1 card with 12 internal User (voice) + 2 external Network (Data) ports.
  vc12E1UiNi  (321),   -- Gmux-2000 Vmux E1 card with 12 internal User (voice) + 2 internal Network (Data) ports.
  vc12T1UeNe  (322),   -- Gmux-2000 Vmux T1 card with 12 external User (voice) + 2 external Network (Data) ports.
  vc12T1UeNi  (323),   -- Gmux-2000 Vmux T1 card with 12 external User (voice) + 2 internal Network (Data) ports.
  vc12T1UiNe  (324),   -- Gmux-2000 Vmux T1 card with 12 internal User (voice) + 2 external Network (Data) ports.
  vc12T1UiNi  (325),   -- Gmux-2000 Vmux T1 card with 12 internal User (voice) + 2 internal Network (Data) ports.

-- New Vmux Card Types
--
  vca16E1UeNe  (326),   -- Gmux-2000 VCA E1 card with 16 external User (voice) + 2 external Network (Data) ports.
  vca16E1UeNi  (327),   -- Gmux-2000 VCA E1 card with 16 external User (voice) + 2 internal Network (Data) ports.
  vca16E1UiNe  (328),   -- Gmux-2000 VCA E1 card with 16 internal User (voice) + 2 external Network (Data) ports.
  vca16E1UiNi  (329),   -- Gmux-2000 VCA E1 card with 16 internal User (voice) + 2 internal Network (Data) ports.
  vca16T1UeNe  (330),   -- Gmux-2000 VCA T1 card with 16 external User (voice) + 2 external Network (Data) ports.
  vca16T1UeNi  (331),   -- Gmux-2000 VCA T1 card with 16 external User (voice) + 2 internal Network (Data) ports.
  vca16T1UiNe  (332),   -- Gmux-2000 VCA T1 card with 16 internal User (voice) + 2 external Network (Data) ports.
  vca16T1UiNi  (333),   -- Gmux-2000 VCA T1 card with 16 internal User (voice) + 2 internal Network (Data) ports.
  vca12E1UeNe  (334),   -- Gmux-2000 VCA E1 card with 12 external User (voice) + 2 external Network (Data) ports.
  vca12E1UeNi  (335),   -- Gmux-2000 VCA E1 card with 12 external User (voice) + 2 internal Network (Data) ports.
  vca12E1UiNe  (336),   -- Gmux-2000 VCA E1 card with 12 internal User (voice) + 2 external Network (Data) ports.
  vca12E1UiNi  (337),   -- Gmux-2000 VCA E1 card with 12 internal User (voice) + 2 internal Network (Data) ports.
  vca12T1UeNe  (338),   -- Gmux-2000 VCA T1 card with 12 external User (voice) + 2 external Network (Data) ports.
  vca12T1UeNi  (339),   -- Gmux-2000 VCA T1 card with 12 external User (voice) + 2 internal Network (Data) ports.
  vca12T1UiNe  (340),   -- Gmux-2000 VCA T1 card with 12 internal User (voice) + 2 external Network (Data) ports.
  vca12T1UiNi  (341),   -- Gmux-2000 VCA T1 card with 12 internal User (voice) + 2 internal Network (Data) ports.
  vmg16E1Ue    (342),   -- Gmux-2000 VMG (Media Gateway) E1 card with 16 external User ports
  vmg16E1Ui    (343),   -- Gmux-2000 VMG (Media Gateway) E1 card with 16 internal User ports
  vmg16T1Ue    (344),   -- Gmux-2000 VMG (Media Gateway) T1 card with 16 external User ports
  vmg16T1Ui    (345),   -- Gmux-2000 VMG (Media Gateway) T1 card with 16 internal User ports
  vmg12E1Ue    (346),   -- Gmux-2000 VMG (Media Gateway) E1 card with 12 external User ports
  vmg12E1Ui    (347),   -- Gmux-2000 VMG (Media Gateway) E1 card with 12 internal User ports
  vmg12T1Ue    (348),   -- Gmux-2000 VMG (Media Gateway) T1 card with 12 external User ports
  vmg12T1Ui    (349),   -- Gmux-2000 VMG (Media Gateway) T1 card with 12 internal User ports


--  ETX-5300A Cards Reservation

--  ETX-5300A Main Cards
  etx5Mc        (500),  -- ETX-5300A Main Card (MC) without Ethernet ports
  etx5Mc10Ge4   (501),  -- ETX-5300A Main Card (MC) with 4 10GE ports
  etx5McSfpPlus (502),  -- ETX-5300A Main Card (MC) with 4 SFP+ ports


--  ETX-5300A Power Supply and Fan Cards
  etx5Pim       (530),  -- ETX-5300A DC inlet, Power Inlet Module
  etx5Psu       (531),  -- ETX-5300A AC inlet, Power Supply Unit
  etx5Fan       (532),  -- ETX-5300A Fan tray module

--  ETX-5300A IO Cards

--  ETX-5300A Ethernet IO Cards
  etx5Gbe20Sfp   (540),  -- ETX-5300A Ethernet IO with 20 GbE ports and SFP connectors
  etx5Gbe20Utp   (541),  -- ETX-5300A Ethernet IO with 20 GbE ports and UTP (twisted pair) connectors

  etx5Io10Gb2Xfp (550),  -- ETX-5300A Ethernet IO with 2 10GbE ports and XFP connector

--  ETX-5300A TDM IO Cards
    -- STM1/OC3 Cards
  etx5cTdmStm1E1 (600),  -- ETX-5300A TDM IO supporting 4 STM-1 E1 interfaces
  etx5cTdmStm1T1 (601),  -- ETX-5300A TDM IO supporting 4 STM-1 T1 interfaces
  etx5cTdmOc3    (602),  -- ETX-5300A TDM IO supporting 4 OC-3 T1 interfaces

    -- STM4/OC12 Cards
  etx5cTdmStm4E1 (603),  -- ETX-5300A TDM IO supporting 1 STM-4 E1 interfaces
  etx5cTdmOc12   (604),  -- ETX-5300A TDM IO supporting 1 OC-12 T1 interfaces


--********************************************
-- The Range 10000is reserved for MP products
--********************************************

         mpUnknown        (10001),
         mpEmpty          (10002),

  -- (10003)..(10007) are reserved ; they appear in the compress structure

         acm            (10009), --alarm module
  --
  -- Power Supply Modules
  --
        ps60W          (10010),
        ps100W         (10011),
   -- (10012)..(10016) are reserved for the Programmed PS cards
        ps             (10017),

  --
  -- Cl Modules
  --
        cl1            (10020),
        clEth          (10021),
        cl2            (10022),
        cl2Eth         (10023),
        cl3            (10024),
        cl3Eth         (10025),
        cl1Clk         (10026), --CL1 with Station Clock (for LRS102)
  --
  -- Packet Cards of Megaplex
  --
        mPh1            (10031),
        mPh3            (10032),
        mPh1T1DSU       (10033),
        mPh1T1CSU       (10034),
        mPh1E1DSU       (10035),
        mPh1E1LTU       (10036),

  -- TDM Cards

        mtmlFT1         (10037),
        mtmlFE1         (10038),
        mtmlH4E1        (10039),
        mtmlH4E12W      (10040),
        mtmlH4T1        (10041),
        mtmlH4T12W      (10042),
        mtHsh4E1        (10043),
        mtHsh4E12W      (10044),
        mtHsh4T1        (10045),
        mtHsh4T12W      (10046),
        mtmlH2E1        (10047),
        mtmlH2E12W      (10048),
        mtmlH2T1        (10049),
        mtmlH2T12W      (10050),
        hsh2E1          (10051),
        hsh2E12W        (10052),
        hsh2T1          (10053),
        hsh2T12W        (10054),
        mlIp            (10055),
        mtml4Ip         (10056),
        ml20N1          (10057),
        ml20N2          (10058),

  -- Packet Cards of Megaplex

        mPl6            (10060),
        mPl3            (10061),

  -- VF cards of Megaplex
        vf24T1          (10062),
        vf30E1          (10063),
        vf48T1          (10064),
        vf60E1          (10065),

  -- Vmux-2100 Main Link cards
        ml2E1           (10068),
        ml4E1           (10069),
        ml2T1           (10070),
        ml4T1           (10071),

        mPv4            (10072),
  --
  -- TDM Cards
  --
      vc16A             (10073),
      vc8EandM          (10074),
      vc8Fxo            (10075),
      vc8Fxs            (10076),
      vc16EandM         (10077),
      vc16Fxo           (10078),
      vc16Fxs           (10079),

      vf3EandM          (10080),
      vf3Fxs            (10081),
      vf3Fxo            (10082),

      vfPbx             (10083),
      vfPbxT1           (10084),
      vfPbxE1           (10085),

      mtMlE2S           (10086), --Single Link
      mtMlE2D           (10087), --Dual Link
      mtMlF2T1          (10088),
      mtMlF2E1          (10089),
      mtMlT1Fiber       (10090),
      mtMlE1Fiber       (10091),
      mtMlT1FiberFb     (10092),
      mtMlE1FiberFb     (10093),
      mtmlHE1           (10094),
      mtmlH1E1          (10095),
      mtmlHSE1          (10096),
      ml20              (10097),
      mtMl4T1           (10098),
      mtMl4E1           (10099),

      mtMl1T1DSU       (10100),
      mtMl1T1CSU       (10101),
      mtMl1E1DSU       (10102),
      mtMl1E1LTU       (10103),
      mtMl1T1DSUfb     (10104),
      mtMl1T1CSUfb     (10105),
      mtMl1E1DSUfb     (10106),
      mtMl1E1LTUfb     (10107),
      mtMl2T1          (10108),
      mtMl2E1          (10109),

      ls2CcittX50     (10110),
      ls2CcittX58     (10111),
      ls2ATandTSdm    (10112),
      ls2ACcittX50    (10113),
      ls2ACcittX58    (10114),
      ls2AATandTSdm   (10115),
      ls2A2Ts         (10116),
      ls2M            (10117),

      mtMlT1           (10118),
      mtMlE1           (10119),

       hs2             (10120),
       hs3             (10121),
       hsq             (10122),
       hs703           (10123),
       hsQM            (10124),
       hsqN            (10125),
       hs6             (10126),
       hs12            (10127),
       hsDp            (10128),
       hsp             (10129),

       hs4T1           (10130),
       hs4E1           (10131),
       hs4             (10132),
       hsEth           (10133),

       ml8T1           (10134),
       ml8E1           (10135),

  --  Vmux-2100  Voice cards
       vc2E1           (10136),
       vc4E1           (10137),
       vc2T1           (10138),
       vc4T1           (10139),

       vc2EandM        (10140),
       vc2Fxs1Plar     (10141),
       vc2Fxo1         (10142),
       vc2Fxs2         (10143),
       vc2Fxo2         (10144),
       vc2Fxs3         (10145),
       vc2Fxo3         (10146),
       vc26EandM       (10147),
       mtvc2           (10148),
       vc2R2Fxs        (10149),

       hsu             (10150),

       mbeA            (10151),
       mbeB            (10152),
       mbeU            (10153),
       tre             (10154),

       hsuI            (10155),
       hsr             (10156),
       hss             (10157),
       hsu1            (10158),

       ls12            (10159),
       ls6             (10160),
       ls6V1EandM      (10161),
       ls6V1Fxo        (10162),
       ls6V1Fxs        (10163),
       ls6V2EandM      (10164),
       ls6V2Fxo        (10165),
       ls6V2Fxs        (10166),
       ls6VfEandM      (10167),
       ls6VfFxo        (10168),
       ls6VfFxs        (10169),

       vc3EandM        (10170),
       vc3Fxo          (10171),
       vc3Fxs          (10172),

       vcPbx           (10173),
       vcPbxT1         (10174),
       vcPbxE1         (10175),

       vc6EandM        (10176),
       vc6Fxo          (10177),
       vc6Fxs          (10178),

       vcq             (10179),

       ls6n            (10180),

  --
  -- Packet Cards of MAXcess and Hybrid
  --

        -- High speed cards

        mhs1V36          (10181),
        mhs1V35          (10182),
        mhs1G703         (10183),
        mhs1DDS          (10184),
        mhs3             (10185),
        mhs1X21          (10186),
        mhs1V24          (10187),
        mhs4             (10188),
        mhsE1Hs          (10189),
        mhsT1Hs          (10190),
        mhsHyE1Hs        (10191), -- 2 HS ports + 1 Hybrid E1 port
        mhsHyT1Hs        (10192), -- 2 HS ports + 1 Hybrid T1 port
        mlfHybE1Hs       (10193), -- Fiber Optic Hybrid: 2 HS + 1 Hybrid E1 port
        mlfHybT1Hs       (10194), -- Fiber Optic Hybrid: 2 HS + 1 Hybrid T1 port

        -- T1/E1 cards

        mhs2e1           (10195),
        mhs2t1           (10196),
        mhsHy2e1         (10197), -- 2 Hybrid E1 ports
        mhsHy2t1         (10198), -- 2 Hybrid T1 ports
        mlfHybE12        (10199), -- Fiber Optic Hybrid: 2 E1 ports

        -- Low speed cards

        mls6             (10200),
        mls3             (10201),

        -- More  T1/E1 cards

        mlHybAtmE1       (10202), -- Hybrid ATM E1
        mlHybAtmT1       (10203), -- Hybrid ATM T1
        mlfHybT12        (10204), -- Fiber Optic Hybrid: 2 T1 ports

        --  Voice cards

        mvc8             (10205), -- MVC-8 name in marketing: MVC-4N
        mvc8PbxE1        (10206),
        mvc8PbxT1Dsu     (10207),
        mvc8PbxT1Csu     (10208),
        mvc8PbxE1Slave   (10209),

        mvc4             (10210),
        mvc4PbxE1        (10211),
        mvc4PbxT1Dsu     (10212),
        mvc4PbxT1Csu     (10213),
        mvc4PbxE1Slave   (10214),
        mvc4PbxT1Slave   (10215),

        mvc8PbxT1Slave   (10216),   -- MVC-8 T1 Slave is here
        mvc8ExtAnalog    (10217), -- MVC-8 with 8 External ports
        mvcE1            (10218), -- 8 External ports & 30 Internals
        mvcT1            (10219), -- 8 External ports & 24 Internals

        -- ISDN for Maxcess
        mhsS             (10220),
        mhsU             (10221),
        mhsPriE1         (10222),
        mhsPriT1         (10223),

        --Card of MP-2100/4
        hsEthSwitch      (10224),

        -- CCS for Maxcess & MPH
        mPriE1FramerCcs  (10225),
        mPriT1FramerCcs  (10226),
        mPriE1SlaveCcs   (10227),
        mPriT1SlaveCcs   (10228),
        mDualBri         (10229),

        --Voice cards for MP
        vc12EandM        (10230),
        vc12Fxo          (10231),
        vc12Fxs          (10232),
        vc6aEandM        (10233),
        vc6aFxo          (10234),
        vc6aFxs          (10235),
        vc6AgFxo         (10236),
        vc6AgFxs         (10237),
        vc6a4LB          (10238),

        --Video card for MP
        vid              (10239),

        --ISDN cards for MP
        hsu12            (10240),
        hsu6             (10241),
        hss12            (10242),
        hss6             (10243),

        -- MPH and MP-2100/4 cards
        hsDp3            (10244),
        hsDp6            (10245),

        -- MP-2100/4 card
        hsf1             (10246),

        -- More Hybrid cards + IP cards for MPH
        mhsHyE1          (10247),   -- 1 Hybrid E1 port
        mhsHyT1          (10248),   -- 1 Hybrid T1 port
        mhsIp            (10249),   -- 1 Eth  port + 1 HS port
        mlIpHs           (10250),   -- 1 Eth  port + 3 HS ports
        mlHybIpE1        (10251),   -- 1 Eth  port + 1 HS port + 1 E1
        mlHybIpT1        (10252),   -- 1 Eth  port + 1 HS port + 1 T1

        -- VOIP cards for MPH & MX
        mvg1Lan          (10253),
        mvg2Lan          (10254),

        -- MP-2100/4 card
        vc4Fxs           (10255),
        vc4EandM         (10256),
        vc4Fxo           (10257),
        hsf2             (10258),

        -- More VOIP cards for MPH
        mvgSwitch4Lan    (10260),

        --SHDSL cards of Megaplex / LRS-102
        msl4E1W2           (10261),
        msl4E1W4           (10262),
        msl8E1W2           (10263),
        msl4E1W2Eth        (10264),
        msl8E1W2Eth        (10265),
        asmi54cE1AndEth    (10266), -- & LRS-102 (10E1 & ETH, New HW)
        asmi54cT1AndEth    (10267), -- & LRS-102 (10T1 & ETH, New HW)
        asmi54c            (10268), -- & LRS-102 (10ETH only)
        asmi54cE1AndEthPF  (10269), -- LRS-102 only (10E1 & ETH, SHDSL Power Feeding, New HW)
        asmi54cE1PF        (10270), -- LRS-102 only (10E1, SHDSL Power Feeding, New HW)

        --HS cards of Megaplex
        hs6N             (10271),
        hs12N            (10272),
        hsNRZ            (10273),

       -- Vmux 2100 Enhanced Voice Cards
       evc2E1            (10281),
       evc4E1            (10282),
       evc2T1            (10283),
       evc4T1            (10284),

   --  Vmux-2200  Voice cards
       vc2E1Pri          (10285),
       vc4E1Pri          (10286),

   --  MP Voice cards
       vc4OmniEandM      (10291),
       vc4OmniWestern    (10292),

   --  MP-4100 and/or LRS-102 cards
       clx1              (10301),
       clx1GbE           (10302),
       clx1S155          (10303),
       clx1S155GbE       (10304),
       ml8T1Eth          (10305),
       ml8E1Eth          (10306),
       op106cEth         (10307),   --no external T1
       op108cEth         (10308),   --no external E1
       op106cEthT1       (10309), --with external T1 (10used also by LRS-102)
       op108cEthE1       (10310), --with external E1 (10used also by LRS-102)
       op108cEthE1Unbal  (10311),   --used only by LRS-102
       mpw1              (10312),
       op34c             (10313), --no external E1
       op25c             (10314), --no external T1
       op34cE1           (10315), --with external E1 (10used also by LRS-102)
       op25cT1           (10316), --with external T1 (10used also by LRS-102)
       m16e1             (10317),
       m16t1             (10318),
       op108cE1Unbal     (10319),  --used only by LRS-102

  -- VFS cards of Megaplex
        vfs24T1          (10321),
        vfs30E1          (10322),
        vfs48T1          (10323),    --2T1
        vfs60E1          (10324),  --2E1

-- MiniCVS cards
        mm4E1            (10325),
        mm4T1            (10326),
        mm8E1            (10327),
        mm8T1            (10328),
        mm12E1           (10329),
        mm12T1           (10330),
        mm16E1           (10331),
        mm16T1           (10332),


-- More MP-4100 / LRS-102  SDHSL Cards
        asmi54cE1N        (10340), -- E1 only New Hardware
        asmi54cN          (10341), -- ETH only New Hardware
        asmi54cHsN        (10342), -- V.35 only (10HighSpeed) New Hardware
        asmi54cHsAndEthN  (10343), -- ETH & V.35 (10HighSpeed) New Hardware

--MP4100 R3.0 cards
       cl2n              (10350), --CL.2
       cl2GbE            (10351), --CL.2-GbE
       cl2s622           (10352), --CL.2-622
       cl2s622GbE        (10353), --CL.2-622GbE
       cl2s622GbEa       (10354), --CL.2-622GbE/a with Advanced ETH features

--MP4100 R4.9 cards
       vsG703            (10360), --VS G703


-- ETX-2XX Cards family

       eth2GF             (11000),  -- 2 Gb Eth ports full card

       hwRouterEthActive    (11050),  -- HW Router Card with Eth port Active
       hwRouterEthNotActive (11051),  -- HW Router Card with Eth port NOT Active


       sHDSL4W            (11100),  -- SHDSL 4 Wire Card
       sHDSL8W            (11101),  -- SHDSL 8 Wire Card

       vdsl24WPots        (11110),  -- VDSL2 4 pairs card with POTS filter
       vdsl24WIsdn        (11111),  -- VDSL2 4 pairs card with ISDN filter

       e1T14F             (11200),  -- PDH 4 port E1 T1  full card
       e1T18F             (11201),  -- PDH 8 port E1 T1  full card
       t31                (11202),  -- PDH 1 port T3 card
       t32                (11203),  -- PDH 2 port T3 card


   --  ETX-2XX Power Supply
       externalPS         (11300),  -- External Power Supply
       inletPSAC          (11301),  -- Inlet Power Supply AC
       inletPSDC          (11302)  -- Inlet Power Supply DC

    }




RadTransportAddressType ::= TEXTUAL-CONVENTION
    STATUS      current
    DESCRIPTION
    "A value that represents a transport domain. This is the
     enumerated version of the transport domain registrations
     in this MIB module. It was added in RAD MIB due to the fact
     that it is not defined in Standard MIB.
     The enumerated values have the following meaning:

     unknown(0)     unknown transport address type
     efmOam (1)     radTransportDomainSnmpEfmOam

     This textual convention can be used to represent transport
     domains in situations where a syntax of TransportDomain is
     unwieldy (for example, when used as an index).

     The usage of this textual convention implies that additional
     transport domains can only be supported by updating this MIB
     module."
    SYNTAX  INTEGER
            {
            unknown(0),
            efmOam (1)
            }

RadTransportAddressEfmOam ::= TEXTUAL-CONVENTION
    STATUS      current
    DESCRIPTION
        "Represents a transport address consisting of an EFM OAM port number."
    SYNTAX      OCTET STRING (SIZE (4))


RadEntityType   ::= TEXTUAL-CONVENTION
    STATUS      current
    DESCRIPTION
    "This object define the entity types."
    SYNTAX  INTEGER
         {
         mep               (1),
         rmep              (2),
         destne            (3),
         ospfNeighbor      (4),
         oamCfmService     (5),
         flow              (6),
         twampSession      (7),
         twampPeer         (8),
         portAndQueueBlock (9)
         }


AlarmForwardingCause   ::= TEXTUAL-CONVENTION
    STATUS      current
    DESCRIPTION
        "Bit map representing possible causes for fault propagation.
         Multiple bits may be set if more than one condition leads to fault propagation."
     SYNTAX   BITS
     {
     los                 (0),  -- LOS received
     ais                 (1),  -- AIS received
     rdi                 (2),  -- RDI received
     protocolDown        (3),  -- Underlying protocol failed
     oamSignalingEfm     (4),  -- OAM EFM signaling received
     oamSignalingCfm     (5),  -- OAM CFM signaling received
     interfaceStatusTlv  (6),  -- OAM CFM interface status TLV received
     oamCfmRdi           (7),  -- OAM CFM RDI received
     oamCfmAis           (8),  -- OAM CFM AIS received
     rlol                (9),  -- RLOL received
     pPPoEFail           (10), -- PPPoE failed
     belowMinimumMembers (11), -- Number of group members below minimum
     allLinksDown        (12), -- All group links failed
     allRemoteMepsFailed (13), -- All remote MEPs failed
     routerInterfaceDown (14), -- Underlying router interface failed
     bfdSessionDown      (15), -- Underlying BFD session failed
     oamCfmCsfClos       (16), -- OAM CFM CSF (C-LOS status) received
     outOfSequence       (17), -- Out of sequence pattern received
     unavailable         (18),  -- Element triggering fault propagation becomes unavailable
     txDisableSignal     (19), -- Tx-disable hardware signal received from PHY
     txFaultSignal       (20)  -- Tx-fault hardware signal received from PHY
     }

-----------------------------------
-- Test Textual Conventions
-----------------------------------

RadTestPbitValues   ::= TEXTUAL-CONVENTION
    STATUS  current
    DESCRIPTION
    "This TC is used for configuring a set of P-bit values."
    SYNTAX      BITS
    {
    pbit0Val    (0),
    pbit1Val    (1),
    pbit2Val    (2),
    pbit3Val    (3),
    pbit4Val    (4),
    pbit5Val    (5),
    pbit6Val    (6),
    pbit7Val    (7)
    }

RadTestResult   ::= TEXTUAL-CONVENTION
    STATUS  current
    DESCRIPTION
    "This TC is used to indicate a test outcome."
    SYNTAX      INTEGER
    {
    notApplicable     (1),
    passed            (2),
    failed            (3),
    userAborted       (4),
    systemAborted     (5),
    llFailure         (6)
    }

END
