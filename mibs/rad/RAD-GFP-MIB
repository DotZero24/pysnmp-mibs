RAD-GFP-MIB DEFINITIONS ::= BEGIN


-- It is RAD's intent to encourage the widespread use of
-- this Specification in connection with the management of
-- RAD products. RAD grants vendors, end-users,
-- and other interested parties a non-exclusive license to
-- use this Specification in connection with the management
-- of RAD products.

-- This Specification is supplied "as is," and RAD makes
-- no warranty, either express or implied, as to the use,
-- operation, condition, or performance of the Specification.


IMPORTS

       ifAlias, ifIndex     FROM  IF-MIB
       Unsigned32, OBJECT-TYPE, MODULE-IDENTITY,
       NOTIFICATION-TYPE     FROM  SNMPv2-SMI
       agnt     FROM  RAD-SMI-MIB
       alarmEventLogSourceName, alarmEventLogAlarmOrEventId, alarmEventLogDescription,
       alarmEventLogSeverity, alarmEventLogDateAndTime, alarmEventReason     FROM  RAD-GEN-MIB;

	gfp MODULE-IDENTITY
		LAST-UPDATED "201502191801Z"  -- February 19, 2015
        ORGANIZATION "RAD Data Communications Ltd."
        CONTACT-INFO
        "System Department

         Email:  mibs@rad.com
         Postal: RAD Data Communications Ltd.
                 24 Raoul Wallenberg St.
                 Tel-Aviv 6971920
                 Israel

         Phone:  +972-3-645-5421
         Fax:    +972-3-760-7844"
         DESCRIPTION
            "Generic Framing Procedure (GFP) MIB."
	::= { agnt 55 }

gfpEvents OBJECT IDENTIFIER  ::= {gfp 0}


gfpCnfgTable OBJECT-TYPE
    SYNTAX  SEQUENCE OF GfpCnfgEntry
    MAX-ACCESS  not-accessible
    STATUS  current
    DESCRIPTION
    "Configuration table for GFP (General Framing Protocol)."
::= {gfp 1}

gfpCnfgEntry OBJECT-TYPE
    SYNTAX  GfpCnfgEntry
    MAX-ACCESS  not-accessible
    STATUS  current
    DESCRIPTION
    "An entry in the GFP configuration table."
     INDEX  { ifIndex, gfpCnfgIdx }
    ::= { gfpCnfgTable 1 }

GfpCnfgEntry ::= SEQUENCE {
    gfpCnfgIdx             Unsigned32,
    gfpPayloadFcs          INTEGER,
    gfpRxTxScramble        INTEGER,
    gfpVcatHeader   INTEGER
 }

gfpCnfgIdx  OBJECT-TYPE
    SYNTAX       Unsigned32
    MAX-ACCESS   not-accessible
    STATUS       current
    DESCRIPTION
    "Index to GFP configuration table."
    ::= { gfpCnfgEntry 1 }

gfpPayloadFcs  OBJECT-TYPE
    SYNTAX     INTEGER
	{
	 disable   (2),
     enable    (3)
    }
	MAX-ACCESS read-write
    STATUS       current
    DESCRIPTION
    "This object defines whether protocol header will
    include FCS."
    ::= { gfpCnfgEntry 2 }


gfpRxTxScramble OBJECT-TYPE
    SYNTAX    INTEGER
	{
	 noScramble     (1),
     rxTxScramble   (2),
     rxOnlyScramble (3),
	 txOnlyScramble	(4)
    }
	MAX-ACCESS read-write
    STATUS       current
    DESCRIPTION
    "This object defines whether transmission will be scrambled."
    ::= { gfpCnfgEntry 3 }

gfpVcatHeader  OBJECT-TYPE
      SYNTAX INTEGER
      {
       notApplicable (1),
       disable       (2),
       enable        (3)
 	  }
      MAX-ACCESS read-write
      STATUS current
      DESCRIPTION
      "VCAT header is LCAS  CONTROL packet as described in the G-7043.
       one control packet is transmitted in a period of 16 Multi frame"
      ::= { gfpCnfgEntry 4}

----------------------------------------------------------
-- Generic Framing Procedure (GFP) Common Trap Definitions
----------------------------------------------------------

-- LOSS OF FRAME (LOF)
gfpLof  NOTIFICATION-TYPE
	OBJECTS { alarmEventLogSourceName, alarmEventLogAlarmOrEventId, alarmEventLogDescription,
     alarmEventLogSeverity, alarmEventLogDateAndTime, alarmEventReason,
     ifAlias }
      STATUS  current
      DESCRIPTION
	  "This trap indicates that a Loss of Frame (LOF) was detected on a GFP interface.
      "
	  ::= { gfpEvents 1 }

-- CLIENT SIGNAL FAIL
gfpCsf  NOTIFICATION-TYPE
	OBJECTS { alarmEventLogSourceName, alarmEventLogAlarmOrEventId, alarmEventLogDescription,
     alarmEventLogSeverity, alarmEventLogDateAndTime, alarmEventReason,
     ifAlias }
      STATUS  current
      DESCRIPTION
	  "This trap indicates that a client signal failure (CSF) in a data frame was detected
	   on a GFP interface.
      "
	  ::= { gfpEvents 2 }





END
